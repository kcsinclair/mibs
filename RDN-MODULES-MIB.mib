-- *****************************************************************
-- RDN-MODULES-MIB.mib:
-- Motorola BSR's Modules Definitions MIB
--
-- Copyright (C) 2001, 2008 by Motorola, Inc.
-- All rights reserved.
-- *****************************************************************
RDN-MODULES-MIB DEFINITIONS ::= BEGIN

    IMPORTS
        MODULE-IDENTITY
            FROM SNMPv2-SMI
        rdnDefinitions
            FROM RDN-DEFINITIONS-MIB;

    -- riverdelta modules definitions mib module

    rdnModules MODULE-IDENTITY
        LAST-UPDATED "200808080000Z" -- August 8, 2008
        ORGANIZATION "Motorola"
        CONTACT-INFO "Motorola
                      Customer Service
                      101 Tournament Drive
                      Horsham, PA 19044
                      US Tel: +1 888 944 4357
                      Int Tel: +1 215 323 0044
	              Fax: +1 215 323 1502
                      Email: CPSSupport@Motorola.com"
        DESCRIPTION
                "MIB module for Motorola Module
                definitions.

		Copyright (C) 2001, 2008 by Motorola, Inc.
	     	All rights reserved."


	REVISION "200808080000Z"  -- 08 August 2008
	DESCRIPTION
		"Added Copyright Statement into MIB modules's
	       	 description."	
        REVISION     "200311050000Z"
        DESCRIPTION
                "+ Updated the CONTACT-INFO.
	         + Reorder REVISION/DESCRIPTION in required 
                   reverse chronological order."
        REVISION     "200304290000Z"
        DESCRIPTION
                "This `corrects past mistakes' where ASN.1 allowed hyphens
	         but SMIv2 states that hyphens are not allowed in 
	         identifiers for objects or for labels on
	         enumerated integer values. 
		
	         Hyphens where removed from object identifiers in this MIB.

                 Also cleans up the CONTACT-INFO."
        REVISION     "200104180000Z"
        DESCRIPTION
                "Initial creation."
        ::= { rdnDefinitions 4 }


      --
      -- module definitions for all riverdelta modules
      --

      rdnModulesUnknown OBJECT-IDENTITY 
           STATUS        current
	   DESCRIPTION
	      "This object ID is used to identify an
	       unknown Module." 
	   ::= { rdnModules 0 }

      rdnModulesSrm OBJECT-IDENTITY
	   STATUS        current
	   DESCRIPTION
	      "This object ID is used to identify the Motorola,
	       SRM Module." 
           ::= { rdnModules 1 }

      rdnModulesCmts OBJECT-IDENTITY
           STATUS        current
	   DESCRIPTION
	       "This object ID is used to identify the Motorola,
                CMTS Module."
	   ::= { rdnModules 2 }

      rdnModulesHsim2 OBJECT-IDENTITY
	   STATUS        current
	   DESCRIPTION
	       "This object ID is used to identify the Motorola,
	        HSIM2 Module." 
	   ::= { rdnModules 3 }

      rdnModulesHsim2PosEth OBJECT-IDENTITY
	   STATUS        current
	   DESCRIPTION
	      "This object ID is used to identify the Motorola,
	       HSIM2 Module with one POS port and one fast ethernet port."
	   ::= { rdnModules 4 }

      rdnModulesHsim2Pos2 OBJECT-IDENTITY
	   STATUS        current
	   DESCRIPTION
	      "This object ID is used to identify the Motorola,
	       HSIM2 Module with two POS ports."
	   ::= { rdnModules 5 }

      rdnModulesHsim2PosOc48 OBJECT-IDENTITY
	   STATUS        current
	   DESCRIPTION
	      "This object ID is used to identify the Motorola,
	       HSIM2 Module with one OC48 port."
	   ::= { rdnModules 6 }

      rdnModulesHsim2PosDoc48 OBJECT-IDENTITY
	   STATUS        current
	   DESCRIPTION
	      "This object ID is used to identify the Motorola,
	       HSIM2 Module with two OC48 ports."
	   ::= { rdnModules 7 }

      rdnModulesHsim2PosAtm OBJECT-IDENTITY 
	   STATUS        current
	   DESCRIPTION
	      "This object ID is used to identify the Motorola,
	       HSIM2 Module with one ATM port."
           ::= { rdnModules 8 }

      rdnModulesHsim2Eth8 OBJECT-IDENTITY
	   STATUS        current
	   DESCRIPTION
	      "This object ID is used to identify the Motorola,
	       HSIM2 Module with eight fast ethernet ports."
	   ::= { rdnModules 9 }

      rdnModulesHsim2Gige OBJECT-IDENTITY 
	   STATUS        current
	   DESCRIPTION
	      "This object ID is used to identify the Motorola,
	       HSIM2 Single Mode GigE Module with one GIGE port."
           ::= { rdnModules 10 }

      rdnModulesOsr OBJECT-IDENTITY 
	   STATUS        current
	   DESCRIPTION
	      "This object ID is used to identify the Motorola
	       OSR."
           ::= { rdnModules 11 }

      rdnModulesBsr1000 OBJECT-IDENTITY
	   STATUS        current
	   DESCRIPTION
	      "This object ID is used to identify the Motorola
	       BSR 1000."
	   ::= { rdnModules 12 }


      rdnModulesHsim2GigeMM OBJECT-IDENTITY
           STATUS        current
           DESCRIPTION
              "This object ID is used to identify the Motorola,
               HSIM2 Multimode GigE Module with one GigE port."
           ::= { rdnModules 13 }


      rdnModulesHsim4GigeEth8 OBJECT-IDENTITY
  	   STATUS        current
       	   DESCRIPTION
              "This object ID is used to identify the Motorola,
               HSIM4 Module with eight fast ethernet ports and 
	       two GigE ports."
           ::= { rdnModules 15 }

END
