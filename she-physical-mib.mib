--
-- she-physical-mib.mib
-- MIB generated by MG-SOFT Visual MIB Builder Version 6.0  Build 88
-- Wednesday, June 17, 2009 at 12:10:34
--

-- Start of ClearCase branch-information of current release:
-- she-physical-mib.mib   /main/she_main_grf/35
-- End of ClearCase branch-information.

	SHE-PHYSICAL-MIB DEFINITIONS ::= BEGIN
 
		IMPORTS
			she			
				FROM AN-MIB			
			entPhysicalIndex, PhysicalIndex			
				FROM ENTITY-MIB			
			ifIndex, ifAdminStatus, ifOperStatus, InterfaceIndex			
				FROM IF-MIB			
			sheAlarmTimeAndDate, sheAlarmReportingSource, sheAlarmReportingSourceType, sheAlarmSeverity, SheAlarmSevProfileIndex			
				FROM SHE-ALARMING-MIB			
			SheControlStatusType, SheAdminStateType, ShePermissionType			
				FROM SHE-TC-MIB			
			SnmpAdminString			
				FROM SNMP-FRAMEWORK-MIB			
			OBJECT-GROUP, MODULE-COMPLIANCE, NOTIFICATION-GROUP			
				FROM SNMPv2-CONF			
			Integer32, Unsigned32, OBJECT-TYPE, MODULE-IDENTITY, NOTIFICATION-TYPE			
				FROM SNMPv2-SMI			
			DisplayString, TruthValue, TEXTUAL-CONVENTION			
				FROM SNMPv2-TC;
	
	
		shePhysical MODULE-IDENTITY 
			LAST-UPDATED "200906171000Z"		-- June 17, 2009 at 10:00 GMT
			ORGANIZATION 
				"Nokia Siemens Networks"
			CONTACT-INFO 
				"gerd Barchmann
				COO BBA DSLAM RD SDE
				
				gerd.barchmann@nsn.com
				+49 3834 555 654"
			DESCRIPTION 
				"The MIB module for representing multiple logical
				entities for the SHE Equipment management."
			REVISION "200503091000Z"		-- March 09, 2005 at 10:00 GMT
			DESCRIPTION 
				"Change PIU-Types for Modules"
			REVISION "200503161000Z"		-- March 16, 2005 at 10:00 GMT
			DESCRIPTION 
				"New notifications for shePhysCardPlugged and sheEntPhysCardUnplugged.
				Add shePhysPortUserLabel to portTable and corresponding control-group."
			REVISION "200503181000Z"		-- March 18, 2005 at 10:00 GMT
			DESCRIPTION 
				"Change PIU-Types  for acceptable cards again (without M:).
				Change syntax for UserLabel in shePhysPortTable to OctetString (0..40)."
			REVISION "200503301138Z"		-- March 30, 2005 at 11:38 GMT
			DESCRIPTION 
				"Correct typo for shePhysContainerAccCardTypes."
			REVISION "200504211548Z"		-- April 21, 2005 at 15:48 GMT
			DESCRIPTION 
				"Add PIU-Types for infineon based IUADSL:72 and
				CXU_C to shePhysContainerAccCardTypes.
				Change syntax for all ControlTimeStamp to U32 and unit sec."
			REVISION "200505181043Z"		-- May 18, 2005 at 10:43 GMT
			DESCRIPTION 
				"Change description for shePhysCardProtDynamicRole."
			REVISION "200505301428Z"		-- May 30, 2005 at 14:28 GMT
			DESCRIPTION 
				"Add external alarms to shePhysShelfAlarm-notificationgroup.
				Add configuration and status entrys for external alarm inputs 
				and outputs to shePhysShelfTable and shePhysShelfControl-group.
				Add new configuration request and result event for this external
				alarm configuration's."
			REVISION "200506061036Z"		-- June 06, 2005 at 10:36 GMT
			DESCRIPTION 
				"Add new attribute to configure special redundancy features for CXU."
			REVISION "200506221010Z"		-- June 22, 2005 at 10:10 GMT
			DESCRIPTION 
				"Add new trap shePhysRedundancyFeatureModified.
				Change syntax for shePhysCardTemperatureCurrent to integer.
				Add enum value for default shePhysCardUpgradeState."
			REVISION "200508101557Z"		-- August 10, 2005 at 15:57 GMT
			DESCRIPTION 
				"Increase length of OctedString for PortUserLabel to 100."
			REVISION "200608171134Z"		-- August 17, 2006 at 11:34 GMT
			DESCRIPTION 
				"Take over by Gerd Barchmann for R2.5.
				Base was she MIB release 151."
			REVISION "200609131011Z"		-- September 13, 2006 at 10:11 GMT
			DESCRIPTION 
				"Correct info about usable Shelftype's.
				Add new CardTypes to shePhysContainerAccCardType.
				Use TemperatureWarning-Alarm from VSHE only."
			REVISION "200609291056Z"		-- September 29, 2006 at 10:56 GMT
			DESCRIPTION 
				"Add some removed elements for backward compatibility of the managment system.
				The NE release up R2.5 will still NOT support this elements, but some used OID has been moved!
				Add card types of power modules for shelf M1100:E and G1100:E."
			REVISION "200610061623Z"		-- October 06, 2006 at 16:23 GMT
			DESCRIPTION 
				"Correct possible shelftype list."
			REVISION "200611071136Z"		-- November 07, 2006 at 11:36 GMT
			DESCRIPTION 
				"Add IU:ADSL:48 for backward copatibility reason's."
			REVISION "200701311631Z"		-- January 31, 2007 at 16:31 GMT
			DESCRIPTION 
				"New IU board IU_VDSL24P supported."
			REVISION "200702231558Z"		-- February 23, 2007 at 15:58 GMT
			DESCRIPTION 
				"Add new shelftype G400:E."
			REVISION "200703141031Z"		-- March 14, 2007 at 10:31 GMT
			DESCRIPTION 
				"New IU boards IU_VDSL48P, IU_VDSL48I and IU_10x1G supported.
				New CXU boards CXU_C2 and CXU_B2 supported."
			REVISION "200704161502Z"		-- April 16, 2007 at 15:02 GMT
			DESCRIPTION 
				"Add shePhysPortNeInfo to support ACI licensing feature."
			REVISION "200705081043Z"		-- May 08, 2007 at 10:43 GMT
			DESCRIPTION 
				"Support of shelf G400:R:A and additional power modules."
			REVISION "200705141319Z"		-- May 14, 2007 at 13:19 GMT
			DESCRIPTION 
				"Expand shePhysPortUserLabel to 200 byte."
			REVISION "200706041416Z"		-- June 04, 2007 at 14:16 GMT
			DESCRIPTION 
				"Expand range for shePhysContainerAccCardTypes."
			REVISION "200706130948Z"		-- June 13, 2007 at 09:48 GMT
			DESCRIPTION 
				"New powermodul PM:R:A supported."
			REVISION "200708221401Z"		-- August 22, 2007 at 14:01 GMT
			DESCRIPTION 
				"Add support for new ISDN service boards. 
				Add parameter for relative humidity status and alarm threshold configuration to
				shePhysShelfTable and corresponding threshold alarm to shePhysShelfAlarms group.
				Modify description for shePhysShelfMupState1 / 2 alarms.
				Add new shePhysShelfHeatExchangerIn / Out  alarms."
			REVISION "200709171116Z"		-- September 17, 2007 at 11:16 GMT
			DESCRIPTION 
				"Add support for new ADSL2+ and SHDSL service boards (only first integration).
				Add support for new 72-Port VoIP over POTS Service Module."
			REVISION "200710161126Z"		-- October 16, 2007 at 11:26 GMT
			DESCRIPTION 
				"Add new central board CXU_B22 and CXU_B3 support."
			REVISION "200711151002Z"		-- November 15, 2007 at 10:02 GMT
			DESCRIPTION 
				"Add support for Shelf-types G600 and MDUS.
				Add support for Card-types CXU_M and SB_XDSL (hiX5622).
				Correct description of fanAlarms (depends on used shelftype)."
			REVISION "200802251025Z"		-- February 25, 2008 at 10:25 GMT
			DESCRIPTION 
				"Add shePhysPortNEInfo for ISDNPorts.
				Add parameter for BatteryBackup configuration in hix5622 system.
				Modify comments for usage of external alarms in hix5622.
				Add new alarm shePhysCardSWVersionProblem.
				Correct Mnemocode for CXU_M (hix5622)."
			REVISION "200803070834Z"		-- March 07, 2008 at 08:34 GMT
			DESCRIPTION 
				"Correct description for fan-alarms to support hix5622."
			REVISION "200804021035Z"		-- April 02, 2008 at 10:35 GMT
			DESCRIPTION 
				"Add support for Card-type IU1GE:10O:SYN:E."
			REVISION "200804231448Z"		-- April 23, 2008 at 14:48 GMT
			DESCRIPTION 
				"Add new shelftype G600:R:E."
			REVISION "200805071022Z"		-- May 07, 2008 at 10:22 GMT
			DESCRIPTION 
				"Remove not supported 1GE board.
				Add new ADSL72 CGH board for Annex J support only."
			REVISION "200806181021Z"		-- June 18, 2008 at 10:21 GMT
			DESCRIPTION 
				"Add new card types for CXU and IU's.
				Not all of them are supported by all releases!
				Add new Subtypes for Shelf G1100 and M1100 with first support in R2.8."
			REVISION "200809190857Z"		-- September 19, 2008 at 08:57 GMT
			DESCRIPTION 
				"Add module for hiX5608.
				New RejResult value for port control."
			REVISION "200811070902Z"		-- November 07, 2008 at 09:02 GMT
			DESCRIPTION 
				"Remove not longer supported board CXU_B22.
				New shelftypes G100 and G200 supported.
				Add new parameter to shelfTable for alarmoutput switching.
				Add new parameter to portTable for timestamp info of last state changes.
				Define default usage of ExternalAlarm01 for hiX5608."
			REVISION "200811201005Z"		-- November 20, 2008 at 10:05 GMT
			DESCRIPTION 
				"New card and powermodules supported by R3.7M."
			REVISION "200901211059Z"		-- January 21, 2009 at 10:59 GMT
			DESCRIPTION 
				"Add missing shelf type definitions for G1100:A and M600:DF:E.
				Add new IU types for support in R3.7M version.
				Add new 2G shelftypes also for support in R2.8 maintenance.
				Add new 2G powermodules used with 2G shelftypes."
			REVISION "200901271135Z"		-- January 27, 2009 at 11:35 GMT
			DESCRIPTION 
				"Update list of supported cards for R3.7M."
			REVISION "200903031031Z"		-- March 03, 2009 at 10:31 GMT
			DESCRIPTION 
				"Correct mnemocode for new 2G powermodule.
				Correct mnemocode for new 2G shelftype.
				Add G200S 2G shelftype.
				Add new IUSHDSL:48E:8Q:E board."
			REVISION "200903040841Z"		-- March 04, 2009 at 08:41 GMT
			DESCRIPTION 
				"Correct mnemocode list for IU's supported with R3.7M."
			REVISION "200905061452Z"		-- May 06, 2009 at 14:52 GMT
			DESCRIPTION 
				"Set parameter shePhysCardUpgradeState to obsolete state."
			REVISION "200906171208Z"		-- June 17, 2009 at 12:08 GMT
			DESCRIPTION 
				"Add new Shelf-Alarm shePhysShelfExtAlarmCollectorNotConnected."
			::= { she 1 }

		
	
--
-- Textual conventions
--
	
-- -----------------------------------------------------------------
-- Textual Conventions Cards
-- -----------------------------------------------------------------
		ShePhysSlotStatusType ::= TEXTUAL-CONVENTION
			STATUS current
			DESCRIPTION 
				"The slot status type"
			SYNTAX INTEGER
				{
				empty(1),
				used(2)
				}

		ShePhysCardAdminStateType ::= TEXTUAL-CONVENTION
			STATUS current
			DESCRIPTION 
				"The adminstrative state type for cards. "
			SYNTAX INTEGER
				{
				unlocked(1),
				locked(2),
				notEquipped(3),
				planned(4)
				}

		ShePhysAvailabilityStateType ::= TEXTUAL-CONVENTION
			STATUS current
			DESCRIPTION 
				"The availability state type"
			SYNTAX INTEGER
				{
				available(1),
				failed(2),
				degraded(3),
				offline(4),
				notInstalled(5),
				dependency(7)
				}

		ShePhysCardOperStateType ::= TEXTUAL-CONVENTION
			STATUS current
			DESCRIPTION 
				"The operational state type for cards. "
			SYNTAX INTEGER
				{
				enabled(1),
				disabled(2)
				}

		ShePhysProtectionCapabilityType ::= TEXTUAL-CONVENTION
			STATUS current
			DESCRIPTION 
				"The protection modes a card can work (1=mode possible).
				bit 0: standalone mode
				bit 1: protection mode"
			SYNTAX INTEGER (0..3)

		ShePhysProtectionModeType ::= TEXTUAL-CONVENTION
			STATUS current
			DESCRIPTION 
				"The protection mode in which a card works."
			SYNTAX INTEGER
				{
				standaloneMode(1),
				protectionMode(2)
				}

		ShePhysDefaultRoleType ::= TEXTUAL-CONVENTION
			STATUS current
			DESCRIPTION 
				"The default role type."
			SYNTAX INTEGER
				{
				protecting(1),
				working(2)
				}

		ShePhysDynamicRoleType ::= TEXTUAL-CONVENTION
			STATUS current
			DESCRIPTION 
				"The dynamic role type."
			SYNTAX INTEGER
				{
				active(1),
				standby(2),
				notDefined(3)
				}

		ShePhysProtState ::= TEXTUAL-CONVENTION
			STATUS current
			DESCRIPTION 
				"The protection state type."
			SYNTAX INTEGER
				{
				unknown(1),
				activeNoRedundancy(2),
				activeProtected(3),
				activeDegraded(4),
				standbyNotPresent(5),
				standbyBooting(6),
				standbyProtecting(7),
				standbyDegraded(8)
				}

		ShePhysUpgradeStateType ::= TEXTUAL-CONVENTION
			STATUS current
			DESCRIPTION 
				"The upgrade state type."
			SYNTAX INTEGER
				{
				none(0),
				upgradeInitialized(1),
				upgradeToDo(2),
				upgradeStarted(3),
				upgradeCrashed(4),
				upgradeFtpDone(5),
				upgradeDone(6),
				upgradeReadyForReset(7),
				upgradeObsolete(8)
				}

		ShePhysCardControlRequestType ::= TEXTUAL-CONVENTION
			STATUS current
			DESCRIPTION 
				"The card control request type (user command)."
			SYNTAX INTEGER
				{
				createCard(1),
				deleteCard(2),
				convertCard(3),
				changeAdminState(4),
				resetSystem(6),
				resetSystemWithDefault(7),
				resetCard(8),
				resetCardsAllOfType(9),
				changeAlarmSeverityProfile(10),
				setTemperatureThreshold(11)
				}

-- GENERAL VALUES FOR USER COMMAND HANDLING
-- RETURN VALUES
-- 
		ShePhysCardControlRequestResultType ::= TEXTUAL-CONVENTION
			STATUS current
			DESCRIPTION 
				"The card control request result type, set after command completed or started.
				
				"
			SYNTAX INTEGER
				{
				commExecStarted(30),
				paramFaulty(31),
				requestBusy(32),
				setDataFailed(34),
				aswTimeout(35),
				commandFailed(36),
				commandSucceeded(37),
				upgradeRunning(40),
				resetRunning(41),
				cardNotAvail(42),
				resetNotSupported(43),
				resetNotSupportedOnStandbyBoard(44)
				}

		ShePhysAdminStateChangeType ::= TEXTUAL-CONVENTION
			STATUS current
			DESCRIPTION 
				"The admin state type for changeAdminState command."
			SYNTAX INTEGER
				{
				unlocked(1),
				locked(2),
				planned(4)
				}

		ShePhysAdminStateCreateType ::= TEXTUAL-CONVENTION
			STATUS current
			DESCRIPTION 
				"The admin state type for createCard command."
			SYNTAX INTEGER
				{
				locked(2),
				planned(4)
				}

		ShePhysControlRequestType ::= TEXTUAL-CONVENTION
			STATUS current
			DESCRIPTION 
				"The rack/shelf control request type (user command)."
			SYNTAX INTEGER
				{
				changeAlarmSeverityProfile(2),
				changeShelfExternalAlarmSettings(3),
				changeShelfExternalAlarmOutputStatus(4),
				changeTemperatureWarningThreshold(5),
				changeShelfRelativeHumidityAlarmThreshold(6),
				changeShelfBatteryBackupMode(10)
				}

--    USER COMMAND VALUES
-- 
-- GENERAL VALUES FOR USER COMMAND HANDLING 
-- RETURN VALUES                            
-- Reject reasons
--                      
-- -----------------------------------------------------------------
-- Textual Conventions Ports
-- -----------------------------------------------------------------    
		ShePhysPortControlRequestType ::= TEXTUAL-CONVENTION
			STATUS current
			DESCRIPTION 
				"The port control request type (user command)."
			SYNTAX INTEGER
				{
				changeAdminState(1),
				changeAlarmSeverityProfile(2),
				resetStatisticCounters(3),
				changeUserLabel(4),
				changeOperStateTrapEnablePermission(5)
				}

--    GENERAL VALUES FOR USER COMMAND HANDLING
-- RETURN VALUES
		ShePhysPortControlRequestResultType ::= TEXTUAL-CONVENTION
			STATUS current
			DESCRIPTION 
				"The port control request result type, set after command completed or started."
			SYNTAX INTEGER
				{
				commExecStarted(30),
				paramFaulty(31),
				requestBusy(32),
				setDataFailed(34),
				aswTimeout(35),
				commandFailed(36),
				commandSucceeded(37),
				singlePortNotAvailIfBonded(41)
				}

		ShePhysBrdControlRequestType ::= TEXTUAL-CONVENTION
			STATUS current
			DESCRIPTION 
				"The type for redundancy enabling/disabling and switchOver commands.
				Modify redundancy feature for CXU."
			SYNTAX INTEGER
				{
				enableBoardRedundancy(1),
				disableBoardRedundancy(2),
				switchOver(3),
				switchOverForced(4),
				modifyRedundancyFeature(5),
				modifyRedundancyInterlink(6)
				}

--    USER COMMAND VALUES
-- 
-- GENERAL VALUES FOR USER COMMAND HANDLING 
-- RETURN VALUES                            
		ShePhysBrdControlRequestResultType ::= TEXTUAL-CONVENTION
			STATUS current
			DESCRIPTION 
				"The type of rejest result after redundancy enabling/disabling or switchOver commands."
			SYNTAX INTEGER
				{
				commExecStarted(30),
				paramFaulty(31),
				requestBusy(32),
				setDataFailed(34),
				aswTimeout(35),
				commandFailed(36),
				commandSucceeded(37),
				brdObjNotAvail(41),
				brdBoardNotInWorkingSlot(45),
				brdUpgradeRunningOnBoardInProtection(48),
				redundancyDisabled(52),
				boardSwitchOverForcedOnly(54),
				brdWrongEntPhysicalIndex(56),
				brdNoRedundancyAvailable(57)
				}

		ShePhysControlRequestResultType ::= TEXTUAL-CONVENTION
			STATUS current
			DESCRIPTION 
				"The rack/shelf control request result type, set after command completed or started.
				"
			SYNTAX INTEGER
				{
				commExecStarted(30),
				paramFaulty(31),
				requestBusy(32),
				setDataFailed(34),
				aswTimeout(35),
				commandFailed(36),
				commandSucceeded(37)
				}

		ShePhysShelfExternalAlarmOutputStatusType ::= TEXTUAL-CONVENTION
			STATUS current
			DESCRIPTION 
				"Used for alarmOutPutStatus and setting. "
			SYNTAX INTEGER
				{
				notActive(0),
				active(1)
				}

		ShePhysShelfExternalAlarmLevelType ::= TEXTUAL-CONVENTION
			STATUS current
			DESCRIPTION 
				"Used for configuration of alarmInputLevels."
			SYNTAX INTEGER
				{
				activeLow(0),
				activeHigh(1)
				}

		ShePhysRedundancyFeatureType ::= TEXTUAL-CONVENTION
			STATUS current
			DESCRIPTION 
				"Used for configuration of redundancy feature."
			SYNTAX INTEGER
				{
				noOpticalSplitter(0),
				useOpticalSplitter(1)
				}

		ShePhysRedundancyInterlinkType ::= TEXTUAL-CONVENTION
			STATUS current
			DESCRIPTION 
				"Used for configuration of interlink types in case of redundancy."
			SYNTAX INTEGER
				{
				disable(0),
				electrical(1),
				optical(2)
				}

	
--
-- Node definitions
--
	
-- -----------------------------------------------------------------    
-- MIB contains the following groups
-- -----------------------------------------------------------------
-- 1.3.6.1.4.1.231.7.1.2.2.1.1.1
		shePhysContainerObjects OBJECT IDENTIFIER ::= { shePhysical 1 }

		
--    GENERAL VALUES FOR USER COMMAND HANDLING
-- RETURN VALUES
-- -----------------------------------------------------------------
-- SHE Container/Slot Objects
-- -----------------------------------------------------------------
-- 1.3.6.1.4.1.231.7.1.2.2.1.1.1.1
		shePhysContainerTable OBJECT-TYPE
			SYNTAX SEQUENCE OF ShePhysContainerEntry
			MAX-ACCESS not-accessible
			STATUS current
			DESCRIPTION
				" The container/slot table. "
			::= { shePhysContainerObjects 1 }

		
-- 1.3.6.1.4.1.231.7.1.2.2.1.1.1.1.1
		shePhysContainerEntry OBJECT-TYPE
			SYNTAX ShePhysContainerEntry
			MAX-ACCESS not-accessible
			STATUS current
			DESCRIPTION
				" Entry of the container table.
				The entries represent the slots of a SHE shelf
				"
			INDEX { entPhysicalIndex }
			::= { shePhysContainerTable 1 }

		
		ShePhysContainerEntry ::=
			SEQUENCE { 
				shePhysContainerAccCardTypes
					OCTET STRING,
				shePhysContainerSlotStatus
					ShePhysSlotStatusType,
				shePhysContainerConfiguredCardType
					DisplayString,
				shePhysContainerPluggedCardType
					DisplayString
			 }

-- 1.3.6.1.4.1.231.7.1.2.2.1.1.1.1.1.1
		shePhysContainerAccCardTypes OBJECT-TYPE
			SYNTAX OCTET STRING (SIZE (0..350))
			MAX-ACCESS read-only
			STATUS current
			DESCRIPTION
				"This attribute identifies the types of plug-in units to be
				accepted by this slot. The strings are separated by newline
				characters. That means CR LF.
				Valid strings are:
				emptyCardType
				
				Central cards (support depend on NE release and used shelf):
				CXUGE:4E:E
				CXUCGE:4E:E
				CXUB1GE:4E:E
				CXUB2GE:4:E
				CXUC2GE:4:E
				CXUB3GE:4:E
				CXUB21GE:4:E
				CXUG1B:2O:4E:E (>=3.7M)
				
				DSL IU card's (support depend on used NE release):
				IUSHDSL:48S:E
				IUSHDSL:48B:E
				IUADSL:48P:E
				IUADSL:72A:E
				IUADSL:72B:E     (obsolete)
				IUADSL:72P:IFX
				IUADSL:72I:IFX
				IUADSL:72AI:WC
				IUADSL:72AJ:WC
				IUVDSL:24D:IFX
				IUVDSL:24D2:IFX
				IUADSL:72A:CG
				IUADSL:72B:CG
				IUVDSL:24P:E
				IUVDSL:48P:E
				IUVDSL:48I:E      (obsolete)
				IUADSL:72A:CGH
				IUADSL:72B:CGH
				IUADSL:72J:CGH
				IUSHDSL:48E:E
				IUSHDSL:48E:8Q:E (>=R2.8 maintenance)
				IUVDSL:48I2:E    (>=R2.8)
				IUVDSL:48P2:E    (>=R2.8)
				IUSHDSL:48E:ME:E (>=R3.7M)
				IUADSL:72B:M:CG  (>=R3.7M)
				IUADSL:72B:ME:CG (>=R3.7M)
				IUADSL:72J:ME:CG (>=R3.7M)
				IUVDSL:48I3:M:E  (>=R3.7M)
				IUVDSL:48I3:ME:E (>=R3.7M)
				IUVDSL:48J3:ME:E (>=R3.7M)
				
				Subtending card (with R3.7M also used as UNI card):
				IU1GE:10O:SYN:E
				
				VoIP-Cards (only supported if NE support VoIP at all):
				VPLU-S72-POTS:E
				IU:32I4:E
				IU:32I2:E
				VPLU:72P:E 
				VPLU:72P1:E  (>=R2.8M)
				VPLU:72P2:E  (>=R2.8M)
				
				Powermodules (support depend on NE release and used shelf):
				PM1:E
				PM2:E
				PM3:A
				PM:UPL:E
				PM:UPL:R:E
				PM:UPL:A
				PM1:R:E
				PM1:R:A
				PM:R:A
				
				Powermodules for new shelftypes 2. generation -> 2G (>= R2.8 maintenance):
				PM:UPL:2G:E
				PM:UPL:2G:A
				PM1:R:2G:E
				PM:R:2G:E
				PM:R:2G:A
				PM:ONU:2G:E
				
				Boards for hiX5622 R1.0: (obsolete because release was canceled)
				CXUMGE:4:E
				SBXDSL:16P:E
				SBXDSL:16:E
				
				Board for hiX5608 (MiniIPD):
				HIX5608:E
				"
			REFERENCE
				"check definition of DisplayString for reference"
			::= { shePhysContainerEntry 1 }

		
-- 1.3.6.1.4.1.231.7.1.2.2.1.1.1.1.1.4
		shePhysContainerSlotStatus OBJECT-TYPE
			SYNTAX ShePhysSlotStatusType
			MAX-ACCESS read-only
			STATUS current
			DESCRIPTION
				" Indicates whether a slot is empty or used. "
			::= { shePhysContainerEntry 4 }

		
-- 1.3.6.1.4.1.231.7.1.2.2.1.1.1.1.1.5
		shePhysContainerConfiguredCardType OBJECT-TYPE
			SYNTAX DisplayString
			MAX-ACCESS read-only
			STATUS current
			DESCRIPTION
				"This attribute identifies the card type configured for this slot.
				Valid strings for card types are according to content of 
				shePhysContainerAccCardTypes. "
			::= { shePhysContainerEntry 5 }

		
-- 1.3.6.1.4.1.231.7.1.2.2.1.1.1.1.1.6
		shePhysContainerPluggedCardType OBJECT-TYPE
			SYNTAX DisplayString
			MAX-ACCESS read-only
			STATUS current
			DESCRIPTION
				"This attribute identifies the card type plugged for this slot.
				Valid strings for card types are according to content of 
				shePhysContainerAccCardTypes. "
			::= { shePhysContainerEntry 6 }

		
-- 1.3.6.1.4.1.231.7.1.2.2.1.1.2
		shePhysCardObjects OBJECT IDENTIFIER ::= { shePhysical 2 }

		
-- --------------------------------------------------------------
-- Entity Card MIB Objects
-- --------------------------------------------------------------
-- --------------------------------------------------------------
-- Entity Card Table
-- --------------------------------------------------------------
-- 1.3.6.1.4.1.231.7.1.2.2.1.1.2.1
		shePhysCardTable OBJECT-TYPE
			SYNTAX SEQUENCE OF ShePhysCardEntry
			MAX-ACCESS not-accessible
			STATUS current
			DESCRIPTION
				" Table containing the plug-in unit entries. "
			::= { shePhysCardObjects 1 }

		
-- 1.3.6.1.4.1.231.7.1.2.2.1.1.2.1.1
		shePhysCardEntry OBJECT-TYPE
			SYNTAX ShePhysCardEntry
			MAX-ACCESS not-accessible
			STATUS current
			DESCRIPTION
				" Entry of shePhysCardTable.
				Each entry is used to represent a card independently whether
				it is present or not (feature offline configuration).
				Cards can be created either by auto-configuration (plug-in)
				or by user command.
				Notifications : 
				    shePhysStateChangeOper.
				    shePhysStateChangeAdmin.
				    shePhysCardCreated.
				    shePhysCardDeleted.
				    Alarm traps when a fault has been detected or cleared. "
			INDEX { entPhysicalIndex }
			::= { shePhysCardTable 1 }

		
		ShePhysCardEntry ::=
			SEQUENCE { 
				shePhysCardAdminState
					ShePhysCardAdminStateType,
				shePhysCardAvailState
					ShePhysAvailabilityStateType,
				shePhysCardOperState
					ShePhysCardOperStateType,
				shePhysCardProtCapability
					ShePhysProtectionCapabilityType,
				shePhysCardProtMode
					ShePhysProtectionModeType,
				shePhysCardProtDefaultRole
					ShePhysDefaultRoleType,
				shePhysCardProtDynamicRole
					ShePhysDynamicRoleType,
				shePhysCardProtGroupId
					INTEGER,
				shePhysCardProtState
					ShePhysProtState,
				shePhysCardAlarmSeverityIndex
					SheAlarmSevProfileIndex,
				shePhysCardUpgradeState
					ShePhysUpgradeStateType,
				shePhysCardSwRunningLoad
					OCTET STRING,
				shePhysCardSwStoredLoad
					OCTET STRING,
				shePhysCardTemperatureCurrent
					INTEGER
			 }

-- 1.3.6.1.4.1.231.7.1.2.2.1.1.2.1.1.1
		shePhysCardAdminState OBJECT-TYPE
			SYNTAX ShePhysCardAdminStateType
			MAX-ACCESS read-only
			STATUS current
			DESCRIPTION
				" This attribute shows the administrative state
				of the plugin unit.
				In the transition from lock to unlock the plug-in unit is
				diagnosed.
				Default is notEquipped except for controller cards.
				The AdminState of controller cards is always unlocked.
				Planned is very similar to the locked state.
				Planned is used for configuration of cards without having
				a card equipped. A correct card being plugged leads to an
				auto-configuration of the card: the AdminState changes
				automatically from planned to unlocked. "
			::= { shePhysCardEntry 1 }

		
-- 1.3.6.1.4.1.231.7.1.2.2.1.1.2.1.1.2
		shePhysCardAvailState OBJECT-TYPE
			SYNTAX ShePhysAvailabilityStateType
			MAX-ACCESS read-only
			STATUS current
			DESCRIPTION
				" The availability state of a card. "
			::= { shePhysCardEntry 2 }

		
-- 1.3.6.1.4.1.231.7.1.2.2.1.1.2.1.1.3
		shePhysCardOperState OBJECT-TYPE
			SYNTAX ShePhysCardOperStateType
			MAX-ACCESS read-only
			STATUS current
			DESCRIPTION
				" The operational state of a card.  "
			::= { shePhysCardEntry 3 }

		
-- 1.3.6.1.4.1.231.7.1.2.2.1.1.2.1.1.4
		shePhysCardProtCapability OBJECT-TYPE
			SYNTAX ShePhysProtectionCapabilityType
			MAX-ACCESS read-only
			STATUS current
			DESCRIPTION
				"The protection modes the card can work:
				-bit0=1: Card can work as standalone card. 
				-bit1=1: Card can work as standby card."
			::= { shePhysCardEntry 4 }

		
-- 1.3.6.1.4.1.231.7.1.2.2.1.1.2.1.1.5
		shePhysCardProtMode OBJECT-TYPE
			SYNTAX ShePhysProtectionModeType
			MAX-ACCESS read-only
			STATUS current
			DESCRIPTION
				"The redundancy mode the card is running.
				-standaloneCard: The card works as standalone board. 
				 No redundancy is supported.   
				-protectionCard: The card works in redundancy mode."
			::= { shePhysCardEntry 5 }

		
-- 1.3.6.1.4.1.231.7.1.2.2.1.1.2.1.1.6
		shePhysCardProtDefaultRole OBJECT-TYPE
			SYNTAX ShePhysDefaultRoleType
			MAX-ACCESS read-only
			STATUS current
			DESCRIPTION
				"Defines the default role of the card (e.g. after power on) if more
				than one card which belong to the same protection group are become
				availible at the same time.
				Note, this attribute is only valid if 
				shePhysCardProtCapability = protectionCard.
				-working: The card becomes the active card by default.
				-protecting: The card becomes the standby card by default."
			::= { shePhysCardEntry 6 }

		
-- 1.3.6.1.4.1.231.7.1.2.2.1.1.2.1.1.7
		shePhysCardProtDynamicRole OBJECT-TYPE
			SYNTAX ShePhysDynamicRoleType
			MAX-ACCESS read-only
			STATUS current
			DESCRIPTION
				"The dynamic role of card. 
				Note, this attribute is only valid if 
				shePhysCardProtMode = protectionCard.
				-active: The card is the active card.
				-standby: The card is the standby card.
				-notDefined: If there is no card plugged, it is not possible
				 to say which card will become the active or standby card.
				"
			::= { shePhysCardEntry 7 }

		
-- 1.3.6.1.4.1.231.7.1.2.2.1.1.2.1.1.8
		shePhysCardProtGroupId OBJECT-TYPE
			SYNTAX INTEGER (0..255)
			MAX-ACCESS read-only
			STATUS current
			DESCRIPTION
				"The ID of protection group this card belongs to.
				Cards with the same Id can protect each other.
				Note, this attribute is only valid if 
				shePhysCardProtCapability = protectionCard."
			::= { shePhysCardEntry 8 }

		
-- 1.3.6.1.4.1.231.7.1.2.2.1.1.2.1.1.9
		shePhysCardProtState OBJECT-TYPE
			SYNTAX ShePhysProtState
			MAX-ACCESS read-only
			STATUS current
			DESCRIPTION
				"The current state of the protection:
				-unknown
				 If the dynamic role of the cards which belong to a protection group
				 is not set yet, there is no information about the protection state 
				 available.
				-active_noRedundancy: 
				 The card is the active card but is not protected by a standby card.
				-active_protected:
				 The card is the active card is is protected by a standby card.
				-active_degraded:
				 The card is the active card but not all functionality is protected
				 by the standby card.
				-standby_notPresent:
				 The card is the standby card but it is not available.
				-standby_booting:
				 The card is the standby card but is still booting.
				-standby_protecting:
				 The card is the standby card and protects the active card.
				-standby_degraded:
				 The card is the standby card but can not take over all functionality
				 of the current active board.
				Note, this attribute is only valid if 
				shePhysCardProtCapability = protectionCard."
			::= { shePhysCardEntry 9 }

		
-- 1.3.6.1.4.1.231.7.1.2.2.1.1.2.1.1.10
		shePhysCardAlarmSeverityIndex OBJECT-TYPE
			SYNTAX SheAlarmSevProfileIndex
			MAX-ACCESS read-only
			STATUS current
			DESCRIPTION
				" It is a pointer to the instance of the alarm severity profile
				that contains the severity assignments for alarms 
				reported by this managed entity. Default is 1. "
			::= { shePhysCardEntry 10 }

		
-- to be discussed
-- 1.3.6.1.4.1.231.7.1.2.2.1.1.2.1.1.11
		shePhysCardUpgradeState OBJECT-TYPE
			SYNTAX ShePhysUpgradeStateType
			MAX-ACCESS read-only
			STATUS obsolete
			DESCRIPTION
				"Informs about the state of the SW upgrade task during
				loading and the result at the end of loading the current plug-in unit. 
				
				NOTE:
				The parameter is set to obsolete state with R3.7M. 
				Also former releases does not report a valid information on this parameter.
				Valid informations about SW upgrade could only be retrieved via sheSystemSwMaintenanceTaskTable."
			::= { shePhysCardEntry 11 }

		
-- 1.3.6.1.4.1.231.7.1.2.2.1.1.2.1.1.12
		shePhysCardSwRunningLoad OBJECT-TYPE
			SYNTAX OCTET STRING (SIZE (0..128))
			MAX-ACCESS read-only
			STATUS current
			DESCRIPTION
				"Informs about the currently running load.
				"
			::= { shePhysCardEntry 12 }

		
-- 1.3.6.1.4.1.231.7.1.2.2.1.1.2.1.1.13
		shePhysCardSwStoredLoad OBJECT-TYPE
			SYNTAX OCTET STRING (SIZE (0..128))
			MAX-ACCESS read-only
			STATUS current
			DESCRIPTION
				"Informs about the currently stored load.  "
			::= { shePhysCardEntry 13 }

		
-- 1.3.6.1.4.1.231.7.1.2.2.1.1.2.1.1.14
		shePhysCardTemperatureCurrent OBJECT-TYPE
			SYNTAX INTEGER (-40..200 | 255)
			UNITS "°C"
			MAX-ACCESS read-only
			STATUS current
			DESCRIPTION
				"Current temperature of a card - 255 means unknown value."
			::= { shePhysCardEntry 14 }

		
-- --------------------------------------------------------------
-- Card control subgroup
-- --------------------------------------------------------------
-- 1.3.6.1.4.1.231.7.1.2.2.1.1.2.2
		shePhysCardControl OBJECT IDENTIFIER ::= { shePhysCardObjects 2 }

		
-- 1.3.6.1.4.1.231.7.1.2.2.1.1.2.2.1
		shePhysCardControlRequest OBJECT-TYPE
			SYNTAX ShePhysCardControlRequestType
			MAX-ACCESS read-write
			STATUS current
			DESCRIPTION
				" The card commands :
				changeAdminState: changes the shePhysCardAdminState of a card.
				   AdminState of controller cards cannot be changed.
				changeAlarmSeverityProfile: changes the shePhysCardAlarmSeverityIndex of a card.
				   This is the pointer to a alarm severity profile. 
				
				createCard:
				   creates plugin units. Acceptable in state NotEquipped and
				   when object does not exist. The AdminState after creation,
				   possible values are Planned or Locked,
				   is specified as command parameter.
				   The command is not accepted for CXUs.
				   These HW objects are automatically created.
				   The acceptable CardTypes are specified in the slot
				   attribute shePhysContainerAccCardTypes. The content of this
				   attribute changes after the creation to values allowed for
				   the convert command.
				deleteCard:
				   deletes a card. Acceptable only in state Planned/Locked.
				   The command is not accepted for CXUs.
				   CXUs are automatically deleted when board redundancy is disabled.
				   The AdminState changes to NotEquipped.
				convertCard:
				   converts the type of card. Acceptable only within
				   the same card group, e.g. ADSL to ADSL according to content of
				   types listed in shePhysContainerAccCardTypes.
				   convertCard allowed in state Planned/Locked.
				Notifications: shePhysCardControlResult when a command has finished. 
				
				reset commands:
				 
				resetSystem: reset of system (all cards) and activates loads after SW download. 
				    The main card will perform a restart.                            
				resetSystemWithDefaultConf : restart with default configuration is performed. 
				
				resetCard:
				    after SW download to activate the new load of a specific card.
				resetCardAllOfType:
				    after SW download of cards of the same type to activate the new load.				
				                   
				Notifications : 
				 shePhysCardReset at beginning of reset.
				 shePhysCardResetEnd at end of reset.
				 shePhysCardControlResult for reset of CXU in case of a failure occured
				 after the reset has been accepted.
				 
				changeAlarmSeverityProfile: 
				  the alarm severity profile is changed for a specific card.
				
				THIS REQUEST WILL NOT LONGER BE SUPPORTED BY NE R2.5:
				setTemperatureThreshold:
				  configure the temperature threshold which is used.
				  When temperature reaches the threshold, alarm is turned on. "
			::= { shePhysCardControl 1 }

		
-- 1.3.6.1.4.1.231.7.1.2.2.1.1.2.2.2
		shePhysCardControlStatus OBJECT-TYPE
			SYNTAX SheControlStatusType
			MAX-ACCESS read-only
			STATUS current
			DESCRIPTION
				" The status of a user command. "
			::= { shePhysCardControl 2 }

		
-- 1.3.6.1.4.1.231.7.1.2.2.1.1.2.2.3
		shePhysCardControlPhysicalName OBJECT-TYPE
			SYNTAX SnmpAdminString
			MAX-ACCESS read-write
			STATUS current
			DESCRIPTION
				" A valid string for a card.
				Identifies the type of card which should be created.
				Default is \0. "
			::= { shePhysCardControl 3 }

		
-- 1.3.6.1.4.1.231.7.1.2.2.1.1.2.2.4
		shePhysCardControlContainedInIndex OBJECT-TYPE
			SYNTAX PhysicalIndex
			MAX-ACCESS read-write
			STATUS current
			DESCRIPTION
				" The entPhysicalIndex of the slot which contains the card. "
			::= { shePhysCardControl 4 }

		
-- 1.3.6.1.4.1.231.7.1.2.2.1.1.2.2.5
		shePhysCardControlTimer OBJECT-TYPE
			SYNTAX Unsigned32
			MAX-ACCESS read-only
			STATUS current
			DESCRIPTION
				" The maximum wait time for the manager for a long running 
				user command. "
			::= { shePhysCardControl 5 }

		
-- 1.3.6.1.4.1.231.7.1.2.2.1.1.2.2.6
		shePhysCardControlReqResult OBJECT-TYPE
			SYNTAX ShePhysCardControlRequestResultType
			MAX-ACCESS read-only
			STATUS current
			DESCRIPTION
				" The result of the last user command. "
			::= { shePhysCardControl 6 }

		
-- 1.3.6.1.4.1.231.7.1.2.2.1.1.2.2.7
		shePhysCardControlTimeStamp OBJECT-TYPE
			SYNTAX Unsigned32
			UNITS "sec"
			MAX-ACCESS read-only
			STATUS current
			DESCRIPTION
				" The time stamp of the last command (end of command). "
			::= { shePhysCardControl 7 }

		
-- command parameter for changeAdminState
-- 1.3.6.1.4.1.231.7.1.2.2.1.1.2.2.8
		shePhysCardControlAdminStateChange OBJECT-TYPE
			SYNTAX ShePhysAdminStateChangeType
			MAX-ACCESS read-write
			STATUS current
			DESCRIPTION
				" Selects the desired adminstrative state.  "
			::= { shePhysCardControl 8 }

		
-- command parameter for createCard
-- 1.3.6.1.4.1.231.7.1.2.2.1.1.2.2.9
		shePhysCardControlAdminStateCreate OBJECT-TYPE
			SYNTAX ShePhysAdminStateCreateType
			MAX-ACCESS read-write
			STATUS current
			DESCRIPTION
				" Selects the desired adminstrative state
				in user command createCard. "
			::= { shePhysCardControl 9 }

		
-- 1.3.6.1.4.1.231.7.1.2.2.1.1.2.2.10
		shePhysCardControlTemperatureThreshold OBJECT-TYPE
			SYNTAX INTEGER (-40..200)
			UNITS "°C"
			MAX-ACCESS read-write
			STATUS obsolete
			DESCRIPTION
				"The temperature threshold for all cards.
				
				THIS ELEMENT WILL NOT LONGER BE SUPPORTED BY NE up R2.5."
			::= { shePhysCardControl 10 }

		
-- ------------------------------------------
-- card reset parameters
-- ------------------------------------------
-- 1.3.6.1.4.1.231.7.1.2.2.1.1.2.2.13
		shePhysCardControlEntPhysicalIndex OBJECT-TYPE
			SYNTAX PhysicalIndex
			MAX-ACCESS read-write
			STATUS current
			DESCRIPTION
				" The entPhysicalIndex of the plugin unit which should get the
				reset. "
			::= { shePhysCardControl 13 }

		
-- 1.3.6.1.4.1.231.7.1.2.2.1.1.2.2.14
		shePhysCardControlAlarmSeverityIndex OBJECT-TYPE
			SYNTAX SheAlarmSevProfileIndex
			MAX-ACCESS read-write
			STATUS current
			DESCRIPTION
				" The new AlarmSeverityIndex of the alarm severity profile 
				assigned to the card. "
			::= { shePhysCardControl 14 }

		
-- ------------------------------------------
-- Temperature handling
-- ------------------------------------------
-- 1.3.6.1.4.1.231.7.1.2.2.1.1.2.3
		sheTemperatureObjects OBJECT IDENTIFIER ::= { shePhysCardObjects 3 }

		
-- ------------------------------------------
-- Thresholds for alarm generation/clearing 
-- These are global objects for all line cards 
-- Alarm before high temperature turn off
-- ------------------------------------------	
-- 1.3.6.1.4.1.231.7.1.2.2.1.1.2.3.1
		shePhysCardTemperaturePowerDownOn OBJECT-TYPE
			SYNTAX INTEGER (0..120)
			UNITS "°C"
			MAX-ACCESS read-only
			STATUS current
			DESCRIPTION
				"Temperature threshold for generation of shePhysCardTemperaturePowerDown alarm for line cards. 
				IU will start now with action to reduce power consumption."
			::= { sheTemperatureObjects 1 }

		
-- 1.3.6.1.4.1.231.7.1.2.2.1.1.2.3.2
		shePhysCardTemperaturePowerDownOff OBJECT-TYPE
			SYNTAX INTEGER (0..120)
			UNITS "°C"
			MAX-ACCESS read-only
			STATUS current
			DESCRIPTION
				"Temperature threshold for clearing of shePhysCardOverTemperatureReset alarm for the line cards. "
			::= { sheTemperatureObjects 2 }

		
-- 1.3.6.1.4.1.231.7.1.2.2.1.1.2.3.3
		shePhysCardOverTemperatureResetOn OBJECT-TYPE
			SYNTAX INTEGER (0..120)
			UNITS "°C"
			MAX-ACCESS read-only
			STATUS current
			DESCRIPTION
				"Temperature threshold for the generation of the shePhysCardOverTemperatureReset alarm for line cards.
				CXU has forced IU tp reset state, to prevend from further damages. "
			::= { sheTemperatureObjects 3 }

		
-- 1.3.6.1.4.1.231.7.1.2.2.1.1.2.3.4
		shePhysCardOverTemperatureResetOff OBJECT-TYPE
			SYNTAX INTEGER (0..120)
			UNITS "°C"
			MAX-ACCESS read-only
			STATUS current
			DESCRIPTION
				"Temperature threshold for the clearing the shePhysCardOverTemperatureReset alarm for line cards. "
			::= { sheTemperatureObjects 4 }

		
-- 1.3.6.1.4.1.231.7.1.2.2.1.1.2.3.5
		shePhysCardTemperatureThreshold OBJECT-TYPE
			SYNTAX Integer32 (-40..200)
			UNITS "°C"
			MAX-ACCESS read-only
			STATUS obsolete
			DESCRIPTION
				"THIS ELEMENT WILL NOT LONGER BE SUPPORTED BY NE up R2.5.
				
				Temperature threshold for all cards of shePhysCardOverTemperatureThreshold."
			DEFVAL { 50 }
			::= { sheTemperatureObjects 5 }

		
-- ------------------------------------------
-- Thresholds for alarm generation/clearing 
-- These are global objects for all line cards 
-- Alarm before high temperature turn off
-- ------------------------------------------
-- 1.3.6.1.4.1.231.7.1.2.2.1.1.2.3.6
		shePhysCardTemperatureWarningOn OBJECT-TYPE
			SYNTAX INTEGER (-40..120)
			UNITS "°C"
			MAX-ACCESS read-only
			STATUS current
			DESCRIPTION
				"Temperature threshold for generation of shePhysCardTemperatureWarning alarm for line cards. 
				The NE will not start any actions in that case. It is only warning for changed temperature conditions.
				"
			DEFVAL { 65 }
			::= { sheTemperatureObjects 6 }

		
-- 1.3.6.1.4.1.231.7.1.2.2.1.1.2.3.7
		shePhysCardTemperatureWarningOff OBJECT-TYPE
			SYNTAX INTEGER (-40..120)
			UNITS "°C"
			MAX-ACCESS read-only
			STATUS current
			DESCRIPTION
				"Temperature threshold for clearing of shePhysCardTemperatureWarning alarm for line cards. 
				The NE will not start any actions in that case. It is only warning for changed temperature conditions.
				"
			DEFVAL { 55 }
			::= { sheTemperatureObjects 7 }

		
-- 1.3.6.1.4.1.231.7.1.2.2.1.1.2.3.10
		sheTemperatureControlObjects OBJECT IDENTIFIER ::= { sheTemperatureObjects 10 }

		
-- 1.3.6.1.4.1.231.7.1.2.2.1.1.2.3.10.1
		shePhysCardTemperatureControlRequest OBJECT-TYPE
			SYNTAX ShePhysControlRequestType
			MAX-ACCESS read-write
			STATUS current
			DESCRIPTION
				" The card commands :
				changeTemperatureWarningThreshold: 
				changes the shePhysCardTemperatureWarningThreshold's.
				                   
				"
			::= { sheTemperatureControlObjects 1 }

		
-- 1.3.6.1.4.1.231.7.1.2.2.1.1.2.3.10.2
		shePhysCardTemperatureControlStatus OBJECT-TYPE
			SYNTAX SheControlStatusType
			MAX-ACCESS read-only
			STATUS current
			DESCRIPTION
				" The status of a user command. "
			::= { sheTemperatureControlObjects 2 }

		
-- 1.3.6.1.4.1.231.7.1.2.2.1.1.2.3.10.3
		shePhysCardTemperatureControlTimer OBJECT-TYPE
			SYNTAX Unsigned32
			MAX-ACCESS read-only
			STATUS current
			DESCRIPTION
				" The maximum wait time for the manager for a long running 
				user command. "
			::= { sheTemperatureControlObjects 3 }

		
-- 1.3.6.1.4.1.231.7.1.2.2.1.1.2.3.10.4
		shePhysCardTemperatureControlReqResult OBJECT-TYPE
			SYNTAX ShePhysCardControlRequestResultType
			MAX-ACCESS read-only
			STATUS current
			DESCRIPTION
				" The result of the last user command. "
			::= { sheTemperatureControlObjects 4 }

		
-- 1.3.6.1.4.1.231.7.1.2.2.1.1.2.3.10.5
		shePhysCardTemperatureControlTimeStamp OBJECT-TYPE
			SYNTAX Unsigned32
			UNITS "sec"
			MAX-ACCESS read-only
			STATUS current
			DESCRIPTION
				" The time stamp of the last command (end of command). "
			::= { sheTemperatureControlObjects 5 }

		
-- ------------------------------------------
-- Thresholds for alarm generation/clearing 
-- These are global objects for all line cards 
-- Alarm before high temperature turn off
-- ------------------------------------------
-- 1.3.6.1.4.1.231.7.1.2.2.1.1.2.3.10.6
		shePhysCardTemperatureControlWarningOn OBJECT-TYPE
			SYNTAX INTEGER (-40..120)
			UNITS "°C"
			MAX-ACCESS read-write
			STATUS current
			DESCRIPTION
				"Temperature threshold for generation of shePhysCardTemperatureWarning alarm for line cards. 
				The NE will not start any actions in that case. It is only warning for changed temperature conditions.
				"
			::= { sheTemperatureControlObjects 6 }

		
-- 1.3.6.1.4.1.231.7.1.2.2.1.1.2.3.10.7
		shePhysCardTemperatureControlWarningOff OBJECT-TYPE
			SYNTAX INTEGER (-40..120)
			UNITS "°C"
			MAX-ACCESS read-write
			STATUS current
			DESCRIPTION
				"Temperature threshold for clearing of shePhysCardTemperatureWarning alarm for line cards. 
				The NE will not start any actions in that case. It is only warning for changed temperature conditions.
				"
			::= { sheTemperatureControlObjects 7 }

		
-- 1.3.6.1.4.1.231.7.1.2.2.1.1.3
		shePhysPortObjects OBJECT IDENTIFIER ::= { shePhysical 3 }

		
-- --------------------------------------------------------------
-- Port objects subgroup
-- --------------------------------------------------------------                    
-- 1.3.6.1.4.1.231.7.1.2.2.1.1.3.1
		shePhysPortTable OBJECT-TYPE
			SYNTAX SEQUENCE OF ShePhysPortEntry
			MAX-ACCESS not-accessible
			STATUS current
			DESCRIPTION
				" The port table extension of the IfTable.
				Provides the mapping information concerning port and card 
				the port is contained and the alarm severity profile. "
			::= { shePhysPortObjects 1 }

		
-- 1.3.6.1.4.1.231.7.1.2.2.1.1.3.1.1
		shePhysPortEntry OBJECT-TYPE
			SYNTAX ShePhysPortEntry
			MAX-ACCESS not-accessible
			STATUS current
			DESCRIPTION
				" Entry of the port table.
				Represents a physical interface (a port).
				"
			INDEX { ifIndex }
			::= { shePhysPortTable 1 }

		
		ShePhysPortEntry ::=
			SEQUENCE { 
				shePhysPortEntPhysicalIndex
					PhysicalIndex,
				shePhysPortId
					INTEGER,
				shePhysPortAlarmSeverityIndex
					SheAlarmSevProfileIndex,
				shePhysPortUserLabel
					OCTET STRING,
				shePhysPortAdminStateLastChangeTime
					Unsigned32,
				shePhysPortOperStateUpLastChangeTime
					Unsigned32,
				shePhysPortOperStateDownLastChangeTime
					Unsigned32
			 }

-- 1.3.6.1.4.1.231.7.1.2.2.1.1.3.1.1.1
		shePhysPortEntPhysicalIndex OBJECT-TYPE
			SYNTAX PhysicalIndex
			MAX-ACCESS read-only
			STATUS current
			DESCRIPTION
				" The entPhysical index of the card this port is contained in. "
			::= { shePhysPortEntry 1 }

		
-- 1.3.6.1.4.1.231.7.1.2.2.1.1.3.1.1.2
		shePhysPortId OBJECT-TYPE
			SYNTAX INTEGER (0..255)
			MAX-ACCESS read-only
			STATUS current
			DESCRIPTION
				" The port number/port ID related to the card this port is contained in. "
			::= { shePhysPortEntry 2 }

		
-- 1.3.6.1.4.1.231.7.1.2.2.1.1.3.1.1.3
		shePhysPortAlarmSeverityIndex OBJECT-TYPE
			SYNTAX SheAlarmSevProfileIndex
			MAX-ACCESS read-only
			STATUS current
			DESCRIPTION
				" A pointer to the instance of the alarm severity profile 
				that contains the severity assignments for alarms 
				reported by this managed entity. Default is 1. "
			::= { shePhysPortEntry 3 }

		
-- 1.3.6.1.4.1.231.7.1.2.2.1.1.3.1.1.4
		shePhysPortUserLabel OBJECT-TYPE
			SYNTAX OCTET STRING (SIZE (0..200))
			MAX-ACCESS read-only
			STATUS current
			DESCRIPTION
				"Port specific ASCII  identification.
				This string is only used by the ACI to identifying a physical UserPort.
				The data is stored in NE but has no further meaning for the NE himself."
			::= { shePhysPortEntry 4 }

		
		shePhysPortAdminStateLastChangeTime OBJECT-TYPE
			SYNTAX Unsigned32
			UNITS "sec"
			MAX-ACCESS read-only
			STATUS current
			DESCRIPTION
				"The timestamp when this port last times changes adminstate.
				
				New parameter with SHE R2.8 maintenance."
			::= { shePhysPortEntry 5 }

		
		shePhysPortOperStateUpLastChangeTime OBJECT-TYPE
			SYNTAX Unsigned32
			UNITS "sec"
			MAX-ACCESS read-only
			STATUS current
			DESCRIPTION
				"The timestamp when this port last times reaches operstate UP.
				
				New parameter with SHE R2.8 maintenance."
			::= { shePhysPortEntry 6 }

		
		shePhysPortOperStateDownLastChangeTime OBJECT-TYPE
			SYNTAX Unsigned32
			UNITS "sec"
			MAX-ACCESS read-only
			STATUS current
			DESCRIPTION
				"The timestamp when this port last times reaches operstate DOWN.
				
				New parameter with SHE R2.8 maintenance."
			::= { shePhysPortEntry 7 }

		
-- 1.3.6.1.4.1.231.7.1.2.2.1.1.3.2
		shePhysPortControl OBJECT IDENTIFIER ::= { shePhysPortObjects 2 }

		
-- 1.3.6.1.4.1.231.7.1.2.2.1.1.3.2.1
		shePhysPortControlRequest OBJECT-TYPE
			SYNTAX ShePhysPortControlRequestType
			MAX-ACCESS read-write
			STATUS current
			DESCRIPTION
				" The port commands :
				changeAdminState: 
				  the AdminState of the current port shall be changed.
				changeAlarmSeverityProfile: 
				  the alarm severity profile of the port is changed.        
				resetStatisticCounters: 
				  reset all statistic counters in if- and ifx-table for this port.
				changeUserLabel:
				change the value of the UserLabel for this port.
				changeOperStateTrapEnablePermission:
				  change the permission to send operstate trap for this port.
				
				Notifications : 
				  shePhysPortControlResult at the command ending in case of long running command. "
			::= { shePhysPortControl 1 }

		
-- 1.3.6.1.4.1.231.7.1.2.2.1.1.3.2.2
		shePhysPortControlStatus OBJECT-TYPE
			SYNTAX SheControlStatusType
			MAX-ACCESS read-only
			STATUS current
			DESCRIPTION
				" The status of a user command. "
			::= { shePhysPortControl 2 }

		
-- 1.3.6.1.4.1.231.7.1.2.2.1.1.3.2.3
		shePhysPortControlIfIndex OBJECT-TYPE
			SYNTAX InterfaceIndex
			MAX-ACCESS read-write
			STATUS current
			DESCRIPTION
				" The IfIndex of the port that shall be configured. "
			::= { shePhysPortControl 3 }

		
-- 1.3.6.1.4.1.231.7.1.2.2.1.1.3.2.4
		shePhysPortControlAlarmSeverityIndex OBJECT-TYPE
			SYNTAX SheAlarmSevProfileIndex
			MAX-ACCESS read-write
			STATUS current
			DESCRIPTION
				" The new AlarmSeverityIndex of the alarm severity profile 
				assigned to the port. "
			::= { shePhysPortControl 4 }

		
-- 1.3.6.1.4.1.231.7.1.2.2.1.1.3.2.5
		shePhysPortControlAdminState OBJECT-TYPE
			SYNTAX SheAdminStateType
			MAX-ACCESS read-write
			STATUS current
			DESCRIPTION
				" The desired AdminState of the port that shall be configured. "
			::= { shePhysPortControl 5 }

		
-- 1.3.6.1.4.1.231.7.1.2.2.1.1.3.2.6
		shePhysPortControlTimeStamp OBJECT-TYPE
			SYNTAX Unsigned32
			UNITS "sec"
			MAX-ACCESS read-only
			STATUS current
			DESCRIPTION
				" The time stamp of the last command (end of command). "
			::= { shePhysPortControl 6 }

		
-- 1.3.6.1.4.1.231.7.1.2.2.1.1.3.2.7
		shePhysPortControlTimer OBJECT-TYPE
			SYNTAX Unsigned32
			MAX-ACCESS read-only
			STATUS current
			DESCRIPTION
				" The maximum wait time for the manager for command ending
				in case of long running user commands.
				The manager reads this value from the PPE SHE.
				The end of request indicates the trap ShePhysRiResult . "
			::= { shePhysPortControl 7 }

		
-- 1.3.6.1.4.1.231.7.1.2.2.1.1.3.2.8
		shePhysPortControlReqResult OBJECT-TYPE
			SYNTAX ShePhysPortControlRequestResultType
			MAX-ACCESS read-only
			STATUS current
			DESCRIPTION
				" The result of the last user command. "
			::= { shePhysPortControl 8 }

		
-- 1.3.6.1.4.1.231.7.1.2.2.1.1.3.2.9
		shePhysPortControlUserLabel OBJECT-TYPE
			SYNTAX OCTET STRING (SIZE (0..200))
			MAX-ACCESS read-write
			STATUS current
			DESCRIPTION
				"Port specific ASCII  identification.
				This string is only used by the ACI to identifying a physical UserPort.
				The data is stored in NE but has no further meaning for the NE himself."
			::= { shePhysPortControl 9 }

		
-- 1.3.6.1.4.1.231.7.1.2.2.1.1.3.2.10
		shePhysPortControlOperStateTrapEnable OBJECT-TYPE
			SYNTAX ShePermissionType
			MAX-ACCESS read-write
			STATUS current
			DESCRIPTION
				"Enable/disable OperStateTrap's. Current status could be read from ifx-table."
			::= { shePhysPortControl 10 }

		
		shePhysPortNEInfo OBJECT IDENTIFIER ::= { shePhysPortObjects 3 }

		
		shePhysPortAdslCount OBJECT-TYPE
			SYNTAX Unsigned32
			MAX-ACCESS read-only
			STATUS current
			DESCRIPTION
				"This attribute returns the current number of available physical port's of type 
				ADSL (ifType 94) of the NE.
				The attribute could be used by the management system for licensing.   "
			::= { shePhysPortNEInfo 1 }

		
		shePhysPortShdslCount OBJECT-TYPE
			SYNTAX Unsigned32
			MAX-ACCESS read-only
			STATUS current
			DESCRIPTION
				"This attribute returns the current number of available physical port's of type 
				SHDSL (ifType 96) of the NE.
				The attribute could be used by the management system for licensing.   "
			::= { shePhysPortNEInfo 2 }

		
		shePhysPortVdslCount OBJECT-TYPE
			SYNTAX Unsigned32
			MAX-ACCESS read-only
			STATUS current
			DESCRIPTION
				"This attribute returns the current number of available physical port's of type 
				VDSL (ifType 97) of the NE.
				The attribute could be used by the management system for licensing.   "
			::= { shePhysPortNEInfo 3 }

		
		shePhysPortAdsl2Count OBJECT-TYPE
			SYNTAX Unsigned32
			MAX-ACCESS read-only
			STATUS current
			DESCRIPTION
				"This attribute returns the current number of available physical port's of type 
				ADSL2 (ifType 230) of the NE.
				The attribute could be used by the management system for licensing.   "
			::= { shePhysPortNEInfo 4 }

		
		shePhysPortVoipCount OBJECT-TYPE
			SYNTAX Unsigned32
			MAX-ACCESS read-only
			STATUS current
			DESCRIPTION
				"This attribute returns the current number of available physical port's of type 
				VOIP (ifType 104) of the NE.
				The attribute could be used by the management system for licensing.   "
			::= { shePhysPortNEInfo 5 }

		
		shePhysPortIsdnCount OBJECT-TYPE
			SYNTAX Unsigned32
			MAX-ACCESS read-only
			STATUS current
			DESCRIPTION
				"This attribute returns the current number of available physical port's of type 
				ISDN (ifType 63) of the NE.
				The attribute could be used by the management system for licensing.   "
			::= { shePhysPortNEInfo 6 }

		
-- 1.3.6.1.4.1.231.7.1.2.2.1.1.4
		shePhysRedundancyObjects OBJECT IDENTIFIER ::= { shePhysical 4 }

		
-- --------------------------------------------------------------
-- Board redundancy subgroup
-- --------------------------------------------------------------
-- 1.3.6.1.4.1.231.7.1.2.2.1.1.4.1
		shePhysBoardRedundancyControl OBJECT IDENTIFIER ::= { shePhysRedundancyObjects 1 }

		
-- 1.3.6.1.4.1.231.7.1.2.2.1.1.4.1.1
		shePhysBrdControlRequest OBJECT-TYPE
			SYNTAX ShePhysBrdControlRequestType
			MAX-ACCESS read-write
			STATUS current
			DESCRIPTION
				" The user commands for board redundancy and switch over.
				enableBoardRedundancy, disableBoardRedundancy:
				   to enable/disable board redundancy.
				boardSwitchOver: applicable when board redundancy
				   is enabled and the standby board is in the state 
				   ShePhysCardProtState = standby_protecting
				   (There is no traffic interruption in case of swithover.)
				boardSwitchOverForced: applicable when board redundancy
				   is enabled, ShePhysCardProtState = standby_protecting or
				   standby_degraded.
				modifyRedundancyFeature: applicable only for CXU-board
				modifyRedundancyInterlinksFeature: applicable only for CXU-board"
			::= { shePhysBoardRedundancyControl 1 }

		
-- 1.3.6.1.4.1.231.7.1.2.2.1.1.4.1.2
		shePhysBrdControlStatus OBJECT-TYPE
			SYNTAX SheControlStatusType
			MAX-ACCESS read-only
			STATUS current
			DESCRIPTION
				" The status of the control request. "
			::= { shePhysBoardRedundancyControl 2 }

		
-- 1.3.6.1.4.1.231.7.1.2.2.1.1.4.1.3
		shePhysBrdControlReqResult OBJECT-TYPE
			SYNTAX ShePhysBrdControlRequestResultType
			MAX-ACCESS read-only
			STATUS current
			DESCRIPTION
				" The result of the last user command. "
			::= { shePhysBoardRedundancyControl 3 }

		
-- 1.3.6.1.4.1.231.7.1.2.2.1.1.4.1.4
		shePhysBrdControlTimeStamp OBJECT-TYPE
			SYNTAX Unsigned32
			UNITS "sec"
			MAX-ACCESS read-only
			STATUS current
			DESCRIPTION
				" The time stamp of the last command (end of command). "
			::= { shePhysBoardRedundancyControl 4 }

		
-- 1.3.6.1.4.1.231.7.1.2.2.1.1.4.1.5
		shePhysBrdControlTimer OBJECT-TYPE
			SYNTAX Unsigned32
			MAX-ACCESS read-only
			STATUS current
			DESCRIPTION
				" The maximum wait time for the manager for 
				a line redundancy user command. "
			::= { shePhysBoardRedundancyControl 5 }

		
-- 1.3.6.1.4.1.231.7.1.2.2.1.1.4.1.6
		shePhysBrdControlEntPhysicalIndex OBJECT-TYPE
			SYNTAX PhysicalIndex
			MAX-ACCESS read-write
			STATUS current
			DESCRIPTION
				" The entPhysicalIndex of the card to be switched over or modified. "
			::= { shePhysBoardRedundancyControl 6 }

		
-- 1.3.6.1.4.1.231.7.1.2.2.1.1.4.1.7
		shePhysBrdControlRedundancyFeature OBJECT-TYPE
			SYNTAX ShePhysRedundancyFeatureType
			MAX-ACCESS read-write
			STATUS current
			DESCRIPTION
				"Only applicable for CXU-board."
			::= { shePhysBoardRedundancyControl 7 }

		
-- 1.3.6.1.4.1.231.7.1.2.2.1.1.4.1.8
		shePhysBrdControlRedundancyInterlink OBJECT-TYPE
			SYNTAX ShePhysRedundancyInterlinkType
			MAX-ACCESS read-write
			STATUS current
			DESCRIPTION
				"Configure a medium type for connecting interlink ports on board redundancy."
			::= { shePhysBoardRedundancyControl 8 }

		
-- 1.3.6.1.4.1.231.7.1.2.2.1.1.4.2
		shePhysRedundancyBase OBJECT IDENTIFIER ::= { shePhysRedundancyObjects 2 }

		
-- 1.3.6.1.4.1.231.7.1.2.2.1.1.4.2.1
		shePhysRedundancyFeature OBJECT-TYPE
			SYNTAX ShePhysRedundancyFeatureType
			MAX-ACCESS read-only
			STATUS current
			DESCRIPTION
				"Configure special features they are importend for redundancy handling."
			DEFVAL { noOpticalSplitter }
			::= { shePhysRedundancyBase 1 }

		
-- 1.3.6.1.4.1.231.7.1.2.2.1.1.4.2.2
		shePhysRedundancyInterlink OBJECT-TYPE
			SYNTAX ShePhysRedundancyInterlinkType
			MAX-ACCESS read-only
			STATUS current
			DESCRIPTION
				"Configure a medium type for connecting interlink ports on board redundancy."
			DEFVAL { electrical }
			::= { shePhysRedundancyBase 2 }

		
-- 1.3.6.1.4.1.231.7.1.2.2.1.1.5
		shePhysicalNotifications OBJECT IDENTIFIER ::= { shePhysical 5 }

		
-- --------------------------------------------------------------
-- SHE Physical MIB Notifications
-- --------------------------------------------------------------
-- The PPE NE destincts event from alarm notification. 
-- Event notification is an autonoumous message from the NE 
-- which is not stored in the NE and cannot be retrieved in case
-- it gets lost
-- Alarm notification are sent when an alarm is present and again
-- when it is  cleared.
-- Alarms currently present in the NE are stored in the 
-- AlarmTable (see SHE-ALARMING-MIB) and are deleted from the
-- table when they are cleared
-- Alarm notifications have a specific PDU including 
-- sheAlarmStatus, ...
-- --------------------------------------------------------------
-- Rack notification subgroup
-- --------------------------------------------------------------
-- 1.3.6.1.4.1.231.7.1.2.2.1.1.5.1
		shePhysRackEvents OBJECT IDENTIFIER ::= { shePhysicalNotifications 1 }

		
-- 1.3.6.1.4.1.231.7.1.2.2.1.1.5.1.1
		shePhysRackControlResult NOTIFICATION-TYPE
			OBJECTS { shePhysRackControlRequest, shePhysRackControlTimeStamp, shePhysRackControlReqResult }
			STATUS current
			DESCRIPTION 
				"Notification of rack command ending and result. "
			::= { shePhysRackEvents 1 }

		
-- 1.3.6.1.4.1.231.7.1.2.2.1.1.5.2
		shePhysRackAlarms OBJECT IDENTIFIER ::= { shePhysicalNotifications 2 }

		
-- rack alarms
-- 1.3.6.1.4.1.231.7.1.2.2.1.1.5.2.1
		shePhysDCAlarm0 NOTIFICATION-TYPE
			OBJECTS { sheAlarmTimeAndDate, sheAlarmReportingSource, sheAlarmReportingSourceType, sheAlarmSeverity }
			STATUS current
			DESCRIPTION 
				"Break down of power supply fan group 0 ."
			::= { shePhysRackAlarms 1 }

		
-- 1.3.6.1.4.1.231.7.1.2.2.1.1.5.2.2
		shePhysDCAlarm1 NOTIFICATION-TYPE
			OBJECTS { sheAlarmTimeAndDate, sheAlarmReportingSource, sheAlarmReportingSourceType, sheAlarmSeverity }
			STATUS current
			DESCRIPTION 
				"Break down of power supply fan group 1 ."
			::= { shePhysRackAlarms 2 }

		
-- 1.3.6.1.4.1.231.7.1.2.2.1.1.5.2.3
		shePhysFanAlarm0 NOTIFICATION-TYPE
			OBJECTS { sheAlarmTimeAndDate, sheAlarmReportingSource, sheAlarmReportingSourceType, sheAlarmSeverity }
			STATUS current
			DESCRIPTION 
				"Depending on used shelftype the alarm stand for:
				M400, M600, M1200, MDUS:
				->  Alarm for Fan 0.
				
				G100 G200 G400, G600, M1100, G1100:
				-> Fan control defective.
				"
			::= { shePhysRackAlarms 3 }

		
-- 1.3.6.1.4.1.231.7.1.2.2.1.1.5.2.4
		shePhysFanAlarm1 NOTIFICATION-TYPE
			OBJECTS { sheAlarmTimeAndDate, sheAlarmReportingSource, sheAlarmReportingSourceType, sheAlarmSeverity }
			STATUS current
			DESCRIPTION 
				"Depending on used shelftype the alarm stand for:
				M400, M600, M1200, MDUS:
				->  Alarm for Fan 1.
				
				G100 G200 G400, G600, M1100, G1100:
				-> Fan defective (Sum alarm)."
			::= { shePhysRackAlarms 4 }

		
-- 1.3.6.1.4.1.231.7.1.2.2.1.1.5.2.5
		shePhysFanAlarm2 NOTIFICATION-TYPE
			OBJECTS { sheAlarmTimeAndDate, sheAlarmReportingSource, sheAlarmReportingSourceType, sheAlarmSeverity }
			STATUS current
			DESCRIPTION 
				"Depending on used shelftype the alarm stand for:
				M400, M600, M1200:
				->  Alarm for Fan 2.
				
				G100 G200 G400, G600, M1100, G1100:
				-> Filter pad must be cleaned.
				
				MDUS:
				-> not used."
			::= { shePhysRackAlarms 5 }

		
-- 1.3.6.1.4.1.231.7.1.2.2.1.1.5.2.6
		shePhysFanAlarm3 NOTIFICATION-TYPE
			OBJECTS { sheAlarmTimeAndDate, sheAlarmReportingSource, sheAlarmReportingSourceType, sheAlarmSeverity }
			STATUS current
			DESCRIPTION 
				"Depending on used shelftype the alarm stand for:
				M400, M600, M1200:
				->  Alarm for Fan 3.
				
				G100 G200 G400, G600, M1100, G1100, MDUS:
				-> not used"
			::= { shePhysRackAlarms 6 }

		
-- 1.3.6.1.4.1.231.7.1.2.2.1.1.5.2.7
		shePhysFanAlarm4 NOTIFICATION-TYPE
			OBJECTS { sheAlarmTimeAndDate, sheAlarmReportingSource, sheAlarmReportingSourceType, sheAlarmSeverity }
			STATUS current
			DESCRIPTION 
				"Depending on used shelftype the alarm stand for:
				M400, M600, M1200:
				->  Alarm for Fan 4 (if equiped).
				
				G100 G200 G400, G600, M1100, G1100, MDUS:
				-> not used"
			::= { shePhysRackAlarms 7 }

		
-- 1.3.6.1.4.1.231.7.1.2.2.1.1.5.2.8
		shePhysFanAlarm5 NOTIFICATION-TYPE
			OBJECTS { sheAlarmTimeAndDate, sheAlarmReportingSource, sheAlarmReportingSourceType, sheAlarmSeverity }
			STATUS current
			DESCRIPTION 
				"Depending on used shelftype the alarm stand for:
				M400, M600, M1200:
				->  Alarm for Fan 4 (if equiped).
				
				G100 G200 G400, G600, M1100, G1100, MDUS:
				-> not used"
			::= { shePhysRackAlarms 8 }

		
-- --------------------------------------------------------------
-- Shelf notification subgroup
-- --------------------------------------------------------------
-- 1.3.6.1.4.1.231.7.1.2.2.1.1.5.3
		shePhysShelfEvents OBJECT IDENTIFIER ::= { shePhysicalNotifications 3 }

		
-- 1.3.6.1.4.1.231.7.1.2.2.1.1.5.3.1
		shePhysShelfControlResult NOTIFICATION-TYPE
			OBJECTS { shePhysShelfControlRequest, shePhysShelfControlTimeStamp, shePhysShelfControlReqResult }
			STATUS current
			DESCRIPTION 
				" Notification of chassis command ending and result. "
			::= { shePhysShelfEvents 1 }

		
-- 1.3.6.1.4.1.231.7.1.2.2.1.1.5.3.2
		shePhysShelfControlExternalAlarmsConfigurationChanged NOTIFICATION-TYPE
			OBJECTS { shePhysShelfControlStatus, shePhysShelfControlIndex, shePhysShelfControlReqResult, shePhysShelfControlTimeStamp, shePhysShelfControlExternalAlarmOutput01Usage, 
				shePhysShelfControlExternalAlarmOutput02Usage, shePhysShelfControlExternalAlarmOutput03Usage, shePhysShelfControlExternalAlarm01Level, shePhysShelfControlExternalAlarm01Usage, shePhysShelfControlExternalAlarm02Level, 
				shePhysShelfControlExternalAlarm02Usage, shePhysShelfControlExternalAlarm03Level, shePhysShelfControlExternalAlarm03Usage, shePhysShelfControlExternalAlarm04Level, shePhysShelfControlExternalAlarm04Usage, 
				shePhysShelfControlExternalAlarm05Level, shePhysShelfControlExternalAlarm05Usage, shePhysShelfControlExternalAlarm06Level, shePhysShelfControlExternalAlarm06Usage, shePhysShelfControlExternalAlarm07Level, 
				shePhysShelfControlExternalAlarm07Usage, shePhysShelfControlExternalAlarm08Level, shePhysShelfControlExternalAlarm08Usage }
			STATUS current
			DESCRIPTION 
				"External alarm configuration changed."
			::= { shePhysShelfEvents 2 }

		
-- 1.3.6.1.4.1.231.7.1.2.2.1.1.5.3.3
		shePhysShelfControlRelativeHumidityAlarmThresholdChanged NOTIFICATION-TYPE
			OBJECTS { shePhysShelfControlStatus, shePhysShelfControlIndex, shePhysShelfControlReqResult, shePhysShelfControlTimeStamp, shePhysShelfControlRelativeHumidityAlarmOn, 
				shePhysShelfControlRelativeHumidityAlarmOff }
			STATUS current
			DESCRIPTION 
				"Alarm threshold configuration changed."
			::= { shePhysShelfEvents 3 }

		
		shePhysShelfBatteryBackupModified NOTIFICATION-TYPE
			OBJECTS { shePhysShelfControlTimeStamp, shePhysShelfControlBatteryBackupMode }
			STATUS current
			DESCRIPTION 
				"Could only occur in shelf SHE hiX5622 R1.0 -> MDUS:E, if battery backupMode was modified."
			::= { shePhysShelfEvents 4 }

		
-- 1.3.6.1.4.1.231.7.1.2.2.1.1.5.3.5
		shePhysShelfControlExternalAlarmsOutputStatusChanged NOTIFICATION-TYPE
			OBJECTS { shePhysShelfControlStatus, shePhysShelfControlIndex, shePhysShelfControlReqResult, shePhysShelfControlTimeStamp, shePhysShelfControlExternalAlarmOutput01Status, 
				shePhysShelfControlExternalAlarmOutput02Status, shePhysShelfControlExternalAlarmOutput03Status }
			STATUS current
			DESCRIPTION 
				"External alarm output status configuration changed."
			::= { shePhysShelfEvents 5 }

		
-- 1.3.6.1.4.1.231.7.1.2.2.1.1.5.4
		shePhysShelfAlarms OBJECT IDENTIFIER ::= { shePhysicalNotifications 4 }

		
-- shelf alarms
-- 1.3.6.1.4.1.231.7.1.2.2.1.1.5.4.1
		shePhysShelfMupState1 NOTIFICATION-TYPE
			OBJECTS { sheAlarmTimeAndDate, sheAlarmReportingSource, sheAlarmReportingSourceType, sheAlarmSeverity }
			STATUS current
			DESCRIPTION 
				"Break down of redundancy power supply 1 ( Power Supply or battery ).
				
				Note:
				This alarm will never occur in case of used shelftype G400R/G600:R:E with plugged PM_R module.
				"
			::= { shePhysShelfAlarms 1 }

		
-- 1.3.6.1.4.1.231.7.1.2.2.1.1.5.4.2
		shePhysShelfMupState2 NOTIFICATION-TYPE
			OBJECTS { sheAlarmTimeAndDate, sheAlarmReportingSource, sheAlarmReportingSourceType, sheAlarmSeverity }
			STATUS current
			DESCRIPTION 
				"Break down of redundancy power supply 2 ( Power Supply or battery ).
				
				Note:
				This alarm will never occur in case of used shelftype G400R/G600:R:E with plugged PM_R module."
			::= { shePhysShelfAlarms 2 }

		
-- 1.3.6.1.4.1.231.7.1.2.2.1.1.5.4.3
		shePhysShelfExternalAlarm01 NOTIFICATION-TYPE
			OBJECTS { sheAlarmTimeAndDate, sheAlarmReportingSource, sheAlarmReportingSourceType, sheAlarmSeverity }
			STATUS current
			DESCRIPTION 
				"External Alarm 01.
				
				Default usage in hix5622 R1.0 system (shelftyp MDUS:E):
				AC Failure -> Powering Alarm -  Loss of external power."
			::= { shePhysShelfAlarms 3 }

		
-- 1.3.6.1.4.1.231.7.1.2.2.1.1.5.4.4
		shePhysShelfExternalAlarm02 NOTIFICATION-TYPE
			OBJECTS { sheAlarmTimeAndDate, sheAlarmReportingSource, sheAlarmReportingSourceType, sheAlarmSeverity }
			STATUS current
			DESCRIPTION 
				"External Alarm 2.
				
				Default usage in hix5622 R1.0 system (shelftyp MDUS:E):
				DC Failure (internal fault) -> Equipment Alarm - A functional failure on an internal interface."
			::= { shePhysShelfAlarms 4 }

		
-- 1.3.6.1.4.1.231.7.1.2.2.1.1.5.4.5
		shePhysShelfExternalAlarm03 NOTIFICATION-TYPE
			OBJECTS { sheAlarmTimeAndDate, sheAlarmReportingSource, sheAlarmReportingSourceType, sheAlarmSeverity }
			STATUS current
			DESCRIPTION 
				"External Alarm 3.
				
				Default usage in hix5622 system R1.0 (shelftyp MDUS:E):
				Deep battery discharge -> Battery Low - battery is provisioned and present but voltage is too low.
				"
			::= { shePhysShelfAlarms 5 }

		
-- 1.3.6.1.4.1.231.7.1.2.2.1.1.5.4.6
		shePhysShelfExternalAlarm04 NOTIFICATION-TYPE
			OBJECTS { sheAlarmTimeAndDate, sheAlarmReportingSource, sheAlarmReportingSourceType, sheAlarmSeverity }
			STATUS current
			DESCRIPTION 
				"External Alarm 4.
				
				Default usage in hix5622 R1.0 system (shelftyp MDUS:E):
				Battery missing -> Battery is provisioned but missing."
			::= { shePhysShelfAlarms 6 }

		
-- 1.3.6.1.4.1.231.7.1.2.2.1.1.5.4.7
		shePhysShelfExternalAlarm05 NOTIFICATION-TYPE
			OBJECTS { sheAlarmTimeAndDate, sheAlarmReportingSource, sheAlarmReportingSourceType, sheAlarmSeverity }
			STATUS current
			DESCRIPTION 
				"External Alarm 5.
				
				Default usage in hix5622 R1.0 system (shelftyp MDUS:E):
				Battery replace (end of life) -> Battery Failure - Battery is provisioned and present but cannot recharge.
				"
			::= { shePhysShelfAlarms 7 }

		
-- 1.3.6.1.4.1.231.7.1.2.2.1.1.5.4.8
		shePhysShelfExternalAlarm06 NOTIFICATION-TYPE
			OBJECTS { sheAlarmTimeAndDate, sheAlarmReportingSource, sheAlarmReportingSourceType, sheAlarmSeverity }
			STATUS current
			DESCRIPTION 
				"External Alarm 6.
				
				Default usage in hix5622 R1.0 system (shelftyp MDUS:E):
				Door Contact -> Physical Intrusion alarm.
				"
			::= { shePhysShelfAlarms 8 }

		
-- 1.3.6.1.4.1.231.7.1.2.2.1.1.5.4.9
		shePhysShelfExternalAlarm07 NOTIFICATION-TYPE
			OBJECTS { sheAlarmTimeAndDate, sheAlarmReportingSource, sheAlarmReportingSourceType, sheAlarmSeverity }
			STATUS current
			DESCRIPTION 
				"External Alarm 7."
			::= { shePhysShelfAlarms 9 }

		
-- 1.3.6.1.4.1.231.7.1.2.2.1.1.5.4.10
		shePhysShelfExternalAlarm08 NOTIFICATION-TYPE
			OBJECTS { sheAlarmTimeAndDate, sheAlarmReportingSource, sheAlarmReportingSourceType, sheAlarmSeverity }
			STATUS current
			DESCRIPTION 
				"External Alarm 8."
			::= { shePhysShelfAlarms 10 }

		
-- 1.3.6.1.4.1.231.7.1.2.2.1.1.5.4.11
		shePhysShelfRelativeHumidityAlarm NOTIFICATION-TYPE
			OBJECTS { sheAlarmTimeAndDate, sheAlarmReportingSource, sheAlarmReportingSourceType, sheAlarmSeverity }
			STATUS current
			DESCRIPTION 
				"The configured threshold for relative humidity was reached. "
			::= { shePhysShelfAlarms 11 }

		
-- 1.3.6.1.4.1.231.7.1.2.2.1.1.5.4.12
		shePhysShelfHeatExchangerIn NOTIFICATION-TYPE
			OBJECTS { sheAlarmTimeAndDate, sheAlarmReportingSource, sheAlarmReportingSourceType, sheAlarmSeverity }
			STATUS current
			DESCRIPTION 
				"Break down of 1 or more fan of the heat exchanger inner circle.
				
				Note:
				This alarm could only occur in case of used shelftype G400R/G600:R:E with plugged PM_R module."
			::= { shePhysShelfAlarms 12 }

		
-- 1.3.6.1.4.1.231.7.1.2.2.1.1.5.4.13
		shePhysShelfHeatExchangerOut NOTIFICATION-TYPE
			OBJECTS { sheAlarmTimeAndDate, sheAlarmReportingSource, sheAlarmReportingSourceType, sheAlarmSeverity }
			STATUS current
			DESCRIPTION 
				"Break down of 1 or more fan of the heat exchanger outer circle.
				
				Note:
				This alarm could only occur in case of used shelftype G400R/G600:R:E with plugged PM_R module."
			::= { shePhysShelfAlarms 13 }

		
-- 1.3.6.1.4.1.231.7.1.2.2.1.1.5.4.14
		shePhysShelfExtAlarmCollectorNotConnected NOTIFICATION-TYPE
			OBJECTS { sheAlarmTimeAndDate, sheAlarmReportingSource, sheAlarmReportingSourceType, sheAlarmSeverity }
			STATUS current
			DESCRIPTION 
				"External Alarm Collector is not connected. The detection of external Alarms is not possible.
				
				Only valid if powermodule PM:ONU:2G:E is used."
			::= { shePhysShelfAlarms 14 }

		
-- --------------------------------------------------------------
-- Card notification subgroup
-- --------------------------------------------------------------
-- 1.3.6.1.4.1.231.7.1.2.2.1.1.5.5
		shePhysCardEvents OBJECT IDENTIFIER ::= { shePhysicalNotifications 5 }

		
-- card events
-- result trap for card specific user commands
-- 1.3.6.1.4.1.231.7.1.2.2.1.1.5.5.1
		shePhysCardControlResult NOTIFICATION-TYPE
			OBJECTS { shePhysCardControlTimeStamp, entPhysicalIndex, shePhysCardControlRequest, shePhysCardControlReqResult, shePhysCardControlPhysicalName
				 }
			STATUS current
			DESCRIPTION 
				" Notification sent end of a long running card command. "
			::= { shePhysCardEvents 1 }

		
-- 1.3.6.1.4.1.231.7.1.2.2.1.1.5.5.2
		shePhysCardAdminStateChanged NOTIFICATION-TYPE
			OBJECTS { shePhysCardControlTimeStamp, shePhysCardAdminState }
			STATUS current
			DESCRIPTION 
				" The card´s adminState changed. "
			::= { shePhysCardEvents 2 }

		
-- 1.3.6.1.4.1.231.7.1.2.2.1.1.5.5.3
		shePhysCardStateChanged NOTIFICATION-TYPE
			OBJECTS { shePhysCardControlTimeStamp, shePhysCardOperState, shePhysCardAvailState }
			STATUS current
			DESCRIPTION 
				" The card´s operational/availabilty state changed. "
			::= { shePhysCardEvents 3 }

		
-- 1.3.6.1.4.1.231.7.1.2.2.1.1.5.5.4
		shePhysCardReset NOTIFICATION-TYPE
			OBJECTS { shePhysCardControlTimeStamp, entPhysicalIndex }
			STATUS current
			DESCRIPTION 
				" Card is performing a reset. "
			::= { shePhysCardEvents 4 }

		
-- 1.3.6.1.4.1.231.7.1.2.2.1.1.5.5.5
		shePhysCardResetEnd NOTIFICATION-TYPE
			OBJECTS { shePhysCardControlTimeStamp, entPhysicalIndex }
			STATUS current
			DESCRIPTION 
				" End of card reset. "
			::= { shePhysCardEvents 5 }

		
-- 1.3.6.1.4.1.231.7.1.2.2.1.1.5.5.6
		shePhysCardCreated NOTIFICATION-TYPE
			OBJECTS { shePhysCardControlTimeStamp, entPhysicalIndex }
			STATUS current
			DESCRIPTION 
				" Card created. "
			::= { shePhysCardEvents 6 }

		
-- 1.3.6.1.4.1.231.7.1.2.2.1.1.5.5.7
		shePhysCardDeleted NOTIFICATION-TYPE
			OBJECTS { shePhysCardControlTimeStamp, entPhysicalIndex }
			STATUS current
			DESCRIPTION 
				" Card deleted. "
			::= { shePhysCardEvents 7 }

		
-- 1.3.6.1.4.1.231.7.1.2.2.1.1.5.5.8
		shePhysCardDeletionStarted NOTIFICATION-TYPE
			OBJECTS { entPhysicalIndex, shePhysCardControlTimeStamp }
			STATUS current
			DESCRIPTION 
				"The card deletion procedure in the NE was started."
			::= { shePhysCardEvents 8 }

		
-- 1.3.6.1.4.1.231.7.1.2.2.1.1.5.5.9
		shePhysContainerCardTypeConverted NOTIFICATION-TYPE
			OBJECTS { shePhysCardControlTimeStamp, entPhysicalIndex }
			STATUS current
			DESCRIPTION 
				" Card type converted. "
			::= { shePhysCardEvents 9 }

		
-- 1.3.6.1.4.1.231.7.1.2.2.1.1.5.5.10
		shePhysCardConvertionStarted NOTIFICATION-TYPE
			OBJECTS { entPhysicalIndex, shePhysCardControlTimeStamp }
			STATUS current
			DESCRIPTION 
				"The card convertion procedure in the NE was started."
			::= { shePhysCardEvents 10 }

		
-- 1.3.6.1.4.1.231.7.1.2.2.1.1.5.5.11
		shePhysCardPlugged NOTIFICATION-TYPE
			OBJECTS { entPhysicalIndex }
			STATUS current
			DESCRIPTION 
				"A card was plugged. This notification contains a list of two entPhysicalIndices.
				First is the entPhysicalIndex of the slot, were these module was plugged and the second,
				the entPhysicalIndex of the card itself."
			::= { shePhysCardEvents 11 }

		
-- 1.3.6.1.4.1.231.7.1.2.2.1.1.5.5.12
		shePhysCardUnplugged NOTIFICATION-TYPE
			OBJECTS { entPhysicalIndex }
			STATUS current
			DESCRIPTION 
				"A card was unplugged. This notification contains a list of two entPhysicalIndices.
				First is the entPhysicalIndex of the slot, were these module was plugged before and 
				the second, the entPhysicalIndex of the card itself."
			::= { shePhysCardEvents 12 }

		
-- 1.3.6.1.4.1.231.7.1.2.2.1.1.5.5.13
		shePhysCardChangedTemperatureThreshold NOTIFICATION-TYPE
			OBJECTS { shePhysCardControlTemperatureThreshold }
			STATUS obsolete
			DESCRIPTION 
				"The temperature threshold has been configured. 
				
				THIS ELEMENT WILL NOT LONGER BE SUPPORTED BY NE up R2.5."
			::= { shePhysCardEvents 13 }

		
-- 1.3.6.1.4.1.231.7.1.2.2.1.1.5.5.13
		shePhysCardTemperatureWarningThresholdsChanged NOTIFICATION-TYPE
			OBJECTS { shePhysCardTemperatureControlTimeStamp, shePhysCardTemperatureControlWarningOn, shePhysCardTemperatureControlWarningOff }
			STATUS current
			DESCRIPTION 
				"Configuration event."
			::= { shePhysCardEvents 14 }

		
-- 1.3.6.1.4.1.231.7.1.2.2.1.1.5.6
		shePhysCardAlarms OBJECT IDENTIFIER ::= { shePhysicalNotifications 6 }

		
-- card alarms
-- 1.3.6.1.4.1.231.7.1.2.2.1.1.5.6.1
		shePhysCardTypeMismatch NOTIFICATION-TYPE
			OBJECTS { sheAlarmTimeAndDate, sheAlarmReportingSource, sheAlarmReportingSourceType, sheAlarmSeverity }
			STATUS current
			DESCRIPTION 
				" Wrong card is plugged. "
			::= { shePhysCardAlarms 1 }

		
-- 1.3.6.1.4.1.231.7.1.2.2.1.1.5.6.2
		shePhysCardFailure NOTIFICATION-TYPE
			OBJECTS { sheAlarmTimeAndDate, sheAlarmReportingSource, sheAlarmReportingSourceType, sheAlarmSeverity }
			STATUS current
			DESCRIPTION 
				" Card out of service. "
			::= { shePhysCardAlarms 2 }

		
-- 1.3.6.1.4.1.231.7.1.2.2.1.1.5.6.3
		shePhysCardProblem NOTIFICATION-TYPE
			OBJECTS { sheAlarmTimeAndDate, sheAlarmReportingSource, sheAlarmReportingSourceType, sheAlarmSeverity }
			STATUS current
			DESCRIPTION 
				" Card partly out of service. "
			::= { shePhysCardAlarms 3 }

		
-- 1.3.6.1.4.1.231.7.1.2.2.1.1.5.6.4
		shePhysCardNotInstalled NOTIFICATION-TYPE
			OBJECTS { sheAlarmTimeAndDate, sheAlarmReportingSource, sheAlarmReportingSourceType, sheAlarmSeverity }
			STATUS current
			DESCRIPTION 
				" Card not plugged. "
			::= { shePhysCardAlarms 4 }

		
-- Temperature alarms
-- 1.3.6.1.4.1.231.7.1.2.2.1.1.5.6.5
		shePhysCardTemperaturePowerDown NOTIFICATION-TYPE
			OBJECTS { sheAlarmTimeAndDate, sheAlarmReportingSource, sheAlarmReportingSourceType, sheAlarmSeverity }
			STATUS current
			DESCRIPTION 
				"Temperature alarm. The IU has detect high temperature and start's first action to reduce power consumption. "
			::= { shePhysCardAlarms 5 }

		
-- 1.3.6.1.4.1.231.7.1.2.2.1.1.5.6.6
		shePhysCardOverTemperatureReset NOTIFICATION-TYPE
			OBJECTS { sheAlarmTimeAndDate, sheAlarmReportingSource, sheAlarmReportingSourceType, sheAlarmSeverity }
			STATUS current
			DESCRIPTION 
				"CXU has forced IU-Card to reset because of over temperature."
			::= { shePhysCardAlarms 6 }

		
-- 1.3.6.1.4.1.231.7.1.2.2.1.1.5.6.7
		shePhysCardOverTemperatureThreshold NOTIFICATION-TYPE
			OBJECTS { sheAlarmTimeAndDate, sheAlarmReportingSource, sheAlarmReportingSourceType, sheAlarmSeverity }
			STATUS current
			DESCRIPTION 
				"  Card temperature Threshold alarm.
				
				THIS ELEMENT WILL NOT LONGER BE SUPPORTED BY NE up R2.5."
			::= { shePhysCardAlarms 7 }

		
-- 1.3.6.1.4.1.231.7.1.2.2.1.1.5.6.8
		shePhysCardTemperatureWarning NOTIFICATION-TYPE
			OBJECTS { sheAlarmTimeAndDate, sheAlarmReportingSource, sheAlarmReportingSourceType, sheAlarmSeverity }
			STATUS current
			DESCRIPTION 
				"Temperature warning alarm. The CXU has detected a higher temperature then the configured value.  "
			::= { shePhysCardAlarms 8 }

		
-- 1.3.6.1.4.1.231.7.1.2.2.1.1.5.6.9
		shePhysCardSWVersionProblem NOTIFICATION-TYPE
			OBJECTS { sheAlarmTimeAndDate, sheAlarmReportingSource, sheAlarmReportingSourceType, sheAlarmSeverity }
			STATUS current
			DESCRIPTION 
				"Card out of service due to wrong SW version. Please upgrade!"
			::= { shePhysCardAlarms 9 }

		
-- --------------------------------------------------------------
-- Port notification subgroup
-- --------------------------------------------------------------   
-- Port events
-- 1.3.6.1.4.1.231.7.1.2.2.1.1.5.7
		shePhysPortEvents OBJECT IDENTIFIER ::= { shePhysicalNotifications 7 }

		
-- standard notifications linkDown/linkUp (IF-MIB) sent
-- 1.3.6.1.4.1.231.7.1.2.2.1.1.5.7.1
		shePhysPortAdminStateChanged NOTIFICATION-TYPE
			OBJECTS { shePhysPortControlTimeStamp, ifAdminStatus }
			STATUS current
			DESCRIPTION 
				" The port´s adminState changed. Could be send as a collection trap. That means,
				this notification could contain more then one indexed ifAdminState. During system startup
				 normaly a large number of notifications are needed. In such a case, it is possible to 
				send only one notification per card which contain the ifAdminStates of all
				port's. "
			::= { shePhysPortEvents 1 }

		
-- 1.3.6.1.4.1.231.7.1.2.2.1.1.5.7.2
		shePhysPortOperStateChanged NOTIFICATION-TYPE
			OBJECTS { shePhysPortControlTimeStamp, ifOperStatus }
			STATUS current
			DESCRIPTION 
				" The port´s operational state changed. Could be send as a collection trap. That means,
				this notification could contain more then one indexed ifOperState. During system startup
				 normaly a large number of notifications are needed. In such a case, it is possible to 
				send only one notification per card which contain the ifOperStates of all
				port's."
			::= { shePhysPortEvents 2 }

		
-- 1.3.6.1.4.1.231.7.1.2.2.1.1.5.7.3
		shePhysPortControlResult NOTIFICATION-TYPE
			OBJECTS { shePhysPortControlTimeStamp, shePhysPortControlRequest, shePhysPortControlReqResult }
			STATUS current
			DESCRIPTION 
				" Notification of port command ending and result. "
			::= { shePhysPortEvents 3 }

		
-- 1.3.6.1.4.1.231.7.1.2.2.1.1.5.7.4
		shePhysPortCreated NOTIFICATION-TYPE
			OBJECTS { ifIndex, shePhysPortEntPhysicalIndex, shePhysPortControlTimeStamp }
			STATUS current
			DESCRIPTION 
				"Notification about port creation. Could be send as a collection trap. That means,
				this notification could contain more then one ifIndex. In case of a card creation 
				sequence, normaly a large number of PortCreated-notifications are needed. In such a
				case, it is possible to send only one notification which contain the ifIndeces of all
				created port's for the entPhysicalIndex of this new card."
			::= { shePhysPortEvents 4 }

		
-- 1.3.6.1.4.1.231.7.1.2.2.1.1.5.7.5
		shePhysPortDeleted NOTIFICATION-TYPE
			OBJECTS { ifIndex, shePhysPortEntPhysicalIndex, shePhysPortControlTimeStamp }
			STATUS current
			DESCRIPTION 
				"Notification about the succesfull delete of a port. Could be send as a collection trap. That means,
				this notification could contain more then one ifIndex. In case of a card deletion 
				sequence, normaly a large number of PortDeleted-notifications are needed. In such a
				case, it is possible to send only one notification which contain the ifIndeces of all
				deleted port's for the entPhysicalIndex of this card."
			::= { shePhysPortEvents 5 }

		
-- 1.3.6.1.4.1.231.7.1.2.2.1.1.5.8
		shePhysPortAlarms OBJECT IDENTIFIER ::= { shePhysicalNotifications 8 }

		
-- 1.3.6.1.4.1.231.7.1.2.2.1.1.5.8.1
		shePhysPortOperStateDown NOTIFICATION-TYPE
			OBJECTS { sheAlarmTimeAndDate, sheAlarmReportingSource, sheAlarmReportingSourceType, sheAlarmSeverity }
			STATUS current
			DESCRIPTION 
				"This is a operstate-down alarm trap. This trap could not be send as 
				collection trap (different from OperStateChanged - Event trap)!!
				This trap could be blocked by setting in alarmseverity-profile."
			::= { shePhysPortAlarms 1 }

		
-- --------------------------------------------------------------
-- Redundancy notification subgroup
-- --------------------------------------------------------------
-- 1.3.6.1.4.1.231.7.1.2.2.1.1.5.9
		shePhysRedundancyEvents OBJECT IDENTIFIER ::= { shePhysicalNotifications 9 }

		
-- redundancy events
-- 1.3.6.1.4.1.231.7.1.2.2.1.1.5.9.1
		shePhysBrdControlResult NOTIFICATION-TYPE
			OBJECTS { shePhysBrdControlTimeStamp, shePhysBrdControlRequest, shePhysBrdControlReqResult }
			STATUS current
			DESCRIPTION 
				" Notification of board redundancy command ending and result. "
			::= { shePhysRedundancyEvents 1 }

		
-- 1.3.6.1.4.1.231.7.1.2.2.1.1.5.9.2
		shePhysRedundancyStateChanged NOTIFICATION-TYPE
			OBJECTS { shePhysBrdControlTimeStamp, entPhysicalIndex, shePhysCardProtMode, shePhysCardProtDynamicRole, shePhysCardProtState, 
				shePhysCardProtCapability }
			STATUS current
			DESCRIPTION 
				"Notification of change of redundancy ralated attributes of a card."
			::= { shePhysRedundancyEvents 2 }

		
-- 1.3.6.1.4.1.231.7.1.2.2.1.1.5.9.3
		shePhysRedundancyFeatureModified NOTIFICATION-TYPE
			OBJECTS { shePhysBrdControlTimeStamp, shePhysRedundancyFeature }
			STATUS current
			DESCRIPTION 
				"Modification response trap."
			::= { shePhysRedundancyEvents 3 }

		
-- 1.3.6.1.4.1.231.7.1.2.2.1.1.5.9.4
		shePhysRedundancyInterlinkModified NOTIFICATION-TYPE
			OBJECTS { shePhysBrdControlTimeStamp, shePhysRedundancyInterlink }
			STATUS current
			DESCRIPTION 
				"The medium type for interlink has been changed."
			::= { shePhysRedundancyEvents 4 }

		
-- 1.3.6.1.4.1.231.7.1.2.2.1.1.5.10
		shePhysRedundancyAlarms OBJECT IDENTIFIER ::= { shePhysicalNotifications 10 }

		
-- redundancy alarms
-- 1.3.6.1.4.1.231.7.1.2.2.1.1.5.10.1
		shePhysRedundancyNoRedundancy NOTIFICATION-TYPE
			OBJECTS { sheAlarmTimeAndDate, sheAlarmReportingSource, sheAlarmReportingSourceType, sheAlarmSeverity }
			STATUS current
			DESCRIPTION 
				"Redundancy is not available for a card."
			::= { shePhysRedundancyAlarms 1 }

		
-- 1.3.6.1.4.1.231.7.1.2.2.1.1.6
		shePhysRackObjects OBJECT IDENTIFIER ::= { shePhysical 6 }

		
-- -----------------------------------------------------------------
-- SHE Rack Objects
-- -----------------------------------------------------------------
-- 1.3.6.1.4.1.231.7.1.2.2.1.1.6.1
		shePhysRackTable OBJECT-TYPE
			SYNTAX SEQUENCE OF ShePhysRackEntry
			MAX-ACCESS not-accessible
			STATUS current
			DESCRIPTION
				" The shelf/chassis table. "
			::= { shePhysRackObjects 1 }

		
-- 1.3.6.1.4.1.231.7.1.2.2.1.1.6.1.1
		shePhysRackEntry OBJECT-TYPE
			SYNTAX ShePhysRackEntry
			MAX-ACCESS not-accessible
			STATUS current
			DESCRIPTION
				" Entry of the rack table.
				The entries represent the SHE rack.
				"
			INDEX { entPhysicalIndex }
			::= { shePhysRackTable 1 }

		
		ShePhysRackEntry ::=
			SEQUENCE { 
				shePhysRackAlarmSeverityIndex
					SheAlarmSevProfileIndex
			 }

-- 1.3.6.1.4.1.231.7.1.2.2.1.1.6.1.1.1
		shePhysRackAlarmSeverityIndex OBJECT-TYPE
			SYNTAX SheAlarmSevProfileIndex
			MAX-ACCESS read-only
			STATUS current
			DESCRIPTION
				" A pointer to the instance of the alarm severity profile 
				that contains the severity assignments for alarms 
				reported by this managed entity. Default is 1. "
			::= { shePhysRackEntry 1 }

		
-- 1.3.6.1.4.1.231.7.1.2.2.1.1.6.2
		shePhysRackControl OBJECT IDENTIFIER ::= { shePhysRackObjects 2 }

		
-- 1.3.6.1.4.1.231.7.1.2.2.1.1.6.2.1
		shePhysRackControlRequest OBJECT-TYPE
			SYNTAX ShePhysControlRequestType
			MAX-ACCESS read-write
			STATUS current
			DESCRIPTION
				" The rack commands :
				changeAlarmSeverityProfile: 
				  the alarm severity profile of the rack is changed.        
				Notifications : 
				  shePhysRackControlResult at the command ending in case of long running command. "
			::= { shePhysRackControl 1 }

		
-- 1.3.6.1.4.1.231.7.1.2.2.1.1.6.2.2
		shePhysRackControlStatus OBJECT-TYPE
			SYNTAX SheControlStatusType
			MAX-ACCESS read-only
			STATUS current
			DESCRIPTION
				" The status of a user command. "
			::= { shePhysRackControl 2 }

		
-- 1.3.6.1.4.1.231.7.1.2.2.1.1.6.2.3
		shePhysRackControlIndex OBJECT-TYPE
			SYNTAX PhysicalIndex
			MAX-ACCESS read-write
			STATUS current
			DESCRIPTION
				" The entPhysicalIndex of the rack. "
			::= { shePhysRackControl 3 }

		
-- 1.3.6.1.4.1.231.7.1.2.2.1.1.6.2.4
		shePhysRackControlAlarmSeverityIndex OBJECT-TYPE
			SYNTAX SheAlarmSevProfileIndex
			MAX-ACCESS read-write
			STATUS current
			DESCRIPTION
				" The new AlarmSeverityIndex of the alarm severity profile 
				assigned to the rack. "
			::= { shePhysRackControl 4 }

		
-- 1.3.6.1.4.1.231.7.1.2.2.1.1.6.2.5
		shePhysRackControlTimeStamp OBJECT-TYPE
			SYNTAX Unsigned32
			UNITS "sec"
			MAX-ACCESS read-only
			STATUS current
			DESCRIPTION
				" The time stamp of the last command (end of command). "
			::= { shePhysRackControl 5 }

		
-- 1.3.6.1.4.1.231.7.1.2.2.1.1.6.2.6
		shePhysRackControlTimer OBJECT-TYPE
			SYNTAX Unsigned32
			MAX-ACCESS read-only
			STATUS current
			DESCRIPTION
				" The maximum wait time for the manager for command ending
				in case of long running user commands.
				The manager reads this value from the PPE SHE.
				The end of request indicates the trap ShePhysResult . "
			::= { shePhysRackControl 6 }

		
-- 1.3.6.1.4.1.231.7.1.2.2.1.1.6.2.7
		shePhysRackControlReqResult OBJECT-TYPE
			SYNTAX ShePhysControlRequestResultType
			MAX-ACCESS read-only
			STATUS current
			DESCRIPTION
				" The result of the last user command. "
			::= { shePhysRackControl 7 }

		
-- 1.3.6.1.4.1.231.7.1.2.2.1.1.7
		shePhysShelfObjects OBJECT IDENTIFIER ::= { shePhysical 7 }

		
-- -----------------------------------------------------------------
-- SHE Shelf Objects
-- -----------------------------------------------------------------
-- 1.3.6.1.4.1.231.7.1.2.2.1.1.7.1
		shePhysShelfTable OBJECT-TYPE
			SYNTAX SEQUENCE OF ShePhysShelfEntry
			MAX-ACCESS not-accessible
			STATUS current
			DESCRIPTION
				" The shelf/chassis table. "
			::= { shePhysShelfObjects 1 }

		
-- 1.3.6.1.4.1.231.7.1.2.2.1.1.7.1.1
		shePhysShelfEntry OBJECT-TYPE
			SYNTAX ShePhysShelfEntry
			MAX-ACCESS not-accessible
			STATUS current
			DESCRIPTION
				" Entry of the chassis table.
				The entries represent the SHE shelf(s).
				"
			INDEX { entPhysicalIndex }
			::= { shePhysShelfTable 1 }

		
		ShePhysShelfEntry ::=
			SEQUENCE { 
				shePhysShelfAlarmSeverityIndex
					SheAlarmSevProfileIndex,
				shePhysShelfTypeCode
					DisplayString,
				shePhysShelfExternalAlarmOutput01Status
					ShePhysShelfExternalAlarmOutputStatusType,
				shePhysShelfExternalAlarmOutput01Usage
					OCTET STRING,
				shePhysShelfExternalAlarmOutput02Status
					ShePhysShelfExternalAlarmOutputStatusType,
				shePhysShelfExternalAlarmOutput02Usage
					OCTET STRING,
				shePhysShelfExternalAlarmOutput03Status
					ShePhysShelfExternalAlarmOutputStatusType,
				shePhysShelfExternalAlarmOutput03Usage
					OCTET STRING,
				shePhysShelfExternalAlarm01Level
					ShePhysShelfExternalAlarmLevelType,
				shePhysShelfExternalAlarm01Usage
					OCTET STRING,
				shePhysShelfExternalAlarm02Level
					ShePhysShelfExternalAlarmLevelType,
				shePhysShelfExternalAlarm02Usage
					OCTET STRING,
				shePhysShelfExternalAlarm03Level
					ShePhysShelfExternalAlarmLevelType,
				shePhysShelfExternalAlarm03Usage
					OCTET STRING,
				shePhysShelfExternalAlarm04Level
					ShePhysShelfExternalAlarmLevelType,
				shePhysShelfExternalAlarm04Usage
					OCTET STRING,
				shePhysShelfExternalAlarm05Level
					ShePhysShelfExternalAlarmLevelType,
				shePhysShelfExternalAlarm05Usage
					OCTET STRING,
				shePhysShelfExternalAlarm06Level
					ShePhysShelfExternalAlarmLevelType,
				shePhysShelfExternalAlarm06Usage
					OCTET STRING,
				shePhysShelfExternalAlarm07Level
					ShePhysShelfExternalAlarmLevelType,
				shePhysShelfExternalAlarm07Usage
					OCTET STRING,
				shePhysShelfExternalAlarm08Level
					ShePhysShelfExternalAlarmLevelType,
				shePhysShelfExternalAlarm08Usage
					OCTET STRING,
				shePhysShelfRelativeHumidity
					Unsigned32,
				shePhysShelfRelativeHumidityAlarmOn
					Unsigned32,
				shePhysShelfRelativeHumidityAlarmOff
					Unsigned32,
				shePhysShelfBatteryBackupOption
					TruthValue,
				shePhysShelfBatteryBackupMode
					TruthValue
			 }

-- 1.3.6.1.4.1.231.7.1.2.2.1.1.7.1.1.1
		shePhysShelfAlarmSeverityIndex OBJECT-TYPE
			SYNTAX SheAlarmSevProfileIndex
			MAX-ACCESS read-only
			STATUS current
			DESCRIPTION
				" A pointer to the instance of the alarm severity profile 
				that contains the severity assignments for alarms 
				reported by this managed entity. Default is 1. "
			::= { shePhysShelfEntry 1 }

		
-- 1.3.6.1.4.1.231.7.1.2.2.1.1.7.1.1.2
		shePhysShelfTypeCode OBJECT-TYPE
			SYNTAX DisplayString
			MAX-ACCESS read-only
			STATUS current
			DESCRIPTION
				"Contains the typecode for the possible used She-Shelf's.
				Depending on the detected shelftype-code the corresponding system version will be displayed.
				
				Systemversion -> Shelftypes
				SHE hiX5635   -> M1200:E, M1100:E, G1100:E, G1100:A, G1100:B:E
				SHE hiX5630   -> M600:E, G600:E, G600:R:E, M600:DF:E
				SHE hiX5625   -> M400:E, G400:E, G400:R:A, 
				SHE hiX5622 R1.0  -> MDUS:E (obsolete because release was canceled)
				SHE hiX5608   -> 'empty' string because no shelf is used, single box system
				
				Shelftype's 2 generation - only new 2G powermodules could be used!  (>= with R2.8 maintenance)
				SHE hiX5635   -> G1100:2G:E, M1100:2G:E
				SHE hiX5630   -> G600:2G:E, G600:R:2G:E, 
				SHE hiX5625   -> G400:2G:E, G400:R:2G:E, 
				SHE hiX5622   -> G200:2G:E, G200S:2G:E"
			::= { shePhysShelfEntry 2 }

		
-- 1.3.6.1.4.1.231.7.1.2.2.1.1.7.1.1.3
		shePhysShelfExternalAlarmOutput01Status OBJECT-TYPE
			SYNTAX ShePhysShelfExternalAlarmOutputStatusType
			MAX-ACCESS read-only
			STATUS current
			DESCRIPTION
				"Status of the external alarm output 01."
			DEFVAL { notActive }
			::= { shePhysShelfEntry 3 }

		
-- 1.3.6.1.4.1.231.7.1.2.2.1.1.7.1.1.4
		shePhysShelfExternalAlarmOutput01Usage OBJECT-TYPE
			SYNTAX OCTET STRING (SIZE (0..64))
			MAX-ACCESS read-only
			STATUS current
			DESCRIPTION
				"Description for usage of this external alarm output. Only for managment interface and 
				no special meaning for the NE."
			::= { shePhysShelfEntry 4 }

		
-- 1.3.6.1.4.1.231.7.1.2.2.1.1.7.1.1.5
		shePhysShelfExternalAlarmOutput02Status OBJECT-TYPE
			SYNTAX ShePhysShelfExternalAlarmOutputStatusType
			MAX-ACCESS read-only
			STATUS current
			DESCRIPTION
				"Status of the external alarm output 02."
			DEFVAL { notActive }
			::= { shePhysShelfEntry 5 }

		
-- 1.3.6.1.4.1.231.7.1.2.2.1.1.7.1.1.6
		shePhysShelfExternalAlarmOutput02Usage OBJECT-TYPE
			SYNTAX OCTET STRING (SIZE (0..64))
			MAX-ACCESS read-only
			STATUS current
			DESCRIPTION
				"Description for usage of this external alarm output. Only for managment interface and 
				no special meaning for the NE."
			::= { shePhysShelfEntry 6 }

		
-- 1.3.6.1.4.1.231.7.1.2.2.1.1.7.1.1.7
		shePhysShelfExternalAlarmOutput03Status OBJECT-TYPE
			SYNTAX ShePhysShelfExternalAlarmOutputStatusType
			MAX-ACCESS read-only
			STATUS current
			DESCRIPTION
				"Status of the external alarm output 03."
			DEFVAL { notActive }
			::= { shePhysShelfEntry 7 }

		
-- 1.3.6.1.4.1.231.7.1.2.2.1.1.7.1.1.8
		shePhysShelfExternalAlarmOutput03Usage OBJECT-TYPE
			SYNTAX OCTET STRING (SIZE (0..64))
			MAX-ACCESS read-only
			STATUS current
			DESCRIPTION
				"Description for usage of this external alarm output. Only for managment interface and 
				no special meaning for the NE."
			::= { shePhysShelfEntry 8 }

		
-- 1.3.6.1.4.1.231.7.1.2.2.1.1.7.1.1.9
		shePhysShelfExternalAlarm01Level OBJECT-TYPE
			SYNTAX ShePhysShelfExternalAlarmLevelType
			MAX-ACCESS read-only
			STATUS current
			DESCRIPTION
				"Configured level for active alarm."
			DEFVAL { activeHigh }
			::= { shePhysShelfEntry 9 }

		
-- 1.3.6.1.4.1.231.7.1.2.2.1.1.7.1.1.10
		shePhysShelfExternalAlarm01Usage OBJECT-TYPE
			SYNTAX OCTET STRING (SIZE (0..64))
			MAX-ACCESS read-only
			STATUS current
			DESCRIPTION
				"Description for usage of this external alarm. Only for managment interface and 
				no special meaning for the NE.
				
				Default usage in hiX5622 R1.0 system (shelftyp MDUS:E): AC Failure -> Powering Alarm -  Loss of external power
				Default usage in hiX5608 R1.0 system: Door Contact -> Physical Intrusion alarm."
			::= { shePhysShelfEntry 10 }

		
-- 1.3.6.1.4.1.231.7.1.2.2.1.1.7.1.1.11
		shePhysShelfExternalAlarm02Level OBJECT-TYPE
			SYNTAX ShePhysShelfExternalAlarmLevelType
			MAX-ACCESS read-only
			STATUS current
			DESCRIPTION
				"Configured level for active alarm."
			DEFVAL { activeHigh }
			::= { shePhysShelfEntry 11 }

		
-- 1.3.6.1.4.1.231.7.1.2.2.1.1.7.1.1.12
		shePhysShelfExternalAlarm02Usage OBJECT-TYPE
			SYNTAX OCTET STRING (SIZE (0..64))
			MAX-ACCESS read-only
			STATUS current
			DESCRIPTION
				"Description for usage of this external alarm. Only for managment interface and 
				no special meaning for the NE.
				
				Default usage in hix5622 R1.0 system (shelftyp MDUS:E):
				DC Failure (internal fault) -> Equipment Alarm - A functional failure on an internal interface."
			::= { shePhysShelfEntry 12 }

		
-- 1.3.6.1.4.1.231.7.1.2.2.1.1.7.1.1.13
		shePhysShelfExternalAlarm03Level OBJECT-TYPE
			SYNTAX ShePhysShelfExternalAlarmLevelType
			MAX-ACCESS read-only
			STATUS current
			DESCRIPTION
				"Configured level for active alarm."
			DEFVAL { activeHigh }
			::= { shePhysShelfEntry 13 }

		
-- 1.3.6.1.4.1.231.7.1.2.2.1.1.7.1.1.14
		shePhysShelfExternalAlarm03Usage OBJECT-TYPE
			SYNTAX OCTET STRING (SIZE (0..64))
			MAX-ACCESS read-only
			STATUS current
			DESCRIPTION
				"Description for usage of this external alarm. Only for managment interface and 
				no special meaning for the NE.
				
				Default usage in hix5622 R1.0 system (shelftyp MDUS:E):
				Deep battery discharge -> Battery Low - battery is provisioned and present but voltage is too low."
			::= { shePhysShelfEntry 14 }

		
-- 1.3.6.1.4.1.231.7.1.2.2.1.1.7.1.1.15
		shePhysShelfExternalAlarm04Level OBJECT-TYPE
			SYNTAX ShePhysShelfExternalAlarmLevelType
			MAX-ACCESS read-only
			STATUS current
			DESCRIPTION
				"Configured level for active alarm."
			DEFVAL { activeHigh }
			::= { shePhysShelfEntry 15 }

		
-- 1.3.6.1.4.1.231.7.1.2.2.1.1.7.1.1.16
		shePhysShelfExternalAlarm04Usage OBJECT-TYPE
			SYNTAX OCTET STRING (SIZE (0..64))
			MAX-ACCESS read-only
			STATUS current
			DESCRIPTION
				"Description for usage of this external alarm. Only for managment interface and 
				no special meaning for the NE.
				
				Default usage in hix5622 R1.0 system (shelftyp MDUS:E):
				Battery missing -> Battery is provisioned but missing."
			::= { shePhysShelfEntry 16 }

		
-- 1.3.6.1.4.1.231.7.1.2.2.1.1.7.1.1.17
		shePhysShelfExternalAlarm05Level OBJECT-TYPE
			SYNTAX ShePhysShelfExternalAlarmLevelType
			MAX-ACCESS read-only
			STATUS current
			DESCRIPTION
				"Configured level for active alarm."
			DEFVAL { activeHigh }
			::= { shePhysShelfEntry 17 }

		
-- 1.3.6.1.4.1.231.7.1.2.2.1.1.7.1.1.18
		shePhysShelfExternalAlarm05Usage OBJECT-TYPE
			SYNTAX OCTET STRING (SIZE (0..64))
			MAX-ACCESS read-only
			STATUS current
			DESCRIPTION
				"Description for usage of this external alarm. Only for managment interface and 
				no special meaning for the NE.
				
				Default usage in hix5622 R1.0 system (shelftyp MDUS:E):
				Battery replace (end of life) -> Battery Failure - Battery is provisioned and present but cannot recharge."
			::= { shePhysShelfEntry 18 }

		
-- 1.3.6.1.4.1.231.7.1.2.2.1.1.7.1.1.19
		shePhysShelfExternalAlarm06Level OBJECT-TYPE
			SYNTAX ShePhysShelfExternalAlarmLevelType
			MAX-ACCESS read-only
			STATUS current
			DESCRIPTION
				"Configured level for active alarm."
			DEFVAL { activeHigh }
			::= { shePhysShelfEntry 19 }

		
-- 1.3.6.1.4.1.231.7.1.2.2.1.1.7.1.1.20
		shePhysShelfExternalAlarm06Usage OBJECT-TYPE
			SYNTAX OCTET STRING (SIZE (0..64))
			MAX-ACCESS read-only
			STATUS current
			DESCRIPTION
				"Description for usage of this external alarm. Only for managment interface and 
				no special meaning for the NE.
				
				Default usage in hix5622 R1.0 system (shelftyp MDUS:E):
				Door Contact -> Physical Intrusion alarm."
			::= { shePhysShelfEntry 20 }

		
-- 1.3.6.1.4.1.231.7.1.2.2.1.1.7.1.1.21
		shePhysShelfExternalAlarm07Level OBJECT-TYPE
			SYNTAX ShePhysShelfExternalAlarmLevelType
			MAX-ACCESS read-only
			STATUS current
			DESCRIPTION
				"Configured level for active alarm."
			DEFVAL { activeHigh }
			::= { shePhysShelfEntry 21 }

		
-- 1.3.6.1.4.1.231.7.1.2.2.1.1.7.1.1.22
		shePhysShelfExternalAlarm07Usage OBJECT-TYPE
			SYNTAX OCTET STRING (SIZE (0..64))
			MAX-ACCESS read-only
			STATUS current
			DESCRIPTION
				"Description for usage of this external alarm. Only for managment interface and 
				no special meaning for the NE."
			::= { shePhysShelfEntry 22 }

		
-- 1.3.6.1.4.1.231.7.1.2.2.1.1.7.1.1.23
		shePhysShelfExternalAlarm08Level OBJECT-TYPE
			SYNTAX ShePhysShelfExternalAlarmLevelType
			MAX-ACCESS read-only
			STATUS current
			DESCRIPTION
				"Configured level for active alarm."
			DEFVAL { activeHigh }
			::= { shePhysShelfEntry 23 }

		
-- 1.3.6.1.4.1.231.7.1.2.2.1.1.7.1.1.24
		shePhysShelfExternalAlarm08Usage OBJECT-TYPE
			SYNTAX OCTET STRING (SIZE (0..64))
			MAX-ACCESS read-only
			STATUS current
			DESCRIPTION
				"Description for usage of this external alarm. Only for managment interface and 
				no special meaning for the NE."
			::= { shePhysShelfEntry 24 }

		
-- 1.3.6.1.4.1.231.7.1.2.2.1.1.7.1.1.25
		shePhysShelfRelativeHumidity OBJECT-TYPE
			SYNTAX Unsigned32 (0..100 | 255)
			UNITS "%"
			MAX-ACCESS read-only
			STATUS current
			DESCRIPTION
				"Environmentale parameter for relative humidity in %.
				This parameter is only valid for shelftype G400R//G600:R:E with powermodule PM_R is plugged
				and optional humidity sensor is available.
				In all other cases the value 255 will report, that a valid measurement result is not available."
			::= { shePhysShelfEntry 25 }

		
-- 1.3.6.1.4.1.231.7.1.2.2.1.1.7.1.1.26
		shePhysShelfRelativeHumidityAlarmOn OBJECT-TYPE
			SYNTAX Unsigned32 (0..100)
			UNITS "%"
			MAX-ACCESS read-only
			STATUS current
			DESCRIPTION
				"Environmentale parameter for relative humidity alarm threshold on.
				This parameter is only valid for shelftype G400R/G600:R:E with powermodule PM_R is plugged
				and optional humidity sensor is available."
			DEFVAL { 75 }
			::= { shePhysShelfEntry 26 }

		
-- 1.3.6.1.4.1.231.7.1.2.2.1.1.7.1.1.27
		shePhysShelfRelativeHumidityAlarmOff OBJECT-TYPE
			SYNTAX Unsigned32 (0..100)
			UNITS "%"
			MAX-ACCESS read-only
			STATUS current
			DESCRIPTION
				"Environmentale parameter for relative humidity alarm threshold off.
				This parameter is only valid for shelftype G400R/G600:R:E with powermodule PM_R is plugged
				and optional humidity sensor is available."
			DEFVAL { 60 }
			::= { shePhysShelfEntry 27 }

		
		shePhysShelfBatteryBackupOption OBJECT-TYPE
			SYNTAX TruthValue
			MAX-ACCESS read-only
			STATUS current
			DESCRIPTION
				"Indication wether the SHE supports battery backup.
				Only shelftype SHE hiX5622 R1.0 -> MDUS:E will support battery backup, otherwise false."
			DEFVAL { false }
			::= { shePhysShelfEntry 28 }

		
		shePhysShelfBatteryBackupMode OBJECT-TYPE
			SYNTAX TruthValue
			MAX-ACCESS read-only
			STATUS current
			DESCRIPTION
				"Indication wether battery backup is provisioned.
				Only valid for shelftype SHE hiX5622 R1.0 -> MDUS:E."
			::= { shePhysShelfEntry 29 }

		
-- 1.3.6.1.4.1.231.7.1.2.2.1.1.7.2
		shePhysShelfControl OBJECT IDENTIFIER ::= { shePhysShelfObjects 2 }

		
-- 1.3.6.1.4.1.231.7.1.2.2.1.1.7.2.1
		shePhysShelfControlRequest OBJECT-TYPE
			SYNTAX ShePhysControlRequestType
			MAX-ACCESS read-write
			STATUS current
			DESCRIPTION
				"The chassis commands :
				
				changeAlarmSeverityProfile: 
				  the alarm severity profile of the chassis is changed.      
				
				changeShelfExternalAlarmSettings
				  change level for active external alarms and set a descriptional name for usage  
				Notifications :
				 shePhysShelfControlExternalAlarmsConfigurationChanged 
				 shePhysShelfControlResult at the command ending in case of long running command. 
				
				changeShelfRelativeHumidityAlarmThreshold
				  change the alarm threshold configuration for environmental parameter relative humidity
				Notifications:
				 shePhysShelfControlRelativeHumidityAlarmThresholdChanged
				
				hiX5622 R1.0 only:
				changeShelfBatteryBackupMode:
				  shePhysShelfControlBatteryBackupMode
				Notifications:
				 shePhysShelfBatteryBackupModified
				
				New with R2.8:
				changeShelfExternalAlarmOutputStatus
				  change status external alarm outputs
				Notifications : 
				 shePhysShelfControlExternalAlarmsOutputStatusChanged 
				"
			::= { shePhysShelfControl 1 }

		
-- 1.3.6.1.4.1.231.7.1.2.2.1.1.7.2.2
		shePhysShelfControlStatus OBJECT-TYPE
			SYNTAX SheControlStatusType
			MAX-ACCESS read-only
			STATUS current
			DESCRIPTION
				" The status of a user command. "
			::= { shePhysShelfControl 2 }

		
-- 1.3.6.1.4.1.231.7.1.2.2.1.1.7.2.3
		shePhysShelfControlIndex OBJECT-TYPE
			SYNTAX PhysicalIndex
			MAX-ACCESS read-write
			STATUS current
			DESCRIPTION
				" The entPhysicalIndex of the shelf. "
			::= { shePhysShelfControl 3 }

		
-- 1.3.6.1.4.1.231.7.1.2.2.1.1.7.2.4
		shePhysShelfControlTimeStamp OBJECT-TYPE
			SYNTAX Unsigned32
			UNITS "sec"
			MAX-ACCESS read-only
			STATUS current
			DESCRIPTION
				" The time stamp of the last command (end of command). "
			::= { shePhysShelfControl 4 }

		
-- 1.3.6.1.4.1.231.7.1.2.2.1.1.7.2.5
		shePhysShelfControlTimer OBJECT-TYPE
			SYNTAX Unsigned32
			MAX-ACCESS read-only
			STATUS current
			DESCRIPTION
				" The maximum wait time for the manager for command ending
				in case of long running user commands.
				The manager reads this value from the PPE SHE.
				The end of request indicates the trap ShePhysRiResult . "
			::= { shePhysShelfControl 5 }

		
-- 1.3.6.1.4.1.231.7.1.2.2.1.1.7.2.6
		shePhysShelfControlReqResult OBJECT-TYPE
			SYNTAX ShePhysControlRequestResultType
			MAX-ACCESS read-only
			STATUS current
			DESCRIPTION
				" The result of the last user command. "
			::= { shePhysShelfControl 6 }

		
-- 1.3.6.1.4.1.231.7.1.2.2.1.1.7.2.7
		shePhysShelfControlAlarmSeverityIndex OBJECT-TYPE
			SYNTAX SheAlarmSevProfileIndex
			MAX-ACCESS read-write
			STATUS current
			DESCRIPTION
				" The new AlarmSeverityIndex of the alarm severity profile 
				assigned to the chassis. "
			::= { shePhysShelfControl 7 }

		
-- 1.3.6.1.4.1.231.7.1.2.2.1.1.7.2.8
		shePhysShelfControlExternalAlarmOutput01Usage OBJECT-TYPE
			SYNTAX OCTET STRING (SIZE (0..64))
			MAX-ACCESS read-write
			STATUS current
			DESCRIPTION
				"Description for usage of this external alarm output. Only for managment interface and 
				no special meaning for the NE."
			::= { shePhysShelfControl 8 }

		
-- 1.3.6.1.4.1.231.7.1.2.2.1.1.7.2.9
		shePhysShelfControlExternalAlarmOutput02Usage OBJECT-TYPE
			SYNTAX OCTET STRING (SIZE (0..64))
			MAX-ACCESS read-write
			STATUS current
			DESCRIPTION
				"Description for usage of this external alarm output. Only for managment interface and 
				no special meaning for the NE."
			::= { shePhysShelfControl 9 }

		
-- 1.3.6.1.4.1.231.7.1.2.2.1.1.7.2.10
		shePhysShelfControlExternalAlarmOutput03Usage OBJECT-TYPE
			SYNTAX OCTET STRING (SIZE (0..64))
			MAX-ACCESS read-write
			STATUS current
			DESCRIPTION
				"Description for usage of this external alarm output. Only for managment interface and 
				no special meaning for the NE."
			::= { shePhysShelfControl 10 }

		
-- 1.3.6.1.4.1.231.7.1.2.2.1.1.7.2.11
		shePhysShelfControlExternalAlarm01Level OBJECT-TYPE
			SYNTAX ShePhysShelfExternalAlarmLevelType
			MAX-ACCESS read-write
			STATUS current
			DESCRIPTION
				"Configured level for active alarm."
			::= { shePhysShelfControl 11 }

		
-- 1.3.6.1.4.1.231.7.1.2.2.1.1.7.2.12
		shePhysShelfControlExternalAlarm01Usage OBJECT-TYPE
			SYNTAX OCTET STRING (SIZE (0..64))
			MAX-ACCESS read-write
			STATUS current
			DESCRIPTION
				"Description for usage of this external alarm. Only for managment interface and 
				no special meaning for the NE."
			::= { shePhysShelfControl 12 }

		
-- 1.3.6.1.4.1.231.7.1.2.2.1.1.7.2.13
		shePhysShelfControlExternalAlarm02Level OBJECT-TYPE
			SYNTAX ShePhysShelfExternalAlarmLevelType
			MAX-ACCESS read-write
			STATUS current
			DESCRIPTION
				"Configured level for active alarm."
			::= { shePhysShelfControl 13 }

		
-- 1.3.6.1.4.1.231.7.1.2.2.1.1.7.2.14
		shePhysShelfControlExternalAlarm02Usage OBJECT-TYPE
			SYNTAX OCTET STRING (SIZE (0..64))
			MAX-ACCESS read-write
			STATUS current
			DESCRIPTION
				"Description for usage of this external alarm. Only for managment interface and 
				no special meaning for the NE."
			::= { shePhysShelfControl 14 }

		
-- 1.3.6.1.4.1.231.7.1.2.2.1.1.7.2.15
		shePhysShelfControlExternalAlarm03Level OBJECT-TYPE
			SYNTAX ShePhysShelfExternalAlarmLevelType
			MAX-ACCESS read-write
			STATUS current
			DESCRIPTION
				"Configured level for active alarm."
			::= { shePhysShelfControl 15 }

		
-- 1.3.6.1.4.1.231.7.1.2.2.1.1.7.2.16
		shePhysShelfControlExternalAlarm03Usage OBJECT-TYPE
			SYNTAX OCTET STRING (SIZE (0..64))
			MAX-ACCESS read-write
			STATUS current
			DESCRIPTION
				"Description for usage of this external alarm. Only for managment interface and 
				no special meaning for the NE."
			::= { shePhysShelfControl 16 }

		
-- 1.3.6.1.4.1.231.7.1.2.2.1.1.7.2.17
		shePhysShelfControlExternalAlarm04Level OBJECT-TYPE
			SYNTAX ShePhysShelfExternalAlarmLevelType
			MAX-ACCESS read-write
			STATUS current
			DESCRIPTION
				"Configured level for active alarm."
			::= { shePhysShelfControl 17 }

		
-- 1.3.6.1.4.1.231.7.1.2.2.1.1.7.2.18
		shePhysShelfControlExternalAlarm04Usage OBJECT-TYPE
			SYNTAX OCTET STRING (SIZE (0..64))
			MAX-ACCESS read-write
			STATUS current
			DESCRIPTION
				"Description for usage of this external alarm. Only for managment interface and 
				no special meaning for the NE."
			::= { shePhysShelfControl 18 }

		
-- 1.3.6.1.4.1.231.7.1.2.2.1.1.7.2.19
		shePhysShelfControlExternalAlarm05Level OBJECT-TYPE
			SYNTAX ShePhysShelfExternalAlarmLevelType
			MAX-ACCESS read-write
			STATUS current
			DESCRIPTION
				"Configured level for active alarm."
			::= { shePhysShelfControl 19 }

		
-- 1.3.6.1.4.1.231.7.1.2.2.1.1.7.2.20
		shePhysShelfControlExternalAlarm05Usage OBJECT-TYPE
			SYNTAX OCTET STRING (SIZE (0..64))
			MAX-ACCESS read-write
			STATUS current
			DESCRIPTION
				"Description for usage of this external alarm. Only for managment interface and 
				no special meaning for the NE."
			::= { shePhysShelfControl 20 }

		
-- 1.3.6.1.4.1.231.7.1.2.2.1.1.7.2.21
		shePhysShelfControlExternalAlarm06Level OBJECT-TYPE
			SYNTAX ShePhysShelfExternalAlarmLevelType
			MAX-ACCESS read-write
			STATUS current
			DESCRIPTION
				"Configured level for active alarm."
			::= { shePhysShelfControl 21 }

		
-- 1.3.6.1.4.1.231.7.1.2.2.1.1.7.2.22
		shePhysShelfControlExternalAlarm06Usage OBJECT-TYPE
			SYNTAX OCTET STRING (SIZE (0..64))
			MAX-ACCESS read-write
			STATUS current
			DESCRIPTION
				"Description for usage of this external alarm. Only for managment interface and 
				no special meaning for the NE."
			::= { shePhysShelfControl 22 }

		
-- 1.3.6.1.4.1.231.7.1.2.2.1.1.7.2.23
		shePhysShelfControlExternalAlarm07Level OBJECT-TYPE
			SYNTAX ShePhysShelfExternalAlarmLevelType
			MAX-ACCESS read-write
			STATUS current
			DESCRIPTION
				"Configured level for active alarm."
			::= { shePhysShelfControl 23 }

		
-- 1.3.6.1.4.1.231.7.1.2.2.1.1.7.2.24
		shePhysShelfControlExternalAlarm07Usage OBJECT-TYPE
			SYNTAX OCTET STRING (SIZE (0..64))
			MAX-ACCESS read-write
			STATUS current
			DESCRIPTION
				"Description for usage of this external alarm. Only for managment interface and 
				no special meaning for the NE."
			::= { shePhysShelfControl 24 }

		
-- 1.3.6.1.4.1.231.7.1.2.2.1.1.7.2.25
		shePhysShelfControlExternalAlarm08Level OBJECT-TYPE
			SYNTAX ShePhysShelfExternalAlarmLevelType
			MAX-ACCESS read-write
			STATUS current
			DESCRIPTION
				"Configured level for active alarm."
			::= { shePhysShelfControl 25 }

		
-- 1.3.6.1.4.1.231.7.1.2.2.1.1.7.2.26
		shePhysShelfControlExternalAlarm08Usage OBJECT-TYPE
			SYNTAX OCTET STRING (SIZE (0..64))
			MAX-ACCESS read-write
			STATUS current
			DESCRIPTION
				"Description for usage of this external alarm. Only for managment interface and 
				no special meaning for the NE."
			::= { shePhysShelfControl 26 }

		
-- 1.3.6.1.4.1.231.7.1.2.2.1.1.7.2.27
		shePhysShelfControlRelativeHumidityAlarmOn OBJECT-TYPE
			SYNTAX Unsigned32 (0..100)
			UNITS "%"
			MAX-ACCESS read-write
			STATUS current
			DESCRIPTION
				"Configure the environmentale parameter for relative humidity alarm threshold on.
				This parameter is only valid for shelftype G400R/G600:R:E with powermodule PM_R is plugged
				and optional humidity sensor is available."
			::= { shePhysShelfControl 27 }

		
-- 1.3.6.1.4.1.231.7.1.2.2.1.1.7.2.28
		shePhysShelfControlRelativeHumidityAlarmOff OBJECT-TYPE
			SYNTAX Unsigned32 (0..100)
			UNITS "%"
			MAX-ACCESS read-write
			STATUS current
			DESCRIPTION
				"Configure the environmentale parameter for relative humidity alarm threshold off.
				This parameter is only valid for shelftype G400R/G600:R:E with powermodule PM_R is plugged
				and optional humidity sensor is available."
			::= { shePhysShelfControl 28 }

		
		shePhysShelfControlBatteryBackupMode OBJECT-TYPE
			SYNTAX TruthValue
			MAX-ACCESS read-write
			STATUS current
			DESCRIPTION
				"Provisioning of battery backup.
				Only valid for shelftype SHE hiX5622 R1.0 -> MDUS:E."
			::= { shePhysShelfControl 29 }

		
-- 1.3.6.1.4.1.231.7.1.2.2.1.1.7.2.8
		shePhysShelfControlExternalAlarmOutput01Status OBJECT-TYPE
			SYNTAX ShePhysShelfExternalAlarmOutputStatusType
			MAX-ACCESS read-write
			STATUS current
			DESCRIPTION
				"Set the status of the external alarm output 01."
			::= { shePhysShelfControl 30 }

		
-- 1.3.6.1.4.1.231.7.1.2.2.1.1.7.2.8
		shePhysShelfControlExternalAlarmOutput02Status OBJECT-TYPE
			SYNTAX ShePhysShelfExternalAlarmOutputStatusType
			MAX-ACCESS read-write
			STATUS current
			DESCRIPTION
				"Set the status of the external alarm output 02."
			::= { shePhysShelfControl 31 }

		
-- 1.3.6.1.4.1.231.7.1.2.2.1.1.7.2.8
		shePhysShelfControlExternalAlarmOutput03Status OBJECT-TYPE
			SYNTAX ShePhysShelfExternalAlarmOutputStatusType
			MAX-ACCESS read-write
			STATUS current
			DESCRIPTION
				"Set the status of the external alarm output 03."
			::= { shePhysShelfControl 32 }

		
-- conformance information
-- 1.3.6.1.4.1.231.7.1.2.2.1.1.100
		shePhysicalConformance OBJECT IDENTIFIER ::= { shePhysical 100 }

		
-- 1.3.6.1.4.1.231.7.1.2.2.1.1.100.1
		shePhysicalGroups OBJECT IDENTIFIER ::= { shePhysicalConformance 1 }

		
-- units of conformance
-- 1.3.6.1.4.1.231.7.1.2.2.1.1.100.1.1
		shePhysicalGroup OBJECT-GROUP
			OBJECTS { shePhysContainerAccCardTypes, shePhysContainerSlotStatus, shePhysContainerConfiguredCardType, shePhysContainerPluggedCardType, shePhysCardAdminState, 
				shePhysCardAvailState, shePhysCardOperState, shePhysCardProtCapability, shePhysCardProtMode, shePhysCardProtDefaultRole, 
				shePhysCardProtDynamicRole, shePhysCardProtGroupId, shePhysCardProtState, shePhysCardAlarmSeverityIndex, shePhysCardSwRunningLoad, 
				shePhysCardSwStoredLoad, shePhysCardTemperatureCurrent, shePhysPortEntPhysicalIndex, shePhysPortId, shePhysPortAlarmSeverityIndex, 
				shePhysPortUserLabel, shePhysPortAdminStateLastChangeTime, shePhysPortOperStateUpLastChangeTime, shePhysPortOperStateDownLastChangeTime, shePhysRackAlarmSeverityIndex, 
				shePhysShelfAlarmSeverityIndex, shePhysShelfTypeCode, shePhysShelfExternalAlarmOutput01Status, shePhysShelfExternalAlarmOutput01Usage, shePhysShelfExternalAlarmOutput02Status, 
				shePhysShelfExternalAlarmOutput02Usage, shePhysShelfExternalAlarmOutput03Status, shePhysShelfExternalAlarmOutput03Usage, shePhysShelfExternalAlarm01Level, shePhysShelfExternalAlarm01Usage, 
				shePhysShelfExternalAlarm02Level, shePhysShelfExternalAlarm02Usage, shePhysShelfExternalAlarm03Level, shePhysShelfExternalAlarm03Usage, shePhysShelfExternalAlarm04Level, 
				shePhysShelfExternalAlarm04Usage, shePhysShelfExternalAlarm05Level, shePhysShelfExternalAlarm05Usage, shePhysShelfExternalAlarm06Level, shePhysShelfExternalAlarm06Usage, 
				shePhysShelfExternalAlarm07Level, shePhysShelfExternalAlarm07Usage, shePhysShelfExternalAlarm08Level, shePhysShelfExternalAlarm08Usage, shePhysShelfRelativeHumidityAlarmOn, 
				shePhysShelfRelativeHumidityAlarmOff, shePhysShelfRelativeHumidity, shePhysShelfBatteryBackupMode, shePhysShelfBatteryBackupOption, shePhysRedundancyFeature, 
				shePhysRedundancyInterlink, shePhysPortAdslCount, shePhysPortShdslCount, shePhysPortVdslCount, shePhysPortAdsl2Count, 
				shePhysPortVoipCount, shePhysPortIsdnCount, shePhysCardTemperaturePowerDownOn, shePhysCardTemperaturePowerDownOff, shePhysCardOverTemperatureResetOn, 
				shePhysCardOverTemperatureResetOff, shePhysCardTemperatureWarningOn, shePhysCardTemperatureWarningOff }
			STATUS current
			DESCRIPTION 
				"Description."
			::= { shePhysicalGroups 1 }

		
-- 1.3.6.1.4.1.231.7.1.2.2.1.1.100.1.2
		shePhysicalControlGroup OBJECT-GROUP
			OBJECTS { shePhysCardControlRequest, shePhysCardControlStatus, shePhysCardControlPhysicalName, shePhysCardControlContainedInIndex, shePhysCardControlTimer, 
				shePhysCardControlReqResult, shePhysCardControlTimeStamp, shePhysCardControlAdminStateChange, shePhysCardControlAdminStateCreate, shePhysCardControlEntPhysicalIndex, 
				shePhysCardControlAlarmSeverityIndex, shePhysPortControlRequest, shePhysPortControlStatus, shePhysPortControlIfIndex, shePhysPortControlAlarmSeverityIndex, 
				shePhysPortControlAdminState, shePhysPortControlTimeStamp, shePhysPortControlTimer, shePhysPortControlReqResult, shePhysPortControlUserLabel, 
				shePhysPortControlOperStateTrapEnable, shePhysBrdControlRequest, shePhysBrdControlStatus, shePhysBrdControlReqResult, shePhysBrdControlTimeStamp, 
				shePhysBrdControlTimer, shePhysBrdControlEntPhysicalIndex, shePhysBrdControlRedundancyFeature, shePhysRackControlRequest, shePhysRackControlStatus, 
				shePhysRackControlIndex, shePhysRackControlAlarmSeverityIndex, shePhysRackControlTimeStamp, shePhysRackControlTimer, shePhysRackControlReqResult, 
				shePhysShelfControlRequest, shePhysShelfControlStatus, shePhysShelfControlIndex, shePhysShelfControlTimeStamp, shePhysShelfControlTimer, 
				shePhysShelfControlReqResult, shePhysShelfControlAlarmSeverityIndex, shePhysShelfControlExternalAlarmOutput01Usage, shePhysShelfControlExternalAlarmOutput02Usage, shePhysShelfControlExternalAlarmOutput03Usage, 
				shePhysShelfControlExternalAlarm01Level, shePhysShelfControlExternalAlarm01Usage, shePhysShelfControlExternalAlarm02Level, shePhysShelfControlExternalAlarm02Usage, shePhysShelfControlExternalAlarm03Level, 
				shePhysShelfControlExternalAlarm03Usage, shePhysShelfControlExternalAlarm04Level, shePhysShelfControlExternalAlarm04Usage, shePhysShelfControlExternalAlarm05Level, shePhysShelfControlExternalAlarm05Usage, 
				shePhysShelfControlExternalAlarm06Level, shePhysShelfControlExternalAlarm06Usage, shePhysShelfControlExternalAlarm07Level, shePhysShelfControlExternalAlarm07Usage, shePhysShelfControlExternalAlarm08Level, 
				shePhysShelfControlExternalAlarm08Usage, shePhysShelfControlRelativeHumidityAlarmOn, shePhysShelfControlRelativeHumidityAlarmOff, shePhysShelfControlBatteryBackupMode, shePhysShelfControlExternalAlarmOutput01Status, 
				shePhysShelfControlExternalAlarmOutput02Status, shePhysShelfControlExternalAlarmOutput03Status, shePhysBrdControlRedundancyInterlink, shePhysCardTemperatureControlRequest, shePhysCardTemperatureControlStatus, 
				shePhysCardTemperatureControlTimer, shePhysCardTemperatureControlReqResult, shePhysCardTemperatureControlTimeStamp, shePhysCardTemperatureControlWarningOn, shePhysCardTemperatureControlWarningOff
				 }
			STATUS current
			DESCRIPTION 
				"Description."
			::= { shePhysicalGroups 2 }

		
-- 1.3.6.1.4.1.231.7.1.2.2.1.1.100.1.3
		shePhysicalNotificationGroup NOTIFICATION-GROUP
			NOTIFICATIONS { shePhysRackControlResult, shePhysDCAlarm0, shePhysDCAlarm1, shePhysFanAlarm0, shePhysFanAlarm1, 
				shePhysFanAlarm2, shePhysFanAlarm3, shePhysFanAlarm4, shePhysFanAlarm5, shePhysShelfControlResult, 
				shePhysShelfControlExternalAlarmsConfigurationChanged, shePhysShelfMupState1, shePhysShelfMupState2, shePhysShelfExternalAlarm01, shePhysShelfExternalAlarm02, 
				shePhysShelfExternalAlarm03, shePhysShelfExternalAlarm04, shePhysShelfExternalAlarm05, shePhysShelfExternalAlarm06, shePhysShelfExternalAlarm07, 
				shePhysShelfExternalAlarm08, shePhysShelfExtAlarmCollectorNotConnected, shePhysCardControlResult, shePhysCardAdminStateChanged, shePhysCardStateChanged, 
				shePhysCardReset, shePhysCardResetEnd, shePhysCardCreated, shePhysCardDeleted, shePhysCardDeletionStarted, 
				shePhysContainerCardTypeConverted, shePhysCardConvertionStarted, shePhysCardPlugged, shePhysCardUnplugged, shePhysCardTypeMismatch, 
				shePhysCardFailure, shePhysCardProblem, shePhysCardNotInstalled, shePhysCardTemperaturePowerDown, shePhysCardOverTemperatureReset, 
				shePhysPortAdminStateChanged, shePhysPortOperStateChanged, shePhysPortControlResult, shePhysPortCreated, shePhysPortDeleted, 
				shePhysBrdControlResult, shePhysRedundancyStateChanged, shePhysRedundancyFeatureModified, shePhysCardTemperatureWarningThresholdsChanged, shePhysCardTemperatureWarning, 
				shePhysRedundancyInterlinkModified, shePhysShelfControlRelativeHumidityAlarmThresholdChanged, shePhysShelfRelativeHumidityAlarm, shePhysShelfHeatExchangerIn, shePhysShelfHeatExchangerOut, 
				shePhysShelfBatteryBackupModified, shePhysCardSWVersionProblem, shePhysShelfControlExternalAlarmsOutputStatusChanged, shePhysRedundancyNoRedundancy, shePhysPortOperStateDown
				 }
			STATUS current
			DESCRIPTION 
				"This group supports notifications of significant 
				conditions associated with physical objects."
			::= { shePhysicalGroups 3 }

		
-- 1.3.6.1.4.1.231.7.1.2.2.1.1.100.1.4
		shePhysicalObsoleteGroup OBJECT-GROUP
			OBJECTS { shePhysCardControlTemperatureThreshold, shePhysCardTemperatureThreshold, shePhysCardUpgradeState }
			STATUS obsolete
			DESCRIPTION 
				"Description."
			::= { shePhysicalGroups 4 }

		
-- 1.3.6.1.4.1.231.7.1.2.2.1.1.100.1.5
		shePhysicalObsoleteNotificationGroup NOTIFICATION-GROUP
			NOTIFICATIONS { shePhysCardChangedTemperatureThreshold, shePhysCardOverTemperatureThreshold }
			STATUS obsolete
			DESCRIPTION 
				"Description."
			::= { shePhysicalGroups 5 }

		
-- 1.3.6.1.4.1.231.7.1.2.2.1.1.100.2
		shePhysicalCompliances OBJECT IDENTIFIER ::= { shePhysicalConformance 2 }

		
-- this module
-- 1.3.6.1.4.1.231.7.1.2.2.1.1.100.2.1
		shePhysicalMibCompliance MODULE-COMPLIANCE
			STATUS current
			DESCRIPTION 
				"The compliance statement for SNMP entities which 
				manage physical interfaces in SHE."
			MODULE -- this module
				MANDATORY-GROUPS { shePhysicalGroup, shePhysicalControlGroup, shePhysicalNotificationGroup }
				GROUP shePhysicalObsoleteNotificationGroup
					DESCRIPTION 
						"Contained elements not longer supported by NE up R2.5."
				GROUP shePhysicalObsoleteGroup
					DESCRIPTION 
						"Contained elements not longer supported by NE up R2.5."
			::= { shePhysicalCompliances 1 }

		
	
	END

--
-- she-physical-mib.mib
--
