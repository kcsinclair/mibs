-- ======================================================== --
	-- Network Appliance Custom MIB                             --
	--                                                          --
	-- This MIB contains only information specific to           --
	-- Network Appliance products.  The Network Appliance       --
	-- SNMP agent supports the information specified            --
	-- in the RFC1213 MIB, but the specification of the         --
	-- RFC1213 MIB is not included in this file.                --
	-- =======================================================  --

	-- Version 1.19.3, March 2007 (See NOTE below)

	-- Copyright (c) 1995-2006 Network Appliance, Inc.
	-- All rights reserved.

	-- This Network Appliance SNMP Management Information Base
	-- (Specification) embodies Network Appliance's confidential
	-- and proprietary intellectual property.  Network Appliance
	-- retains all title and ownership in the Specification,
	-- including any revisions.

	-- This Specification is supplied "AS IS," and Network Appliance
	-- makes no warranty, either express or implied, as to the use,
	-- operation, condition, or performance of the Specification.

	-- NOTE:   Please maintain the format of the line above
		-- containing the MIB's version number as:
		--
		-- Version <version #>, <Date> (See NOTE below)
		--
		-- This line is parsed during the release process
		-- to extract the version of the MIB.


	NETWORK-APPLIANCE-MIB DEFINITIONS ::= BEGIN

	IMPORTS
		enterprises, Counter, IpAddress, TimeTicks, Gauge
			FROM RFC1155-SMI
		PhysAddress, DisplayString
			FROM RFC1213-MIB
		TRAP-TYPE
			FROM RFC-1215
		OBJECT-TYPE
			FROM RFC-1212;

	--  This MIB module uses the extended OBJECT-TYPE macro as
	--  defined in RFC-1212


	--  MIB-II (same prefix as MIB-I)


	-- the Network Appliance MIB

	-- NetApp conventions

	netapp OBJECT IDENTIFIER ::= { enterprises 789 }

	-- the current netapp mib

	netapp1	OBJECT IDENTIFIER ::= { netapp 1 }

	-- 
	-- This is the tree under which values for the sysObjectID
	-- are allocated.
	--

	netappProducts OBJECT IDENTIFIER ::= { netapp 2 }

	-- 
	-- This is the tree under which values for the DataFabric Manager
	-- are allocated. Those values are defined in separate mib file,
	-- distributed with DataFabric Manager product.
	--

	netappDataFabricManager OBJECT IDENTIFIER ::= { netapp 3 }

	-- 
	-- This is the tree under which values for the NetApp Support Console
	-- are allocated. Those values are defined in separate mib file,
	-- distributed with the Support Console
	--

	netappSupportConsole OBJECT IDENTIFIER ::= { netapp 4 }

	--
	-- We distinguish between filers and NetCaches.
	--

	netappFiler	OBJECT IDENTIFIER ::= { netappProducts 1 }
	netappNetCache	OBJECT IDENTIFIER ::= { netappProducts 2 }
	netappClusteredFiler	OBJECT IDENTIFIER ::= { netappProducts 3 }

	-- top-level netapp groups

	product	OBJECT IDENTIFIER ::= { netapp1 1 }

	sysStat	OBJECT IDENTIFIER ::= { netapp1 2 }

	nfs	OBJECT IDENTIFIER ::= { netapp1 3 }

	quota	OBJECT IDENTIFIER ::= { netapp1 4 }

	filesys	OBJECT IDENTIFIER ::= { netapp1 5 }

	raid	OBJECT IDENTIFIER ::= { netapp1 6 }

	cifs	OBJECT IDENTIFIER ::= { netapp1 7 }

	netcache      	OBJECT IDENTIFIER ::= { netapp1 8 }

	snapmirror     	OBJECT IDENTIFIER ::= { netapp1 9 }

	ndmp     	OBJECT IDENTIFIER ::= { netapp1 10 }

	fabric     	OBJECT IDENTIFIER ::= { netapp1 11 }

	dafs		OBJECT IDENTIFIER ::= { netapp1 12 }

	vi		OBJECT IDENTIFIER ::= { netapp1 13 }

	backup		OBJECT IDENTIFIER ::= { netapp1 14 }

        vfiler          OBJECT IDENTIFIER ::= { netapp1 16 }

	blocks		OBJECT IDENTIFIER ::= { netapp1 17 }

	nfscache	OBJECT IDENTIFIER ::= { netapp1 18 }

	snapvault     	OBJECT IDENTIFIER ::= { netapp1 19 }

	ftpd		OBJECT IDENTIFIER ::= { netapp1 20 }

	storage   	OBJECT IDENTIFIER ::= { netapp1 21 }

	network		OBJECT IDENTIFIER ::= { netapp1 22 }

	sis		OBJECT IDENTIFIER ::= { netapp1 23 }

	-- -- -- -- -- -- -- --
	-- the product group --
	-- -- -- -- -- -- -- --

	productType	OBJECT-TYPE
	SYNTAX		INTEGER {
			    eisa-based(1),
			    pci-based(2)
	}
	ACCESS		read-only
	STATUS		mandatory
	DESCRIPTION
			"The product type representing the target platform."
	::= { product 1 }

	productVersion	OBJECT-TYPE
	SYNTAX		DisplayString
	ACCESS		read-only
	STATUS		mandatory
	DESCRIPTION
			"Version String for the Software Running on
			 this platform."
	::= { product 2 }

	productId	OBJECT-TYPE
	SYNTAX		DisplayString
	ACCESS		read-only
	STATUS		mandatory
	DESCRIPTION
			"The System ID of this system."
	::= { product 3 }

	productVendor	OBJECT-TYPE
	SYNTAX		INTEGER {
			    netapp(1),
			    dell(2),
			    ibm(3)
	}
	ACCESS		read-only
	STATUS		mandatory
	DESCRIPTION
			"The vendor id of this system, indicating the company
			that has supplied the product."
	::= { product 4 }

	productModel	OBJECT-TYPE
	SYNTAX		DisplayString
	ACCESS		read-only
	STATUS		mandatory
	DESCRIPTION
			"The model name of the system.  Examples
			 are FAS980 and FAS3050."
	::= { product 5 }

	productFirmwareVersion	OBJECT-TYPE
	SYNTAX		DisplayString
	ACCESS		read-only
	STATUS		mandatory
	DESCRIPTION
			"Version string for the Firmware running on
			 this platform."
	::= { product 6 }

	productGuiUrl	OBJECT-TYPE
	SYNTAX		DisplayString
	ACCESS		read-only
	STATUS		mandatory
	DESCRIPTION
			"The complete URL used to access the administrative GUI
			 for a browser-based interface."
	::= { product 7 }

	productApiUrl	OBJECT-TYPE
	SYNTAX		DisplayString
	ACCESS		read-only
	STATUS		mandatory
	DESCRIPTION
			"The complete URL used to access the administrative API
			 for a programmatic interface."
	::= { product 8 }
	
	productSerialNum  OBJECT-TYPE
	SYNTAX		  DisplayString
	ACCESS		  read-only
	STATUS		  mandatory
	DESCRIPTION
			  "The product serial number. Returns unknown if it 
			   cannot be determined."
	::= { product 9 }

	productPartnerSerialNum   OBJECT-TYPE
	SYNTAX			  DisplayString
	ACCESS			  read-only
	STATUS			  mandatory
	DESCRIPTION
				  "The partner's serial number, not applicable
				   if there is no partner, and unknown if it
				   cannot be determined."
	::= { product 10 }

	productCPUArch  OBJECT-TYPE
	SYNTAX		INTEGER {
				x86(1),
				alpha(2),
				mips(3),
				sparc(4)
			}
	ACCESS		read-only
	STATUS		mandatory
	DESCRIPTION
	                "The CPU architecture type of this appliance"


			
        ::= { product 11 }

	productTrapData	OBJECT-TYPE
	SYNTAX			DisplayString
	ACCESS			read-only
	STATUS			mandatory
	DESCRIPTION
			"This returns a static string. This object is used
			as a placeholder for enterprise traps."
	::= { product 12 }

	productMachineType	OBJECT-TYPE
	SYNTAX		DisplayString
	ACCESS		read-only
	STATUS		mandatory
	DESCRIPTION
			"The machine type of the system.  Examples
			 are FAS980 and FAS3050."
	::= { product 13 }

	-- -- -- -- -- -- -- --
	-- the sysStat group --
	-- -- -- -- -- -- -- --

	cpu	OBJECT IDENTIFIER ::=	{ sysStat 1 }

	misc	OBJECT IDENTIFIER ::=	{ sysStat 2 }

	cf	OBJECT IDENTIFIER ::=	{ sysStat 3 }

	environment OBJECT IDENTIFIER ::= { sysStat 4 }

	nvram	OBJECT IDENTIFIER ::= { sysStat 5 }

	cp	OBJECT IDENTIFIER ::= { sysStat 6 }

	autosupport OBJECT IDENTIFIER ::= { sysStat 7 }


	-- the cpu group for sysStat

	cpuUpTime		OBJECT-TYPE
	SYNTAX			TimeTicks
	ACCESS			read-only
	STATUS			mandatory
	DESCRIPTION
			"The time (in hundredths of a second) that the
			 CPU has been up since the last boot."
	::= { cpu 1 }

	cpuBusyTime		OBJECT-TYPE
	SYNTAX			TimeTicks
	ACCESS			read-only
	STATUS			mandatory
	DESCRIPTION
			"The time (in hundredths of a second) that the
			 CPU has been doing useful work since the last
			 boot."
	::= { cpu 2 }

	cpuBusyTimePerCent	OBJECT-TYPE
	SYNTAX			INTEGER (0..100)
	ACCESS			read-only
	STATUS			mandatory
	DESCRIPTION
			"The percent of time that the CPU has been doing
			 useful work since the last time a client requested
			 the cpuBusyTimePerCent."
	::= { cpu 3 }

	cpuIdleTime		OBJECT-TYPE
	SYNTAX			TimeTicks
	ACCESS			read-only
	STATUS			mandatory
	DESCRIPTION
			"The time (in hundredths of a second) that the
			 CPU has been idle since the last boot."
	::= { cpu 4 }

	cpuIdleTimePerCent	OBJECT-TYPE
	SYNTAX			INTEGER (0..100)
	ACCESS			read-only
	STATUS			mandatory
	DESCRIPTION
			"The percent of time that the CPU has been idle
			 since the last time a client requested the
			 cpuBusyTimePerCent."
	::= { cpu 5 }

	cpuCount		OBJECT-TYPE
	SYNTAX			INTEGER (1..2)
	ACCESS			read-only
	STATUS			mandatory
	DESCRIPTION
			"The number of CPUs in the system."
	
	::= { cpu 6 }

        cpuSwitchInvocations	OBJECT-TYPE
	SYNTAX			Counter
	ACCESS			read-only
	STATUS			mandatory
	DESCRIPTION	
			"The number of sk_switch invocations."
	::= { cpu 7 }

	cpuContextSwitches	OBJECT-TYPE
	SYNTAX			Counter
	ACCESS			read-only
	STATUS			mandatory
	DESCRIPTION		
			"The number of hardware context switches."
	::= { cpu 8 }

	cpuInterrupts		OBJECT-TYPE
	SYNTAX			Counter
	ACCESS			read-only
	STATUS			mandatory
	DESCRIPTION		
			"The number of interrupts during a CP."
	::= { cpu 9 }


	cpuNonCPInterrupts	OBJECT-TYPE
	SYNTAX			Counter
	ACCESS			read-only
	STATUS			mandatory
	DESCRIPTION		
			"The number of interrupts not during a CP."
	::= { cpu 10 }

	cpuCPInterruptPercent	OBJECT-TYPE
	SYNTAX			INTEGER (0..100)
	ACCESS			read-only
	STATUS			mandatory
	DESCRIPTION	
			" The percentage of time handling CP interrupts."
	::= { cpu 11 }

        cpuNonCPInterruptPercent OBJECT-TYPE
	SYNTAX			INTEGER (0..100)
	ACCESS			read-only
	STATUS			mandatory
	DESCRIPTION	
			" The percentage of time handling non-cp interrupts."
        ::= { cpu 12 }
	
        cpuTotalDomainSwitches OBJECT-TYPE
	SYNTAX			Counter
	ACCESS			read-only
	STATUS			mandatory
	DESCRIPTION	
			" The total number of Domain Switches."
        ::= { cpu 13 }

 	-- the misc group for sysStat

	-- miscNfsOps is DEPRECATED; use miscHighNfsOps
	--    and miscLowNfsOps

	miscNfsOps		OBJECT-TYPE
	SYNTAX			INTEGER
	ACCESS			read-only
	STATUS			mandatory
	DESCRIPTION
			"The total number of Server side NFS calls since
			 the last boot"
	::= { misc 1 }


	-- miscNetRcvdKB is DEPRECATED; use miscHighNetRcvdBytes
	--  and miscLowNetRcvdBytes

	miscNetRcvdKB		OBJECT-TYPE
	SYNTAX			INTEGER
	ACCESS			read-only
	STATUS			mandatory
	DESCRIPTION
			"The total number of KBytes received on all the
			 network interfaces, since the last boot."
	::= { misc 2 }

	-- miscNetSentKB is DEPRECATED; use miscHighNetSentBytes
	--  and miscLowNetSentBytes

	miscNetSentKB		OBJECT-TYPE
	SYNTAX			INTEGER
	ACCESS			read-only
	STATUS			mandatory
	DESCRIPTION
			"The total number of KBytes transmitted on all the
			 network interfaces, since the last boot."
	::= { misc 3 }

	miscGlobalStatus	OBJECT-TYPE
	SYNTAX			INTEGER {
					other(1),
					unknown(2),
					ok(3),
					nonCritical(4),
					critical(5),
					nonRecoverable(6)
				}
	ACCESS			read-only
	STATUS			mandatory
	DESCRIPTION
			"This indicates the overall status of the appliance.
			The algorithm to determine the value uses both
			hardware status (e.g. the number of failed fans) and
			volume status (e.g. number of volumes that are full).
			The algorithm is subject to change in future releases,
			but the range of values will not change."
	::= { misc 4 }

	miscHighNfsOps		OBJECT-TYPE
	SYNTAX			Counter
	ACCESS			read-only
	STATUS			mandatory
	DESCRIPTION
			"The total number of Server side NFS calls since
			 the last boot.  This object returns the most
			 significant 32 bits of the 64 bit unsigned integer."
	::= { misc 5 }

	miscLowNfsOps		OBJECT-TYPE
	SYNTAX			Counter
	ACCESS			read-only
	STATUS			mandatory
	DESCRIPTION
			"The total number of Server side NFS calls since
			 the last boot.  This object returns the least
			 significant 32 bits of the 64 bit unsigned integer."

	::= { misc 6 }

	miscHighCifsOps		OBJECT-TYPE
	SYNTAX			Counter
	ACCESS			read-only
	STATUS			mandatory
	DESCRIPTION
			"The total number of Server side CIFS calls since
			 the last boot.  This object returns the most
			 significant 32 bits of the 64 bit unsigned integer."
	::= { misc 7 }

	miscLowCifsOps		OBJECT-TYPE
	SYNTAX			Counter
	ACCESS			read-only
	STATUS			mandatory
	DESCRIPTION
			"The total number of Server side CIFS calls since
			 the last boot.  This object returns the least
			 significant 32 bits of the 64 bit unsigned integer."

	::= { misc 8 }


	miscHighHttpOps		OBJECT-TYPE
	SYNTAX			Counter
	ACCESS			read-only
	STATUS			mandatory
	DESCRIPTION
			"The total number of HTTP operations received
			 since the last boot.  This object returns the most
			 significant 32 bits of the 64 bit unsigned integer."
	::= { misc 9 }

	miscLowHttpOps		OBJECT-TYPE
	SYNTAX			Counter
	ACCESS			read-only
	STATUS			mandatory
	DESCRIPTION
			"The total number of HTTP operations received
			 since the last boot.  This object returns the least
			 significant 32 bits of the 64 bit unsigned integer."

	::= { misc 10 }


	miscHighNetRcvdBytes	OBJECT-TYPE
	SYNTAX			Counter
	ACCESS			read-only
	STATUS			mandatory
	DESCRIPTION
			"The total number of bytes received on all the
			 network interfaces, since the last boot.  This
			 object returns the most significant 32 bits
			 of the 64 bit unsigned integer."
	::= { misc 11 }

	miscLowNetRcvdBytes	OBJECT-TYPE
	SYNTAX			Counter
	ACCESS			read-only
	STATUS			mandatory
	DESCRIPTION
			"The total number of bytes received on all the
			 network interfaces, since the last boot.  This
			 object returns the least significant 32 bits
			 of the 64 bit unsigned integer."
	::= { misc 12 }


	miscHighNetSentBytes	OBJECT-TYPE
	SYNTAX			Counter
	ACCESS			read-only
	STATUS			mandatory
	DESCRIPTION
			"The total number of bytes transmitted on all the
			 network interfaces, since the last boot.  This
			 object returns the most significant 32 bits
			 of the 64 bit unsigned integer."
	::= { misc 13 }


	miscLowNetSentBytes	OBJECT-TYPE
	SYNTAX			Counter
	ACCESS			read-only
	STATUS			mandatory
	DESCRIPTION
			"The total number of bytes transmitted on all the
			 network interfaces, since the last boot.  This
			 object returns the least significant 32 bits
			 of the 64 bit unsigned integer."

	::= { misc 14 }

	miscHighDiskReadBytes	OBJECT-TYPE
	SYNTAX			Counter
	ACCESS			read-only
	STATUS			mandatory
	DESCRIPTION
			"The total number of bytes read from disk
			 since the last boot.  This object returns
			 the most significant 32 bits of the 64 bit unsigned 
			 integer."

	::= { misc 15 }

	miscLowDiskReadBytes	OBJECT-TYPE
	SYNTAX			Counter
	ACCESS			read-only
	STATUS			mandatory
	DESCRIPTION
			"The total number of bytes read from disk since
			 the last boot.  This object returns the least
			 significant 32 bits of the 64 bit unsigned integer."
	::= { misc 16 }


	miscHighDiskWriteBytes	OBJECT-TYPE
	SYNTAX			Counter
	ACCESS			read-only
	STATUS			mandatory
	DESCRIPTION
			"The total number of bytes written to disk
			 since the last boot.  This object returns
			 the most significant 32 bits of the 64 bit unsigned
			 integer."
	::= { misc 17 }

	miscLowDiskWriteBytes	OBJECT-TYPE
	SYNTAX			Counter
	ACCESS			read-only
	STATUS			mandatory
	DESCRIPTION
			"The total number of bytes written to disk since
			 the last boot.  This object returns the least
			 significant 32 bits of the 64 bit unsigned integer."
	::= { misc 18 }



	miscHighTapeReadBytes	OBJECT-TYPE
	SYNTAX			Counter
	ACCESS			read-only
	STATUS			mandatory
	DESCRIPTION
			"The total number of bytes read from tape
			 since the last boot.  This object returns
			 the most significant 32 bits of the 64 bit unsigned 
			 integer."
	::= { misc 19 }

	miscLowTapeReadBytes	OBJECT-TYPE
	SYNTAX			Counter
	ACCESS			read-only
	STATUS			mandatory
	DESCRIPTION
			"The total number of bytes read from tape since
			 the last boot.  This object returns the least
			 significant 32 bits of the 64 bit unsigned integer."
	::= { misc 20 }


	miscHighTapeWriteBytes	OBJECT-TYPE
	SYNTAX			Counter
	ACCESS			read-only
	STATUS			mandatory
	DESCRIPTION
			"The total number of bytes written to tape
			 since the last boot.  This object returns
			 the most significant 32 bits of the 64 bit unsigned 
			 integer."
	::= { misc 21 }

	miscLowTapeWriteBytes	OBJECT-TYPE
	SYNTAX			Counter
	ACCESS			read-only
	STATUS			mandatory
	DESCRIPTION
			"The total number of bytes written to tape since
			 the last boot.  This object returns the least
			 significant 32 bits of the 64 bit unsigned integer."
	::= { misc 22 }

	miscCacheAge		OBJECT-TYPE
	SYNTAX			INTEGER
	ACCESS			read-only
	STATUS			mandatory
	DESCRIPTION
			"Age in minutes of the oldest read-only blocks
			 in the buffer cache.  This indicates how fast
			 read operations are cycling through system
			 memory; when the appliance is reading very
			 large files (larger than the machine's memory
			 size), buffer cache age will be very low."
	::= { misc 23 }

	miscCorrectedMachineChecks	OBJECT-TYPE
	SYNTAX			Counter
	ACCESS			read-only
	STATUS			mandatory
	DESCRIPTION
			"Number of corrected machine checks since
			the last boot."

	::= { misc 24 }

	miscGlobalStatusMessage	OBJECT-TYPE
	SYNTAX			DisplayString
	ACCESS			read-only
	STATUS			mandatory
	DESCRIPTION
			"A string describing the global status,
			including a description of the condition (if
			any) that caused the status to be anything
			other than ok(3)."
	::= { misc 25 }

	miscWindowsSetupWizardVersion	OBJECT-TYPE
	SYNTAX			INTEGER
	ACCESS			read-only
	STATUS			mandatory
	DESCRIPTION
			"The version number of Windows Setup Wizard 
			required to configure the appliance.  Windows
			Setup Wizard with a version number lower than 
			this integer is not capable of configuring the 
			appliance."
	::= { misc 26 }

	-- the Clustered Failover group

	cfSettings		OBJECT-TYPE
	SYNTAX			INTEGER {
					notConfigured(1),
					enabled(2),
					disabled(3),
					takeoverByPartnerDisabled(4),
					thisNodeDead(5)
				}
	ACCESS			read-only
	STATUS			mandatory
	DESCRIPTION
				"Clustered Failover configuration settings.
				 The value notConfigured(1) indicates that the
				 cluster is not licensed. The thisNodeDead(5)
				 setting indicates that this node has been 
				 taken over."
	::= { cf 1 }

	cfState			OBJECT-TYPE
	SYNTAX			INTEGER {
					dead(1),
					canTakeover(2),
					cannotTakeover(3),
					takeover(4)
				}
	ACCESS			read-only
	STATUS			mandatory
	DESCRIPTION
				"Clustered Failover state."
	::= { cf 2 }

	cfCannotTakeoverCause	OBJECT-TYPE
	SYNTAX			INTEGER {
					ok(1),
					unknownReason(2),
					disabledByOperator(3),
					interconnectOffline(4),
					disabledByPartner(5),
					takeoverFailed(6)
				}
	ACCESS			read-only
	STATUS			mandatory
	DESCRIPTION
				"The reason this node cannot takeover its
				 partner"
	::= { cf 3 }

	cfPartnerStatus		OBJECT-TYPE
	SYNTAX			INTEGER {
					maybeDown(1),
					ok(2),
					dead(3)
				}
	ACCESS			read-only
	STATUS		        mandatory
	DESCRIPTION
				"This is the status last returned by the
				 Clustered Failover partner."
	::= { cf 4 }

	cfPartnerLastStatusUpdate	OBJECT-TYPE
	SYNTAX				TimeTicks
	ACCESS				read-only
	STATUS				mandatory
	DESCRIPTION
				"If non-zero, the absolute time of the last
				 update from the Clustered Failover partner."
	::= { cf 5 }

	cfPartnerName		OBJECT-TYPE
	SYNTAX			DisplayString
	ACCESS			read-only
	STATUS			mandatory
	DESCRIPTION
				"Hostname for Clustered Failover partner."
	::= { cf 6 }

	cfPartnerSysid		OBJECT-TYPE
	SYNTAX			INTEGER
	ACCESS			read-only
	STATUS			mandatory
	DESCRIPTION
				"System ID for Clustered Failover partner."
	::= { cf 7 }
	
	cfInterconnectStatus	OBJECT-TYPE
	SYNTAX			INTEGER {
					notPresent(1),
					down(2),
					partialFailure(3),
					up(4)
				}
	ACCESS			read-only
	STATUS			mandatory
	DESCRIPTION
				"The current status of the interconnect.
				 The partialFailure(3) status indicates that
				 one of the links in the interconnect hardware
				 is down." 
	::= { cf 8 }

	-- the environment group for sysStat

	envOverTemperature	OBJECT-TYPE
	SYNTAX			INTEGER {
					no(1),
					yes(2)
				}
	ACCESS			read-only
	STATUS			mandatory
	DESCRIPTION
			"An indication of whether the hardware is
			 currently operating outside of its recommended
			 temperature range.  The hardware will shutdown
			 if the temperature exceeds critical thresholds."

	::= { environment 1 }

	envFailedFanCount	OBJECT-TYPE
	SYNTAX			INTEGER
	ACCESS			read-only
	STATUS			mandatory
	DESCRIPTION
			"Count of the number of chassis fans which
			 are not operating within the recommended
			 RPM range."

	::= { environment 2 }

	envFailedFanMessage	OBJECT-TYPE
	SYNTAX			DisplayString
	ACCESS			read-only
	STATUS			mandatory
	DESCRIPTION
			"Text message describing the current condition of
			 chassis fans.  This is useful only if
			 envFailedFanCount is not zero."

	::= { environment 3 }


	envFailedPowerSupplyCount	OBJECT-TYPE
	SYNTAX			INTEGER
	ACCESS			read-only
	STATUS			mandatory
	DESCRIPTION
			"Count of the number of power supplies which
			 are in degraded mode."

	::= { environment 4 }

	envFailedPowerSupplyMessage	OBJECT-TYPE
	SYNTAX			DisplayString
	ACCESS			read-only
	STATUS			mandatory
	DESCRIPTION
			"Text message describing the state of any
			 power supplies which are currently degraded.
			 This is useful only if envFailedPowerSupplyCount
			 is not zero."

	::= { environment 5 }

	-- -- -- -- -- -- --
	-- the nvram group for sysStat

	nvramBatteryStatus	OBJECT-TYPE
	SYNTAX			INTEGER {
					ok(1),
					partiallyDischarged(2),
					fullyDischarged(3),
					notPresent(4),
					nearEndOfLife(5),
					atEndOfLife(6),
					unknown(7),
					overCharged(8),
					fullyCharged(9)
				}
	ACCESS			read-only
	STATUS			mandatory
	DESCRIPTION
			"An indication of the current status of the
			 NVRAM battery or batteries.  Batteries which
			 are fully or partially discharged may not
			 fully protect the system during a crash.

			 The end-of-life status values are based on
			 the manufacturer's recommended life for the
			 batteries."

	::= { nvram 1 }

	-- -- -- -- -- -- --
	-- the cp group for sysStat

	cpTime			OBJECT-TYPE
	SYNTAX			TimeTicks
	ACCESS			read-only
	STATUS			mandatory
	DESCRIPTION
			"The time (in hundredths of a second) since boot
			 during which the system has had a consistency point
			 (cp) operation in progress."
	::= { cp 1 }

	cpFromTimerOps		OBJECT-TYPE
	SYNTAX			Counter	
	ACCESS			read-only
	STATUS			mandatory
	DESCRIPTION
			"The number of consistency point operations since boot
			 that were caused by timer."
	::= { cp 2 }

	cpFromSnapshotOps	OBJECT-TYPE
	SYNTAX			Counter	
	ACCESS			read-only
	STATUS			mandatory
	DESCRIPTION
			"The number of consistency point operations since boot
			 that were caused by snapshot operation."
	::= { cp 3 }

	cpFromLowWaterOps	OBJECT-TYPE
	SYNTAX			Counter	
	ACCESS			read-only
	STATUS			mandatory
	DESCRIPTION
			"The number of consistency point operations since boot
			 that were caused by low water mark."
	::= { cp 4 }

	cpFromHighWaterOps	OBJECT-TYPE
	SYNTAX			Counter	
	ACCESS			read-only
	STATUS			mandatory
	DESCRIPTION
			"The number of consistency point operations since boot
			 that were caused by high water mark."
	::= { cp 5 }

	cpFromLogFullOps	OBJECT-TYPE
	SYNTAX			Counter	
	ACCESS			read-only
	STATUS			mandatory
	DESCRIPTION
			"The number of consistency point operations since boot
			 that were caused by nv-log full."
	::= { cp 6 }

	cpFromCpOps		OBJECT-TYPE
	SYNTAX			Counter	
	ACCESS			read-only
	STATUS			mandatory
	DESCRIPTION
			"The number of back to back consistency point 
			operations since boot."
	::= { cp 7 }

	cpTotalOps		OBJECT-TYPE
	SYNTAX			Counter	
	ACCESS			read-only
	STATUS			mandatory
	DESCRIPTION
			"The total number of consistency point operations
			 since boot."
	::= { cp 8 }

	cpFromFlushOps		OBJECT-TYPE
	SYNTAX			Counter	
	ACCESS			read-only
	STATUS			mandatory
	DESCRIPTION
			"The number of consistency point operations since boot
			that were caused by flushing unlogged write data."
	::= { cp 9 }

	cpFromSyncOps		OBJECT-TYPE
	SYNTAX			Counter	
	ACCESS			read-only
	STATUS			mandatory
	DESCRIPTION
			"The number of consistency point operations since boot
			that were caused by file system sync requests."
	::= { cp 10 }

	cpFromLowVbufOps	OBJECT-TYPE
	SYNTAX			Counter	
	ACCESS			read-only
	STATUS			mandatory
	DESCRIPTION
			"The number of consistency point operations since boot
			that were caused by low virtual buffers."
	::= { cp 11 }

	cpFromCpDeferredOps	OBJECT-TYPE
	SYNTAX			Counter	
	ACCESS			read-only
	STATUS			mandatory
	DESCRIPTION
			"The number of back to back consistency point
			operations since boot that were deferred."
	::= { cp 12 }

	cpFromLowDatavecsOps	OBJECT-TYPE
	SYNTAX			Counter	
	ACCESS			read-only
	STATUS			mandatory
	DESCRIPTION
			"The number of consistency point operations since boot
			that were caused by low datavecs."
	::= { cp 13 }

	-- -- -- -- -- -- --
	-- the autosupport group for sysStat

	autosupportStatus	    OBJECT-TYPE
	SYNTAX			    INTEGER {
					    ok(1),
					    smtpFailure(2),
					    postFailure(3),
					    smtp-postFailure(4),
					    unknown(5)
				    }
	ACCESS			    read-only
	STATUS			    mandatory
	DESCRIPTION
			"An indication of the current status of
			 autosupport on the appliance.  describes
			 the success or failure of most recent 
			 attempts to send autosupports."
	
	::= { autosupport 1 }

	autosupportStatusMessage    OBJECT-TYPE
	SYNTAX			    DisplayString
	ACCESS			    read-only
	STATUS                      mandatory
	DESCRIPTION
			"A string describing the autosupport status,
			including a description of the condition (if
			any) that caused the status to be anything
			other than ok(1)."

	::= { autosupport 2 }

	autosupportSuccessfulSends  OBJECT-TYPE
	SYNTAX			    Counter
	ACCESS			    read-only
	STATUS                      mandatory
	DESCRIPTION
			"Count of the number of autosupport messages
			 successfully sent since the last reset."
	
	::= { autosupport 3 }

	autosupportFailedSends      OBJECT-TYPE
	SYNTAX			    Counter
	ACCESS                      read-only
	STATUS                      mandatory
	DESCRIPTION
	                 "Count of the number of autosupport messages
			 not sent successfully since the last reset."

	::= { autosupport 4 }


	-- -- -- -- -- -- --
	-- the NFS group  --
	-- -- -- -- -- -- --

	curNfs		OBJECT IDENTIFIER ::= { nfs 1 }

	totNfs		OBJECT IDENTIFIER ::= { nfs 2 }

	nfsOptions	OBJECT IDENTIFIER ::= { nfs 3 }


	-- the curNfs group

		-- this group contains NFS statistics since the last
		-- time the statistics were cleared

	rpcServ		OBJECT IDENTIFIER ::= { curNfs 1 }

	nfsServ		OBJECT IDENTIFIER ::= { curNfs 2 }

	nfsPerClient	OBJECT IDENTIFIER ::= { curNfs 3 }



	-- the rpcServ group

 	rpcCalls	OBJECT-TYPE
	SYNTAX		Counter
	ACCESS		read-only
	STATUS		mandatory
	DESCRIPTION
			"The total number of RPC calls received, since
			 the last time the statistics were cleared."
	::= { rpcServ 1 }

	rpcBadCalls	OBJECT-TYPE
	SYNTAX		Counter
	ACCESS		read-only
	STATUS		mandatory
	DESCRIPTION
			"The total number of calls rejected by the RPC
			 layer, since the last time the statistics were
			 cleared."
	::= { rpcServ 2 }

	rpcNullRecvs	OBJECT-TYPE
	SYNTAX		Counter
	ACCESS		read-only
	STATUS		mandatory
	DESCRIPTION
			"The number of times an RPC call was not available
			 when it was thought to be received, since the
			 last time the statistics were cleared."
	::= { rpcServ 3 }

	rpcBadLens	OBJECT-TYPE
	SYNTAX		Counter
	ACCESS		read-only
	STATUS		mandatory
	DESCRIPTION
			"The number of RPC calls received with a length
			 shorter than a minimum-sized RPC call, since the
			 last time the statistics were cleared."
	::= { rpcServ 4 }

	rpcServXDRCalls	OBJECT-TYPE
	SYNTAX		Counter
	ACCESS		read-only
	STATUS		mandatory
	DESCRIPTION
			"The number of RPC calls received whose header
			 could not be XDR decoded, since the last time
			 the statistics were cleared."
	::= { rpcServ 5 }

 	rcpTcpCalls	OBJECT-TYPE
	SYNTAX		Counter
	ACCESS		read-only
	STATUS		mandatory
	DESCRIPTION
			"The total number of RPC calls received for the
			 TCP protocol, since the last time the statistics
			 were cleared."
	::= { rpcServ 6 }

	rcpTcpBadCalls	OBJECT-TYPE
	SYNTAX		Counter
	ACCESS		read-only
	STATUS		mandatory
	DESCRIPTION
			"The total number of calls rejected by the RPC
			 layer for the TCP protocol, since the last 
			 time the statistics were cleared."
	::= { rpcServ 7 }

	rcpTcpNullRecvs	OBJECT-TYPE
	SYNTAX		Counter
	ACCESS		read-only
	STATUS		mandatory
	DESCRIPTION
			"The number of times an RPC call for the TCP 
			 protocol was not available when it was thought 
			 to be received, since the last time the 
			 statistics were cleared."
	::= { rpcServ 8 }

	rcpTcpBadLens	OBJECT-TYPE
	SYNTAX		Counter
	ACCESS		read-only
	STATUS		mandatory
	DESCRIPTION
			"The number of RPC calls for the TCP protocol
			 received with a length shorter than a minimum-sized 
			 RPC call, since the last time the statistics 
			 were cleared."
	::= { rpcServ 9 }

	rcpTcpServXDRCalls	OBJECT-TYPE
	SYNTAX		Counter
	ACCESS		read-only
	STATUS		mandatory
	DESCRIPTION
			"The number of RPC calls for the TCP protocol
			 received whose header could not be XDR decoded, 
			 since the last time the statistics were cleared."
	::= { rpcServ 10 }

 	rpcUdpCalls	OBJECT-TYPE
	SYNTAX		Counter
	ACCESS		read-only
	STATUS		mandatory
	DESCRIPTION
			"The total number of RPC calls received for the
			 UDP protocol, since the last time the statistics
			 were cleared."
	::= { rpcServ 11 }

	rpcUdpBadCalls	OBJECT-TYPE
	SYNTAX		Counter
	ACCESS		read-only
	STATUS		mandatory
	DESCRIPTION
			"The total number of calls rejected by the RPC
			 layer for the UDP protocol, since the last 
			 time the statistics were cleared."
	::= { rpcServ 12 }

	rpcUdpNullRecvs	OBJECT-TYPE
	SYNTAX		Counter
	ACCESS		read-only
	STATUS		mandatory
	DESCRIPTION
			"The number of times an RPC call for the UDP 
			 protocol was not available when it was thought 
			 to be received, since the last time the 
			 statistics were cleared."
	::= { rpcServ 13 }

	rpcUdpBadLens	OBJECT-TYPE
	SYNTAX		Counter
	ACCESS		read-only
	STATUS		mandatory
	DESCRIPTION
			"The number of RPC calls for the UDP protocol
			 received with a length shorter than a minimum-sized 
			 RPC call, since the last time the statistics 
			 were cleared."
	::= { rpcServ 14 }

	rpcUdpServXDRCalls	OBJECT-TYPE
	SYNTAX		Counter
	ACCESS		read-only
	STATUS		mandatory
	DESCRIPTION
			"The number of RPC calls for the UDP protocol
			 received whose header could not be XDR decoded, 
			 since the last time the statistics were cleared."
	::= { rpcServ 15 }


	-- the nfsServ group

	nfsCalls	OBJECT-TYPE
	SYNTAX		Counter
	ACCESS		read-only
	STATUS		mandatory
	DESCRIPTION
			"The total number of NFS calls received, since
			 the last time the statistics were cleared."
	::= { nfsServ 1 }

	nfsServBadCalls	OBJECT-TYPE
	SYNTAX		Counter
	ACCESS		read-only
	STATUS		mandatory
	DESCRIPTION
			"The total number of received NFS calls rejected,
			 since the last time the statistics were cleared."
	::= { nfsServ 2 }

	nfsV2		OBJECT IDENTIFIER ::= { nfsServ 3 }

	nfsV3		OBJECT IDENTIFIER ::= { nfsServ 4 }

	replyCache	OBJECT IDENTIFIER ::= { nfsServ 5 }

	nfsrwStats	OBJECT IDENTIFIER ::= { nfsServ 6 }


	-- the nfsV2 group

		-- this group contains statistics for NFS
		-- Version 2 calls processed since the last
		-- time the statistics were cleared

	v2Calls		OBJECT IDENTIFIER ::= { nfsV2 1 }

	v2Percent	OBJECT IDENTIFIER ::= { nfsV2 2 }

	v2CachedCalls	OBJECT IDENTIFIER ::= { nfsV2 3 }

	v2CachedPerCent	OBJECT IDENTIFIER ::= { nfsV2 4 }



	-- the v2Calls group

		-- this group contains statistics for the number of
		-- calls received for each NFS Version 2 procedure
		-- since the last time the statistics were cleared

	v2cNulls	OBJECT-TYPE
	SYNTAX		Counter
	ACCESS		read-only
	STATUS		mandatory
	DESCRIPTION
			"The number of NFS Version 2 calls received
			 for the NFSPROC_NULL (Do Nothing) procedure,
			 since the last time the statistics were cleared."
	::= { v2Calls 1 }

	v2cGetattrs	OBJECT-TYPE
	SYNTAX		Counter
	ACCESS		read-only
	STATUS		mandatory
	DESCRIPTION
			"The number of NFS Version 2 calls received
			 for the NFSPROC_GETATTR (Get File Attributes)
			 procedure, since the last time the statistics
			 were cleared."
	::= { v2Calls 2 }

	v2cSetattrs	OBJECT-TYPE
	SYNTAX		Counter
	ACCESS		read-only
	STATUS		mandatory
	DESCRIPTION
			"The number of NFS Version 2 calls received
			 for the NFSPROC_SETATTR (Set File Attributes)
			 procedure, since the last time the statistics
			 were cleared."
	::= { v2Calls 3 }

	v2cRoots	OBJECT-TYPE
	SYNTAX		Counter
	ACCESS		read-only
	STATUS		mandatory
	DESCRIPTION
			"The number of NFS Version 2 calls received
			 for the NFSPROC_ROOT (Get Filesystem Root)
			 procedure, since the last time the statistics
			 were cleared."
	::= { v2Calls 4 }

	v2cLookups	OBJECT-TYPE
	SYNTAX		Counter
	ACCESS		read-only
	STATUS		mandatory
	DESCRIPTION
			"The number of NFS Version 2 calls received
			 for the NFSPROC_LOOKUP (Look Up File Name)
			 procedure, since the last time the statistics
			 were cleared."
	::= { v2Calls 5 }

	v2cReadlinks	OBJECT-TYPE
	SYNTAX		Counter
	ACCESS		read-only
	STATUS		mandatory
	DESCRIPTION
			"The number of NFS Version 2 calls received
			 for the NFSPROC_READLINK (Read From Symbolic
			 Link) procedure, since the last time the
			 statistics were cleared."
	::= { v2Calls 6 }

	v2cReads	OBJECT-TYPE
	SYNTAX		Counter
	ACCESS		read-only
	STATUS		mandatory
	DESCRIPTION
			"The number of NFS Version 2 calls received
			 for the NFSPROC_READ (Read From File)
			 procedure, since the last time the statistics
			 were cleared."
	::= { v2Calls 7 }

	v2cWrcaches	OBJECT-TYPE
	SYNTAX		Counter
	ACCESS		read-only
	STATUS		mandatory
	DESCRIPTION
			"The number of NFS Version 2 calls received
			 for the NFSPROC_WRITECACHE (Write to Cache)
			 procedure, since the last time the statistics
			 were cleared."
	::= { v2Calls 8 }

	v2cWrites	OBJECT-TYPE
	SYNTAX		Counter
	ACCESS		read-only
	STATUS		mandatory
	DESCRIPTION
			"The number of NFS Version 2 calls received
			 for the NFSPROC_WRITE (Write to File)
			 procedure, since the last time the statistics
			 were cleared."
	::= { v2Calls 9 }

	v2cCreates	OBJECT-TYPE
	SYNTAX		Counter
	ACCESS		read-only
	STATUS		mandatory
	DESCRIPTION
			"The number of NFS Version 2 calls received
			 for the NFSPROC_CREATE (Create File)
			 procedure, since the last time the statistics
			 were cleared."
	::= { v2Calls 10 }

	v2cRemoves	OBJECT-TYPE
	SYNTAX		Counter
	ACCESS		read-only
	STATUS		mandatory
	DESCRIPTION
			"The number of NFS Version 2 calls received
			 for the NFSPROC_REMOVE (Remove File)
			 procedure, since the last time the statistics
			 were cleared."
	::= { v2Calls 11 }

	v2cRenames	OBJECT-TYPE
	SYNTAX		Counter
	ACCESS		read-only
	STATUS		mandatory
	DESCRIPTION
			"The number of NFS Version 2 calls received
			 for the NFSPROC_RENAME (Rename File)
			 procedure, since the last time the statistics
			 were cleared."
	::= { v2Calls 12 }

	v2cLinks	OBJECT-TYPE
	SYNTAX		Counter
	ACCESS		read-only
	STATUS		mandatory
	DESCRIPTION
			"The number of NFS Version 2 calls received
			 for the NFSPROC_LINK (Create Link to File)
			 procedure, since the last time the statistics
			 were cleared."
	::= { v2Calls 13 }

	v2cSymlinks	OBJECT-TYPE
	SYNTAX		Counter
	ACCESS		read-only
	STATUS		mandatory
	DESCRIPTION
			"The number of NFS Version 2 calls received
			 for the NFSPROC_SYMLINK (Create Symbolic Link)
			 procedure, since the last time the statistics
			 were cleared."
	::= { v2Calls 14 }

	v2cMkdirs	OBJECT-TYPE
	SYNTAX		Counter
	ACCESS		read-only
	STATUS		mandatory
	DESCRIPTION
			"The number of NFS Version 2 calls received
			 for the NFSPROC_MKDIR (Create Directory)
			 procedure, since the last time the statistics
			 were cleared."
	::= { v2Calls 15 }

	v2cRmdirs	OBJECT-TYPE
	SYNTAX		Counter
	ACCESS		read-only
	STATUS		mandatory
	DESCRIPTION
			"The number of NFS Version 2 calls received
			 for the NFSPROC_RMDIR (Remove Directory)
			 procedure, since the last time the statistics
			 were cleared."
	::= { v2Calls 16 }

	v2cReaddirs	OBJECT-TYPE
	SYNTAX		Counter
	ACCESS		read-only
	STATUS		mandatory
	DESCRIPTION
			"The number of NFS Version 2 calls received
			 for the NFSPROC_READDIR (Read From Directory)
			 procedure, since the last time the statistics
			 were cleared."
	::= { v2Calls 17 }

	v2cStatfss	OBJECT-TYPE
	SYNTAX		Counter
	ACCESS		read-only
	STATUS		mandatory
	DESCRIPTION
			"The number of NFS Version 2 calls received
			 for the NFSPROC_STATFS (Get Filesystem
			 Attributes) procedure, since the last time
			 the statistics were cleared."
	::= { v2Calls 18 }



	-- the v2Percent group

		-- this group contains statistics for the number of
		-- calls received for each NFS Version 2 procedure,
		-- as a percentage of total NFS calls received,
		-- since the last time the statistics were cleared

	v2pNulls	OBJECT-TYPE
	SYNTAX		INTEGER (0..100)
	ACCESS		read-only
	STATUS		mandatory
	DESCRIPTION
			"The number of NFS Version 2 calls received
			 for the NFSPROC_NULL (Do Nothing) procedure
			 as a percentage of total NFS calls received,
			 since the last time the statistics were cleared."
	::= { v2Percent 1 }

	v2pGetattrs	OBJECT-TYPE
	SYNTAX		INTEGER (0..100)
	ACCESS		read-only
	STATUS		mandatory
	DESCRIPTION
			"The number of NFS Version 2 calls received
			 for the NFSPROC_GETATTR (Get File Attributes)
			 procedure as a percentage of total NFS calls
			 received, since the last time the statistics
			 were cleared."
	::= { v2Percent 2 }

	v2pSetattrs	OBJECT-TYPE
	SYNTAX		INTEGER (0..100)
	ACCESS		read-only
	STATUS		mandatory
	DESCRIPTION
			"The number of NFS Version 2 calls received
			 for the NFSPROC_SETATTR (Set File Attributes)
			 procedure as a percentage of total NFS calls
			 received, since the last time the statistics
			 were cleared."
	::= { v2Percent 3 }

	v2pRoots	OBJECT-TYPE
	SYNTAX		INTEGER (0..100)
	ACCESS		read-only
	STATUS		mandatory
	DESCRIPTION
			"The number of NFS Version 2 calls received
			 for the NFSPROC_ROOT (Get Filesystem Root)
			 procedure as a percentage of total NFS calls
			 received, since the last time the statistics
			 were cleared."
	::= { v2Percent 4 }

	v2pLookups	OBJECT-TYPE
	SYNTAX		INTEGER (0..100)
	ACCESS		read-only
	STATUS		mandatory
	DESCRIPTION
			"The number of NFS Version 2 calls received
			 for the NFSPROC_LOOKUP (Look Up File Name)
			 procedure as a percentage of total NFS calls
			 received, since the last time the statistics
			 were cleared."
	::= { v2Percent 5 }

	v2pReadlinks	OBJECT-TYPE
	SYNTAX		INTEGER (0..100)
	ACCESS		read-only
	STATUS		mandatory
	DESCRIPTION
			"The number of NFS Version 2 calls received
			 for the NFSPROC_READLINK (Read From Symbolic
			 Link) procedure as a percentage of total NFS
			 calls received, since the last time the
			 statistics were cleared."
	::= { v2Percent 6 }

	v2pReads	OBJECT-TYPE
	SYNTAX		INTEGER (0..100)
	ACCESS		read-only
	STATUS		mandatory
	DESCRIPTION
			"The number of NFS Version 2 calls received
			 for the NFSPROC_READ (Read From File)
			 procedure as a percentage of total NFS calls
			 received, since the last time the statistics
			 were cleared."
	::= { v2Percent 7 }

	v2pWrcaches	OBJECT-TYPE
	SYNTAX		INTEGER (0..100)
	ACCESS		read-only
	STATUS		mandatory
	DESCRIPTION
			"The number of NFS Version 2 calls received
			 for the NFSPROC_WRITECACHE (Write to Cache)
			 procedure as a percentage of total NFS calls
			 received, since the last time the statistics
			 were cleared."
	::= { v2Percent 8 }

	v2pWrites	OBJECT-TYPE
	SYNTAX		INTEGER (0..100)
	ACCESS		read-only
	STATUS		mandatory
	DESCRIPTION
			"The number of NFS Version 2 calls received
			 for the NFSPROC_WRITE (Write to File)
			 procedure as a percentage of total NFS calls
			 received, since the last time the statistics
			 were cleared."
	::= { v2Percent 9 }

	v2pCreates	OBJECT-TYPE
	SYNTAX		INTEGER (0..100)
	ACCESS		read-only
	STATUS		mandatory
	DESCRIPTION
			"The number of NFS Version 2 calls received
			 for the NFSPROC_CREATE (Create File)
			 procedure as a percentage of total NFS calls
			 received, since the last time the statistics
			 were cleared."
	::= { v2Percent 10 }

	v2pRemoves	OBJECT-TYPE
	SYNTAX		INTEGER (0..100)
	ACCESS		read-only
	STATUS		mandatory
	DESCRIPTION
			"The number of NFS Version 2 calls received
			 for the NFSPROC_REMOVE (Remove File)
			 procedure as a percentage of total NFS calls
			 received, since the last time the statistics
			 were cleared."
	::= { v2Percent 11 }

	v2pRenames	OBJECT-TYPE
	SYNTAX		INTEGER (0..100)
	ACCESS		read-only
	STATUS		mandatory
	DESCRIPTION
			"The number of NFS Version 2 calls received
			 for the NFSPROC_RENAME (Rename File)
			 procedure as a percentage of total NFS calls
			 received, since the last time the statistics
			 were cleared."
	::= { v2Percent 12 }

	v2pLinks	OBJECT-TYPE
	SYNTAX		INTEGER (0..100)
	ACCESS		read-only
	STATUS		mandatory
	DESCRIPTION
			"The number of NFS Version 2 calls received
			 for the NFSPROC_LINK (Create Link to File)
			 procedure as a percentage of total NFS calls
			 received, since the last time the statistics
			 were cleared."
	::= { v2Percent 13 }

	v2pSymlinks	OBJECT-TYPE
	SYNTAX		INTEGER (0..100)
	ACCESS		read-only
	STATUS		mandatory
	DESCRIPTION
			"The number of NFS Version 2 calls received
			 for the NFSPROC_SYMLINK (Create Symbolic Link)
			 procedure as a percentage of total NFS calls
			 received, since the last time the statistics
			 were cleared."
	::= { v2Percent 14 }

	v2pMkdirs	OBJECT-TYPE
	SYNTAX		INTEGER (0..100)
	ACCESS		read-only
	STATUS		mandatory
	DESCRIPTION
			"The number of NFS Version 2 calls received
			 for the NFSPROC_MKDIR (Create Directory)
			 procedure as a percentage of total NFS calls
			 received, since the last time the statistics
			 were cleared."
	::= { v2Percent 15 }

	v2pRmdirs	OBJECT-TYPE
	SYNTAX		INTEGER (0..100)
	ACCESS		read-only
	STATUS		mandatory
	DESCRIPTION
			"The number of NFS Version 2 calls received
			 for the NFSPROC_RMDIR (Remove Directory)
			 procedure as a percentage of total NFS calls
			 received, since the last time the statistics
			 were cleared."
	::= { v2Percent 16 }

	v2pReaddirs	OBJECT-TYPE
	SYNTAX		INTEGER (0..100)
	ACCESS		read-only
	STATUS		mandatory
	DESCRIPTION
			"The number of NFS Version 2 calls received
			 for the NFSPROC_READDIR (Read From Directory)
			 procedure as a percentage of total NFS calls
			 received, since the last time the statistics
			 were cleared."
	::= { v2Percent 17 }

	v2pStatfss	OBJECT-TYPE
	SYNTAX		INTEGER (0..100)
	ACCESS		read-only
	STATUS		mandatory
	DESCRIPTION
			"The number of NFS Version 2 calls received
			 for the NFSPROC_STATFS (Get Filesystem
			 Attributes) procedure as a percentage of
			 total NFS calls received, since the last
			 time the statistics were cleared."
	::= { v2Percent 18 }



	-- the v2CachedCalls group

		-- this group contains statistics for the number of
		-- calls received for each NFS Version 2 procedure,
		-- that did not result in the filesystem blocking to
		-- read from disk, since the last time the statistics
		-- were cleared

	v2ccNulls	OBJECT-TYPE
	SYNTAX		Counter
	ACCESS		read-only
	STATUS		mandatory
	DESCRIPTION
			"The number of NFS Version 2 calls received
			 for the NFSPROC_NULL (Do Nothing) procedure,
			 that did not result in the filesystem
			 blocking to read from disk, since the last
			 time the statistics were cleared."
	::= { v2CachedCalls 1 }

	v2ccGetattrs	OBJECT-TYPE
	SYNTAX		Counter
	ACCESS		read-only
	STATUS		mandatory
	DESCRIPTION
			"The number of NFS Version 2 calls received
			 for the NFSPROC_GETATTR (Get File Attributes)
			 procedure, that did not result in the
			 filesystem blocking to read from disk, since
			 the last time the statistics were cleared."
	::= { v2CachedCalls 2 }

	v2ccSetattrs	OBJECT-TYPE
	SYNTAX		Counter
	ACCESS		read-only
	STATUS		mandatory
	DESCRIPTION
			"The number of NFS Version 2 calls received
			 for the NFSPROC_SETATTR (Set File Attributes)
			 procedure, that did not result in the
			 filesystem blocking to read from disk, since
			 the last time the statistics were cleared."
	::= { v2CachedCalls 3 }

	v2ccRoots	OBJECT-TYPE
	SYNTAX		Counter
	ACCESS		read-only
	STATUS		mandatory
	DESCRIPTION
			"The number of NFS Version 2 calls received
			 for the NFSPROC_ROOT (Get Filesystem Root)
			 procedure, that did not result in the
			 filesystem blocking to read from disk, since
			 the last time the statistics were cleared."
	::= { v2CachedCalls 4 }

	v2ccLookups	OBJECT-TYPE
	SYNTAX		Counter
	ACCESS		read-only
	STATUS		mandatory
	DESCRIPTION
			"The number of NFS Version 2 calls received
			 for the NFSPROC_LOOKUP (Look Up File Name)
			 procedure, that did not result in the
			 filesystem blocking to read from disk, since
			 the last time the statistics were cleared."
	::= { v2CachedCalls 5 }

	v2ccReadlinks	OBJECT-TYPE
	SYNTAX		Counter
	ACCESS		read-only
	STATUS		mandatory
	DESCRIPTION
			"The number of NFS Version 2 calls received
			 for the NFSPROC_READLINK (Read From Symbolic
			 Link) procedure, that did not result in the
			 filesystem blocking to read from disk, since
			 the last time the statistics were cleared."
	::= { v2CachedCalls 6 }

	v2ccReads	OBJECT-TYPE
	SYNTAX		Counter
	ACCESS		read-only
	STATUS		mandatory
	DESCRIPTION
			"The number of NFS Version 2 calls received
			 for the NFSPROC_READ (Read From File)
			 procedure, that did not result in the
			 filesystem blocking to read from disk, since
			 the last time the statistics were cleared."
	::= { v2CachedCalls 7 }

	v2ccWrcaches	OBJECT-TYPE
	SYNTAX		Counter
	ACCESS		read-only
	STATUS		mandatory
	DESCRIPTION
			"The number of NFS Version 2 calls received
			 for the NFSPROC_WRITECACHE (Write to Cache)
			 procedure, that did not result in the
			 filesystem blocking to read from disk, since
			 the last time the statistics were cleared."
	::= { v2CachedCalls 8 }

	v2ccWrites	OBJECT-TYPE
	SYNTAX		Counter ACCESS		read-only
	STATUS		mandatory
	DESCRIPTION
			"The number of NFS Version 2 calls received
			 for the NFSPROC_WRITE (Write to File)
			 procedure, that did not result in the
			 filesystem blocking to read from disk, since
			 the last time the statistics were cleared."
	::= { v2CachedCalls 9 }

	v2ccCreates	OBJECT-TYPE
	SYNTAX		Counter
	ACCESS		read-only
	STATUS		mandatory
	DESCRIPTION
			"The number of NFS Version 2 calls received
			 for the NFSPROC_CREATE (Create File)
			 procedure, that did not result in the
			 filesystem blocking to read from disk, since
			 the last time the statistics were cleared."
	::= { v2CachedCalls 10 }

	v2ccRemoves	OBJECT-TYPE
	SYNTAX		Counter
	ACCESS		read-only
	STATUS		mandatory
	DESCRIPTION
			"The number of NFS Version 2 calls received
			 for the NFSPROC_REMOVE (Remove File)
			 procedure, that did not result in the
			 filesystem blocking to read from disk, since
			 the last time the statistics were cleared."
	::= { v2CachedCalls 11 }

	v2ccRenames	OBJECT-TYPE
	SYNTAX		Counter
	ACCESS		read-only
	STATUS		mandatory
	DESCRIPTION
			"The number of NFS Version 2 calls received
			 for the NFSPROC_RENAME (Rename File)
			 procedure, that did not result in the
			 filesystem blocking to read from disk, since
			 the last time the statistics were cleared."
	::= { v2CachedCalls 12 }

	v2ccLinks	OBJECT-TYPE
	SYNTAX		Counter
	ACCESS		read-only
	STATUS		mandatory
	DESCRIPTION
			"The number of NFS Version 2 calls received
			 for the NFSPROC_LINK (Create Link to File)
			 procedure, that did not result in the
			 filesystem blocking to read from disk, since
			 the last time the statistics were cleared."
	::= { v2CachedCalls 13 }

	v2ccSymlinks	OBJECT-TYPE
	SYNTAX		Counter
	ACCESS		read-only
	STATUS		mandatory
	DESCRIPTION
			"The number of NFS Version 2 calls received
			 for the NFSPROC_SYMLINK (Create Symbolic Link)
			 procedure, that did not result in the
			 filesystem blocking to read from disk, since
			 the last time the statistics were cleared."
	::= { v2CachedCalls 14 }

	v2ccMkdirs	OBJECT-TYPE
	SYNTAX		Counter
	ACCESS		read-only
	STATUS		mandatory
	DESCRIPTION
			"The number of NFS Version 2 calls received
			 for the NFSPROC_MKDIR (Create Directory)
			 procedure, that did not result in the
			 filesystem blocking to read from disk, since
			 the last time the statistics were cleared."
	::= { v2CachedCalls 15 }

	v2ccRmdirs	OBJECT-TYPE
	SYNTAX		Counter
	ACCESS		read-only
	STATUS		mandatory
	DESCRIPTION
			"The number of NFS Version 2 calls received
			 for the NFSPROC_RMDIR (Remove Directory)
			 procedure, that did not result in the
			 filesystem blocking to read from disk, since
			 the last time the statistics were cleared."
	::= { v2CachedCalls 16 }

	v2ccReaddirs	OBJECT-TYPE
	SYNTAX		Counter
	ACCESS		read-only
	STATUS		mandatory
	DESCRIPTION
			"The number of NFS Version 2 calls received
			 for the NFSPROC_READDIR (Read From Directory)
			 procedure, that did not result in the
			 filesystem blocking to read from disk, since
			 the last time the statistics were cleared."
	::= { v2CachedCalls 17 }

	v2ccStatfss	OBJECT-TYPE
	SYNTAX		Counter
	ACCESS		read-only
	STATUS		mandatory
	DESCRIPTION
			"The number of NFS Version 2 calls received
			 for the NFSPROC_STATFS (Get Filesystem
			 Attributes) procedure, that did not result
			 in the filesystem blocking to read from disk,
			 since the last time the statistics were cleared."
	::= { v2CachedCalls 18 }



	-- the v2CachedPerCent group

		-- this group contains statistics for the number of
		-- calls received for each NFS Version 2 procedure,
		-- that did not result in the filesystem blocking to
		-- read from disk, as a percentage of the total
		-- number of calls received for that procedure,
		-- since the last time the statistics were cleared

	v2cpNulls	OBJECT-TYPE
	SYNTAX		INTEGER (0..100)
	ACCESS		read-only
	STATUS		mandatory
	DESCRIPTION
			"The number of NFS Version 2 calls received
			 for the NFSPROC_NULL (Do Nothing) procedure,
			 that did not result in the filesystem
			 blocking to read from disk, as a percentage
			 of the total number of calls received for
			 this procedure, since the last time the
			 statistics were cleared."
	::= { v2CachedPerCent 1 }

	v2cpGetattrs	OBJECT-TYPE
	SYNTAX		INTEGER (0..100)
	ACCESS		read-only
	STATUS		mandatory
	DESCRIPTION
			"The number of NFS Version 2 calls received
			 for the NFSPROC_GETATTR (Get File Attributes)
			 procedure, that did not result in the
			 filesystem blocking to read from disk, as a
			 percentage of the total number of calls
			 received for this procedure, since the last
			 time the statistics were cleared."
	::= { v2CachedPerCent 2 }

	v2cpSetattrs	OBJECT-TYPE
	SYNTAX		INTEGER (0..100)
	ACCESS		read-only
	STATUS		mandatory
	DESCRIPTION
			"The number of NFS Version 2 calls received
			 for the NFSPROC_SETATTR (Set File Attributes)
			 procedure, that did not result in the
			 filesystem blocking to read from disk, as a
			 percentage of the total number of calls
			 received for this procedure, since the last
			 time the statistics were cleared."
	::= { v2CachedPerCent 3 }

	v2cpRoots	OBJECT-TYPE
	SYNTAX		INTEGER (0..100)
	ACCESS		read-only
	STATUS		mandatory
	DESCRIPTION
			"The number of NFS Version 2 calls received
			 for the NFSPROC_ROOT (Get Filesystem Root)
			 procedure, that did not result in the
			 filesystem blocking to read from disk, as a
			 percentage of the total number of calls
			 received for this procedure, since the last
			 time the statistics were cleared."
	::= { v2CachedPerCent 4 }

	v2cpLookups	OBJECT-TYPE
	SYNTAX		INTEGER (0..100)
	ACCESS		read-only
	STATUS		mandatory
	DESCRIPTION
			"The number of NFS Version 2 calls received
			 for the NFSPROC_LOOKUP (Look Up File Name)
			 procedure, that did not result in the
			 filesystem blocking to read from disk, as a
			 percentage of the total number of calls
			 received for this procedure, since the last
			 time the statistics were cleared."
	::= { v2CachedPerCent 5 }

	v2cpReadlinks	OBJECT-TYPE
	SYNTAX		INTEGER (0..100)
	ACCESS		read-only
	STATUS		mandatory
	DESCRIPTION
			"The number of NFS Version 2 calls received
			 for the NFSPROC_READLINK (Read From Symbolic
			 Link) procedure, that did not result in the
			 filesystem blocking to read from disk, as a
			 percentage of the total number of calls
			 received for this procedure, since the last
			 time the statistics were cleared."
	::= { v2CachedPerCent 6 }

	v2cpReads	OBJECT-TYPE
	SYNTAX		INTEGER (0..100)
	ACCESS		read-only
	STATUS		mandatory
	DESCRIPTION
			"The number of NFS Version 2 calls received
			 for the NFSPROC_READ (Read From File)
			 procedure, that did not result in the
			 filesystem blocking to read from disk, as a
			 percentage of the total number of calls
			 received for this procedure, since the last
			 time the statistics were cleared."
	::= { v2CachedPerCent 7 }

	v2cpWrcaches	OBJECT-TYPE
	SYNTAX		INTEGER (0..100)
	ACCESS		read-only
	STATUS		mandatory
	DESCRIPTION
			"The number of NFS Version 2 calls received
			 for the NFSPROC_WRITECACHE (Write to Cache)
			 procedure, that did not result in the
			 filesystem blocking to read from disk, as a
			 percentage of the total number of calls
			 received for this procedure, since the last
			 time the statistics were cleared."
	::= { v2CachedPerCent 8 }

	v2cpWrites	OBJECT-TYPE
	SYNTAX		INTEGER (0..100)
	ACCESS		read-only
	STATUS		mandatory
	DESCRIPTION
			"The number of NFS Version 2 calls received
			 for the NFSPROC_WRITE (Write to File)
			 procedure, that did not result in the
			 filesystem blocking to read from disk, as a
			 percentage of the total number of calls
			 received for this procedure, since the last
			 time the statistics were cleared."
	::= { v2CachedPerCent 9 }

	v2cpCreates	OBJECT-TYPE
	SYNTAX		INTEGER (0..100)
	ACCESS		read-only
	STATUS		mandatory
	DESCRIPTION
			"The number of NFS Version 2 calls received
			 for the NFSPROC_CREATE (Create File)
			 procedure, that did not result in the
			 filesystem blocking to read from disk, as a
			 percentage of the total number of calls
			 received for this procedure, since the last
			 time the statistics were cleared."
	::= { v2CachedPerCent 10 }

	v2cpRemoves	OBJECT-TYPE
	SYNTAX		INTEGER (0..100)
	ACCESS		read-only
	STATUS		mandatory
	DESCRIPTION
			"The number of NFS Version 2 calls received
			 for the NFSPROC_REMOVE (Remove File)
			 procedure, that did not result in the
			 filesystem blocking to read from disk, as a
			 percentage of the total number of calls
			 received for this procedure, since the last
			 time the statistics were cleared."
	::= { v2CachedPerCent 11 }

	v2cpRenames	OBJECT-TYPE
	SYNTAX		INTEGER (0..100)
	ACCESS		read-only
	STATUS		mandatory
	DESCRIPTION
			"The number of NFS Version 2 calls received
			 for the NFSPROC_RENAME (Rename File)
			 procedure, that did not result in the
			 filesystem blocking to read from disk, as a
			 percentage of the total number of calls
			 received for this procedure, since the last
			 time the statistics were cleared."
	::= { v2CachedPerCent 12 }

	v2cpLinks	OBJECT-TYPE
	SYNTAX		INTEGER (0..100)
	ACCESS		read-only
	STATUS		mandatory
	DESCRIPTION
			"The number of NFS Version 2 calls received
			 for the NFSPROC_LINK (Create Link to File)
			 procedure, that did not result in the
			 filesystem blocking to read from disk, as a
			 percentage of the total number of calls
			 received for this procedure, since the last
			 time the statistics were cleared."
	::= { v2CachedPerCent 13 }

	v2cpSymlinks	OBJECT-TYPE
	SYNTAX		INTEGER (0..100)
	ACCESS		read-only
	STATUS		mandatory
	DESCRIPTION
			"The number of NFS Version 2 calls received
			 for the NFSPROC_SYMLINK (Create Symbolic
			 Link) procedure, that did not result in the
			 filesystem blocking to read from disk, as a
			 percentage of the total number of calls
			 received for this procedure, since the last
			 time the statistics were cleared."
	::= { v2CachedPerCent 14 }

	v2cpMkdirs	OBJECT-TYPE
	SYNTAX		INTEGER (0..100)
	ACCESS		read-only
	STATUS		mandatory
	DESCRIPTION
			"The number of NFS Version 2 calls received
			 for the NFSPROC_MKDIR (Create Directory)
			 procedure, that did not result in the
			 filesystem blocking to read from disk, as a
			 percentage of the total number of calls
			 received for this procedure, since the last
			 time the statistics were cleared."
	::= { v2CachedPerCent 15 }

	v2cpRmdirs	OBJECT-TYPE
	SYNTAX		INTEGER (0..100)
	ACCESS		read-only
	STATUS		mandatory
	DESCRIPTION
			"The number of NFS Version 2 calls received
			 for the NFSPROC_RMDIR (Remove Directory)
			 procedure, that did not result in the
			 filesystem blocking to read from disk, as a
			 percentage of the total number of calls
			 received for this procedure, since the last
			 time the statistics were cleared."
	::= { v2CachedPerCent 16 }

	v2cpReaddirs	OBJECT-TYPE
	SYNTAX		INTEGER (0..100)
	ACCESS		read-only
	STATUS		mandatory
	DESCRIPTION
			"The number of NFS Version 2 calls received
			 for the NFSPROC_READDIR (Read From Directory)
			 procedure, that did not result in the
			 filesystem blocking to read from disk, as a
			 percentage of the total number of calls
			 received for this procedure, since the last
			 time the statistics were cleared."
	::= { v2CachedPerCent 17 }

	v2cpStatfss	OBJECT-TYPE
	SYNTAX		INTEGER (0..100)
	ACCESS		read-only
	STATUS		mandatory
	DESCRIPTION
			"The number of NFS Version 2 calls received
			 for the NFSPROC_STATFS (Get Filesystem
			 Attributes) procedure, that did not result
			 in the filesystem blocking to read from
			 disk, as a percentage of the total number
			 of calls received for this procedure, since
			 the last time the statistics were cleared."
	::= { v2CachedPerCent 18 }



	-- the nfsV3 group

		-- this group contains statistics for NFS
		-- Version 3 calls processed since the last
		-- time the statistics were cleared

	v3Calls		OBJECT IDENTIFIER ::= { nfsV3 1 }

	v3Percent	OBJECT IDENTIFIER ::= { nfsV3 2 }

	v3CachedCalls	OBJECT IDENTIFIER ::= { nfsV3 3 }

	v3CachedPerCent	OBJECT IDENTIFIER ::= { nfsV3 4 }



	-- the v3Calls group

		-- this group contains statistics for the number of
		-- calls received for each NFS Version 3 procedure
		-- since the last time the statistics were cleared

	v3cNulls	OBJECT-TYPE
	SYNTAX		Counter
	ACCESS		read-only
	STATUS		mandatory
	DESCRIPTION
			"The number of NFS Version 3 calls received
			 for the NFSPROC3_NULL (Do Nothing) procedure,
			 since the last time the statistics were cleared."
	::= { v3Calls 1 }

	v3cGetattrs	OBJECT-TYPE
	SYNTAX		Counter
	ACCESS		read-only
	STATUS		mandatory
	DESCRIPTION
			"The number of NFS Version 3 calls received
			 for the NFSPROC3_GETATTR (Get File Attributes)
			 procedure, since the last time the statistics
			 were cleared."
	::= { v3Calls 2 }

	v3cSetattrs	OBJECT-TYPE
	SYNTAX		Counter
	ACCESS		read-only
	STATUS		mandatory
	DESCRIPTION
			"The number of NFS Version 3 calls received
			 for the NFSPROC3_SETATTR (Set File Attributes)
			 procedure, since the last time the statistics
			 were cleared."
	::= { v3Calls 3 }

	v3cLookups	OBJECT-TYPE
	SYNTAX		Counter
	ACCESS		read-only
	STATUS		mandatory
	DESCRIPTION
			"The number of NFS Version 3 calls received
			 for the NFSPROC3_LOOKUP (Lookup Filename)
			 procedure, since the last time the statistics
			 were cleared."
	::= { v3Calls 4 }

	v3cAccesss	OBJECT-TYPE
	SYNTAX		Counter
	ACCESS		read-only
	STATUS		mandatory
	DESCRIPTION
			"The number of NFS Version 3 calls received
			 for the NFSPROC3_ACCESS (Check Access Permission)
			 procedure, since the last time the statistics
			 were cleared."
	::= { v3Calls 5 }

	v3cReadlinks	OBJECT-TYPE
	SYNTAX		Counter
	ACCESS		read-only
	STATUS		mandatory
	DESCRIPTION
			"The number of NFS Version 3 calls received
			 for the NFSPROC3_READLINK (Read from Symbolic
			 Link) procedure, since the last time the
			 statistics were cleared."
	::= { v3Calls 6 }

	v3cReads	OBJECT-TYPE
	SYNTAX		Counter
	ACCESS		read-only
	STATUS		mandatory
	DESCRIPTION
			"The number of NFS Version 3 calls received
			 for the NFSPROC3_READ (Read From File)
			 procedure, since the last time the statistics
			 were cleared."
	::= { v3Calls 7 }

	v3cWrites	OBJECT-TYPE
	SYNTAX		Counter
	ACCESS		read-only
	STATUS		mandatory
	DESCRIPTION
			"The number of NFS Version 3 calls received
			 for the NFSPROC3_WRITE (Write to File)
			 procedure, since the last time the statistics
			 were cleared."
	::= { v3Calls 8 }

	v3cCreates	OBJECT-TYPE
	SYNTAX		Counter
	ACCESS		read-only
	STATUS		mandatory
	DESCRIPTION
			"The number of NFS Version 3 calls received
			 for the NFSPROC3_CREATE (Create a File)
			 procedure, since the last time the statistics
			 were cleared."
	::= { v3Calls 9 }

	v3cMkdirs	OBJECT-TYPE
	SYNTAX		Counter
	ACCESS		read-only
	STATUS		mandatory
	DESCRIPTION
			"The number of NFS Version 3 calls received
			 for the NFSPROC3_MKDIR (Create a Directory)
			 procedure, since the last time the statistics
			 were cleared."
	::= { v3Calls 10 }

	v3cSymlinks	OBJECT-TYPE
	SYNTAX		Counter
	ACCESS		read-only
	STATUS		mandatory
	DESCRIPTION
			"The number of NFS Version 3 calls received
			 for the NFSPROC3_SYMLINK (Create a Symbolic
			 Link) procedure, since the last time the
			 statistics were cleared."
	::= { v3Calls 11 }

	v3cMknods	OBJECT-TYPE
	SYNTAX		Counter
	ACCESS		read-only
	STATUS		mandatory
	DESCRIPTION
			"The number of NFS Version 3 calls received
			 for the NFSPROC3_MKNOD (Create a Special
			 Device) procedure, since the last time the
			 statistics were cleared."
	::= { v3Calls 12 }

	v3cRemoves	OBJECT-TYPE
	SYNTAX		Counter
	ACCESS		read-only
	STATUS		mandatory
	DESCRIPTION
			"The number of NFS Version 3 calls received
			 for the NFSPROC3_REMOVE (Remove a File)
			 procedure, since the last time the statistics
			 were cleared."
	::= { v3Calls 13 }

	v3cRmdirs	OBJECT-TYPE
	SYNTAX		Counter
	ACCESS		read-only
	STATUS		mandatory
	DESCRIPTION
			"The number of NFS Version 3 calls received
			 for the NFSPROC3_RMDIR (Remove a Directory)
			 procedure, since the last time the statistics
			 were cleared."
	::= { v3Calls 14 }

	v3cRenames	OBJECT-TYPE
	SYNTAX		Counter
	ACCESS		read-only
	STATUS		mandatory
	DESCRIPTION
			"The number of NFS Version 3 calls received
			 for the NFSPROC3_RENAME (Rename a File or
			 Directory) procedure, since the last time
			 the statistics were cleared."
	::= { v3Calls 15 }

	v3cLinks	OBJECT-TYPE
	SYNTAX		Counter
	ACCESS		read-only
	STATUS		mandatory
	DESCRIPTION
			"The number of NFS Version 3 calls received
			 for the NFSPROC3_LINK (Create Link to an
			 Object) procedure, since the last time the
			 statistics were cleared."
	::= { v3Calls 16 }

	v3cReaddirs	OBJECT-TYPE
	SYNTAX		Counter
	ACCESS		read-only
	STATUS		mandatory
	DESCRIPTION
			"The number of NFS Version 3 calls received
			 for the NFSPROC3_READDIR (Read From Directory)
			 procedure, since the last time the statistics
			 were cleared."
	::= { v3Calls 17 }

	v3cReaddirPluss	OBJECT-TYPE
	SYNTAX		Counter
	ACCESS		read-only
	STATUS		mandatory
	DESCRIPTION
			"The number of NFS Version 3 calls received
			 for the NFSPROC3_READDIRPLUS (Extended Read
			 from Directory) procedure, since the last
			 time the statistics were cleared."
	::= { v3Calls 18 }

	v3cFsstats	OBJECT-TYPE
	SYNTAX		Counter
	ACCESS		read-only
	STATUS		mandatory
	DESCRIPTION
			"The number of NFS Version 3 calls received
			 for the NFSPROC3_FSSTAT (Get Dynamic File
			 System Information) procedure, since the
			 last time the statistics were cleared."
	::= { v3Calls 19 }

	v3cFsinfos	OBJECT-TYPE
	SYNTAX		Counter
	ACCESS		read-only
	STATUS		mandatory
	DESCRIPTION
			"The number of NFS Version 3 calls received
			 for the NFSPROC3_FSINFO (Get Static File System
			 Information) procedure, since the last time
			 the statistics were cleared."
	::= { v3Calls 20 }

	v3cPathconfs	OBJECT-TYPE
	SYNTAX		Counter
	ACCESS		read-only
	STATUS		mandatory
	DESCRIPTION
			"The number of NFS Version 3 calls received
			 for the NFSPROC3_PATHCONF (Retrieve POSIX
			 Information) procedure, since the last time
			 the statistics were cleared."
	::= { v3Calls 21 }

	v3cCommits	OBJECT-TYPE
	SYNTAX		Counter
	ACCESS		read-only
	STATUS		mandatory
	DESCRIPTION
			"The number of NFS Version 3 calls received
			 for the NFSPROC3_COMMIT (Commit Cached Data on
			 a Server to Stable Storage) procedure, since
			 the last time the statistics were cleared."
	::= { v3Calls 22 }



	-- the v3Percent group

		-- this group contains statistics for the number of
		-- calls received for each NFS Version 3 procedure,
		-- as a percentage of total NFS calls received,
		-- since the last time the statistics were cleared

	v3pNulls	OBJECT-TYPE
	SYNTAX		INTEGER (0..100)
	ACCESS		read-only
	STATUS		mandatory
	DESCRIPTION
			"The number of NFS Version 3 calls received
			 for the NFSPROC3_NULL (Do Nothing) procedure,
			 as a percentage of the total NFS calls
			 received, since the last time the statistics
			 were cleared."
	::= { v3Percent 1 }

	v3pGetattrs	OBJECT-TYPE
	SYNTAX		INTEGER (0..100)
	ACCESS		read-only
	STATUS		mandatory
	DESCRIPTION
			"The number of NFS Version 3 calls received
			 for the NFSPROC3_GETATTR (Get File Attributes)
			 procedure, as a percentage of the total NFS
			 calls received, since the last time the
			 statistics were cleared."
	::= { v3Percent 2 }

	v3pSetattrs	OBJECT-TYPE
	SYNTAX		INTEGER (0..100)
	ACCESS		read-only
	STATUS		mandatory
	DESCRIPTION
			"The number of NFS Version 3 calls received
			 for the NFSPROC3_SETATTR (Set File Attributes)
			 procedure, as a percentage of the total NFS
			 calls received, since the last time the
			 statistics were cleared."
	::= { v3Percent 3 }

	v3pLookups	OBJECT-TYPE
	SYNTAX		INTEGER (0..100)
	ACCESS		read-only
	STATUS		mandatory
	DESCRIPTION
			"The number of NFS Version 3 calls received
			 for the NFSPROC3_LOOKUP (Lookup Filename)
			 procedure, as a percentage of the total NFS
			 calls received, since the last time the
			 statistics were cleared."
	::= { v3Percent 4 }

	v3pAccesss	OBJECT-TYPE
	SYNTAX		INTEGER (0..100)
	ACCESS		read-only
	STATUS		mandatory
	DESCRIPTION
			"The number of NFS Version 3 calls received
			 for the NFSPROC3_ACCESS (Check Access
			 Permission) procedure, as a percentage of
			 the total NFS calls received, since the
			 last time the statistics were cleared."
	::= { v3Percent 5 }

	v3pReadlinks	OBJECT-TYPE
	SYNTAX		INTEGER (0..100)
	ACCESS		read-only
	STATUS		mandatory
	DESCRIPTION
			"The number of NFS Version 3 calls received
			 for the NFSPROC3_READLINK (Read from Symbolic
			 Link) procedure, as a percentage of the total
			 NFS calls received, since the last time the
			 statistics were cleared."
	::= { v3Percent 6 }

	v3pReads	OBJECT-TYPE
	SYNTAX		INTEGER (0..100)
	ACCESS		read-only
	STATUS		mandatory
	DESCRIPTION
			"The number of NFS Version 3 calls received
			 for the NFSPROC3_READ (Read From File)
			 procedure, as a percentage of the total NFS
			 calls received, since the last time the
			 statistics were cleared."
	::= { v3Percent 7 }

	v3pWrites	OBJECT-TYPE
	SYNTAX		INTEGER (0..100)
	ACCESS		read-only
	STATUS		mandatory
	DESCRIPTION
			"The number of NFS Version 3 calls received
			 for the NFSPROC3_WRITE (Write to File)
			 procedure, as a percentage of the total NFS
			 calls received, since the last time the
			 statistics were cleared."
	::= { v3Percent 8 }

	v3pCreates	OBJECT-TYPE
	SYNTAX		INTEGER (0..100)
	ACCESS		read-only
	STATUS		mandatory
	DESCRIPTION
			"The number of NFS Version 3 calls received
			 for the NFSPROC3_CREATE (Create a File)
			 procedure, as a percentage of the total NFS
			 calls received, since the last time the
			 statistics were cleared."
	::= { v3Percent 9 }

	v3pMkdirs	OBJECT-TYPE
	SYNTAX		INTEGER (0..100)
	ACCESS		read-only
	STATUS		mandatory
	DESCRIPTION
			"The number of NFS Version 3 calls received
			 for the NFSPROC3_MKDIR (Create a Directory)
			 procedure, as a percentage of the total NFS
			 calls received, since the last time the
			 statistics were cleared."
	::= { v3Percent 10 }

	v3pSymlinks	OBJECT-TYPE
	SYNTAX		INTEGER (0..100)
	ACCESS		read-only
	STATUS		mandatory
	DESCRIPTION
			"The number of NFS Version 3 calls received
			 for the NFSPROC3_SYMLINK (Create a Symbolic
			 Link) procedure, as a percentage of the total
			 NFS calls received, since the last time the
			 statistics were cleared."
	::= { v3Percent 11 }

	v3pMknods	OBJECT-TYPE
	SYNTAX		INTEGER (0..100)
	ACCESS		read-only
	STATUS		mandatory
	DESCRIPTION
			"The number of NFS Version 3 calls received
			 for the NFSPROC3_MKNOD (Create a Special
			 Device) procedure, as a percentage of the
			 total NFS calls received, since the last
			 time the statistics were cleared."
	::= { v3Percent 12 }

	v3pRemoves	OBJECT-TYPE
	SYNTAX		INTEGER (0..100)
	ACCESS		read-only
	STATUS		mandatory
	DESCRIPTION
			"The number of NFS Version 3 calls received
			 for the NFSPROC3_REMOVE (Remove a File)
			 procedure, as a percentage of the total NFS
			 calls received, since the last time the
			 statistics were cleared."
	::= { v3Percent 13 }

	v3pRmdirs	OBJECT-TYPE
	SYNTAX		INTEGER (0..100)
	ACCESS		read-only
	STATUS		mandatory
	DESCRIPTION
			"The number of NFS Version 3 calls received
			 for the NFSPROC3_RMDIR (Remove a Directory)
			 procedure, as a percentage of the total NFS
			 calls received, since the last time the
			 statistics were cleared."
	::= { v3Percent 14 }

	v3pRenames	OBJECT-TYPE
	SYNTAX		INTEGER (0..100)
	ACCESS		read-only
	STATUS		mandatory
	DESCRIPTION
			"The number of NFS Version 3 calls received
			 for the NFSPROC3_RENAME (Rename a File or
			 Directory) procedure, as a percentage of
			 the total NFS calls received, since the
			 last time the statistics were cleared."
	::= { v3Percent 15 }

	v3pLinks	OBJECT-TYPE
	SYNTAX		INTEGER (0..100)
	ACCESS		read-only
	STATUS		mandatory
	DESCRIPTION
			"The number of NFS Version 3 calls received
			 for the NFSPROC3_LINK (Create Link to an
			 Object) procedure, as a percentage of
			 the total NFS calls received, since the
			 last time the statistics were cleared."
	::= { v3Percent 16 }

	v3pReaddirs	OBJECT-TYPE
	SYNTAX		INTEGER (0..100)
	ACCESS		read-only
	STATUS		mandatory
	DESCRIPTION
			"The number of NFS Version 3 calls received
			 for the NFSPROC3_READDIR (Read From Directory)
			 procedure, as a percentage of the total NFS
			 calls received, since the last time the
			 statistics were cleared."
	::= { v3Percent 17 }

	v3pReaddirPluss	OBJECT-TYPE
	SYNTAX		INTEGER (0..100)
	ACCESS		read-only
	STATUS		mandatory
	DESCRIPTION
			"The number of NFS Version 3 calls received
			 for the NFSPROC3_READDIRPLUS (Extended Read
			 from Directory) procedure, as a percentage
			 of the total NFS calls received, since the
			 last time the statistics were cleared."
	::= { v3Percent 18 }

	v3pFsstats	OBJECT-TYPE
	SYNTAX		INTEGER (0..100)
	ACCESS		read-only
	STATUS		mandatory
	DESCRIPTION
			"The number of NFS Version 3 calls received
			 for the NFSPROC3_FSSTAT (Get Dynamic File
			 System Information) procedure, as a percentage
			 of the total NFS calls received, since the
			 last time the statistics were cleared."
	::= { v3Percent 19 }

	v3pFsinfos	OBJECT-TYPE
	SYNTAX		INTEGER (0..100)
	ACCESS		read-only
	STATUS		mandatory
	DESCRIPTION
			"The number of NFS Version 3 calls received
			 for the NFSPROC3_FSINFO (Get Static File System
			 Information) procedure, as a percentage of the
			 total NFS calls received, since the last time
			 the statistics were cleared."
	::= { v3Percent 20 }

	v3pPathconfs	OBJECT-TYPE
	SYNTAX		INTEGER (0..100)
	ACCESS		read-only
	STATUS		mandatory
	DESCRIPTION
			"The number of NFS Version 3 calls received
			 for the NFSPROC3_PATHCONF (Retrieve POSIX
			 Information) procedure, as a percentage of the
			 total NFS calls received, since the last time
			 the statistics were cleared."
	::= { v3Percent 21 }

	v3pCommits	OBJECT-TYPE
	SYNTAX		INTEGER (0..100)
	ACCESS		read-only
	STATUS		mandatory
	DESCRIPTION
			"The number of NFS Version 3 calls received
			 for the NFSPROC3_COMMIT (Commit Cached Data on
			 a Server to Stable Storage) procedure, as a
			 percentage of the total NFS calls received,
			 since the last time the statistics were cleared."
	::= { v3Percent 22 }



	-- the v3CachedCalls group

		-- this group contains statistics for the number of
		-- calls received for each NFS Version 3 procedure,
		-- that did not result in the filesystem blocking to
		-- read from disk, since the last time the statistics
		-- were cleared

	v3ccNulls	OBJECT-TYPE
	SYNTAX		Counter
	ACCESS		read-only
	STATUS		mandatory
	DESCRIPTION
			"The number of NFS Version 3 calls received
			 for the NFSPROC3_NULL (Do Nothing) procedure,
			 that did not result in the filesystem
			 blocking to read from disk, since the last
			 time the statistics were cleared."
	::= { v3CachedCalls 1 }

	v3ccGetattrs	OBJECT-TYPE
	SYNTAX		Counter
	ACCESS		read-only
	STATUS		mandatory
	DESCRIPTION
			"The number of NFS Version 3 calls received
			 for the NFSPROC3_GETATTR (Get File Attributes)
			 procedure, that did not result in the filesystem
			 blocking to read from disk, since the last
			 time the statistics were cleared."
	::= { v3CachedCalls 2 }

	v3ccSetattrs	OBJECT-TYPE
	SYNTAX		Counter
	ACCESS		read-only
	STATUS		mandatory
	DESCRIPTION
			"The number of NFS Version 3 calls received
			 for the NFSPROC3_SETATTR (Set File Attributes)
			 procedure, that did not result in the filesystem
			 blocking to read from disk, since the last
			 time the statistics were cleared."
	::= { v3CachedCalls 3 }

	v3ccLookups	OBJECT-TYPE
	SYNTAX		Counter
	ACCESS		read-only
	STATUS		mandatory
	DESCRIPTION
			"The number of NFS Version 3 calls received
			 for the NFSPROC3_LOOKUP (Lookup Filename)
			 procedure, that did not result in the filesystem
			 blocking to read from disk, since the last
			 time the statistics were cleared."
	::= { v3CachedCalls 4 }

	v3ccAccesss	OBJECT-TYPE
	SYNTAX		Counter
	ACCESS		read-only
	STATUS		mandatory
	DESCRIPTION
			"The number of NFS Version 3 calls received
			 for the NFSPROC3_ACCESS (Check Access Permission)
			 procedure, that did not result in the filesystem
			 blocking to read from disk, since the last
			 time the statistics were cleared."
	::= { v3CachedCalls 5 }

	v3ccReadlinks	OBJECT-TYPE
	SYNTAX		Counter
	ACCESS		read-only
	STATUS		mandatory
	DESCRIPTION
			"The number of NFS Version 3 calls received
			 for the NFSPROC3_READLINK (Read from Symbolic
			 Link) procedure, that did not result in the
			 filesystem blocking to read from disk, since
			 the last time the statistics were cleared."
	::= { v3CachedCalls 6 }

	v3ccReads	OBJECT-TYPE
	SYNTAX		Counter
	ACCESS		read-only
	STATUS		mandatory
	DESCRIPTION
			"The number of NFS Version 3 calls received
			 for the NFSPROC3_READ (Read From File)
			 procedure, that did not result in the filesystem
			 blocking to read from disk, since the last
			 time the statistics were cleared."
	::= { v3CachedCalls 7 }

	v3ccWrites	OBJECT-TYPE
	SYNTAX		Counter
	ACCESS		read-only
	STATUS		mandatory
	DESCRIPTION
			"The number of NFS Version 3 calls received
			 for the NFSPROC3_WRITE (Write to File)
			 procedure, that did not result in the filesystem
			 blocking to read from disk, since the last
			 time the statistics were cleared."
	::= { v3CachedCalls 8 }

	v3ccCreates	OBJECT-TYPE
	SYNTAX		Counter
	ACCESS		read-only
	STATUS		mandatory
	DESCRIPTION
			"The number of NFS Version 3 calls received
			 for the NFSPROC3_CREATE (Create a File)
			 procedure, that did not result in the filesystem
			 blocking to read from disk, since the last
			 time the statistics were cleared."
	::= { v3CachedCalls 9 }

	v3ccMkdirs	OBJECT-TYPE
	SYNTAX		Counter
	ACCESS		read-only
	STATUS		mandatory
	DESCRIPTION
			"The number of NFS Version 3 calls received
			 for the NFSPROC3_MKDIR (Create a Directory)
			 procedure, that did not result in the filesystem
			 blocking to read from disk, since the last
			 time the statistics were cleared."
	::= { v3CachedCalls 10 }

	v3ccSymlinks	OBJECT-TYPE
	SYNTAX		Counter
	ACCESS		read-only
	STATUS		mandatory
	DESCRIPTION
			"The number of NFS Version 3 calls received
			 for the NFSPROC3_SYMLINK (Create a Symbolic
			 Link) procedure, that did not result in the
			 filesystem blocking to read from disk, since
			 the last time the statistics were cleared."
	::= { v3CachedCalls 11 }

	v3ccMknods	OBJECT-TYPE
	SYNTAX		Counter
	ACCESS		read-only
	STATUS		mandatory
	DESCRIPTION
			"The number of NFS Version 3 calls received
			 for the NFSPROC3_MKNOD (Create a Special
			 Device) procedure, that did not result in the
			 filesystem blocking to read from disk, since
			 the last time the statistics were cleared."
	::= { v3CachedCalls 12 }

	v3ccRemoves	OBJECT-TYPE
	SYNTAX		Counter
	ACCESS		read-only
	STATUS		mandatory
	DESCRIPTION
			"The number of NFS Version 3 calls received
			 for the NFSPROC3_REMOVE (Remove a File)
			 procedure, that did not result in the
			 filesystem blocking to read from disk, since
			 the last time the statistics were cleared."
	::= { v3CachedCalls 13 }

	v3ccRmdirs	OBJECT-TYPE
	SYNTAX		Counter
	ACCESS		read-only
	STATUS		mandatory
	DESCRIPTION
			"The number of NFS Version 3 calls received
			 for the NFSPROC3_RMDIR (Remove a Directory)
			 procedure, that did not result in the
			 filesystem blocking to read from disk, since
			 the last time the statistics were cleared."
	::= { v3CachedCalls 14 }

	v3ccRenames	OBJECT-TYPE
	SYNTAX		Counter
	ACCESS		read-only
	STATUS		mandatory
	DESCRIPTION
			"The number of NFS Version 3 calls received
			 for the NFSPROC3_RENAME (Rename a File or
			 Directory) procedure, that did not result in
			 the filesystem blocking to read from disk, since
			 the last time the statistics were cleared."
	::= { v3CachedCalls 15 }

	v3ccLinks	OBJECT-TYPE
	SYNTAX		Counter
	ACCESS		read-only
	STATUS		mandatory
	DESCRIPTION
			"The number of NFS Version 3 calls received
			 for the NFSPROC3_LINK (Create Link to an
			 Object) procedure, that did not result in
			 the filesystem blocking to read from disk, since
			 the last time the statistics were cleared."
	::= { v3CachedCalls 16 }

	v3ccReaddirs	OBJECT-TYPE
	SYNTAX		Counter
	ACCESS		read-only
	STATUS		mandatory
	DESCRIPTION
			"The number of NFS Version 3 calls received
			 for the NFSPROC3_READDIR (Read From
			 Directory) procedure, that did not result in
			 the filesystem blocking to read from disk, since
			 the last time the statistics were cleared."
	::= { v3CachedCalls 17 }

	v3ccReaddirPluss OBJECT-TYPE
	SYNTAX		 Counter
	ACCESS		 read-only
	STATUS		 mandatory
	DESCRIPTION
			"The number of NFS Version 3 calls received
			 for the NFSPROC3_READDIRPLUS (Extended Read
			 from Directory) procedure, that did not result in
			 the filesystem blocking to read from disk, since
			 the last time the statistics were cleared."
	::= { v3CachedCalls 18 }

	v3ccFsstats	OBJECT-TYPE
	SYNTAX		Counter
	ACCESS		read-only
	STATUS		mandatory
	DESCRIPTION
			"The number of NFS Version 3 calls received
			 for the NFSPROC3_FSSTAT (Get Dynamic File
			 System Information) procedure, that did not
			 result in the filesystem blocking to read
			 from disk, since the last time the statistics
			 were cleared."
	::= { v3CachedCalls 19 }

	v3ccFsinfos	OBJECT-TYPE
	SYNTAX		Counter
	ACCESS		read-only
	STATUS		mandatory
	DESCRIPTION
			"The number of NFS Version 3 calls received
			 for the NFSPROC3_FSINFO (Get Static File
			 System Information) procedure, that did not
			 result in the filesystem blocking to read
			 from disk, since the last time the statistics
			 were cleared."
	::= { v3CachedCalls 20 }

	v3ccPathconfs	OBJECT-TYPE
	SYNTAX		Counter
	ACCESS		read-only
	STATUS		mandatory
	DESCRIPTION
			"The number of NFS Version 3 calls received
			 for the NFSPROC3_PATHCONF (Retrieve POSIX
			 Information) procedure, that did not result
			 in the filesystem blocking to read from disk,
			 since the last time the statistics were cleared."
	::= { v3CachedCalls 21 }

	v3ccCommits	OBJECT-TYPE
	SYNTAX		Counter
	ACCESS		read-only
	STATUS		mandatory
	DESCRIPTION
			"The number of NFS Version 3 calls received
			 for the NFSPROC3_COMMIT (Commit Cached Data on
			 a Server to Stable Storage) procedure, that did
			 not result in the filesystem blocking to read
			 from disk, since the last time the statistics
			 were cleared."
	::= { v3CachedCalls 22 }



	-- the v3CachedPerCent group

		-- this group contains statistics for the number of
		-- calls received for each NFS Version 3 procedure,
		-- that did not result in the filesystem blocking to
		-- read from disk, as a percentage of the total
		-- number of calls received for that procedure,
		-- since the last time the statistics were cleared

	v3cpNulls	OBJECT-TYPE
	SYNTAX		INTEGER (0..100)
	ACCESS		read-only
	STATUS		mandatory
	DESCRIPTION
			"The number of NFS Version 3 calls received
			 for the NFSPROC3_NULL (Do Nothing) procedure,
			 that did not result in the filesystem
			 blocking to read from disk, as a percentage
			 of the total number of calls received for
			 this procedure, since the last time the
			 statistics were cleared."
	::= { v3CachedPerCent 1 }

	v3cpGetattrs	OBJECT-TYPE
	SYNTAX		INTEGER (0..100)
	ACCESS		read-only
	STATUS		mandatory
	DESCRIPTION
			"The number of NFS Version 3 calls received
			 for the NFSPROC3_GETATTR (Get File Attributes)
			 procedure, that did not result in the filesystem
			 blocking to read from disk, as a percentage
			 of the total number of calls received for
			 this procedure, since the last time the
			 statistics were cleared."
	::= { v3CachedPerCent 2 }

	v3cpSetattrs	OBJECT-TYPE
	SYNTAX		INTEGER (0..100)
	ACCESS		read-only
	STATUS		mandatory
	DESCRIPTION
			"The number of NFS Version 3 calls received
			 for the NFSPROC3_SETATTR (Set File Attributes)
			 procedure, that did not result in the filesystem
			 blocking to read from disk, as a percentage
			 of the total number of calls received for
			 this procedure, since the last time the
			 statistics were cleared."
	::= { v3CachedPerCent 3 }

	v3cpLookups	OBJECT-TYPE
	SYNTAX		INTEGER (0..100)
	ACCESS		read-only
	STATUS		mandatory
	DESCRIPTION
			"The number of NFS Version 3 calls received
			 for the NFSPROC3_LOOKUP (Lookup Filename)
			 procedure, that did not result in the filesystem
			 blocking to read from disk, as a percentage
			 of the total number of calls received for
			 this procedure, since the last time the
			 statistics were cleared."
	::= { v3CachedPerCent 4 }

	v3cpAccesss	OBJECT-TYPE
	SYNTAX		INTEGER (0..100)
	ACCESS		read-only
	STATUS		mandatory
	DESCRIPTION
			"The number of NFS Version 3 calls received
			 for the NFSPROC3_ACCESS (Check Access Permission)
			 procedure, that did not result in the filesystem
			 blocking to read from disk, as a percentage
			 of the total number of calls received for
			 this procedure, since the last time the
			 statistics were cleared."
	::= { v3CachedPerCent 5 }

	v3cpReadlinks	OBJECT-TYPE
	SYNTAX		INTEGER (0..100)
	ACCESS		read-only
	STATUS		mandatory
	DESCRIPTION
			"The number of NFS Version 3 calls received
			 for the NFSPROC3_READLINK (Read from Symbolic
			 Link) procedure, that did not result in the
			 filesystem blocking to read from disk, as a
			 percentage of the total number of calls
			 received for this procedure, since the last
			 time the statistics were cleared."
	::= { v3CachedPerCent 6 }

	v3cpReads	OBJECT-TYPE
	SYNTAX		INTEGER (0..100)
	ACCESS		read-only
	STATUS		mandatory
	DESCRIPTION
			"The number of NFS Version 3 calls received
			 for the NFSPROC3_READ (Read From File)
			 procedure, that did not result in the
			 filesystem blocking to read from disk, as a
			 percentage of the total number of calls
			 received for this procedure, since the last
			 time the statistics were cleared."
	::= { v3CachedPerCent 7 }

	v3cpWrites	OBJECT-TYPE
	SYNTAX		INTEGER (0..100)
	ACCESS		read-only
	STATUS		mandatory
	DESCRIPTION
			"The number of NFS Version 3 calls received
			 for the NFSPROC3_WRITE (Write to File)
			 procedure, that did not result in the
			 filesystem blocking to read from disk, as a
			 percentage of the total number of calls
			 received for this procedure, since the last
			 time the statistics were cleared."
	::= { v3CachedPerCent 8 }

	v3cpCreates	OBJECT-TYPE
	SYNTAX		INTEGER (0..100)
	ACCESS		read-only
	STATUS		mandatory
	DESCRIPTION
			"The number of NFS Version 3 calls received
			 for the NFSPROC3_CREATE (Create a File)
			 procedure, that did not result in the
			 filesystem blocking to read from disk, as a
			 percentage of the total number of calls
			 received for this procedure, since the last
			 time the statistics were cleared."
	::= { v3CachedPerCent 9 }

	v3cpMkdirs	OBJECT-TYPE
	SYNTAX		INTEGER (0..100)
	ACCESS		read-only
	STATUS		mandatory
	DESCRIPTION
			"The number of NFS Version 3 calls received
			 for the NFSPROC3_MKDIR (Create a Directory)
			 procedure, that did not result in the
			 filesystem blocking to read from disk, as a
			 percentage of the total number of calls
			 received for this procedure, since the last
			 time the statistics were cleared."
	::= { v3CachedPerCent 10 }

	v3cpSymlinks	OBJECT-TYPE
	SYNTAX		INTEGER (0..100)
	ACCESS		read-only
	STATUS		mandatory
	DESCRIPTION
			"The number of NFS Version 3 calls received
			 for the NFSPROC3_SYMLINK (Create a Symbolic
			 Link) procedure, that did not result in the
			 filesystem blocking to read from disk, as a
			 percentage of the total number of calls
			 received for this procedure, since the last
			 time the statistics were cleared."
	::= { v3CachedPerCent 11 }

	v3cpMknods	OBJECT-TYPE
	SYNTAX		INTEGER (0..100)
	ACCESS		read-only
	STATUS		mandatory
	DESCRIPTION
			"The number of NFS Version 3 calls received
			 for the NFSPROC3_MKNOD (Create a Special
			 Device) procedure, that did not result in the
			 filesystem blocking to read from disk, as a
			 percentage of the total number of calls
			 received for this procedure, since the last
			 time the statistics were cleared."
	::= { v3CachedPerCent 12 }

	v3cpRemoves	OBJECT-TYPE
	SYNTAX		INTEGER (0..100)
	ACCESS		read-only
	STATUS		mandatory
	DESCRIPTION
			"The number of NFS Version 3 calls received
			 for the NFSPROC3_REMOVE (Remove a File)
			 procedure, that did not result in the
			 filesystem blocking to read from disk, as a
			 percentage of the total number of calls
			 received for this procedure, since the last
			 time the statistics were cleared."
	::= { v3CachedPerCent 13 }

	v3cpRmdirs	OBJECT-TYPE
	SYNTAX		INTEGER (0..100)
	ACCESS		read-only
	STATUS		mandatory
	DESCRIPTION
			"The number of NFS Version 3 calls received
			 for the NFSPROC3_RMDIR (Remove a Directory)
			 procedure, that did not result in the
			 filesystem blocking to read from disk, as a
			 percentage of the total number of calls
			 received for this procedure, since the last
			 time the statistics were cleared."
	::= { v3CachedPerCent 14 }

	v3cpRenames	OBJECT-TYPE
	SYNTAX		INTEGER (0..100)
	ACCESS		read-only
	STATUS		mandatory
	DESCRIPTION
			"The number of NFS Version 3 calls received
			 for the NFSPROC3_RENAME (Rename a File or
			 Directory) procedure, that did not result in
			 the filesystem blocking to read from disk,
			 as a percentage of the total number of calls
			 received for this procedure, since the last
			 time the statistics were cleared."
	::= { v3CachedPerCent 15 }

	v3cpLinks	OBJECT-TYPE
	SYNTAX		INTEGER (0..100)
	ACCESS		read-only
	STATUS		mandatory
	DESCRIPTION
			"The number of NFS Version 3 calls received
			 for the NFSPROC3_LINK (Create Link to an
			 Object) procedure, that did not result in
			 the filesystem blocking to read from disk,
			 as a percentage of the total number of calls
			 received for this procedure, since the last
			 time the statistics were cleared."
	::= { v3CachedPerCent 16 }

	v3cpReaddirs	OBJECT-TYPE
	SYNTAX		INTEGER (0..100)
	ACCESS		read-only
	STATUS		mandatory
	DESCRIPTION
			"The number of NFS Version 3 calls received
			 for the NFSPROC3_READDIR (Read From Directory)
			 procedure, that did not result in the
			 filesystem blocking to read from disk, as a
			 percentage of the total number of calls
			 received for this procedure, since the last
			 time the statistics were cleared."
	::= { v3CachedPerCent 17 }

	v3cpReaddirPluss OBJECT-TYPE
	SYNTAX		 INTEGER (0..100)
	ACCESS		 read-only
	STATUS		 mandatory
	DESCRIPTION
			"The number of NFS Version 3 calls received
			 for the NFSPROC3_READDIRPLUS (Extended Read
			 from Directory) procedure, that did not result
			 in the filesystem blocking to read from disk,
			 as a percentage of the total number of calls
			 received for this procedure, since the last
			 time the statistics were cleared."
	::= { v3CachedPerCent 18 }

	v3cpFsstats	OBJECT-TYPE
	SYNTAX		INTEGER (0..100)
	ACCESS		read-only
	STATUS		mandatory
	DESCRIPTION
			"The number of NFS Version 3 calls received
			 for the NFSPROC3_FSSTAT (Get Dynamic File
			 System Information) procedure, that did not
			 result in the filesystem blocking to read from
			 disk, as a percentage of the total number of
			 calls received for this procedure, since the
			 last time the statistics were cleared."
	::= { v3CachedPerCent 19 }

	v3cpFsinfos	OBJECT-TYPE
	SYNTAX		INTEGER (0..100)
	ACCESS		read-only
	STATUS		mandatory
	DESCRIPTION
			"The number of NFS Version 3 calls received
			 for the NFSPROC3_FSINFO (Get Static File System
			 Information) procedure, that did not result
			 in the filesystem blocking to read from disk,
			 as a percentage of the total number of calls
			 received for this procedure, since the last
			 time the statistics were cleared."
	::= { v3CachedPerCent 20 }

	v3cpPathconfs	OBJECT-TYPE
	SYNTAX		INTEGER (0..100)
	ACCESS		read-only
	STATUS		mandatory
	DESCRIPTION
			"The number of NFS Version 3 calls received
			 for the NFSPROC3_PATHCONF (Retrieve POSIX
			 Information) procedure, that did not result
			 in the filesystem blocking to read from disk,
			 as a percentage of the total number of calls
			 received for this procedure, since the last
			 time the statistics were cleared."
	::= { v3CachedPerCent 21 }

	v3cpCommits	OBJECT-TYPE
	SYNTAX		INTEGER (0..100)
	ACCESS		read-only
	STATUS		mandatory
	DESCRIPTION
			"The number of NFS Version 3 calls received
			 for the NFSPROC3_COMMIT (Commit Cached Data on
			 a Server to Stable Storage) procedure, that
			 did not result in the filesystem blocking to
			 read from disk, as a percentage of the total
			 number of calls received for this procedure,
			 since the last time the statistics were cleared."
	::= { v3CachedPerCent 22 }



	-- the replyCache group

		-- this group contains statistics related to the 
		-- Reply Cache processing, since the last time the
		-- statistics were cleared

	rcInProgressHits OBJECT-TYPE
	SYNTAX		 Counter
	ACCESS		 read-only
	STATUS		 mandatory
	DESCRIPTION
			"The number of NFS requests that were dropped,
			 for calls already in progress, since the last
			 time the statistics were cleared."
	::= { replyCache 1 }

	rcDelayHits	OBJECT-TYPE
	SYNTAX		Counter
	ACCESS		read-only
	STATUS		deprecated
	DESCRIPTION
			"The number of NFS requests that were dropped,
			 for replies already generated within a short
			 interval, since the last time the statistics
			 were cleared. These stats are deprecated.
			 A value of zero will always be returned
			 for these stats." 
	::= { replyCache 2 }

	rcMisses	OBJECT-TYPE
	SYNTAX		Counter
	ACCESS		read-only
	STATUS		mandatory
	DESCRIPTION
			"The number of NFS requests received for which
			 there were no corresponding entries already in
			 the Reply Cache, since the last time the
			 statistics were cleared."
	::= { replyCache 3 }

	rcNonIdemDoneHits OBJECT-TYPE
	SYNTAX		  Counter
	ACCESS		  read-only
	STATUS		  mandatory
	DESCRIPTION
			"The number of NFS requests received that
			 resulted in replies being replayed from
			 the Reply Cache, since the last time the
			 statistics were cleared."
	::= { replyCache 4 }

	rcNonIdemNotDoneHits OBJECT-TYPE
	SYNTAX		     Counter
	ACCESS		     read-only
	STATUS		     mandatory
	DESCRIPTION
			"The number of NFS requests received for calls
			 that resulted in this request being processed
			 as a new request even when a corresponding
			 entry existed in the Reply Cache, since the
			 last time the statistics were cleared."
	::= { replyCache 5 }

	rcTcpInProgressHits OBJECT-TYPE
	SYNTAX		 Counter
	ACCESS		 read-only
	STATUS		 mandatory
	DESCRIPTION
			"The number of NFS requests that were dropped
			 for the TCP protocol, for calls already in
			 progress, since the last time the statistics
			 were cleared."
	::= { replyCache 6 }

	rcTcpDelayHits	OBJECT-TYPE
	SYNTAX		Counter
	ACCESS		read-only
	STATUS		deprecated
	DESCRIPTION
			"The number of NFS requests that were dropped
			 for the TCP protocol, for replies already
			 generated within a short interval, since the
			 last time the statistics were cleared. These 
			 stats are deprecated. A value of zero will 
			 always be returned for these stats."
	::= { replyCache 7 }

	rcTcpMisses	OBJECT-TYPE
	SYNTAX		Counter
	ACCESS		read-only
	STATUS		mandatory
	DESCRIPTION
			"The number of NFS requests received for the
			 TCP protocol for which there were no
			 corresponding entries already in the Reply
			 Cache, since the last time the statistics
			 were cleared."
	::= { replyCache 8 }

	rcTcpNonIdemDoneHits OBJECT-TYPE
	SYNTAX		  Counter
	ACCESS		  read-only
	STATUS		  mandatory
	DESCRIPTION
			"The number of NFS requests received for the
			 TCP protocol that resulted in replies being
			 replayed from the Reply Cache, since the last
			 time the statistics were cleared."
	::= { replyCache 9 }

	rcTcpNonIdemNotDoneHits OBJECT-TYPE
	SYNTAX		     Counter
	ACCESS		     read-only
	STATUS		     mandatory
	DESCRIPTION
			"The number of NFS requests received for the
			 TCP protocol for calls that resulted in this
			 request being processed as a new request even
			 when a corresponding entry existed in the Reply
			 Cache, since the last time the statistics were
			 cleared."
	::= { replyCache 10 }

	rcUdpInProgressHits OBJECT-TYPE
	SYNTAX		 Counter
	ACCESS		 read-only
	STATUS		 mandatory
	DESCRIPTION
			"The number of NFS requests that were dropped
			 for the UDP protocol, for calls already in
			 progress, since the last time the statistics
			 were cleared."
	::= { replyCache 11 }

	rcUdpDelayHits	OBJECT-TYPE
	SYNTAX		Counter
	ACCESS		read-only
	STATUS		deprecated
	DESCRIPTION
			"The number of NFS requests that were dropped
			 for the UDP protocol, for replies already
			 generated within a short interval, since the
			 last time the statistics were cleared. These 
			 stats are deprecated. A value of zero will 
			 always be returned for these stats."
	::= { replyCache 12 }

	rcUdpMisses	OBJECT-TYPE
	SYNTAX		Counter
	ACCESS		read-only
	STATUS		mandatory
	DESCRIPTION
			"The number of NFS requests received for the
			 UDP protocol for which there were no
			 corresponding entries already in the Reply
			 Cache, since the last time the statistics
			 were cleared."
	::= { replyCache 13 }

	rcUdpNonIdemDoneHits OBJECT-TYPE
	SYNTAX		  Counter
	ACCESS		  read-only
	STATUS		  mandatory
	DESCRIPTION
			"The number of NFS requests received for the
			 UDP protocol that resulted in replies being
			 replayed from the Reply Cache, since the last
			 time the statistics were cleared."
	::= { replyCache 14 }

	rcUdpNonIdemNotDoneHits OBJECT-TYPE
	SYNTAX		     Counter
	ACCESS		     read-only
	STATUS		     mandatory
	DESCRIPTION
			"The number of NFS requests received for the
			 UDP protocol for calls that resulted in this
			 request being processed as a new request even
			 when a corresponding entry existed in the Reply
			 Cache, since the last time the statistics were
			 cleared."
	::= { replyCache 15 }

	-- the nfsrwStats group

		-- this group contains statistics for the sizes of
                -- NFS version 2 and 3 read and write calls made
		-- since the last time the stats were zeroed.

	v2ReadStats            OBJECT IDENTIFIER ::= { nfsrwStats 1 }

	v2WriteStats           OBJECT IDENTIFIER ::= { nfsrwStats 2 }

        v3ReadStats            OBJECT IDENTIFIER ::= { nfsrwStats 3 }

        v3WriteStats           OBJECT IDENTIFIER ::= { nfsrwStats 4 }

	
	-- v2ReadStats group
		
		-- this group contains statistics for the sizes of
		-- NFS version 2 read calls since they were last
		-- zeroed.

	v2Read512Calls OBJECT-TYPE
        SYNTAX          Counter
        ACCESS          read-only
        STATUS          mandatory
        DESCRIPTION
                        "The number of NFS Version 2 read calls
			received by the server since last zeroing
                        with request sizes between 0-511 bytes."
        ::= { v2ReadStats 1 }

        v2Read1KCalls  OBJECT-TYPE
        SYNTAX          Counter
        ACCESS          read-only
        STATUS          mandatory
        DESCRIPTION
                        "The number of NFS Version 2 read calls
			received by the server since last zeroing
                        with request sizes between 512-1023 bytes."
        ::= { v2ReadStats 2 }

        v2Read2KCalls  OBJECT-TYPE
        SYNTAX          Counter
        ACCESS          read-only
        STATUS          mandatory
        DESCRIPTION
                        "The number of NFS Version 2 read calls
			received by the server since last zeroing
                        with request sizes between 1K-2047 bytes."
	::= { v2ReadStats 3 }

        v2Read4KCalls  OBJECT-TYPE
        SYNTAX          Counter
        ACCESS          read-only
        STATUS          mandatory
        DESCRIPTION
                        "The number of NFS Version 2 read calls
			received by the server since last zeroing
                        with request sizes between 2K-4095 bytes."
        ::= { v2ReadStats 4 }

        v2Read8KCalls  OBJECT-TYPE
        SYNTAX          Counter
        ACCESS          read-only
        STATUS          mandatory
        DESCRIPTION
                        "The number of NFS Version 2 read calls
			received by the server since last zeroing
                        with request sizes between 4K-8191 bytes."
        ::= { v2ReadStats 5 }

        v2Read16KCalls OBJECT-TYPE
        SYNTAX          Counter
        ACCESS          read-only
        STATUS          mandatory
        DESCRIPTION
                        "The number of NFS Version 2 read calls
			received by the server since last zeroing
                        with request sizes between 8K-16383 bytes."
        ::= { v2ReadStats 6 }

        v2Read32KCalls OBJECT-TYPE
        SYNTAX          Counter
        ACCESS          read-only
        STATUS          mandatory
        DESCRIPTION
                        "The number of NFS Version 2 read calls
			received by the server since last zeroing
                        with request sizes between 16K-32767 bytes."
        ::= { v2ReadStats 7 }

	v2Read64KCalls OBJECT-TYPE
        SYNTAX          Counter
        ACCESS          read-only
        STATUS          mandatory
        DESCRIPTION
                        "The number of NFS Version 2 read calls
			received by the server since last zeroing
                        with request sizes between 32K-65535 bytes."
        ::= { v2ReadStats 8 }

        v2Read128KCalls        OBJECT-TYPE
        SYNTAX          Counter
        ACCESS          read-only
        STATUS          mandatory
        DESCRIPTION
                        "The number of NFS Version 2 read calls
			received by the server since last zeroing
                        with request sizes between 64K-131071 bytes."
        ::= { v2ReadStats 9 }


        -- the v2WriteStats group

                -- this group contains statistics for the sizes of
                -- NFS version 2 write calls since they were last
		-- zeroed.

        v2Write512Calls        OBJECT-TYPE
        SYNTAX          Counter
        ACCESS          read-only
        STATUS          mandatory
        DESCRIPTION
                        "The number of NFS Version 2 write calls
			received by the server since last zeroing
                        with request sizes between 0-511 bytes."
        ::= { v2WriteStats 1 }

	v2Write1KCalls OBJECT-TYPE
        SYNTAX          Counter
        ACCESS          read-only
        STATUS          mandatory
        DESCRIPTION
                        "The number of NFS Version 2 write calls
			received by the server since last zeroing
                        with request sizes between 512-1023 bytes."
        ::= { v2WriteStats 2 }

        v2Write2KCalls OBJECT-TYPE
        SYNTAX          Counter
        ACCESS          read-only
        STATUS          mandatory
        DESCRIPTION
                        "The number of NFS Version 2 write calls
			received by the server since last zeroing
                        with request sizes between 1K-2047 bytes."
        ::= { v2WriteStats 3 }

        v2Write4KCalls OBJECT-TYPE
        SYNTAX          Counter
        ACCESS          read-only
        STATUS          mandatory
        DESCRIPTION
                        "The number of NFS Version 2 write calls
			received by the server since last zeroing
                        with request sizes between 2K-4095 bytes."
        ::= { v2WriteStats 4 }

        v2Write8KCalls OBJECT-TYPE
        SYNTAX          Counter
        ACCESS          read-only
        STATUS          mandatory
        DESCRIPTION
                        "The number of NFS Version 2 write calls
			received by the server since last zeroing
                        with request sizes between 4K-8191 bytes."
        ::= { v2WriteStats 5 }

	v2Write16KCalls        OBJECT-TYPE
        SYNTAX          Counter
        ACCESS          read-only
        STATUS          mandatory
        DESCRIPTION
                        "The number of NFS Version 2 write calls
			received by the server since last zeroing
                        with request sizes between 8K-16383 bytes."
        ::= { v2WriteStats 6 }

        v2Write32KCalls        OBJECT-TYPE
        SYNTAX          Counter
        ACCESS          read-only
        STATUS          mandatory
        DESCRIPTION
                        "The number of NFS Version 2 write calls
			received by the server since last zeroing
                        with request sizes between 16K-32767 bytes."
        ::= { v2WriteStats 7 }

        v2Write64KCalls        OBJECT-TYPE
        SYNTAX          Counter
        ACCESS          read-only
        STATUS          mandatory
        DESCRIPTION
                        "The number of NFS Version 2 write calls
			received by the server since last zeroing
                        with request sizes between 32K-65535 bytes."
        ::= { v2WriteStats 8 }

        v2Write128KCalls       OBJECT-TYPE
        SYNTAX          Counter
        ACCESS          read-only
        STATUS          mandatory
        DESCRIPTION
                        "The number of NFS Version 2 write calls
			received by the server since last zeroing
                        with request sizes between 64K-131071 bytes."
        ::= { v2WriteStats 9 }


	-- the v3ReadStats group

                -- this group contains statistics for the sizes of
                -- NFS version 3 read calls since they were last
		-- zeroed.

        v3Read512Calls OBJECT-TYPE
        SYNTAX          Counter
        ACCESS          read-only
        STATUS          mandatory
        DESCRIPTION
                        "The number of NFS Version 3 read calls
			received by the server since last boot
                        with request sizes between 0-511 bytes."
        ::= { v3ReadStats 1 }

        v3Read1KCalls  OBJECT-TYPE
        SYNTAX          Counter
        ACCESS          read-only
        STATUS          mandatory
        DESCRIPTION
                        "The number of NFS Version 3 read calls
			received by the server since last zeroing
                        with request sizes between 512-1023 bytes."
        ::= { v3ReadStats 2 }

        v3Read2KCalls  OBJECT-TYPE
        SYNTAX          Counter
        ACCESS          read-only
        STATUS          mandatory
        DESCRIPTION
                        "The number of NFS Version 3 read calls
			received by the server since last zeroing
                        with request sizes between 1K-2047 bytes."
        ::= { v3ReadStats 3 }

	v3Read4KCalls  OBJECT-TYPE
        SYNTAX          Counter
        ACCESS          read-only
        STATUS          mandatory
        DESCRIPTION
                        "The number of NFS Version 3 read calls
			received by the server since last zeroing
                        with request sizes between 2K-4095 bytes."
        ::= { v3ReadStats 4 }

        v3Read8KCalls  OBJECT-TYPE
        SYNTAX          Counter
        ACCESS          read-only
        STATUS          mandatory
        DESCRIPTION
                        "The number of NFS Version 3 read calls
			received by the server since last zeroing
                        with request sizes between 4K-8191 bytes."
        ::= { v3ReadStats 5 }

        v3Read16KCalls         OBJECT-TYPE
        SYNTAX          Counter
        ACCESS          read-only
        STATUS          mandatory
        DESCRIPTION
                        "The number of NFS Version 3 read calls
			received by the server since last zeroing
                        with request sizes between 8K-16383 bytes."
        ::= { v3ReadStats 6 }

        v3Read32KCalls OBJECT-TYPE
        SYNTAX          Counter
        ACCESS          read-only
        STATUS          mandatory
        DESCRIPTION
                        "The number of NFS Version 3 read calls
			received by the server since last zeroing
                        with request sizes between 16K-32767 bytes."
        ::= { v3ReadStats 7 }

	v3Read64KCalls OBJECT-TYPE
        SYNTAX          Counter
        ACCESS          read-only
        STATUS          mandatory
        DESCRIPTION
                        "The number of NFS Version 3 read calls
			received by the server since last zeroing
                        with request sizes between 32K-65535 bytes."
        ::= { v3ReadStats 8 }

        v3Read128KCalls        OBJECT-TYPE
        SYNTAX          Counter
        ACCESS          read-only
        STATUS          mandatory
        DESCRIPTION
                        "The number of NFS Version 3 read calls
			received by the server since last zeroing
                        with request sizes between 64K-131071 bytes."
        ::= { v3ReadStats 9 }


        -- the v3WriteStats group

                -- this group contains statistics for the sizes of
                -- NFS version 3 write calls since they were last
		-- zeroed.

        v3Write512Calls        OBJECT-TYPE
        SYNTAX          Counter
        ACCESS          read-only
        STATUS          mandatory
        DESCRIPTION
                        "The number of NFS Version 3 write calls
			received by the server since last zeroing
                        with request sizes between 0-511 bytes."
        ::= { v3WriteStats 1 }

	v3Write1KCalls OBJECT-TYPE
        SYNTAX          Counter
        ACCESS          read-only
        STATUS          mandatory
        DESCRIPTION
                        "The number of NFS Version 3 write calls
			received by the server since last zeroing
                        with request sizes between 512-1023 bytes."
        ::= { v3WriteStats 2 }

        v3Write2KCalls OBJECT-TYPE
        SYNTAX          Counter
        ACCESS          read-only
        STATUS          mandatory
        DESCRIPTION
                        "The number of NFS Version 3 write calls
			received by the server since last zeroing
                        with request sizes between 1K-2047 bytes."
        ::= { v3WriteStats 3 }

        v3Write4KCalls OBJECT-TYPE
        SYNTAX          Counter
        ACCESS          read-only
        STATUS          mandatory
        DESCRIPTION
                        "The number of NFS Version 3 write calls
			received by the server since last zeroing
                        with request sizes between 2K-4095 bytes."
        ::= { v3WriteStats 4 }

        v3Write8KCalls OBJECT-TYPE
        SYNTAX          Counter
        ACCESS          read-only
        STATUS          mandatory
        DESCRIPTION
                        "The number of NFS Version 3 write calls
			received by the server since last zeroing
                        with request sizes between 4K-8191 bytes."
        ::= { v3WriteStats 5 }

	v3Write16KCalls        OBJECT-TYPE
        SYNTAX          Counter
        ACCESS          read-only
        STATUS          mandatory
        DESCRIPTION
                        "The number of NFS Version 3 write calls
			received by the server since last zeroing
                        with request sizes between 8K-16383 bytes."
        ::= { v3WriteStats 6 }

        v3Write32KCalls        OBJECT-TYPE
        SYNTAX          Counter
        ACCESS          read-only
        STATUS          mandatory
        DESCRIPTION
                        "The number of NFS Version 3 write calls
			received by the server since last zeroing
                        with request sizes between 16K-32767 bytes."
        ::= { v3WriteStats 7 }

        v3Write64KCalls        OBJECT-TYPE
        SYNTAX          Counter
        ACCESS          read-only
        STATUS          mandatory
        DESCRIPTION
                        "The number of NFS Version 3 write calls
			received by the server since last zeroing
                        with request sizes between 32K-65535 bytes."
        ::= { v3WriteStats 8 }

        v3Write128KCalls       OBJECT-TYPE
        SYNTAX          Counter
        ACCESS          read-only
        STATUS          mandatory
        DESCRIPTION
                        "The number of NFS Version 3 write calls
			received by the server since last zeroing
                        with request sizes between 64K-131071 bytes."
        ::= { v3WriteStats 9 }


	-- the per-client nfs statistics table
 
	pclTable	OBJECT-TYPE
	SYNTAX		SEQUENCE OF PclEntry
	ACCESS		not-accessible
	STATUS		mandatory
	DESCRIPTION
			"Provide a report of per-client NFS statistics
			 since the last time the statistics were cleared."
	::= { nfsPerClient 1 }
 
	pclEntry	OBJECT-TYPE
	SYNTAX		PclEntry
	ACCESS		not-accessible
	STATUS		mandatory
	DESCRIPTION
			"Provide a report of NFS statistics for the
			 referenced NFS client since the last time the
			 statistics were cleared."
	INDEX	{ pclIpAddr }
	::= { pclTable 1 }

	PclEntry ::=
	    SEQUENCE {
		pclIpAddr
		    IpAddress,
		pclRpcCalls
		    Counter,
		pclRpcBadCalls
		    Counter,
		pclRpcNullRecvs
		    Counter,
		pclRpcBadLens
		    Counter,
		pclRpcServXDRCalls
		    Counter,
		pclNfsCalls
		    Counter,
		pclNfsServBadCalls
		    Counter,
		pclNfsV2Nulls
		    Counter,
		pclNfsV2Getattrs
		    Counter,
		pclNfsV2Setattrs
		    Counter,
		pclNfsV2Roots
		    Counter,
		pclNfsV2Lookups
		    Counter,
		pclNfsV2Readlinks
		    Counter,
		pclNfsV2Reads
		    Counter,
		pclNfsV2Wrcaches
		    Counter,
		pclNfsV2Writes
		    Counter,
		pclNfsV2Creates
		    Counter,
		pclNfsV2Removes
		    Counter,
		pclNfsV2Renames
		    Counter,
		pclNfsV2Links
		    Counter,
		pclNfsV2Symlinks
		    Counter,
		pclNfsV2Mkdirs
		    Counter,
		pclNfsV2Rmdirs
		    Counter,
		pclNfsV2Readdirs
		    Counter,
		pclNfsV2Statfss
		    Counter,
		pclNfsV3Nulls
		    Counter,
		pclNfsV3Getattrs
		    Counter,
		pclNfsV3Setattrs
		    Counter,
		pclNfsV3Lookups
		    Counter,
		pclNfsV3Accesss
		    Counter,
		pclNfsV3Readlinks
		    Counter,
		pclNfsV3Reads
		    Counter,
		pclNfsV3Writes
		    Counter,
		pclNfsV3Creates
		    Counter,
		pclNfsV3Mkdirs
		    Counter,
		pclNfsV3Symlinks
		    Counter,
		pclNfsV3Mknods
		    Counter,
		pclNfsV3Removes
		    Counter,
		pclNfsV3Rmdirs
		    Counter,
		pclNfsV3Renames
		    Counter,
		pclNfsV3Links
		    Counter,
		pclNfsV3Readdirs
		    Counter,
		pclNfsV3ReaddirPluss
		    Counter,
		pclNfsV3Fsstats
		    Counter,
		pclNfsV3Fsinfos
		    Counter,
		pclNfsV3Pathconfs
		    Counter,
		pclNfsV3Commits
		    Counter,
		pclPerCent
		    INTEGER (0..100),
		pclNfsV2NullPerCent
		    INTEGER (0..100),
		pclNfsV2GetattrPerCent
		    INTEGER (0..100),
		pclNfsV2SetattrPerCent
		    INTEGER (0..100),
		pclNfsV2RootPerCent
		    INTEGER (0..100),
		pclNfsV2LookupPerCent
		    INTEGER (0..100),
		pclNfsV2ReadlinkPerCent
		    INTEGER (0..100),
		pclNfsV2ReadPerCent
		    INTEGER (0..100),
		pclNfsV2WrcachePerCent
		    INTEGER (0..100),
		pclNfsV2WritePerCent
		    INTEGER (0..100),
		pclNfsV2CreatePerCent
		    INTEGER (0..100),
		pclNfsV2RemovePerCent
		    INTEGER (0..100),
		pclNfsV2RenamePerCent
		    INTEGER (0..100),
		pclNfsV2LinkPerCent
		    INTEGER (0..100),
		pclNfsV2SymlinkPerCent
		    INTEGER (0..100),
		pclNfsV2MkdirPerCent
		    INTEGER (0..100),
		pclNfsV2RmdirPerCent
		    INTEGER (0..100),
		pclNfsV2ReaddirPerCent
		    INTEGER (0..100),
		pclNfsV2StatfsPerCent
		    INTEGER (0..100),
		pclNfsV3NullPerCent
		    INTEGER (0..100),
		pclNfsV3GetattrPerCent
		    INTEGER (0..100),
		pclNfsV3SetattrPerCent
		    INTEGER (0..100),
		pclNfsV3LookupPerCent
		    INTEGER (0..100),
		pclNfsV3AccessPerCent
		    INTEGER (0..100),
		pclNfsV3ReadlinkPerCent
		    INTEGER (0..100),
		pclNfsV3ReadPerCent
		    INTEGER (0..100),
		pclNfsV3WritePerCent
		    INTEGER (0..100),
		pclNfsV3CreatePerCent
		    INTEGER (0..100),
		pclNfsV3MkdirPerCent
		    INTEGER (0..100),
		pclNfsV3SymlinkPerCent
		    INTEGER (0..100),
		pclNfsV3MknodPerCent
		    INTEGER (0..100),
		pclNfsV3RemovePerCent
		    INTEGER (0..100),
		pclNfsV3RmdirPerCent
		    INTEGER (0..100),
		pclNfsV3RenamePerCent
		    INTEGER (0..100),
		pclNfsV3LinkPerCent
		    INTEGER (0..100),
		pclNfsV3ReaddirPerCent
		    INTEGER (0..100),
		pclNfsV3ReaddirPlusPerCent
		    INTEGER (0..100),
		pclNfsV3FsstatPerCent
		    INTEGER (0..100),
		pclNfsV3FsinfoPerCent
		    INTEGER (0..100),
		pclNfsV3PathconfPerCent
		    INTEGER (0..100),
		pclNfsV3CommitPerCent
		    INTEGER (0..100),
		pclNfsV2Read512Calls
		    Counter,
		pclNfsV2Read1KCalls
		    Counter,
		pclNfsV2Read2KCalls
		    Counter,
		pclNfsV2Read4KCalls
		    Counter,
		pclNfsV2Read8KCalls
		    Counter,
		pclNfsV2Read16KCalls
		    Counter,
		pclNfsV2Read32KCalls
		    Counter,
		pclNfsV2Read64KCalls
		    Counter,
		pclNfsV2Read128KCalls
		    Counter,
		pclNfsV2Write512Calls
		    Counter,
		pclNfsV2Write1KCalls
		    Counter,
		pclNfsV2Write2KCalls
		    Counter,
		pclNfsV2Write4KCalls
		    Counter,
		pclNfsV2Write8KCalls
		    Counter,
		pclNfsV2Write16KCalls
		    Counter,
		pclNfsV2Write32KCalls
		    Counter,
		pclNfsV2Write64KCalls
		    Counter,
		pclNfsV2Write128KCalls
		    Counter,
		pclNfsV3Read512Calls
		    Counter,
		pclNfsV3Read1KCalls
		    Counter,
		pclNfsV3Read2KCalls
		    Counter,
		pclNfsV3Read4KCalls
		    Counter,
		pclNfsV3Read8KCalls
		    Counter,
		pclNfsV3Read16KCalls
		    Counter,
		pclNfsV3Read32KCalls
		    Counter,
		pclNfsV3Read64KCalls
		    Counter,
		pclNfsV3Read128KCalls
		    Counter,
		pclNfsV3Write512Calls
		    Counter,
		pclNfsV3Write1KCalls
		    Counter,
		pclNfsV3Write2KCalls
		    Counter,
		pclNfsV3Write4KCalls
		    Counter,
		pclNfsV3Write8KCalls
		    Counter,
		pclNfsV3Write16KCalls
		    Counter,
		pclNfsV3Write32KCalls
		    Counter,
		pclNfsV3Write64KCalls
		    Counter,
		pclNfsV3Write128KCalls
		    Counter
	    }

	pclIpAddr	OBJECT-TYPE
	SYNTAX		IpAddress
	ACCESS		read-only
	STATUS		mandatory
	DESCRIPTION
			"The IP address of the referenced client."
	::= { pclEntry 1 }

	pclRpcCalls	OBJECT-TYPE
	SYNTAX		Counter
	ACCESS		read-only
	STATUS		mandatory
	DESCRIPTION
			"The total number of RPC calls received from
			 the referenced client, since the last time the
			 statistics were cleared."
	::= { pclEntry 2 }

	pclRpcBadCalls	OBJECT-TYPE
	SYNTAX		Counter
	ACCESS		read-only
	STATUS		mandatory
	DESCRIPTION
			"The total number of calls received from the
			 referenced client that were rejected by the
			 RPC layer, since the last time the
			 statistics were cleared."
	::= { pclEntry 3 }

	pclRpcNullRecvs	OBJECT-TYPE
	SYNTAX		Counter
	ACCESS		read-only
	STATUS		mandatory
	DESCRIPTION
			"The number of times an RPC call was not available
			 when it was thought to be received from
			 referenced client, since the last time the
			 statistics were cleared."
	::= { pclEntry 4 }

	pclRpcBadLens	OBJECT-TYPE
	SYNTAX		Counter
	ACCESS		read-only
	STATUS		mandatory
	DESCRIPTION
			"The number of RPC calls received from the
			 referenced client with a length shorter
			 than a minimum-sized RPC call, since the
			 last time the statistics were cleared."
	::= { pclEntry 5 }

	pclRpcServXDRCalls OBJECT-TYPE
	SYNTAX		   Counter
	ACCESS		   read-only
	STATUS		   mandatory
	DESCRIPTION
			   "The number of RPC calls received from the
			    referenced client whose header could not
			    be XDR decoded, since the last time the
			    statistics were cleared."
	::= { pclEntry 6 }

	pclNfsCalls	   OBJECT-TYPE
	SYNTAX		   Counter
	ACCESS		   read-only
	STATUS		   mandatory
	DESCRIPTION
			   "The total number of NFS calls received from
			    the referenced client, since the last time
			    the statistics were cleared."
	::= { pclEntry 7 }

	pclNfsServBadCalls OBJECT-TYPE
	SYNTAX		   Counter
	ACCESS		   read-only
	STATUS		   mandatory
	DESCRIPTION
			   "The total number of NFS calls received from
			    the referenced client that were rejected, since
			    the last time the statistics were cleared."
	::= { pclEntry 8 }

	pclNfsV2Nulls	OBJECT-TYPE
	SYNTAX		Counter
	ACCESS		read-only
	STATUS		mandatory
	DESCRIPTION
			"The number of NFS Version 2 calls received
			 from the referenced client for the NFSPROC_NULL
			 (Do Nothing) procedure, since the last time the
			 statistics were cleared."
	::= { pclEntry 9 }

	pclNfsV2Getattrs OBJECT-TYPE
	SYNTAX		 Counter
	ACCESS		 read-only
	STATUS		 mandatory
	DESCRIPTION
			"The number of NFS Version 2 calls received
			 from the referenced client for the NFSPROC_GETATTR
			 (Get File Attributes) procedure, since the last
			 time the statistics were cleared."
	::= { pclEntry 10 }

	pclNfsV2Setattrs OBJECT-TYPE
	SYNTAX		 Counter
	ACCESS		 read-only
	STATUS		 mandatory
	DESCRIPTION
			"The number of NFS Version 2 calls received
			 from the referenced client for the NFSPROC_SETATTR
			 (Set File Attributes) procedure, since the last
			 time the statistics were cleared."
	::= { pclEntry 11 }

	pclNfsV2Roots	OBJECT-TYPE
	SYNTAX		Counter
	ACCESS		read-only
	STATUS		mandatory
	DESCRIPTION
			"The number of NFS Version 2 calls received
			 from the referenced client for the NFSPROC_ROOT
			 (Get Filesystem Root) procedure, since the last
			 time the statistics were cleared."
	::= { pclEntry 12 }

	pclNfsV2Lookups	OBJECT-TYPE
	SYNTAX		Counter
	ACCESS		read-only
	STATUS		mandatory
	DESCRIPTION
			"The number of NFS Version 2 calls received
			 from the referenced client for the NFSPROC_LOOKUP
			 (Look Up File Name) procedure, since the last
			 time the statistics were cleared."
	::= { pclEntry 13 }

	pclNfsV2Readlinks OBJECT-TYPE
	SYNTAX		  Counter
	ACCESS		  read-only
	STATUS		  mandatory
	DESCRIPTION
			 "The number of NFS Version 2 calls received
			  from the referenced client for the NFSPROC_READLINK
			  (Read From Symbolic Link) procedure, since the last
			  time the statistics were cleared."
	::= { pclEntry 14 }

	pclNfsV2Reads	OBJECT-TYPE
	SYNTAX		Counter
	ACCESS		read-only
	STATUS		mandatory
	DESCRIPTION
			"The number of NFS Version 2 calls received
			 from the referenced client for the NFSPROC_READ
			 (Read From File) procedure, since the last
			 time the statistics were cleared."
	::= { pclEntry 15 }

	pclNfsV2Wrcaches OBJECT-TYPE
	SYNTAX		 Counter
	ACCESS		 read-only
	STATUS		 mandatory
	DESCRIPTION
			"The number of NFS Version 2 calls received
			 from the referenced client for the NFSPROC_WRITECACHE
			 (Write to Cache) procedure, since the last
			 time the statistics were cleared."
	::= { pclEntry 16 }

	pclNfsV2Writes	OBJECT-TYPE
	SYNTAX		Counter
	ACCESS		read-only
	STATUS		mandatory
	DESCRIPTION
			"The number of NFS Version 2 calls received
			 from the referenced client for the NFSPROC_WRITE
			 (Write to File) procedure, since the last
			 time the statistics were cleared."
	::= { pclEntry 17 }

	pclNfsV2Creates	OBJECT-TYPE
	SYNTAX		Counter
	ACCESS		read-only
	STATUS		mandatory
	DESCRIPTION
			"The number of NFS Version 2 calls received
			 from the referenced client for the NFSPROC_CREATE
			 (Create File) procedure, since the last
			 time the statistics were cleared."
	::= { pclEntry 18 }

	pclNfsV2Removes	OBJECT-TYPE
	SYNTAX		Counter
	ACCESS		read-only
	STATUS		mandatory
	DESCRIPTION
			"The number of NFS Version 2 calls received
			 from the referenced client for the NFSPROC_REMOVE
			 (Remove File) procedure, since the last
			 time the statistics were cleared."
	::= { pclEntry 19 }

	pclNfsV2Renames	OBJECT-TYPE
	SYNTAX		Counter
	ACCESS		read-only
	STATUS		mandatory
	DESCRIPTION
			"The number of NFS Version 2 calls received
			 from the referenced client for the NFSPROC_RENAME
			 (Rename File) procedure, since the last
			 time the statistics were cleared."
	::= { pclEntry 20 }

	pclNfsV2Links	OBJECT-TYPE
	SYNTAX		Counter
	ACCESS		read-only
	STATUS		mandatory
	DESCRIPTION
			"The number of NFS Version 2 calls received
			 from the referenced client for the NFSPROC_LINK
			 (Create Link to File) procedure, since the last
			 time the statistics were cleared."
	::= { pclEntry 21 }

	pclNfsV2Symlinks OBJECT-TYPE
	SYNTAX		 Counter
	ACCESS		 read-only
	STATUS		 mandatory
	DESCRIPTION
			"The number of NFS Version 2 calls received
			 from the referenced client for the NFSPROC_SYMLINK
			 (Create Symbolic Link) procedure, since the last
			 time the statistics were cleared."
	::= { pclEntry 22 }

	pclNfsV2Mkdirs	OBJECT-TYPE
	SYNTAX		Counter
	ACCESS		read-only
	STATUS		mandatory
	DESCRIPTION
			"The number of NFS Version 2 calls received
			 from the referenced client for the NFSPROC_MKDIR
			 (Create Directory) procedure, since the last
			 time the statistics were cleared."
	::= { pclEntry 23 }

	pclNfsV2Rmdirs	OBJECT-TYPE
	SYNTAX		Counter
	ACCESS		read-only
	STATUS		mandatory
	DESCRIPTION
			"The number of NFS Version 2 calls received
			 from the referenced client for the NFSPROC_RMDIR
			 (Remove Directory) procedure, since the last
			 time the statistics were cleared."
	::= { pclEntry 24 }

	pclNfsV2Readdirs OBJECT-TYPE
	SYNTAX		 Counter
	ACCESS		 read-only
	STATUS		 mandatory
	DESCRIPTION
			"The number of NFS Version 2 calls received
			 from the referenced client for the NFSPROC_READDIR
			 (Read From Directory) procedure, since the last
			 time the statistics were cleared."
	::= { pclEntry 25 }

	pclNfsV2Statfss OBJECT-TYPE
	SYNTAX		Counter
	ACCESS		read-only
	STATUS		mandatory
	DESCRIPTION
			"The number of NFS Version 2 calls received
			 from the referenced client for the NFSPROC_STATFS
			 (Get Filesystem Attributes) procedure, since the
			 last time the statistics were cleared."
	::= { pclEntry 26 }

	pclNfsV3Nulls	OBJECT-TYPE
	SYNTAX		Counter
	ACCESS		read-only
	STATUS		mandatory
	DESCRIPTION
			"The number of NFS Version 3 calls received
			 from the referenced client for the NFSPROC3_NULL
			 (Do Nothing) procedure, since the last time the
			 statistics were cleared."
	::= { pclEntry 27 }

	pclNfsV3Getattrs OBJECT-TYPE
	SYNTAX		 Counter
	ACCESS		 read-only
	STATUS		 mandatory
	DESCRIPTION
			"The number of NFS Version 3 calls received
			 from the referenced client for the NFSPROC3_GETATTR
			 (Get File Attributes) procedure, since the last
			 time the statistics were cleared."
	::= { pclEntry 28 }

	pclNfsV3Setattrs OBJECT-TYPE
	SYNTAX		 Counter
	ACCESS		 read-only
	STATUS		 mandatory
	DESCRIPTION
			"The number of NFS Version 3 calls received
			 from the referenced client for the NFSPROC3_SETATTR
			 (Set File Attributes) procedure, since the last
			 time the statistics were cleared."
	::= { pclEntry 29 }

	pclNfsV3Lookups	OBJECT-TYPE
	SYNTAX		Counter
	ACCESS		read-only
	STATUS		mandatory
	DESCRIPTION
			"The number of NFS Version 3 calls received
			 from the referenced client for the NFSPROC3_LOOKUP
			 (Lookup Filename) procedure, since the last time
			 the statistics were cleared."
	::= { pclEntry 30 }

	pclNfsV3Accesss	OBJECT-TYPE
	SYNTAX		Counter
	ACCESS		read-only
	STATUS		mandatory
	DESCRIPTION
			"The number of NFS Version 3 calls received
			 from the referenced client for the NFSPROC3_ACCESS
			 (Check Access Permission) procedure, since the
			 last time the statistics were cleared."
	::= { pclEntry 31 }

	pclNfsV3Readlinks OBJECT-TYPE
	SYNTAX		  Counter
	ACCESS		  read-only
	STATUS		  mandatory
	DESCRIPTION
			"The number of NFS Version 3 calls received
			 from the referenced client for the NFSPROC3_READLINK
			 (Read from Symbolic Link) procedure, since the
			 last time the statistics were cleared."
	::= { pclEntry 32 }

	pclNfsV3Reads	OBJECT-TYPE
	SYNTAX		Counter
	ACCESS		read-only
	STATUS		mandatory
	DESCRIPTION
			"The number of NFS Version 3 calls received
			 from the referenced client for the NFSPROC3_READ
			 (Read From File) procedure, since the last time
			 the statistics were cleared."
	::= { pclEntry 33 }

	pclNfsV3Writes	OBJECT-TYPE
	SYNTAX		Counter
	ACCESS		read-only
	STATUS		mandatory
	DESCRIPTION
			"The number of NFS Version 3 calls received
			 from the referenced client for the NFSPROC3_WRITE
			 (Write to File) procedure, since the last time
			 the statistics were cleared."
	::= { pclEntry 34 }

	pclNfsV3Creates	OBJECT-TYPE
	SYNTAX		Counter
	ACCESS		read-only
	STATUS		mandatory
	DESCRIPTION
			"The number of NFS Version 3 calls received
			 from the referenced client for the NFSPROC3_CREATE
			 (Create a File) procedure, since the last time
			 the statistics were cleared."
	::= { pclEntry 35 }

	pclNfsV3Mkdirs	OBJECT-TYPE
	SYNTAX		Counter
	ACCESS		read-only
	STATUS		mandatory
	DESCRIPTION
			"The number of NFS Version 3 calls received
			 from the referenced client for the NFSPROC3_MKDIR
			 (Create a Directory) procedure, since the last
			 time the statistics were cleared."
	::= { pclEntry 36 }

	pclNfsV3Symlinks OBJECT-TYPE
	SYNTAX		 Counter
	ACCESS		 read-only
	STATUS		 mandatory
	DESCRIPTION
			"The number of NFS Version 3 calls received
			 from the referenced client for the NFSPROC3_SYMLINK
			 (Create a Symbolic Link) procedure, since the last
			 time the statistics were cleared."
	::= { pclEntry 37 }

	pclNfsV3Mknods	OBJECT-TYPE
	SYNTAX		Counter
	ACCESS		read-only
	STATUS		mandatory
	DESCRIPTION
			"The number of NFS Version 3 calls received
			 from the referenced client for the NFSPROC3_MKNOD
			 (Create a Special Device) procedure, since the
			 last time the statistics were cleared."
	::= { pclEntry 38 }

	pclNfsV3Removes	OBJECT-TYPE
	SYNTAX		Counter
	ACCESS		read-only
	STATUS		mandatory
	DESCRIPTION
			"The number of NFS Version 3 calls received
			 from the referenced client for the NFSPROC3_REMOVE
			 (Remove a File) procedure, since the last time
			 the statistics were cleared."
	::= { pclEntry 39 }

	pclNfsV3Rmdirs	OBJECT-TYPE
	SYNTAX		Counter
	ACCESS		read-only
	STATUS		mandatory
	DESCRIPTION
			"The number of NFS Version 3 calls received
			 from the referenced client for the NFSPROC3_RMDIR
			 (Remove a Directory) procedure, since the last
			 time the statistics were cleared."
	::= { pclEntry 40 }

	pclNfsV3Renames	OBJECT-TYPE
	SYNTAX		Counter
	ACCESS		read-only
	STATUS		mandatory
	DESCRIPTION
			"The number of NFS Version 3 calls received
			 from the referenced client for the NFSPROC3_RENAME
			 (Rename a File or Directory) procedure, since the
			 last time the statistics were cleared."
	::= { pclEntry 41 }

	pclNfsV3Links	OBJECT-TYPE
	SYNTAX		Counter
	ACCESS		read-only
	STATUS		mandatory
	DESCRIPTION
			"The number of NFS Version 3 calls received
			 from the referenced client for the NFSPROC3_LINK
			 (Create Link to an Object) procedure, since the
			 last time the statistics were cleared."
	::= { pclEntry 42 }

	pclNfsV3Readdirs OBJECT-TYPE
	SYNTAX		 Counter
	ACCESS		 read-only
	STATUS		 mandatory
	DESCRIPTION
			"The number of NFS Version 3 calls received
			 from the referenced client for the NFSPROC3_READDIR
			 (Read From Directory) procedure, since the last
			 time the statistics were cleared."
	::= { pclEntry 43 }

	pclNfsV3ReaddirPluss OBJECT-TYPE
	SYNTAX		     Counter
	ACCESS		     read-only
	STATUS		     mandatory
	DESCRIPTION
			     "The number of NFS Version 3 calls received
			      from the referenced client for the
			      NFSPROC3_READDIRPLUS (Extended Read from
			      Directory) procedure, since the last time
			      the statistics were cleared."
	::= { pclEntry 44 }

	pclNfsV3Fsstats	OBJECT-TYPE
	SYNTAX		Counter
	ACCESS		read-only
	STATUS		mandatory
	DESCRIPTION
			"The number of NFS Version 3 calls received
			 from the referenced client for the NFSPROC3_FSSTAT
			 (Get Dynamic File System Information) procedure,
			 since the last time the statistics were cleared."
	::= { pclEntry 45 }

	pclNfsV3Fsinfos	OBJECT-TYPE
	SYNTAX		Counter
	ACCESS		read-only
	STATUS		mandatory
	DESCRIPTION
			"The number of NFS Version 3 calls received
			 from the referenced client for the NFSPROC3_FSINFO
			 (Get Static File System Information) procedure,
			 since the last time the statistics were cleared."
	::= { pclEntry 46 }

	pclNfsV3Pathconfs OBJECT-TYPE
	SYNTAX		  Counter
	ACCESS		  read-only
	STATUS		  mandatory
	DESCRIPTION
			  "The number of NFS Version 3 calls received
			   from the referenced client for the NFSPROC3_PATHCONF
			   (Retrieve POSIX Information) procedure, since the
			   last time the statistics were cleared."
	::= { pclEntry 47 }

	pclNfsV3Commits	OBJECT-TYPE
	SYNTAX		Counter
	ACCESS		read-only
	STATUS		mandatory
	DESCRIPTION
			"The number of NFS Version 3 calls received
			 from the referenced client for the NFSPROC3_COMMIT
			 (Commit Cached Data on a Server to Stable Storage)
			 procedure, since the last time the statistics were
			 cleared."
	::= { pclEntry 48 }

	pclPerCent		OBJECT-TYPE
	SYNTAX			INTEGER(0..100)
	ACCESS			read-only
	STATUS			mandatory
	DESCRIPTION
				"The number of the total NFS calls for the
				 referenced client as a percentage of the
				 total NFS calls received from all
				 clients, since the last time the
				 statistics were cleared."
	::= { pclEntry 49 }

	pclNfsV2NullPerCent	OBJECT-TYPE
	SYNTAX			INTEGER(0..100)
	ACCESS			read-only
	STATUS			mandatory
	DESCRIPTION
				"The number of NFS Version 2 calls
				 received from the referenced client for
				 the NFSPROC_NULL (Do Nothing) procedure,
				 as a percentage of the total calls
				 received from this client, since the
				 last time the statistics were cleared."
	::= { pclEntry 50 }

	pclNfsV2GetattrPerCent	OBJECT-TYPE
	SYNTAX			INTEGER(0..100)
	ACCESS			read-only
	STATUS			mandatory
	DESCRIPTION
				"The number of NFS Version 2 calls
				 received from the referenced client for
				 the NFSPROC_GETATTR (Get File Attributes)
				 procedure, as a percentage of the total
				 calls received from this client, since
				 the last time the statistics were cleared."
	::= { pclEntry 51 }

	pclNfsV2SetattrPerCent	OBJECT-TYPE
	SYNTAX			INTEGER(0..100)
	ACCESS			read-only
	STATUS			mandatory
	DESCRIPTION
				"The number of NFS Version 2 calls
				 received from the referenced client for
				 the NFSPROC_SETATTR (Set File Attributes)
				 procedure, as a percentage of the total
				 calls received from this client, since
				 the last time the statistics were cleared."
	::= { pclEntry 52 }

	pclNfsV2RootPerCent	OBJECT-TYPE
	SYNTAX			INTEGER(0..100)
	ACCESS			read-only
	STATUS			mandatory
	DESCRIPTION
				"The number of NFS Version 2 calls
				 received from the referenced client for
				 the NFSPROC_ROOT (Get Filesystem Root)
				 procedure, as a percentage of the total
				 calls received from this client, since
				 the last time the statistics were cleared."
	::= { pclEntry 53 }

	pclNfsV2LookupPerCent	OBJECT-TYPE
	SYNTAX			INTEGER(0..100)
	ACCESS			read-only
	STATUS			mandatory
	DESCRIPTION
				"The number of NFS Version 2 calls
				 received from the referenced client for
				 the NFSPROC_LOOKUP (Look Up File Name)
				 procedure, as a percentage of the total
				 calls received from this client, since
				 the last time the statistics were cleared."
	::= { pclEntry 54 }

	pclNfsV2ReadlinkPerCent	OBJECT-TYPE
	SYNTAX			INTEGER(0..100)
	ACCESS			read-only
	STATUS			mandatory
	DESCRIPTION
				"The number of NFS Version 2 calls
				 received from the referenced client for
				 the NFSPROC_READLINK (Read From Symbolic
				 Link) procedure, as a percentage of the
				 total calls received from this client,
				 since the last time the statistics were
				 cleared."
	::= { pclEntry 55 }

	pclNfsV2ReadPerCent	OBJECT-TYPE
	SYNTAX			INTEGER(0..100)
	ACCESS			read-only
	STATUS			mandatory
	DESCRIPTION
				"The number of NFS Version 2 calls
				 received from the referenced client for
				 the NFSPROC_READ (Read From File)
				 procedure, as a percentage of the total
				 calls received from this client, since
				 the last time the statistics were cleared."
	::= { pclEntry 56 }

	pclNfsV2WrcachePerCent	OBJECT-TYPE
	SYNTAX			INTEGER(0..100)
	ACCESS			read-only
	STATUS			mandatory
	DESCRIPTION
				"The number of NFS Version 2 calls
				 received from the referenced client for
				 the NFSPROC_WRITECACHE (Write to Cache)
				 procedure, as a percentage of the total
				 calls received from this client, since
				 the last time the statistics were cleared."
	::= { pclEntry 57 }

	pclNfsV2WritePerCent	OBJECT-TYPE
	SYNTAX			INTEGER(0..100)
	ACCESS			read-only
	STATUS			mandatory
	DESCRIPTION
				"The number of NFS Version 2 calls
				 received from the referenced client for
				 the NFSPROC_WRITE (Write to File)
				 procedure, as a percentage of the total
				 calls received from this client, since
				 the last time the statistics were cleared."
	::= { pclEntry 58 }

	pclNfsV2CreatePerCent	OBJECT-TYPE
	SYNTAX			INTEGER(0..100)
	ACCESS			read-only
	STATUS			mandatory
	DESCRIPTION
				"The number of NFS Version 2 calls
				 received from the referenced client for
				 the NFSPROC_CREATE (Create File)
				 procedure, as a percentage of the total
				 calls received from this client, since
				 the last time the statistics were cleared."
	::= { pclEntry 59 }

	pclNfsV2RemovePerCent	OBJECT-TYPE
	SYNTAX			INTEGER(0..100)
	ACCESS			read-only
	STATUS			mandatory
	DESCRIPTION
				"The number of NFS Version 2 calls
				 received from the referenced client for
				 the NFSPROC_REMOVE (Remove File)
				 procedure, as a percentage of the total
				 calls received from this client, since
				 the last time the statistics were cleared."
	::= { pclEntry 60 }

	pclNfsV2RenamePerCent	OBJECT-TYPE
	SYNTAX			INTEGER(0..100)
	ACCESS			read-only
	STATUS			mandatory
	DESCRIPTION
				"The number of NFS Version 2 calls
				 received from the referenced client for
				 the NFSPROC_RENAME (Rename File)
				 procedure, as a percentage of the total
				 calls received from this client, since
				 the last time the statistics were cleared."
	::= { pclEntry 61 }

	pclNfsV2LinkPerCent	OBJECT-TYPE
	SYNTAX			INTEGER(0..100)
	ACCESS			read-only
	STATUS			mandatory
	DESCRIPTION
				"The number of NFS Version 2 calls
				 received from the referenced client for
				 the NFSPROC_LINK (Create Link to File)
				 procedure, as a percentage of the total
				 calls received from this client, since
				 the last time the statistics were cleared."
	::= { pclEntry 62 }

	pclNfsV2SymlinkPerCent	OBJECT-TYPE
	SYNTAX			INTEGER(0..100)
	ACCESS			read-only
	STATUS			mandatory
	DESCRIPTION
				"The number of NFS Version 2 calls
				 received from the referenced client for
				 the NFSPROC_SYMLINK (Create Symbolic Link)
				 procedure, as a percentage of the total
				 calls received from this client, since
				 the last time the statistics were cleared."
	::= { pclEntry 63 }

	pclNfsV2MkdirPerCent	OBJECT-TYPE
	SYNTAX			INTEGER(0..100)
	ACCESS			read-only
	STATUS			mandatory
	DESCRIPTION
				"The number of NFS Version 2 calls
				 received from the referenced client for
				 the NFSPROC_MKDIR (Create Directory)
				 procedure, as a percentage of the total
				 calls received from this client, since
				 the last time the statistics were cleared."
	::= { pclEntry 64 }

	pclNfsV2RmdirPerCent	OBJECT-TYPE
	SYNTAX		 	INTEGER(0..100)
	ACCESS			read-only
	STATUS			mandatory
	DESCRIPTION
				"The number of NFS Version 2 calls
				 received from the referenced client for
				 the NFSPROC_RMDIR (Remove Directory)
				 procedure, as a percentage of the total
				 calls received from this client, since
				 the last time the statistics were cleared."
	::= { pclEntry 65 }

	pclNfsV2ReaddirPerCent	OBJECT-TYPE
	SYNTAX			INTEGER(0..100)
	ACCESS			read-only
	STATUS			mandatory
	DESCRIPTION
				"The number of NFS Version 2 calls
				 received from the referenced client for
				 the NFSPROC_READDIR (Read From Directory)
				 procedure, as a percentage of the total
				 calls received from this client, since
				 the last time the statistics were cleared."
	::= { pclEntry 66 }

	pclNfsV2StatfsPerCent	OBJECT-TYPE
	SYNTAX			INTEGER(0..100)
	ACCESS			read-only
	STATUS			mandatory
	DESCRIPTION
				"The number of NFS Version 2 calls
				 received from the referenced client for
				 the NFSPROC_STATFS (Get Filesystem
				 Attributes) procedure, as a percentage
				 of the total calls received from this
				 client, since the last time the
				 statistics were cleared."
	::= { pclEntry 67 }

	pclNfsV3NullPerCent	OBJECT-TYPE
	SYNTAX			INTEGER(0..100)
	ACCESS			read-only
	STATUS			mandatory
	DESCRIPTION
				"The number of NFS Version 3 calls
				 received from the referenced client for
				 the NFSPROC3_NULL (Do Nothing) 
				 procedure, as a percentage of the total
				 calls received from this client, since
				 the last time the statistics were cleared."
	::= { pclEntry 68 }

	pclNfsV3GetattrPerCent	OBJECT-TYPE
	SYNTAX			INTEGER(0..100)
	ACCESS			read-only
	STATUS			mandatory
	DESCRIPTION
				"The number of NFS Version 3 calls
				 received from the referenced client for
				 the NFSPROC3_GETATTR (Get File Attributes)
				 procedure, as a percentage of the total
				 calls received from this client, since
				 the last time the statistics were cleared."
	::= { pclEntry 69 }

	pclNfsV3SetattrPerCent	OBJECT-TYPE
	SYNTAX			INTEGER(0..100)
	ACCESS			read-only
	STATUS			mandatory
	DESCRIPTION
				"The number of NFS Version 3 calls
				 received from the referenced client for
				 the NFSPROC3_SETATTR (Set File Attributes)
				 procedure, as a percentage of the total
				 calls received from this client, since
				 the last time the statistics were cleared."
	::= { pclEntry 70 }

	pclNfsV3LookupPerCent	OBJECT-TYPE
	SYNTAX			INTEGER(0..100)
	ACCESS			read-only
	STATUS			mandatory
	DESCRIPTION
				"The number of NFS Version 3 calls
				 received from the referenced client for
				 the NFSPROC3_LOOKUP (Lookup Filename)
				 procedure, as a percentage of the total
				 calls received from this client, since
				 the last time the statistics were cleared."
	::= { pclEntry 71 }

	pclNfsV3AccessPerCent	OBJECT-TYPE
	SYNTAX			INTEGER(0..100)
	ACCESS			read-only
	STATUS			mandatory
	DESCRIPTION
				"The number of NFS Version 3 calls
				 received from the referenced client for
				 the NFSPROC3_ACCESS (Check Access Permission)
				 procedure, as a percentage of the total
				 calls received from this client, since
				 the last time the statistics were cleared."
	::= { pclEntry 72 }

	pclNfsV3ReadlinkPerCent	OBJECT-TYPE
	SYNTAX			INTEGER(0..100)
	ACCESS			read-only
	STATUS			mandatory
	DESCRIPTION
				"The number of NFS Version 3 calls
				 received from the referenced client for
				 the NFSPROC3_READLINK (Read from Symbolic
				 Link) procedure, as a percentage of the total
				 calls received from this client, since
				 the last time the statistics were cleared."
	::= { pclEntry 73 }

	pclNfsV3ReadPerCent	OBJECT-TYPE
	SYNTAX			INTEGER(0..100)
	ACCESS			read-only
	STATUS			mandatory
	DESCRIPTION
				"The number of NFS Version 3 calls
				 received from the referenced client for
				 the NFSPROC3_READ (Read From File)
				 procedure, as a percentage of the total
				 calls received from this client, since
				 the last time the statistics were cleared."
	::= { pclEntry 74 }

	pclNfsV3WritePerCent	OBJECT-TYPE
	SYNTAX			INTEGER(0..100)
	ACCESS			read-only
	STATUS			mandatory
	DESCRIPTION
				"The number of NFS Version 3 calls
				 received from the referenced client for
				 the NFSPROC3_WRITE (Write to File)
				 procedure, as a percentage of the total
				 calls received from this client, since
				 the last time the statistics were cleared."
	::= { pclEntry 75 }

	pclNfsV3CreatePerCent	OBJECT-TYPE
	SYNTAX			INTEGER(0..100)
	ACCESS			read-only
	STATUS			mandatory
	DESCRIPTION
				"The number of NFS Version 3 calls
				 received from the referenced client for
				 the NFSPROC3_CREATE (Create a File)
				 procedure, as a percentage of the total
				 calls received from this client, since
				 the last time the statistics were cleared."
	::= { pclEntry 76 }

	pclNfsV3MkdirPerCent	OBJECT-TYPE
	SYNTAX			INTEGER(0..100)
	ACCESS			read-only
	STATUS			mandatory
	DESCRIPTION
				"The number of NFS Version 3 calls
				 received from the referenced client for
				 the NFSPROC3_MKDIR (Create a Directory)
				 procedure, as a percentage of the total
				 calls received from this client, since
				 the last time the statistics were cleared."
	::= { pclEntry 77 }

	pclNfsV3SymlinkPerCent	OBJECT-TYPE
	SYNTAX			INTEGER(0..100)
	ACCESS			read-only
	STATUS			mandatory
	DESCRIPTION
				"The number of NFS Version 3 calls
				 received from the referenced client for
				 the NFSPROC3_SYMLINK (Create a Symbolic
				 Link) procedure, as a percentage of the
				 total calls received from this client, since
				 the last time the statistics were cleared."
	::= { pclEntry 78 }

	pclNfsV3MknodPerCent	OBJECT-TYPE
	SYNTAX			INTEGER(0..100)
	ACCESS			read-only
	STATUS			mandatory
	DESCRIPTION
				"The number of NFS Version 3 calls
				 received from the referenced client for
				 the NFSPROC3_MKNOD (Create a Special
				 Device) procedure, as a percentage of the
				 total calls received from this client, since
				 the last time the statistics were cleared."
	::= { pclEntry 79 }

	pclNfsV3RemovePerCent	OBJECT-TYPE
	SYNTAX			INTEGER(0..100)
	ACCESS			read-only
	STATUS			mandatory
	DESCRIPTION
				"The number of NFS Version 3 calls
				 received from the referenced client for
				 the NFSPROC3_REMOVE (Remove a File)
				 procedure, as a percentage of the total
				 calls received from this client, since
				 the last time the statistics were cleared."
	::= { pclEntry 80 }

	pclNfsV3RmdirPerCent	OBJECT-TYPE
	SYNTAX			INTEGER(0..100)
	ACCESS			read-only
	STATUS			mandatory
	DESCRIPTION
				"The number of NFS Version 3 calls
				 received from the referenced client for
				 the NFSPROC3_RMDIR (Remove a Directory)
				 procedure, as a percentage of the total
				 calls received from this client, since
				 the last time the statistics were cleared."
	::= { pclEntry 81 }

	pclNfsV3RenamePerCent	OBJECT-TYPE
	SYNTAX			INTEGER(0..100)
	ACCESS			read-only
	STATUS			mandatory
	DESCRIPTION
				"The number of NFS Version 3 calls
				 received from the referenced client for
				 the NFSPROC3_RENAME (Rename a File or
				 Directory) procedure, as a percentage of
				 the total calls received from this client,
				 since the last time the statistics were
				 cleared."
	::= { pclEntry 82 }

	pclNfsV3LinkPerCent	OBJECT-TYPE
	SYNTAX			INTEGER(0..100)
	ACCESS			read-only
	STATUS			mandatory
	DESCRIPTION
				"The number of NFS Version 3 calls
				 received from the referenced client for
				 the NFSPROC3_LINK (Create Link to an Object) 
				 procedure, as a percentage of the total
				 calls received from this client, since
				 the last time the statistics were cleared."
	::= { pclEntry 83 }

	pclNfsV3ReaddirPerCent	OBJECT-TYPE
	SYNTAX			INTEGER(0..100)
	ACCESS			read-only
	STATUS			mandatory
	DESCRIPTION
				"The number of NFS Version 3 calls
				 received from the referenced client for
				 the NFSPROC3_READDIR (Read From Directory)
				 procedure, as a percentage of the total
				 calls received from this client, since
				 the last time the statistics were cleared."
	::= { pclEntry 84 }

	pclNfsV3ReaddirPlusPerCent	OBJECT-TYPE
	SYNTAX				INTEGER(0..100)
	ACCESS				read-only
	STATUS				mandatory
	DESCRIPTION
				"The number of NFS Version 3 calls
				 received from the referenced client for
				 the NFSPROC3_READDIRPLUS (Extended Read from
				 Directory) procedure, as a percentage of the
				 total calls received from this client, since
				 the last time the statistics were cleared."
	::= { pclEntry 85 }

	pclNfsV3FsstatPerCent	OBJECT-TYPE
	SYNTAX			INTEGER(0..100)
	ACCESS			read-only
	STATUS			mandatory
	DESCRIPTION
				"The number of NFS Version 3 calls
				 received from the referenced client for
				 the NFSPROC3_FSSTAT (Get Dynamic File
				 System Information) procedure, as a
				 percentage of the total calls received
				 from this client, since the last time
				 the statistics were cleared."
	::= { pclEntry 86 }

	pclNfsV3FsinfoPerCent	OBJECT-TYPE
	SYNTAX			INTEGER(0..100)
	ACCESS			read-only
	STATUS			mandatory
	DESCRIPTION
				"The number of NFS Version 3 calls
				 received from the referenced client for
				 the NFSPROC3_FSINFO (Get Static File System
				 Information) procedure, as a percentage of the
				 total calls received from this client, since
				 the last time the statistics were cleared."
	::= { pclEntry 87 }

	pclNfsV3PathconfPerCent	OBJECT-TYPE
	SYNTAX			INTEGER(0..100)
	ACCESS			read-only
	STATUS			mandatory
	DESCRIPTION
				"The number of NFS Version 3 calls
				 received from the referenced client for
				 the NFSPROC3_PATHCONF (Retrieve POSIX
				 Information) procedure, as a percentage of the
				 total calls received from this client, since
				 the last time the statistics were cleared."
	::= { pclEntry 88 }

	pclNfsV3CommitPerCent	OBJECT-TYPE
	SYNTAX			INTEGER(0..100)
	ACCESS			read-only
	STATUS			mandatory
	DESCRIPTION
				"The number of NFS Version 3 calls
				 received from the referenced client for
				 the NFSPROC3_COMMIT (Commit Cached Data on
				 a Server to Stable Storage) procedure, as
				 a percentage of the total calls received
				 from this client, since the last time the
				 statistics were cleared."
	::= { pclEntry 89 }

	pclNfsV2Read512Calls	OBJECT-TYPE
	SYNTAX			Counter
	ACCESS			read-only
	STATUS			mandatory
	DESCRIPTION
				"The number of NFS Version 2 read calls 
				with request sizes between 0-511 bytes 
				received from this client."
	::= { pclEntry 90 }

	pclNfsV2Read1KCalls	OBJECT-TYPE
	SYNTAX			Counter
	ACCESS			read-only
	STATUS			mandatory
	DESCRIPTION
				"The number of NFS Version 2 read calls 
				with request sizes between 512-1023 bytes 
				received from this client."
	::= { pclEntry 91 }

	pclNfsV2Read2KCalls	OBJECT-TYPE
	SYNTAX			Counter
	ACCESS			read-only
	STATUS			mandatory
	DESCRIPTION
				"The number of NFS Version 2 read calls 
				with request sizes between 1K-2047 bytes 
				received from this client."
	::= { pclEntry 92 }

	pclNfsV2Read4KCalls	OBJECT-TYPE
	SYNTAX			Counter
	ACCESS			read-only
	STATUS			mandatory
	DESCRIPTION
				"The number of NFS Version 2 read calls 
				with request sizes between 2K-4095 bytes 
				received from this client."
	::= { pclEntry 93 }

	pclNfsV2Read8KCalls	OBJECT-TYPE
	SYNTAX			Counter
	ACCESS			read-only
	STATUS			mandatory
	DESCRIPTION
				"The number of NFS Version 2 read calls 
				with request sizes between 4K-8191 bytes 
				received from this client."
	::= { pclEntry 94 }

	pclNfsV2Read16KCalls	OBJECT-TYPE
	SYNTAX			Counter
	ACCESS			read-only
	STATUS			mandatory
	DESCRIPTION
				"The number of NFS Version 2 read calls 
				with request sizes between 8K-16383 bytes 
				received from this client."
	::= { pclEntry 95 }

	pclNfsV2Read32KCalls	OBJECT-TYPE
	SYNTAX			Counter
	ACCESS			read-only
	STATUS			mandatory
	DESCRIPTION
				"The number of NFS Version 2 read calls 
				with request sizes between 16K-32767 bytes 
				received from this client."
	::= { pclEntry 96 }

	pclNfsV2Read64KCalls	OBJECT-TYPE
	SYNTAX			Counter
	ACCESS			read-only
	STATUS			mandatory
	DESCRIPTION
				"The number of NFS Version 2 read calls 
				with request sizes between 32K-65535 bytes 
				received from this client."
	::= { pclEntry 97 }

	pclNfsV2Read128KCalls	OBJECT-TYPE
	SYNTAX			Counter
	ACCESS			read-only
	STATUS			mandatory
	DESCRIPTION
				"The number of NFS Version 2 read calls 
				with request sizes between 64K-131071 bytes 
				received from this client."
	::= { pclEntry 98 }

	pclNfsV2Write512Calls	OBJECT-TYPE
	SYNTAX			Counter
	ACCESS			read-only
	STATUS			mandatory
	DESCRIPTION
				"The number of NFS Version 2 write calls
				with request sizes between 0-511 bytes
				received from this client."
	::= { pclEntry 99 }

	pclNfsV2Write1KCalls	OBJECT-TYPE
	SYNTAX			Counter
	ACCESS			read-only
	STATUS			mandatory
	DESCRIPTION
				"The number of NFS Version 2 write calls
				with request sizes between 512-1023 bytes
				received from this client."
	::= { pclEntry 100 }

	pclNfsV2Write2KCalls	OBJECT-TYPE
	SYNTAX			Counter
	ACCESS			read-only
	STATUS			mandatory
	DESCRIPTION
				"The number of NFS Version 2 write calls
				with request sizes between 1K-2047 bytes
				received from this client."
	::= { pclEntry 101 }

	pclNfsV2Write4KCalls	OBJECT-TYPE
	SYNTAX			Counter
	ACCESS			read-only
	STATUS			mandatory
	DESCRIPTION
				"The number of NFS Version 2 write calls
				with request sizes between 2K-4095 bytes
				received from this client."
	::= { pclEntry 102 }

	pclNfsV2Write8KCalls	OBJECT-TYPE
	SYNTAX			Counter
	ACCESS			read-only
	STATUS			mandatory
	DESCRIPTION
				"The number of NFS Version 2 write calls
				with request sizes between 4K-8191 bytes
				received from this client."
	::= { pclEntry 103 }

	pclNfsV2Write16KCalls	OBJECT-TYPE
	SYNTAX			Counter
	ACCESS			read-only
	STATUS			mandatory
	DESCRIPTION
				"The number of NFS Version 2 write calls
				with request sizes between 8K-16383 bytes
				received from this client."
	::= { pclEntry 104 }

	pclNfsV2Write32KCalls	OBJECT-TYPE
	SYNTAX			Counter
	ACCESS			read-only
	STATUS			mandatory
	DESCRIPTION
				"The number of NFS Version 2 write calls
				with request sizes between 16K-32767 bytes
				received from this client."
	::= { pclEntry 105 }

	pclNfsV2Write64KCalls	OBJECT-TYPE
	SYNTAX			Counter
	ACCESS			read-only
	STATUS			mandatory
	DESCRIPTION
				"The number of NFS Version 2 write calls
				with request sizes between 32K-65535 bytes
				received from this client."
	::= { pclEntry 106 }

	pclNfsV2Write128KCalls	OBJECT-TYPE
	SYNTAX			Counter
	ACCESS			read-only
	STATUS			mandatory
	DESCRIPTION
				"The number of NFS Version 2 write calls
				with request sizes between 64K-131071 bytes
				received from this client."
	::= { pclEntry 107 }

	pclNfsV3Read512Calls	OBJECT-TYPE
	SYNTAX			Counter
	ACCESS			read-only
	STATUS			mandatory
	DESCRIPTION
				"The number of NFS Version 3 read calls
				with request sizes between 0-511 bytes
				received from this client."
	::= { pclEntry 108 }

	pclNfsV3Read1KCalls	OBJECT-TYPE
	SYNTAX			Counter
	ACCESS			read-only
	STATUS			mandatory
	DESCRIPTION
				"The number of NFS Version 3 read calls
				with request sizes between 512-1023 bytes
				received from this client."
	::= { pclEntry 109 }

	pclNfsV3Read2KCalls	OBJECT-TYPE
	SYNTAX			Counter
	ACCESS			read-only
	STATUS			mandatory
	DESCRIPTION
				"The number of NFS Version 3 read calls
				with request sizes between 1K-2047 bytes
				received from this client."
	::= { pclEntry 110 }

	pclNfsV3Read4KCalls	OBJECT-TYPE
	SYNTAX			Counter
	ACCESS			read-only
	STATUS			mandatory
	DESCRIPTION
				"The number of NFS Version 3 read calls
				with request sizes between 2K-4095 bytes
				received from this client."
	::= { pclEntry 111 }

	pclNfsV3Read8KCalls	OBJECT-TYPE
	SYNTAX			Counter
	ACCESS			read-only
	STATUS			mandatory
	DESCRIPTION
				"The number of NFS Version 3 read calls
				with request sizes between 4K-8191 bytes
				received from this client."
	::= { pclEntry 112 }

	pclNfsV3Read16KCalls	OBJECT-TYPE
	SYNTAX			Counter
	ACCESS			read-only
	STATUS			mandatory
	DESCRIPTION
				"The number of NFS Version 3 read calls
				with request sizes between 8K-16383 bytes
				received from this client."
	::= { pclEntry 113 }

	pclNfsV3Read32KCalls	OBJECT-TYPE
	SYNTAX			Counter
	ACCESS			read-only
	STATUS			mandatory
	DESCRIPTION
				"The number of NFS Version 3 read calls
				with request sizes between 16K-32767 bytes
				received from this client."
	::= { pclEntry 114 }

	pclNfsV3Read64KCalls	OBJECT-TYPE
	SYNTAX			Counter
	ACCESS			read-only
	STATUS			mandatory
	DESCRIPTION
				"The number of NFS Version 3 read calls
				with request sizes between 32K-65535 bytes
				received from this client."
	::= { pclEntry 115 }

	pclNfsV3Read128KCalls	OBJECT-TYPE
	SYNTAX			Counter
	ACCESS			read-only
	STATUS			mandatory
	DESCRIPTION
				"The number of NFS Version 3 read calls
				with request sizes between 64K-131071 bytes
				received from this client."
	::= { pclEntry 116 }

	pclNfsV3Write512Calls	OBJECT-TYPE
	SYNTAX			Counter
	ACCESS			read-only
	STATUS			mandatory
	DESCRIPTION
				"The number of NFS Version 3 write calls
				with request sizes between 0-511 bytes
				received from this client."
	::= { pclEntry 117 }

	pclNfsV3Write1KCalls	OBJECT-TYPE
	SYNTAX			Counter
	ACCESS			read-only
	STATUS			mandatory
	DESCRIPTION
				"The number of NFS Version 3 write calls
				with request sizes between 512-1023 bytes
				received from this client."
	::= { pclEntry 118 }

	pclNfsV3Write2KCalls	OBJECT-TYPE
	SYNTAX			Counter
	ACCESS			read-only
	STATUS			mandatory
	DESCRIPTION
				"The number of NFS Version 3 write calls
				with request sizes between 1K-2047 bytes
				received from this client."
	::= { pclEntry 119 }

	pclNfsV3Write4KCalls	OBJECT-TYPE
	SYNTAX			Counter
	ACCESS			read-only
	STATUS			mandatory
	DESCRIPTION
				"The number of NFS Version 3 write calls
				with request sizes between 2K-4095 bytes
				received from this client."
	::= { pclEntry 120 }

	pclNfsV3Write8KCalls	OBJECT-TYPE
	SYNTAX			Counter
	ACCESS			read-only
	STATUS			mandatory
	DESCRIPTION
				"The number of NFS Version 3 write calls
				with request sizes between 4K-8191 bytes
				received from this client."
	::= { pclEntry 121 }

	pclNfsV3Write16KCalls	OBJECT-TYPE
	SYNTAX			Counter
	ACCESS			read-only
	STATUS			mandatory
	DESCRIPTION
				"The number of NFS Version 3 write calls
				with request sizes between 8K-16383 bytes
				received from this client."
	::= { pclEntry 122 }

	pclNfsV3Write32KCalls	OBJECT-TYPE
	SYNTAX			Counter
	ACCESS			read-only
	STATUS			mandatory
	DESCRIPTION
				"The number of NFS Version 3 write calls
				with request sizes between 16K-32767 bytes
				received from this client."
	::= { pclEntry 123 }

	pclNfsV3Write64KCalls	OBJECT-TYPE
	SYNTAX			Counter
	ACCESS			read-only
	STATUS			mandatory
	DESCRIPTION
				"The number of NFS Version 3 write calls
				with request sizes between 32K-65535 bytes
				received from this client."
	::= { pclEntry 124 }

	pclNfsV3Write128KCalls	OBJECT-TYPE
	SYNTAX			Counter
	ACCESS			read-only
	STATUS			mandatory
	DESCRIPTION
				"The number of NFS Version 3 write calls
				with request sizes between 64K-131071 bytes
				received from this client."
	::= { pclEntry 125 }


	pclNumber		OBJECT-TYPE
	SYNTAX			INTEGER
	ACCESS			read-only
	STATUS			mandatory
	DESCRIPTION
			"Number of entries in the pclTable table."

	::= { nfsPerClient 2 }



	-- the totNfs group

		-- this group contains the NFS statistics since the
		-- last boot

	trpcServ	OBJECT IDENTIFIER ::= { totNfs 1 }

	tnfsServ	OBJECT IDENTIFIER ::= { totNfs 2 }



	-- the trpcServ group

 	trpcCalls	OBJECT-TYPE
	SYNTAX		Counter
	ACCESS		read-only
	STATUS		mandatory
	DESCRIPTION
			"The total number of RPC calls received,
			 since the last boot."
	::= { trpcServ 1 }

	trpcBadCalls	OBJECT-TYPE
	SYNTAX		Counter
	ACCESS		read-only
	STATUS		mandatory
	DESCRIPTION
			"The total number of calls rejected by the RPC
			 layer, since the last boot."
	::= { trpcServ 2 }

	trpcNullRecvs	OBJECT-TYPE
	SYNTAX		Counter
	ACCESS		read-only
	STATUS		mandatory
	DESCRIPTION
			"The number of times an RPC call was not
			 available when it was thought to be received,
			 since the last boot."
	::= { trpcServ 3 }

	trpcBadLens	OBJECT-TYPE
	SYNTAX		Counter
	ACCESS		read-only
	STATUS		mandatory
	DESCRIPTION
			"The number of RPC calls received with a length
			 shorter than a minimum-sized RPC call, since
			 the last boot."
	::= { trpcServ 4 }

	trpcServXDRCalls OBJECT-TYPE
	SYNTAX		 Counter
	ACCESS		 read-only
	STATUS		 mandatory
	DESCRIPTION
			"The number of RPC calls received whose header
			 could not be XDR decoded, since the last boot."
	::= { trpcServ 5 }



	-- the tnfsServ group

	tnfsCalls	 OBJECT-TYPE
	SYNTAX		 Counter
	ACCESS		 read-only
	STATUS		 mandatory
	DESCRIPTION
			 "The total number of NFS calls received, since
			  last boot."
	::= { tnfsServ 1 }

	tnfsServBadCalls OBJECT-TYPE
	SYNTAX		 Counter
	ACCESS		 read-only
	STATUS		 mandatory
	DESCRIPTION
			 "The total number of received NFS calls rejected,
			  since last boot."
	::= { tnfsServ 2 }

	tnfsV2		OBJECT IDENTIFIER ::= { tnfsServ 3 }

	tnfsV3		OBJECT IDENTIFIER ::= { tnfsServ 4 }

	treplyCache	OBJECT IDENTIFIER ::= { tnfsServ 5 }
	
	tnfsrwStats 	OBJECT IDENTIFIER ::= { tnfsServ 6 }



	-- the tnfsV2 group

		-- this group contains statistics for NFS
		-- Version 2 calls processed since the last boot

	tv2Calls		OBJECT IDENTIFIER ::= { tnfsV2 1 }

	tv2Percent		OBJECT IDENTIFIER ::= { tnfsV2 2 }

	tv2CachedCalls		OBJECT IDENTIFIER ::= { tnfsV2 3 }

	tv2CachedPerCent	OBJECT IDENTIFIER ::= { tnfsV2 4 }
	

	-- the tv2Calls group

		-- this group contains statistics for the number of
		-- calls received for each NFS Version 2 procedure
		-- since the last boot

	tv2cNulls	OBJECT-TYPE
	SYNTAX		Counter
	ACCESS		read-only
	STATUS		mandatory
	DESCRIPTION
			"The number of NFS Version 2 calls received
			 for the NFSPROC_NULL (Do Nothing) procedure,
			 since the last boot."
	::= { tv2Calls 1 }

	tv2cGetattrs	OBJECT-TYPE
	SYNTAX		Counter
	ACCESS		read-only
	STATUS		mandatory
	DESCRIPTION
			"The number of NFS Version 2 calls received
			 for the NFSPROC_GETATTR (Get File Attributes)
			 procedure, since the last boot."
	::= { tv2Calls 2 }

	tv2cSetattrs	OBJECT-TYPE
	SYNTAX		Counter
	ACCESS		read-only
	STATUS		mandatory
	DESCRIPTION
			"The number of NFS Version 2 calls received
			 for the NFSPROC_SETATTR (Set File Attributes)
			 procedure, since the the last boot."
	::= { tv2Calls 3 }

	tv2cRoots	OBJECT-TYPE
	SYNTAX		Counter
	ACCESS		read-only
	STATUS		mandatory
	DESCRIPTION
			"The number of NFS Version 2 calls received
			 for the NFSPROC_ROOT (Get Filesystem Root)
			 procedure, since the last boot."
	::= { tv2Calls 4 }

	tv2cLookups	OBJECT-TYPE
	SYNTAX		Counter
	ACCESS		read-only
	STATUS		mandatory
	DESCRIPTION
			"The number of NFS Version 2 calls received
			 for the NFSPROC_LOOKUP (Look Up File Name)
			 procedure, since the last boot."
	::= { tv2Calls 5 }

	tv2cReadlinks	OBJECT-TYPE
	SYNTAX		Counter
	ACCESS		read-only
	STATUS		mandatory
	DESCRIPTION
			"The number of NFS Version 2 calls received
			 for the NFSPROC_READLINK (Read From Symbolic
			 Link) procedure, since the last boot."
	::= { tv2Calls 6 }

	tv2cReads	OBJECT-TYPE
	SYNTAX		Counter
	ACCESS		read-only
	STATUS		mandatory
	DESCRIPTION
			"The number of NFS Version 2 calls received
			 for the NFSPROC_READ (Read From File)
			 procedure, since the last boot."
	::= { tv2Calls 7 }

	tv2cWrcaches	OBJECT-TYPE
	SYNTAX		Counter
	ACCESS		read-only
	STATUS		mandatory
	DESCRIPTION
			"The number of NFS Version 2 calls received
			 for the NFSPROC_WRITECACHE (Write to Cache)
			 procedure, since the last boot."
	::= { tv2Calls 8 }

	tv2cWrites	OBJECT-TYPE
	SYNTAX		Counter
	ACCESS		read-only
	STATUS		mandatory
	DESCRIPTION
			"The number of NFS Version 2 calls received
			 for the NFSPROC_WRITE (Write to File)
			 procedure, since the last boot."
	::= { tv2Calls 9 }

	tv2cCreates	OBJECT-TYPE
	SYNTAX		Counter
	ACCESS		read-only
	STATUS		mandatory
	DESCRIPTION
			"The number of NFS Version 2 calls received
			 for the NFSPROC_CREATE (Create File)
			 procedure, since the last boot."
	::= { tv2Calls 10 }

	tv2cRemoves	OBJECT-TYPE
	SYNTAX		Counter
	ACCESS		read-only
	STATUS		mandatory
	DESCRIPTION
			"The number of NFS Version 2 calls received
			 for the NFSPROC_REMOVE (Remove File)
			 procedure, since the last boot."
	::= { tv2Calls 11 }

	tv2cRenames	OBJECT-TYPE
	SYNTAX		Counter
	ACCESS		read-only
	STATUS		mandatory
	DESCRIPTION
			"The number of NFS Version 2 calls received
			 for the NFSPROC_RENAME (Rename File)
			 procedure, since the last boot."
	::= { tv2Calls 12 }

	tv2cLinks	OBJECT-TYPE
	SYNTAX		Counter
	ACCESS		read-only
	STATUS		mandatory
	DESCRIPTION
			"The number of NFS Version 2 calls received
			 for the NFSPROC_LINK (Create Link to File)
			 procedure, since the last boot."
	::= { tv2Calls 13 }

	tv2cSymlinks	OBJECT-TYPE
	SYNTAX		Counter
	ACCESS		read-only
	STATUS		mandatory
	DESCRIPTION
			"The number of NFS Version 2 calls received
			 for the NFSPROC_SYMLINK (Create Symbolic Link)
			 procedure, since the last boot."
	::= { tv2Calls 14 }

	tv2cMkdirs	OBJECT-TYPE
	SYNTAX		Counter
	ACCESS		read-only
	STATUS		mandatory
	DESCRIPTION
			"The number of NFS Version 2 calls received
			 for the NFSPROC_MKDIR (Create Directory)
			 procedure, since the last boot."
	::= { tv2Calls 15 }

	tv2cRmdirs	OBJECT-TYPE
	SYNTAX		Counter
	ACCESS		read-only
	STATUS		mandatory
	DESCRIPTION
			"The number of NFS Version 2 calls received
			 for the NFSPROC_RMDIR (Remove Directory)
			 procedure, since the last boot."
	::= { tv2Calls 16 }

	tv2cReaddirs	OBJECT-TYPE
	SYNTAX		Counter
	ACCESS		read-only
	STATUS		mandatory
	DESCRIPTION
			"The number of NFS Version 2 calls received
			 for the NFSPROC_READDIR (Read From Directory)
			 procedure, since the last boot."
	::= { tv2Calls 17 }

	tv2cStatfss	OBJECT-TYPE
	SYNTAX		Counter
	ACCESS		read-only
	STATUS		mandatory
	DESCRIPTION
			"The number of NFS Version 2 calls received
			 for the NFSPROC_STATFS (Get Filesystem
			 Attributes) procedure, since the last boot."
	::= { tv2Calls 18 }



	-- the tv2Percent group

		-- this group contains statistics for the number of
		-- calls received for each NFS Version 2 procedure,
		-- as a percentage of total NFS calls received,
		-- since the last boot

	tv2pNulls	OBJECT-TYPE
	SYNTAX		INTEGER (0..100)
	ACCESS		read-only
	STATUS		mandatory
	DESCRIPTION
			"The number of NFS Version 2 calls received
			 for the NFSPROC_NULL (Do Nothing) procedure
			 as a percentage of total NFS calls received,
			 since the last boot."
	::= { tv2Percent 1 }

	tv2pGetattrs	OBJECT-TYPE
	SYNTAX		INTEGER (0..100)
	ACCESS		read-only
	STATUS		mandatory
	DESCRIPTION
			"The number of NFS Version 2 calls received
			 for the NFSPROC_GETATTR (Get File Attributes)
			 procedure as a percentage of total NFS calls
			 received, since the last boot."
	::= { tv2Percent 2 }

	tv2pSetattrs	OBJECT-TYPE
	SYNTAX		INTEGER (0..100)
	ACCESS		read-only
	STATUS		mandatory
	DESCRIPTION
			"The number of NFS Version 2 calls received
			 for the NFSPROC_SETATTR (Set File Attributes)
			 procedure as a percentage of total NFS calls
			 received, since the last boot."
	::= { tv2Percent 3 }

	tv2pRoots	OBJECT-TYPE
	SYNTAX		INTEGER (0..100)
	ACCESS		read-only
	STATUS		mandatory
	DESCRIPTION
			"The number of NFS Version 2 calls received
			 for the NFSPROC_ROOT (Get Filesystem Root)
			 procedure as a percentage of total NFS calls
			 received, since the last boot."
	::= { tv2Percent 4 }

	tv2pLookups	OBJECT-TYPE
	SYNTAX		INTEGER (0..100)
	ACCESS		read-only
	STATUS		mandatory
	DESCRIPTION
			"The number of NFS Version 2 calls received
			 for the NFSPROC_LOOKUP (Look Up File Name)
			 procedure as a percentage of total NFS calls
			 received, since the last boot."
	::= { tv2Percent 5 }

	tv2pReadlinks	OBJECT-TYPE
	SYNTAX		INTEGER (0..100)
	ACCESS		read-only
	STATUS		mandatory
	DESCRIPTION
			"The number of NFS Version 2 calls received
			 for the NFSPROC_READLINK (Read From Symbolic
			 Link) procedure as a percentage of total NFS
			 calls received, since the last boot."
	::= { tv2Percent 6 }

	tv2pReads	OBJECT-TYPE
	SYNTAX		INTEGER (0..100)
	ACCESS		read-only
	STATUS		mandatory
	DESCRIPTION
			"The number of NFS Version 2 calls received
			 for the NFSPROC_READ (Read From File)
			 procedure as a percentage of total NFS calls
			 received, since the last boot."
	::= { tv2Percent 7 }

	tv2pWrcaches	OBJECT-TYPE
	SYNTAX		INTEGER (0..100)
	ACCESS		read-only
	STATUS		mandatory
	DESCRIPTION
			"The number of NFS Version 2 calls received
			 for the NFSPROC_WRITECACHE (Write to Cache)
			 procedure as a percentage of total NFS calls
			 received, since the last boot."
	::= { tv2Percent 8 }

	tv2pWrites	OBJECT-TYPE
	SYNTAX		INTEGER (0..100)
	ACCESS		read-only
	STATUS		mandatory
	DESCRIPTION
			"The number of NFS Version 2 calls received
			 for the NFSPROC_WRITE (Write to File)
			 procedure as a percentage of total NFS calls
			 received, since the last boot."
	::= { tv2Percent 9 }

	tv2pCreates	OBJECT-TYPE
	SYNTAX		INTEGER (0..100)
	ACCESS		read-only
	STATUS		mandatory
	DESCRIPTION
			"The number of NFS Version 2 calls received
			 for the NFSPROC_CREATE (Create File)
			 procedure as a percentage of total NFS calls
			 received, since the last boot."
	::= { tv2Percent 10 }

	tv2pRemoves	OBJECT-TYPE
	SYNTAX		INTEGER (0..100)
	ACCESS		read-only
	STATUS		mandatory
	DESCRIPTION
			"The number of NFS Version 2 calls received
			 for the NFSPROC_REMOVE (Remove File)
			 procedure as a percentage of total NFS calls
			 received, since the last boot."
	::= { tv2Percent 11 }

	tv2pRenames	OBJECT-TYPE
	SYNTAX		INTEGER (0..100)
	ACCESS		read-only
	STATUS		mandatory
	DESCRIPTION
			"The number of NFS Version 2 calls received
			 for the NFSPROC_RENAME (Rename File)
			 procedure as a percentage of total NFS calls
			 received, since the last boot."
	::= { tv2Percent 12 }

	tv2pLinks	OBJECT-TYPE
	SYNTAX		INTEGER (0..100)
	ACCESS		read-only
	STATUS		mandatory
	DESCRIPTION
			"The number of NFS Version 2 calls received
			 for the NFSPROC_LINK (Create Link to File)
			 procedure as a percentage of total NFS calls
			 received, since the last boot."
	::= { tv2Percent 13 }

	tv2pSymlinks	OBJECT-TYPE
	SYNTAX		INTEGER (0..100)
	ACCESS		read-only
	STATUS		mandatory
	DESCRIPTION
			"The number of NFS Version 2 calls received
			 for the NFSPROC_SYMLINK (Create Symbolic Link)
			 procedure as a percentage of total NFS calls
			 received, since the last boot."
	::= { tv2Percent 14 }

	tv2pMkdirs	OBJECT-TYPE
	SYNTAX		INTEGER (0..100)
	ACCESS		read-only
	STATUS		mandatory
	DESCRIPTION
			"The number of NFS Version 2 calls received
			 for the NFSPROC_MKDIR (Create Directory)
			 procedure as a percentage of total NFS calls
			 received, since the last boot."
	::= { tv2Percent 15 }

	tv2pRmdirs	OBJECT-TYPE
	SYNTAX		INTEGER (0..100)
	ACCESS		read-only
	STATUS		mandatory
	DESCRIPTION
			"The number of NFS Version 2 calls received
			 for the NFSPROC_RMDIR (Remove Directory)
			 procedure as a percentage of total NFS calls
			 received, since the last boot."
	::= { tv2Percent 16 }

	tv2pReaddirs	OBJECT-TYPE
	SYNTAX		INTEGER (0..100)
	ACCESS		read-only
	STATUS		mandatory
	DESCRIPTION
			"The number of NFS Version 2 calls received
			 for the NFSPROC_READDIR (Read From Directory)
			 procedure as a percentage of total NFS calls
			 received, since the last boot."
	::= { tv2Percent 17 }

	tv2pStatfss	OBJECT-TYPE
	SYNTAX		INTEGER (0..100)
	ACCESS		read-only
	STATUS		mandatory
	DESCRIPTION
			"The number of NFS Version 2 calls received
			 for the NFSPROC_STATFS (Get Filesystem
			 Attributes) procedure as a percentage of
			 total NFS calls received, since the last boot."
	::= { tv2Percent 18 }



	-- the tv2CachedCalls group

		-- this group contains statistics for the number of
		-- calls received for each NFS Version 2 procedure,
		-- that did not result in the filesystem blocking to
		-- read from disk, since the last boot

	tv2ccNulls	OBJECT-TYPE
	SYNTAX		Counter
	ACCESS		read-only
	STATUS		mandatory
	DESCRIPTION
			"The number of NFS Version 2 calls received
			 for the NFSPROC_NULL (Do Nothing) procedure,
			 that did not result in the filesystem blocking
			 to read from disk, since the last boot."
	::= { tv2CachedCalls 1 }

	tv2ccGetattrs	OBJECT-TYPE
	SYNTAX		Counter
	ACCESS		read-only
	STATUS		mandatory
	DESCRIPTION
			"The number of NFS Version 2 calls received
			 for the NFSPROC_GETATTR (Get File Attributes)
			 procedure, that did not result in the
			 filesystem blocking to read from disk, 
			 since the last boot."
	::= { tv2CachedCalls 2 }

	tv2ccSetattrs	OBJECT-TYPE
	SYNTAX		Counter
	ACCESS		read-only
	STATUS		mandatory
	DESCRIPTION
			"The number of NFS Version 2 calls received
			 for the NFSPROC_SETATTR (Set File Attributes)
			 procedure, that did not result in the
			 filesystem blocking to read from disk,
			 since the last boot."
	::= { tv2CachedCalls 3 }

	tv2ccRoots	OBJECT-TYPE
	SYNTAX		Counter
	ACCESS		read-only
	STATUS		mandatory
	DESCRIPTION
			"The number of NFS Version 2 calls received
			 for the NFSPROC_ROOT (Get Filesystem Root)
			 procedure, that did not result in the
			 filesystem blocking to read from disk,
			 since the last boot."
	::= { tv2CachedCalls 4 }

	tv2ccLookups	OBJECT-TYPE
	SYNTAX		Counter
	ACCESS		read-only
	STATUS		mandatory
	DESCRIPTION
			"The number of NFS Version 2 calls received
			 for the NFSPROC_LOOKUP (Look Up File Name)
			 procedure, that did not result in the
			 filesystem blocking to read from disk,
			 since the last boot."
	::= { tv2CachedCalls 5 }

	tv2ccReadlinks	OBJECT-TYPE
	SYNTAX		Counter
	ACCESS		read-only
	STATUS		mandatory
	DESCRIPTION
			"The number of NFS Version 2 calls received
			 for the NFSPROC_READLINK (Read From Symbolic
			 Link) procedure, that did not result in the
			 filesystem blocking to read from disk, 
			 since the last boot."
	::= { tv2CachedCalls 6 }

	tv2ccReads	OBJECT-TYPE
	SYNTAX		Counter
	ACCESS		read-only
	STATUS		mandatory
	DESCRIPTION
			"The number of NFS Version 2 calls received
			 for the NFSPROC_READ (Read From File)
			 procedure, that did not result in the
			 filesystem blocking to read from disk,
			 since the last boot."
	::= { tv2CachedCalls 7 }

	tv2ccWrcaches	OBJECT-TYPE
	SYNTAX		Counter
	ACCESS		read-only
	STATUS		mandatory
	DESCRIPTION
			"The number of NFS Version 2 calls received
			 for the NFSPROC_WRITECACHE (Write to Cache)
			 procedure, that did not result in the
			 filesystem blocking to read from disk,
			 since the last boot."
	::= { tv2CachedCalls 8 }

	tv2ccWrites	OBJECT-TYPE
	SYNTAX		Counter
        ACCESS		read-only
	STATUS		mandatory
	DESCRIPTION
			"The number of NFS Version 2 calls received
			 for the NFSPROC_WRITE (Write to File)
			 procedure, that did not result in the
			 filesystem blocking to read from disk,
			 since the last boot."
	::= { tv2CachedCalls 9 }

	tv2ccCreates	OBJECT-TYPE
	SYNTAX		Counter
	ACCESS		read-only
	STATUS		mandatory
	DESCRIPTION
			"The number of NFS Version 2 calls received
			 for the NFSPROC_CREATE (Create File)
			 procedure, that did not result in the
			 filesystem blocking to read from disk,
			 since the last boot."
	::= { tv2CachedCalls 10 }

	tv2ccRemoves	OBJECT-TYPE
	SYNTAX		Counter
	ACCESS		read-only
	STATUS		mandatory
	DESCRIPTION
			"The number of NFS Version 2 calls received
			 for the NFSPROC_REMOVE (Remove File)
			 procedure, that did not result in the
			 filesystem blocking to read from disk,
			 since the last boot."
	::= { tv2CachedCalls 11 }

	tv2ccRenames	OBJECT-TYPE
	SYNTAX		Counter
	ACCESS		read-only
	STATUS		mandatory
	DESCRIPTION
			"The number of NFS Version 2 calls received
			 for the NFSPROC_RENAME (Rename File)
			 procedure, that did not result in the
			 filesystem blocking to read from disk,
			 since the last boot."
	::= { tv2CachedCalls 12 }

	tv2ccLinks	OBJECT-TYPE
	SYNTAX		Counter
	ACCESS		read-only
	STATUS		mandatory
	DESCRIPTION
			"The number of NFS Version 2 calls received
			 for the NFSPROC_LINK (Create Link to File)
			 procedure, that did not result in the
			 filesystem blocking to read from disk,
			 since the last boot."
	::= { tv2CachedCalls 13 }

	tv2ccSymlinks	OBJECT-TYPE
	SYNTAX		Counter
	ACCESS		read-only
	STATUS		mandatory
	DESCRIPTION
			"The number of NFS Version 2 calls received
			 for the NFSPROC_SYMLINK (Create Symbolic Link)
			 procedure, that did not result in the
			 filesystem blocking to read from disk,
			 since the last boot."
	::= { tv2CachedCalls 14 }

	tv2ccMkdirs	OBJECT-TYPE
	SYNTAX		Counter
	ACCESS		read-only
	STATUS		mandatory
	DESCRIPTION
			"The number of NFS Version 2 calls received
			 for the NFSPROC_MKDIR (Create Directory)
			 procedure, that did not result in the
			 filesystem blocking to read from disk,
			 since the last boot."
	::= { tv2CachedCalls 15 }

	tv2ccRmdirs	OBJECT-TYPE
	SYNTAX		Counter
	ACCESS		read-only
	STATUS		mandatory
	DESCRIPTION
			"The number of NFS Version 2 calls received
			 for the NFSPROC_RMDIR (Remove Directory)
			 procedure, that did not result in the
			 filesystem blocking to read from disk,
			 since the last boot."
	::= { tv2CachedCalls 16 }

	tv2ccReaddirs	OBJECT-TYPE
	SYNTAX		Counter
	ACCESS		read-only
	STATUS		mandatory
	DESCRIPTION
			"The number of NFS Version 2 calls received
			 for the NFSPROC_READDIR (Read From Directory)
			 procedure, that did not result in the
			 filesystem blocking to read from disk,
			 since the last boot."
	::= { tv2CachedCalls 17 }

	tv2ccStatfss	OBJECT-TYPE
	SYNTAX		Counter
	ACCESS		read-only
	STATUS		mandatory
	DESCRIPTION
			"The number of NFS Version 2 calls received
			 for the NFSPROC_STATFS (Get Filesystem
			 Attributes) procedure, that did not result
			 in the filesystem blocking to read from disk,
			 since the last boot."
	::= { tv2CachedCalls 18 }



	-- the tv2CachedPerCent group

		-- this group contains statistics for the number of
		-- calls received for each NFS Version 2 procedure,
		-- that did not result in the filesystem blocking to
		-- read from disk, as a percentage of the total
		-- number of calls received for that procedure,
		-- since the last boot

	tv2cpNulls	OBJECT-TYPE
	SYNTAX		INTEGER (0..100)
	ACCESS		read-only
	STATUS		mandatory
	DESCRIPTION
			"The number of NFS Version 2 calls received
			 for the NFSPROC_NULL (Do Nothing) procedure,
			 that did not result in the filesystem
			 blocking to read from disk, as a percentage
			 of the total number of calls received for
			 this procedure, since the last boot."
	::= { tv2CachedPerCent 1 }

	tv2cpGetattrs	OBJECT-TYPE
	SYNTAX		INTEGER (0..100)
	ACCESS		read-only
	STATUS		mandatory
	DESCRIPTION
			"The number of NFS Version 2 calls received
			 for the NFSPROC_GETATTR (Get File Attributes)
			 procedure, that did not result in the
			 filesystem blocking to read from disk, as a
			 percentage of the total number of calls
			 received for this procedure, since the last boot."
	::= { tv2CachedPerCent 2 }

	tv2cpSetattrs	OBJECT-TYPE
	SYNTAX		INTEGER (0..100)
	ACCESS		read-only
	STATUS		mandatory
	DESCRIPTION
			"The number of NFS Version 2 calls received
			 for the NFSPROC_SETATTR (Set File Attributes)
			 procedure, that did not result in the
			 filesystem blocking to read from disk, as a
			 percentage of the total number of calls
			 received for this procedure, since the last boot."
	::= { tv2CachedPerCent 3 }

	tv2cpRoots	OBJECT-TYPE
	SYNTAX		INTEGER (0..100)
	ACCESS		read-only
	STATUS		mandatory
	DESCRIPTION
			"The number of NFS Version 2 calls received
			 for the NFSPROC_ROOT (Get Filesystem Root)
			 procedure, that did not result in the
			 filesystem blocking to read from disk, as a
			 percentage of the total number of calls
			 received for this procedure, since the last boot."
	::= { tv2CachedPerCent 4 }

	tv2cpLookups	OBJECT-TYPE
	SYNTAX		INTEGER (0..100)
	ACCESS		read-only
	STATUS		mandatory
	DESCRIPTION
			"The number of NFS Version 2 calls received
			 for the NFSPROC_LOOKUP (Look Up File Name)
			 procedure, that did not result in the
			 filesystem blocking to read from disk, as a
			 percentage of the total number of calls
			 received for this procedure, since the last boot."
	::= { tv2CachedPerCent 5 }

	tv2cpReadlinks	OBJECT-TYPE
	SYNTAX		INTEGER (0..100)
	ACCESS		read-only
	STATUS		mandatory
	DESCRIPTION
			"The number of NFS Version 2 calls received
			 for the NFSPROC_READLINK (Read From Symbolic
			 Link) procedure, that did not result in the
			 filesystem blocking to read from disk, as a
			 percentage of the total number of calls
			 received for this procedure, since the last boot."
	::= { tv2CachedPerCent 6 }

	tv2cpReads	OBJECT-TYPE
	SYNTAX		INTEGER (0..100)
	ACCESS		read-only
	STATUS		mandatory
	DESCRIPTION
			"The number of NFS Version 2 calls received
			 for the NFSPROC_READ (Read From File)
			 procedure, that did not result in the
			 filesystem blocking to read from disk, as a
			 percentage of the total number of calls
			 received for this procedure, since the last boot."
	::= { tv2CachedPerCent 7 }

	tv2cpWrcaches	OBJECT-TYPE
	SYNTAX		INTEGER (0..100)
	ACCESS		read-only
	STATUS		mandatory
	DESCRIPTION
			"The number of NFS Version 2 calls received
			 for the NFSPROC_WRITECACHE (Write to Cache)
			 procedure, that did not result in the
			 filesystem blocking to read from disk, as a
			 percentage of the total number of calls
			 received for this procedure, since the last boot."
	::= { tv2CachedPerCent 8 }

	tv2cpWrites	OBJECT-TYPE
	SYNTAX		INTEGER (0..100)
	ACCESS		read-only
	STATUS		mandatory
	DESCRIPTION
			"The number of NFS Version 2 calls received
			 for the NFSPROC_WRITE (Write to File)
			 procedure, that did not result in the
			 filesystem blocking to read from disk, as a
			 percentage of the total number of calls
			 received for this procedure, since the last boot."
	::= { tv2CachedPerCent 9 }

	tv2cpCreates	OBJECT-TYPE
	SYNTAX          INTEGER (0..100)
	ACCESS		read-only
	STATUS		mandatory
	DESCRIPTION
			"The number of NFS Version 2 calls received
			 for the NFSPROC_CREATE (Create File)
			 procedure, that did not result in the
			 filesystem blocking to read from disk, as a
			 percentage of the total number of calls
			 received for this procedure, since the last boot."
	::= { tv2CachedPerCent 10 }

	tv2cpRemoves	OBJECT-TYPE
	SYNTAX		INTEGER (0..100)
	ACCESS		read-only
	STATUS		mandatory
	DESCRIPTION
			"The number of NFS Version 2 calls received
			 for the NFSPROC_REMOVE (Remove File)
			 procedure, that did not result in the
			 filesystem blocking to read from disk, as a
			 percentage of the total number of calls
			 received for this procedure, since the last boot."
	::= { tv2CachedPerCent 11 }

	tv2cpRenames	OBJECT-TYPE
	SYNTAX		INTEGER (0..100)
	ACCESS		read-only
	STATUS		mandatory
	DESCRIPTION
			"The number of NFS Version 2 calls received
			 for the NFSPROC_RENAME (Rename File)
			 procedure, that did not result in the
			 filesystem blocking to read from disk, as a
			 percentage of the total number of calls
			 received for this procedure, since the last boot."
	::= { tv2CachedPerCent 12 }

	tv2cpLinks	OBJECT-TYPE
	SYNTAX		INTEGER (0..100)
	ACCESS		read-only
	STATUS		mandatory
	DESCRIPTION
			"The number of NFS Version 2 calls received
			 for the NFSPROC_LINK (Create Link to File)
			 procedure, that did not result in the
			 filesystem blocking to read from disk, as a
			 percentage of the total number of calls
			 received for this procedure, since the last boot."
	::= { tv2CachedPerCent 13 }

	tv2cpSymlinks	OBJECT-TYPE
	SYNTAX		INTEGER (0..100)
	ACCESS		read-only
	STATUS		mandatory
	DESCRIPTION
			"The number of NFS Version 2 calls received
			 for the NFSPROC_SYMLINK (Create Symbolic
			 Link) procedure, that did not result in the
			 filesystem blocking to read from disk, as a
			 percentage of the total number of calls
			 received for this procedure, since the last boot."
	::= { tv2CachedPerCent 14 }

	tv2cpMkdirs	OBJECT-TYPE
	SYNTAX		INTEGER (0..100)
	ACCESS		read-only
	STATUS		mandatory
	DESCRIPTION
			"The number of NFS Version 2 calls received
			 for the NFSPROC_MKDIR (Create Directory)
			 procedure, that did not result in the
			 filesystem blocking to read from disk, as a
			 percentage of the total number of calls
			 received for this procedure, since the last boot."
	::= { tv2CachedPerCent 15 }

	tv2cpRmdirs	OBJECT-TYPE
	SYNTAX		INTEGER (0..100)
	ACCESS		read-only
	STATUS		mandatory
	DESCRIPTION
			"The number of NFS Version 2 calls received
			 for the NFSPROC_RMDIR (Remove Directory)
			 procedure, that did not result in the
			 filesystem blocking to read from disk, as a
			 percentage of the total number of calls
			 received for this procedure, since the last boot."
	::= { tv2CachedPerCent 16 }

	tv2cpReaddirs	OBJECT-TYPE
	SYNTAX		INTEGER (0..100)
	ACCESS		read-only
	STATUS		mandatory
	DESCRIPTION
			"The number of NFS Version 2 calls received
			 for the NFSPROC_READDIR (Read From Directory)
			 procedure, that did not result in the
			 filesystem blocking to read from disk, as a
			 percentage of the total number of calls
			 received for this procedure, since the last boot."
	::= { tv2CachedPerCent 17 }

	tv2cpStatfss	OBJECT-TYPE
	SYNTAX		INTEGER (0..100)
	ACCESS		read-only
	STATUS		mandatory
	DESCRIPTION
			"The number of NFS Version 2 calls received
			 for the NFSPROC_STATFS (Get Filesystem
			 Attributes) procedure, that did not result
			 in the filesystem blocking to read from
			 disk, as a percentage of the total number
			 of calls received for this procedure, 
			 since the last boot."
	::= { tv2CachedPerCent 18 }


	-- the tnfsV3 group

		-- this group contains statistics for NFS
		-- Version 3 calls processed since the last boot

	tv3Calls		OBJECT IDENTIFIER ::= { tnfsV3 1 }

	tv3Percent		OBJECT IDENTIFIER ::= { tnfsV3 2 }

	tv3CachedCalls		OBJECT IDENTIFIER ::= { tnfsV3 3 }

	tv3CachedPerCent	OBJECT IDENTIFIER ::= { tnfsV3 4 }
	

	-- the tv3Calls group

		-- this group contains statistics for the number of
		-- calls received for each NFS Version 3 procedure
		-- since the last boot

	tv3cNulls	OBJECT-TYPE
	SYNTAX		Counter
	ACCESS		read-only
	STATUS		mandatory
	DESCRIPTION
			"The number of NFS Version 3 calls received
			 for the NFSPROC3_NULL (Do Nothing) procedure,
			 since the last boot."
	::= { tv3Calls 1 }

	tv3cGetattrs	OBJECT-TYPE
	SYNTAX		Counter
	ACCESS		read-only
	STATUS		mandatory
	DESCRIPTION
			"The number of NFS Version 3 calls received
			 for the NFSPROC3_GETATTR (Get File Attributes)
			 procedure, since the last boot."
	::= { tv3Calls 2 }

	tv3cSetattrs	OBJECT-TYPE
	SYNTAX		Counter
	ACCESS		read-only
	STATUS		mandatory
	DESCRIPTION
			"The number of NFS Version 3 calls received
			 for the NFSPROC3_SETATTR (Set File Attributes)
			 procedure, since the last boot."
	::= { tv3Calls 3 }

	tv3cLookups	OBJECT-TYPE
	SYNTAX		Counter
	ACCESS		read-only
	STATUS		mandatory
	DESCRIPTION
			"The number of NFS Version 3 calls received
			 for the NFSPROC3_LOOKUP (Lookup Filename)
			 procedure, since the last boot."
	::= { tv3Calls 4 }

	tv3cAccesss	OBJECT-TYPE
	SYNTAX		Counter
	ACCESS		read-only
	STATUS		mandatory
	DESCRIPTION
			"The number of NFS Version 3 calls received
			 for the NFSPROC3_ACCESS (Check Access Permission)
			 procedure, since the last boot."
	::= { tv3Calls 5 }

	tv3cReadlinks	OBJECT-TYPE
	SYNTAX		Counter
	ACCESS		read-only
	STATUS		mandatory
	DESCRIPTION
			"The number of NFS Version 3 calls received
			 for the NFSPROC3_READLINK (Read from Symbolic
			 Link) procedure, since the last boot."
	::= { tv3Calls 6 }

	tv3cReads	OBJECT-TYPE
	SYNTAX		Counter
	ACCESS		read-only
	STATUS		mandatory
	DESCRIPTION
			"The number of NFS Version 3 calls received
			 for the NFSPROC3_READ (Read From File)
			 procedure, since the last boot."
	::= { tv3Calls 7 }

	tv3cWrites	OBJECT-TYPE
	SYNTAX		Counter
	ACCESS		read-only
	STATUS		mandatory
	DESCRIPTION
			"The number of NFS Version 3 calls received
			 for the NFSPROC3_WRITE (Write to File)
			 procedure, since the last boot."
	::= { tv3Calls 8 }

	tv3cCreates	OBJECT-TYPE
	SYNTAX		Counter
	ACCESS		read-only
	STATUS		mandatory
	DESCRIPTION
			"The number of NFS Version 3 calls received
			 for the NFSPROC3_CREATE (Create a File)
			 procedure, since the last boot."
	::= { tv3Calls 9 }

	tv3cMkdirs	OBJECT-TYPE
	SYNTAX		Counter
	ACCESS		read-only
	STATUS		mandatory
	DESCRIPTION
			"The number of NFS Version 3 calls received
			 for the NFSPROC3_MKDIR (Create a Directory)
			 procedure, since the last boot."
	::= { tv3Calls 10 }

	tv3cSymlinks	OBJECT-TYPE
	SYNTAX		Counter
	ACCESS		read-only
	STATUS		mandatory
	DESCRIPTION
			"The number of NFS Version 3 calls received
			 for the NFSPROC3_SYMLINK (Create a Symbolic
			 Link) procedure, since the last boot."
	::= { tv3Calls 11 }

	tv3cMknods	OBJECT-TYPE
	SYNTAX		Counter
	ACCESS		read-only
	STATUS		mandatory
	DESCRIPTION
			"The number of NFS Version 3 calls received
			 for the NFSPROC3_MKNOD (Create a Special
			 Device) procedure, since the last boot."
	::= { tv3Calls 12 }

	tv3cRemoves	OBJECT-TYPE
	SYNTAX		Counter
	ACCESS		read-only
	STATUS		mandatory
	DESCRIPTION
			"The number of NFS Version 3 calls received
			 for the NFSPROC3_REMOVE (Remove a File)
			 procedure, since the last boot."
	::= { tv3Calls 13 }

	tv3cRmdirs	OBJECT-TYPE
	SYNTAX		Counter
	ACCESS		read-only
	STATUS		mandatory
	DESCRIPTION
			"The number of NFS Version 3 calls received
			 for the NFSPROC3_RMDIR (Remove a Directory)
			 procedure, since the last boot."
	::= { tv3Calls 14 }

	tv3cRenames	OBJECT-TYPE
	SYNTAX		Counter
	ACCESS		read-only
	STATUS		mandatory
	DESCRIPTION
			"The number of NFS Version 3 calls received
			 for the NFSPROC3_RENAME (Rename a File or
			 Directory) procedure, since the last boot."
	::= { tv3Calls 15 }

	tv3cLinks	OBJECT-TYPE
	SYNTAX		Counter
	ACCESS		read-only
	STATUS		mandatory
	DESCRIPTION
			"The number of NFS Version 3 calls received
			 for the NFSPROC3_LINK (Create Link to an
			 Object) procedure, since the last boot."
	::= { tv3Calls 16 }

	tv3cReaddirs	OBJECT-TYPE
	SYNTAX		Counter
	ACCESS		read-only
	STATUS		mandatory
	DESCRIPTION
			"The number of NFS Version 3 calls received
			 for the NFSPROC3_READDIR (Read From Directory)
			 procedure, since the last boot."
	::= { tv3Calls 17 }

	tv3cReaddirPluss OBJECT-TYPE
	SYNTAX		 Counter
	ACCESS		 read-only
	STATUS		 mandatory
	DESCRIPTION
			"The number of NFS Version 3 calls received
			 for the NFSPROC3_READDIRPLUS (Extended Read
			 from Directory) procedure, since the last boot."
	::= { tv3Calls 18 }

	tv3cFsstats	OBJECT-TYPE
	SYNTAX		Counter
	ACCESS		read-only
	STATUS		mandatory
	DESCRIPTION
			"The number of NFS Version 3 calls received
			 for the NFSPROC3_FSSTAT (Get Dynamic File
			 System Information) procedure, since the
			 last boot."
	::= { tv3Calls 19 }

	tv3cFsinfos	OBJECT-TYPE
	SYNTAX		Counter
	ACCESS		read-only
	STATUS		mandatory
	DESCRIPTION
			"The number of NFS Version 3 calls received
			 for the NFSPROC3_FSINFO (Get Static File System
			 Information) procedure, since the last boot."
	::= { tv3Calls 20 }

	tv3cPathconfs	OBJECT-TYPE
	SYNTAX		Counter
	ACCESS		read-only
	STATUS		mandatory
	DESCRIPTION
			"The number of NFS Version 3 calls received
			 for the NFSPROC3_PATHCONF (Retrieve POSIX
			 Information) procedure, since the last boot."
	::= { tv3Calls 21 }

	tv3cCommits	OBJECT-TYPE
	SYNTAX		Counter
	ACCESS		read-only
	STATUS		mandatory
	DESCRIPTION
			"The number of NFS Version 3 calls received
			 for the NFSPROC3_COMMIT (Commit Cached Data on
			 a Server to Stable Storage) procedure, since
			 the last boot."
	::= { tv3Calls 22 }



	-- the tv3Percent group

		-- this group contains statistics for the number of
		-- calls received for each NFS Version 3 procedure,
		-- as a percentage of total NFS calls received,
		-- since the last boot

	tv3pNulls	OBJECT-TYPE
	SYNTAX		INTEGER (0..100)
	ACCESS		read-only
	STATUS		mandatory
	DESCRIPTION
			"The number of NFS Version 3 calls received
			 for the NFSPROC3_NULL (Do Nothing) procedure,
			 as a percentage of the total NFS calls
			 received, since the last boot."
	::= { tv3Percent 1 }

	tv3pGetattrs	OBJECT-TYPE
	SYNTAX		INTEGER (0..100)
	ACCESS		read-only
	STATUS		mandatory
	DESCRIPTION
			"The number of NFS Version 3 calls received
			 for the NFSPROC3_GETATTR (Get File Attributes)
			 procedure, as a percentage of the total NFS
			 calls received, since the last boot."
	::= { tv3Percent 2 }

	tv3pSetattrs	OBJECT-TYPE
	SYNTAX		INTEGER (0..100)
	ACCESS		read-only
	STATUS		mandatory
	DESCRIPTION
			"The number of NFS Version 3 calls received
			 for the NFSPROC3_SETATTR (Set File Attributes)
			 procedure, as a percentage of the total NFS
			 calls received, since the last boot."
	::= { tv3Percent 3 }

	tv3pLookups	OBJECT-TYPE
	SYNTAX		INTEGER (0..100)
	ACCESS		read-only
	STATUS		mandatory
	DESCRIPTION
			"The number of NFS Version 3 calls received
			 for the NFSPROC3_LOOKUP (Lookup Filename)
			 procedure, as a percentage of the total NFS
			 calls received, since the last boot."
	::= { tv3Percent 4 }

	tv3pAccesss	OBJECT-TYPE
	SYNTAX		INTEGER (0..100)
	ACCESS		read-only
	STATUS		mandatory
	DESCRIPTION
			"The number of NFS Version 3 calls received
			 for the NFSPROC3_ACCESS (Check Access
			 Permission) procedure, as a percentage of
			 the total NFS calls received, since the last boot."
	::= { tv3Percent 5 }

	tv3pReadlinks	OBJECT-TYPE
	SYNTAX		INTEGER (0..100)
	ACCESS		read-only
	STATUS		mandatory
	DESCRIPTION
			"The number of NFS Version 3 calls received
			 for the NFSPROC3_READLINK (Read from Symbolic
			 Link) procedure, as a percentage of the total
			 NFS calls received, since the last boot."
	::= { tv3Percent 6 }

	tv3pReads	OBJECT-TYPE
	SYNTAX		INTEGER (0..100)
	ACCESS		read-only
	STATUS		mandatory
	DESCRIPTION
			"The number of NFS Version 3 calls received
			 for the NFSPROC3_READ (Read From File)
			 procedure, as a percentage of the total NFS
			 calls received, since the last boot."
	::= { tv3Percent 7 }

	tv3pWrites	OBJECT-TYPE
	SYNTAX		INTEGER (0..100)
	ACCESS		read-only
	STATUS		mandatory
	DESCRIPTION
			"The number of NFS Version 3 calls received
			 for the NFSPROC3_WRITE (Write to File)
			 procedure, as a percentage of the total NFS
			 calls received, since the last boot."
	::= { tv3Percent 8 }

	tv3pCreates	OBJECT-TYPE
	SYNTAX		INTEGER (0..100)
	ACCESS		read-only
	STATUS		mandatory
	DESCRIPTION
			"The number of NFS Version 3 calls received
			 for the NFSPROC3_CREATE (Create a File)
			 procedure, as a percentage of the total NFS
			 calls received, since the last boot."
	::= { tv3Percent 9 }

	tv3pMkdirs	OBJECT-TYPE
	SYNTAX		INTEGER (0..100)
	ACCESS		read-only
	STATUS		mandatory
	DESCRIPTION
			"The number of NFS Version 3 calls received
			 for the NFSPROC3_MKDIR (Create a Directory)
			 procedure, as a percentage of the total NFS
			 calls received, since the last boot."
	::= { tv3Percent 10 }

	tv3pSymlinks	OBJECT-TYPE
	SYNTAX		INTEGER (0..100)
	ACCESS		read-only
	STATUS		mandatory
	DESCRIPTION
			"The number of NFS Version 3 calls received
			 for the NFSPROC3_SYMLINK (Create a Symbolic
			 Link) procedure, as a percentage of the total
			 NFS calls received, since the last boot."
	::= { tv3Percent 11 }

	tv3pMknods	OBJECT-TYPE
	SYNTAX		INTEGER (0..100)
	ACCESS		read-only
	STATUS		mandatory
	DESCRIPTION
			"The number of NFS Version 3 calls received
			 for the NFSPROC3_MKNOD (Create a Special
			 Device) procedure, as a percentage of the
			 total NFS calls received, since the last boot."
	::= { tv3Percent 12 }

	tv3pRemoves	OBJECT-TYPE
	SYNTAX		INTEGER (0..100)
	ACCESS		read-only
	STATUS		mandatory
	DESCRIPTION
			"The number of NFS Version 3 calls received
			 for the NFSPROC3_REMOVE (Remove a File)
			 procedure, as a percentage of the total NFS
			 calls received, since the last boot."
	::= { tv3Percent 13 }

	tv3pRmdirs	OBJECT-TYPE
	SYNTAX		INTEGER (0..100)
	ACCESS		read-only
	STATUS		mandatory
	DESCRIPTION
			"The number of NFS Version 3 calls received
			 for the NFSPROC3_RMDIR (Remove a Directory)
			 procedure, as a percentage of the total NFS
			 calls received, since the last boot."
	::= { tv3Percent 14 }

	tv3pRenames	OBJECT-TYPE
	SYNTAX		INTEGER (0..100) ACCESS          read-only
	STATUS		mandatory
	DESCRIPTION
			"The number of NFS Version 3 calls received
			 for the NFSPROC3_RENAME (Rename a File or
			 Directory) procedure, as a percentage of
			 the total NFS calls received, since the
			 last boot."
	::= { tv3Percent 15 }

	tv3pLinks	OBJECT-TYPE
	SYNTAX		INTEGER (0..100)
	ACCESS		read-only
	STATUS		mandatory
	DESCRIPTION
			"The number of NFS Version 3 calls received
			 for the NFSPROC3_LINK (Create Link to an
			 Object) procedure, as a percentage of
			 the total NFS calls received, since the
			 last boot."
	::= { tv3Percent 16 }

	tv3pReaddirs	OBJECT-TYPE
	SYNTAX		INTEGER (0..100)
	ACCESS		read-only
	STATUS		mandatory
	DESCRIPTION
			"The number of NFS Version 3 calls received
			 for the NFSPROC3_READDIR (Read From Directory)
			 procedure, as a percentage of the total NFS
			 calls received, since the last boot."
	::= { tv3Percent 17 }

	tv3pReaddirPluss OBJECT-TYPE
	SYNTAX		 INTEGER (0..100)
	ACCESS		 read-only
	STATUS		 mandatory
	DESCRIPTION
			"The number of NFS Version 3 calls received
			 for the NFSPROC3_READDIRPLUS (Extended Read
			 from Directory) procedure, as a percentage
			 of the total NFS calls received, since the
			 last boot."
	::= { tv3Percent 18 }

	tv3pFsstats	OBJECT-TYPE
	SYNTAX		INTEGER (0..100)
	ACCESS		read-only
	STATUS		mandatory
	DESCRIPTION
			"The number of NFS Version 3 calls received
			 for the NFSPROC3_FSSTAT (Get Dynamic File
			 System Information) procedure, as a percentage
			 of the total NFS calls received, since the
			 last boot."
	::= { tv3Percent 19 }

	tv3pFsinfos	OBJECT-TYPE
	SYNTAX		INTEGER (0..100)
	ACCESS		read-only
	STATUS		mandatory
	DESCRIPTION
			"The number of NFS Version 3 calls received
			 for the NFSPROC3_FSINFO (Get Static File System
			 Information) procedure, as a percentage of the
			 total NFS calls received, since the last boot."
	::= { tv3Percent 20 }

	tv3pPathconfs	OBJECT-TYPE
	SYNTAX		INTEGER (0..100)
	ACCESS		read-only
	STATUS		mandatory
	DESCRIPTION
			"The number of NFS Version 3 calls received
			 for the NFSPROC3_PATHCONF (Retrieve POSIX
			 Information) procedure, as a percentage of the
			 total NFS calls received, since the last boot."
	::= { tv3Percent 21 }

	tv3pCommits	OBJECT-TYPE
	SYNTAX		INTEGER (0..100)
	ACCESS		read-only
	STATUS		mandatory
	DESCRIPTION
			"The number of NFS Version 3 calls received
			 for the NFSPROC3_COMMIT (Commit Cached Data on
			 a Server to Stable Storage) procedure, as a
			 percentage of the total NFS calls received,
			 since the last boot."
	::= { tv3Percent 22 }



	-- the tv3CachedCalls group

		-- this group contains statistics for the number of
		-- calls received for each NFS Version 3 procedure,
		-- that did not result in the filesystem blocking to
		-- read from disk, since the last boot

	tv3ccNulls	OBJECT-TYPE
	SYNTAX		Counter
	ACCESS		read-only
	STATUS		mandatory
	DESCRIPTION
			"The number of NFS Version 3 calls received
			 for the NFSPROC3_NULL (Do Nothing) procedure,
			 that did not result in the filesystem blocking
			 to read from disk, since the last boot."
	::= { tv3CachedCalls 1 }

	tv3ccGetattrs	OBJECT-TYPE
	SYNTAX		Counter
	ACCESS		read-only
	STATUS		mandatory
	DESCRIPTION
			"The number of NFS Version 3 calls received
			 for the NFSPROC3_GETATTR (Get File Attributes)
			 procedure, that did not result in the filesystem
			 blocking to read from disk, since the last boot."
	::= { tv3CachedCalls 2 }

	tv3ccSetattrs	OBJECT-TYPE
	SYNTAX		Counter
	ACCESS		read-only
	STATUS		mandatory
	DESCRIPTION
			"The number of NFS Version 3 calls received
			 for the NFSPROC3_SETATTR (Set File Attributes)
			 procedure, that did not result in the filesystem
			 blocking to read from disk, since the last boot."
	::= { tv3CachedCalls 3 }

	tv3ccLookups	OBJECT-TYPE
	SYNTAX		Counter
	ACCESS		read-only
	STATUS		mandatory
	DESCRIPTION
			"The number of NFS Version 3 calls received
			 for the NFSPROC3_LOOKUP (Lookup Filename)
			 procedure, that did not result in the filesystem
			 blocking to read from disk, since the last boot."
	::= { tv3CachedCalls 4 }

	tv3ccAccesss	OBJECT-TYPE
	SYNTAX		Counter
	ACCESS		read-only
	STATUS		mandatory
	DESCRIPTION
			"The number of NFS Version 3 calls received
			 for the NFSPROC3_ACCESS (Check Access Permission)
			 procedure, that did not result in the filesystem
			 blocking to read from disk, since the last boot."
	::= { tv3CachedCalls 5 }

	tv3ccReadlinks	OBJECT-TYPE
	SYNTAX		Counter
	ACCESS		read-only
	STATUS		mandatory
	DESCRIPTION
			"The number of NFS Version 3 calls received
			 for the NFSPROC3_READLINK (Read from Symbolic
			 Link) procedure, that did not result in the
			 filesystem blocking to read from disk, since
			 the last boot."
	::= { tv3CachedCalls 6 }

	tv3ccReads	OBJECT-TYPE
	SYNTAX		Counter
	ACCESS		read-only
	STATUS		mandatory
	DESCRIPTION
			"The number of NFS Version 3 calls received
			 for the NFSPROC3_READ (Read From File)
			 procedure, that did not result in the filesystem
			 blocking to read from disk, since the last boot."
	::= { tv3CachedCalls 7 }

	tv3ccWrites	OBJECT-TYPE
	SYNTAX		Counter
	ACCESS		read-only
	STATUS		mandatory
	DESCRIPTION
			"The number of NFS Version 3 calls received
			 for the NFSPROC3_WRITE (Write to File)
			 procedure, that did not result in the filesystem
			 blocking to read from disk, since the last boot."
	::= { tv3CachedCalls 8 }

	tv3ccCreates	OBJECT-TYPE
	SYNTAX		Counter
	ACCESS		read-only
	STATUS		mandatory
	DESCRIPTION
			"The number of NFS Version 3 calls received
			 for the NFSPROC3_CREATE (Create a File)
			 procedure, that did not result in the filesystem
			 blocking to read from disk, since the last boot."
	::= { tv3CachedCalls 9 }

	tv3ccMkdirs	OBJECT-TYPE
	SYNTAX		Counter
	ACCESS		read-only
	STATUS		mandatory
	DESCRIPTION
			"The number of NFS Version 3 calls received
			 for the NFSPROC3_MKDIR (Create a Directory)
			 procedure, that did not result in the filesystem
			 blocking to read from disk, since the last boot."
	::= { tv3CachedCalls 10 }

	tv3ccSymlinks	OBJECT-TYPE
	SYNTAX		Counter
	ACCESS		read-only
	STATUS		mandatory
	DESCRIPTION
			"The number of NFS Version 3 calls received
			 for the NFSPROC3_SYMLINK (Create a Symbolic
			 Link) procedure, that did not result in the
			 filesystem blocking to read from disk, since
			 the last boot."
	::= { tv3CachedCalls 11 }

	tv3ccMknods	OBJECT-TYPE
	SYNTAX		Counter
	ACCESS		read-only
	STATUS		mandatory
	DESCRIPTION
			"The number of NFS Version 3 calls received
			 for the NFSPROC3_MKNOD (Create a Special
			 Device) procedure, that did not result in the
			 filesystem blocking to read from disk, since
			 the last boot."
	::= { tv3CachedCalls 12 }

	tv3ccRemoves	OBJECT-TYPE
	SYNTAX		Counter
	ACCESS		read-only
	STATUS		mandatory
	DESCRIPTION
			"The number of NFS Version 3 calls received
			 for the NFSPROC3_REMOVE (Remove a File)
			 procedure, that did not result in the
			 filesystem blocking to read from disk, 
			 since the last boot."
	::= { tv3CachedCalls 13 }

	tv3ccRmdirs	OBJECT-TYPE
	SYNTAX		Counter
	ACCESS		read-only
	STATUS		mandatory
	DESCRIPTION
			"The number of NFS Version 3 calls received
			 for the NFSPROC3_RMDIR (Remove a Directory)
			 procedure, that did not result in the
			 filesystem blocking to read from disk,
			 since the last boot."
	::= { tv3CachedCalls 14 }

	tv3ccRenames	OBJECT-TYPE
	SYNTAX		Counter
	ACCESS		read-only
	STATUS		mandatory
	DESCRIPTION
			"The number of NFS Version 3 calls received
			 for the NFSPROC3_RENAME (Rename a File or
			 Directory) procedure, that did not result in
			 the filesystem blocking to read from disk,
			 since the last boot."
	::= { tv3CachedCalls 15 }

	tv3ccLinks	OBJECT-TYPE
	SYNTAX		Counter
	ACCESS		read-only
	STATUS		mandatory
	DESCRIPTION
			"The number of NFS Version 3 calls received
			 for the NFSPROC3_LINK (Create Link to an
			 Object) procedure, that did not result in
			 the filesystem blocking to read from disk, 
			 since the last boot."
	::= { tv3CachedCalls 16 }

	tv3ccReaddirs	OBJECT-TYPE
	SYNTAX		Counter
	ACCESS		read-only
	STATUS		mandatory
	DESCRIPTION
			"The number of NFS Version 3 calls received
			 for the NFSPROC3_READDIR (Read From
			 Directory) procedure, that did not result in
			 the filesystem blocking to read from disk, 
			 since the last boot."
	::= { tv3CachedCalls 17 }

	tv3ccReaddirPluss OBJECT-TYPE
	SYNTAX		  Counter
	ACCESS		  read-only
	STATUS		  mandatory
	DESCRIPTION
			"The number of NFS Version 3 calls received
			 for the NFSPROC3_READDIRPLUS (Extended Read
			 from Directory) procedure, that did not result in
			 the filesystem blocking to read from disk, 
			 since the last boot."
	::= { tv3CachedCalls 18 }

	tv3ccFsstats	OBJECT-TYPE
	SYNTAX		Counter
	ACCESS		read-only
	STATUS		mandatory
	DESCRIPTION
			"The number of NFS Version 3 calls received
			 for the NFSPROC3_FSSTAT (Get Dynamic File
			 System Information) procedure, that did not
			 result in the filesystem blocking to read
			 from disk, since the last boot."
	::= { tv3CachedCalls 19 }

	tv3ccFsinfos	OBJECT-TYPE
	SYNTAX		Counter
	ACCESS          read-only
	STATUS		mandatory
	DESCRIPTION
			"The number of NFS Version 3 calls received
			 for the NFSPROC3_FSINFO (Get Static File
			 System Information) procedure, that did not
			 result in the filesystem blocking to read
			 from disk, since the last boot."
	::= { tv3CachedCalls 20 }

	tv3ccPathconfs	OBJECT-TYPE
	SYNTAX		Counter
	ACCESS		read-only
	STATUS		mandatory
	DESCRIPTION
			"The number of NFS Version 3 calls received
			 for the NFSPROC3_PATHCONF (Retrieve POSIX
			 Information) procedure, that did not result
			 in the filesystem blocking to read from disk,
			 since the last boot."
	::= { tv3CachedCalls 21 }

	tv3ccCommits	OBJECT-TYPE
	SYNTAX		Counter
	ACCESS		read-only
	STATUS		mandatory
	DESCRIPTION
			"The number of NFS Version 3 calls received
			 for the NFSPROC3_COMMIT (Commit Cached Data on
			 a Server to Stable Storage) procedure, that did
			 not result in the filesystem blocking to read
			 from disk, since the last boot."
	::= { tv3CachedCalls 22 }



	-- the tv3CachedPerCent group

		-- this group contains statistics for the number of
		-- calls received for each NFS Version 3 procedure,
		-- that did not result in the filesystem blocking to
		-- read from disk, as a percentage of the total
		-- number of calls received for that procedure,
		-- since the last boot

	tv3cpNulls	OBJECT-TYPE
	SYNTAX		INTEGER (0..100)
	ACCESS		read-only
	STATUS		mandatory
	DESCRIPTION
			"The number of NFS Version 3 calls received
			 for the NFSPROC3_NULL (Do Nothing) procedure,
			 that did not result in the filesystem
			 blocking to read from disk, as a percentage
			 of the total number of calls received for
			 this procedure, since the last boot."
	::= { tv3CachedPerCent 1 }

	tv3cpGetattrs	OBJECT-TYPE
	SYNTAX		INTEGER (0..100)
	ACCESS		read-only
	STATUS		mandatory
	DESCRIPTION
			"The number of NFS Version 3 calls received
			 for the NFSPROC3_GETATTR (Get File Attributes)
			 procedure, that did not result in the filesystem
			 blocking to read from disk, as a percentage
			 of the total number of calls received for
			 this procedure, since the last boot."
	::= { tv3CachedPerCent 2 }

	tv3cpSetattrs	OBJECT-TYPE
	SYNTAX		INTEGER (0..100)
	ACCESS		read-only
	STATUS		mandatory
	DESCRIPTION
			"The number of NFS Version 3 calls received
			 for the NFSPROC3_SETATTR (Set File Attributes)
			 procedure, that did not result in the filesystem
			 blocking to read from disk, as a percentage
			 of the total number of calls received for
			 this procedure, since the last boot."
	::= { tv3CachedPerCent 3 }

	tv3cpLookups	OBJECT-TYPE
	SYNTAX		INTEGER (0..100)
	ACCESS		read-only
	STATUS		mandatory
	DESCRIPTION
			"The number of NFS Version 3 calls received
			 for the NFSPROC3_LOOKUP (Lookup Filename)
			 procedure, that did not result in the filesystem
			 blocking to read from disk, as a percentage
			 of the total number of calls received for
			 this procedure, since the last boot."
	::= { tv3CachedPerCent 4 }

	tv3cpAccesss	OBJECT-TYPE
	SYNTAX		INTEGER (0..100)
	ACCESS		read-only
	STATUS		mandatory
	DESCRIPTION
			"The number of NFS Version 3 calls received
			 for the NFSPROC3_ACCESS (Check Access Permission)
			 procedure, that did not result in the filesystem
			 blocking to read from disk, as a percentage
			 of the total number of calls received for
			 this procedure, since the last boot."
	::= { tv3CachedPerCent 5 }

	tv3cpReadlinks	OBJECT-TYPE
	SYNTAX		INTEGER (0..100)
	ACCESS		read-only
	STATUS		mandatory
	DESCRIPTION
			"The number of NFS Version 3 calls received
			 for the NFSPROC3_READLINK (Read from Symbolic
			 Link) procedure, that did not result in the
			 filesystem blocking to read from disk, as a
			 percentage of the total number of calls
			 received for this procedure, since the last
			 last boot."
	::= { tv3CachedPerCent 6 }

	tv3cpReads	OBJECT-TYPE
	SYNTAX		INTEGER (0..100)
	ACCESS		read-only
	STATUS		mandatory
	DESCRIPTION
			"The number of NFS Version 3 calls received
			 for the NFSPROC3_READ (Read From File)
			 procedure, that did not result in the
			 filesystem blocking to read from disk, as a
			 percentage of the total number of calls
			 received for this procedure, since the last boot."
	::= { tv3CachedPerCent 7 }

	tv3cpWrites	OBJECT-TYPE
	SYNTAX		INTEGER (0..100)
	ACCESS		read-only
	STATUS		mandatory
	DESCRIPTION
			"The number of NFS Version 3 calls received
			 for the NFSPROC3_WRITE (Write to File)
			 procedure, that did not result in the
			 filesystem blocking to read from disk, as a
			 percentage of the total number of calls
			 received for this procedure, since the last boot."
	::= { tv3CachedPerCent 8 }

	tv3cpCreates	OBJECT-TYPE
	SYNTAX		INTEGER (0..100)
	ACCESS		read-only
	STATUS		mandatory
	DESCRIPTION
			"The number of NFS Version 3 calls received
			 for the NFSPROC3_CREATE (Create a File)
			 procedure, that did not result in the
			 filesystem blocking to read from disk, as a
			 percentage of the total number of calls
			 received for this procedure, since the last boot."
	::= { tv3CachedPerCent 9 }

	tv3cpMkdirs	OBJECT-TYPE
	SYNTAX		INTEGER (0..100)
	ACCESS		read-only
	STATUS		mandatory
	DESCRIPTION
			"The number of NFS Version 3 calls received
			 for the NFSPROC3_MKDIR (Create a Directory)
			 procedure, that did not result in the
			 filesystem blocking to read from disk, as a
			 percentage of the total number of calls
			 received for this procedure, since the last boot."
	::= { tv3CachedPerCent 10 }

	tv3cpSymlinks	OBJECT-TYPE
	SYNTAX		INTEGER (0..100)
	ACCESS		read-only
	STATUS		mandatory
	DESCRIPTION
			"The number of NFS Version 3 calls received
			 for the NFSPROC3_SYMLINK (Create a Symbolic
			 Link) procedure, that did not result in the
			 filesystem blocking to read from disk, as a
			 percentage of the total number of calls
			 received for this procedure, since the last boot."
	::= { tv3CachedPerCent 11 }

	tv3cpMknods	OBJECT-TYPE
	SYNTAX		INTEGER (0..100)
	ACCESS		read-only
	STATUS		mandatory
	DESCRIPTION
			"The number of NFS Version 3 calls received
			 for the NFSPROC3_MKNOD (Create a Special
			 Device) procedure, that did not result in the
			 filesystem blocking to read from disk, as a
			 percentage of the total number of calls
			 received for this procedure, since the last boot."
	::= { tv3CachedPerCent 12 }

	tv3cpRemoves	OBJECT-TYPE
	SYNTAX		INTEGER (0..100)
	ACCESS		read-only
	STATUS		mandatory
	DESCRIPTION
			"The number of NFS Version 3 calls received
			 for the NFSPROC3_REMOVE (Remove a File)
			 procedure, that did not result in the
			 filesystem blocking to read from disk, as a
			 percentage of the total number of calls
			 received for this procedure, since the last boot."
	::= { tv3CachedPerCent 13 }

	tv3cpRmdirs	OBJECT-TYPE
	SYNTAX		INTEGER (0..100)
	ACCESS		read-only
	STATUS		mandatory
	DESCRIPTION
			"The number of NFS Version 3 calls received
			 for the NFSPROC3_RMDIR (Remove a Directory)
			 procedure, that did not result in the
			 filesystem blocking to read from disk, as a
			 percentage of the total number of calls
			 received for this procedure, since the last boot."
	::= { tv3CachedPerCent 14 }

	tv3cpRenames	OBJECT-TYPE
	SYNTAX		INTEGER (0..100)
	ACCESS		read-only
	STATUS		mandatory
	DESCRIPTION
			"The number of NFS Version 3 calls received
			 for the NFSPROC3_RENAME (Rename a File or
			 Directory) procedure, that did not result in
			 the filesystem blocking to read from disk,
			 as a percentage of the total number of calls
			 received for this procedure, since the last boot."
	::= { tv3CachedPerCent 15 }

	tv3cpLinks	OBJECT-TYPE
	SYNTAX		INTEGER (0..100)
	ACCESS		read-only
	STATUS		mandatory
	DESCRIPTION
			"The number of NFS Version 3 calls received
			 for the NFSPROC3_LINK (Create Link to an
			 Object) procedure, that did not result in
			 the filesystem blocking to read from disk,
			 as a percentage of the total number of calls
			 received for this procedure, since the last boot."
	::= { tv3CachedPerCent 16 }

	tv3cpReaddirs	OBJECT-TYPE
	SYNTAX		INTEGER (0..100)
	ACCESS		read-only
	STATUS		mandatory
	DESCRIPTION
			"The number of NFS Version 3 calls received
			 for the NFSPROC3_READDIR (Read From Directory)
			 procedure, that did not result in the
			 filesystem blocking to read from disk, as a
			 percentage of the total number of calls
			 received for this procedure, since the last boot."
	::= { tv3CachedPerCent 17 }

	tv3cpReaddirPluss OBJECT-TYPE
	SYNTAX		  INTEGER (0..100)
	ACCESS		  read-only
	STATUS		  mandatory
	DESCRIPTION
			"The number of NFS Version 3 calls received
			 for the NFSPROC3_READIRPLUS (Extended Read
			 from Directory) procedure, that did not result
			 in the filesystem blocking to read from disk,
			 as a percentage of the total number of calls
			 received for this procedure, since the last boot."
	::= { tv3CachedPerCent 18 }

	tv3cpFsstats	OBJECT-TYPE
	SYNTAX		INTEGER (0..100)
	ACCESS		read-only
	STATUS		mandatory
	DESCRIPTION
			"The number of NFS Version 3 calls received
			 for the NFSPROC3_FSSTAT (Get Dynamic File
			 System Information) procedure, that did not
			 result in the filesystem blocking to read from
			 disk, as a percentage of the total number of
			 calls received for this procedure, since the
			 last boot."
	::= { tv3CachedPerCent 19 }

	tv3cpFsinfos	OBJECT-TYPE
	SYNTAX		INTEGER (0..100)
	ACCESS		read-only
	STATUS		mandatory
	DESCRIPTION
			"The number of NFS Version 3 calls received
			 for the NFSPROC3_FSINFO (Get Static File System
			 Information) procedure, that did not result
			 in the filesystem blocking to read from disk,
			 as a percentage of the total number of calls
			 received for this procedure, since the last boot."
	::= { tv3CachedPerCent 20 }

	tv3cpPathconfs	OBJECT-TYPE
	SYNTAX		INTEGER (0..100)
	ACCESS		read-only
	STATUS		mandatory
	DESCRIPTION
			"The number of NFS Version 3 calls received
			 for the NFSPROC3_PATHCONF (Retrieve POSIX
			 Information) procedure, that did not result
			 in the filesystem blocking to read from disk,
			 as a percentage of the total number of calls
			 received for this procedure, since the last boot."
	::= { tv3CachedPerCent 21 }

	tv3cpCommits	OBJECT-TYPE
	SYNTAX		INTEGER (0..100)
	ACCESS		read-only
	STATUS		mandatory
	DESCRIPTION
			"The number of NFS Version 3 calls received
			 for the NFSPROC3_COMMIT (Commit Cached Data on
			 a Server to Stable Storage) procedure, that
			 did not result in the filesystem blocking to
			 read from disk, as a percentage of the total
			 number of calls received for this procedure,
			 since the last boot."
	::= { tv3CachedPerCent 22 }


	-- the treplyCache group

		-- this group contains statistics related to the 
		-- Reply Cache processing, since the last boot

	trcInProgressHits OBJECT-TYPE
	SYNTAX		  Counter
	ACCESS		  read-only
	STATUS		  mandatory
	DESCRIPTION
			"The number of NFS requests that were dropped, for
			 calls already in progress, since the last boot."
	::= { treplyCache 1 }

	trcDelayHits	OBJECT-TYPE
	SYNTAX		Counter
	ACCESS		read-only
	STATUS		deprecated
	DESCRIPTION
			"The number of NFS requests that were dropped,
			 for replies already generated within a short
			 interval, since the last boot. These stats are 
			 deprecated. A value of zero will always be 
			 returned for these stats."
	::= { treplyCache 2 }

	trcMisses	OBJECT-TYPE
	SYNTAX		Counter
	ACCESS		read-only
	STATUS		mandatory
	DESCRIPTION
			"The number of NFS requests received for which
			 there were no corresponding entries already in
			 the Reply Cache, since the last boot."
	::= { treplyCache 3 }

	trcNonIdemDoneHits OBJECT-TYPE
	SYNTAX		   Counter
	ACCESS		   read-only
	STATUS		   mandatory
	DESCRIPTION
			"The number of NFS requests received that
			 resulted in replies being replayed from
			 the Reply Cache, since the last boot."
	::= { treplyCache 4 }

	trcNonIdemNotDoneHits OBJECT-TYPE
	SYNTAX		      Counter
	ACCESS		      read-only
	STATUS		      mandatory
	DESCRIPTION
			"The number of NFS requests received for calls
			 that resulted in this request being processed
			 as a new request even when a corresponding
			 entry existed in the Reply Cache, since the
			 last boot."
	::= { treplyCache 5 }

	trcTcpInProgressHits OBJECT-TYPE
	SYNTAX		  Counter
	ACCESS		  read-only
	STATUS		  mandatory
	DESCRIPTION
			"The number of NFS requests that were dropped
			 for the TCP protocol, for calls already in
			 progress, since the last boot."
	::= { treplyCache 6 }

	trcTcpDelayHits	OBJECT-TYPE
	SYNTAX		Counter
	ACCESS		read-only
	STATUS		deprecated
	DESCRIPTION
			"The number of NFS requests that were dropped
			 for the TCP protocol, for replies already
			 generated within a short interval, since the
			 last boot. These stats are deprecated. A value 
			 of zero will always be returned for these stats."
	::= { treplyCache 7 }

	trcTcpMisses	OBJECT-TYPE
	SYNTAX		Counter
	ACCESS		read-only
	STATUS		mandatory
	DESCRIPTION 
			"The number of NFS requests received for the
			 TCP protocol for which there were no corresponding
			 entries already in the Reply Cache, since the
			 last boot."
	::= { treplyCache 8 }

	trcTcpNonIdemDoneHits OBJECT-TYPE
	SYNTAX		   Counter
	ACCESS		   read-only
	STATUS		   mandatory
	DESCRIPTION
			"The number of NFS requests received for the
			 TCP protocol that resulted in replies being
			 replayed from the Reply Cache, since the
			 last boot."
	::= { treplyCache 9 }

	trcTcpNonIdemNotDoneHits OBJECT-TYPE
	SYNTAX		      Counter
	ACCESS		      read-only
	STATUS		      mandatory
	DESCRIPTION
			"The number of NFS requests received for the
			 TCP protocol for calls that resulted in this
			 request being processed as a new request even
			 when a corresponding entry existed in the Reply
			 Cache, since the last boot."
	::= { treplyCache 10 }

	trcUdpInProgressHits OBJECT-TYPE
	SYNTAX		  Counter
	ACCESS		  read-only
	STATUS		  mandatory
	DESCRIPTION
			"The number of NFS requests that were dropped
			 for the UDP protocol, for calls already in
			 progress, since the last boot."
	::= { treplyCache 11 }

	trcUdpDelayHits	OBJECT-TYPE
	SYNTAX		Counter
	ACCESS		read-only
	STATUS		deprecated
	DESCRIPTION
			"The number of NFS requests that were dropped
			 for the UDP protocol, for replies already
			 generated within a short interval, since the
			 last boot. These stats are deprecated. A value 
			 of zero will always be returned for these stats."
	::= { treplyCache 12 }

	trcUdpMisses	OBJECT-TYPE
	SYNTAX		Counter
	ACCESS		read-only
	STATUS		mandatory
	DESCRIPTION 
			"The number of NFS requests received for the
			 UDP protocol for which there were no corresponding
			 entries already in the Reply Cache, since the
			 last boot."
	::= { treplyCache 13 }

	trcUdpNonIdemDoneHits OBJECT-TYPE
	SYNTAX		   Counter
	ACCESS		   read-only
	STATUS		   mandatory
	DESCRIPTION
			"The number of NFS requests received for the
			 UDP protocol that resulted in replies being
			 replayed from the Reply Cache, since the
			 last boot."
	::= { treplyCache 14 }

	trcUdpNonIdemNotDoneHits OBJECT-TYPE
	SYNTAX		      Counter
	ACCESS		      read-only
	STATUS		      mandatory
	DESCRIPTION
			"The number of NFS requests received for the
			 UDP protocol for calls that resulted in this
			 request being processed as a new request even
			 when a corresponding entry existed in the Reply
			 Cache, since the last boot."
	::= { treplyCache 15 }

	-- the tnfsrwStats group

		-- this group contains statistics for the sizes of
                -- NFS version 2 and 3 read and write calls since
		-- last boot.

	tv2ReadStats            OBJECT IDENTIFIER ::= { tnfsrwStats 1 }

	tv2WriteStats           OBJECT IDENTIFIER ::= { tnfsrwStats 2 }

	tv3ReadStats            OBJECT IDENTIFIER ::= { tnfsrwStats 3 }

	tv3WriteStats           OBJECT IDENTIFIER ::= { tnfsrwStats 4 }


	-- the tv2ReadStats group

		-- this group contains statistics for the sizes of
		-- NFS version 2 read calls since last boot.

	tv2Read512Calls	OBJECT-TYPE
	SYNTAX		Counter
	ACCESS		read-only
	STATUS		mandatory
	DESCRIPTION
			"The number of NFS Version 2 read calls
			received by the server since last boot
			with request sizes between 0-511 bytes."
	::= { tv2ReadStats 1 }

	tv2Read1KCalls	OBJECT-TYPE
	SYNTAX		Counter
	ACCESS		read-only
	STATUS		mandatory
	DESCRIPTION
			"The number of NFS Version 2 read calls
			received by the server since last boot
			with request sizes between 512-1023 bytes."
	::= { tv2ReadStats 2 }

	tv2Read2KCalls	OBJECT-TYPE
	SYNTAX		Counter
	ACCESS		read-only
	STATUS		mandatory
	DESCRIPTION
			"The number of NFS Version 2 read calls
			received by the server since last boot
			with request sizes between 1K-2047 bytes."
	::= { tv2ReadStats 3 }


	tv2Read4KCalls	OBJECT-TYPE
	SYNTAX		Counter
	ACCESS		read-only
	STATUS		mandatory
	DESCRIPTION
			"The number of NFS Version 2 read calls
			received by the server since last boot
			with request sizes between 2K-4095 bytes."
	::= { tv2ReadStats 4 }

	tv2Read8KCalls	OBJECT-TYPE
	SYNTAX		Counter
	ACCESS		read-only
	STATUS		mandatory
	DESCRIPTION
			"The number of NFS Version 2 read calls
			received by the server since last boot
			with request sizes between 4K-8191 bytes."
	::= { tv2ReadStats 5 }

	tv2Read16KCalls	OBJECT-TYPE
	SYNTAX		Counter
	ACCESS		read-only
	STATUS		mandatory
	DESCRIPTION
			"The number of NFS Version 2 read calls
			received by the server since last boot
			with request sizes between 8K-16383 bytes."
	::= { tv2ReadStats 6 }

	tv2Read32KCalls	OBJECT-TYPE
	SYNTAX		Counter
	ACCESS		read-only
	STATUS		mandatory
	DESCRIPTION
			"The number of NFS Version 2 read calls
			received by the server since last boot
			with request sizes between 16K-32767 bytes."
	::= { tv2ReadStats 7 }

	tv2Read64KCalls	OBJECT-TYPE
	SYNTAX		Counter
	ACCESS		read-only
	STATUS		mandatory
	DESCRIPTION
			"The number of NFS Version 2 read calls
			received by the server since last boot
			with request sizes between 32K-65535 bytes."
	::= { tv2ReadStats 8 }

	tv2Read128KCalls	OBJECT-TYPE
	SYNTAX		Counter
	ACCESS		read-only
	STATUS		mandatory
	DESCRIPTION
			"The number of NFS Version 2 read calls
			received by the server since last boot
			with request sizes between 64K-131071 bytes."
	::= { tv2ReadStats 9 }


	-- the tv2WriteStats group

		-- this group contains statistics for the sizes of
		-- NFS version 2 write calls since last boot.

	tv2Write512Calls	OBJECT-TYPE
	SYNTAX		Counter
	ACCESS		read-only
	STATUS		mandatory
	DESCRIPTION
			"The number of NFS Version 2 write calls
			received by the server since last boot
			with request sizes between 0-511 bytes."
	::= { tv2WriteStats 1 }

	tv2Write1KCalls	OBJECT-TYPE
	SYNTAX		Counter
	ACCESS		read-only
	STATUS		mandatory
	DESCRIPTION
			"The number of NFS Version 2 write calls
			received by the server since last boot
			with request sizes between 512-1023 bytes."
	::= { tv2WriteStats 2 }

	tv2Write2KCalls	OBJECT-TYPE
	SYNTAX		Counter
	ACCESS		read-only
	STATUS		mandatory
	DESCRIPTION
			"The number of NFS Version 2 write calls
			received by the server since last boot
			with request sizes between 1K-2047 bytes."
	::= { tv2WriteStats 3 }


	tv2Write4KCalls	OBJECT-TYPE
	SYNTAX		Counter
	ACCESS		read-only
	STATUS		mandatory
	DESCRIPTION
			"The number of NFS Version 2 write calls
			received by the server since last boot
			with request sizes between 2K-4095 bytes."
	::= { tv2WriteStats 4 }

	tv2Write8KCalls	OBJECT-TYPE
	SYNTAX		Counter
	ACCESS		read-only
	STATUS		mandatory
	DESCRIPTION
			"The number of NFS Version 2 write calls
			received by the server since last boot
			with request sizes between 4K-8191 bytes."
	::= { tv2WriteStats 5 }

	tv2Write16KCalls	OBJECT-TYPE
	SYNTAX		Counter
	ACCESS		read-only
	STATUS		mandatory
	DESCRIPTION
			"The number of NFS Version 2 write calls
			received by the server since last boot
			with request sizes between 8K-16383 bytes."
	::= { tv2WriteStats 6 }

	tv2Write32KCalls	OBJECT-TYPE
	SYNTAX		Counter
	ACCESS		read-only
	STATUS		mandatory
	DESCRIPTION
			"The number of NFS Version 2 write calls
			received by the server since last boot
			with request sizes between 16K-32767 bytes."
	::= { tv2WriteStats 7 }

	tv2Write64KCalls	OBJECT-TYPE
	SYNTAX		Counter
	ACCESS		read-only
	STATUS		mandatory
	DESCRIPTION
			"The number of NFS Version 2 write calls
			received by the server since last boot
			with request sizes between 32K-65535 bytes."
	::= { tv2WriteStats 8 }

	tv2Write128KCalls	OBJECT-TYPE
	SYNTAX		Counter
	ACCESS		read-only
	STATUS		mandatory
	DESCRIPTION
			"The number of NFS Version 2 write calls
			received by the server since last boot
			with request sizes between 64K-131071 bytes."
	::= { tv2WriteStats 9 }


	-- the tv3ReadStats group

		-- this group contains statistics for the sizes of
		-- NFS version 3 read calls since last boot.

	tv3Read512Calls	OBJECT-TYPE
	SYNTAX		Counter
	ACCESS		read-only
	STATUS		mandatory
	DESCRIPTION
			"The number of NFS Version 3 read calls
			received by the server since last boot
			with request sizes between 0-511 bytes."
	::= { tv3ReadStats 1 }

	tv3Read1KCalls	OBJECT-TYPE
	SYNTAX		Counter
	ACCESS		read-only
	STATUS		mandatory
	DESCRIPTION
			"The number of NFS Version 3 read calls
			received by the server since last boot
			with request sizes between 512-1023 bytes."
	::= { tv3ReadStats 2 }

	tv3Read2KCalls	OBJECT-TYPE
	SYNTAX		Counter
	ACCESS		read-only
	STATUS		mandatory
	DESCRIPTION
			"The number of NFS Version 3 read calls
			received by the server since last boot
			with request sizes between 1K-2047 bytes."
	::= { tv3ReadStats 3 }


	tv3Read4KCalls	OBJECT-TYPE
	SYNTAX		Counter
	ACCESS		read-only
	STATUS		mandatory
	DESCRIPTION
			"The number of NFS Version 3 read calls
			received by the server since last boot
			with request sizes between 2K-4095 bytes."
	::= { tv3ReadStats 4 }

	tv3Read8KCalls	OBJECT-TYPE
	SYNTAX		Counter
	ACCESS		read-only
	STATUS		mandatory
	DESCRIPTION
			"The number of NFS Version 3 read calls
			received by the server since last boot
			with request sizes between 4K-8191 bytes."
	::= { tv3ReadStats 5 }

	tv3Read16KCalls 	OBJECT-TYPE
	SYNTAX		Counter
	ACCESS		read-only
	STATUS		mandatory
	DESCRIPTION
			"The number of NFS Version 3 read calls
			received by the server since last boot
			with request sizes between 8K-16383 bytes."
	::= { tv3ReadStats 6 }

	tv3Read32KCalls	OBJECT-TYPE
	SYNTAX		Counter
	ACCESS		read-only
	STATUS		mandatory
	DESCRIPTION
			"The number of NFS Version 3 read calls
			received by the server since last boot
			with request sizes between 16K-32767 bytes."
	::= { tv3ReadStats 7 }

	tv3Read64KCalls	OBJECT-TYPE
	SYNTAX		Counter
	ACCESS		read-only
	STATUS		mandatory
	DESCRIPTION
			"The number of NFS Version 3 read calls
			received by the server since last boot
			with request sizes between 32K-65535 bytes."
	::= { tv3ReadStats 8 }

	tv3Read128KCalls	OBJECT-TYPE
	SYNTAX		Counter
	ACCESS		read-only
	STATUS		mandatory
	DESCRIPTION
			"The number of NFS Version 3 read calls
			received by the server since last boot
			with request sizes between 64K-131071 bytes."
	::= { tv3ReadStats 9 }


	-- the tv3WriteStats group

		-- this group contains statistics for the sizes of
		-- NFS version 3 write calls since last boot.

	tv3Write512Calls	OBJECT-TYPE
	SYNTAX		Counter
	ACCESS		read-only
	STATUS		mandatory
	DESCRIPTION
			"The number of NFS Version 3 write calls
			received by the server since last boot
			with request sizes between 0-511 bytes."
	::= { tv3WriteStats 1 }

	tv3Write1KCalls	OBJECT-TYPE
	SYNTAX		Counter
	ACCESS		read-only
	STATUS		mandatory
	DESCRIPTION
			"The number of NFS Version 3 write calls
			received by the server since last boot
			with request sizes between 512-1023 bytes."
	::= { tv3WriteStats 2 }

	tv3Write2KCalls	OBJECT-TYPE
	SYNTAX		Counter
	ACCESS		read-only
	STATUS		mandatory
	DESCRIPTION
			"The number of NFS Version 3 write calls
			received by the server since last boot
			with request sizes between 1K-2047 bytes."
	::= { tv3WriteStats 3 }

	tv3Write4KCalls	OBJECT-TYPE
	SYNTAX		Counter
	ACCESS		read-only
	STATUS		mandatory
	DESCRIPTION
			"The number of NFS Version 3 write calls
			received by the server since last boot
			with request sizes between 2K-4095 bytes."
	::= { tv3WriteStats 4 }

	tv3Write8KCalls	OBJECT-TYPE
	SYNTAX		Counter
	ACCESS		read-only
	STATUS		mandatory
	DESCRIPTION
			"The number of NFS Version 3 write calls
			received by the server since last boot
			with request sizes between 4K-8191 bytes."
	::= { tv3WriteStats 5 }

	tv3Write16KCalls	OBJECT-TYPE
	SYNTAX		Counter
	ACCESS		read-only
	STATUS		mandatory
	DESCRIPTION
			"The number of NFS Version 3 write calls
			received by the server since last boot
			with request sizes between 8K-16383 bytes."
	::= { tv3WriteStats 6 }

	tv3Write32KCalls	OBJECT-TYPE
	SYNTAX		Counter
	ACCESS		read-only
	STATUS		mandatory
	DESCRIPTION
			"The number of NFS Version 3 write calls
			received by the server since last boot
			with request sizes between 16K-32767 bytes."
	::= { tv3WriteStats 7 }

	tv3Write64KCalls	OBJECT-TYPE
	SYNTAX		Counter
	ACCESS		read-only
	STATUS		mandatory
	DESCRIPTION
			"The number of NFS Version 3 write calls
			received by the server since last boot
			with request sizes between 32K-65535 bytes."
	::= { tv3WriteStats 8 }

	tv3Write128KCalls	OBJECT-TYPE
	SYNTAX		Counter
	ACCESS		read-only
	STATUS		mandatory
	DESCRIPTION
			"The number of NFS Version 3 write calls
			received by the server since last boot
			with request sizes between 64K-131071 bytes."
	::= { tv3WriteStats 9 }


	-- -- -- -- -- -- -- -- -- -- -- -- -- -- -- -- -- --
	-- the nfsOptions group
	-- -- -- -- -- -- -- -- -- -- -- -- -- -- -- -- -- --

	nfsIsLicensed	OBJECT-TYPE
	SYNTAX		INTEGER {
					false(1),
					true(2)
				}
	ACCESS		read-only
	STATUS		mandatory
	DESCRIPTION
			"Whether the nfs protocol is licensed on the
			 filer."
	::= { nfsOptions 1 }
		

	-- -- -- -- -- --  --
	-- the quota group --
	-- -- -- -- -- --  --

	quotaState	OBJECT-TYPE
	SYNTAX		INTEGER {
		quotaStateOff(1),
		quotaStateOn(2),
		quotaStateInit(3)
	}
	ACCESS		read-only
	STATUS		deprecated
	DESCRIPTION
			"Indicates whether the root volume's quotas are ON, 
			 OFF or initializing.  This object is deprecated -
			 use qvStateTable.qvStateStat instead."
	::= { quota 1 }

	quotaInitPercent OBJECT-TYPE
	SYNTAX		 INTEGER (0..100)
	ACCESS		 read-only
	STATUS		 deprecated
	DESCRIPTION
			"Indicates percentage of root volume quota 
			 computation done while quotas are in initializing 
			 state. This object is deprecated - use 
			 qvStateTable.qvInitPercent instead."
	::= { quota 2 }


	-- the old volume-unaware quota report table.  DEPRECATED

	qrTable		OBJECT-TYPE
	SYNTAX		SEQUENCE OF QrEntry
	ACCESS		not-accessible
	STATUS		deprecated
	DESCRIPTION
			"Provide a report of the current file and
			 space consumption for each user or group with
			 a quota in /etc/quotas.  All quotas are displayed
			 regardless of volume, and no volume information
			 is given.  This table is deprecated - use qrVTable 
			 instead."
	::= { quota 3 }

	qrEntry		OBJECT-TYPE
	SYNTAX		QrEntry
	ACCESS		not-accessible
	STATUS		deprecated
	DESCRIPTION
			"Provide a report of the current file and
			 space consumption for a referenced entry
			 with a quota in the file /etc/quotas.
			 All quotas are displayed regardless of volume, 
			 and no volume information is given.  This object is 
			 deprecated - use qrVEntry instead."

	INDEX	{ qrIndex }
	::= { qrTable 1 }

	QrEntry ::=
	    SEQUENCE {
		qrIndex
		    INTEGER,
		qrType
		    INTEGER,
		qrId
		    INTEGER,
		qrKBytesUsed
		    INTEGER,
		qrKBytesLimit
		    INTEGER,
		qrFilesUsed
		    INTEGER,
		qrFileLimit
		    INTEGER,
		qrPathName
		    DisplayString
	    }

	qrIndex		OBJECT-TYPE
	SYNTAX		INTEGER (1..2147483647)
	ACCESS		read-only
	STATUS		deprecated
	DESCRIPTION
			"A number that identifies this entry in the
			 file /etc/quotas."
	::= { qrEntry 1 }

	qrType		OBJECT-TYPE
	SYNTAX		INTEGER {
		qrTypeUser(1),
		qrTypeGroup(2),
		qrTypeTree(3),
		qrTypeUnknown(4)
	}
	ACCESS		read-only
	STATUS		deprecated
	DESCRIPTION
			"Identifies the kind of quota for this qrEntry."
	::= { qrEntry 2 }

	qrId		OBJECT-TYPE
	SYNTAX		INTEGER
	ACCESS		read-only
	STATUS		deprecated
	DESCRIPTION
			"The UID (user's numerical ID) or the GID (numerical
			 ID of  the  group  that a user belongs to), as
			 applicable, associated with this qrEntry."
	::= { qrEntry 3 }

	qrKBytesUsed	OBJECT-TYPE
	SYNTAX		INTEGER
	ACCESS		read-only
	STATUS		deprecated
	DESCRIPTION
			"The current number of KBytes used for this
			 qrEntry."
	::= { qrEntry 4 }

	qrKBytesLimit	OBJECT-TYPE
	SYNTAX		INTEGER
	ACCESS		read-only
	STATUS		deprecated
	DESCRIPTION
			"The limit of KBytes that can be used for this
			 qrEntry."
	::= { qrEntry 5 }

	qrFilesUsed	OBJECT-TYPE
	SYNTAX		INTEGER
	ACCESS		read-only
	STATUS		deprecated
	DESCRIPTION
			"The current number of files used for this
			 qrEntry."
	::= { qrEntry 6 }

	qrFileLimit	OBJECT-TYPE
	SYNTAX		INTEGER
	ACCESS		read-only
	STATUS		deprecated
	DESCRIPTION
			"The limit of files that can be used for this
			 qrEntry."
	::= { qrEntry 7 }

	qrPathName	OBJECT-TYPE
	SYNTAX		DisplayString
	ACCESS		read-only
	STATUS		deprecated
	DESCRIPTION
			"A textual string that contains the path
			 corresponding to this qrEntry."
	::= { qrEntry 8 }

	-- quota volume state table	

	qvStateTable	OBJECT-TYPE
	SYNTAX		SEQUENCE OF QvStateEntry
	ACCESS		not-accessible
	STATUS		mandatory
	DESCRIPTION
			"Provide a report of the current quota state of
			each volume in the system."
	::= { quota 4 }

	qvStateEntry		OBJECT-TYPE
	SYNTAX		QvStateEntry
	ACCESS		not-accessible
	STATUS		mandatory
	DESCRIPTION
			"Provide a report of the current quota state of
			each volume in the system."
	INDEX	{ qvStateVolume }
	::= { qvStateTable 1 }

	QvStateEntry ::=
	    SEQUENCE {
		qvStateVolume
		    INTEGER,
		qvStateName
		    DisplayString,
		qvStateStat
		    INTEGER,
		qvStateInitPercent
		    INTEGER
	    }

	qvStateVolume	OBJECT-TYPE
	SYNTAX		INTEGER (1..2147483647)
	ACCESS		read-only
	STATUS		mandatory
	DESCRIPTION
			"A number that identifies this volume.  The mapping
       			 of this number to actual volumes may change if 
			 volumes are added or deleted.  Use qvStateName to 
			 unambiguously identify a volume.  The mapping
			 established by this object is the same as 
			 the mapping of qrVVolume (below) to actual volumes.
			 For instance, if a qvStateVolume value of '5'
			 represents the volume 'vol2', a value of '5'
			 in qrVVolume also represents the volume 'vol2'."
	::= { qvStateEntry 1 }

	qvStateName	 OBJECT-TYPE
	SYNTAX		 DisplayString
	ACCESS		 read-only
	STATUS		 mandatory
	DESCRIPTION
			"Indicates the name of this volume."
	::= { qvStateEntry 2 }

	qvStateStat	OBJECT-TYPE
	SYNTAX		INTEGER {
		quotaStateOff(1),
		quotaStateOn(2),
		quotaStateInit(3)
	}
	ACCESS		read-only
	STATUS		mandatory
	DESCRIPTION
			"Indicates whether quotas are ON, OFF or
			 initializing."
	::= { qvStateEntry 3 }

	qvStateInitPercent OBJECT-TYPE
	SYNTAX		 INTEGER (0..100)
	ACCESS		 read-only
	STATUS		 mandatory
	DESCRIPTION
			"Indicates percentage of quota computation done
			 while quotas are in initializing state."
	::= { qvStateEntry 4 }


	-- multi-volume-aware quota table
	-- THIS IS DEPRECATED, please use qrV2Table instead

	qrVTable	OBJECT-TYPE
	SYNTAX		SEQUENCE OF QrVEntry
	ACCESS		not-accessible
	STATUS		deprecated
	DESCRIPTION
			"Provide a report of the current file and
			 space consumption for each user or group with
			 a quota in /etc/quotas."
	::= { quota 5 }


	qrVEntry	OBJECT-TYPE
	SYNTAX		QrVEntry
	ACCESS		not-accessible
	STATUS		deprecated
	DESCRIPTION
			"Provide a report of the current file and
			 space consumption for a referenced entry
			 with a quota in the file /etc/quotas.  Indices
			 select the volume of the quota and the quota entry
			 itself."
	INDEX	{ qrVVolume, qrVIndex }
	::= { qrVTable 1 }

	QrVEntry ::=
	    SEQUENCE {
		qrVIndex
		    INTEGER,
		qrVType
		    INTEGER,
		qrVId
		    INTEGER,
		qrVKBytesUsed
		    INTEGER,
		qrVKBytesLimit
		    INTEGER,
		qrVFilesUsed
		    INTEGER,
		qrVFileLimit
		    INTEGER,
		qrVPathName
		    DisplayString,
		qrVVolume
		    INTEGER,
		qrVTree
		    DisplayString,
		qrVIdType
		    INTEGER,
                qrVSid
                    DisplayString,
	        qrVKBytesThreshold
                    INTEGER,
		qrVKBytesLimitSoft
		    INTEGER,
		qrVFileLimitSoft
		    INTEGER
	    }

	qrVIndex	OBJECT-TYPE
	SYNTAX		INTEGER (1..2147483647)
	ACCESS		read-only
	STATUS		deprecated
	DESCRIPTION
			"A number that identifies this entry in the
			 file /etc/quotas in the given volume."
	::= { qrVEntry 1 }

	qrVType		OBJECT-TYPE
	SYNTAX		INTEGER {
		qrVTypeUser(1),
		qrVTypeGroup(2),
		qrVTypeTree(3),
		qrVTypeUserDefault(4),
		qrVTypeGroupDefault(5),
		qrVTypeUnknown(6)
	}
	ACCESS		read-only
	STATUS		deprecated
	DESCRIPTION
			"Identifies the kind of quota for this qrVEntry."
	::= { qrVEntry 2 }

	qrVId		OBJECT-TYPE
	SYNTAX		INTEGER
	ACCESS		read-only
	STATUS		deprecated
	DESCRIPTION
			"The UID (user's numerical ID) or the GID (numerical
			 ID of  the  group  that a user belongs to), as
			 applicable, associated with this qrVEntry. Check
                         the qrVIdType field to see if this field is valid."
	::= { qrVEntry 3 }

	qrVKBytesUsed	OBJECT-TYPE
	SYNTAX		INTEGER
	ACCESS		read-only
	STATUS		deprecated
	DESCRIPTION
			"The current number of KBytes used for this
			 qrVEntry."
	::= { qrVEntry 4 }

	qrVKBytesLimit	OBJECT-TYPE
	SYNTAX		INTEGER
	ACCESS		read-only
	STATUS		deprecated
	DESCRIPTION
			"The limit of KBytes that can be used for this
			 qrVEntry."
	::= { qrVEntry 5 }

	qrVFilesUsed	OBJECT-TYPE
	SYNTAX		INTEGER
	ACCESS		read-only
	STATUS		deprecated
	DESCRIPTION
			"The current number of files used for this
			 qrVEntry."
	::= { qrVEntry 6 }

	qrVFileLimit	OBJECT-TYPE
	SYNTAX		INTEGER
	ACCESS		read-only
	STATUS		deprecated
	DESCRIPTION
			"The limit of files that can be used for this
			 qrVEntry."
	::= { qrVEntry 7 }

	qrVPathName	OBJECT-TYPE
	SYNTAX		DisplayString
	ACCESS		read-only
	STATUS		deprecated
	DESCRIPTION
			"A textual string that contains the path
			 corresponding to this qrVEntry."
	::= { qrVEntry 8 }

	qrVVolume	OBJECT-TYPE
	SYNTAX		INTEGER (1..2147483647)
	ACCESS		read-only
	STATUS		deprecated
	DESCRIPTION
			"A number that identifies the volume for which
			this quota is in effect on.  The volume that this
			value represents can be determined by checking
			the value of qvStateName (above) with 
			qvStateVolume set to the value found here."
	::= { qrVEntry 9 }

        qrVTree		OBJECT-TYPE
        SYNTAX          DisplayString
        ACCESS          read-only
        STATUS          deprecated
        DESCRIPTION
			"A string that indicates which qtree this quota
			belongs to."        
	::= { qrVEntry 10 }

        qrVIdType       OBJECT-TYPE
        SYNTAX          INTEGER {
             qrVIdValid(1),
             qrVSidValid(2)
        }
        ACCESS          read-only
        STATUS          deprecated
        DESCRIPTION
                        "A value that indicates which ID field is valid."
        ::= { qrVEntry 11}

	qrVSid		OBJECT-TYPE
	SYNTAX		DisplayString
	ACCESS		read-only
	STATUS		deprecated
	DESCRIPTION
			"The one or more IDs associated with this qrVEntry.
                         If the qrVentry is associated with a Windows ID, the
			 text form of the Windows ID (the SID) is here. If
			 the qrVEntry is associated with more than one id,
			 this contains a blank separated list of those IDs.
                         Check the qrVIdType field to see if this field is
                         valid."
	::= { qrVEntry 12 }

        qrVKBytesThreshold   OBJECT-TYPE
        SYNTAX          INTEGER
	ACCESS          read-only
        STATUS          deprecated
        DESCRIPTION
                        "A number of KBytes that when used by this entry
			 produces a warning message."
        ::= { qrVEntry 13 }

        qrVKBytesLimitSoft   OBJECT-TYPE
        SYNTAX          INTEGER
	ACCESS          read-only
        STATUS          deprecated
        DESCRIPTION
			"The limit of KBytes that can be used for this
			 qrVEntry before a warning message and SNMP
			 trap is produced."
        ::= { qrVEntry 14 }

        qrVFileLimitSoft   OBJECT-TYPE
        SYNTAX          INTEGER
	ACCESS          read-only
        STATUS          deprecated
        DESCRIPTION
			"The limit of files that can be used for this
			 qrVEntry before a warning message and SNMP
			 trap is produced."
        ::= { qrVEntry 15 }

	--
	-- multi-volume-aware quota table with 64 bit values
	--

	qrV2Table	OBJECT-TYPE
	SYNTAX		SEQUENCE OF QrV2Entry
	ACCESS		not-accessible
	STATUS		mandatory
	DESCRIPTION
			"Provide a report of the current file and
			 space consumption for each user or group with
			 a quota in /etc/quotas."
	::= { quota 6 }


	qrV2Entry	OBJECT-TYPE
	SYNTAX		QrV2Entry
	ACCESS		not-accessible
	STATUS		mandatory
	DESCRIPTION
			"Provide a report of the current file and
			 space consumption for a referenced entry
			 with a quota in the file /etc/quotas.  Indices
			 select the volume of the quota and the quota entry
			 itself."
	INDEX	{ qrV2Volume, qrV2Index }
	::= { qrV2Table 1 }

	QrV2Entry ::=
	    SEQUENCE {
		qrV2Index
		    INTEGER,
		qrV2Type
		    INTEGER,
		qrV2Id
		    INTEGER,
		qrV2HighKBytesUsed
		    INTEGER,
		qrV2LowKBytesUsed
		    INTEGER,
                qrV2QuotaUnlimited
		    INTEGER,
		qrV2HighKBytesLimit
		    INTEGER,
		qrV2LowKBytesLimit
		    INTEGER,
		qrV2FilesUsed
		    INTEGER,
                qrV2FileQuotaUnlimited
		    INTEGER,
		qrV2FileLimit
		    INTEGER,
		qrV2PathName
		    DisplayString,
		qrV2Volume
		    INTEGER,
		qrV2Tree
		    DisplayString,
		qrV2IdType
		    INTEGER,
                qrV2Sid
                    DisplayString,
                qrV2ThresholdUnlimited
		    INTEGER,		    
	        qrV2HighKBytesThreshold
                    INTEGER,
	        qrV2LowKBytesThreshold
                    INTEGER,
                qrV2SoftQuotaUnlimited
		    INTEGER,
		qrV2HighKBytesSoftLimit
		    INTEGER,
		qrV2LowKBytesSoftLimit
		    INTEGER,
		qrV2SoftFileQuotaUnlimited
		    INTEGER,
		qrV2SoftFileLimit
		    INTEGER
	    }

	qrV2Index	OBJECT-TYPE
	SYNTAX		INTEGER (1..2147483647)
	ACCESS		read-only
	STATUS		mandatory
	DESCRIPTION
			"A number that identifies this entry in the
			 file /etc/quotas in the given volume."
	::= { qrV2Entry 1 }

	qrV2Type		OBJECT-TYPE
	SYNTAX		INTEGER {
		qrV2TypeUser(1),
		qrV2TypeGroup(2),
		qrV2TypeTree(3),
		qrV2TypeUserDefault(4),
		qrV2TypeGroupDefault(5),
		qrV2TypeUnknown(6)
	}
	ACCESS		read-only
	STATUS		mandatory
	DESCRIPTION
			"Identifies the kind of quota for this qrV2Entry."
	::= { qrV2Entry 2 }

	qrV2Id		OBJECT-TYPE
	SYNTAX		INTEGER
	ACCESS		read-only
	STATUS		mandatory
	DESCRIPTION
			"The UID (user's numerical ID) or the GID (numerical
			 ID of  the  group  that a user belongs to), as
			 applicable, associated with this qrV2Entry. Check
                         the qrV2IdType field to see if this field is valid."
	::= { qrV2Entry 3 }

	qrV2HighKBytesUsed	OBJECT-TYPE
	SYNTAX			INTEGER
	ACCESS			read-only
	STATUS			mandatory
	DESCRIPTION
			"The current number of KBytes used for this
			 qrV2Entry. This object returns the most significant
			 32 bits of the 64 bit unsigned integer."
	::= { qrV2Entry 4 }

	qrV2LowKBytesUsed	OBJECT-TYPE
	SYNTAX			INTEGER
	ACCESS			read-only
	STATUS			mandatory
	DESCRIPTION
			"The current number of KBytes used for this
			 qrV2Entry. This object returns the least significant
			 32 bits of the 64 bit unsigned integer."
	::= { qrV2Entry 5 }

	qrV2QuotaUnlimited      OBJECT-TYPE
	SYNTAX			INTEGER {
					false(1),
					true(2)
				}
	ACCESS			read-only
	STATUS			mandatory
	DESCRIPTION
			"This flag designates whether or not the
			size based quota limit for this qrV2Entry is unlimited.
			If false(1) then qrV2HighKBytesLimit and
			qrV2LowKBytesLimit are valid, if true(0) both
			qrV2HighKBytesLimit and qrV2LowKBytesLimit are unused
			and will return 0."
	::= { qrV2Entry 6 }

	qrV2HighKBytesLimit	OBJECT-TYPE
	SYNTAX			INTEGER
	ACCESS			read-only
	STATUS			mandatory
	DESCRIPTION
			"The limit of KBytes that can be used for this
			 qrV2Entry. This object returns the most significant
			 32 bits of the 64 bit unsigned integer. This will 
			 return 0 if qrV2QuotaUnlimited is true."
	::= { qrV2Entry 7 }

	qrV2LowKBytesLimit	OBJECT-TYPE
	SYNTAX			INTEGER
	ACCESS			read-only
	STATUS			mandatory
	DESCRIPTION
			"The limit of KBytes that can be used for this
			 qrV2Entry. This object returns the least significant
			 32 bits of the 64 bit unsigned integer. This will 
			 return 0 if qrV2QuotaUnlimited is true."
	::= { qrV2Entry 8 }

	qrV2FilesUsed	OBJECT-TYPE
	SYNTAX		INTEGER
	ACCESS		read-only
	STATUS		mandatory
	DESCRIPTION
			"The current number of files used for this
			 qrV2Entry."
	::= { qrV2Entry 9 }

	qrV2FileQuotaUnlimited	 OBJECT-TYPE
	SYNTAX			 INTEGER {
					 false(1),
					 true(2)	
				 }	 
	ACCESS			 read-only
	STATUS			 mandatory
	DESCRIPTION
			"This flag designates whether or not the
			file based quota limit for this qrV2Entry is unlimited.
			If false(1) then qrV2FileLimit is valid, if true(0)
			qrV2FileLimit will return 0."
	::= { qrV2Entry 10 }
	

	qrV2FileLimit	OBJECT-TYPE
	SYNTAX		INTEGER
	ACCESS		read-only
	STATUS		mandatory
	DESCRIPTION
			"The limit of files that can be used for this
			 qrV2Entry."
	::= { qrV2Entry 11 }

	qrV2PathName	OBJECT-TYPE
	SYNTAX		DisplayString
	ACCESS		read-only
	STATUS		mandatory
	DESCRIPTION
			"A textual string that contains the path
			 corresponding to this qrV2Entry."
	::= { qrV2Entry 12 }

	qrV2Volume	OBJECT-TYPE
	SYNTAX		INTEGER (1..2147483647)
	ACCESS		read-only
	STATUS		mandatory
	DESCRIPTION
			"A number that identifies the volume for which
			this quota is in effect on.  The volume that this
			value represents can be determined by checking
			the value of qvStateName (above) with 
			qvStateVolume set to the value found here."
	::= { qrV2Entry 13 }

        qrV2Tree		OBJECT-TYPE
        SYNTAX          DisplayString
        ACCESS          read-only
        STATUS          mandatory
        DESCRIPTION
			"A string that indicates which qtree this quota
			belongs to."        
	::= { qrV2Entry 14 }

        qrV2IdType       OBJECT-TYPE
        SYNTAX          INTEGER {
				qrV2IdValid(1),
				qrV2SidValid(2)
			}
        ACCESS          read-only
        STATUS          mandatory
        DESCRIPTION
                        "A value that indicates which ID field is valid."
        ::= { qrV2Entry 15 }

	qrV2Sid		OBJECT-TYPE
	SYNTAX		DisplayString
	ACCESS		read-only
	STATUS		mandatory
	DESCRIPTION
			"The one or more IDs associated with this qrV2Entry.
                         If the qrV2entry is associated with a Windows ID, the
			 text form of the Windows ID (the SID) is here. If
			 the qrV2Entry is associated with more than one id,
			 this contains a blank separated list of those IDs.
                         Check the qrV2IdType field to see if this field is
                         valid."
	::= { qrV2Entry 16 }

	qrV2ThresholdUnlimited	 OBJECT-TYPE
	SYNTAX			 INTEGER {
					 false(1),
					 true(2)
				 }
	ACCESS			 read-only
	STATUS			 mandatory
	DESCRIPTION
			"This flag designates whether or not the
			size based threshold limit for this qrV2Entry is 
			unlimited. If false(1) then qrV2HighKBytesThreshold and
			qrV2LowKBytesThreshold are valid, if true(0) both
			qrV2HighKBytesThreshold and qrV2LowKBytesThreshold 
			are unused and will return 0."
	::= { qrV2Entry 17 }

        qrV2HighKBytesThreshold	 OBJECT-TYPE
        SYNTAX			 INTEGER
	ACCESS			 read-only
        STATUS			 mandatory
        DESCRIPTION
                        "A number of KBytes that when used by this entry
			 produces a warning message. This object returns the 
			 most significant 32 bits of the 64 bit unsigned 
			 integer. This will return 0 if qrV2ThresholdUnlimited
			 is true."
        ::= { qrV2Entry 18 }

        qrV2LowKBytesThreshold	 OBJECT-TYPE
        SYNTAX			 INTEGER
	ACCESS			 read-only
        STATUS			 mandatory
        DESCRIPTION
                        "A number of KBytes that when used by this entry
			 produces a warning message. This object returns the 
			 least significant 32 bits of the 64 bit unsigned 
			 integer. This will return 0 if qrV2ThresholdUnlimited
			 is true."
        ::= { qrV2Entry 19 }

	qrV2SoftQuotaUnlimited	 OBJECT-TYPE
	SYNTAX			 INTEGER {
					 false(1),
					 true(2)
				 }
	ACCESS			 read-only
	STATUS			 mandatory
	DESCRIPTION
			"This flag designates whether or not the
			size based soft quota limit for this qrV2Entry is 
			unlimited. If false(1) then qrV2HighKBytesSoftLimit and
			qrV2LowKBytesSoftLimit are valid, if true(0) both
			qrV2HighKBytesSoftLimit and qrV2LowKBytesSoftLimit 
			are unused and will return 0."
	::= { qrV2Entry 20 }

        qrV2HighKBytesSoftLimit	 OBJECT-TYPE
        SYNTAX			 INTEGER
	ACCESS			 read-only
        STATUS			 mandatory
        DESCRIPTION
			"The limit of KBytes that can be used for this
			 qrV2Entry before a warning message and SNMP
			 trap is produced. This object returns the most
			 significant 32 bits of the 64 bit unsigned integer."
        ::= { qrV2Entry 21 }
        qrV2LowKBytesSoftLimit	 OBJECT-TYPE
        SYNTAX			 INTEGER
	ACCESS			 read-only
        STATUS			 mandatory
        DESCRIPTION
			"The limit of KBytes that can be used for this
			 qrV2Entry before a warning message and SNMP
			 trap is produced. This object returns the least
			 significant 32 bits of the 64 bit unsigned integer."
        ::= { qrV2Entry 22 }

	qrV2SoftFileQuotaUnlimited  OBJECT-TYPE
	SYNTAX			    INTEGER {
					     false(1),
					     true(2)
				    }
	ACCESS			    read-only
	STATUS			    mandatory
	DESCRIPTION
			"This flag designates whether or not the
			file based soft quota limit for this qrV2Entry is 
			unlimited. If false(1) then qrV2SoftFileLimit is valid,
			if true(0) qrV2SoftFileLimit is unused and will 
			return 0."
	::= { qrV2Entry 23 }

        qrV2SoftFileLimit OBJECT-TYPE
        SYNTAX		  INTEGER
	ACCESS		  read-only
        STATUS		  mandatory
        DESCRIPTION
			"The limit of files that can be used for this
			 qrV2Entry before a warning message and SNMP
			 trap is produced. This will return 0 if 
			 qrV2SoftFileQuotaUnlimited is true."
        ::= { qrV2Entry 24 }


	-- -- -- -- -- -- -- --  --
	-- the file system group --
	-- -- -- -- -- -- -- --  --

	filesysMaxfilesAvail	OBJECT-TYPE
	SYNTAX			INTEGER
	ACCESS			read-only
	STATUS			deprecated
	DESCRIPTION
				"The count of the maximum number of
				 files allowable on the root volume.  This
				 object is deprecated - use 
				 dfEntry.dfMaxFilesAvail instead."
	::= { filesys 1 }

	filesysMaxfilesUsed	OBJECT-TYPE
	SYNTAX			INTEGER
	ACCESS			read-only
	STATUS			deprecated
	DESCRIPTION
				"The count of the number of files
				 currently in use on the root volume.  
				 This object is deprecated - use
				 dfEntry.dfMaxFilesUsed instead."
	::= { filesys 2 }

	filesysMaxfilesPossible	OBJECT-TYPE
	SYNTAX                  INTEGER
	ACCESS			read-only
	STATUS			deprecated
	DESCRIPTION
				"The largest value to which the
				 filesysMaxfilesAvail parameter above can
				 be increased by reconfiguration on the
				 root volume.  This object is deprecated -
				 use dfEntry.dfMaxFilesPossible."
	::= { filesys 3 }

	dfTable			OBJECT-TYPE
	SYNTAX			SEQUENCE OF DfEntry
	ACCESS			not-accessible
	STATUS			mandatory
	DESCRIPTION
				"Provide a report of the available disk space
				 on the file systems. The tables shows the
				 available disk space for volumes as well as
				 aggregates."
	::= { filesys 4 }

	snapshot OBJECT IDENTIFIER ::= { filesys 5 }

	-- the display file system table

	dfEntry		OBJECT-TYPE
	SYNTAX		DfEntry
	ACCESS		not-accessible
	STATUS		mandatory
	DESCRIPTION
			"Provide a report of the available disk space on
			 the referenced file system."
	INDEX      { dfIndex }
	::= { dfTable 1 }

	DfEntry ::=
	    SEQUENCE {
		dfIndex
		    INTEGER,
		dfFileSys
		    DisplayString,
		dfKBytesTotal
		    INTEGER,
		dfKBytesUsed
		    INTEGER,
		dfKBytesAvail
		    INTEGER,
		dfPerCentKBytesCapacity
		    INTEGER,
		dfInodesUsed
		    INTEGER,
		dfInodesFree
		    INTEGER,
		dfPerCentInodeCapacity
		    INTEGER,
		dfMountedOn
		    DisplayString,
		dfMaxFilesAvail
		    INTEGER,
		dfMaxFilesUsed
		    INTEGER,
		dfMaxFilesPossible
		    INTEGER,
		dfHighTotalKBytes
		    INTEGER,
		dfLowTotalKBytes
		    INTEGER,
		dfHighUsedKBytes
		    INTEGER,
		dfLowUsedKBytes
		    INTEGER,
		dfHighAvailKBytes
		    INTEGER,
		dfLowAvailKBytes
		    INTEGER,
		dfStatus 
		    INTEGER,
		dfMirrorStatus 
		    INTEGER,
		dfPlexCount
		    INTEGER,
		dfType
		    INTEGER,
		dfHighSisSharedKBytes
		    INTEGER,
		dfLowSisSharedKBytes
		    INTEGER,
		dfHighSisSavedKBytes
		    INTEGER,
		dfLowSisSavedKBytes
		    INTEGER,
		dfPerCentSaved
		    INTEGER

	    }

	dfIndex		OBJECT-TYPE
	SYNTAX		INTEGER (1..2147483647)
	ACCESS		read-only
	STATUS		mandatory
	DESCRIPTION
			"A number that identifies this entry for the
			 referenced file system."
	::= { dfEntry 1 }

	dfFileSys	OBJECT-TYPE
	SYNTAX		DisplayString
	ACCESS		read-only
	STATUS		mandatory
	DESCRIPTION
			"The name for the referenced file system."
	::= { dfEntry 2 }

	-- dfKBytesTotal is DEPRECATED;
	-- use dfHighTotalKBytes and dfLowTotalKBytes

	dfKBytesTotal	OBJECT-TYPE
	SYNTAX		INTEGER
	ACCESS		read-only
	STATUS		mandatory
	DESCRIPTION
			"The total capacity in KBytes for the
			 referenced file system."
	::= { dfEntry 3 }

	-- dfKBytesUsed is DEPRECATED;
	-- use dfHighUsedKBytes and dfLowUsedKBytes

	dfKBytesUsed	OBJECT-TYPE
	SYNTAX		INTEGER
	ACCESS		read-only
	STATUS		mandatory
	DESCRIPTION
			"The total disk space in KBytes that is in use
			 on the referenced file system."
	::= { dfEntry 4 }

	-- dfKBytesAvail is DEPRECATED;
	-- use dfHighAvailKBytes and dfLowAvailKBytes

	dfKBytesAvail	OBJECT-TYPE
	SYNTAX		INTEGER
	ACCESS		read-only
	STATUS		mandatory
	DESCRIPTION
			"The total disk space in KBytes that is
			 free for use on the referenced file system."
	::= { dfEntry 5 }

	dfPerCentKBytesCapacity	OBJECT-TYPE
	SYNTAX			INTEGER
	ACCESS			read-only
	STATUS			mandatory
	DESCRIPTION
				"The percentage of disk space currently
				 in use on the referenced file system."
	::= { dfEntry 6 }

	dfInodesUsed		OBJECT-TYPE
	SYNTAX			INTEGER
	ACCESS			read-only
	STATUS			mandatory
	DESCRIPTION
				"The total number of inodes in use on the
				 referenced file system."
	::= { dfEntry 7 }

	dfInodesFree		OBJECT-TYPE
	SYNTAX			INTEGER
	ACCESS			read-only
	STATUS			mandatory
	DESCRIPTION
				"The total number of inodes that are
				 available for use on the referenced
				 file system."
	::= { dfEntry 8 }

	dfPerCentInodeCapacity	OBJECT-TYPE
	SYNTAX			INTEGER
	ACCESS			read-only
	STATUS			mandatory
	DESCRIPTION
				"The percentage of disk space currently
				 in use based on inode counts, on the
				 referenced file system."
	::= { dfEntry 9 }

	dfMountedOn		OBJECT-TYPE
	SYNTAX			DisplayString
	ACCESS			read-only
	STATUS			mandatory
	DESCRIPTION
				"The name of the file on which this file
				 system is mounted."
	::= { dfEntry 10 }

	dfMaxFilesAvail		OBJECT-TYPE
	SYNTAX			INTEGER
	ACCESS			read-only
	STATUS			mandatory
	DESCRIPTION
				"The count of the maximum number of
				 files allowable on the referenced file
				 system."
	::= { dfEntry 11 }

	dfMaxFilesUsed		OBJECT-TYPE
	SYNTAX			INTEGER
	ACCESS			read-only
	STATUS			mandatory
	DESCRIPTION
				"The count of the number of files
				 currently in use on the referenced file
				 system."
	::= { dfEntry 12 }

	dfMaxFilesPossible	OBJECT-TYPE
	SYNTAX                  INTEGER
	ACCESS			read-only
	STATUS			mandatory
	DESCRIPTION
				"The largest value to which the
				 filesysMaxfilesAvail parameter above can
				 be increased by reconfiguration on the
				 referenced file system."
	::= { dfEntry 13 }

	dfHighTotalKBytes	OBJECT-TYPE
	SYNTAX			INTEGER
	ACCESS			read-only
	STATUS			mandatory
	DESCRIPTION
				"The total capacity in KBytes for the
				 referenced file system.  This object returns
				 the most significant 32 bits of the 64 bit 
				 unsigned integer."
	::= { dfEntry 14 }

	dfLowTotalKBytes	OBJECT-TYPE
	SYNTAX			INTEGER
	ACCESS			read-only
	STATUS			mandatory
	DESCRIPTION
				"The total capacity in KBytes for the
				 referenced file system.  This object returns
				 the least significant 32 bits of the 64 bit 
				 unsigned integer."
	::= { dfEntry 15 }

	dfHighUsedKBytes	OBJECT-TYPE
	SYNTAX			INTEGER
	ACCESS			read-only
	STATUS			mandatory
	DESCRIPTION
				"The total disk space in KBytes that is in use
				 on the referenced file system.  This object
				 returns the most significant 32 bits of the
				 64 bit unsigned integer."
	::= { dfEntry 16 }

	dfLowUsedKBytes		OBJECT-TYPE
	SYNTAX			INTEGER
	ACCESS			read-only
	STATUS			mandatory
	DESCRIPTION
				"The total disk space in KBytes that is in use
				 on the referenced file system.  This object
				 returns the least significant 32 bits of the
				 64 bit unsigned integer."
	::= { dfEntry 17 }

	dfHighAvailKBytes	OBJECT-TYPE
	SYNTAX			INTEGER
	ACCESS			read-only
	STATUS			mandatory
	DESCRIPTION
				"The total disk space in KBytes that is free
				 for use on the referenced file system.
				 This object returns the most significant
				 32 bits of the 64 bit unsigned integer."
	::= { dfEntry 18 }

	dfLowAvailKBytes	OBJECT-TYPE
	SYNTAX			INTEGER
	ACCESS			read-only
	STATUS			mandatory
	DESCRIPTION
				"The total disk space in KBytes that is free
				 for use on the referenced file system.
				 This object returns the least significant
				 32 bits of the 64 bit unsigned integer."
	::= { dfEntry 19 }


        dfStatus                OBJECT-TYPE
        SYNTAX                  INTEGER { 
		unmounted(1),
		mounted(2),
		frozen(3),
		destroying(4),
		creating(5),
		mounting(6),
		unmounting(7),
		nofsinfo(8),
		replaying(9),
		replayed(10)
	} 
        ACCESS                  read-only
        STATUS                  mandatory
        DESCRIPTION
                                "The status of the file system."
        ::= { dfEntry 20 }

        dfMirrorStatus          OBJECT-TYPE
        SYNTAX                  INTEGER {
		invalid(1),
		uninitialized(2),
		needcpcheck(3),
		cpcheckwait(4),
		unmirrored(5),
		normal(6),
		degraded(7),
		resyncing(8),
		failed(9),
		limbo(10)
	} 
        ACCESS                  read-only
        STATUS                  mandatory
        DESCRIPTION
                                "Overall mirror status of the file system."
        ::= { dfEntry 21 }

        dfPlexCount             OBJECT-TYPE
        SYNTAX                  INTEGER
        ACCESS                  read-only
        STATUS                  mandatory
        DESCRIPTION
                                "Number of plexes in this file system."
        ::= { dfEntry 22 }

        dfType                  OBJECT-TYPE
        SYNTAX                  INTEGER {
		    traditionalVolume(1),
		    flexibleVolume(2),		
		    aggregate(3)
	}
        ACCESS                  read-only
        STATUS                  mandatory
        DESCRIPTION
                                "Indicates the type of container." 
        ::= { dfEntry 23 }

	dfHighSisSharedKBytes	OBJECT-TYPE
	SYNTAX			INTEGER
	ACCESS			read-only
	STATUS			mandatory
	DESCRIPTION
				"The total amount of data in KBytes that is
				 shared by more that one instance on the
				 referenced file system.  This object returns
				 the most significant 32 bits of the 64 bit
				 unsigned integer."
	::= { dfEntry 24 }

	dfLowSisSharedKBytes	OBJECT-TYPE
	SYNTAX			INTEGER
	ACCESS			read-only
	STATUS			mandatory
	DESCRIPTION
				"The total amount of data in KBytes that is
				 shared by more that one instance on the
				 referenced file system.  This object returns
				 the least significant 32 bits of the 64 bit
				 unsigned integer."
	::= { dfEntry 25 }

	dfHighSisSavedKBytes	OBJECT-TYPE
	SYNTAX			INTEGER
	ACCESS			read-only
	STATUS			mandatory
	DESCRIPTION
				"The total disk space in KBytes that is saved
				 by storing only one copy of the duplicated
				 blocks on the referenced file system.  The
				 object returns the most significant 32 bits
				 of the 64 bit unsigned integer."
	::= { dfEntry 26 }

	dfLowSisSavedKBytes	OBJECT-TYPE
	SYNTAX			INTEGER
	ACCESS			read-only
	STATUS			mandatory
	DESCRIPTION
				"The total disk space in KBytes that is saved
				 by storing only one copy of the duplicated
				 blocks on the referenced file system.  The
				 object returns the least significant 32 bits
				 of the 64 bit unsigned integer."
	::= { dfEntry 27 }

	dfPerCentSaved		OBJECT-TYPE
	SYNTAX			INTEGER
	ACCESS			read-only
	STATUS			mandatory
	DESCRIPTION
				"The percentage of disk space saved by
				 eliminating the duplicated blocks on the
				 referenced file system."
	::= { dfEntry 28 }

	-- the old single-volume snapshot table.  DEPRECATED

	slTable		OBJECT-TYPE
	SYNTAX		SEQUENCE OF SlEntry
	ACCESS		not-accessible
	STATUS		deprecated
	DESCRIPTION
			"Provide a report of the snapshots on the
			 root volume.  This table is deprecated - use
			 slVTable instead."
	::= { snapshot 1 }

	slEntry		OBJECT-TYPE
	SYNTAX		SlEntry
	ACCESS		not-accessible
	STATUS		deprecated
	DESCRIPTION
			"Provide a report on a given snapshot on the
			 root volume.  This object is deprecated - use
			 slVEntry instead."
	INDEX	{ slIndex }
	::= { slTable 1 }

	SlEntry ::=
	    SEQUENCE {
		slIndex
		    INTEGER,
		slMonth
		    INTEGER,
		slDay
		    INTEGER (1..31),
		slHour
		    INTEGER (0..23),
		slMinutes
		    INTEGER (0..59),
		slName
		    DisplayString
	    }

	slIndex		OBJECT-TYPE
	SYNTAX		INTEGER (1..2147483647)
	ACCESS		read-only
	STATUS		deprecated
	DESCRIPTION
			"A number that identifies this entry for the
			 referenced file system."
	::= { slEntry 1 }

	slMonth		OBJECT-TYPE
	SYNTAX		INTEGER {
		january(1),
		february(2),
		march(3),
		april(4),
		may(5),
		june(6),
		july(7),
		august(8),
		september(9),
		october(10),
		november(11),
		december(12)
	}
	ACCESS		read-only
	STATUS		deprecated
	DESCRIPTION
			"The month in which the snapshot was created."
	::= { slEntry 2 }

	slDay		OBJECT-TYPE
	SYNTAX		INTEGER (1..31)
	ACCESS		read-only
	STATUS		deprecated
	DESCRIPTION
			"The day on which the snapshot was created."
	::= { slEntry 3 }

	slHour		OBJECT-TYPE
	SYNTAX		INTEGER (0..23)
	ACCESS		read-only
	STATUS		deprecated
	DESCRIPTION
			"The hour in which the snapshot was created."
	::= { slEntry 4 }

	slMinutes	OBJECT-TYPE
	SYNTAX		INTEGER (0..59)
	ACCESS		read-only
	STATUS		deprecated
	DESCRIPTION
			"The minute in which the snapshot was created."
	::= { slEntry 5 }

	slName		OBJECT-TYPE
	SYNTAX		DisplayString
	ACCESS		read-only
	STATUS		deprecated
	DESCRIPTION
			"The name of the referenced snapshot."
	::= { slEntry 6 }


	-- The multivolume / aggregate snapshot table.

	slVTable	OBJECT-TYPE
	SYNTAX		SEQUENCE OF SlVEntry
	ACCESS		not-accessible
	STATUS		mandatory
	DESCRIPTION
			"Provide a report of the snapshots on the
			 file systems."
	::= { snapshot 2 }

	slVEntry	OBJECT-TYPE
	SYNTAX		SlVEntry
	ACCESS		not-accessible
	STATUS		mandatory
	DESCRIPTION
			"Provide a report on a given snapshot on the
			 file system.  Indices select the volume of
			 the snapshot and the snapshot entry itself."
	INDEX	{ slVVolume, slVIndex }
	::= { slVTable 1 }

	SlVEntry ::=
	    SEQUENCE {
		slVIndex
		    INTEGER,
		slVMonth
		    INTEGER,
		slVDay
		    INTEGER (1..31),
		slVHour
		    INTEGER (0..23),
		slVMinutes
		    INTEGER (0..59),
		slVName
		    DisplayString,
		slVVolume
		    INTEGER,
		slVNumber
		    INTEGER,
		slVVolumeName
		    DisplayString,
		slVType
		    INTEGER
	    }

	slVIndex	OBJECT-TYPE
	SYNTAX		INTEGER (1..2147483647)
	ACCESS		read-only
	STATUS		mandatory
	DESCRIPTION
			"A number that identifies this entry for the
			 referenced file system."
	::= { slVEntry 1 }

	slVMonth		OBJECT-TYPE
	SYNTAX		INTEGER {
		january(1),
		february(2),
		march(3),
		april(4),
		may(5),
		june(6),
		july(7),
		august(8),
		september(9),
		october(10),
		november(11),
		december(12)
	}
	ACCESS		read-only
	STATUS		mandatory
	DESCRIPTION
			"The month in which the snapshot was created."
	::= { slVEntry 2 }

	slVDay		OBJECT-TYPE
	SYNTAX		INTEGER (1..31)
	ACCESS		read-only
	STATUS		mandatory
	DESCRIPTION
			"The day on which the snapshot was created."
	::= { slVEntry 3 }

	slVHour		OBJECT-TYPE
	SYNTAX		INTEGER (0..23)
	ACCESS		read-only
	STATUS		mandatory
	DESCRIPTION
			"The hour in which the snapshot was created."
	::= { slVEntry 4 }

	slVMinutes	OBJECT-TYPE
	SYNTAX		INTEGER (0..59)
	ACCESS		read-only
	STATUS		mandatory
	DESCRIPTION
			"The minute in which the snapshot was created."
	::= { slVEntry 5 }

	slVName		OBJECT-TYPE
	SYNTAX		DisplayString
	ACCESS		read-only
	STATUS		mandatory
	DESCRIPTION
			"The name of the referenced snapshot."
	::= { slVEntry 6 }

	slVVolume	OBJECT-TYPE
	SYNTAX		INTEGER (1..2147483647)
	ACCESS		read-only
	STATUS		mandatory
	DESCRIPTION
			"A number that identifies the volume  / aggregate that 
			 contains this snapshot."
	::= { slVEntry 7 }

	slVNumber	OBJECT-TYPE
	SYNTAX		INTEGER
	ACCESS		read-only
	STATUS		mandatory
	DESCRIPTION
			"Number of snapshots for this volume / aggregate."
	::= { slVEntry 8 }

	slVVolumeName	OBJECT-TYPE
	SYNTAX		DisplayString
	ACCESS		read-only
	STATUS		mandatory
	DESCRIPTION
			"The name of the volume / aggregate. This does not 
			 have a /vol/ prefix."

	::= { slVEntry 9 }

	slVType 	OBJECT-TYPE
	SYNTAX		INTEGER {
		  traditionalVolume(1),
		  flexibleVolume(2),
		  aggregate(3)	
	}
	ACCESS		read-only
	STATUS		mandatory
	DESCRIPTION
			"Indicates the type of container for this
			 snapshot."

	::= { slVEntry 10 }


	-- The snapshot content table.

	slQTable	OBJECT-TYPE
	SYNTAX		SEQUENCE OF SlQEntry
	ACCESS		not-accessible
	STATUS		mandatory
	DESCRIPTION
			"Provide a report of the snapshots and their contents
			on the file systems."
	::= { snapshot 3 }

	slQEntry	OBJECT-TYPE
	SYNTAX		SlQEntry
	ACCESS		not-accessible
	STATUS		mandatory
	DESCRIPTION
			"Provide a report on a given snapshot for a given 
			qtree on the file system.  Indices select the volume 
			and qtree of the snapshot and the snapshot entry 
			itself."

	INDEX	{ slQVolume, slQQtree, slQIndex }
	::= { slQTable 1 }

	SlQEntry ::=
	    SEQUENCE {
		slQIndex
		    INTEGER,
		slQVolume
		    INTEGER,    
		slQQtree
		    INTEGER,
		slQSnapshotName
		    DisplayString,
    	        slQSnapshotTime
		    INTEGER,
		slQQtreeName
		    DisplayString,
  	        slQQtreeContent
		    INTEGER,
		slQSource	
		    OCTET STRING,
		slQSourceTime
		    INTEGER,
		slQVolumeName
		    DisplayString
	    }

	slQIndex	OBJECT-TYPE
	SYNTAX		INTEGER (1..2147483647)
	ACCESS		read-only
	STATUS		mandatory
	DESCRIPTION
			"A number that identifies this entry for the
			 referenced file system."
	::= { slQEntry 1 }

	slQVolume	OBJECT-TYPE
	SYNTAX		INTEGER (1..2147483647)
	ACCESS		read-only
	STATUS		mandatory
	DESCRIPTION
			"A number that identifies the volume that contains
			this snapshot."
	::= { slQEntry 2 }

	slQQtree	OBJECT-TYPE
	SYNTAX		INTEGER (1..2147483647)
	ACCESS		read-only
	STATUS		mandatory
	DESCRIPTION
			"A number that identifies the qtree that contains
			this snapshot."
	::= { slQEntry 3 }

	slQSnapshotName	OBJECT-TYPE
	SYNTAX		DisplayString
	ACCESS		read-only
	STATUS		mandatory
	DESCRIPTION
			"The name of the referenced snapshot."
	::= { slQEntry 4 }

	slQSnapshotTime	OBJECT-TYPE
	SYNTAX		INTEGER
	ACCESS		read-only
	STATUS		mandatory
	DESCRIPTION
			"Time of the snapshot on the system. The time in 
			seconds since January 1, 1970."
	::= { slQEntry 5 }

	slQQtreeName	OBJECT-TYPE
	SYNTAX		DisplayString
	ACCESS		read-only
	STATUS		mandatory
	DESCRIPTION
			"A string that indicates which qtree is in this 
			snapshot"
	::= { slQEntry 6 }

        slQQtreeContent	OBJECT-TYPE 
	SYNTAX		INTEGER {
				replica(1),
				transitioning(2),
				original(3)
				}
	ACCESS		read-only
	STATUS		mandatory
	DESCRIPTION
	                "The content of the qtree tree"
	::= { slQEntry 7 }

	slQSource	OBJECT-TYPE 
	SYNTAX		OCTET STRING
	ACCESS		read-only
	STATUS		mandatory
	DESCRIPTION
	    		"The source of this qtree for a replicated qtree.
			'-' for a original qtree."
	::= { slQEntry 8 }

	slQSourceTime	OBJECT-TYPE
	SYNTAX		INTEGER
	ACCESS		read-only
	STATUS		mandatory
	DESCRIPTION
			"Time of the source snapshot for a replicated qtree.
			Time of the current snapshot for an original qtree.
			The time in seconds since January 1, 1970. 0 if the 
			qtree is in a transitioning stage"

	::= { slQEntry 9 }

	slQVolumeName	OBJECT-TYPE
	SYNTAX		DisplayString
	ACCESS		read-only
	STATUS		mandatory
	DESCRIPTION
			"The name of the volume. This does not have a /vol/
			prefix."
	::= { slQEntry 10 }


	dfNumber		OBJECT-TYPE
	SYNTAX			INTEGER
	ACCESS			read-only
	STATUS			mandatory
	DESCRIPTION
			"Number of entries in the dfTable table."

	::= { filesys 6 }

	-- -- -- -- -- -- -- -- -- -- -- --
	-- file system status information --
	-- -- -- -- -- -- -- -- -- -- -- --

	fsStatus OBJECT IDENTIFIER ::= { filesys 7 }

	fsOverallStatus	OBJECT-TYPE
	SYNTAX		INTEGER {
				ok(1),
				nearlyFull(2),
				full(3)
				}
	ACCESS		read-only
	STATUS		mandatory
	DESCRIPTION
			"An indication of overall file system
			health.  'ok' indicates that all file systems
			have adequate space.  'nearlyFull' means
			that one or more is nearly full (more than
			95% full). 'full' means that one or more
			are more than 98% full."
	::= { fsStatus 1 }

	fsStatusMessage	OBJECT-TYPE
	SYNTAX		DisplayString
	ACCESS		read-only
	STATUS		mandatory
	DESCRIPTION
			"A string indicating any file systems which
			are full or nearly full."
	::= { fsStatus 2 }

	fsMaxUsedBytesPerCent	OBJECT-TYPE
	SYNTAX		INTEGER (0..100)
	ACCESS		read-only
	STATUS		mandatory
	DESCRIPTION
			"The percentage of space currently in use
			by the file system which is most full."
	::= { fsStatus 3 }

	fsMaxUsedInodesPerCent	OBJECT-TYPE
	SYNTAX		INTEGER (0..100)
	ACCESS		read-only
	STATUS		mandatory
	DESCRIPTION
			"The percentage of inodes currently in use
			by the file system which is most full."
	::= { fsStatus 4 }
	
	fsMaxUsedReservedPerCent OBJECT-TYPE
	SYNTAX		INTEGER (0..100)
	ACCESS		read-only
	STATUS		mandatory
	DESCRIPTION
			"The percentage of reserved space currently 
			in use by the file system which is most full."
	::= { fsStatus 5 }

	-- -- -- -- -- -- -- -- -- -- -- -- -- -- -- -- -- -- --
	-- 
	--  All volumes, including those offline and those
	--  owned by the cluster partner.
	--
	-- -- -- -- -- -- -- -- -- -- -- -- -- -- -- -- -- -- --

	volTable	OBJECT-TYPE
	SYNTAX		SEQUENCE OF VolEntry
	ACCESS		not-accessible
	STATUS		mandatory
	DESCRIPTION
			"List the volumes defined on the system,
			including offline volumes."

	::= { filesys 8 }

	volEntry	OBJECT-TYPE
	SYNTAX		VolEntry
	ACCESS		not-accessible
	STATUS		mandatory
	DESCRIPTION
			"Provide details about a particular volume."
	INDEX	{ volIndex }
	::= { volTable 1 }

	VolEntry ::=
	    SEQUENCE {
		volIndex	INTEGER,
		volName		DisplayString,
		volFSID		DisplayString,
		volOwningHost	INTEGER,
		volState	DisplayString,
		volStatus	DisplayString,
		volOptions	DisplayString,
		volUUID		DisplayString,
		volAggrName	DisplayString,
		volType		INTEGER,
		volClone	INTEGER,
		volCloneOf	DisplayString,
		volCloneSnap	DisplayString
	    }

	volIndex	OBJECT-TYPE
	SYNTAX		INTEGER (1..2048)
	ACCESS		read-only
	STATUS		mandatory
	DESCRIPTION
			"A number that identifies this volume.  The
			volIndex is not related to any other table
			defined in this MIB, and may change as
			volumes are created and destroyed."
	::= { volEntry 1 }

	volName		OBJECT-TYPE
	SYNTAX		DisplayString
	ACCESS		read-only
	STATUS		mandatory
	DESCRIPTION
			"Name of the volume.  This includes no /vol/
			prefix."
	::= { volEntry 2 }

	volFSID		OBJECT-TYPE
	SYNTAX		DisplayString
	ACCESS		read-only
	STATUS		mandatory
	DESCRIPTION
			"Unique identifier for this volume."
	::= { volEntry 3 }

	volOwningHost	OBJECT-TYPE
	SYNTAX		INTEGER {
				local(1),
				partner(2)
	}
	ACCESS		read-only
	STATUS		mandatory
	DESCRIPTION
			"Indication of which host owns this volume."
	::= { volEntry 4 }

	volState	OBJECT-TYPE
	SYNTAX		DisplayString
	ACCESS		read-only
	STATUS		mandatory
	DESCRIPTION
			"State of the volume, such as 'online' or
			'offline'."
	::= { volEntry 5 }

	volStatus	OBJECT-TYPE
	SYNTAX		DisplayString
	ACCESS		read-only
	STATUS		mandatory
	DESCRIPTION
			"Status of the volume, such as 'normal' or
			'reconstructing'. May include several values
			separated by comma and space."
	::= { volEntry 6 }

	volOptions	OBJECT-TYPE
	SYNTAX		DisplayString
	ACCESS		read-only
	STATUS		mandatory
	DESCRIPTION
			"Options associated with the volume, such 
			as 'root' and 'nosnapdir=off'. May include
			several values separated by comma."
	::= { volEntry 7 }

	volUUID		OBJECT-TYPE
	SYNTAX		DisplayString
	ACCESS		read-only
	STATUS		mandatory
	DESCRIPTION
			"A unique id associated with the volume."  
	::= { volEntry 8 }

        volAggrName 	OBJECT-TYPE
        SYNTAX          DisplayString
        ACCESS          read-only
        STATUS         	optional 
        DESCRIPTION
                        "Name of the aggregate this flexible volume is a
                         part of."
        ::= { volEntry 9 }

        volType     	OBJECT-TYPE
        SYNTAX          INTEGER {
                                traditional(1),
                                flexible(2)
        }
        ACCESS          read-only
        STATUS         	optional 
        DESCRIPTION
                        "Type of this volume, older volumes are
                         traditional while newer volumes contained in
                         aggregates are flexible."
        ::= { volEntry 10 }

        volClone    	OBJECT-TYPE
        SYNTAX          INTEGER {
                                false(1),
                                true(2)
        }
        ACCESS          read-only
        STATUS          optional  
        DESCRIPTION
                        "True indicates flexible volume is a clone."
        ::= { volEntry 11 }

        volCloneOf  	OBJECT-TYPE
        SYNTAX          DisplayString
        ACCESS          read-only
        STATUS         	optional 
        DESCRIPTION
                        "Name of flexible volume this flexible volume is
                         a clone of."
        ::= { volEntry 12 }

        volCloneSnap 	OBJECT-TYPE
        SYNTAX          DisplayString
        ACCESS          read-only
        STATUS         	optional 
        DESCRIPTION
                        "Name of original cloned snapshot."
        ::= { volEntry 13 }

	volNumber	OBJECT-TYPE
	SYNTAX		INTEGER (0..2048)
	ACCESS		read-only
	STATUS		mandatory
	DESCRIPTION
			"Number of volumes in the volTable."

	::= { filesys 9 }


        qtreeTable	OBJECT-TYPE
	SYNTAX		SEQUENCE OF QtreeEntry
	ACCESS		not-accessible
	STATUS		mandatory
	DESCRIPTION
			"Provide a list of the qtrees on the system."

	::= { filesys 10 }

	qtreeEntry	OBJECT-TYPE
	SYNTAX		QtreeEntry
	ACCESS		not-accessible
	STATUS		mandatory
	DESCRIPTION
	                "Provide details about a particular qtree."

	INDEX   { qtreeVolume, qtreeIndex }
        ::= { qtreeTable 1 }

        QtreeEntry ::=
	    SEQUENCE {
		qtreeIndex	INTEGER,
		qtreeVolume	INTEGER,
		qtreeVolumeName	DisplayString,
		qtreeId	        INTEGER,
		qtreeName	DisplayString,
		qtreeStyle	INTEGER,
		qtreeStatus	INTEGER,
		qtreeOplock	INTEGER
	    }	    

	qtreeIndex	OBJECT-TYPE
    	SYNTAX		INTEGER (1..255)
	ACCESS		read-only
	STATUS		mandatory
	DESCRIPTION
			"Index into the qtree table."  
	    
	::= { qtreeEntry 1 }	    

	qtreeVolume	OBJECT-TYPE
	SYNTAX		INTEGER (1..2147483647)
	ACCESS		read-only
	STATUS		mandatory
	DESCRIPTION
	                "A number that identifies the volume that contains
			this qtree."

	::= { qtreeEntry 2 }

	qtreeVolumeName	OBJECT-TYPE
	SYNTAX		DisplayString
	ACCESS		read-only
	STATUS		mandatory
	DESCRIPTION
			"The name of the volume that contains this qtree. 
			This includes no /vol/prefix."

	::= { qtreeEntry 3 }	    	    

	qtreeId		OBJECT-TYPE
    	SYNTAX		INTEGER (1..255)
	ACCESS		read-only
	STATUS		mandatory
	DESCRIPTION
			"The Id number of the qtree."  
	    
	::= { qtreeEntry 4 }

	qtreeName	OBJECT-TYPE
	SYNTAX		DisplayString
	ACCESS		read-only
	STATUS		mandatory
	DESCRIPTION
	                "The name of the qtree."

	::= { qtreeEntry 5 }	    

	qtreeStyle	OBJECT-TYPE
        SYNTAX          INTEGER {
                                unix(1),
                                ntfs(2),
				mixed(3)
                                }
        ACCESS          read-only
        STATUS          mandatory
        DESCRIPTION
	                "The security style of the qtree."

        ::= { qtreeEntry 6 }	    

	qtreeStatus	OBJECT-TYPE
        SYNTAX          INTEGER {
                                normal(1),
                                snapmirrored(2),
				snapvaulted(3)
                                }
        ACCESS          read-only
        STATUS          mandatory
        DESCRIPTION
	                "The status of the qtree."

	::= { qtreeEntry 7 }	        

	qtreeOplock	OBJECT-TYPE
        SYNTAX          INTEGER {
                                enabled(1),
                                disabled(2)
                                }
        ACCESS          read-only
        STATUS          mandatory
        DESCRIPTION
                        "An indication of whether the oplocks is enabled or not
			for this qtree."

	::= { qtreeEntry 8 }

        -- -- -- -- -- -- -- -- -- -- -- -- -- -- -- -- -- -- --
        --
        --  All aggregates, including those offline and those
        --  owned by the cluster partner.
        --
        -- -- -- -- -- -- -- -- -- -- -- -- -- -- -- -- -- -- --

        aggrTable       OBJECT-TYPE
        SYNTAX          SEQUENCE OF AggrEntry
        ACCESS          not-accessible
        STATUS          mandatory
        DESCRIPTION
                        "List the aggregates defined on the system,
                        including offline aggregates."

        ::= { filesys 11 }

        aggrEntry       OBJECT-TYPE
        SYNTAX          AggrEntry
        ACCESS          not-accessible
        STATUS          mandatory
        DESCRIPTION
                        "Provide details about a particular aggregate."
        INDEX   { aggrIndex }
        ::= { aggrTable 1 }

        AggrEntry ::=
            SEQUENCE {
                aggrIndex       INTEGER,
                aggrName        DisplayString,
                aggrFSID        DisplayString,
                aggrOwningHost  INTEGER,
                aggrState       DisplayString,
                aggrStatus      DisplayString,
                aggrOptions     DisplayString,
                aggrUUID        DisplayString,
		aggrFlexvollist OCTET STRING,
		aggrType	INTEGER
            }

        aggrIndex       OBJECT-TYPE
        SYNTAX          INTEGER (1..2048)
        ACCESS          read-only
        STATUS          mandatory
        DESCRIPTION
                        "A number that identifies this aggregate.  The
                        aggrIndex is not related to any other table
                        defined in this MIB, and may change as
                        aggregates are created and destroyed."
        ::= { aggrEntry 1 }

        aggrName        OBJECT-TYPE
        SYNTAX          DisplayString
        ACCESS          read-only
        STATUS          mandatory
        DESCRIPTION
                        "Name of the aggregate.  This includes no /vol/
                        prefix."
        ::= { aggrEntry 2 }

        aggrFSID        OBJECT-TYPE
        SYNTAX          DisplayString
        ACCESS          read-only
        STATUS          mandatory
        DESCRIPTION
                        "Unique identifier for this aggregate."
        ::= { aggrEntry 3 }

        aggrOwningHost  OBJECT-TYPE
        SYNTAX          INTEGER {
                                local(1),
                                partner(2)
        }
        ACCESS          read-only
        STATUS          mandatory
        DESCRIPTION
                        "Indication of which host owns this aggregate."
        ::= { aggrEntry 4 }

        aggrState       OBJECT-TYPE
        SYNTAX          DisplayString
        ACCESS          read-only
        STATUS          mandatory
        DESCRIPTION
                        "State of the aggregate, such as 'online' or
                        'offline'."
        ::= { aggrEntry 5 }

        aggrStatus      OBJECT-TYPE
        SYNTAX          DisplayString
        ACCESS          read-only
        STATUS          mandatory
        DESCRIPTION
                        "Status of the aggregate, such as 'normal' or
                        'reconstructing'. May include several values
                        separated by comma and space."
        ::= { aggrEntry 6 }

        aggrOptions     OBJECT-TYPE
        SYNTAX          DisplayString
        ACCESS          read-only
        STATUS          mandatory
        DESCRIPTION
                        "Options associated with the aggregate."
        ::= { aggrEntry 7 }

        aggrUUID        OBJECT-TYPE
        SYNTAX          DisplayString
        ACCESS          read-only
        STATUS          mandatory
        DESCRIPTION
                        "A unique id associated with the aggregate."
        ::= { aggrEntry 8 }

        aggrFlexvollist OBJECT-TYPE
        SYNTAX          OCTET STRING (SIZE (0..1024))
        ACCESS          read-only
        STATUS          mandatory
        DESCRIPTION
                        "List of all the flexible volumes within this
			 aggregate."
        ::= { aggrEntry 9 }

        aggrType     	OBJECT-TYPE
        SYNTAX          INTEGER {
                                traditional(1),
                                aggregate(2)
        }
        ACCESS          read-only
        STATUS         	mandatory 
        DESCRIPTION
                        "Type of this container, containers
			 containing flexible volumes are aggregate."
        ::= { aggrEntry 10 }

        aggrNumber      OBJECT-TYPE
        SYNTAX          INTEGER (0..2048)
        ACCESS          read-only
        STATUS          mandatory
        DESCRIPTION
                        "Number of aggregates in the aggrTable."
        ::= { filesys 12 }

	-- -- -- -- -- -- --
	-- the RAID group --
	-- -- -- -- -- -- --

	-- Old root volume raid table.  DEPRECATED

	raidTable	OBJECT-TYPE
	SYNTAX		SEQUENCE OF RaidEntry
	ACCESS		not-accessible
	STATUS		deprecated
	DESCRIPTION
			"Display RAID configuration information for the
			 root volume.  This table is deprecated - use
			 raidVTable instead."
	::= { raid 1 }

	raidEntry	OBJECT-TYPE
	SYNTAX		RaidEntry
	ACCESS		not-accessible
	STATUS		deprecated
	DESCRIPTION
			"Display RAID configuration information for
			 the referenced disk drive.  This only works for
			 disks contained within the root volume, and will
			 include spare drives.  This object is 
			 deprecated - use raidVEntry instead."
	INDEX	{ raidIndex }
	::= { raidTable 1 }

	RaidEntry ::=
	    SEQUENCE {
		raidIndex
		    INTEGER,
		raidDiskName
		    DisplayString,
		raidStatus
		    INTEGER,
		raidDiskId
		    INTEGER,
		raidScsiAdapter
		    DisplayString,
		raidScsiId
		    INTEGER (0..100),
		raidUsedMb
		    INTEGER,
		raidUsedBlocks
		    INTEGER,
		raidTotalMb
		    INTEGER,
		raidTotalBlocks
		    INTEGER,
		raidCompletionPerCent
		    INTEGER (0..100)
	    }

	raidIndex	OBJECT-TYPE
	SYNTAX		INTEGER (1..2147483647)
	ACCESS		read-only
	STATUS		deprecated
	DESCRIPTION
			"A number that identifies this entry for the
			 referenced disk drive."
	::= { raidEntry 1 }

	raidDiskName	OBJECT-TYPE
	SYNTAX		DisplayString
	ACCESS		read-only
	STATUS		deprecated
	DESCRIPTION
			"The name identifying the referenced disk drive."
	::= { raidEntry 2 }

	raidStatus	OBJECT-TYPE
	SYNTAX		INTEGER {
		active(1),
		reconstructionInProgress(2),
		parityReconstructionInProgress(3),
		parityVerificationInProgress(4),
		scrubbingInProgress(5),
		failed(6),
		addingSpare(7),
		spare(8),
		prefailed(9),
		offline(10)
	}
	ACCESS		read-only
	STATUS		deprecated
	DESCRIPTION
			"The status of the referenced disk drive."
	::= { raidEntry 3 }

	raidDiskId	OBJECT-TYPE
	SYNTAX		INTEGER
	ACCESS		read-only
	STATUS		deprecated
	DESCRIPTION
			"The disk identifier for the referenced disk
			 drive."
	::= { raidEntry 4 }

	raidScsiAdapter	OBJECT-TYPE
	SYNTAX		DisplayString
	ACCESS		read-only
	STATUS		deprecated
	DESCRIPTION
			"The identifier of the SCSI adapter for the
			 referenced disk drive."
	::= { raidEntry 5 }

	raidScsiId	OBJECT-TYPE
	SYNTAX		INTEGER (0..100)
	ACCESS		read-only
	STATUS		deprecated
	DESCRIPTION
			"The identifier for the referenced disk drive
			 on the referenced SCSI adapter."
	::= { raidEntry 6 }

	raidUsedMb	OBJECT-TYPE
	SYNTAX		INTEGER
	ACCESS		read-only
	STATUS		deprecated
	DESCRIPTION
			"The number of MBytes currently in use on
			 the referenced disk drive."
	::= { raidEntry 7 }

	raidUsedBlocks	OBJECT-TYPE
	SYNTAX		INTEGER
	ACCESS		read-only
	STATUS		deprecated
	DESCRIPTION
			"The number of Blocks currently in use on
			 the referenced disk drive."
	::= { raidEntry 8 }

	raidTotalMb	OBJECT-TYPE
	SYNTAX		INTEGER
	ACCESS		read-only
	STATUS		deprecated
	DESCRIPTION
			"The number of MBytes physically available
			 on the referenced disk drive."
	::= { raidEntry 9 }

	raidTotalBlocks	OBJECT-TYPE
	SYNTAX		INTEGER
	ACCESS		read-only
	STATUS		deprecated
	DESCRIPTION
			"The number of Blocks physically available
			 on the referenced disk drive."
	::= { raidEntry 10 }

	raidCompletionPerCent OBJECT-TYPE
	SYNTAX		      INTEGER (0..100)
	ACCESS		      read-only
	STATUS		      deprecated
	DESCRIPTION
			 "In the case when reconstruction/adding a
			  spare, verification or scrubbing is in progress,
			  the percent of such reconstruction, verification
			  or scrubbing that has been completed on the
			  referenced disk drive."
	::= { raidEntry 11 }


	-- Multivolume raidTable.


 	raidVTable	OBJECT-TYPE
	SYNTAX		SEQUENCE OF RaidVEntry
	ACCESS		not-accessible
	STATUS		mandatory
	DESCRIPTION
			"Display RAID configuration information."
	::= { raid 2 }

	raidVEntry	OBJECT-TYPE
	SYNTAX		RaidVEntry
	ACCESS		not-accessible
	STATUS		mandatory
	DESCRIPTION
			"Display RAID configuration information for
			 the referenced volume, raid group, and disk drive."
	INDEX	{ raidVVol, raidVGroup, raidVIndex }
	::= { raidVTable 1 }

	RaidVEntry ::=
	    SEQUENCE {
		raidVIndex
		    INTEGER,
		raidVDiskName
		    DisplayString,
		raidVStatus
		    INTEGER,
		raidVDiskId
		    INTEGER,
		raidVScsiAdapter
		    DisplayString,
		raidVScsiId
		    INTEGER (0..100),
		raidVUsedMb
		    INTEGER,
		raidVUsedBlocks
		    INTEGER,
		raidVTotalMb
		    INTEGER,
		raidVTotalBlocks
		    INTEGER,
		raidVCompletionPerCent
		    INTEGER (0..100),
		raidVVol
		    INTEGER,
		raidVGroup
		    INTEGER,
		raidVDiskNumber
		    INTEGER,
		raidVGroupNumber
		    INTEGER,
		raidVDiskPort
		    INTEGER,
		raidVSecondaryDiskName
		    DisplayString,
		raidVSecondaryDiskPort
		    INTEGER,
		raidVShelf
		    INTEGER,
		raidVBay
		    INTEGER,
                raidVPlex
                    INTEGER, 
                raidVPlexGroup
                    INTEGER, 
                raidVPlexNumber
                    INTEGER (1..2), 
                raidVPlexName
                    DisplayString, 
                raidVSectorSize
                    INTEGER, 
		raidVDiskSerialNumber
		    DisplayString,
		raidVDiskVendor
		    DisplayString,
		raidVDiskModel
		    DisplayString,
		raidVDiskFirmwareRevision
		    DisplayString,
		raidVDiskRPM
		    DisplayString,
		raidVDiskType
		    DisplayString,
		raidVDiskPool
		    DisplayString,
		raidVDiskCopyDestDiskName
		    DisplayString
	    }

	raidVIndex	OBJECT-TYPE
	SYNTAX		INTEGER (1..2147483647)
	ACCESS		read-only
	STATUS		mandatory
	DESCRIPTION
			"A number that identifies this disk drive within 
			 the given volume and RAID group."
	::= { raidVEntry 1 }

	raidVDiskName	OBJECT-TYPE
	SYNTAX		DisplayString
	ACCESS		read-only
	STATUS		mandatory
	DESCRIPTION
			"The name identifying the referenced disk drive."
	::= { raidVEntry 2 }

	raidVStatus	OBJECT-TYPE
	SYNTAX		INTEGER {
		active(1),
		reconstructionInProgress(2),
		parityReconstructionInProgress(3),
		parityVerificationInProgress(4),
		scrubbingInProgress(5),
		failed(6),
		prefailed(9),
		offline(10)
	}
	ACCESS		read-only
	STATUS		mandatory
	DESCRIPTION
			"The status of the referenced disk drive."
	::= { raidVEntry 3 }

	raidVDiskId	OBJECT-TYPE
	SYNTAX		INTEGER
	ACCESS		read-only
	STATUS		mandatory
	DESCRIPTION
			"The disk identifier for the referenced disk
			 drive."
	::= { raidVEntry 4 }

	raidVScsiAdapter	OBJECT-TYPE
	SYNTAX		DisplayString
	ACCESS		read-only
	STATUS		mandatory
	DESCRIPTION
			"The identifier of the SCSI adapter for the
			 referenced disk drive."
	::= { raidVEntry 5 }

	raidVScsiId	OBJECT-TYPE
	SYNTAX		INTEGER (0..100)
	ACCESS		read-only
	STATUS		mandatory
	DESCRIPTION
			"The identifier for the referenced disk drive
			 on the referenced SCSI adapter."
	::= { raidVEntry 6 }

	raidVUsedMb	OBJECT-TYPE
	SYNTAX		INTEGER
	ACCESS		read-only
	STATUS		mandatory
	DESCRIPTION
			"The number of MBytes currently in use on
			 the referenced disk drive."
	::= { raidVEntry 7 }

	raidVUsedBlocks	OBJECT-TYPE
	SYNTAX		INTEGER
	ACCESS		read-only
	STATUS		mandatory
	DESCRIPTION
			"The number of Blocks currently in use on
			 the referenced disk drive."
	::= { raidVEntry 8 }

	raidVTotalMb	OBJECT-TYPE
	SYNTAX		INTEGER
	ACCESS		read-only
	STATUS		mandatory
	DESCRIPTION
			"The number of MBytes physically available
			 on the referenced disk drive."
	::= { raidVEntry 9 }

	raidVTotalBlocks	OBJECT-TYPE
	SYNTAX		INTEGER
	ACCESS		read-only
	STATUS		mandatory
	DESCRIPTION
			"The number of Blocks physically available
			 on the referenced disk drive."
	::= { raidVEntry 10 }

	raidVCompletionPerCent OBJECT-TYPE
	SYNTAX		      INTEGER (0..100)
	ACCESS		      read-only
	STATUS		      mandatory
	DESCRIPTION
			 "In the case when rapid raid recovery, disk copy,
			  reconstruction/adding a spare, verification or 
			  scrubbing is in progress, the percent of such 
			  copy, reconstruction, verification or scrubbing 
			  that has been completed on the referenced disk 
			  drive."
	::= { raidVEntry 11 }

	raidVVol	OBJECT-TYPE
	SYNTAX		INTEGER (1..2147483647)
	ACCESS		read-only
	STATUS		mandatory
	DESCRIPTION
			"A number that identifies the volume that this entry
			 belongs to.  The first volume is '1'."
	::= { raidVEntry 12 }

	raidVGroup	OBJECT-TYPE
	SYNTAX		INTEGER (1..2147483647)
	ACCESS		read-only
	STATUS		mandatory
	DESCRIPTION
			"A number that identifies the RAID group within the
			 given volume that this entry belongs to.  The
			 first RAID group is '1', and number across all plexes."
	::= { raidVEntry 13 }

	raidVDiskNumber	OBJECT-TYPE
	SYNTAX		INTEGER
	ACCESS		read-only
	STATUS		mandatory
	DESCRIPTION
			"The number of disks within this RAID group."
	::= { raidVEntry 14 }

	raidVGroupNumber OBJECT-TYPE
	SYNTAX		INTEGER
	ACCESS		read-only
	STATUS		mandatory
	DESCRIPTION
			"The number of RAID groups within this volume."
	::= { raidVEntry 15 }

	raidVDiskPort	OBJECT-TYPE
	SYNTAX		INTEGER {
					portA(1),
					portB(2),
					portSingle(3),
					portNone(4)
				}
	ACCESS		read-only
	STATUS		mandatory
	DESCRIPTION
			"A number that indicates which port of the
			disk is being used by the primary path to the disk.
			For a dual-ported disk, values of portA and portB
			indicate which port is being used.
			If the disk only has a single port, the value
			is portSingle, and if the port is not active, 
			the value is portNone."
	::= { raidVEntry 16 }

	raidVSecondaryDiskName	OBJECT-TYPE
	SYNTAX		DisplayString
	ACCESS		read-only
	STATUS		mandatory
	DESCRIPTION
			"The name identifying the secondary path to
			the referenced disk drive."
	::= { raidVEntry 17 }

	raidVSecondaryDiskPort	OBJECT-TYPE
	SYNTAX		INTEGER {
					portA(1),
					portB(2),
					portSingle(3),
					portNone(4)
				}
	ACCESS		read-only
	STATUS		mandatory
	DESCRIPTION
			"A number that indicates which port of the
			disk is being used by the secondary path to the disk.
			For a dual-ported disk, values of portA and portB
			indicate which port is being used.
			If the disk only has a single port, the value
			is portSingle, and if the port is not active, 
			the value is portNone."
	::= { raidVEntry 18 }

	raidVShelf	OBJECT-TYPE
	SYNTAX		INTEGER
	ACCESS		read-only
	STATUS		mandatory
	DESCRIPTION
			"Number identifying the shelf where the disk
			is located."
	::= { raidVEntry 19 }

	raidVBay	OBJECT-TYPE
	SYNTAX		INTEGER
	ACCESS		read-only
	STATUS		mandatory
	DESCRIPTION
			"Number identifying the disk bay within
			the shelf where the disk is located."
	::= { raidVEntry 20 }


        raidVPlex       OBJECT-TYPE
        SYNTAX          INTEGER
        ACCESS          read-only
        STATUS          mandatory
        DESCRIPTION
                        "A number that identifies the plex within the
                         given volume that this entry belongs to.  The
                         first plex is '1'."
        ::= { raidVEntry 21 } 

        raidVPlexGroup  OBJECT-TYPE
        SYNTAX          INTEGER
        ACCESS          read-only
        STATUS          mandatory
        DESCRIPTION
                        "A number that identifies the RAID group within
                         the given plex that this entry belongs to.  The
                         first RAID group is '1'."
        ::= { raidVEntry 22 } 

	raidVPlexNumber	OBJECT-TYPE
	SYNTAX		INTEGER (1..2)
	ACCESS		read-only
	STATUS		mandatory
	DESCRIPTION
			"The number of plexes within this volume.
                        This number is always 1 or 2."
	::= { raidVEntry 23 }

        raidVPlexName   OBJECT-TYPE
	SYNTAX		DisplayString
	ACCESS		read-only
	STATUS		mandatory
	DESCRIPTION
			"A name that identifies the plex that this entry
			 belongs to.  A plex name can be anything, but
                         is usually a string like 'plex0' or 'plex1'."
        ::= { raidVEntry 24 } 

        raidVSectorSize OBJECT-TYPE
        SYNTAX          INTEGER
        ACCESS          read-only
        STATUS          mandatory
        DESCRIPTION
                        "A number that specifies bytes per sector
                         for this entry.  Values are '512' or '520'."
        ::= { raidVEntry 25 } 

	raidVDiskSerialNumber 	  OBJECT-TYPE
	SYNTAX			  DisplayString
	ACCESS          	  read-only
	STATUS          	  mandatory
	DESCRIPTION 
		"Serial number of the referenced disk drive." 
	::= { raidVEntry 26 } 

	raidVDiskVendor 	  OBJECT-TYPE 
	SYNTAX			  DisplayString 
	ACCESS          	  read-only 
	STATUS          	  mandatory 
	DESCRIPTION 
		"The vendor of the referenced disk drive." 
	::= { raidVEntry 27 } 

	raidVDiskModel 		  OBJECT-TYPE 
	SYNTAX			  DisplayString 
	ACCESS          	  read-only 
	STATUS          	  mandatory 
	DESCRIPTION 
		"Model string of the referenced disk drive." 
	::= { raidVEntry 28 } 

	raidVDiskFirmwareRevision OBJECT-TYPE 
	SYNTAX			  DisplayString 
	ACCESS          	  read-only 
	STATUS          	  mandatory 
	DESCRIPTION 
		"Firmware revision number of the referenced disk drive." 
	::= { raidVEntry 29 } 

	raidVDiskRPM 		  OBJECT-TYPE 
	SYNTAX			  DisplayString 
	ACCESS          	  read-only 
	STATUS          	  mandatory 
	DESCRIPTION 
		"RPM of the referenced disk drive." 
	::= { raidVEntry 30 } 

	raidVDiskType 	  	  OBJECT-TYPE 
	SYNTAX			  DisplayString 
	ACCESS          	  read-only 
	STATUS          	  mandatory 
	DESCRIPTION 
		"Interface type of the referenced disk drive. e.g SCSI, 
		 or ATA." 
	::= { raidVEntry 31 } 

	raidVDiskPool 	  	  OBJECT-TYPE 
	SYNTAX			  DisplayString 
	ACCESS          	  read-only 
	STATUS          	  mandatory 
	DESCRIPTION 
		"A name that identifies the disk pool that this entry 
		 belongs to."
	::= { raidVEntry 32 } 

	raidVDiskCopyDestDiskName OBJECT-TYPE 
	SYNTAX			  DisplayString 
	ACCESS          	  read-only 
	STATUS          	  mandatory 
	DESCRIPTION 
		"When raidVStatus value is prefailed, this string identifies 
		 the name of the disk which is the copy target of the 
		 referenced prefailed disk."
	::= { raidVEntry 33 } 

	-- Spare disk table.

	spareTable	OBJECT-TYPE
	SYNTAX		SEQUENCE OF SpareEntry
	ACCESS		not-accessible
	STATUS		mandatory
	DESCRIPTION
			"Display spare disk configuration information."
	::= { raid 3 }

	spareEntry	OBJECT-TYPE
	SYNTAX		SpareEntry
	ACCESS		not-accessible
	STATUS		mandatory
	DESCRIPTION
			"Display configuration information for
			 the referenced spare disk drive."
	INDEX	{ spareIndex }
	::= { spareTable 1 }

	SpareEntry ::=
	    SEQUENCE {
		spareIndex
		    INTEGER,
		spareDiskName
		    DisplayString,
		spareStatus
		    INTEGER,
		spareDiskId
		    INTEGER,
		spareScsiAdapter
		    DisplayString,
		spareScsiId
		    INTEGER (0..100),
		spareTotalMb
		    INTEGER,
		spareTotalBlocks
		    INTEGER,
		spareDiskPort
		    INTEGER,
		spareSecondaryDiskName
		    DisplayString,
		spareSecondaryDiskPort
		    INTEGER,
		spareShelf
		    INTEGER,
		spareBay
		    INTEGER,
		sparePool
		    DisplayString,
		spareSectorSize
		    INTEGER,
		spareDiskSerialNumber
		    DisplayString,
		spareDiskVendor
		    DisplayString,
		spareDiskModel
		    DisplayString,
		spareDiskFirmwareRevision
		    DisplayString,
		spareDiskRPM
		    DisplayString,
		spareDiskType
		    DisplayString
	    }

	spareIndex	OBJECT-TYPE
	SYNTAX		INTEGER (1..2147483647)
	ACCESS		read-only
	STATUS		mandatory
	DESCRIPTION
			"A number that identifies this entry for the
			 referenced disk drive in the list of spare disk
			 drives."
	::= { spareEntry 1 }

	spareDiskName	OBJECT-TYPE
	SYNTAX		DisplayString
	ACCESS		read-only
	STATUS		mandatory
	DESCRIPTION
			"The name identifying the referenced spare disk 
			 drive."
	::= { spareEntry 2 }

	spareStatus	OBJECT-TYPE
	SYNTAX		INTEGER {
                            spare(1),
                            addingspare(2),
                            bypassed(3),
                            unknown(4),
			    offline(10)
	}
	ACCESS		read-only
	STATUS		mandatory
	DESCRIPTION
			"The status of the referenced spare disk drive."
	::= { spareEntry 3 }

	spareDiskId	OBJECT-TYPE
	SYNTAX		INTEGER
	ACCESS		read-only
	STATUS		mandatory
	DESCRIPTION
			"The disk identifier for the referenced spare disk
			 drive."
	::= { spareEntry 4 }

	spareScsiAdapter	OBJECT-TYPE
	SYNTAX		DisplayString
	ACCESS		read-only
	STATUS		mandatory
	DESCRIPTION
			"The identifier of the SCSI adapter for the
			 referenced spare disk drive."
	::= { spareEntry 5 }

	spareScsiId	OBJECT-TYPE
	SYNTAX		INTEGER (0..100)
	ACCESS		read-only
	STATUS		mandatory
	DESCRIPTION
			"The identifier for the referenced spare disk drive
			 on the referenced SCSI adapter."
	::= { spareEntry 6 }

	spareTotalMb	OBJECT-TYPE
	SYNTAX		INTEGER
	ACCESS		read-only
	STATUS		mandatory
	DESCRIPTION
			"The number of MBytes physically available
			 on the referenced spare disk drive."
	::= { spareEntry 7 }

	spareTotalBlocks	OBJECT-TYPE
	SYNTAX		INTEGER
	ACCESS		read-only
	STATUS		mandatory
	DESCRIPTION
			"The number of Blocks physically available
			 on the referenced spare disk drive."
	::= { spareEntry 8 }

	spareDiskPort	OBJECT-TYPE
	SYNTAX		INTEGER {
					portA(1),
					portB(2),
					portSingle(3),
					portNone(4)
				}
	ACCESS		read-only
	STATUS		mandatory
	DESCRIPTION
			"A number that indicates which port of the
			disk is being used by the primary path to the disk.
			For a dual-ported disk, values of portA and portB
			indicate which port is being used.
			If the disk only has a single port, the value
			is portSingle, and if the port is not active, 
			the value is portNone."
	::= { spareEntry 9 }

	spareSecondaryDiskName	OBJECT-TYPE
	SYNTAX		DisplayString
	ACCESS		read-only
	STATUS		mandatory
	DESCRIPTION
			"The name identifying the secondary path to
			the referenced disk drive."
	::= { spareEntry 10 }

	spareSecondaryDiskPort	OBJECT-TYPE
	SYNTAX		INTEGER {
					portA(1),
					portB(2),
					portSingle(3),
					portNone(4)
				}
	ACCESS		read-only
	STATUS		mandatory
	DESCRIPTION
			"A number that indicates which port of the
			disk is being used by the secondary path to the disk.
			For a dual-ported disk, values of portA and portB
			indicate which port is being used.
			If the disk only has a single port, the value
			is portSingle, and if the port is not active, 
			the value is portNone."
	::= { spareEntry 11 }

	spareShelf	OBJECT-TYPE
	SYNTAX		INTEGER
	ACCESS		read-only
	STATUS		mandatory
	DESCRIPTION
			"Number identifying the shelf where the disk
			is located."
	::= { spareEntry 12 }

	spareBay	OBJECT-TYPE
	SYNTAX		INTEGER
	ACCESS		read-only
	STATUS		mandatory
	DESCRIPTION
			"Number identifying the disk bay within
			the shelf where the disk is located."
	::= { spareEntry 13 }

        sparePool       OBJECT-TYPE
        SYNTAX          DisplayString
        ACCESS          read-only
        STATUS          mandatory
        DESCRIPTION
                        "A name that identifies the disk pool that this
                         entry belongs to."
        ::= { spareEntry 14 } 

        spareSectorSize OBJECT-TYPE
        SYNTAX          INTEGER
        ACCESS          read-only
        STATUS          mandatory
        DESCRIPTION
                        "A number that specifies bytes per sector
                         for this entry.  Values are '512' or '520'."
        ::= { spareEntry 15 } 

	spareDiskSerialNumber 	  OBJECT-TYPE 
	SYNTAX			  DisplayString 
	ACCESS          	  read-only 
	STATUS          	  mandatory 
	DESCRIPTION 
		"Serial number of the referenced disk drive." 
	::= { spareEntry 16 } 

	spareDiskVendor 	  OBJECT-TYPE 
	SYNTAX			  DisplayString 
	ACCESS          	  read-only 
	STATUS          	  mandatory 
	DESCRIPTION 
		"The vendor of the referenced disk drive." 
	::= { spareEntry 17 } 

	spareDiskModel 		  OBJECT-TYPE 
	SYNTAX			  DisplayString 
	ACCESS          	  read-only 
	STATUS          	  mandatory 
	DESCRIPTION 
		"Model string of the referenced disk drive." 
	::= { spareEntry 18 } 

	spareDiskFirmwareRevision OBJECT-TYPE 
	SYNTAX			  DisplayString 
	ACCESS          	  read-only 
	STATUS          	  mandatory 
	DESCRIPTION 
		"Firmware revision number of the referenced disk drive." 
	::= { spareEntry 19 } 

	spareDiskRPM 		  OBJECT-TYPE 
	SYNTAX			  DisplayString 
	ACCESS          	  read-only 
	STATUS          	  mandatory 
	DESCRIPTION 
		"RPM of the referenced disk drive." 
	::= { spareEntry 20 } 

	spareDiskType 	  	  OBJECT-TYPE 
	SYNTAX			  DisplayString 
	ACCESS          	  read-only 
	STATUS          	  mandatory 
	DESCRIPTION 
		"Interface type of the referenced disk drive. e.g SCSI, 
		 or ATA." 
	::= { spareEntry 21 } 

	-- Disk summaries

	diskSummary	OBJECT IDENTIFIER ::= { raid 4 }

	diskTotalCount	OBJECT-TYPE
	SYNTAX		INTEGER
	ACCESS		read-only
	STATUS		mandatory
	DESCRIPTION
			"The total number of disks on the system."

	::= { diskSummary 1 }

	diskActiveCount	OBJECT-TYPE
	SYNTAX		INTEGER
	ACCESS		read-only
	STATUS		mandatory
	DESCRIPTION
			"The number of disks which are currently active,
			including parity disks."

	::= { diskSummary 2 }

	diskReconstructingCount	OBJECT-TYPE
	SYNTAX		INTEGER
	ACCESS		read-only
	STATUS		mandatory
	DESCRIPTION
			"The number of disks which are
			currently being reconstructed."

	::= { diskSummary 3 }

	diskReconstructingParityCount	OBJECT-TYPE
	SYNTAX		INTEGER
	ACCESS		read-only
	STATUS		mandatory
	DESCRIPTION
			"The number of parity disks which are
			currently being reconstructed."

	::= { diskSummary 4 }

	diskVerifyingParityCount	OBJECT-TYPE
	SYNTAX		INTEGER
	ACCESS		read-only
	STATUS		mandatory
	DESCRIPTION
			"The number of parity disks which are
			currently being verified."

	::= { diskSummary 5 }

	diskScrubbingCount	OBJECT-TYPE
	SYNTAX		INTEGER
	ACCESS		read-only
	STATUS		mandatory
	DESCRIPTION
			"The number of disks which are
			currently being scrubbed."

	::= { diskSummary 6 }

	diskFailedCount	OBJECT-TYPE
	SYNTAX		INTEGER
	ACCESS		read-only
	STATUS		mandatory
	DESCRIPTION
			"The number of disks which are
			currently broken."

	::= { diskSummary 7 }

	diskSpareCount	OBJECT-TYPE
	SYNTAX		INTEGER
	ACCESS		read-only
	STATUS		mandatory
	DESCRIPTION
			"The number of available spare disks."

	::= { diskSummary 8 }

	diskAddingSpareCount	OBJECT-TYPE
	SYNTAX		INTEGER
	ACCESS		read-only
	STATUS		mandatory
	DESCRIPTION
			"The number of spare disks which are
			currently being added into a RAID group."

	::= { diskSummary 9 }

	diskFailedMessage	OBJECT-TYPE
	SYNTAX		DisplayString
	ACCESS		read-only
	STATUS		mandatory
	DESCRIPTION
			"If diskFailedCount is non-zero, this is
			a string describing the failed disk or 
			disks.  Each failed disk is described with
			a sentence like

			Parity disk in volume vol0, RAID group 1, failed.

			or

			Disk on adapter 8a, shelf 1, bay 0, failed."

	::= { diskSummary 10 }

        diskPrefailedCount	OBJECT-TYPE
        SYNTAX		INTEGER
        ACCESS		read-only
	STATUS		mandatory
        DESCRIPTION
			"The number of disks which are prefailed and marked
			  for rapid raid recovery."
        
        ::= { diskSummary 11 }

	raidVNumber		OBJECT-TYPE
	SYNTAX			INTEGER
	ACCESS			read-only
	STATUS			mandatory
	DESCRIPTION
			"Number of entries in the raidVTable table.
			This is the number of volumes in the system."

	::= { raid 5 }

	spareNumber		OBJECT-TYPE
	SYNTAX			INTEGER
	ACCESS			read-only
	STATUS			mandatory
	DESCRIPTION
			"Number of entries in the spareTable table."

	::= { raid 6 }

	otherDiskNumber		OBJECT-TYPE
	SYNTAX			INTEGER
	ACCESS			read-only
	STATUS			mandatory
	DESCRIPTION
			"Number of entries in the otherDiskTable table."

	::= { raid 7 }

	raidPNumber		OBJECT-TYPE
	SYNTAX			INTEGER
	ACCESS			read-only
	STATUS			mandatory
	DESCRIPTION
			"Number of entries in the raidPTable table.
			This is the number of volumes in the system."

	::= { raid 8 }

	-- Other (out-of-service) disk table.

	otherDiskTable	OBJECT-TYPE
	SYNTAX		SEQUENCE OF OtherDiskEntry
	ACCESS		not-accessible
	STATUS		mandatory
	DESCRIPTION
			"Display out-of-service disk configuration information."
	::= { raid 9 }

	otherDiskEntry	OBJECT-TYPE
	SYNTAX		OtherDiskEntry
	ACCESS		not-accessible
	STATUS		mandatory
	DESCRIPTION
			"Display configuration information for
			 the referenced disk drive."
	INDEX	{ otherDiskIndex }
	::= { otherDiskTable 1 }

	OtherDiskEntry ::=
	    SEQUENCE {
		otherDiskIndex
		    INTEGER,
		otherDiskDiskName
		    DisplayString,
		otherDiskStatus
		    INTEGER,
		otherDiskDiskId
		    INTEGER,
		otherDiskScsiAdapter
		    DisplayString,
		otherDiskScsiId
		    INTEGER (0..100),
		otherDiskTotalMb
		    INTEGER,
		otherDiskTotalBlocks
		    INTEGER,
		otherDiskDiskPort
		    INTEGER,
		otherDiskSecondaryDiskName
		    DisplayString,
		otherDiskSecondaryDiskPort
		    INTEGER,
		otherDiskShelf
		    INTEGER,
		otherDiskBay
		    INTEGER,
		otherDiskPool
		    DisplayString,
		otherDiskSectorSize
		    INTEGER,
		otherDiskSerialNumber
		    DisplayString,
		otherDiskVendor
		    DisplayString,
		otherDiskModel
		    DisplayString,
		otherDiskFirmwareRevision
		    DisplayString,
		otherDiskRPM
		    DisplayString,
		otherDiskType
		    DisplayString
	    }

	otherDiskIndex	OBJECT-TYPE
	SYNTAX		INTEGER (1..2147483647)
	ACCESS		read-only
	STATUS		mandatory
	DESCRIPTION
			"A number that identifies this entry for the
			 referenced disk drive in the list of out-of-service
			 diskdrives. Out-of-service disks include all disks
                         that are not in service in a raid group or available
                         as a spare disk."
	::= { otherDiskEntry 1 }

	otherDiskDiskName	OBJECT-TYPE
	SYNTAX		DisplayString
	ACCESS		read-only
	STATUS		mandatory
	DESCRIPTION
			"The name identifying the referenced disk 
			 drive."
	::= { otherDiskEntry 2 }

	otherDiskStatus	OBJECT-TYPE
	SYNTAX		INTEGER {
		broken(1),
		bypassed(2),
                unknown(3)
	}
	ACCESS		read-only
	STATUS		mandatory
	DESCRIPTION
			"The status of the referenced disk drive."
	::= { otherDiskEntry 3 }

	otherDiskDiskId	OBJECT-TYPE
	SYNTAX		INTEGER
	ACCESS		read-only
	STATUS		mandatory
	DESCRIPTION
			"The disk identifier for the referenced disk
			 drive."
	::= { otherDiskEntry 4 }

	otherDiskScsiAdapter	OBJECT-TYPE
	SYNTAX		DisplayString
	ACCESS		read-only
	STATUS		mandatory
	DESCRIPTION
			"The identifier of the SCSI adapter for the
			 referenced disk drive."
	::= { otherDiskEntry 5 }

	otherDiskScsiId	OBJECT-TYPE
	SYNTAX		INTEGER (0..100)
	ACCESS		read-only
	STATUS		mandatory
	DESCRIPTION
			"The identifier for the referenced disk drive
			 on the referenced SCSI adapter."
	::= { otherDiskEntry 6 }

	otherDiskTotalMb	OBJECT-TYPE
	SYNTAX		INTEGER
	ACCESS		read-only
	STATUS		mandatory
	DESCRIPTION
			"The number of MBytes physically available
			 on the referenced disk drive."
	::= { otherDiskEntry 7 }

	otherDiskTotalBlocks	OBJECT-TYPE
	SYNTAX		INTEGER
	ACCESS		read-only
	STATUS		mandatory
	DESCRIPTION
			"The number of Blocks physically available
			 on the referenced disk drive."
	::= { otherDiskEntry 8 }

	otherDiskDiskPort	OBJECT-TYPE
	SYNTAX		INTEGER {
					portA(1),
					portB(2),
					portSingle(3),
					portNone(4)
				}
	ACCESS		read-only
	STATUS		mandatory
	DESCRIPTION
			"A number that indicates which port of the
			disk is being used by the primary path to the disk.
			For a dual-ported disk, values of portA and portB
			indicate which port is being used.
			If the disk only has a single port, the value
			is portSingle, and if the port is not active, 
			the value is portNone."
	::= { otherDiskEntry 9 }

	otherDiskSecondaryDiskName	OBJECT-TYPE
	SYNTAX		DisplayString
	ACCESS		read-only
	STATUS		mandatory
	DESCRIPTION
			"The name identifying the secondary path to
			the referenced disk drive."
	::= { otherDiskEntry 10 }

	otherDiskSecondaryDiskPort	OBJECT-TYPE
	SYNTAX		INTEGER {
					portA(1),
					portB(2),
					portSingle(3),
					portNone(4)
				}
	ACCESS		read-only
	STATUS		mandatory
	DESCRIPTION
			"A number that indicates which port of the
			disk is being used by the secondary path to the disk.
			For a dual-ported disk, values of portA and portB
			indicate which port is being used.
			If the disk only has a single port, the value
			is portSingle, and if the port is not active, 
			the value is portNone."
	::= { otherDiskEntry 11 }

	otherDiskShelf	OBJECT-TYPE
	SYNTAX		INTEGER
	ACCESS		read-only
	STATUS		mandatory
	DESCRIPTION
			"Number identifying the shelf where the disk
			is located."
	::= { otherDiskEntry 12 }

	otherDiskBay	OBJECT-TYPE
	SYNTAX		INTEGER
	ACCESS		read-only
	STATUS		mandatory
	DESCRIPTION
			"Number identifying the disk bay within
			the shelf where the disk is located."
	::= { otherDiskEntry 13 }

        otherDiskPool     OBJECT-TYPE
        SYNTAX          DisplayString
        ACCESS          read-only
        STATUS          mandatory
        DESCRIPTION
                        "A name that identifies the disk pool that this
                         entry belongs to."
        ::= { otherDiskEntry 14 } 

        otherDiskSectorSize OBJECT-TYPE
        SYNTAX          INTEGER
        ACCESS          read-only
        STATUS          mandatory
        DESCRIPTION
                        "A number that specifies bytes per sector
                         for this entry.  Values are '512' or '520'."
        ::= { otherDiskEntry 15 } 

	otherDiskSerialNumber 	  OBJECT-TYPE 
	SYNTAX			  DisplayString 
	ACCESS          	  read-only 
	STATUS          	  mandatory 
	DESCRIPTION 
		"Serial number of the referenced disk drive." 
	::= { otherDiskEntry 16 } 

	otherDiskVendor 	  OBJECT-TYPE 
	SYNTAX			  DisplayString 
	ACCESS          	  read-only 
	STATUS          	  mandatory 
	DESCRIPTION 
		"The vendor of the referenced disk drive." 
	::= { otherDiskEntry 17 } 

	otherDiskModel 		  OBJECT-TYPE 
	SYNTAX			  DisplayString 
	ACCESS          	  read-only 
	STATUS          	  mandatory 
	DESCRIPTION 
		"Model string of the referenced disk drive." 
	::= { otherDiskEntry 18 } 

	otherDiskFirmwareRevision OBJECT-TYPE 
	SYNTAX			  DisplayString 
	ACCESS          	  read-only 
	STATUS          	  mandatory 
	DESCRIPTION 
		"Firmware revision number of the referenced disk drive." 
	::= { otherDiskEntry 19 } 

	otherDiskRPM 		  OBJECT-TYPE 
	SYNTAX			  DisplayString 
	ACCESS          	  read-only 
	STATUS          	  mandatory 
	DESCRIPTION 
		"RPM of the referenced disk drive." 
	::= { otherDiskEntry 20 } 

	otherDiskType 	  	  OBJECT-TYPE 
	SYNTAX			  DisplayString 
	ACCESS          	  read-only 
	STATUS          	  mandatory 
	DESCRIPTION 
		"Interface type of the referenced disk drive. e.g SCSI, 
		 or ATA." 
	::= { otherDiskEntry 21 } 

	-- Multivolume and multiplex raidTable.

	raidPTable	OBJECT-TYPE
	SYNTAX		SEQUENCE OF RaidPEntry
	ACCESS		not-accessible
	STATUS		mandatory
	DESCRIPTION
			"Display RAID configuration information."
	::= { raid 10 }

	raidPEntry	OBJECT-TYPE
	SYNTAX		RaidPEntry
	ACCESS		not-accessible
	STATUS		mandatory
	DESCRIPTION
			"Display RAID configuration information for
			 the referenced volume, plex, raid group, and disk drive."
	INDEX	{ raidPVol, raidPPlex, raidPGroup, raidPIndex }
	::= { raidPTable 1 }

	RaidPEntry ::=
	    SEQUENCE {
		raidPIndex
		    INTEGER,
		raidPStatus
		    INTEGER,
		raidPVol
		    INTEGER,
                raidPPlex
                    INTEGER, 
		raidPGroup
		    INTEGER,
		raidPPlexNumber
		    INTEGER (1..2),
		raidPGroupNumber
		    INTEGER,
		raidPDiskNumber
		    INTEGER (1..100),
                raidPPlexName
                    DisplayString, 
		raidPDiskName
		    DisplayString,
		raidPDiskPort
		    INTEGER,
		raidPSecondaryDiskName
		    DisplayString,
		raidPSecondaryDiskPort
		    INTEGER,
		raidPScsiAdapter
		    DisplayString,
		raidPScsiId
		    INTEGER (0..100),
		raidPDiskId
		    INTEGER,
		raidPShelf
		    INTEGER,
		raidPBay
		    INTEGER,
                raidPSectorSize
                    INTEGER, 
		raidPUsedMb
		    INTEGER,
		raidPUsedBlocks
		    INTEGER,
		raidPTotalMb
		    INTEGER,
		raidPTotalBlocks
		    INTEGER,
		raidPCompletionPerCent
		    INTEGER (0..100),
		raidPDiskSerialNumber
		    DisplayString,
		raidPDiskVendor
		    DisplayString,
		raidPDiskModel
		    DisplayString,
		raidPDiskFirmwareRevision
		    DisplayString,
		raidPDiskRPM
		    DisplayString,
		raidPDiskType
		    DisplayString,
		raidPDiskPool
		    DisplayString,
		raidPDiskCopyDestDiskName
		    DisplayString
	    }

	raidPIndex	OBJECT-TYPE
	SYNTAX		INTEGER (1..2147483647)
	ACCESS		read-only
	STATUS		mandatory
	DESCRIPTION
			"A number that identifies this disk drive within 
			 the given volume and RAID group."
	::= { raidPEntry 1 }

	raidPStatus	OBJECT-TYPE
	SYNTAX		INTEGER {
				active(1),
				reconstructionInProgress(2),
				parityReconstructionInProgress(3),
				parityVerificationInProgress(4),
				scrubbingInProgress(5),
				failed(6),
				prefailed(9),
				offline(10)
				}
	ACCESS		read-only
	STATUS		mandatory
	DESCRIPTION
			"The status of the referenced disk drive."
	::= { raidPEntry 2 }

	raidPVol	OBJECT-TYPE
	SYNTAX		INTEGER (1..2147483647)
	ACCESS		read-only
	STATUS		mandatory
	DESCRIPTION
			"A number that identifies the volume that this entry
			 belongs to. The first volume is '1'."
	::= { raidPEntry 3 }

	raidPPlex	OBJECT-TYPE
	SYNTAX		INTEGER (1..2147483647)
	ACCESS		read-only
	STATUS		mandatory
	DESCRIPTION
			"A number that identifies the plex that this entry
			 belongs to. The first plex is '1'."
	::= { raidPEntry 4 }

	raidPGroup	OBJECT-TYPE
	SYNTAX		INTEGER (1..2147483647)
	ACCESS		read-only
	STATUS		mandatory
	DESCRIPTION
			"A number that identifies the RAID group within the
			 given plex that this entry belongs to. The
			 first RAID group is '1'."
	::= { raidPEntry 5 }

	raidPPlexNumber	OBJECT-TYPE
	SYNTAX		INTEGER (1..2)
	ACCESS		read-only
	STATUS		mandatory
	DESCRIPTION
			"The number of plexes within this volume.
                        This number is always 1 or 2."
	::= { raidPEntry 6 }

	raidPGroupNumber OBJECT-TYPE
	SYNTAX		INTEGER
	ACCESS		read-only
	STATUS		mandatory
	DESCRIPTION
			"The number of RAID groups within this plex."
	::= { raidPEntry 7 }

	raidPDiskNumber	OBJECT-TYPE
	SYNTAX		INTEGER (1..100)
	ACCESS		read-only
	STATUS		mandatory
	DESCRIPTION
			"The number of disks within this RAID group."
	::= { raidPEntry 8 }

	raidPPlexName	OBJECT-TYPE
	SYNTAX		DisplayString
	ACCESS		read-only
	STATUS		mandatory
	DESCRIPTION
			"A name that identifies the plex that this entry
			 belongs to.  A plex name can be anything, but
                         is usually a string like 'plex0' or 'plex1'."
	::= { raidPEntry 9 }

	raidPDiskName	OBJECT-TYPE
	SYNTAX		DisplayString
	ACCESS		read-only
	STATUS		mandatory
	DESCRIPTION
			"The name identifying the referenced disk drive."
	::= { raidPEntry 10 }

	raidPDiskPort	OBJECT-TYPE
	SYNTAX		INTEGER {
                                portA(1),
                                portB(2),
                                portSingle(3),
                                portNone(4)
				}
	ACCESS		read-only
	STATUS		mandatory
	DESCRIPTION
			"A number that indicates which port of the
			disk is being used by the primary path to the disk.
			For a dual-ported disk, values of portA and portB
			indicate which port is being used.
			If the disk only has a single port, the value
			is portSingle, and if the port is not active, 
			the value is portNone."
	::= { raidPEntry 11 }

	raidPSecondaryDiskName	OBJECT-TYPE
	SYNTAX		DisplayString
	ACCESS		read-only
	STATUS		mandatory
	DESCRIPTION
			"The name identifying the secondary path to
			the referenced disk drive."
	::= { raidPEntry 12 }

	raidPSecondaryDiskPort	OBJECT-TYPE
	SYNTAX		INTEGER {
                                portA(1),
                                portB(2),
                                portSingle(3),
                                portNone(4)
				}
	ACCESS		read-only
	STATUS		mandatory
	DESCRIPTION
			"A number that indicates which port of the
			disk is being used by the secondary path to the disk.
			For a dual-ported disk, values of portA and portB
			indicate which port is being used.
			If the disk only has a single port, the value
			is portSingle, and if the port is not active, 
			the value is portNone."
	::= { raidPEntry 13 }

	raidPScsiAdapter	OBJECT-TYPE
	SYNTAX		DisplayString
	ACCESS		read-only
	STATUS		mandatory
	DESCRIPTION
			"The identifier of the SCSI adapter for the
			 referenced disk drive."
	::= { raidPEntry 14 }

	raidPScsiId	OBJECT-TYPE
	SYNTAX		INTEGER (0..100)
	ACCESS		read-only
	STATUS		mandatory
	DESCRIPTION
			"The identifier for the referenced disk drive
			 on the referenced SCSI adapter."
	::= { raidPEntry 15 }

	raidPDiskId	OBJECT-TYPE
	SYNTAX		INTEGER
	ACCESS		read-only
	STATUS		mandatory
	DESCRIPTION
			"The disk identifier for the referenced disk
			 drive."
	::= { raidPEntry 16 }

	raidPShelf	OBJECT-TYPE
	SYNTAX		INTEGER
	ACCESS		read-only
	STATUS		mandatory
	DESCRIPTION
			"Number identifying the shelf where the disk
			is located."
	::= { raidPEntry 17 }

	raidPBay	OBJECT-TYPE
	SYNTAX		INTEGER
	ACCESS		read-only
	STATUS		mandatory
	DESCRIPTION
			"Number identifying the disk bay within
			the shelf where the disk is located."
	::= { raidPEntry 18 }


        raidPSectorSize OBJECT-TYPE
        SYNTAX          INTEGER
        ACCESS          read-only
        STATUS          mandatory
        DESCRIPTION
                        "A number that specifies bytes per sector
                         for this entry.  Values are '512' or '520'."
        ::= { raidPEntry 19 } 

	raidPUsedMb	OBJECT-TYPE
	SYNTAX		INTEGER
	ACCESS		read-only
	STATUS		mandatory
	DESCRIPTION
			"The number of MBytes currently in use on
			 the referenced disk drive."
	::= { raidPEntry 20 }

	raidPUsedBlocks	OBJECT-TYPE
	SYNTAX		INTEGER
	ACCESS		read-only
	STATUS		mandatory
	DESCRIPTION
			"The number of Blocks currently in use on
			 the referenced disk drive."
	::= { raidPEntry 21 }

	raidPTotalMb	OBJECT-TYPE
	SYNTAX		INTEGER
	ACCESS		read-only
	STATUS		mandatory
	DESCRIPTION
			"The number of MBytes physically available
			 on the referenced disk drive."
	::= { raidPEntry 22 }

	raidPTotalBlocks	OBJECT-TYPE
	SYNTAX		INTEGER
	ACCESS		read-only
	STATUS		mandatory
	DESCRIPTION
			"The number of Blocks physically available
			 on the referenced disk drive."
	::= { raidPEntry 23 }

	raidPCompletionPerCent OBJECT-TYPE
	SYNTAX		      INTEGER (0..100)
	ACCESS		      read-only
	STATUS		      mandatory
	DESCRIPTION
			 "In the case when rapid raid recovery, disk copy,
			  reconstruction or adding a spare, verification or 
			  scrubbing is in progress, the percent of such copy, 
			  reconstruction, verification or scrubbing that has 
			  been completed on the referenced disk drive."
	::= { raidPEntry 24 }

	raidPDiskSerialNumber 	  OBJECT-TYPE
	SYNTAX			  DisplayString
	ACCESS          	  read-only
	STATUS          	  mandatory
	DESCRIPTION 
		"Serial number of the referenced disk drive." 
	::= { raidPEntry 25 } 

	raidPDiskVendor 	  OBJECT-TYPE 
	SYNTAX			  DisplayString 
	ACCESS          	  read-only 
	STATUS          	  mandatory 
	DESCRIPTION 
		"The vendor of the referenced disk drive." 
	::= { raidPEntry 26 } 

	raidPDiskModel 		  OBJECT-TYPE 
	SYNTAX			  DisplayString 
	ACCESS          	  read-only 
	STATUS          	  mandatory 
	DESCRIPTION 
		"Model string of the referenced disk drive." 
	::= { raidPEntry 27 } 

	raidPDiskFirmwareRevision OBJECT-TYPE 
	SYNTAX			  DisplayString 
	ACCESS          	  read-only 
	STATUS          	  mandatory 
	DESCRIPTION 
		"Firmware revision number of the referenced disk drive." 
	::= { raidPEntry 28 } 

	raidPDiskRPM 		  OBJECT-TYPE 
	SYNTAX			  DisplayString 
	ACCESS          	  read-only 
	STATUS          	  mandatory 
	DESCRIPTION 
		"RPM of the referenced disk drive." 
	::= { raidPEntry 29 } 

	raidPDiskType 	  	  OBJECT-TYPE 
	SYNTAX			  DisplayString 
	ACCESS          	  read-only 
	STATUS          	  mandatory 
	DESCRIPTION 
		"Interface type of the referenced disk drive. e.g SCSI, 
		 or ATA." 
	::= { raidPEntry 30 } 

	raidPDiskPool 	  	  OBJECT-TYPE 
	SYNTAX			  DisplayString 
	ACCESS          	  read-only 
	STATUS          	  mandatory 
	DESCRIPTION 
		"A name that identifies the disk pool that this entry 
		 belongs to."
	::= { raidPEntry 31 } 

	raidPDiskCopyDestDiskName OBJECT-TYPE 
	SYNTAX			  DisplayString 
	ACCESS          	  read-only 
	STATUS          	  mandatory 
	DESCRIPTION 
		"When raidPStatus value is prefailed, this string identifies 
		 the name of the disk which is the copy target of the 
		 referenced prefailed disk."
	::= { raidPEntry 32 } 

	-- RAID Plex table.

        plexTable   OBJECT-TYPE
        SYNTAX      SEQUENCE OF PlexEntry
        ACCESS      not-accessible
        STATUS      mandatory
        DESCRIPTION
                    "A table containing plex specific information."
        ::= {raid 11}

        -- display plexes 

        plexEntry       OBJECT-TYPE
        SYNTAX          PlexEntry 
        ACCESS          not-accessible
        STATUS          mandatory
        DESCRIPTION
                        "Provide a report on file system plexes."
        INDEX           { plexIndex } 
        ::= { plexTable 1 }

        PlexEntry ::=
            SEQUENCE {
                plexIndex
                    INTEGER,
                plexName
                    DisplayString,
                plexVolName
                    DisplayString,
                plexStatus
                    INTEGER,
                plexPercentResyncing
                    INTEGER
            } 

        plexIndex       OBJECT-TYPE
        SYNTAX          INTEGER (1..2147483647)
        ACCESS          read-only
        STATUS          mandatory
        DESCRIPTION
                        "A number that identifies this entry for the
                         referenced plex."
        ::= { plexEntry 1 }

        plexName        OBJECT-TYPE
        SYNTAX          DisplayString
        ACCESS          read-only
        STATUS          mandatory
        DESCRIPTION
                        "The identifier of the plex."
        ::= { plexEntry 2 }

        plexVolName     OBJECT-TYPE
        SYNTAX          DisplayString
        ACCESS          read-only
        STATUS          mandatory
        DESCRIPTION
                        "The volume to which this plex belongs."
        ::= { plexEntry 3 }

        plexStatus      OBJECT-TYPE
        SYNTAX          INTEGER { 
		offline(1),
		resyncing(2),
		online(3)
	} 
        ACCESS          read-only
        STATUS          mandatory
        DESCRIPTION
                        "The status of the plex."
        ::= { plexEntry 4 }

        plexPercentResyncing OBJECT-TYPE
        SYNTAX               INTEGER 
        ACCESS               read-only
        STATUS               mandatory
        DESCRIPTION
                             "If the plex is resyncing, the percent 
                              completion of the resync."
        ::= { plexEntry 5 }

	--out-of-dateDisks

	outOfDateDiskCount	OBJECT-TYPE
	SYNTAX			INTEGER
	ACCESS			read-only
	STATUS			mandatory
	DESCRIPTION
			"Number of entries in the outOfDateDiskTable table."

	::= { raid 12 }

	-- out-of-date disk table.

	outOfDateDiskTable	OBJECT-TYPE
	SYNTAX		SEQUENCE OF OutOfDateDiskEntry
	ACCESS		not-accessible
	STATUS		mandatory
	DESCRIPTION
			"Display out-of-date disk information."
	::= { raid 13 }

	outOfDateDiskEntry	OBJECT-TYPE
	SYNTAX		OutOfDateDiskEntry
	ACCESS		not-accessible
	STATUS		mandatory
	DESCRIPTION
			"Display information for the referenced
			 out-of-date disk."
	INDEX	{ outOfDateDiskIndex }
	::= { outOfDateDiskTable 1 }

	OutOfDateDiskEntry ::=
	    SEQUENCE {
		outOfDateDiskIndex
		    INTEGER,
		outOfDateDiskDiskName
		    DisplayString,
		outOfDateDiskDiskId
		    INTEGER,
		outOfDateDiskScsiAdapter
		    DisplayString,
		outOfDateDiskScsiId
		    INTEGER (0..100),
		outOfDateDiskTotalMb
		    INTEGER,
		outOfDateDiskTotalBlocks
		    INTEGER,
		outOfDateDiskDiskPort
		    INTEGER,
		outOfDateDiskSecondaryDiskName
		    DisplayString,
		outOfDateDiskSecondaryDiskPort
		    INTEGER,
		outOfDateDiskShelf
		    INTEGER,
		outOfDateDiskBay
		    INTEGER,
		outOfDateDiskPool
		    DisplayString,
		outOfDateDiskSectorSize
		    INTEGER,
		outOfDateDiskSerialNumber
		    DisplayString,
		outOfDateDiskVendor
		    DisplayString,
		outOfDateDiskModel
		    DisplayString,
		outOfDateDiskFirmwareRevision
		    DisplayString,
		outOfDateDiskRPM
		    DisplayString,
		outOfDateDiskType
		    DisplayString
	    }

	outOfDateDiskIndex	OBJECT-TYPE
	SYNTAX			INTEGER (1..2147483647)
	ACCESS			read-only
	STATUS			mandatory
	DESCRIPTION
			"A number that identifies this entry for the
			 referenced disk drive in the list of out-of-date
			 diskdrives."
	::= { outOfDateDiskEntry 1 }

	outOfDateDiskDiskName	OBJECT-TYPE
	SYNTAX			DisplayString
	ACCESS			read-only
	STATUS			mandatory
	DESCRIPTION
			"The name identifying the referenced disk 
			 drive."
	::= { outOfDateDiskEntry 2 }

	outOfDateDiskDiskId	OBJECT-TYPE
	SYNTAX			INTEGER
	ACCESS			read-only
	STATUS			mandatory
	DESCRIPTION
			"The disk identifier for the referenced disk
			 drive."
	::= { outOfDateDiskEntry 3 }

	outOfDateDiskScsiAdapter	OBJECT-TYPE
	SYNTAX				DisplayString
	ACCESS				read-only
	STATUS				mandatory
	DESCRIPTION
			"The identifier of the SCSI adapter for the
			 referenced disk drive."
	::= { outOfDateDiskEntry 4 }

	outOfDateDiskScsiId	OBJECT-TYPE
	SYNTAX			INTEGER (0..100)
	ACCESS			read-only
	STATUS			mandatory
	DESCRIPTION
			"The identifier for the referenced disk drive
			 on the referenced SCSI adapter."
	::= { outOfDateDiskEntry 5 }

	outOfDateDiskTotalMb	OBJECT-TYPE
	SYNTAX			INTEGER
	ACCESS			read-only
	STATUS			mandatory
	DESCRIPTION
			"The number of MBytes physically available
			 on the referenced disk drive."
	::= { outOfDateDiskEntry 6 }

	outOfDateDiskTotalBlocks	OBJECT-TYPE
	SYNTAX				INTEGER
	ACCESS				read-only
	STATUS				mandatory
	DESCRIPTION
			"The number of Blocks physically available
			 on the referenced disk drive."
	::= { outOfDateDiskEntry 7 }

	outOfDateDiskDiskPort		OBJECT-TYPE
	SYNTAX				INTEGER {
						portA(1),
						portB(2),
						portSingle(3),
						portNone(4)
					}
	ACCESS				read-only
	STATUS				mandatory
	DESCRIPTION
			"A number that indicates which port of the
			disk is being used by the primary path to the disk.
			For a dual-ported disk, values of portA and portB
			indicate which port is being used.
			If the disk only has a single port, the value
			is portSingle, and if the port is not active, 
			the value is portNone."
	::= { outOfDateDiskEntry 8 }

	outOfDateDiskSecondaryDiskName	OBJECT-TYPE
	SYNTAX				DisplayString
	ACCESS				read-only
	STATUS				mandatory
	DESCRIPTION
			"The name identifying the secondary path to
			the referenced disk drive."
	::= { outOfDateDiskEntry 9 }

	outOfDateDiskSecondaryDiskPort	OBJECT-TYPE
	SYNTAX				INTEGER {
						portA(1),
						portB(2),
						portSingle(3),
						portNone(4)
					}
	ACCESS				read-only
	STATUS				mandatory
	DESCRIPTION
			"A number that indicates which port of the
			disk is being used by the secondary path to the disk.
			For a dual-ported disk, values of portA and portB
			indicate which port is being used.
			If the disk only has a single port, the value
			is portSingle, and if the port is not active, 
			the value is portNone."
	::= { outOfDateDiskEntry 10 }

	outOfDateDiskShelf	OBJECT-TYPE
	SYNTAX			INTEGER
	ACCESS			read-only
	STATUS			mandatory
	DESCRIPTION
			"Number identifying the shelf where the disk
			is located."
	::= { outOfDateDiskEntry 11 }

	outOfDateDiskBay	OBJECT-TYPE
	SYNTAX			INTEGER
	ACCESS			read-only
	STATUS			mandatory
	DESCRIPTION
			"Number identifying the disk bay within
			the shelf where the disk is located."
	::= { outOfDateDiskEntry 12 }

        outOfDateDiskPool	OBJECT-TYPE
        SYNTAX          	DisplayString
        ACCESS          	read-only
        STATUS          	mandatory
        DESCRIPTION
                        "A name that identifies the disk pool that this
                         entry belongs to."
        ::= { outOfDateDiskEntry 13 } 

        outOfDateDiskSectorSize OBJECT-TYPE
        SYNTAX         		INTEGER
        ACCESS         		read-only
        STATUS         		mandatory
        DESCRIPTION
                        "A number that specifies bytes per sector
                         for this entry.  Values are '512' or '520'."
        ::= { outOfDateDiskEntry 14 } 

	outOfDateDiskSerialNumber 	OBJECT-TYPE 
	SYNTAX				DisplayString 
	ACCESS          		read-only 
	STATUS          		mandatory 
	DESCRIPTION 
		"Serial number of the referenced disk drive." 
	::= { outOfDateDiskEntry 15 } 

	outOfDateDiskVendor 		OBJECT-TYPE 
	SYNTAX				DisplayString 
	ACCESS          		read-only 
	STATUS          		mandatory 
	DESCRIPTION 
		"The vendor of the referenced disk drive." 
	::= { outOfDateDiskEntry 16 } 

	outOfDateDiskModel 		OBJECT-TYPE 
	SYNTAX				DisplayString 
	ACCESS          		read-only 
	STATUS          		mandatory 
	DESCRIPTION 
		"Model string of the referenced disk drive." 
	::= { outOfDateDiskEntry 17 } 

	outOfDateDiskFirmwareRevision 	OBJECT-TYPE 
	SYNTAX				DisplayString 
	ACCESS          		read-only 
	STATUS          		mandatory 
	DESCRIPTION 
		"Firmware revision number of the referenced disk drive." 
	::= { outOfDateDiskEntry 18 } 

	outOfDateDiskRPM 	  OBJECT-TYPE 
	SYNTAX			  DisplayString 
	ACCESS          	  read-only 
	STATUS          	  mandatory 
	DESCRIPTION 
		"RPM of the referenced disk drive." 
	::= { outOfDateDiskEntry 19 } 

	outOfDateDiskType   	  OBJECT-TYPE 
	SYNTAX			  DisplayString 
	ACCESS          	  read-only 
	STATUS          	  mandatory 
	DESCRIPTION 
		"Interface type of the referenced disk drive. e.g SCSI, 
		 or ATA." 
	::= { outOfDateDiskEntry 20 } 

	-- -- -- -- -- -- -- -- -- -- -- -- -- -- -- -- -- --
	-- -- -- -- -- -- -- -- -- -- -- -- -- -- -- -- -- --
	-- the CIFS group    --
	-- -- -- -- -- -- -- -- -- -- -- -- -- -- -- -- -- --
	-- -- -- -- -- -- -- -- -- -- -- -- -- -- -- -- -- --


	cifsOptions	OBJECT IDENTIFIER ::= { cifs 1 }

	cifsInfo	OBJECT IDENTIFIER ::= { cifs 2 }

	cifsStats	OBJECT IDENTIFIER ::= { cifs 3 }

	cifsMisc	OBJECT IDENTIFIER ::= { cifs 4 }

	-- -- -- -- -- -- -- -- -- -- -- -- -- -- -- -- -- --
	-- the cifsOptions group
	-- -- -- -- -- -- -- -- -- -- -- -- -- -- -- -- -- --

	cifsIsEnabled	OBJECT-TYPE
	SYNTAX		INTEGER {
					false(1),
					true(2)
				}
	ACCESS		read-only
	STATUS		mandatory
	DESCRIPTION
			"Whether the CIFS protocol is active on the
			 filer."
	::= { cifsOptions 1 }
		
	cifsIsLoginEnabled	OBJECT-TYPE
	SYNTAX			INTEGER {
						false(1),
						true(2)
					}
	ACCESS			read-only
	STATUS			mandatory
	DESCRIPTION
			"Whether new CIFS connections to the filer
			 are currently allowed."
	::= { cifsOptions 2 }
		

	cifsHostName	OBJECT-TYPE
	SYNTAX		DisplayString
	ACCESS		read-only
	STATUS		mandatory
	DESCRIPTION
			"The host name used by the CIFS protocol on this
			 filer."
	::= { cifsOptions 3 }

		
	cifsAltNames	OBJECT-TYPE
	SYNTAX		DisplayString
	ACCESS		read-only
	STATUS		mandatory
	DESCRIPTION
			"Alternate names recognized by the filer."
	::= { cifsOptions 4 }

		
	cifsDomainJoined	OBJECT-TYPE
	SYNTAX			INTEGER {
					    false(1),
					    true(2)
					}
	ACCESS			read-only
	STATUS			mandatory
	DESCRIPTION
			"Has the filer joined an NT domain?
			 If this value is true, cifsDomainName
			 will contain the name of the domain.
			 Otherwise, the filer may have joined
			 a WorkGroup, and cifsWGName will contain
			 the name of the WorkGroup. "
        ::= { cifsOptions 5 }

 
 	cifsDomainName	OBJECT-TYPE
	SYNTAX		DisplayString
	ACCESS		read-only
	STATUS		mandatory
	DESCRIPTION
			"The domain name used by the CIFS 
			 protocol on this filer."
	::= { cifsOptions 6 }


	cifsWGName	OBJECT-TYPE
	SYNTAX		DisplayString
	ACCESS		read-only
	STATUS		mandatory
	DESCRIPTION
			"The workgroup name (if any) used by 
			 the CIFS protocol on this filer."
	::= { cifsOptions 7 }

		
	cifsDCName	OBJECT-TYPE
	SYNTAX		DisplayString
	ACCESS		read-only
	STATUS		mandatory
	DESCRIPTION
			"The name of the Domain Controller used by
			 this filer to authenticate users and file
			 requests."
	::= { cifsOptions 8 }
		

	cifsIsWinsEnabled	OBJECT-TYPE
	SYNTAX			INTEGER {
					    false(1),
					    true(2)
					}
	ACCESS			read-only
	STATUS			mandatory
	DESCRIPTION
			"True if WINS name resolution is enabled
			 on the filer."
	::= { cifsOptions 9 }
		

	cifsWinsServers	OBJECT-TYPE
	SYNTAX		DisplayString
	ACCESS		read-only
	STATUS		mandatory
	DESCRIPTION
			"The name(s) of the WINS servers registered
			 with the filer."
	::= { cifsOptions 10 }


	cifsSecurityModel	OBJECT-TYPE
	SYNTAX			INTEGER {
					    unix(1),
					    pc(2)
					}
	ACCESS			read-only
	STATUS			mandatory
	DESCRIPTION
			"Which type of authentication semantics
			 (Unix or PC) are in use for PC access to 
			 Unix files on the filer. If Unix semantics
			 are in use, no ACL on a Unix file is ever 
			 checked. If PC semantics are in use, the 
			 share level ACL on the share containing the 
			 file is used for authentication instead of 
			 the group portion of the permissions on 
			 the file."
	::= { cifsOptions 11 }
		
		
	cifsPCGenericUser	OBJECT-TYPE
	SYNTAX			DisplayString
	ACCESS			read-only
	STATUS			mandatory
	DESCRIPTION
			"The name of the generic PC user, if any.  This
			 username is used for CIFS access by Unix users
			 who have not authenticated through CIFS or NT."
	::= { cifsOptions 12 }	
	
	  
	cifsOplocksEnabled	OBJECT-TYPE
	SYNTAX			INTEGER {
					not-enabled(1),
					enabled(2)
				}
	ACCESS			read-only
	STATUS			mandatory
	DESCRIPTION
			"Whether oplocks are enabled on the filer."
	::= { cifsOptions 15 }

		
	cifsLevel2OplocksEnabled OBJECT-TYPE
	SYNTAX			INTEGER {
					not-enabled(1),
					enabled(2)
				}
	ACCESS			read-only
	STATUS			mandatory
	DESCRIPTION
			"Whether level 2 oplocks are enabled on the filer."
	::= { cifsOptions 16 }


	cifsPreserveCase	OBJECT-TYPE
	SYNTAX			INTEGER {
					no-preserve-case(1),
					preserve-case(2)
				}
	ACCESS			read-only
	STATUS			mandatory
	DESCRIPTION
			"If this option is set to preserve-case
			 (the default), all filename references
			 will be case preserving.  Otherwise,
			 they are forced to lowercase."
	::= { cifsOptions 17 }
		
		
	cifsSymlinksEnabled	OBJECT-TYPE
	SYNTAX			INTEGER {
					not-enabled(1),
					enabled(2)
				}
	ACCESS			read-only
	STATUS			mandatory
	DESCRIPTION
			"If this option is enabled, CIFS accesses will
			 follow symbolic links using Unix semantics."
	::= { cifsOptions 19 }	


	cifsSymlinkCycleProtEnabled	OBJECT-TYPE
	SYNTAX			INTEGER {
					not-enabled(1),
					enabled(2)
				}
	ACCESS			read-only
	STATUS			mandatory
	DESCRIPTION
			"If this option is enabled, CIFS accesses will
			 through symbolic links will check for cycles
			 in the link graph."
	::= { cifsOptions 20 }	
		

	cifsIsLicensed	OBJECT-TYPE
	SYNTAX		INTEGER {
					false(1),
					true(2)
				}
	ACCESS		read-only
	STATUS		mandatory
	DESCRIPTION
			"Whether the CIFS protocol is licensed on the
			 filer."
	::= { cifsOptions 21 }
		
	cifsPerClientStatsEnabled	OBJECT-TYPE
	SYNTAX		INTEGER {
					false(1),
					true(2)
				}
	ACCESS		read-only
	STATUS		mandatory
	DESCRIPTION
			"True when cifs.per_client_stats are
			 being collected."
	::= { cifsOptions 22 }

	-- -- -- -- -- -- -- -- -- -- -- -- -- -- -- -- -- --
	-- the cifsInfo group
	-- -- -- -- -- -- -- -- -- -- -- -- -- -- -- -- -- --

	cifsStatus		OBJECT-TYPE
	SYNTAX			INTEGER
	ACCESS			read-only
	STATUS			mandatory
	DESCRIPTION
			"Encoding of CIFS startup state on the filer."
              ::= { cifsInfo 1 }
 
	cifsNeedPW		OBJECT-TYPE
	SYNTAX			INTEGER
	ACCESS			read-only
	STATUS			mandatory
	DESCRIPTION
			"Does the administrative password need 
			 to be set before start?"
	::= { cifsInfo 2 }
		
	cifsTimeToShutdown	OBJECT-TYPE
	SYNTAX			INTEGER
	ACCESS			read-only
	STATUS			mandatory
	DESCRIPTION
			"Time remaining until CIFS shutdown"
	::= { cifsInfo 3 }

	
 	cifsMaxConnections	OBJECT-TYPE
	SYNTAX			INTEGER
	ACCESS			read-only
	STATUS			mandatory
	DESCRIPTION
			"The maximum number of simultaneous CIFS 
			 connections allowed on the filer."
	::= { cifsInfo 4 }
		
	cifsMaxTrees		OBJECT-TYPE
	SYNTAX			INTEGER
	ACCESS			read-only
	STATUS			mandatory
	DESCRIPTION
			"The maximum number of simultaneous CIFS
			 trees allowed on the filer."
	::= { cifsInfo 5 }
		
	cifsMaxShares		OBJECT-TYPE
	SYNTAX			INTEGER
	ACCESS			read-only
	STATUS			mandatory
	DESCRIPTION
			"The maximum number of simultaneous CIFS
			 shares allowed on the filer."
	::= { cifsInfo 6 }
		
	cifsMaxFiles		OBJECT-TYPE
	SYNTAX			INTEGER
	ACCESS			read-only
	STATUS			mandatory
	DESCRIPTION
			"The maximum number of concurrently open CIFS
			 files and directories allowed on the filer."
	::= { cifsInfo 7 }


	cifsMaxACLs		OBJECT-TYPE
	SYNTAX			INTEGER
	ACCESS			read-only
	STATUS			mandatory
	DESCRIPTION
			"This object is deprecated, and always has a
			 value of 0."
	::= { cifsInfo 8 }

		
	cifsConnectedUsers	OBJECT-TYPE
	SYNTAX			Counter
	ACCESS			read-only
	STATUS			mandatory
	DESCRIPTION
			"The current number of CIFS users on the
			 filer."
	::= { cifsInfo 9 }
		
	cifsNTrees		OBJECT-TYPE
	SYNTAX			Counter
	ACCESS			read-only
	STATUS			mandatory
	DESCRIPTION
			"The current number of CIFS trees on the
			 filer."
	::= { cifsInfo 10 }
		
	cifsNShares		OBJECT-TYPE
	SYNTAX			Counter
	ACCESS			read-only
	STATUS			mandatory
	DESCRIPTION
			"The current number of CIFS shares on the
			 filer."
	::= { cifsInfo 11 }
		
	cifsNSessions		OBJECT-TYPE
	SYNTAX			Counter
	ACCESS			read-only
	STATUS			mandatory
	DESCRIPTION
			"The current number of active CIFS sessions
			 on the filer."
	::= { cifsInfo 12 }
		
	cifsNOpenFiles		OBJECT-TYPE
	SYNTAX			Counter
	ACCESS			read-only
	STATUS			mandatory
	DESCRIPTION
			"The number of open CIFS files and directories
			 on the filer."
	::= { cifsInfo 13 }
		
	cifsNOpenDirs		OBJECT-TYPE
	SYNTAX			Counter
	ACCESS			read-only
	STATUS			mandatory
	DESCRIPTION
			"The number of open CIFS directories on the
			 filer."
	::= { cifsInfo 14 }
			

	cifsNOplockBreakWaits	OBJECT-TYPE
	SYNTAX			Counter
	ACCESS			read-only
	STATUS			mandatory
	DESCRIPTION
			"The number of open files waiting for oplock
			 break messages to be sent."
	::= { cifsInfo 16 }

		
	cifsNOplockAckWaits	OBJECT-TYPE
	SYNTAX			Counter
	ACCESS			read-only
	STATUS			mandatory
	DESCRIPTION
			"The number of open files waiting for 
			 acknowledgements to oplock break messages."
	::= { cifsInfo 17 }

	cifsSuspectOps		OBJECT-TYPE
	SYNTAX			INTEGER
	ACCESS			read-only
	STATUS			mandatory
	DESCRIPTION
			"A smoothed average of the number of events 
			 per second of the type frequently seen
			 during virus attacks."
	::= { cifsInfo 18 }

	-- -- -- -- -- -- -- -- -- -- -- -- -- -- -- -- -- --
	-- the cifsStats group
	-- -- -- -- -- -- -- -- -- -- -- -- -- -- -- -- -- --

		-- this group contains cifs statistics since the last
		-- time the statistics were cleared

	cifsServ	 OBJECT IDENTIFIER ::= { cifsStats 1 }

	-- cifsPerClient OBJECT IDENTIFIER ::= { cifsStats 2 }

		-- no per-client stats are kept as of the 5.3 release


	-- -- -- -- -- -- -- -- -- -- -- -- -- -- -- -- -- --
	-- the cifsServ group
	-- -- -- -- -- -- -- -- -- -- -- -- -- -- -- -- -- --

		-- this group contains statistics for CIFS
		-- status, and calls processed since the last
		-- time the statistics were cleared

	cifsOps		OBJECT IDENTIFIER ::= { cifsServ 1 }

	cifsReqs	OBJECT IDENTIFIER ::= { cifsServ 2 }

	cifsPercent	OBJECT IDENTIFIER ::= { cifsServ 3 }

	cifsObsReqs	OBJECT IDENTIFIER ::= { cifsServ 4 }

	cifsObsPercent	OBJECT IDENTIFIER ::= { cifsServ 5 }

	-- -- -- -- -- -- -- -- -- -- -- -- -- -- -- -- -- -- 
	-- the cifsOps group
	-- -- -- -- -- -- -- -- -- -- -- -- -- -- -- -- -- -- 

	cifsTotalOps		OBJECT-TYPE
	SYNTAX			Counter
	ACCESS			read-only
	STATUS			mandatory
	DESCRIPTION
			"The number of CIFS operations done by the filer,
			 since the last time the statistics were cleared."
	::= { cifsOps 1 }	

	cifsTotalCalls	OBJECT-TYPE
	SYNTAX		Counter
	ACCESS		read-only
	STATUS		mandatory
	DESCRIPTION
			"The total number of CIFS calls received, since
			 the last time the statistics were cleared.  This
			 is the number of cifsTotalOps plus the number of
			 miscellaneous operations that are not logged
			 which were received in that time period."
	::= { cifsOps 2 }

	cifsBadCalls	OBJECT-TYPE
	SYNTAX		Counter
	ACCESS		read-only
	STATUS		mandatory
	DESCRIPTION
			"The total number of received CIFS calls rejected,
			 since the last time the statistics were cleared."
	::= { cifsOps 3 }

 
	cifsGetAttrs		OBJECT-TYPE
	SYNTAX			Counter
	ACCESS			read-only
	STATUS			mandatory
	DESCRIPTION
			"The total number of CIFS operations to get
			 the attributes on a file or directory, since
			 the last time the statistics were reset."
        ::= { cifsOps 4 }
 
 
	cifsReads		OBJECT-TYPE
	SYNTAX			Counter
	ACCESS			read-only
	STATUS			mandatory
	DESCRIPTION
			"The total number of CIFS Read operations on
			 a file or directory, since the last time the
			 statistics were reset."
	::= { cifsOps 5 }
 
 
	cifsWrites		OBJECT-TYPE
	SYNTAX			Counter
	ACCESS			read-only
	STATUS			mandatory
	DESCRIPTION
			"The total number of CIFS write operations on
			 a file or directory, since the last time the
			 statistics were reset."
	::= { cifsOps 6 }
 
 
	cifsLocks		OBJECT-TYPE
	SYNTAX			Counter
	ACCESS			read-only
	STATUS			mandatory
	DESCRIPTION
			"The number of CIFS file locking requests
			 since the last time the statistics were reset."
	::= { cifsOps 7 }
 

	cifsOpens		OBJECT-TYPE
	SYNTAX			Counter
	ACCESS			read-only
	STATUS			mandatory
	DESCRIPTION
			"The number of calls, via CIFS, to open
			 a file or directory, since the last time
			 the statistics were reset."
	::= { cifsOps 8 }
 
 
 	cifsDirOps		OBJECT-TYPE
 	SYNTAX			Counter
 	ACCESS			read-only
 	STATUS			mandatory
 	DESCRIPTION
			"The number of CIFS directory operations,
			 since the last time the statistics were reset."
        ::= { cifsOps 9 }


 	cifsOthers		OBJECT-TYPE
 	SYNTAX			Counter
 	ACCESS			read-only
 	STATUS			mandatory
 	DESCRIPTION
			"The number of CIFS operations, since the
			 last time the statistics were reset, that
			 don't fall into the categories for GetAttr,
			 Read, Write, Lock, DirOp and Open."
        ::= { cifsOps 10 }
 
 	-- -- -- -- -- -- -- -- -- -- -- -- -- -- -- -- -- -- 
	-- the cifsReqs group
	-- -- -- -- -- -- -- -- -- -- -- -- -- -- -- -- -- -- 

		-- this group contains statistics for the number of
		-- calls received for each CIFS SMB request
		-- since the last time the statistics were cleared

	smbNegProts		OBJECT-TYPE
	SYNTAX			Counter
	ACCESS			read-only
	STATUS			mandatory
	DESCRIPTION
			"The number of SMB NEGOTIATE requests,
			 since the last time the statistics were cleared."
	::= { cifsReqs 1 }

	smbSessionSetupAndXs	OBJECT-TYPE
	SYNTAX			Counter
	ACCESS			read-only
	STATUS			mandatory
	DESCRIPTION
			"The number of SMB SESSION_SETUP_ANDX requests,
			 since the last time the statistics were cleared."
	::= { cifsReqs 2 }

	smbLogoffAndXs		OBJECT-TYPE
	SYNTAX			Counter
	ACCESS			read-only
	STATUS			mandatory
	DESCRIPTION
			"The number of SMB LOGOFF_ANDX requests,
			 since the last time the statistics were cleared."
	::= { cifsReqs 3 }

	smbTreeConnectAndXs	OBJECT-TYPE
	SYNTAX			Counter
	ACCESS			read-only
	STATUS			mandatory
	DESCRIPTION
			"The number of SMB TREE_CONNECT_ANDX requests,
			 since the last time the statistics were cleared."
	::= { cifsReqs 4 }

	smbTreeDisconnects	OBJECT-TYPE
	SYNTAX			Counter
	ACCESS			read-only
	STATUS			mandatory
	DESCRIPTION
			"The number of SMB TREE_DISCONNECT requests,
			 since the last time the statistics were cleared."
	::= { cifsReqs 5 }

	smbTrans2QueryFSInfos	OBJECT-TYPE
	SYNTAX			Counter
	ACCESS			read-only
	STATUS			mandatory
	DESCRIPTION
			"The number of SMB TRANS2_QUERY_FS_INFORMATION
			 requests, since the last time the statistics 
			 were cleared."
	::= { cifsReqs 6 }

	smbEchos		OBJECT-TYPE
	SYNTAX			Counter
	ACCESS			read-only
	STATUS			mandatory
	DESCRIPTION
			"The number of SMB ECHO requests,
			 since the last time the statistics were cleared."
	::= { cifsReqs 7 }

	smbNTCancels		OBJECT-TYPE
	SYNTAX			Counter
	ACCESS			read-only
	STATUS			mandatory
	DESCRIPTION
			"The number of SMB NT_CANCEL requests, since the
			 last time the statistics were cleared."
	::= { cifsReqs 8 }

	smbNTCreateAndXs	OBJECT-TYPE
	SYNTAX			Counter
	ACCESS			read-only
	STATUS			mandatory
	DESCRIPTION
			"The number of SMB NT_CREATE_ANDX requests,
			 since the last time the statistics were cleared."
	::= { cifsReqs 9 }

	smbNTTransactCreates	OBJECT-TYPE
	SYNTAX			Counter
	ACCESS			read-only
	STATUS			mandatory
	DESCRIPTION
			"The number of SMB NT_TRANSACT_CREATE requests,
			 since the last time the statistics were cleared."
	::= { cifsReqs 10 }

	smbCreateTemporaries	OBJECT-TYPE
	SYNTAX			Counter
	ACCESS			read-only
	STATUS			mandatory
	DESCRIPTION
			"The SMB CREATE_TEMPORARY operation is not presently
			 supported, so this value should always be zero."
	::= { cifsReqs 11 }

	smbReadAndXs		OBJECT-TYPE
	SYNTAX			Counter
	ACCESS			read-only
	STATUS			mandatory
	DESCRIPTION
			"The number of SMB READ_ANDX requests,
			 since the last time the statistics were cleared."
	::= { cifsReqs 12 }

	smbWriteAndXs		OBJECT-TYPE
	SYNTAX			Counter
	ACCESS			read-only
	STATUS			mandatory
	DESCRIPTION
			"The number of SMB WRITE_ANDX requests,
			 since the last time the statistics were cleared."
	::= { cifsReqs 13 }

	smbLockingAndXs		OBJECT-TYPE
	SYNTAX			Counter
	ACCESS			read-only
	STATUS			mandatory
	DESCRIPTION
			"The number of SMB LOCKING_ANDX requests,
			 since the last time the statistics were cleared."
	::= { cifsReqs 14 }

	smbSeeks		OBJECT-TYPE
	SYNTAX			Counter
	ACCESS			read-only
	STATUS			mandatory
	DESCRIPTION
			"The number of SMB SEEK requests,
			 since the last time the statistics were cleared."
	::= { cifsReqs 15 }

	smbFlushes		OBJECT-TYPE
	SYNTAX			Counter
	ACCESS			read-only
	STATUS			mandatory
	DESCRIPTION
			"The number of SMB FLUSH requests,
			 since the last time the statistics were cleared."
	::= { cifsReqs 16 }

	smbCloses		OBJECT-TYPE
	SYNTAX			Counter
	ACCESS			read-only
	STATUS			mandatory
	DESCRIPTION
			"The number of SMB CLOSE requests,
			 since the last time the statistics were cleared."
	::= { cifsReqs 17 }

	smbDeletes		OBJECT-TYPE
	SYNTAX			Counter
	ACCESS			read-only
	STATUS			mandatory
	DESCRIPTION
			"The number of SMB DELETE requests,
			 since the last time the statistics were cleared."
	::= { cifsReqs 18 }

	smbRenames		OBJECT-TYPE
	SYNTAX			Counter
	ACCESS			read-only
	STATUS			mandatory
	DESCRIPTION
			"The number of SMB RENAME requests,
			 since the last time the statistics were cleared."
	::= { cifsReqs 19 }

	smbMoves		OBJECT-TYPE
	SYNTAX			Counter
	ACCESS			read-only
	STATUS			mandatory
	DESCRIPTION
			"The SMB MOVE request is not presently supported,
			 so this value should always be zero."
	::= { cifsReqs 20 }

	smbCopies		OBJECT-TYPE
	SYNTAX			Counter
	ACCESS			read-only
	STATUS			mandatory
	DESCRIPTION
			"The SMB COPY request is not presently supported,
			 so this value should always be zero."
	::= { cifsReqs 21 }

	smbTrans2QueryPathInfos	OBJECT-TYPE
	SYNTAX			Counter
	ACCESS			read-only
	STATUS			mandatory
	DESCRIPTION
			"The number of SMB TRANS2_QUERY_PATH_INFORMATION
			 requests, since the last time the statistics 
			 were cleared."
	::= { cifsReqs 22 }

	smbTrans2QueryFileInfos	OBJECT-TYPE
	SYNTAX			Counter
	ACCESS			read-only
	STATUS			mandatory
	DESCRIPTION
			"The number of SMB TRANS2_QUERY_FILE_INFORMATION
			 requests, since the last time the statistics 
			 were cleared."
	::= { cifsReqs 23 }

	smbTrans2SetPathInfos	OBJECT-TYPE
	SYNTAX			Counter
	ACCESS			read-only
	STATUS			mandatory
	DESCRIPTION
			"The number of SMB TRANS2_SET_PATH_INFORMATION
			 requests, since the last time the statistics 
			 were cleared."
	::= { cifsReqs 24 }

	smbTrans2SetFileInfos	OBJECT-TYPE
	SYNTAX			Counter
	ACCESS			read-only
	STATUS			mandatory
	DESCRIPTION
			"The number of SMB TRANS2_SET_FILE_INFORMATION
			 requests, since the last time the statistics 
			 were cleared."
	::= { cifsReqs 25 }

	smbDeleteDirs		OBJECT-TYPE
	SYNTAX			Counter
	ACCESS			read-only
	STATUS			mandatory
	DESCRIPTION
			"The number of SMB DELETE_DIRECTORY requests,
			 since the last time the statistics were cleared."
	::= { cifsReqs 26 }

	smbCheckDirs		OBJECT-TYPE
	SYNTAX			Counter
	ACCESS			read-only
	STATUS			mandatory
	DESCRIPTION
			"The SMB COPY request is not presently supported,
			 so this value should always be zero."
	::= { cifsReqs 27 }

	smbTrans2FindFirst2s	OBJECT-TYPE
	SYNTAX			Counter
	ACCESS			read-only
	STATUS			mandatory
	DESCRIPTION
			"The number of SMB TRANS2_FIND_FIRST2 requests,
			 since the last time the statistics were cleared."
	::= { cifsReqs 28 }

	smbTrans2FindNext2s	OBJECT-TYPE
	SYNTAX			Counter
	ACCESS			read-only
	STATUS			mandatory
	DESCRIPTION
			"The number of SMB TRANS2_FIND_NEXT2 requests,
			 since the last time the statistics were cleared."
	::= { cifsReqs 29 }

	smbFindClose2s		OBJECT-TYPE
	SYNTAX			Counter
	ACCESS			read-only
	STATUS			mandatory
	DESCRIPTION
			"The number of SMB FIND_CLOSE2 requests,
			 since the last time the statistics were cleared."
	::= { cifsReqs 30 }

	smbNTTransactNotifyChgs	OBJECT-TYPE
	SYNTAX			Counter
	ACCESS			read-only
	STATUS			mandatory
	DESCRIPTION
			"The number of SMB NT_TRANSACT_NOTIFY_CHANGE
			 requests, since the last time the statistics 
			 were cleared."
	::= { cifsReqs 31 }

	smbTrans2GetDFSReferrals	OBJECT-TYPE
	SYNTAX			Counter
	ACCESS			read-only
	STATUS			mandatory
	DESCRIPTION
			"The SMB TRANS2_GET_DFS_REFERRAL request is 
			 not presently supported, so this value should 
			 always be zero."
	::= { cifsReqs 32 }

	smbTrans2ReportDFSIncs	OBJECT-TYPE
	SYNTAX			Counter
	ACCESS			read-only
	STATUS			mandatory
	DESCRIPTION
			"The SMB TRANS2_REPORT_DFS_INCONSISTENCY request is 
			 not presently supported, so this value should 
			 always be zero."
	::= { cifsReqs 33 }

	smbOpenPrintFiles	OBJECT-TYPE
	SYNTAX			Counter
	ACCESS			read-only
	STATUS			mandatory
	DESCRIPTION
			"The SMB OPEN_PRINT_FILE request is not supported,
			 so this value should always be zero."
	::= { cifsReqs 34 }

	smbGetPrintQueues	OBJECT-TYPE
	SYNTAX			Counter
	ACCESS			read-only
	STATUS			mandatory
	DESCRIPTION
			"The SMB GET_PRINT_QUEUE request is not supported,
			 so this value should always be zero."
	::= { cifsReqs 35 }

	smbNTTransactIoctls	OBJECT-TYPE
	SYNTAX			Counter
	ACCESS			read-only
	STATUS			mandatory
	DESCRIPTION
			"The number of SMB NT_TRANSACT_IOCTL requests,
			 since the last time the statistics were cleared."
	::= { cifsReqs 36 }

	smbNTTransactQuerySecDescs OBJECT-TYPE
	SYNTAX			Counter
	ACCESS			read-only
	STATUS			mandatory
	DESCRIPTION
			"The number of SMB NT_TRANSACT_QUERY_SECURITY_DESC
			 requests, since the last time the statistics 
			 were cleared."
	::= { cifsReqs 37 }

	smbNTTransactSetSecDescs	OBJECT-TYPE
	SYNTAX			Counter
	ACCESS			read-only
	STATUS			mandatory
	DESCRIPTION
			"The number of SMB NT_TRANSACT_SET_SECURITY_DESC
			 requests, since the last time the statistics 
			 were cleared."
	::= { cifsReqs 38 }


	smbTrans2CreateDirs	OBJECT-TYPE
	SYNTAX			Counter
	ACCESS			read-only
	STATUS			mandatory
	DESCRIPTION
			"The number of SMB TRANS2_CREATE_DIRECTORY 
			 requests, since the last time the statistics 
			 were cleared."
	::= { cifsReqs 39 }


	smbNTCancelCNs		OBJECT-TYPE
	SYNTAX			Counter
	ACCESS			read-only
	STATUS			mandatory
	DESCRIPTION
			"The number of SMB NT_CANCEL requests against
			 change notifications since the last time
			 the statistics were cleared."
	::= { cifsReqs 40 }

	smbNTCancelOthers	OBJECT-TYPE
	SYNTAX			Counter
	ACCESS			read-only
	STATUS			mandatory
	DESCRIPTION
			"The number of SMB NT_CANCEL requests against
			 operations other than change notifications,
			 since the last time the statistics
			 were cleared."
	::= { cifsReqs 41 }


	-- -- -- -- -- -- -- -- -- -- -- -- -- -- -- -- -- --
	-- the cifsObsReqs group
	-- (Obsolete SMB requests)
	-- -- -- -- -- -- -- -- -- -- -- -- -- -- -- -- -- --

	obsSmbClosePrintFiles	OBJECT-TYPE
	SYNTAX			Counter
	ACCESS			read-only
	STATUS			mandatory
	DESCRIPTION
			"The number of SMB CLOSE_PRINT_FILE requests,
			 since the last time the statistics were cleared."
	::= { cifsObsReqs 1 }

	obsSmbCreates		OBJECT-TYPE
	SYNTAX			Counter
	ACCESS			read-only
	STATUS			mandatory
	DESCRIPTION
			"The number of SMB CREATE requests,
			 since the last time the statistics were cleared."
	::= { cifsObsReqs 2 }

	obsSmbCreateDirs	OBJECT-TYPE
	SYNTAX			Counter
	ACCESS			read-only
	STATUS			mandatory
	DESCRIPTION
			"The number of SMB CREATE_DIRECTORY requests,
			 since the last time the statistics were cleared."
	::= { cifsObsReqs 3 }

	obsSmbCreateNews	OBJECT-TYPE
	SYNTAX			Counter
	ACCESS			read-only
	STATUS			mandatory
	DESCRIPTION
			"The number of SMB CREATE_NEW requests,
			 since the last time the statistics were cleared."
	::= { cifsObsReqs 4 }

	obsSmbLockAndReads	OBJECT-TYPE
	SYNTAX			Counter
	ACCESS			read-only
	STATUS			mandatory
	DESCRIPTION
			"The number of SMB LOCK_AND_READ requests,
			 since the last time the statistics were cleared."
	::= { cifsObsReqs 5 }

	obsSmbLockByteRanges	OBJECT-TYPE
	SYNTAX			Counter
	ACCESS			read-only
	STATUS			mandatory
	DESCRIPTION
			"The number of SMB LOCK_BYTE_RANGE requests,
			 since the last time the statistics were cleared."
	::= { cifsObsReqs 6 }

	obsSmbOpens		OBJECT-TYPE
	SYNTAX			Counter
	ACCESS			read-only
	STATUS			mandatory
	DESCRIPTION
			"The number of SMB OPEN requests,
			 since the last time the statistics were cleared."
	::= { cifsObsReqs 7 }

	obsSmbOpenAndXs		OBJECT-TYPE
	SYNTAX			Counter
	ACCESS			read-only
	STATUS			mandatory
	DESCRIPTION
			"The number of SMB OPEN_ANDX requests,
			 since the last time the statistics were cleared."
	::= { cifsObsReqs 8 }

	obsSmbProcessExits	OBJECT-TYPE
	SYNTAX			Counter
	ACCESS			read-only
	STATUS			mandatory
	DESCRIPTION
			"The number of SMB PROCESS_EXIT requests,
			 since the last time the statistics were cleared."
	::= { cifsObsReqs 9 }

	obsSmbQueryInfos	OBJECT-TYPE
	SYNTAX			Counter
	ACCESS			read-only
	STATUS			mandatory
	DESCRIPTION
			"The number of SMB QUERY_INFORMATION requests,
			 since the last time the statistics were cleared."
	::= { cifsObsReqs 10 }

	obsSmbQueryInfo2s	OBJECT-TYPE
	SYNTAX			Counter
	ACCESS			read-only
	STATUS			mandatory
	DESCRIPTION
			"The number of SMB QUERY_INFORMATION2 requests,
			 since the last time the statistics were cleared."
	::= { cifsObsReqs 11 }

	obsSmbReads		OBJECT-TYPE
	SYNTAX			Counter
	ACCESS			read-only
	STATUS			mandatory
	DESCRIPTION
			"The number of SMB READ requests,
			 since the last time the statistics were cleared."
	::= { cifsObsReqs 12 }

	obsSmbReadMPXs		OBJECT-TYPE
	SYNTAX			Counter
	ACCESS			read-only
	STATUS			mandatory
	DESCRIPTION
			"The SMB READ_MPX request is not supported,
			 so this value should always be zero."
	::= { cifsObsReqs 13 }

	obsSmbReadRaws		OBJECT-TYPE
	SYNTAX			Counter
	ACCESS			read-only
	STATUS			mandatory
	DESCRIPTION
			"The number of SMB READ_RAW requests,
			 since the last time the statistics were cleared."
	::= { cifsObsReqs 14 }

	obsSmbSearchs		OBJECT-TYPE
	SYNTAX			Counter
	ACCESS			read-only
	STATUS			mandatory
	DESCRIPTION
			"The number of SMB SEARCH requests,
			 since the last time the statistics were cleared."
	::= { cifsObsReqs 15 }

	obsSmbSetInfos		OBJECT-TYPE
	SYNTAX			Counter
	ACCESS			read-only
	STATUS			mandatory
	DESCRIPTION
			"The number of SMB SET_INFORMATION requests,
			 since the last time the statistics were cleared."
	::= { cifsObsReqs 16 }

	obsSmbSetInfo2s		OBJECT-TYPE
	SYNTAX			Counter
	ACCESS			read-only
	STATUS			mandatory
	DESCRIPTION
			"The number of SMB SET_INFORMATION2 requests,
			 since the last time the statistics were cleared."
	::= { cifsObsReqs 17 }

	obsSmbQueryInfoDisks	OBJECT-TYPE
	SYNTAX			Counter
	ACCESS			read-only
	STATUS			mandatory
	DESCRIPTION
			"The number of SMB QUERY_INFORMATION_DISK
			 requests, since the last time the statistics 
			 were cleared."
	::= { cifsObsReqs 18 }

	obsSmbTrans2Open2s	OBJECT-TYPE
	SYNTAX			Counter
	ACCESS			read-only
	STATUS			mandatory
	DESCRIPTION
			"The number of SMB TRANS2_OPEN2 requests,
			 since the last time the statistics were cleared."
	::= { cifsObsReqs 19 }

	obsSmbTreeConnects	OBJECT-TYPE
	SYNTAX			Counter
	ACCESS			read-only
	STATUS			mandatory
	DESCRIPTION
			"The number of SMB TREE_CONNECT requests,
			 since the last time the statistics were cleared."
	::= { cifsObsReqs 20 }

	obsSmbUnlockByteRanges	OBJECT-TYPE
	SYNTAX			Counter
	ACCESS			read-only
	STATUS			mandatory
	DESCRIPTION
			"The number of SMB UNLOCK_BYTE_RANGE requests,
			 since the last time the statistics were cleared."
	::= { cifsObsReqs 21 }

	obsSmbWrites		OBJECT-TYPE
	SYNTAX			Counter
	ACCESS			read-only
	STATUS			mandatory
	DESCRIPTION
			"The number of SMB WRITE requests,
			 since the last time the statistics were cleared."
	::= { cifsObsReqs 22 }

	obsSmbWriteAndUnlocks	OBJECT-TYPE
	SYNTAX			Counter
	ACCESS			read-only
	STATUS			mandatory
	DESCRIPTION
			"The number of SMB WRITE_AND_UNLOCK requests,
			 since the last time the statistics were cleared."
	::= { cifsObsReqs 23 }

	obsSmbWriteAndCloses	OBJECT-TYPE
	SYNTAX			Counter
	ACCESS			read-only
	STATUS			mandatory
	DESCRIPTION
			"The number of SMB WRITE_AND_CLOSE requests,
			 since the last time the statistics were cleared."
	::= { cifsObsReqs 24 }

	obsSmbWriteMPXs		OBJECT-TYPE
	SYNTAX			Counter
	ACCESS			read-only
	STATUS			mandatory
	DESCRIPTION
			"The SMB WRITE_MPX request is not supported,
			 so this value should always be zero."
	::= { cifsObsReqs 25 }

	obsSmbWritePrintFiles	OBJECT-TYPE
	SYNTAX			Counter
	ACCESS			read-only
	STATUS			mandatory
	DESCRIPTION
			"The SMB WRITE_PRINT_FILE request is not supported,
			 so this value should always be zero."
	::= { cifsObsReqs 26 }

	obsSmbWriteRaws		OBJECT-TYPE
	SYNTAX			Counter
	ACCESS			read-only
	STATUS			mandatory
	DESCRIPTION
			"The number of SMB WRITE_RAW requests,
			 since the last time the statistics were cleared."
	::= { cifsObsReqs 27 }



	-- -- -- -- -- -- -- -- -- -- -- -- -- -- -- -- -- --
	-- the cifsPercent group
	-- -- -- -- -- -- -- -- -- -- -- -- -- -- -- -- -- --

		-- this group contains statistics for the number of
		-- calls received for each CIFS SMB request
		-- as a percentage of total CIFS calls received,
		-- since the last time the statistics were cleared

	smbNegProtPct		OBJECT-TYPE
	SYNTAX			INTEGER (0..100)
	ACCESS			read-only
	STATUS			mandatory
	DESCRIPTION
			"The number of SMB NEGOTIATE requests,
			 as a percentage of total CIFS calls received,
			 since the last time the statistics were cleared."
	::= { cifsPercent 1 }

	smbSessionSetupAndXPct	OBJECT-TYPE
	SYNTAX			INTEGER (0..100)
	ACCESS			read-only
	STATUS			mandatory
	DESCRIPTION
			"The number of SMB SESSION_SETUP_ANDX requests,
			 as a percentage of total CIFS calls received,
			 since the last time the statistics were cleared."
	::= { cifsPercent 2 }

	smbLogoffAndXPct	OBJECT-TYPE
	SYNTAX			INTEGER (0..100)
	ACCESS			read-only
	STATUS			mandatory
	DESCRIPTION
			"The number of SMB LOGOFF_ANDX requests,
			 as a percentage of total CIFS calls received,
			 since the last time the statistics were cleared."
	::= { cifsPercent 3 }

	smbTreeConnectAndXPct	OBJECT-TYPE
	SYNTAX			INTEGER (0..100)
	ACCESS			read-only
	STATUS			mandatory
	DESCRIPTION
			"The number of SMB TREE_CONNECT_ANDX requests,
			 as a percentage of total CIFS calls received,
			 since the last time the statistics were cleared."
	::= { cifsPercent 4 }

	smbTreeDisconnectAndXPct OBJECT-TYPE
	SYNTAX			INTEGER (0..100)
	ACCESS			read-only
	STATUS			mandatory
	DESCRIPTION
			"The number of SMB TREE_DISCONNECT_ANDX requests,
			 as a percentage of total CIFS calls received,
			 since the last time the statistics were cleared."
	::= { cifsPercent 5 }

	smbTrans2QueryFSInfoPct	OBJECT-TYPE
	SYNTAX			INTEGER (0..100)
	ACCESS			read-only
	STATUS			mandatory
	DESCRIPTION
			"The number of SMB TRANS2_QUERY_FS_INFORMATION
			 requests, as a percentage of total CIFS calls
			 received, since the last time the statistics 
			 were cleared."
	::= { cifsPercent 6 }

	smbEchoPct		OBJECT-TYPE
	SYNTAX			INTEGER (0..100)
	ACCESS			read-only
	STATUS			mandatory
	DESCRIPTION
			"The number of SMB ECHO requests,
			 as a percentage of total CIFS calls received,
			 since the last time the statistics were cleared."
	::= { cifsPercent 7 }

	smbNTCancelPct		OBJECT-TYPE
	SYNTAX			INTEGER (0..100)
	ACCESS			read-only
	STATUS			mandatory
	DESCRIPTION
			"The number of SMB NT_CANCEL requests,
			 as a percentage of total CIFS calls received,
			 since the last time the statistics were cleared."
	::= { cifsPercent 8 }

	smbCreateAndXPct	OBJECT-TYPE
	SYNTAX			INTEGER (0..100)
	ACCESS			read-only
	STATUS			mandatory
	DESCRIPTION
			"The number of SMB NT_CREATE_ANDX requests,
			 as a percentage of total CIFS calls received,
			 since the last time the statistics were cleared."
	::= { cifsPercent 9 }

	smbTransactCreatePct	OBJECT-TYPE
	SYNTAX			INTEGER (0..100)
	ACCESS			read-only
	STATUS			mandatory
	DESCRIPTION
			"The number of SMB NT_TRANSACT_CREATE requests,
			 as a percentage of total CIFS calls received,
			 since the last time the statistics were cleared."
	::= { cifsPercent 10 }

	smbCreateTemporaryPct	OBJECT-TYPE
	SYNTAX			INTEGER (0..100)
	ACCESS			read-only
	STATUS			mandatory
	DESCRIPTION
			"The number of SMB CREATE_TEMPORARY requests,
			 as a percentage of total CIFS calls received,
			 since the last time the statistics were cleared."
	::= { cifsPercent 11 }

	smbReadAndXPct		OBJECT-TYPE
	SYNTAX			INTEGER (0..100)
	ACCESS			read-only
	STATUS			mandatory
	DESCRIPTION
			"The number of SMB READ_ANDX requests,
			 as a percentage of total CIFS calls received,
			 since the last time the statistics were cleared."
	::= { cifsPercent 12 }

	smbWriteAndXPct		OBJECT-TYPE
	SYNTAX			INTEGER (0..100)
	ACCESS			read-only
	STATUS			mandatory
	DESCRIPTION
			"The number of SMB WRITE_ANDX requests,
			 as a percentage of total CIFS calls received,
			 since the last time the statistics were cleared."
	::= { cifsPercent 13 }

	smbLockingAndXPct	OBJECT-TYPE
	SYNTAX			INTEGER (0..100)
	ACCESS			read-only
	STATUS			mandatory
	DESCRIPTION
			"The number of SMB LOCKING_ANDX requests,
			 as a percentage of total CIFS calls received,
			 since the last time the statistics were cleared."
	::= { cifsPercent 14 }

	smbSeekPct		OBJECT-TYPE
	SYNTAX			INTEGER (0..100)
	ACCESS			read-only
	STATUS			mandatory
	DESCRIPTION
			"The number of SMB SEEK requests,
			 as a percentage of total CIFS calls received,
			 since the last time the statistics were cleared."
	::= { cifsPercent 15 }

	smbFlushPct		OBJECT-TYPE
	SYNTAX			INTEGER (0..100)
	ACCESS			read-only
	STATUS			mandatory
	DESCRIPTION
			"The number of SMB FLUSH requests,
			 as a percentage of total CIFS calls received,
			 since the last time the statistics were cleared."
	::= { cifsPercent 16 }

	smbClosePct		OBJECT-TYPE
	SYNTAX			INTEGER (0..100)
	ACCESS			read-only
	STATUS			mandatory
	DESCRIPTION
			"The number of SMB CLOSE requests,
			 as a percentage of total CIFS calls received,
			 since the last time the statistics were cleared."
	::= { cifsPercent 17 }

	smbDeletePct		OBJECT-TYPE
	SYNTAX			INTEGER (0..100)
	ACCESS			read-only
	STATUS			mandatory
	DESCRIPTION
			"The number of SMB DELETE requests,
			 as a percentage of total CIFS calls received,
			 since the last time the statistics were cleared."
	::= { cifsPercent 18 }

	smbRenamePct		OBJECT-TYPE
	SYNTAX			INTEGER (0..100)
	ACCESS			read-only
	STATUS			mandatory
	DESCRIPTION
			"The number of SMB RENAME requests,
			 as a percentage of total CIFS calls received,
			 since the last time the statistics were cleared."
	::= { cifsPercent 19 }

	smbMovePct		OBJECT-TYPE
	SYNTAX			INTEGER (0..100)
	ACCESS			read-only
	STATUS			mandatory
	DESCRIPTION
			"The number of SMB MOVE requests,
			 as a percentage of total CIFS calls received,
			 since the last time the statistics were cleared."
	::= { cifsPercent 20 }

	smbCopyPct		OBJECT-TYPE
	SYNTAX			INTEGER (0..100)
	ACCESS			read-only
	STATUS			mandatory
	DESCRIPTION
			"The number of SMB COPY requests,
			 as a percentage of total CIFS calls received,
			 since the last time the statistics were cleared."
	::= { cifsPercent 21 }

	smbTrans2QueryPathInfoPct OBJECT-TYPE
	SYNTAX			INTEGER (0..100)
	ACCESS			read-only
	STATUS			mandatory
	DESCRIPTION
			"The number of SMB TRANS2_QUERY_PATH_INFORMATION
			 requests, as a percentage of total CIFS calls
			 received, since the last time the statistics 
			 were cleared."
	::= { cifsPercent 22 }

	smbTrans2QueryFileInfoPct OBJECT-TYPE
	SYNTAX			INTEGER (0..100)
	ACCESS			read-only
	STATUS			mandatory
	DESCRIPTION
			"The number of SMB TRANS2_QUERY_FILE_INFORMATION
			 requests, as a percentage of total CIFS calls
			 received, since the last time the statistics 
			 were cleared."
	::= { cifsPercent 23 }

	smbTrans2SetPathInfoPct	OBJECT-TYPE
	SYNTAX			INTEGER (0..100)
	ACCESS			read-only
	STATUS			mandatory
	DESCRIPTION
			"The number of SMB TRANS2_SET_PATH_INFORMATION
			 requests, as a percentage of total CIFS calls
			 received, since the last time the statistics 
			 were cleared."
	::= { cifsPercent 24 }

	smbTrans2SetFileInfoPct	OBJECT-TYPE
	SYNTAX			INTEGER (0..100)
	ACCESS			read-only
	STATUS			mandatory
	DESCRIPTION
			"The number of SMB TRANS2_SET_FILE_INFORMATION
			 requests, as a percentage of total CIFS calls
			 received, since the last time the statistics 
			 were cleared."
	::= { cifsPercent 25 }

	smbDeleteDirPct		OBJECT-TYPE
	SYNTAX			INTEGER (0..100)
	ACCESS			read-only
	STATUS			mandatory
	DESCRIPTION
			"The number of SMB DELETE_DIRECTORY requests,
			 as a percentage of total CIFS calls received,
			 since the last time the statistics were cleared."
	::= { cifsPercent 26 }

	smbCheckDirPct		OBJECT-TYPE
	SYNTAX			INTEGER (0..100)
	ACCESS			read-only
	STATUS			mandatory
	DESCRIPTION
			"The number of SMB CHECK_DIRECTORY requests,
			 as a percentage of total CIFS calls received,
			 since the last time the statistics were cleared."
	::= { cifsPercent 27 }


	smbTrans2FindFirst2Pct	OBJECT-TYPE
	SYNTAX			INTEGER (0..100)
	ACCESS			read-only
	STATUS			mandatory
	DESCRIPTION
			"The number of SMB TRANS2_FIND_FIRST2 requests,
			 as a percentage of total CIFS calls received,
			 since the last time the statistics were cleared."
	::= { cifsPercent 28 }

	smbTrans2FindNext2Pct	OBJECT-TYPE
	SYNTAX			INTEGER (0..100)
	ACCESS			read-only
	STATUS			mandatory
	DESCRIPTION
			"The number of SMB TRANS2_FIND_NEXT2 requests,
			 as a percentage of total CIFS calls received,
			 since the last time the statistics were cleared."
	::= { cifsPercent 29 }

	smbFindClose2Pct	OBJECT-TYPE
	SYNTAX			INTEGER (0..100)
	ACCESS			read-only
	STATUS			mandatory
	DESCRIPTION
			"The number of SMB FIND_CLOSE2 requests,
			 as a percentage of total CIFS calls received,
			 since the last time the statistics were cleared."
	::= { cifsPercent 30 }

	smbNTTransactNotifyChgPct OBJECT-TYPE
	SYNTAX			INTEGER (0..100)
	ACCESS			read-only
	STATUS			mandatory
	DESCRIPTION
			"The number of SMB NT_TRANSACT_NOTIFY_CHANGE
			 requests, as a percentage of total CIFS calls
			 received, since the last time the statistics 
			 were cleared."
	::= { cifsPercent 31 }

	smbTrans2GetDFSReferralPct OBJECT-TYPE
	SYNTAX			INTEGER (0..100)
	ACCESS			read-only
	STATUS			mandatory
	DESCRIPTION
			"The number of SMB TRANS2_GET_DFS_REFERRAL
			 requests, as a percentage of total CIFS calls
			 received, since the last time the statistics 
			 were cleared."
	::= { cifsPercent 32 }

	smbTrans2ReportDFSIncPct OBJECT-TYPE
	SYNTAX			INTEGER (0..100)
	ACCESS			read-only
	STATUS			mandatory
	DESCRIPTION
			"The number of SMB TRANS2_REPORT_DFS_INCONSISTENCY
			 requests, as a percentage of total CIFS calls
			 received, since the last time the statistics 
			 were cleared."
	::= { cifsPercent 33 }

	smbOpenPrintFilePct	OBJECT-TYPE
	SYNTAX			INTEGER (0..100)
	ACCESS			read-only
	STATUS			mandatory
	DESCRIPTION
			"The number of SMB OPEN_PRINT_FILE requests,
			 as a percentage of total CIFS calls received,
			 since the last time the statistics were cleared."
	::= { cifsPercent 34 }

	smbGetPrintQueuePct	OBJECT-TYPE
	SYNTAX			INTEGER (0..100)
	ACCESS			read-only
	STATUS			mandatory
	DESCRIPTION
			"The number of SMB GET_PRINT_QUEUE requests,
			 as a percentage of total CIFS calls received,
			 since the last time the statistics were cleared."
	::= { cifsPercent 35 }

	smbNTTransactIoctlPct	OBJECT-TYPE
	SYNTAX			INTEGER (0..100)
	ACCESS			read-only
	STATUS			mandatory
	DESCRIPTION
			"The number of SMB NT_TRANSACT_IOCTL requests,
			 as a percentage of total CIFS calls received,
			 since the last time the statistics were cleared."
	::= { cifsPercent 36 }

	smbNTTransactQuerySecDescPct OBJECT-TYPE
	SYNTAX			INTEGER (0..100)
	ACCESS			read-only
	STATUS			mandatory
	DESCRIPTION
			"The number of SMB NT_TRANSACT_QUERY_SECURITY_DESC
			 requests, as a percentage of total CIFS calls
			 received, since the last time the statistics 
			 were cleared."
	::= { cifsPercent 37 }

	smbNTTransactSetSecDescPct	OBJECT-TYPE
	SYNTAX			INTEGER (0..100)
	ACCESS			read-only
	STATUS			mandatory
	DESCRIPTION
			"The number of SMB NT_TRANSACT_SET_SECURITY_DESC
			 requests, as a percentage of total CIFS calls
			 received, since the last time the statistics 
			 were cleared."
	::= { cifsPercent 38 }


	smbTrans2CreateDirPct	OBJECT-TYPE
	SYNTAX			INTEGER (0..100)
	ACCESS			read-only
	STATUS			mandatory
	DESCRIPTION
			"The number of SMB TRANS2_CREATE_DIRECTORY 
			 requests, as a percentage of total CIFS calls
			 received, since the last time the statistics 
			 were cleared."
	::= { cifsPercent 39 }


	smbNTCancelCNPct	OBJECT-TYPE
	SYNTAX			INTEGER (0..100)
	ACCESS			read-only
	STATUS			mandatory
	DESCRIPTION
			"The number of SMB NT_CANCEL requests against
			 change notifications, as a percentage of
			 total CIFS calls received, since the last
			 time the statistics were cleared."
	::= { cifsPercent 40 }

	smbNTCancelOtherPct	OBJECT-TYPE
	SYNTAX			INTEGER (0..100)
	ACCESS			read-only
	STATUS			mandatory
	DESCRIPTION
			"The number of SMB NT_CANCEL requests against
			 calls other than change notifications, as 
			 a percentage of total CIFS calls received, 
			 since the last time the statistics were 
			 cleared."
	::= { cifsPercent 41 }

	-- -- -- -- -- -- -- -- -- -- -- -- -- -- -- -- -- --
	-- the obsPct group
	-- (Obsolete SMB requests)
	-- -- -- -- -- -- -- -- -- -- -- -- -- -- -- -- -- --

	obsSmbClosePrintFilePct	OBJECT-TYPE
	SYNTAX			INTEGER (0..100)
	ACCESS			read-only
	STATUS			mandatory
	DESCRIPTION
			"The number of SMB CLOSE_PRINT_FILE requests,
			 as a percentage of total CIFS calls received,
			 since the last time the statistics were cleared."
	::= { cifsObsPercent 1 }

	obsSmbCreatePct		OBJECT-TYPE
	SYNTAX			INTEGER (0..100)
	ACCESS			read-only
	STATUS			mandatory
	DESCRIPTION
			"The number of SMB CREATE requests,
			 as a percentage of total CIFS calls received,
			 since the last time the statistics were cleared."
	::= { cifsObsPercent 2 }

	obsSmbCreateDirPct	OBJECT-TYPE
	SYNTAX			INTEGER (0..100)
	ACCESS			read-only
	STATUS			mandatory
	DESCRIPTION
			"The number of SMB CREATE_DIRECTORY requests,
			 as a percentage of total CIFS calls received,
			 since the last time the statistics were cleared."
	::= { cifsObsPercent 3 }

	obsSmbCreateNewPct	OBJECT-TYPE
	SYNTAX			INTEGER (0..100)
	ACCESS			read-only
	STATUS			mandatory
	DESCRIPTION
			"The number of SMB CREATE_NEW requests,
			 as a percentage of total CIFS calls received,
			 since the last time the statistics were cleared."
	::= { cifsObsPercent 4 }

	obsSmbLockAndReadPct	OBJECT-TYPE
	SYNTAX			INTEGER (0..100)
	ACCESS			read-only
	STATUS			mandatory
	DESCRIPTION
			"The number of SMB LOCK_AND_READ requests,
			 as a percentage of total CIFS calls received,
			 since the last time the statistics were cleared."
	::= { cifsObsPercent 5 }

	obsSmbLockByteRangePct	OBJECT-TYPE
	SYNTAX			INTEGER (0..100)
	ACCESS			read-only
	STATUS			mandatory
	DESCRIPTION
			"The number of SMB LOCK_BYTE_RANGE requests,
			 as a percentage of total CIFS calls received,
			 since the last time the statistics were cleared."
	::= { cifsObsPercent 6 }

	obsSmbOpenPct		OBJECT-TYPE
	SYNTAX			INTEGER (0..100)
	ACCESS			read-only
	STATUS			mandatory
	DESCRIPTION
			"The number of SMB OPEN requests,
			 as a percentage of total CIFS calls received,
			 since the last time the statistics were cleared."
	::= { cifsObsPercent 7 }

	obsSmbOpenAndXPct	OBJECT-TYPE
	SYNTAX			INTEGER (0..100)
	ACCESS			read-only
	STATUS			mandatory
	DESCRIPTION
			"The number of SMB OPEN_ANDX requests,
			 as a percentage of total CIFS calls received,
			 since the last time the statistics were cleared."
	::= { cifsObsPercent 8 }

	obsSmbProcessExitPct	OBJECT-TYPE
	SYNTAX			INTEGER (0..100)
	ACCESS			read-only
	STATUS			mandatory
	DESCRIPTION
			"The number of SMB PROCESS_EXIT requests,
			 as a percentage of total CIFS calls received,
			 since the last time the statistics were cleared."
	::= { cifsObsPercent 9 }

	obsSmbQueryInfoPct	OBJECT-TYPE
	SYNTAX			INTEGER (0..100)
	ACCESS			read-only
	STATUS			mandatory
	DESCRIPTION
			"The number of SMB QUERY_INFORMATION requests,
			 as a percentage of total CIFS calls received,
			 since the last time the statistics were cleared."
	::= { cifsObsPercent 10 }

	obsSmbQueryInfo2Pct	OBJECT-TYPE
	SYNTAX			INTEGER (0..100)
	ACCESS			read-only
	STATUS			mandatory
	DESCRIPTION
			"The number of SMB QUERY_INFORMATION2 requests,
			 as a percentage of total CIFS calls received,
			 since the last time the statistics were cleared."
	::= { cifsObsPercent 11 }

	obsSmbReadPct		OBJECT-TYPE
	SYNTAX			INTEGER (0..100)
	ACCESS			read-only
	STATUS			mandatory
	DESCRIPTION
			"The number of SMB READ requests,
			 as a percentage of total CIFS calls received,
			 since the last time the statistics were cleared."
	::= { cifsObsPercent 12 }

	obsSmbReadMPXPct	OBJECT-TYPE
	SYNTAX			INTEGER (0..100)
	ACCESS			read-only
	STATUS			mandatory
	DESCRIPTION
			"The number of SMB READ_MPX requests,
			 as a percentage of total CIFS calls received,
			 since the last time the statistics were cleared."
	::= { cifsObsPercent 13 }

	obsSmbReadRawPct	OBJECT-TYPE
	SYNTAX			INTEGER (0..100)
	ACCESS			read-only
	STATUS			mandatory
	DESCRIPTION
			"The number of SMB READ_RAW requests,
			 as a percentage of total CIFS calls received,
			 since the last time the statistics were cleared."
	::= { cifsObsPercent 14 }

	obsSmbSearchPct		OBJECT-TYPE
	SYNTAX			INTEGER (0..100)
	ACCESS			read-only
	STATUS			mandatory
	DESCRIPTION
			"The number of SMB SEARCH requests,
			 as a percentage of total CIFS calls received,
			 since the last time the statistics were cleared."
	::= { cifsObsPercent 15 }

	obsSmbSetInfoPct	OBJECT-TYPE
	SYNTAX			INTEGER (0..100)
	ACCESS			read-only
	STATUS			mandatory
	DESCRIPTION
			"The number of SMB SET_INFORMATION requests,
			 as a percentage of total CIFS calls received,
			 since the last time the statistics were cleared."
	::= { cifsObsPercent 16 }

	obsSmbSetInfo2Pct	OBJECT-TYPE
	SYNTAX			INTEGER (0..100)
	ACCESS			read-only
	STATUS			mandatory
	DESCRIPTION
			"The number of SMB SET_INFORMATION2 requests,
			 as a percentage of total CIFS calls received,
			 since the last time the statistics were cleared."
	::= { cifsObsPercent 17 }

	obsSmbQueryInfoDiskPct	OBJECT-TYPE
	SYNTAX			INTEGER (0..100)
	ACCESS			read-only
	STATUS			mandatory
	DESCRIPTION
			"The number of SMB QUERY_INFORMATION_DISK
			 requests, as a percentage of total CIFS calls
			 received, since the last time the statistics 
			 were cleared."
	::= { cifsObsPercent 18 }

	obsSmbTrans2Open2Pct	OBJECT-TYPE
	SYNTAX			INTEGER (0..100)
	ACCESS			read-only
	STATUS			mandatory
	DESCRIPTION
			"The number of SMB TRANS2_OPEN2 requests,
			 as a percentage of total CIFS calls received,
			 since the last time the statistics were cleared."
	::= { cifsObsPercent 19 }

	obsSmbTreeConnectPct	OBJECT-TYPE
	SYNTAX			INTEGER (0..100)
	ACCESS			read-only
	STATUS			mandatory
	DESCRIPTION
			"The number of SMB TREE_CONNECT requests,
			 as a percentage of total CIFS calls received,
			 since the last time the statistics were cleared."
	::= { cifsObsPercent 20 }

	obsSmbUnlockByteRangePct OBJECT-TYPE
	SYNTAX			INTEGER (0..100)
	ACCESS			read-only
	STATUS			mandatory
	DESCRIPTION
			"The number of SMB UNLOCK_BYTE_RANGE requests,
			 as a percentage of total CIFS calls received,
			 since the last time the statistics were cleared."
	::= { cifsObsPercent 21 }

	obsSmbWritePct		OBJECT-TYPE
	SYNTAX			INTEGER (0..100)
	ACCESS			read-only
	STATUS			mandatory
	DESCRIPTION
			"The number of SMB WRITE requests,
			 as a percentage of total CIFS calls received,
			 since the last time the statistics were cleared."
	::= { cifsObsPercent 22 }

	obsSmbWriteAndUnlockPct	OBJECT-TYPE
	SYNTAX			INTEGER (0..100)
	ACCESS			read-only
	STATUS			mandatory
	DESCRIPTION
			"The number of SMB WRITE_AND_UNLOCK requests,
			 as a percentage of total CIFS calls received,
			 since the last time the statistics were cleared."
	::= { cifsObsPercent 23 }

	obsSmbWriteAndClosePct	OBJECT-TYPE
	SYNTAX			INTEGER (0..100)
	ACCESS			read-only
	STATUS			mandatory
	DESCRIPTION
			"The number of SMB WRITE_AND_CLOSE requests,
			 as a percentage of total CIFS calls received,
			 since the last time the statistics were cleared."
	::= { cifsObsPercent 24 }

	obsSmbWriteMPXPct	OBJECT-TYPE
	SYNTAX			INTEGER (0..100)
	ACCESS			read-only
	STATUS			mandatory
	DESCRIPTION
			"The number of SMB WRITE_MPX requests,
			 as a percentage of total CIFS calls received,
			 since the last time the statistics were cleared."
	::= { cifsObsPercent 25 }

	obsSmbWritePrintFilePct	OBJECT-TYPE
	SYNTAX			INTEGER (0..100)
	ACCESS			read-only
	STATUS			mandatory
	DESCRIPTION
			"The number of SMB WRITE_PRINT_FILE requests,
			 as a percentage of total CIFS calls received,
			 since the last time the statistics were cleared."
	::= { cifsObsPercent 26 }

	obsSmbWriteRawPct	OBJECT-TYPE
	SYNTAX			INTEGER (0..100)
	ACCESS			read-only
	STATUS			mandatory
	DESCRIPTION
			"The number of SMB WRITE_RAW requests,
			 as a percentage of total CIFS calls received,
			 since the last time the statistics were cleared."
	::= { cifsObsPercent 27 }

	-- -- -- -- -- -- -- -- -- -- -- -- -- -- -- -- -- -- 
	-- the cifsMisc group
	-- These statistics are primarily of interest to
	-- NetApp developers.
	-- -- -- -- -- -- -- -- -- -- -- -- -- -- -- -- -- -- 

	cifsCancelLocks		OBJECT-TYPE
	SYNTAX			Counter
	ACCESS			read-only
	STATUS			mandatory
	DESCRIPTION
			"Undocumented"
	::= { cifsMisc 1 }
	
	cifsWaitLocks		OBJECT-TYPE
	SYNTAX			Counter
	ACCESS			read-only
	STATUS			mandatory
	DESCRIPTION
			"Undocumented"
	::= { cifsMisc 2 }
	
	cifsCopyToAligns	OBJECT-TYPE
	SYNTAX			Counter
	ACCESS			read-only
	STATUS			mandatory
	DESCRIPTION
			"Undocumented"
	::= { cifsMisc 3 }
	
	cifsAlignedSmalls	OBJECT-TYPE
	SYNTAX			Counter
	ACCESS			read-only
	STATUS			mandatory
	DESCRIPTION
			"Undocumented"
	::= { cifsMisc 4 }
	
	cifsAlignedLarges	OBJECT-TYPE
	SYNTAX			Counter
	ACCESS			read-only
	STATUS			mandatory
	DESCRIPTION
			"Undocumented"
	::= { cifsMisc 5 }
	
	cifsAlignedSmallRels	OBJECT-TYPE
	SYNTAX			Counter
	ACCESS			read-only
	STATUS			mandatory
	DESCRIPTION
			"Undocumented"
	::= { cifsMisc 6 }
	
	cifsAlignedLargeRels	OBJECT-TYPE
	SYNTAX			Counter
	ACCESS			read-only
	STATUS			mandatory
	DESCRIPTION
			"Undocumented"
	::= { cifsMisc 7 }
	
	cifsMbufWaits		OBJECT-TYPE
	SYNTAX			Counter
	ACCESS			read-only
	STATUS			mandatory
	DESCRIPTION
			"Undocumented"
	::= { cifsMisc 8 }
	
	cifsNbtWaits		OBJECT-TYPE
	SYNTAX			Counter
	ACCESS			read-only
	STATUS			mandatory
	DESCRIPTION
			"Undocumented"
	::= { cifsMisc 9 }
	
	cifsCwaWaits		OBJECT-TYPE
	SYNTAX			Counter
	ACCESS			read-only
	STATUS			mandatory
	DESCRIPTION
			"Undocumented"
	::= { cifsMisc 10 }
	
	cifsMultipleVCs		OBJECT-TYPE
	SYNTAX			Counter
	ACCESS			read-only
	STATUS			mandatory
	DESCRIPTION
			"Undocumented"
	::= { cifsMisc 11 }
	
	cifsPDCUpcalls		OBJECT-TYPE
	SYNTAX			Counter
	ACCESS			read-only
	STATUS			mandatory
	DESCRIPTION
			"Undocumented"
	::= { cifsMisc 12 }
	
	cifsQueuedWriteRaws	OBJECT-TYPE
	SYNTAX			Counter
	ACCESS			read-only
	STATUS			mandatory
	DESCRIPTION
			"Undocumented"
	::= { cifsMisc 13 }
	
	cifsNBTDisconnects	OBJECT-TYPE
	SYNTAX			Counter
	ACCESS			read-only
	STATUS			mandatory
	DESCRIPTION
			"Undocumented"
	::= { cifsMisc 14 }
	
	cifsSMBDisconnects	OBJECT-TYPE
	SYNTAX			Counter
	ACCESS			read-only
	STATUS			mandatory
	DESCRIPTION
			"Undocumented"
	::= { cifsMisc 15 }
	
	cifsDupDisconnects	OBJECT-TYPE
	SYNTAX			Counter
	ACCESS			read-only
	STATUS			mandatory
	DESCRIPTION
			"Undocumented"
	::= { cifsMisc 16 }
	
	cifsOpLkBatchToL2s	OBJECT-TYPE
	SYNTAX			Counter
	ACCESS			read-only
	STATUS			mandatory
	DESCRIPTION
			"Undocumented"
	::= { cifsMisc 17 }
	
	cifsOpLkBatchToNones	OBJECT-TYPE
	SYNTAX			Counter
	ACCESS			read-only
	STATUS			mandatory
	DESCRIPTION
			"Undocumented"
	::= { cifsMisc 18 }
	
	cifsOpLkL2ToNones	OBJECT-TYPE
	SYNTAX			Counter
	ACCESS			read-only
	STATUS			mandatory
	DESCRIPTION
			"Undocumented"
	::= { cifsMisc 19 }
	
	cifsOpLkNoBreakAcks	OBJECT-TYPE
	SYNTAX			Counter
	ACCESS			read-only
	STATUS			mandatory
	DESCRIPTION
			"Undocumented"
	::= { cifsMisc 20 }
	
	cifsOpLkIgnoredAcks	OBJECT-TYPE
	SYNTAX			Counter
	ACCESS			read-only
	STATUS			mandatory
	DESCRIPTION
			"Undocumented"
	::= { cifsMisc 21 }
	
	cifsOpLkMultiWaiters	OBJECT-TYPE
	SYNTAX			Counter
	ACCESS			read-only
	STATUS			mandatory
	DESCRIPTION
			"Undocumented"
	::= { cifsMisc 22 }
	
	cifsSharingErrorRetries	OBJECT-TYPE
	SYNTAX			Counter
	ACCESS			read-only
	STATUS			mandatory
	DESCRIPTION
			"Undocumented"
	::= { cifsMisc 23 }
	
	cifsOpLkWaiterTimedOuts	OBJECT-TYPE
	SYNTAX			Counter
	ACCESS			read-only
	STATUS			mandatory
	DESCRIPTION
			"Undocumented"
	::= { cifsMisc 24 }
	
	cifsOpLkDelayedBreaks	OBJECT-TYPE
	SYNTAX			Counter
	ACCESS			read-only
	STATUS			mandatory
	DESCRIPTION
			"Undocumented"
	::= { cifsMisc 25 }
	
	cifsOpLkEarlyNFSs	OBJECT-TYPE
	SYNTAX			Counter
	ACCESS			read-only
	STATUS			mandatory
	DESCRIPTION
			"Undocumented"
	::= { cifsMisc 26 }
	
	cifsOpLkNFSWaiteds	OBJECT-TYPE
	SYNTAX			Counter
	ACCESS			read-only
	STATUS			mandatory
	DESCRIPTION
			"Undocumented"
	::= { cifsMisc 27 }
	
	cifsMaxNFSBkWaiterCount	OBJECT-TYPE
	SYNTAX			INTEGER
	ACCESS			read-only
	STATUS			mandatory
	DESCRIPTION
			"Undocumented"
	::= { cifsMisc 28 }
	
	cifsClearTextPasswd	OBJECT-TYPE
	SYNTAX			INTEGER {
			    		no(1),
			                yes(2)
				}
	ACCESS			read-only
	STATUS			mandatory
	DESCRIPTION
				"This indicates whether the cifs clients are 
				 using clear text passwords when authenticating 
				 with the filer. If cifsDomainJoined is false and
				 this variable is also false, then the filer is
				 using NT Security from a local user list."
	::= { cifsMisc 29 }

	-- -- -- -- -- -- -- -- -- -- -- -- -- -- -- -- -- --
	-- -- -- -- -- -- -- -- -- -- -- -- -- -- -- -- -- --
	-- the netcache group --
	-- -- -- -- -- -- -- -- -- -- -- -- -- -- -- -- -- --
	-- -- -- -- -- -- -- -- -- -- -- -- -- -- -- -- -- --

	ncOptions	OBJECT IDENTIFIER ::= { netcache 1 }

	ncInfo		OBJECT IDENTIFIER ::= { netcache 2 }

	ncStats		OBJECT IDENTIFIER ::= { netcache 3 }

	-- -- -- -- -- -- -- -- -- -- -- -- -- -- -- -- -- --
	-- the netcache options group
	-- -- -- -- -- -- -- -- -- -- -- -- -- -- -- -- -- --

	ncIsEnabled	OBJECT-TYPE
	SYNTAX		INTEGER {
					false(1),
					true(2)
				}
	ACCESS		read-only
	STATUS		mandatory
	DESCRIPTION
			"Whether Netcache is enabled on this system."
	::= { ncOptions 1 }

	ncIsLicensed	OBJECT-TYPE
	SYNTAX		INTEGER {
					false(1),
					true(2)
				}
	ACCESS		read-only
	STATUS		mandatory
	DESCRIPTION
			"Whether Netcache is licensed on this system."
	::= { ncOptions 2 }

	-- -- -- -- -- -- -- -- -- -- -- -- -- -- -- -- -- --
	-- the dns options group
	-- -- -- -- -- -- -- -- -- -- -- -- -- -- -- -- -- --

	ncDnsOptions		OBJECT IDENTIFIER ::= { ncOptions 3 }

	ncDnsIsEnabled	OBJECT-TYPE
	SYNTAX		INTEGER {
					false(1),
					true(2)
				}
	ACCESS		read-only
	STATUS		mandatory
	DESCRIPTION
			"Whether the Domain Name System (DNS)
			is enabled on this system."
	::= { ncDnsOptions 1 }

	-- -- -- -- -- -- -- -- -- -- -- -- -- -- -- -- -- --
	-- the http options group
	-- -- -- -- -- -- -- -- -- -- -- -- -- -- -- -- -- --

	ncHttpOptions		OBJECT IDENTIFIER ::= { ncOptions 4 }

	ncHttpIsEnabled	OBJECT-TYPE
	SYNTAX		INTEGER {
					false(1),
					true(2)
				}
	ACCESS		read-only
	STATUS		mandatory
	DESCRIPTION
			"Whether HTTP is enabled on this system."
	::= { ncHttpOptions 1 }

	-- -- -- -- -- -- -- -- -- -- -- -- -- -- -- -- -- --
	-- the nntp options group
	-- -- -- -- -- -- -- -- -- -- -- -- -- -- -- -- -- --

	ncNntpOptions		OBJECT IDENTIFIER ::= { ncOptions 5 }

	ncNntpIsEnabled	OBJECT-TYPE
	SYNTAX		INTEGER {
					false(1),
					true(2)
				}
	ACCESS		read-only
	STATUS		mandatory
	DESCRIPTION
			"Whether NNTP is enabled on this system."
	::= { ncNntpOptions 1 }

	ncNntpIsLicensed	OBJECT-TYPE
	SYNTAX		INTEGER {
					false(1),
					true(2)
				}
	ACCESS		read-only
	STATUS		mandatory
	DESCRIPTION
			"Whether NNTP is licensed on this system."
	::= { ncNntpOptions 2 }

	-- -- -- -- -- -- -- -- -- -- -- -- -- -- -- -- -- --
	-- the streaming options group
	-- -- -- -- -- -- -- -- -- -- -- -- -- -- -- -- -- --

	ncStreamingOptions	OBJECT IDENTIFIER ::= { ncOptions 6 }

	ncStreamingMmsIsEnabled	OBJECT-TYPE
	SYNTAX		INTEGER {
					false(1),
					true(2)
				}
	ACCESS		read-only
	STATUS		mandatory
	DESCRIPTION
			"Whether Microsoft Media Services (MMS)
			is enabled on this system."
	::= { ncStreamingOptions 1 }

	ncStreamingMmsIsLicensed	OBJECT-TYPE
	SYNTAX		INTEGER {
					false(1),
					true(2)
				}
	ACCESS		read-only
	STATUS		mandatory
	DESCRIPTION
			"Whether Microsoft Windows Media Service (MMS)
			is licensed on this system."
	::= { ncStreamingOptions 2 }

	ncStreamingMmsProIsLicensed	OBJECT-TYPE
	SYNTAX		INTEGER {
					false(1),
					true(2)
				}
	ACCESS		read-only
	STATUS		mandatory
	DESCRIPTION
			"Whether Microsoft Windows Media Service Pro (MMS)
			is licensed on this system."
	::= { ncStreamingOptions 3 }

	ncStreamingRtspIsEnabled	OBJECT-TYPE
	SYNTAX		INTEGER {
					false(1),
					true(2)
				}
	ACCESS		read-only
	STATUS		mandatory
	DESCRIPTION
			"Whether the Real Time Streaming Protocol (RTSP)
			is enabled on this system."
	::= { ncStreamingOptions 4 }

	ncStreamingQuickTimeIsLicensed	OBJECT-TYPE
	SYNTAX		INTEGER {
					false(1),
					true(2)
				}
	ACCESS		read-only
	STATUS		mandatory
	DESCRIPTION
			"Whether QuickTime is licensed on this system."
	::= { ncStreamingOptions 5 }

	ncStreamingRealIsLicensed	OBJECT-TYPE
	SYNTAX		INTEGER {
					false(1),
					true(2)
				}
	ACCESS		read-only
	STATUS		mandatory
	DESCRIPTION
			"Whether Real Media streaming is licensed on 
			this system."
	::= { ncStreamingOptions 6 }

	ncStreamingMmsUltraIsLicensed	OBJECT-TYPE
	SYNTAX		INTEGER {
					false(1),
					true(2)
				}
	ACCESS		read-only
	STATUS		mandatory
	DESCRIPTION
			"Whether Microsoft Windows Media Service Ultra (MMS)
			is licensed on this system."
	::= { ncStreamingOptions 7 }

	ncStreamingRealProIsLicensed	OBJECT-TYPE
	SYNTAX		INTEGER {
					false(1),
					true(2)
				}
	ACCESS		read-only
	STATUS		mandatory
	DESCRIPTION
			"Whether Real Media Pro streaming is licensed on 
			this system."
	::= { ncStreamingOptions 8 }

	ncStreamingRealUltraIsLicensed	OBJECT-TYPE
	SYNTAX		INTEGER {
					false(1),
					true(2)
				}
	ACCESS		read-only
	STATUS		mandatory
	DESCRIPTION
			"Whether Real Media Ultra streaming is licensed on 
			this system."
	::= { ncStreamingOptions 9 }

	-- -- -- -- -- -- -- -- -- -- -- -- -- -- -- -- -- --
	-- the icap options group
	-- -- -- -- -- -- -- -- -- -- -- -- -- -- -- -- -- --

	ncIcapOptions		OBJECT IDENTIFIER ::= { ncOptions 7 }

	ncIcapIsEnabled	OBJECT-TYPE
	SYNTAX		INTEGER {
					false(1),
					true(2)
				}
	ACCESS		read-only
	STATUS		mandatory
	DESCRIPTION
			"Whether ICAP v0.95 is enabled on this system."
	::= { ncIcapOptions 1 }

	ncIcapIsLicensed	OBJECT-TYPE
	SYNTAX		INTEGER {
					false(1),
					true(2)
				}
	ACCESS		read-only
	STATUS		mandatory
	DESCRIPTION
			"Whether ICAP is licensed on this system."
	::= { ncIcapOptions 2 }

	ncIcapv1IsEnabled	OBJECT-TYPE
	SYNTAX		INTEGER {
					false(1),
					true(2)
				}
	ACCESS		read-only
	STATUS		mandatory
	DESCRIPTION
			"Whether ICAP v1.0 is enabled on this system."
	::= { ncIcapOptions 3 }

	-- -- -- -- -- -- -- -- -- -- -- -- -- -- -- -- -- --
	-- the grm options group
	-- -- -- -- -- -- -- -- -- -- -- -- -- -- -- -- -- --

	ncGrmOptions		OBJECT IDENTIFIER ::= { ncOptions 8 }
	
	ncGrmServerOptions	OBJECT IDENTIFIER ::= { ncGrmOptions 1 }

	ncGrmAgentOptions	OBJECT IDENTIFIER ::= { ncGrmOptions 2 }

	ncGrmServerIsEnabled	OBJECT-TYPE
	SYNTAX		INTEGER {
					false(1),
					true(2)
				}
	ACCESS		read-only
	STATUS		mandatory
	DESCRIPTION
			"Whether the Global Request Manager (GRM) Server
			is enabled on this system."
	::= { ncGrmServerOptions 1 }

	ncGrmServerIsLicensed	OBJECT-TYPE
	SYNTAX		INTEGER {
					false(1),
					true(2)
				}
	ACCESS		read-only
	STATUS		mandatory
	DESCRIPTION
			"Whether the Global Request Manager (GRM) Server
			is licensed on this system."
	::= { ncGrmServerOptions 2 }

	ncGrmAgentIsEnabled	OBJECT-TYPE
	SYNTAX		INTEGER {
					false(1),
					true(2)
				}
	ACCESS		read-only
	STATUS		mandatory
	DESCRIPTION
			"Whether the Global Request Manager (GRM) Agent
			enabled on this system."
	::= { ncGrmAgentOptions 1 }

	ncGrmAgentIsLicensed	OBJECT-TYPE
	SYNTAX		INTEGER {
					false(1),
					true(2)
				}
	ACCESS		read-only
	STATUS		mandatory
	DESCRIPTION
			"Whether the Global Request Manager (GRM) Agent
			is licensed on this system."
	::= { ncGrmAgentOptions 2 }

	-- -- -- -- -- -- -- -- -- -- -- -- -- -- -- -- -- --
	-- the content director options group
	-- -- -- -- -- -- -- -- -- -- -- -- -- -- -- -- -- --

	ncCdOptions	OBJECT IDENTIFIER ::= { ncOptions 9 }

	ncCdIsEnabled	OBJECT-TYPE
	SYNTAX		INTEGER {
					false(1),
					true(2)
				}
	ACCESS		read-only
	STATUS		mandatory
	DESCRIPTION
			"Whether Content Director is enabled on this system."
	::= { ncCdOptions 1 }

	-- -- -- -- -- -- -- -- -- -- -- -- -- -- -- -- -- --
	-- the https options group
	-- -- -- -- -- -- -- -- -- -- -- -- -- -- -- -- -- --

	ncHttpsProxyOptions		OBJECT IDENTIFIER ::= { ncOptions 10 }

	ncHttpsProxyIsEnabled	OBJECT-TYPE
	SYNTAX		INTEGER {
					false(1),
					true(2)
				}
	ACCESS		read-only
	STATUS		mandatory
	DESCRIPTION
			"Whether HTTPS is enabled on this system."
	::= { ncHttpsProxyOptions 1 }

	ncHttpsProxyIsLicensed	OBJECT-TYPE
	SYNTAX		INTEGER {
					false(1),
					true(2)
				}
	ACCESS		read-only
	STATUS		mandatory
	DESCRIPTION
			"Whether HTTPS is licensed on this system."
	::= { ncHttpsProxyOptions 2 }

	-- -- -- -- -- -- -- -- -- -- -- -- -- -- -- -- -- --
	-- the cms options group
	-- -- -- -- -- -- -- -- -- -- -- -- -- -- -- -- -- --
	ncCmsOptions		OBJECT IDENTIFIER ::= { ncOptions 11 }

	ncCmsIsEnabled	OBJECT-TYPE
	SYNTAX		INTEGER {
					false(1),
					true(2)
				}
	ACCESS		read-only
	STATUS		mandatory
	DESCRIPTION
			"Whether CMS is enabled on this system."
	::= { ncCmsOptions 1 }

	-- -- -- -- -- -- -- -- -- -- -- -- -- -- -- -- -- --
	-- the netcache info group
	-- -- -- -- -- -- -- -- -- -- -- -- -- -- -- -- -- --

 	ncVersion		OBJECT-TYPE
	SYNTAX			DisplayString
	ACCESS			read-only
	STATUS			mandatory
	DESCRIPTION
			"The Netcache version string."
	::= { ncInfo 1 }

 	ncAdminPort		OBJECT-TYPE
	SYNTAX			INTEGER
	ACCESS			read-only
	STATUS			mandatory
	DESCRIPTION
			"Netcache Admin Port number - this
			 is the first in the list of admin
			 ports configured for the NetCache."
	::= { ncInfo 2 }


	accelmonitor	OBJECT IDENTIFIER ::= { ncInfo 3 }

	-- the acceleration monitor group
	-- Implementation of the Acceleration Monitor (accelmonitor.

	amNumber OBJECT-TYPE
	    SYNTAX  INTEGER
	    ACCESS  read-only
	    STATUS  mandatory
	    DESCRIPTION
		"The number of entries in the acceleration monitor table."
	    ::= { accelmonitor 1 }

	amMonitor OBJECT-TYPE
	    SYNTAX  INTEGER {
			togglea(1),
			toggleb(2)
	    }
	    ACCESS  read-only
	    STATUS  mandatory
	    DESCRIPTION
		"Variable for user defined SNMP traps to monitor whether			there has been a status change of any of the acceleration 
		servers that netcache is probing."
	    ::= { accelmonitor 2 }

	amMonitorString OBJECT-TYPE
	    SYNTAX  DisplayString
	    ACCESS  read-only
	    STATUS  mandatory
	    DESCRIPTION
		"Used in conjunction with amMonitor. This returns a string
		in format of: 'IP:port status' which reports the status
		of all the servers netcache is accelerating as of last
		status change."
	    ::= { accelmonitor 3 }

	-- accelmonitor table

	-- the Acceleration Monitor table contains information of the
	-- the acceleration server, port that we are monitoring and its
	-- status.

	amTable OBJECT-TYPE
	    SYNTAX  SEQUENCE OF AmEntry
	    ACCESS  not-accessible
	    STATUS  mandatory
	    DESCRIPTION
		     "A list of acceleration server and port entries. The
		     number of entries is given by the value of amNumber."
	    ::= { accelmonitor 4 }

	amEntry OBJECT-TYPE
	    SYNTAX  AmEntry
	    ACCESS  not-accessible
	    STATUS  mandatory
	    DESCRIPTION
		    "An acceleration monitor entry contains: the server
		    IP address, server port and the status."
	    INDEX   { amIndex }
	    ::= { amTable 1 }

	AmEntry ::=
	    SEQUENCE {
		amIndex
		    INTEGER,
		amAddress
		    IpAddress,
		amPort
		    INTEGER (0..65535),
		amStatus
		    INTEGER
	    }

	amIndex OBJECT-TYPE
	    SYNTAX  INTEGER (1..2147483647)
	    ACCESS  read-only
	    STATUS  mandatory
	    DESCRIPTION
		    " A unique value for each entry in the acceleration monitor
		    table."
	    ::= { amEntry 1 }

	amAddress OBJECT-TYPE
	    SYNTAX  IpAddress
	    ACCESS  read-only
	    STATUS  mandatory
	    DESCRIPTION
		    "The IP address of the acceleration server the NetCache
		    is monitoring."
	    ::= { amEntry 2 }

	amPort OBJECT-TYPE
	    SYNTAX  INTEGER (0..65535)
	    ACCESS  read-only
	    STATUS  mandatory
	    DESCRIPTION
		   "The corresponding port on the server that NetCache is
		   monitoring."
	    ::= { amEntry 3 }

	amStatus OBJECT-TYPE
	    SYNTAX  INTEGER {
			active(1),
			up(2),
			down(3),
			inactive(4)
		    }
	    ACCESS  read-only
	    STATUS  mandatory
	    DESCRIPTION
		    "The status of the service running on the server.
		    active -  in queue but no probes done yet.
		    up - the server is reachable and responding to probes.
		    down - the server is unreachable.
		    inactive - monitoring is disabled."
	    ::= { amEntry 4 }
	
 	ncLocalConfigChanged	OBJECT-TYPE
	SYNTAX		INTEGER {
					false(1),
					true(2)
				}
	ACCESS				read-only
	STATUS				mandatory
	DESCRIPTION
			"Whether the local configuration file on NetCache
			was changed without using DFM configuration management."
	::= { ncInfo 4 }

 	ncLocalConfigVersion	OBJECT-TYPE
	SYNTAX			INTEGER
	ACCESS			read-only
	STATUS			mandatory
	DESCRIPTION
			"The current cache configuration's version."
	::= { ncInfo 5 }

	grmmonitor	OBJECT IDENTIFIER ::= { ncInfo 6 }

	-- the GRM monitor group
	-- Implementation of the GRM agent monitor

	grmMonitor OBJECT-TYPE
	    SYNTAX  INTEGER {
			togglea(1),
			toggleb(2)
	    }
	    ACCESS  read-only
	    STATUS  mandatory
	    DESCRIPTION
		"Variable for user defined SNMP traps to monitor whether			there has been a status change of any of the GRM 
		agents reporting to this GRM server."
	    ::= { grmmonitor 1 }

	grmMonitorString OBJECT-TYPE
	    SYNTAX  DisplayString
	    ACCESS  read-only
	    STATUS  mandatory
	    DESCRIPTION
		"Used in conjunction with grmMonitor. This returns a string
		in format of: 'IP status.' which reports the status
		of all the GRM agents reporting to this GRM server as of last
		status change."
	    ::= { grmmonitor 2 }

	takeoverinfo	OBJECT IDENTIFIER ::= { ncInfo 7 }

	-- the takeover information group
	-- information same as status.takeover.addrs and 
	-- status.takeover.mode and status.takeover.partner_status

	takeoverAddrs OBJECT-TYPE
	    SYNTAX  DisplayString 
	    ACCESS  read-only
	    STATUS  mandatory
	    DESCRIPTION
		"Indicates the list of interfaces and their corresponding IP
		 addresses of the partner NetCache that this appliance has taken 		 over." 
	    ::= { takeoverinfo 1 }

	takeoverMode OBJECT-TYPE
	    SYNTAX  INTEGER {
			normal(1),
			takingover(2),
			takenover(3),
			giveback(4)
	    } 
	    ACCESS  read-only
	    STATUS  mandatory
	    DESCRIPTION
		"Indicates the current takeover mode of this appliance."
	    ::= { takeoverinfo 2 }

	takeoverStatus OBJECT-TYPE
	    SYNTAX  INTEGER {
			up(1),
			unknown(2),
			failed(3)
	    } 
	    ACCESS  read-only
	    STATUS  mandatory
	    DESCRIPTION
		"Indicates the current status of the takeover partner of 
		 this appliance. up(1) indicates that the takeover partner is 
		 reachable. unknown(2) indicates that an unknown error occured.
		 failed(3) indicates that the partner has failed, takeoverAddrs
		 indicates the partner's IP address this appliance has taken
		 over."
	    ::= { takeoverinfo 3 }


	-- -- -- -- -- -- -- -- -- -- -- -- -- -- -- -- -- --
	-- the netcache stats group --
	-- -- -- -- -- -- -- -- -- -- -- -- -- -- -- -- -- --

 	ncObjectsStored		OBJECT-TYPE
	SYNTAX			INTEGER
	ACCESS			read-only
	STATUS			mandatory
	DESCRIPTION
			"The total number of objects stored currently."
	::= { ncStats 1 }

	ncBytesToClients  OBJECT-TYPE
	SYNTAX			Counter
	ACCESS			read-only
	STATUS			mandatory
	DESCRIPTION
			"Total bytes sent to clients"
	::= { ncStats 2 }

	ncBytesFromClients  OBJECT-TYPE
	SYNTAX			Counter
	ACCESS			read-only
	STATUS			mandatory
	DESCRIPTION
			"Total bytes received from clients"
	::= { ncStats 3 }

	ncBytesToServers  OBJECT-TYPE
	SYNTAX			Counter
	ACCESS			read-only
	STATUS			mandatory
	DESCRIPTION
			"Total bytes sent to servers"
	::= { ncStats 4 }

	ncBytesFromServers  OBJECT-TYPE
	SYNTAX			Counter
	ACCESS			read-only
	STATUS			mandatory
	DESCRIPTION
			"Total bytes received from servers"
	::= { ncStats 5 }    

	ncHttp		OBJECT IDENTIFIER ::= { ncStats 6 }

	-- -- -- -- -- -- -- -- -- -- -- -- -- -- -- -- -- --
	-- the http stats group
	-- -- -- -- -- -- -- -- -- -- -- -- -- -- -- -- -- --

 	ncHttpTotalRequests	OBJECT-TYPE
	SYNTAX			Counter
	ACCESS			read-only
	STATUS			mandatory
	DESCRIPTION
			"Total HTTP requests so far"
	::= { ncHttp 1 }

 	ncHttpHitRequests	OBJECT-TYPE
	SYNTAX			Counter
	ACCESS			read-only
	STATUS			mandatory
	DESCRIPTION
			"HTTP requests that resulted in hits so far"
	::= { ncHttp 2 }

 	ncHttpMissRequests	OBJECT-TYPE
	SYNTAX			Counter
	ACCESS			read-only
	STATUS			mandatory
	DESCRIPTION
			"HTTP requests that resulted in misses so far"
	::= { ncHttp 3 }

 	ncHttpServConns		OBJECT-TYPE
	SYNTAX			INTEGER
	ACCESS			read-only
	STATUS			mandatory
	DESCRIPTION
			"Number of currently open TCP/IP connections to HTTP servers (active and idle)"
	::= { ncHttp 4 }

 	ncHttpCliConns		OBJECT-TYPE
	SYNTAX			INTEGER
	ACCESS			read-only
	STATUS			mandatory
	DESCRIPTION
			"Number of currently open TCP/IP connections to HTTP clients (active and idle)"
	::= { ncHttp 5 }

 	ncHttpBWSavings		OBJECT-TYPE
	SYNTAX			INTEGER
	ACCESS			read-only
	STATUS			mandatory
	DESCRIPTION
			"Bandwidth savings for HTTP requests"
	::= { ncHttp 6 }

 	ncHttpObjHitrate	OBJECT-TYPE
	SYNTAX			INTEGER
	ACCESS			read-only
	STATUS			mandatory
	DESCRIPTION
			"Object Hitrate HTTP requests" 
	::= { ncHttp 7 }

 	ncHttpRespTimePerByte	OBJECT-TYPE
	SYNTAX			INTEGER
	ACCESS			read-only
	STATUS			mandatory
	DESCRIPTION
			"Response time in milliseconds per byte for HTTP requests."
	::= { ncHttp 8 }

 	ncHttpAvgRespTime	OBJECT-TYPE
	SYNTAX			INTEGER
	ACCESS			read-only
	STATUS			mandatory
	DESCRIPTION
			"Average response time in milliseconds for all HTTP requests."
	::= { ncHttp 9 }

 	ncHttpAvgHitRespTime	OBJECT-TYPE
	SYNTAX			INTEGER
	ACCESS			read-only
	STATUS			mandatory
	DESCRIPTION
			"Average response time in milliseconds for HTTP hit requests."
	::= { ncHttp 10 }

 	ncHttpAvgMissRespTime	OBJECT-TYPE
	SYNTAX			INTEGER
	ACCESS			read-only
	STATUS			mandatory
	DESCRIPTION
			"Average response time in milliseconds for HTTP miss requests."
	::= { ncHttp 11 }

 	ncHttpInstAvgRespTime	OBJECT-TYPE
	SYNTAX			INTEGER
	ACCESS			read-only
	STATUS			mandatory
	DESCRIPTION
			"Average response time in milliseconds for all HTTP requests during the last 60 seconds."
	::= { ncHttp 12 }


 	ncHttpInstAvgHitRespTime	OBJECT-TYPE
	SYNTAX			INTEGER
	ACCESS			read-only
	STATUS			mandatory
	DESCRIPTION
			"Average response time in milliseconds for HTTP hit requests during the last 60 seconds."
	::= { ncHttp 13 }

 	ncHttpInstAvgMissRespTime	OBJECT-TYPE
	SYNTAX			INTEGER
	ACCESS			read-only
	STATUS			mandatory
	DESCRIPTION
			"Average response time in milliseconds for HTTP miss requests during the last 60 seconds."
	::= { ncHttp 14 }

	ncHttpTotalRespTime  	OBJECT-TYPE
	SYNTAX			INTEGER
	ACCESS			read-only
	STATUS			mandatory
	DESCRIPTION
			"Total fetch time in milliseconds for HTTP requests"
	::= { ncHttp 15 }

	ncHttpTotalHitRespTime  OBJECT-TYPE
	SYNTAX			INTEGER
	ACCESS			read-only
	STATUS			mandatory
	DESCRIPTION
			"Total fetch time in milliseconds for HTTP HIT requests"
	::= { ncHttp 16 }

	ncHttpTotalMissRespTime  OBJECT-TYPE
	SYNTAX			INTEGER
	ACCESS			read-only
	STATUS			mandatory
	DESCRIPTION
			"Total fetch time in milliseconds for HTTP MISS requests"
	::= { ncHttp 17 }

	ncHttpBytesToClients  OBJECT-TYPE
	SYNTAX			Counter
	ACCESS			read-only
	STATUS			mandatory
	DESCRIPTION
			"Total HTTP bytes sent to clients"
	::= { ncHttp 18 }

	ncHttpBytesFromClients  OBJECT-TYPE
	SYNTAX			Counter
	ACCESS			read-only
	STATUS			mandatory
	DESCRIPTION
			"Total HTTP bytes received from clients"
	::= { ncHttp 19 }

	ncHttpBytesToServers  OBJECT-TYPE
	SYNTAX			Counter
	ACCESS			read-only
	STATUS			mandatory
	DESCRIPTION
			"Total HTTP bytes sent to servers"
	::= { ncHttp 20 }

	ncHttpBytesFromServers  OBJECT-TYPE
	SYNTAX			Counter
	ACCESS			read-only
	STATUS			mandatory
	DESCRIPTION
			"Total HTTP bytes received from servers"
	::= { ncHttp 21 }

	ncHttpHighTotalRespTimes  	OBJECT-TYPE
	SYNTAX			Counter
	ACCESS			read-only
	STATUS			mandatory
	DESCRIPTION
			"Total fetch time in milliseconds for HTTP requests.
			This object returns the most significant 32 bits 
			of the 64 bit unsigned integer."
	::= { ncHttp 22 }

	ncHttpLowTotalRespTimes  	OBJECT-TYPE
	SYNTAX			Counter
	ACCESS			read-only
	STATUS			mandatory
	DESCRIPTION
			"Total fetch time in milliseconds for HTTP requests.
			This object returns the least significant 32 bits 
			of the 64 bit unsigned integer."
	::= { ncHttp 23 }

	ncHttpHighTotalHitRespTimes  OBJECT-TYPE
	SYNTAX			Counter
	ACCESS			read-only
	STATUS			mandatory
	DESCRIPTION
			"Total fetch time in milliseconds for HTTP HIT requests.
			This object returns the most significant 32 bits 
			of the 64 bit unsigned integer."
	::= { ncHttp 24 }

	ncHttpLowTotalHitRespTimes  OBJECT-TYPE
	SYNTAX			Counter
	ACCESS			read-only
	STATUS			mandatory
	DESCRIPTION
			"Total fetch time in milliseconds for HTTP HIT requests.
			This object returns the least significant 32 bits 
			of the 64 bit unsigned integer."
	::= { ncHttp 25 }

	ncHttpHighTotalMissRespTimes  OBJECT-TYPE
	SYNTAX			Counter
	ACCESS			read-only
	STATUS			mandatory
	DESCRIPTION
			"Total fetch time in milliseconds for HTTP MISS requests.
			This object returns the most significant 32 bits 
			of the 64 bit unsigned integer."
	::= { ncHttp 26 }

	ncHttpLowTotalMissRespTimes  OBJECT-TYPE
	SYNTAX			Counter
	ACCESS			read-only
	STATUS			mandatory
	DESCRIPTION
			"Total fetch time in milliseconds for HTTP MISS requests.
			This object returns the least significant 32 bits 
			of the 64 bit unsigned integer."
	::= { ncHttp 27 }

 	ncHttpReqRate	        OBJECT-TYPE
	SYNTAX			INTEGER
	ACCESS			read-only
	STATUS			mandatory
	DESCRIPTION
			"Request Rate for HTTP requests"
	::= { ncHttp 28 }
    
 	ncHttpObjHitRateLast1Min	OBJECT-TYPE
	SYNTAX			INTEGER
	ACCESS			read-only
	STATUS			mandatory
	DESCRIPTION
			"HTTP object hit rate in the last 1 minute."
	::= { ncHttp 29 }

 	ncHttpObjHitRateLast5Min	OBJECT-TYPE
	SYNTAX			INTEGER
	ACCESS			read-only
	STATUS			mandatory
	DESCRIPTION
			"HTTP object hit rate in the last 5 minutes."
	::= { ncHttp 30 }

 	ncHttpByteHitRateLast1Min	OBJECT-TYPE
	SYNTAX			INTEGER
	ACCESS			read-only
	STATUS			mandatory
	DESCRIPTION
			"HTTP byte hit rate in the last 1 minute."
	::= { ncHttp 31 }

 	ncHttpByteHitRateLast5Min	OBJECT-TYPE
	SYNTAX			INTEGER
	ACCESS			read-only
	STATUS			mandatory
	DESCRIPTION
			"HTTP byte hit rate in the last 5 minutes."
	::= { ncHttp 32 }

 	ncHttpBWSavingsLast1Min		OBJECT-TYPE
	SYNTAX			INTEGER
	ACCESS			read-only
	STATUS			mandatory
	DESCRIPTION
			"Bandwidth savings for HTTP requests in the last
			 1 minute"
	::= { ncHttp 33 }

	ncHttpBWSavingsLast5Min	OBJECT-TYPE
	SYNTAX			INTEGER
	ACCESS			read-only
	STATUS			mandatory
	DESCRIPTION
			"Bandwidth savings for HTTP requests in the last
			 5 minutes"
	::= { ncHttp 34 }

 	ncHttpActiveServConns	OBJECT-TYPE
	SYNTAX			INTEGER
	ACCESS			read-only
	STATUS			mandatory
	DESCRIPTION
			"Number of currently active TCP/IP connections to HTTP servers"
	::= { ncHttp 35 }

 	ncHttpActiveCliConns	OBJECT-TYPE
	SYNTAX			INTEGER
	ACCESS			read-only
	STATUS			mandatory
	DESCRIPTION
			"Number of currently active TCP/IP connections to HTTP clients"
	::= { ncHttp 36 }

	ncHttpAccelTable	OBJECT-TYPE
	SYNTAX			SEQUENCE OF NcHttpAccelEntry
	ACCESS 			not-accessible
	STATUS 			mandatory
	DESCRIPTION
		 	"Number of kilobytes sent to and recieved from the client side
			per acceleration rule"

 	::= { ncHttp 37 }

	ncHttpAccelEntry 	OBJECT-TYPE
	SYNTAX 			NcHttpAccelEntry
 	ACCESS			not-accessible
 	STATUS 			mandatory
 	DESCRIPTION
 			"Each entry contains the number of kilobytes sent and
 			received to/from the clients side per acceleration 
			rule"

	INDEX	 { ncHttpAccelIndex }
 	::= { ncHttpAccelTable 1 }

	NcHttpAccelEntry ::=
 	SEQUENCE {
 		ncHttpAccelIndex		INTEGER,
 		ncHttpAccelKbytesFromClient 	Counter,
 		ncHttpAccelKbytesToClient	Counter,
		ncHttpAccelHits			Counter
 		}

 	ncHttpAccelIndex	OBJECT-TYPE
 	SYNTAX			INTEGER (1..513)
 	ACCESS			read-only
 	STATUS			mandatory
 	DESCRIPTION
 			"A unique value for each entry in the http acceleration
			 stats table"
 	::= { ncHttpAccelEntry 1 }

	ncHttpAccelKbytesFromClient OBJECT-TYPE
 	SYNTAX			Counter
 	ACCESS 			read-only
 	STATUS			mandatory
 	DESCRIPTION
 			"The total number of kilobytes received from the client
 			for this acceleration rule"
 	::= { ncHttpAccelEntry 2 }

 	ncHttpAccelKbytesToClient OBJECT-TYPE
 	SYNTAX 			Counter
 	ACCESS			read-only
 	STATUS			mandatory
 	DESCRIPTION
			"The total number of kilobytes sent to the client for
 			this acceleration rule"
	::= { ncHttpAccelEntry 3 }

	ncHttpAccelHits		OBJECT-TYPE
	SYNTAX			Counter
	ACCESS			read-only
	STATUS			mandatory
	DESCRIPTION		
			" The number of times this acceleration rule has been hit"
	::= { ncHttpAccelEntry 4 }

	ncHttpsAccelTable	OBJECT-TYPE
	SYNTAX			SEQUENCE OF NcHttpsAccelEntry
 	ACCESS 			not-accessible
 	STATUS			mandatory
 	DESCRIPTION	
			"Number of kilobytes sent to and recieved from the client side
 			per acceleration rule"

	::= { ncHttp 38 }

	ncHttpsAccelEntry	OBJECT-TYPE
	SYNTAX			NcHttpsAccelEntry
	ACCESS			not-accessible
	STATUS			mandatory
	DESCRIPTION
			"Each entry contains the number of kilobytes sent and
			 received to/from the clients side per acceleration
				rule"

	INDEX	 { ncHttpsAccelIndex }
 	::= { ncHttpsAccelTable 1 }

	NcHttpsAccelEntry ::=
	SEQUENCE {
		ncHttpsAccelIndex		INTEGER,
		ncHttpsAccelKbytesFromClient	Counter,
 		ncHttpsAccelKbytesToClient	Counter,
		ncHttpsAccelHits	Counter
		}

	ncHttpsAccelIndex	OBJECT-TYPE
	SYNTAX			INTEGER (1..513)
 	ACCESS			read-only
 	STATUS			mandatory
 	DESCRIPTION
 			"A unique value for each entry in the http acceleration
			 stats table"
	::= { ncHttpsAccelEntry 1 }

 	ncHttpsAccelKbytesFromClient OBJECT-TYPE
	SYNTAX			Counter
	ACCESS			read-only
	STATUS 			mandatory
 	DESCRIPTION
			"The total number of kilobytes received from the client
			 for this acceleration rule"
	::= { ncHttpsAccelEntry 2 }

	ncHttpsAccelKbytesToClient OBJECT-TYPE
 	SYNTAX			Counter
	ACCESS			read-only
 	STATUS			mandatory
	DESCRIPTION
 			"The total number of kilobytes sent to the client for
			 this acceleration rule"
	::= { ncHttpsAccelEntry 3 }

 	ncHttpsAccelHits	OBJECT-TYPE
 	SYNTAX			Counter
 	ACCESS			read-only
 	STATUS			mandatory
 	DESCRIPTION
 			" The number of times this acceleration rule has been hit"
	::= { ncHttpsAccelEntry 4 }


	ncNntp		OBJECT IDENTIFIER ::= { ncStats 7 }

	-- -- -- -- -- -- -- -- -- -- -- -- -- -- -- -- -- --
	-- the nntp stats group
	-- -- -- -- -- -- -- -- -- -- -- -- -- -- -- -- -- --

 	ncNntpTotalRequests	OBJECT-TYPE
	SYNTAX			Counter
	ACCESS			read-only
	STATUS			mandatory
	DESCRIPTION
			"NNTP total requests so far"
	::= { ncNntp 1 }
 	ncNntpCacheableRequests	OBJECT-TYPE
	SYNTAX			Counter
	ACCESS			read-only
	STATUS			mandatory
	DESCRIPTION
			"NNTP requests that were cacheable"
	::= { ncNntp 2 }

 	ncNntpProxyRequests	OBJECT-TYPE
	SYNTAX			Counter
	ACCESS			read-only
	STATUS			mandatory
	DESCRIPTION
			"NNTP requests that were non-cacheable"
	::= { ncNntp 3 }

 	ncNntpServConns		OBJECT-TYPE
	SYNTAX			INTEGER
	ACCESS			read-only
	STATUS			mandatory
	DESCRIPTION
			"Number of currently open TCP/IP connections to NNTP servers (active and idle)"
	::= { ncNntp 4 }

 	ncNntpCliConns		OBJECT-TYPE
	SYNTAX			INTEGER
	ACCESS			read-only
	STATUS			mandatory
	DESCRIPTION
			"Number of currently open TCP/IP connections to NNTP clients (active and idle)"
	::= { ncNntp 5 }

 	ncNntpBWSavings		OBJECT-TYPE
	SYNTAX			INTEGER
	ACCESS			read-only
	STATUS			mandatory
	DESCRIPTION
			"Bandwidth savings for NNTP requests"
	::= { ncNntp 6 }

 	ncNntpRespTimePerByte	OBJECT-TYPE
	SYNTAX			INTEGER
	ACCESS			read-only
	STATUS			mandatory
	DESCRIPTION
			"Response time per byte for NNTP requests"
	::= { ncNntp 7 }

	ncNntpBytesToClients  OBJECT-TYPE
	SYNTAX			Counter
	ACCESS			read-only
	STATUS			mandatory
	DESCRIPTION
				"Total NNTP bytes sent to clients"
	::= { ncNntp 8 }

	ncNntpBytesFromClients  OBJECT-TYPE
	SYNTAX			Counter
	ACCESS			read-only
	STATUS			mandatory
	DESCRIPTION
				"Total NNTP bytes received from clients"
	::= { ncNntp 9 }

	ncNntpBytesToServers  OBJECT-TYPE
	SYNTAX			Counter
	ACCESS			read-only
	STATUS			mandatory
	DESCRIPTION
				"Total NNTP bytes sent to servers"
	::= { ncNntp 10 }

	ncNntpBytesFromServers  OBJECT-TYPE
	SYNTAX			Counter
	ACCESS			read-only
	STATUS			mandatory
	DESCRIPTION
				"Total NNTP bytes received from servers"
	::= { ncNntp 11 }

 	ncNntpObjHitrate	OBJECT-TYPE
	SYNTAX			INTEGER
	ACCESS			read-only
	STATUS			mandatory
	DESCRIPTION
			"Object Hitrate of NNTP requests" 
	::= { ncNntp 12 }

 	ncNntpActiveServConns	OBJECT-TYPE
	SYNTAX			INTEGER
	ACCESS			read-only
	STATUS			mandatory
	DESCRIPTION
			"Number of currently active TCP/IP connections to NNTP servers"
	::= { ncNntp 13 }

 	ncNntpActiveCliConns	OBJECT-TYPE
	SYNTAX			INTEGER
	ACCESS			read-only
	STATUS			mandatory
	DESCRIPTION
			"Number of currently active TCP/IP connections to NNTP clients"
	::= { ncNntp 14 }

	ncFtp		OBJECT IDENTIFIER ::= { ncStats 8 }

	-- -- -- -- -- -- -- -- -- -- -- -- -- -- -- -- -- --
	-- the ftp stats group
	-- -- -- -- -- -- -- -- -- -- -- -- -- -- -- -- -- --

 	ncFtpTotalRequests	OBJECT-TYPE
	SYNTAX			Counter
	ACCESS			read-only
	STATUS			mandatory
	DESCRIPTION
			"FTP total requests so far"
	::= { ncFtp 1 }

 	ncFtpHitRequests	OBJECT-TYPE
	SYNTAX			Counter
	ACCESS			read-only
	STATUS			mandatory
	DESCRIPTION
			"FTP requests that resulted in hits so far"
	::= { ncFtp 2 }

 	ncFtpMissRequests	OBJECT-TYPE
	SYNTAX			Counter
	ACCESS			read-only
	STATUS			mandatory
	DESCRIPTION
			"FTP requests that resulted in misses so far"
	::= { ncFtp 3 }

 	ncFtpServConns		OBJECT-TYPE
	SYNTAX			INTEGER
	ACCESS			read-only
	STATUS			mandatory
	DESCRIPTION
			"Number of currently open TCP/IP connections to FTP servers (active and idle)"
	::= { ncFtp 4 }

 	ncFtpCliConns		OBJECT-TYPE
	SYNTAX			INTEGER
	ACCESS			read-only
	STATUS			mandatory
	DESCRIPTION
			"Number of currently open TCP/IP connections to FTP clients (active and idle)"
	::= { ncFtp 5 }

 	ncFtpBWSavings		OBJECT-TYPE
	SYNTAX			INTEGER
	ACCESS			read-only
	STATUS			mandatory
	DESCRIPTION
			"Bandwidth savings for FTP requests"
	::= { ncFtp 6 }

 	ncFtpRespTimePerByte	OBJECT-TYPE
	SYNTAX			INTEGER
	ACCESS			read-only
	STATUS			mandatory
	DESCRIPTION
			"Response time per byte for FTP requests"
	::= { ncFtp 7 }

	ncFtpBytesToClients  OBJECT-TYPE
	SYNTAX			Counter
	ACCESS			read-only
	STATUS			mandatory
	DESCRIPTION
				"Total FTP bytes sent to clients"
	::= { ncFtp 8 }

	ncFtpBytesFromClients  OBJECT-TYPE
	SYNTAX			Counter
	ACCESS			read-only
	STATUS			mandatory
	DESCRIPTION
				"Total FTP bytes received from clients"
	::= { ncFtp 9 }

	ncFtpBytesToServers  OBJECT-TYPE
	SYNTAX			Counter
	ACCESS			read-only
	STATUS			mandatory
	DESCRIPTION
				"Total FTP bytes sent to servers"
	::= { ncFtp 10 }

	ncFtpBytesFromServers  OBJECT-TYPE
	SYNTAX			Counter
	ACCESS			read-only
	STATUS			mandatory
	DESCRIPTION
				"Total FTP bytes received from servers"
	::= { ncFtp 11 }

 	ncFtpObjHitrate	OBJECT-TYPE
	SYNTAX			INTEGER
	ACCESS			read-only
	STATUS			mandatory
	DESCRIPTION
			"Object Hitrate of FTP requests" 
	::= { ncFtp 12 }

 	ncFtpActiveServConns	OBJECT-TYPE
	SYNTAX			INTEGER
	ACCESS			read-only
	STATUS			mandatory
	DESCRIPTION
			"Number of currently active TCP/IP connections to FTP servers"
	::= { ncFtp 13 }

 	ncFtpActiveCliConns	OBJECT-TYPE
	SYNTAX			INTEGER
	ACCESS			read-only
	STATUS			mandatory
	DESCRIPTION
			"Number of currently active TCP/IP connections to FTP clients"
	::= { ncFtp 14 }

	ncStreaming	OBJECT IDENTIFIER ::= { ncStats 9 }

	-- -- -- -- -- -- -- -- -- -- -- -- -- -- -- -- -- --
	-- the streaming stats group
	-- -- -- -- -- -- -- -- -- -- -- -- -- -- -- -- -- --

 	ncStreamingServConns	OBJECT-TYPE
	SYNTAX			INTEGER
	ACCESS			read-only
	STATUS			mandatory
	DESCRIPTION
			"Number of currently open TCP/IP connections to streaming servers (active and idle)"
	::= { ncStreaming 1 }

 	ncStreamingCliConns	OBJECT-TYPE
	SYNTAX			INTEGER
	ACCESS			read-only
	STATUS			mandatory
	DESCRIPTION
			"Number of currently open TCP/IP connections to streaming clients (active and idle)"
	::= { ncStreaming 2 }

 	ncStreamingBWSavings	OBJECT-TYPE
	SYNTAX			INTEGER
	ACCESS			read-only
	STATUS			mandatory
	DESCRIPTION
			"Bandwidth savings for all streaming requests"
	::= { ncStreaming 3 }

 	ncStreamingRespTimePerByte	OBJECT-TYPE
	SYNTAX				INTEGER
	ACCESS				read-only
	STATUS				mandatory
	DESCRIPTION
			"Response time per byte for all streaming requests"
	::= { ncStreaming 4 }

 	ncStreamingHitRequests	OBJECT-TYPE
	SYNTAX			Counter
	ACCESS			read-only
	STATUS			mandatory
	DESCRIPTION
			"STREAMING requests that resulted in hits so far"
	::= { ncStreaming 5 }

 	ncStreamingMissRequests	OBJECT-TYPE
	SYNTAX			Counter
	ACCESS			read-only
	STATUS			mandatory
	DESCRIPTION
			"STREAMING requests that resulted in misses so far"
	::= { ncStreaming 6 }

 	ncStreamingTotalRequests	OBJECT-TYPE
	SYNTAX			Counter
	ACCESS			read-only
	STATUS			mandatory
	DESCRIPTION
			"STREAMING total requests so far"
	::= { ncStreaming 7 }

	ncStreamingLiveBytesToClients  OBJECT-TYPE
	SYNTAX			Counter
	ACCESS			read-only
	STATUS			mandatory
	DESCRIPTION
			"Total Streaming Live bytes sent to clients"
	::= { ncStreaming 8 }

	ncStreamingLiveBytesFromClients  OBJECT-TYPE
	SYNTAX			Counter
	ACCESS			read-only
	STATUS			mandatory
	DESCRIPTION
			"Total Streaming Live bytes received from clients"
	::= { ncStreaming 9 }

	ncStreamingLiveBytesToServers  OBJECT-TYPE
	SYNTAX			Counter
	ACCESS			read-only
	STATUS			mandatory
	DESCRIPTION
			"Total Streaming Live bytes sent to servers"
	::= { ncStreaming 10 }

	ncStreamingLiveBytesFromServers  OBJECT-TYPE
	SYNTAX			Counter
	ACCESS			read-only
	STATUS			mandatory
	DESCRIPTION
			"Total Streaming Live bytes received from servers"
	::= { ncStreaming 11 }

	ncStreamingProxyBytesToClients  OBJECT-TYPE
	SYNTAX			Counter
	ACCESS			read-only
	STATUS			mandatory
	DESCRIPTION
			"Total Streaming Proxy bytes sent to clients"
	::= { ncStreaming 12 }

	ncStreamingProxyBytesFromClients  OBJECT-TYPE
	SYNTAX			Counter
	ACCESS			read-only
	STATUS			mandatory
	DESCRIPTION
			"Total Streaming Proxy bytes received from clients"
	::= { ncStreaming 13 }

	ncStreamingProxyBytesToServers  OBJECT-TYPE
	SYNTAX			Counter
	ACCESS			read-only
	STATUS			mandatory
	DESCRIPTION
			"Total Streaming Proxy bytes sent to servers"
	::= { ncStreaming 14 }

	ncStreamingProxyBytesFromServers  OBJECT-TYPE
	SYNTAX			Counter
	ACCESS			read-only
	STATUS			mandatory
	DESCRIPTION
			"Total Streaming Proxy bytes received from servers"
	::= { ncStreaming 15 }

	ncStreamingOndemandBytesToClients  OBJECT-TYPE
	SYNTAX			Counter
	ACCESS			read-only
	STATUS			mandatory
	DESCRIPTION
			"Total Streaming Ondemand bytes sent to clients"
	::= { ncStreaming 16 }

	ncStreamingOndemandBytesFromClients  OBJECT-TYPE
	SYNTAX			Counter
	ACCESS			read-only
	STATUS			mandatory
	DESCRIPTION
			"Total Streaming Ondemand bytes received from clients"
	::= { ncStreaming 17 }

	ncStreamingOndemandBytesToServers  OBJECT-TYPE
	SYNTAX			Counter
	ACCESS			read-only
	STATUS			mandatory
	DESCRIPTION
			"Total Streaming Ondemand bytes sent to servers"
	::= { ncStreaming 18 }

	ncStreamingOndemandBytesFromServers  OBJECT-TYPE
	SYNTAX			Counter
	ACCESS			read-only
	STATUS			mandatory
	DESCRIPTION
			"Total Streaming Ondemand bytes received from servers"
	::= { ncStreaming 19 }

 	ncStreamingObjHitrate	OBJECT-TYPE
	SYNTAX			INTEGER
	ACCESS			read-only
	STATUS			mandatory
	DESCRIPTION
			"Object Hitrate of Streaming requests" 
	::= { ncStreaming 20 }

	ncStreamingRealBytesToClients  OBJECT-TYPE
	SYNTAX			Counter
	ACCESS			read-only
	STATUS			mandatory
	DESCRIPTION
			"Total Streaming Real bytes sent to clients"
	::= { ncStreaming 21 }

	ncStreamingRealBytesFromClients  OBJECT-TYPE
	SYNTAX			Counter
	ACCESS			read-only
	STATUS			mandatory
	DESCRIPTION
			"Total Streaming Real bytes received from clients"
	::= { ncStreaming 22 }

	ncStreamingRealBytesToServers  OBJECT-TYPE
	SYNTAX			Counter
	ACCESS			read-only
	STATUS			mandatory
	DESCRIPTION
			"Total Streaming Real bytes sent to servers"
	::= { ncStreaming 23 }

	ncStreamingRealBytesFromServers  OBJECT-TYPE
	SYNTAX			Counter
	ACCESS			read-only
	STATUS			mandatory
	DESCRIPTION
			"Total Streaming Real bytes received from servers"
	::= { ncStreaming 24 }

	ncStreamingMmsBytesToClients  OBJECT-TYPE
	SYNTAX			Counter
	ACCESS			read-only
	STATUS			mandatory
	DESCRIPTION
			"Total Streaming Mms bytes sent to clients"
	::= { ncStreaming 25 }

	ncStreamingMmsBytesFromClients  OBJECT-TYPE
	SYNTAX			Counter
	ACCESS			read-only
	STATUS			mandatory
	DESCRIPTION
			"Total Streaming Mms bytes received from clients"
	::= { ncStreaming 26 }

	ncStreamingMmsBytesToServers  OBJECT-TYPE
	SYNTAX			Counter
	ACCESS			read-only
	STATUS			mandatory
	DESCRIPTION
			"Total Streaming Mms bytes sent to servers"
	::= { ncStreaming 27 }

	ncStreamingMmsBytesFromServers  OBJECT-TYPE
	SYNTAX			Counter
	ACCESS			read-only
	STATUS			mandatory
	DESCRIPTION
			"Total Streaming Mms bytes received from servers"
	::= { ncStreaming 28 }

	ncStreamingQuickTimeBytesToClients  OBJECT-TYPE
	SYNTAX			Counter
	ACCESS			read-only
	STATUS			mandatory
	DESCRIPTION
			"Total Streaming QuickTime bytes sent to clients"
	::= { ncStreaming 29 }

	ncStreamingQuickTimeBytesFromClients  OBJECT-TYPE
	SYNTAX			Counter
	ACCESS			read-only
	STATUS			mandatory
	DESCRIPTION
			"Total Streaming QuickTime bytes received from clients"
	::= { ncStreaming 30 }

	ncStreamingQuickTimeBytesToServers  OBJECT-TYPE
	SYNTAX			Counter
	ACCESS			read-only
	STATUS			mandatory
	DESCRIPTION
			"Total Streaming QuickTime bytes sent to servers"
	::= { ncStreaming 31 }

	ncStreamingQuickTimeBytesFromServers  OBJECT-TYPE
	SYNTAX			Counter
	ACCESS			read-only
	STATUS			mandatory
	DESCRIPTION
			"Total Streaming QuickTime bytes received from servers"
	::= { ncStreaming 32 }

 	ncStreamingLiveBWSavings	OBJECT-TYPE
	SYNTAX				INTEGER
	ACCESS				read-only
	STATUS				mandatory
	DESCRIPTION
			"Bandwidth savings for all Live streaming requests"
	::= { ncStreaming 33 }

 	ncStreamingOndemandBWSavings	OBJECT-TYPE
	SYNTAX				INTEGER
	ACCESS				read-only
	STATUS				mandatory
	DESCRIPTION
			"Bandwidth savings for all VOD streaming requests"
	::= { ncStreaming 34 }

 	ncStreamingRealBWSavings	OBJECT-TYPE
	SYNTAX				INTEGER
	ACCESS				read-only
	STATUS				mandatory
	DESCRIPTION
			"Bandwidth savings for all Real streaming requests"
	::= { ncStreaming 35 }

 	ncStreamingMmsBWSavings		OBJECT-TYPE
	SYNTAX				INTEGER
	ACCESS				read-only
	STATUS				mandatory
	DESCRIPTION
			"Bandwidth savings for all MMS streaming requests"
	::= { ncStreaming 36 }

 	ncStreamingQuickTimeBWSavings	OBJECT-TYPE
	SYNTAX				INTEGER
	ACCESS				read-only
	STATUS				mandatory
	DESCRIPTION
			"Bandwidth savings for all QuickTime streaming requests"
	::= { ncStreaming 37 }

 	ncStreamingActiveServConns	OBJECT-TYPE
	SYNTAX			INTEGER
	ACCESS			read-only
	STATUS			mandatory
	DESCRIPTION
			"Number of currently active TCP/IP connections to streaming servers"
	::= { ncStreaming 38 }

 	ncStreamingActiveCliConns	OBJECT-TYPE
	SYNTAX			INTEGER
	ACCESS			read-only
	STATUS			mandatory
	DESCRIPTION
			"Number of currently active TCP/IP connections to streaming clients"
	::= { ncStreaming 39 }

	ncStreamingRtspWMBytesToClients OBJECT-TYPE
	SYNTAX				Counter
	ACCESS				read-only
	STATUS				mandatory
	DESCRIPTION
			"Total Streaming Windows Media RTSP bytes sent to clients"
	::= { ncStreaming 40 }

	ncStreamingRtspWMBytesFromClients	OBJECT-TYPE
	SYNTAX					Counter
	ACCESS					read-only
	STATUS					mandatory
	DESCRIPTION
			"Total Streaming Windows Media RTSP bytes received from clients"
	::= { ncStreaming 41 }

	ncStreamingRtspWMBytesToServers	OBJECT-TYPE
	SYNTAX				Counter
	ACCESS				read-only
	STATUS				mandatory
	DESCRIPTION
			"Total Streaming Windows Media RTSP bytes sent to servers"
	::= { ncStreaming 42 }
	
	ncStreamingRtspWMBytesFromServers	OBJECT-TYPE
	SYNTAX					Counter
	ACCESS					read-only
	STATUS					mandatory
	DESCRIPTION
			"Total Streaming Windows Media RTSP bytes received from servers"
	::= { ncStreaming 43 }

	ncStreamingRtspWMBWSavings	OBJECT-TYPE
	SYNTAX				INTEGER
	ACCESS				read-only
	STATUS				mandatory
	DESCRIPTION
			"Bandwidth savings for all Windows Media RTSP streaming requests"
	::= { ncStreaming 44 }

	ncStreamingAccelTable	OBJECT-TYPE
 	SYNTAX			SEQUENCE OF NcStreamingAccelEntry
	ACCESS			not-accessible
	STATUS			mandatory
 	DESCRIPTION
			 "Number of kilobytes sent to and recieved from the 
			 client side per acceleration rule"

 	::= { ncStreaming 45 }

 	ncStreamingAccelEntry	OBJECT-TYPE
 	SYNTAX			NcStreamingAccelEntry
	ACCESS 			not-accessible
	STATUS 			mandatory
	DESCRIPTION
 			"Each entry contains the number of kilobytes sent and
			 received to/from the clients side per acceleration
			 rule"

 	INDEX	{ ncStreamingAccelIndex }
 	::= { ncStreamingAccelTable 1 }

	NcStreamingAccelEntry ::=
 	SEQUENCE {
 		ncStreamingAccelIndex			INTEGER,
 		ncStreamingAccelKbytesFromClient	Counter,
 		ncStreamingAccelKbytesToClient		Counter,
 		ncStreamingAccelHits			Counter
	}

	ncStreamingAccelIndex	OBJECT-TYPE
 	SYNTAX			INTEGER (1..513)
 	ACCESS			read-only
	STATUS			mandatory
	DESCRIPTION
			"A unique value for each entry in the streaming
			 acceleration  stats table"
 	::= { ncStreamingAccelEntry 1 }

 	ncStreamingAccelKbytesFromClient OBJECT-TYPE
	SYNTAX			Counter
 	ACCESS			read-only
 	STATUS			mandatory
	DESCRIPTION
			"The total number of kilobytes received from the client
			 for this acceleration rule"
	::= { ncStreamingAccelEntry 2 }

	ncStreamingAccelKbytesToClient OBJECT-TYPE
	SYNTAX			Counter
 	ACCESS			read-only
 	STATUS			mandatory
	DESCRIPTION
			"The total number of kilobytes sent to the client for
			 this acceleration rule"
	::= { ncStreamingAccelEntry 3 }

	ncStreamingAccelHits	OBJECT-TYPE
 	SYNTAX			Counter
 	ACCESS			read-only
	STATUS 			mandatory
 	DESCRIPTION
 			" The number of times this acceleration rule has 
				been hit"
 	::= { ncStreamingAccelEntry 4 }

	ncStreamingClientsDelayedSW	OBJECT-TYPE
	SYNTAX				Counter
	ACCESS				read-only
	STATUS				mandatory
	DESCRIPTION
			"Number of clients delayed because of a Bandwidth Limit"
	::= { ncStreaming 46 }

	ncTotalBWSavings	OBJECT-TYPE
	SYNTAX			INTEGER
	ACCESS			read-only
	STATUS			mandatory
	DESCRIPTION
			"Total Bandwidth savings for HTTP, FTP, NNTP, and Streaming protocols"
	::= { ncStats 10 }

	ncDns		OBJECT IDENTIFIER ::= { ncStats 11 }
    
	-- -- -- -- -- -- -- -- -- -- -- -- -- -- -- -- -- --
	-- the netcache dns stats group
	-- -- -- -- -- -- -- -- -- -- -- -- -- -- -- -- -- --

	ncDnsRequestsReceived	OBJECT-TYPE
	SYNTAX			Counter
	ACCESS			read-only
	STATUS			mandatory
	DESCRIPTION
			"Total DNS requests received from clients"
	::= { ncDns 1 }

	ncDnsCacheHits		OBJECT-TYPE
	SYNTAX			Counter
	ACCESS			read-only
	STATUS			mandatory
	DESCRIPTION
			"Hits on the DNS cache.  This includes hits
			for DNS lookups generated by NetCache internally"
	::= { ncDns 2 }

	ncDnsCacheMisses	OBJECT-TYPE
	SYNTAX			Counter
	ACCESS			read-only
	STATUS			mandatory
	DESCRIPTION
			"Misses on the DNS cache.  This includes misses
			for DNS lookups generated by NetCache internally"
	::= { ncDns 3 }

	ncDnsSuccessfulForwardLookups	OBJECT-TYPE
	SYNTAX				Counter
	ACCESS				read-only
	STATUS				mandatory
	DESCRIPTION
			"Forward DNS lookups that are successful"
	::= { ncDns 4 }

	ncDnsFailedForwardLookups	OBJECT-TYPE
	SYNTAX				Counter
	ACCESS				read-only
	STATUS				mandatory
	DESCRIPTION
			"Forward DNS lookups that failed"
	::= { ncDns 5 }

	ncDnsPendingForwardLookups	OBJECT-TYPE
	SYNTAX				INTEGER
	ACCESS				read-only
	STATUS				mandatory
	DESCRIPTION
			"Forward DNS lookups that are in progress"
	::= { ncDns 6 }

	ncDnsSuccessfulReverseLookups	OBJECT-TYPE
	SYNTAX				Counter
	ACCESS				read-only
	STATUS				mandatory
	DESCRIPTION
			"Reverse DNS lookups that are successful"
	::= { ncDns 7 }

	ncDnsFailedReverseLookups	OBJECT-TYPE
	SYNTAX				Counter
	ACCESS				read-only
	STATUS				mandatory
	DESCRIPTION
			"Reverse DNS lookups that failed"
	::= { ncDns 8 }

	ncDnsPendingReverseLookups	OBJECT-TYPE
	SYNTAX				INTEGER
	ACCESS				read-only
	STATUS				mandatory
	DESCRIPTION
			"Reverse DNS lookups that are in progress"
	::= { ncDns 9 }

	ncDnsIres	OBJECT IDENTIFIER ::= { ncDns 10 }
    
	-- -- -- -- -- -- -- -- -- -- -- -- -- -- -- -- -- --
	-- the netcache dns ires stats group
	-- -- -- -- -- -- -- -- -- -- -- -- -- -- -- -- -- --


	ncDnsIresIsEnabled		OBJECT-TYPE
	SYNTAX				INTEGER {
						false(1),
						true(2)
					}
	ACCESS				read-only
	STATUS					mandatory
	DESCRIPTION
			"Has Full Service Resolver been enabled"
	::= { ncDnsIres 1 }

	ncDnsIresIsInitialised		OBJECT-TYPE
	SYNTAX				INTEGER {
						false(1),
						true(2)
					}
	ACCESS				read-only
	STATUS				mandatory
	DESCRIPTION
			"Has Full Service Resolver initalised"
	::= { ncDnsIres 2 }

	ncDnsIresForwardLookups		OBJECT-TYPE
	SYNTAX				Counter
	ACCESS				read-only
	STATUS				mandatory
	DESCRIPTION
			"Full Service Resolver's Forward Lookups"
	::= { ncDnsIres 3 }

	ncDnsIresPendingForwardLookups	OBJECT-TYPE
	SYNTAX				Counter
	ACCESS				read-only
	STATUS				mandatory
	DESCRIPTION
			"Full Service Resolver's Pending Forward Lookups"
	::= { ncDnsIres 4 }

	ncDnsIresReverseLookups		OBJECT-TYPE
	SYNTAX				Counter
	ACCESS				read-only
	STATUS				mandatory
	DESCRIPTION
			"Full Service Resolver's Reverse Lookups"
	::= { ncDnsIres 5 }

	ncDnsIresPendingReverseLookups	OBJECT-TYPE
	SYNTAX				Counter
	ACCESS				read-only
	STATUS				mandatory
	DESCRIPTION
			"Full Service Resolver's Pending Reverse Lookups"
	::= { ncDnsIres 6 }


	ncAuth		OBJECT IDENTIFIER ::= { ncStats 12 }

	-- -- -- -- -- -- -- -- -- -- -- -- -- -- -- -- -- --
	-- the netcache authentication stats group
	-- -- -- -- -- -- -- -- -- -- -- -- -- -- -- -- -- --

	ncNtlm		OBJECT IDENTIFIER ::= { ncAuth 1 }

	-- -- -- -- -- -- -- -- -- -- -- -- -- -- -- -- -- --
	-- the netcache ntlm stats group
	-- -- -- -- -- -- -- -- -- -- -- -- -- -- -- -- -- --

 	ncNtlmPossibleProblem	OBJECT-TYPE
	SYNTAX			INTEGER {
					false(1),
					true(2)
				}
	ACCESS			read-only
	STATUS			mandatory
	DESCRIPTION
			"Whether a possible ntlm problem is detected 
			in the appliance's domain environment."
	::= { ncNtlm 1 }


	ncRM		OBJECT IDENTIFIER ::= { ncStats 13 }

	-- -- -- -- -- -- -- -- -- -- -- -- -- -- -- -- -- --
	-- the netcache resource management group
	-- -- -- -- -- -- -- -- -- -- -- -- -- -- -- -- -- --

	ncRMMem		OBJECT IDENTIFIER ::= { ncRM 1 }

	-- -- -- -- -- -- -- -- -- -- -- -- -- -- -- -- -- --
	-- the netcache memory stats group
	-- -- -- -- -- -- -- -- -- -- -- -- -- -- -- -- -- --
	ncRMMemTotal            OBJECT-TYPE
	SYNTAX                  INTEGER
	ACCESS                  read-only
	STATUS                  mandatory
	DESCRIPTION
	                "Total memory in kilobytes available for 
					allocations after boot. It does not imply 
					the total system memory."
	::= { ncRMMem 1 }

	ncRMMemFree             OBJECT-TYPE
	SYNTAX                  INTEGER
	ACCESS                  read-only
	STATUS                  mandatory
	DESCRIPTION
	                "Current free memory in kilobytes available 
					for allocations."
	::= { ncRMMem 2 }

	-- -- -- -- -- -- -- -- --
	-- the snapmirror group --
	-- -- -- -- -- -- -- -- --

	snapmirrorOn		OBJECT-TYPE
	SYNTAX			INTEGER { off(1), on(2) }
	ACCESS			read-only
	STATUS			mandatory
	DESCRIPTION
			"Indicates whether snapmirror has been turned on
			or not."
	::= { snapmirror 1 }

	-- the old active snapmirror destination count, new name is
	-- snapmirrorActiveDstNumber.  DEPRECATED
	snapmirrorActiveRestoreCount	OBJECT-TYPE
	SYNTAX		INTEGER
	ACCESS		read-only
	STATUS		mandatory
	DESCRIPTION
			"Number of active SnapMirror restores."

	::= { snapmirror 2 }

	-- the old active snapmirror destination count, new name is
	-- snapmirrorActiveDstNumber.  DEPRECATED
	snapmirrorScheduledRestoreCount	OBJECT-TYPE
	SYNTAX		INTEGER
	ACCESS		read-only
	STATUS		mandatory
	DESCRIPTION
			"Number of scheduled SnapMirror restores."

	::= { snapmirror 3 }
	
	-- the old active snapmirror destination count, new name is
	-- snapmirrorActiveDstNumber.  DEPRECATED
	snapmirrorBackupNumber	OBJECT-TYPE
	SYNTAX		INTEGER
	ACCESS		read-only
  	STATUS		mandatory
	DESCRIPTION
			"Number of active SnapMirror backups."

	::= { snapmirror 4 }

	-- the old active snapmirror destination count, new name is
	-- snapmirrorActiveDstNumber.  DEPRECATED
	snapmirrorBackupSuccesses OBJECT-TYPE
	SYNTAX		Counter
	ACCESS		read-only
	STATUS		mandatory
	DESCRIPTION	
			"Number of SnapMirror backups which completed.
			Reset on reboot."

	::= { snapmirror 5 }

	-- the old active snapmirror destination count, new name is
	-- snapmirrorActiveDstNumber.  DEPRECATED
	snapmirrorRestoreSuccesses	OBJECT-TYPE
	SYNTAX		Counter
	ACCESS		read-only
	STATUS		mandatory
	DESCRIPTION	
			"Number of SnapMirror restores which completed.
			Reset on reboot."

	::= { snapmirror 6 }

	-- the old active snapmirror destination count, new name is
	-- snapmirrorActiveDstNumber.  DEPRECATED
	snapmirrorBackupAborts		OBJECT-TYPE
	SYNTAX		Counter
	ACCESS		read-only
	STATUS		mandatory
	DESCRIPTION	
			"Number of SnapMirror backup transfers which have
			aborted. Reset on reboot."

	::= { snapmirror 7 }

	-- the old active snapmirror destination count, new name is
	-- snapmirrorActiveDstNumber.  DEPRECATED
	snapmirrorRestoreRestartAborts	OBJECT-TYPE
	SYNTAX		Counter
	ACCESS		read-only
	STATUS		mandatory
	DESCRIPTION	
			"Number of SnapMirror restore temporary aborts.
			Reset on reboot."

	::= { snapmirror 8 }

	-- the old active snapmirror destination count, new name is
	-- snapmirrorActiveDstNumber.  DEPRECATED
	snapmirrorRestoreWaitAborts	OBJECT-TYPE
	SYNTAX		Counter
	ACCESS		read-only
	STATUS		mandatory
	DESCRIPTION	
			"Number of SnapMirror restore permanent aborts.
			Reset on reboot."

	::= { snapmirror 9 }

	-- the old active snapmirror destination count, new name is
	-- snapmirrorActiveDstNumber.  DEPRECATED
	snapmirrorWrittenBytes	OBJECT-TYPE
	SYNTAX		Counter
	ACCESS		read-only
	STATUS		mandatory
	DESCRIPTION	
			"Number of Megabytes written by SnapMirror.
			Reset on reboot."

	::= { snapmirror 10 }

	-- the old active snapmirror destination count, new name is
	-- snapmirrorActiveDstNumber.  DEPRECATED
	snapmirrorReadBytes	OBJECT-TYPE
	SYNTAX		Counter
	ACCESS		read-only
	STATUS		mandatory
	DESCRIPTION	
			"Number of Megabytes read by SnapMirror.
			Reset on reboot."

	::= { snapmirror 11 }

	snapmirrorActiveDstNumber	OBJECT-TYPE
	SYNTAX		INTEGER
	ACCESS		read-only
	STATUS		mandatory
	DESCRIPTION
			"Number of active SnapMirror destination."

	::= { snapmirror 12 }

	snapmirrorActiveSrcNumber	OBJECT-TYPE
	SYNTAX		INTEGER
	ACCESS		read-only
  	STATUS		mandatory
	DESCRIPTION
			"Number of active SnapMirror Source."

	::= { snapmirror 13 }

	snapmirrorFilerTotalDstSuccesses OBJECT-TYPE
	SYNTAX		Counter
	ACCESS		read-only
	STATUS		mandatory
	DESCRIPTION	
			"Total number of successful snapmirror transfers to
			the destination. Persistent across reboot."

	::= { snapmirror 14 }

	snapmirrorFilerTotalSrcSuccesses	OBJECT-TYPE
	SYNTAX		Counter
	ACCESS		read-only
	STATUS		mandatory
	DESCRIPTION	
			"Total number of successful snapmirror transfers
			from the source. Persistent across reboot."

	::= { snapmirror 15 }

	snapmirrorFilerTotalSrcFailures	OBJECT-TYPE
	SYNTAX		Counter
	ACCESS		read-only
	STATUS		mandatory
	DESCRIPTION	
			"Total number of failed SnapMirror transfers on
			the source. Persistent across reboot."

	::= { snapmirror 16 }

	snapmirrorFilerTotalDstFailures	OBJECT-TYPE
	SYNTAX		Counter
	ACCESS		read-only
	STATUS		mandatory
	DESCRIPTION	
			"Total number of failed SnapMirror transfers on
			the destination. Persistent across reboot."

	::= { snapmirror 17 }

	snapmirrorFilerTotalDstDeferments	OBJECT-TYPE
	SYNTAX		Counter
	ACCESS		read-only
	STATUS		mandatory
	DESCRIPTION	
			"Total number of deferred snapmirror transfer on
			the destination. Persistent across reboot."

	::= { snapmirror 18 }

	snapmirrorIsLicensed	OBJECT-TYPE
	SYNTAX  	INTEGER {
				false(1),
				true(2)
			}
	ACCESS  	read-only
	STATUS		mandatory
	DESCRIPTION
		"Whether the snapmirror is licensed on the filer."

	::= { snapmirror 19 }

	snapmirrorStatusTable	OBJECT-TYPE
	SYNTAX		SEQUENCE OF SnapmirrorStatusEntry
	ACCESS		not-accessible
	STATUS		mandatory
	DESCRIPTION
			"provide a list of snapmirror status."

	::= { snapmirror 20 }

	snapmirrorStatusEntry	OBJECT-TYPE
	SYNTAX		SnapmirrorStatusEntry
	ACCESS		not-accessible
	STATUS		mandatory
	DESCRIPTION
			"Provide a report of current status of snapmirror."

	INDEX	{ snapmirrorIndex }
	::= { snapmirrorStatusTable 1 }

	SnapmirrorStatusEntry ::=
	    SEQUENCE {
	    	snapmirrorIndex
			INTEGER,
		snapmirrorSrc
			OCTET STRING,
		snapmirrorDst
			OCTET STRING,
		snapmirrorStatus
			INTEGER,
		snapmirrorState
			INTEGER,
		snapmirrorLag
			TimeTicks,
		snapmirrorTotalSuccesses
			Counter,
		snapmirrorTotalRestartSuccesses
			Counter,
		snapmirrorTotalFailures
			Counter,
		snapmirrorTotalDeferments
			Counter,
		snapmirrorTotalTransMBs
			Counter,
		snapmirrorTotalTransTimeSeconds
			Counter,
		snapmirrorThrottleValue
			INTEGER,
		snapmirrorMirrorTimestamp
			DisplayString,
		snapmirrorBaseSnapshot
			DisplayString,
		snapmirrorLastTransType
			DisplayString,
		snapmirrorLastTransMBs
			Counter,
		snapmirrorLastTransTimeSeconds
			Counter,
		snapmirrorSchedule
			DisplayString,
		snapmirrorScheduleDesc
			DisplayString,
		snapmirrorArguments
			DisplayString,
		snapmirrorSyncToAsync
		        Counter
	    }

	snapmirrorIndex	OBJECT-TYPE
	SYNTAX		INTEGER (1..2147483647)
	ACCESS		read-only
	STATUS		mandatory
	DESCRIPTION
			"Index into the snapmirror status table."

	::= { snapmirrorStatusEntry 1 }

	snapmirrorSrc	OBJECT-TYPE
	SYNTAX		OCTET STRING
	ACCESS		read-only
	STATUS		mandatory
	DESCRIPTION
			"Source of the snapmirror. <filer>:<vol> or
			<filer>:/vol/<qtree_name>"

	::= { snapmirrorStatusEntry 2 }

	snapmirrorDst	OBJECT-TYPE
	SYNTAX		OCTET STRING
	ACCESS		read-only
	STATUS		mandatory
	DESCRIPTION
			"Destination of the snapmirror.
			<filer>:<vol> or <filer>:/vol/<qtree_name>"

	::= { snapmirrorStatusEntry 3 }

	snapmirrorStatus	OBJECT-TYPE
	SYNTAX		INTEGER {
				idle(1),
				transferring(2),
				pending(3),
				aborting(4),
				migrating(5),
				quiescing(6),
				resyncing(7),
				waiting(8),
				syncing(9),
				in-sync(10)
				}
	ACCESS		read-only
	STATUS		mandatory
	DESCRIPTION
			"Current transfer status of the snapmirror."

	::= { snapmirrorStatusEntry 4 }

	snapmirrorState	OBJECT-TYPE
	SYNTAX		INTEGER {
				uninitialized(1),
				snapmirrored(2),
				broken-off(3),
				quiesced(4),
				source(5),
				unknown(6)
				}
	ACCESS		read-only
	STATUS		mandatory
	DESCRIPTION
			"Current state of the snapmirror."

	::= { snapmirrorStatusEntry 5 }

	snapmirrorLag	OBJECT-TYPE
	SYNTAX		TimeTicks
	ACCESS		read-only
	STATUS		mandatory
	DESCRIPTION
			"How far behind from the source the destination is."

	::= { snapmirrorStatusEntry 6 }

	snapmirrorTotalSuccesses	OBJECT-TYPE
	SYNTAX		Counter
	ACCESS		read-only
	STATUS		mandatory
	DESCRIPTION
		"Total number of successful transfer since the snapmirror
		is initialized. Persistent across reboot."

	::= { snapmirrorStatusEntry 7 }

	snapmirrorTotalRestartSuccesses	OBJECT-TYPE
	SYNTAX		Counter
	ACCESS		read-only
	STATUS		mandatory
	DESCRIPTION
		"Total number of successful restarted transfer since
		the snapmirror is initialized. Persistent across reboot."

	::= { snapmirrorStatusEntry 8 }

	snapmirrorTotalFailures	OBJECT-TYPE
	SYNTAX		Counter
	ACCESS		read-only
	STATUS		mandatory
	DESCRIPTION
		"Total number of failed or aborted transfer since
		the snapmirror is initialized. Persistent across reboot."

	::= { snapmirrorStatusEntry 9 }

	snapmirrorTotalDeferments	OBJECT-TYPE
	SYNTAX		Counter
	ACCESS		read-only
	STATUS		mandatory
	DESCRIPTION
		"Total number of deferment since the snapmirror
		is initialized. Persistent across reboot."

	::= { snapmirrorStatusEntry 10 }

	snapmirrorTotalTransMBs		OBJECT-TYPE
	SYNTAX		Counter
	ACCESS		read-only
	STATUS		mandatory
	DESCRIPTION
		"Total transfer size in MB for the snapmirror.
		Reset on reboot."

	::= { snapmirrorStatusEntry 11 }

	snapmirrorTotalTransTimeSeconds	OBJECT-TYPE
	SYNTAX		Counter
	ACCESS		read-only
	STATUS		mandatory
	DESCRIPTION
		"Total number of seconds spent in successful transfer for the 
		snapmirror. Reset on reboot."

	::= { snapmirrorStatusEntry 12 }

	snapmirrorThrottleValue	OBJECT-TYPE
	SYNTAX		INTEGER
	ACCESS		read-only
	STATUS		mandatory
	DESCRIPTION
		"Current throttle value for the snapmirror."

	::= { snapmirrorStatusEntry 13 }

	snapmirrorMirrorTimestamp	OBJECT-TYPE
	SYNTAX		DisplayString
	ACCESS		read-only
	STATUS		mandatory
	DESCRIPTION
		"Timestamp of the last snapshot successfully transferred from 
		 the source to the destination."

	::= { snapmirrorStatusEntry 14 }

	snapmirrorBaseSnapshot	OBJECT-TYPE
	SYNTAX		DisplayString
	ACCESS		read-only
	STATUS		mandatory
	DESCRIPTION
		"The name of the current base snapshot for the snapmirror."

	::= { snapmirrorStatusEntry 15 }

	snapmirrorLastTransType	OBJECT-TYPE
	SYNTAX		DisplayString
	ACCESS		read-only
	STATUS		mandatory
	DESCRIPTION
		"The type of the previous successful transfer."

	::= { snapmirrorStatusEntry 16 }

	snapmirrorLastTransMBs	OBJECT-TYPE
	SYNTAX		Counter
	ACCESS		read-only
	STATUS		mandatory
	DESCRIPTION
		"Last successful transfer size in MB for the snapmirror."

	::= { snapmirrorStatusEntry 17 }

	snapmirrorLastTransTimeSeconds	OBJECT-TYPE
	SYNTAX		Counter
	ACCESS		read-only
	STATUS		mandatory
	DESCRIPTION
		"Duration of last successful transfer in seconds for the
		 snapmirror."

	::= { snapmirrorStatusEntry 18 }

	snapmirrorSchedule	OBJECT-TYPE
	SYNTAX		DisplayString
	ACCESS		read-only
	STATUS		mandatory
	DESCRIPTION
		"Update schedule for the snapmirror in conf file format."

	::= { snapmirrorStatusEntry 19 }

	snapmirrorScheduleDesc	OBJECT-TYPE
	SYNTAX		DisplayString
	ACCESS		read-only
	STATUS		mandatory
	DESCRIPTION
		"Description of the update schedule for the snapmirror."

	::= { snapmirrorStatusEntry 20 }

	snapmirrorArguments	OBJECT-TYPE
	SYNTAX		DisplayString
	ACCESS		read-only
	STATUS		mandatory
	DESCRIPTION
		"Arguments for the snapmirror in conf file format."

	::= { snapmirrorStatusEntry 21 }

        snapmirrorSyncToAsync	OBJECT-TYPE
	SYNTAX		Counter
	ACCESS		read-only
	STATUS		mandatory
	DESCRIPTION
	        "The number of times changing from sync mode to async mode 
		since the snapmirror is initialized. Persistent across reboot."
    
	::= { snapmirrorStatusEntry 22 }

	snapmirrorConnTable	OBJECT-TYPE
	SYNTAX		SEQUENCE OF SnapmirrorConnEntry
	ACCESS		not-accessible
	STATUS		mandatory
	DESCRIPTION
	        "Provide a list of snapmirror connection definitions."

	::= { snapmirror 21 }

	snapmirrorConnEntry	OBJECT-TYPE
	SYNTAX		SnapmirrorConnEntry
	ACCESS		not-accessible
	STATUS		mandatory
	DESCRIPTION
		"Provide a report of a defined multipath connection."

	INDEX	{ snapmirrorConnIndex }
	::= { snapmirrorConnTable 1 }

        SnapmirrorConnEntry ::=
	    SEQUENCE {
	    	snapmirrorConnIndex
			INTEGER,
		snapmirrorConnName
			DisplayString,
		snapmirrorConnType
			INTEGER,
		snapmirrorConnSrc1
			DisplayString,
		snapmirrorConnDst1
		        DisplayString,
		snapmirrorConnSrc2
		        DisplayString, 
		snapmirrorConnDst2
		        DisplayString 
	    }

	snapmirrorConnIndex	OBJECT-TYPE
	SYNTAX		INTEGER (1..2147483647)
	ACCESS		read-only
	STATUS		mandatory
	DESCRIPTION
		"Index into the snapmirror multipath connection table."

	::= { snapmirrorConnEntry 1 }

	snapmirrorConnName	OBJECT-TYPE
	SYNTAX		DisplayString
	ACCESS		read-only
	STATUS		mandatory
	DESCRIPTION
		"The name of the snapmirror multipath connection."
	    
	::= { snapmirrorConnEntry 2 }

	snapmirrorConnType	OBJECT-TYPE
	SYNTAX		INTEGER {
	                        multi(1),
				failover(2)
				}
	ACCESS		read-only
	STATUS		mandatory
	DESCRIPTION
		"The type of the snapmirror multipath connection."

	::= { snapmirrorConnEntry 3 }

	snapmirrorConnSrc1	OBJECT-TYPE
	SYNTAX		DisplayString
	ACCESS		read-only
	STATUS		mandatory
	DESCRIPTION
		"The name of the source for the first path."

        ::= { snapmirrorConnEntry 4 }

	snapmirrorConnDst1	OBJECT-TYPE
	SYNTAX		DisplayString
	ACCESS		read-only
	STATUS		mandatory
	DESCRIPTION
	        "The name of the destination for the first path."

        ::= { snapmirrorConnEntry 5 }

	snapmirrorConnSrc2	OBJECT-TYPE
	SYNTAX		DisplayString
	ACCESS		read-only
	STATUS		mandatory
	DESCRIPTION
		"The name of the source for the second path."

	::= { snapmirrorConnEntry 6 }   

	snapmirrorConnDst2	OBJECT-TYPE
	SYNTAX		DisplayString
	ACCESS		read-only
	STATUS		mandatory
	DESCRIPTION
		"The name of the destination for the second path."

        ::= { snapmirrorConnEntry 7 }

	-- -- -- -- -- -- -- -- --
	-- the snapvault group
	-- -- -- -- -- -- -- -- --
           
                  -- this group contains statistics for the whole system
                  -- unless otherwise specified.

	svOn			OBJECT-TYPE
	SYNTAX			INTEGER { off(1), on(2) }
	ACCESS			read-only
	STATUS			mandatory
	DESCRIPTION
			"Indicates whether snapvault has been turned on
			or not."
	::= { snapvault 1 }

	svSystemActiveDstNumber	OBJECT-TYPE
	SYNTAX		INTEGER
	ACCESS		read-only
	STATUS		mandatory
	DESCRIPTION
			"Number of active snapvault destionations."

	::= { snapvault 2 }

	svSystemActiveSrcNumber	OBJECT-TYPE
	SYNTAX		INTEGER
	ACCESS		read-only
  	STATUS		mandatory
	DESCRIPTION
			"Number of active snapvault sources."

	::= { snapvault 3 }

	svSystemTotalPrimarySuccesses	OBJECT-TYPE
	SYNTAX		Counter
	ACCESS		read-only
	STATUS		mandatory
	DESCRIPTION	
			"Total number of successful snapvault transfers
			from the snapvault primary. Persistent across reboot."

        ::= { snapvault 4 }

	svSystemTotalSecondarySuccesses OBJECT-TYPE
	SYNTAX		Counter
	ACCESS		read-only
	STATUS		mandatory
	DESCRIPTION	
			"Total number of successful snapvault transfers to
			the snapvault secondary. Persistent across reboot."

	::= { snapvault 5 }

	svSystemTotalPrimaryFailures	OBJECT-TYPE
	SYNTAX		Counter
	ACCESS		read-only
	STATUS		mandatory
	DESCRIPTION	
			"Total number of failed snapvault transfers on
			the snapvault primary. Persistent across reboot."

	::= { snapvault 6 }

	svSystemTotalSecondaryFailures	OBJECT-TYPE
	SYNTAX		Counter
	ACCESS		read-only
	STATUS		mandatory
	DESCRIPTION	
			"Total number of failed snapvault transfers on
			the snapvault secondary. Persistent across reboot."

	::= { snapvault 7 }

	svSystemTotalSecondaryDeferments	OBJECT-TYPE
	SYNTAX		Counter
	ACCESS		read-only
	STATUS		mandatory
	DESCRIPTION	
			"Total number of deferred snapvault transfers on
			the snapvault secondary. Persistent across reboot."

	::= { snapvault 8 }

	svPrimaryIsLicensed	OBJECT-TYPE
	SYNTAX  	INTEGER {
				false(1),
				true(2)
			}
	ACCESS  	read-only
	STATUS		mandatory
	DESCRIPTION
		"Whether the snapvault_client(primary) is licensed on the filer."

	::= { snapvault 9 }

	svSecondaryIsLicensed	OBJECT-TYPE
	SYNTAX  	INTEGER {
				false(1),
				true(2)
			}
	ACCESS  	read-only
	STATUS		mandatory
	DESCRIPTION
		"Whether the snapvault_server(secondary) is licensed on the filer."

	::= { snapvault 10 }



	snapvaultStatusTable	OBJECT-TYPE
	SYNTAX		SEQUENCE OF SnapvaultStatusEntry
	ACCESS		not-accessible
	STATUS		mandatory
	DESCRIPTION
			"provide a list of snapvault status."

	::= { snapvault 11 }

	snapvaultStatusEntry	OBJECT-TYPE
	SYNTAX		SnapvaultStatusEntry
	ACCESS		not-accessible
	STATUS		mandatory
	DESCRIPTION
			"Provide a report of current status of snapvault."

	INDEX	{ svIndex }
	::= { snapvaultStatusTable 1 }

	SnapvaultStatusEntry ::=
	    SEQUENCE {
	    	svIndex
			INTEGER,
		svSrc
			OCTET STRING,
		svDst
			OCTET STRING,
		svStatus
			INTEGER,
		svState
			INTEGER,
		svLag
			TimeTicks,
		svTotalSuccesses
			Counter,
		svTotalRestartSuccesses
			Counter,
		svTotalFailures
			Counter,
		svTotalDeferments
			Counter,
		svTotalTransMBs
			Counter,
		svTotalTransTimeSeconds
			Counter,
		svThrottleValue
			INTEGER,
		svSrcSnapshotTime
		        INTEGER,
		svBaseSnapshot
			DisplayString,
		svLastTransType
			DisplayString,
		svLastTransMBs
			INTEGER,
		svLastTransTimeSeconds
			INTEGER
	    }

	svIndex		OBJECT-TYPE
	SYNTAX		INTEGER (1..2147483647)
	ACCESS		read-only
	STATUS		mandatory
	DESCRIPTION
			"Index into the snapvault status table."

	::= { snapvaultStatusEntry 1 }

	svSrc		OBJECT-TYPE
	SYNTAX		OCTET STRING
	ACCESS		read-only
	STATUS		mandatory
	DESCRIPTION
			"Source of the snapvault relationship.
			<filer>:/vol/<qtree_name>"

	::= { snapvaultStatusEntry 2 }

	svDst		OBJECT-TYPE
	SYNTAX		OCTET STRING
	ACCESS		read-only
	STATUS		mandatory
	DESCRIPTION
			"Destionation of the snapvault relationship.
			<filer>:/vol/<qtree_name>"

	::= { snapvaultStatusEntry 3 }

	svStatus	OBJECT-TYPE
	SYNTAX		INTEGER {
				idle(1),
				transferring(2),
				pending(3),
				aborting(4),
				quiescing(6),
				resyncing(7),
				paused(12)
				}
	ACCESS		read-only
	STATUS		mandatory
	DESCRIPTION
			"Current transfer status of the snapvault relationship."

	::= { snapvaultStatusEntry 4 }

	svState		OBJECT-TYPE
	SYNTAX		INTEGER {
				uninitialized(1),
				snapvaulted(2),
				broken-off(3),
				quiesced(4),
				source(5),
				unknown(6),
				restoring(7)
				}
	ACCESS		read-only
	STATUS		mandatory
	DESCRIPTION
			"Current state of the snapvault relationship."

	::= { snapvaultStatusEntry 5 }

	svLag		OBJECT-TYPE
	SYNTAX		TimeTicks
	ACCESS		read-only
	STATUS		mandatory
	DESCRIPTION
			"How far behind from the source the destination is."

	::= { snapvaultStatusEntry 6 }

	svTotalSuccesses	OBJECT-TYPE
	SYNTAX		Counter
	ACCESS		read-only
	STATUS		mandatory
	DESCRIPTION
		"Total number of successful transfer since the snapvault
		 relationship was established. Persistent across reboot."

	::= { snapvaultStatusEntry 7 }

	svTotalRestartSuccesses	OBJECT-TYPE
	SYNTAX		Counter
	ACCESS		read-only
	STATUS		mandatory
	DESCRIPTION
		"Total number of successful restarted transfer since
		 the snapvault relationship was established. Persistent 
		 across reboot."

	::= { snapvaultStatusEntry 8 }

	svTotalFailures	OBJECT-TYPE
	SYNTAX		Counter
	ACCESS		read-only
	STATUS		mandatory
	DESCRIPTION
		"Total number of failed or aborted transfer since
		 the snapvault relationship was established. Persistent 
		 across reboot."

	::= { snapvaultStatusEntry 9 }

	svTotalDeferments	OBJECT-TYPE
	SYNTAX		Counter
	ACCESS		read-only
	STATUS		mandatory
	DESCRIPTION
		"Total number of deferment since the snapvault
		 relationship was established. Persistent across reboot."

	::= { snapvaultStatusEntry 10 }

	svTotalTransMBs		OBJECT-TYPE
	SYNTAX		Counter
	ACCESS		read-only
	STATUS		mandatory
	DESCRIPTION
		"Total transfer size in MB for the snapvault.
		Reset on reboot."

	::= { snapvaultStatusEntry 11 }

	svTotalTransTimeSeconds	OBJECT-TYPE
	SYNTAX		Counter
	ACCESS		read-only
	STATUS		mandatory
	DESCRIPTION
		"Total number of seconds spent in successful transfer for the 
		 snapvault relationship. Reset on reboot."

	::= { snapvaultStatusEntry 12 }

	svThrottleValue	OBJECT-TYPE
	SYNTAX		INTEGER
	ACCESS		read-only
	STATUS		mandatory
	DESCRIPTION
		"Current throttle value for the snapvault relationship."

	::= { snapvaultStatusEntry 13 }

	svSrcSnapshotTime	OBJECT-TYPE
	SYNTAX		INTEGER
	ACCESS		read-only
	STATUS		mandatory
	DESCRIPTION
		"Time when the source snapshot was created. The time in 
		seconds since January 1, 1970. The source snapshot here 
		is the last snapshot successfully transferred from the 
		source to the destination."

	::= { snapvaultStatusEntry 14 }

	svBaseSnapshot	OBJECT-TYPE
	SYNTAX		DisplayString
	ACCESS		read-only
	STATUS		mandatory
	DESCRIPTION
		"The name of the current base snapshot for the 
		 snapvault relationship."

	::= { snapvaultStatusEntry 15 }

	svLastTransType	OBJECT-TYPE
	SYNTAX		DisplayString
	ACCESS		read-only
	STATUS		mandatory
	DESCRIPTION
		"The type of the previous successful transfer."

	::= { snapvaultStatusEntry 16 }

	svLastTransMBs	OBJECT-TYPE
	SYNTAX		INTEGER
	ACCESS		read-only
	STATUS		mandatory
	DESCRIPTION
		"Last successful transfer size in MB for the snapvault 
		 relationship."

	::= { snapvaultStatusEntry 17 }

	svLastTransTimeSeconds	OBJECT-TYPE
	SYNTAX		INTEGER
	ACCESS		read-only
	STATUS		mandatory
	DESCRIPTION
		"Duration of last successful transfer in seconds for the
		 snapvault relationship."

	::= { snapvaultStatusEntry 18 }

	snapvaultHostTable	OBJECT-TYPE
	SYNTAX		SEQUENCE OF SnapvaultHostEntry
	ACCESS		not-accessible
	STATUS		mandatory
	DESCRIPTION
			"Provide a list of remote snapvault hosts."

	::= { snapvault 12 }

	snapvaultHostEntry	OBJECT-TYPE
	SYNTAX		SnapvaultHostEntry
	ACCESS		not-accessible
	STATUS		mandatory
	DESCRIPTION
			"Provide snapvault statistics for a remote host
			 which has one or more current established 
			 relationships with the local snapvault system."

	INDEX	{ svHostIndex }
	::= { snapvaultHostTable 1 }

	SnapvaultHostEntry ::=
	    SEQUENCE {
	    	svHostIndex
			INTEGER,
		svHostName
			DisplayString,
		svHostType
			INTEGER,
		svHostTotalSuccesses
			INTEGER,
		svHostTotalFailures
			INTEGER,
		svHostTotalDeferments
			INTEGER
	    }

	svHostIndex	OBJECT-TYPE
	SYNTAX		INTEGER (1..2147483647)
	ACCESS		read-only
	STATUS		mandatory
	DESCRIPTION
			"Index into the snapvault remote host table."

	::= { snapvaultHostEntry 1 }

	svHostName	OBJECT-TYPE
	SYNTAX		DisplayString
	ACCESS		read-only
	STATUS		mandatory
	DESCRIPTION
		"The name of the remote snapvault host."
	    
	::= { snapvaultHostEntry 2 }

	svHostType	OBJECT-TYPE
	SYNTAX		INTEGER {
	                        primary(1),
				secondary(2)
				}
	ACCESS		read-only
	STATUS		mandatory
	DESCRIPTION
		"The type of the remote snapvault host."

	::= { snapvaultHostEntry 3 }

	svHostTotalSuccesses	OBJECT-TYPE
	SYNTAX		INTEGER 
	ACCESS		read-only
	STATUS		mandatory
	DESCRIPTION
	        "Total number of successful snapvault transfers
		for all current established relationships between
		the local snapvault system and the given remote host."

	::= { snapvaultHostEntry 4 }

	svHostTotalFailures	OBJECT-TYPE
	SYNTAX		INTEGER
	ACCESS		read-only
	STATUS		mandatory
	DESCRIPTION
	        "Total number of failed snapvault transfers
		for all current established relationships between
		the local snapvault system and the given remote host."

	::= { snapvaultHostEntry 5 }

	svHostTotalDeferments	OBJECT-TYPE
	SYNTAX		INTEGER
	ACCESS		read-only
	STATUS		mandatory
	DESCRIPTION
		"Total number of deferred snapvault transfers for
		all current established relationships between
		the local snapvault system and the given remote host.
		0 for snapvault client host."

	::= { snapvaultHostEntry 6 }


	snapvaultSchedTable	OBJECT-TYPE
	SYNTAX		SEQUENCE OF SnapvaultSchedEntry
	ACCESS		not-accessible
	STATUS		mandatory
	DESCRIPTION
			"Provide a list of snapvault schedules."

	::= { snapvault 13 }

	snapvaultSchedEntry	OBJECT-TYPE
	SYNTAX		SnapvaultSchedEntry
	ACCESS		not-accessible
	STATUS		mandatory
	DESCRIPTION
			"Provide a report of schedules of snapvault."

	INDEX	{ svSchedIndex }
	::= { snapvaultSchedTable 1 }

	SnapvaultSchedEntry ::=
	    SEQUENCE {
	    	svSchedIndex
			INTEGER,
		svSchedVolume
			DisplayString,
		svSchedSnapshot
			DisplayString,
		svSchedStatus
			INTEGER,
		svSchedType
			INTEGER,
		svSchedSchedule
			DisplayString
	    }

	svSchedIndex	OBJECT-TYPE
	SYNTAX		INTEGER (1..2147483647)
	ACCESS		read-only
	STATUS		mandatory
	DESCRIPTION
			"Index into the snapvault schedule table."

	::= { snapvaultSchedEntry 1 }

	svSchedVolume	OBJECT-TYPE
	SYNTAX		DisplayString
	ACCESS		read-only
	STATUS		mandatory
	DESCRIPTION
		"The name of the volume on the snapvault for the 
		 snapvault schedule. This does not have a /vol/ prefix."
	    
	::= { snapvaultSchedEntry 2 }

	svSchedSnapshot	OBJECT-TYPE
	SYNTAX		DisplayString
	ACCESS		read-only
	STATUS		mandatory
	DESCRIPTION
		"The name of the snapshot for the snapvault schedule."

	::= { snapvaultSchedEntry 3 }

	svSchedStatus	OBJECT-TYPE
	SYNTAX		INTEGER {
				idle(1),
				queued(2),
				active(3),
				aborting(4)
				}
	ACCESS		read-only
	STATUS		mandatory
	DESCRIPTION
		"Current status of the snapvault schedule."

	::= { snapvaultSchedEntry 4 }

	svSchedType	OBJECT-TYPE
	SYNTAX		INTEGER {
				undef(1),
				xfer(2),
				create(3)
				}
	ACCESS		read-only
	STATUS		mandatory
	DESCRIPTION
		"The type of the snapvault schedule."

	::= { snapvaultSchedEntry 5 }


	svSchedSchedule	OBJECT-TYPE
	SYNTAX		DisplayString
	ACCESS		read-only
	STATUS		mandatory
	DESCRIPTION
		"The update schedule of the snapvault."

	::= { snapvaultSchedEntry 6 }

	svDrPrimaryIsLicensed	OBJECT-TYPE
	SYNTAX  	INTEGER {
				false(1),
				true(2)
			}
	ACCESS  	read-only
	STATUS		mandatory
	DESCRIPTION
		"Whether the snapvault disaster recovery primary is
		licensed on the filer."

	::= { snapvault 14 }

	-- -- -- -- -- -- -- --
	--  the ndmpd group  --
	-- -- -- -- -- -- -- --

	ndmpOn			OBJECT-TYPE
	SYNTAX			INTEGER { off(1), on(2) }
	ACCESS			read-only
	STATUS			mandatory
	DESCRIPTION
		"Indicates whether ndmpd has been turned on or not."
	::= { ndmp 1 }

	ndmpSessionOpened	OBJECT-TYPE
	SYNTAX			INTEGER 
	ACCESS			read-only
	STATUS			mandatory
	DESCRIPTION
		"Total number of ndmpd sessions currently opened.
		Sessions may be running backups, restores or neither."
	::= { ndmp 2 }

	ndmpBackupActive	OBJECT-TYPE
	SYNTAX			INTEGER 
	ACCESS			read-only
	STATUS			mandatory
	DESCRIPTION
		"Number of ndmpd backups currently active."
	::= { ndmp 3 }

	ndmpRestoreActive	OBJECT-TYPE
	SYNTAX			INTEGER 
	ACCESS			read-only
	STATUS			mandatory
	DESCRIPTION
		"Number of ndmpd restores currently active."
	::= { ndmp 4 }

	ndmpTapeActive		OBJECT-TYPE
	SYNTAX			INTEGER 
	ACCESS			read-only
	STATUS			mandatory
	DESCRIPTION
		"Number of tape drives currently active."
	::= { ndmp 5 }

	ndmpBackupSuccesses	OBJECT-TYPE
	SYNTAX			Counter 
	ACCESS			read-only
	STATUS			mandatory
	DESCRIPTION
		"Number of ndmpd backups that succeeded."
	::= { ndmp 6 }

	ndmpRestoreSuccesses	OBJECT-TYPE
	SYNTAX			Counter 
	ACCESS			read-only
	STATUS			mandatory
	DESCRIPTION
		"Number of ndmpd restores that succeeded."
	::= { ndmp 7 }

	ndmpBackupFailures	OBJECT-TYPE
	SYNTAX			Counter 
	ACCESS			read-only
	STATUS			mandatory
	DESCRIPTION
		"Number of ndmpd backups that failed."
	::= { ndmp 8 }

	ndmpRestoreFailures	OBJECT-TYPE
	SYNTAX			Counter
	ACCESS			read-only
	STATUS			mandatory
	DESCRIPTION
		"Number of ndmpd restores that failed."
	::= { ndmp 9 }

	ndmpBackupFailureReason	OBJECT-TYPE
	SYNTAX			DisplayString
	ACCESS			read-only
	STATUS			mandatory
	DESCRIPTION
		"When the ndmpBackupFailures value is non-zero, this string
		describes the reason for the most recent backup failure."
	::= { ndmp 10 }

	ndmpRestoreFailureReason	OBJECT-TYPE
	SYNTAX			DisplayString
	ACCESS			read-only
	STATUS			mandatory
	DESCRIPTION
		"When the ndmpRestoreFailures value is non-zero, this string
		describes the reason for the most recent restore failure."
	::= { ndmp 11 }

	-- -- -- -- -- -- -- --
	--  the ftpd group  --
	-- -- -- -- -- -- -- --

	ftpdOn			OBJECT-TYPE
	SYNTAX			INTEGER { off(1), on(2) }
	ACCESS			read-only
	STATUS			mandatory
	DESCRIPTION
		"Indicates whether ftpd has been turned on or not."
	::= { ftpd 1 }

 	ftpdCurrentConns	OBJECT-TYPE
	SYNTAX			INTEGER
	ACCESS			read-only
	STATUS			mandatory
	DESCRIPTION
			"Number of currently open TCP/IP connections to ftp daemon (active and idle)"
	::= { ftpd 2 }

 	ftpdMaxConns		OBJECT-TYPE
	SYNTAX			INTEGER
	ACCESS			read-only
	STATUS			mandatory
	DESCRIPTION
			"Number of maximum simultaneous TCP/IP connections to ftp daemon"
	::= { ftpd 3 }

 	ftpdTotalConns		OBJECT-TYPE
	SYNTAX			INTEGER
	ACCESS			read-only
	STATUS			mandatory
	DESCRIPTION
			"Number of total TCP/IP connections to ftp daemon"
	::= { ftpd 4 }

	-- -- -- -- -- -- -- --
	--  the fabric group  --
	-- -- -- -- -- -- -- --

	fabricInstances	OBJECT-TYPE
	SYNTAX			INTEGER
	ACCESS			read-only
	STATUS			mandatory
	DESCRIPTION
			"The number of distinct fabrics present."
	::= { fabric 1 }

	fabricTable	OBJECT-TYPE
	SYNTAX		SEQUENCE OF FabricEntry
	ACCESS		not-accessible
	STATUS		mandatory
	DESCRIPTION
			"Provide a list of fabrics."
	::= { fabric 2 }

	fabricEntry	OBJECT-TYPE
	SYNTAX		FabricEntry
	ACCESS		not-accessible
	STATUS		mandatory
	DESCRIPTION
			"Provide a report of current configuration and
			status of fabrics."

	INDEX	{ fabricIndex }
	::= { fabricTable 1 }

	FabricEntry ::=
	    SEQUENCE {
		fabricIndex
		    INTEGER,
		fabricStatus
		    INTEGER,
		fabricStatusMessage
		    DisplayString,
		fabricName
		    OCTET STRING (SIZE (8)),
		fabricOwner
		    INTEGER
	    }

	fabricIndex	OBJECT-TYPE
	SYNTAX		INTEGER (1..2147483647)
	ACCESS		read-only
	STATUS		mandatory
	DESCRIPTION
			"A number that identifies this fabric entry."
	::= { fabricEntry 1 }

	fabricStatus	OBJECT-TYPE
	SYNTAX		INTEGER {
				ok(1),
				faulty(2),
				unknown(3)
			}
	ACCESS		read-only
	STATUS		mandatory
	DESCRIPTION
			"This indicates the overall status of the SAN fabric(s)."
	::= { fabricEntry 2 }

	fabricStatusMessage	OBJECT-TYPE
	SYNTAX			DisplayString
	ACCESS			read-only
	STATUS			mandatory
	DESCRIPTION
			"A string describing the fabric status,
			including a description of the condition (if
			any) that caused the status to be anything
			other than ok(3)."
	::= { fabricEntry 3 }

	fabricName	OBJECT-TYPE
	SYNTAX		OCTET STRING (SIZE (8))
	ACCESS		read-only
	STATUS		mandatory
	DESCRIPTION
			"This is the WWN of the fabric."
	::= { fabricEntry 4 }

	fabricOwner	OBJECT-TYPE
	SYNTAX		INTEGER {
				netapp(1),
				other(2),
				unknown(3)
			}
	ACCESS		read-only
	STATUS		mandatory
	DESCRIPTION
			"This indicates who owns the management of
			the fabric."
	::= { fabricEntry 5 }

	switchTable	OBJECT-TYPE
	SYNTAX		SEQUENCE OF SwitchEntry
	ACCESS		not-accessible
	STATUS		mandatory
	DESCRIPTION
			"Provide a list of switches and hubs
			connected to the fabric."
	::= { fabric 3 }

	switchEntry	OBJECT-TYPE
	SYNTAX		SwitchEntry
	ACCESS		not-accessible
	STATUS		mandatory
	DESCRIPTION
			"Provide a report of current configuration and
			status of fabric interconnect elements.  This
			include switches and hubs."

	INDEX	{ switchFabricIndex, switchIndex }
	::= { switchTable 1 }

	SwitchEntry ::=
	    SEQUENCE {
		switchIndex
		    INTEGER,
		switchName
		    OCTET STRING (SIZE (8)),
		switchSymbolicName
		    OCTET STRING (SIZE (0..255)),
		switchType
		    INTEGER,
		switchDomain
		    INTEGER,
		switchManagementId
		    INTEGER,
		switchStatus
		    INTEGER,
		switchStatusMessage
		    DisplayString,
		switchLinkSpeed
		    INTEGER,
		switchHighPacketsProcessed
		    Counter,
		switchLowPacketsProcessed
		    Counter,
		switchHighPacketsRejected
		    Counter,
		switchLowPacketsRejected
		    Counter,
		switchFabricIndex
		    INTEGER
	    }

	switchIndex	OBJECT-TYPE
	SYNTAX		INTEGER (1..2147483647)
	ACCESS		read-only
	STATUS		mandatory
	DESCRIPTION
			"A number that identifies this switch entry."
	::= { switchEntry 1 }

	switchName	OBJECT-TYPE
	SYNTAX		OCTET STRING (SIZE (8))
	ACCESS		read-only
	STATUS		mandatory
	DESCRIPTION
			"This is the WWN of the switch."
	::= { switchEntry 2 }

	switchSymbolicName OBJECT-TYPE
	SYNTAX		OCTET STRING (SIZE (0..255))
	ACCESS		read-only
	STATUS		mandatory
	DESCRIPTION
			"This is the symbolic name of the switch."
	::= { switchEntry 3 }

	switchType	OBJECT-TYPE
	SYNTAX		INTEGER {
				hub(1),
				switch(2),
				unknown(3)
			}
	ACCESS		read-only
	STATUS		mandatory
	DESCRIPTION
			"The type of the switch."
	::= { switchEntry 4 }

	switchDomain	OBJECT-TYPE
	SYNTAX		INTEGER
	ACCESS		read-only
	STATUS		mandatory
	DESCRIPTION
			"The domain identifier of the switch."
	::= { switchEntry 5 }

	switchManagementId OBJECT-TYPE
	SYNTAX		INTEGER
	ACCESS		read-only
	STATUS		mandatory
	DESCRIPTION
			"The in-band management identifier of the switch."
	::= { switchEntry 6 }

	switchStatus	OBJECT-TYPE
	SYNTAX		INTEGER {
				other(1),
				unknown(2),
				ok(3),
				nonCritical(4),
				critical(5),
				nonRecoverable(6)
			}
	ACCESS		read-only
	STATUS		mandatory
	DESCRIPTION
			"The current status of the switch."
	::= { switchEntry 7 }

	switchStatusMessage	OBJECT-TYPE
	SYNTAX			DisplayString
	ACCESS			read-only
	STATUS			mandatory
	DESCRIPTION
			"A string describing the switch status,
			including a description of the condition (if
			any) that caused the status to be anything
			other than ok(3)."
	::= { switchEntry 8 }

	switchLinkSpeed OBJECT-TYPE
	SYNTAX		INTEGER
	ACCESS		read-only
	STATUS		mandatory
	DESCRIPTION
			"The link speed of the switch.  The value is an integer
			whose units are Gbits (for example, a value of 2 represents
			a link speed of 2 Gbit)."
	::= { switchEntry 9 }

	switchHighPacketsProcessed OBJECT-TYPE
	SYNTAX		Counter
	ACCESS		read-only
	STATUS		mandatory
	DESCRIPTION	
			"Number of Packets successfully processed
			since the last reboot/reset of the switch.
			This object returns the most
			significant 32 bits of the 64 bit unsigned integer."
	::= { switchEntry 10 }

	switchLowPacketsProcessed OBJECT-TYPE
	SYNTAX		Counter
	ACCESS		read-only
	STATUS		mandatory
	DESCRIPTION	
			"Number of Packets successfully processed
			since the last reboot/reset of the switch.
			This object returns the least
			significant 32 bits of the 64 bit unsigned integer."
	::= { switchEntry 11 }

	switchHighPacketsRejected OBJECT-TYPE
	SYNTAX		Counter
	ACCESS		read-only
	STATUS		mandatory
	DESCRIPTION	
			"Number of Packets rejected
			since the last reboot/reset of the switch.
			This object returns the most
			significant 32 bits of the 64 bit unsigned integer."
	::= { switchEntry 12 }

	switchLowPacketsRejected OBJECT-TYPE
	SYNTAX		Counter
	ACCESS		read-only
	STATUS		mandatory
	DESCRIPTION	
			"Number of Packets rejected
			since the last reboot/reset of the switch.
			This object returns the least
			significant 32 bits of the 64 bit unsigned integer."
	::= { switchEntry 13 }

	switchFabricIndex	OBJECT-TYPE
	SYNTAX		INTEGER (1..2147483647)
	ACCESS		read-only
	STATUS		mandatory
	DESCRIPTION	
			"The index of the fabric on which this switch
			resides.  The value ranges from 1 to the value
			of fabricInstances."
	::= { switchEntry 14 }

	portTable	OBJECT-TYPE
	SYNTAX		SEQUENCE OF PortEntry
	ACCESS		not-accessible
	STATUS		mandatory
	DESCRIPTION
			"Provide a list of ports
			connected to the fabric."
	::= { fabric 4 }

	portEntry	OBJECT-TYPE
	SYNTAX		PortEntry
	ACCESS		not-accessible
	STATUS		mandatory
	DESCRIPTION
			"Provide a report of current configuration and
			status of ports in the fabric."

	INDEX	{ portFabricIndex, portSwitchIndex, portIndex }
	::= { portTable 1 }

	PortEntry ::=
	    SEQUENCE {
		portIndex
		    INTEGER,
		portName
		    OCTET STRING (SIZE (8)),
		portSwitchIndex
		    INTEGER,
		portSwitchName
		    OCTET STRING (SIZE (8)),
		portNumber
		    INTEGER,
		portType
		    INTEGER,
		portState
		    INTEGER,
		portFabricIndex
		    INTEGER
	    }

	portIndex	OBJECT-TYPE
	SYNTAX		INTEGER (1..2147483647)
	ACCESS		read-only
	STATUS		mandatory
	DESCRIPTION
			"A number that identifies this port entry."
	::= { portEntry 1 }

	portName	OBJECT-TYPE
	SYNTAX		OCTET STRING (SIZE (8))
	ACCESS		read-only
	STATUS		mandatory
	DESCRIPTION
			"This is the WWN of the port."
	::= { portEntry 2 }

	portSwitchIndex	OBJECT-TYPE
	SYNTAX		INTEGER (1..2147483647)
	ACCESS		read-only
	STATUS		mandatory
	DESCRIPTION	
			"The index of the switch on which this port
			resides.  The value ranges from 1 to the number of
			of switches."
	::= { portEntry 3 }

	portSwitchName	OBJECT-TYPE
	SYNTAX		OCTET STRING (SIZE (8))
	ACCESS		read-only
	STATUS		mandatory
	DESCRIPTION
			"This is the WWN of the switch to which
			the port is attached."
	::= { portEntry 4 }

	portNumber	OBJECT-TYPE
	SYNTAX		INTEGER
	ACCESS		read-only
	STATUS		mandatory
	DESCRIPTION
			"The port number on the switch."
	::= { portEntry 5 }

	portType	OBJECT-TYPE
	SYNTAX		INTEGER {
				unidentified(1),
				n-port(2),
				nl-port(3),
				f-port(4),
				fl-port(5),
				e-port(6),
				b-port(7)
			}
	ACCESS		read-only
	STATUS		mandatory
	DESCRIPTION
			"The type of the port."
	::= { portEntry 6 }

	portState	OBJECT-TYPE
	SYNTAX		INTEGER {
				online(1),
				offline(2),
				testing(3),
				faulty(4),
				unknown(5)
			}
	ACCESS		read-only
	STATUS		mandatory
	DESCRIPTION
			"The current state of the port."
	::= { portEntry 7 }

	portFabricIndex	OBJECT-TYPE
	SYNTAX		INTEGER (1..2147483647)
	ACCESS		read-only
	STATUS		mandatory
	DESCRIPTION	
			"The index of the fabric on which this port
			resides.  The value ranges from 1 to the value
			of fabricInstances."
	::= { portEntry 8 }

	-- -- -- -- -- -- -- -- -- -- -- -- --
	-- The backup(dump/restore) group   --
	-- -- -- -- -- -- -- -- -- -- -- -- --

	dump	OBJECT	IDENTIFIER ::= { backup 1 }

	restore OBJECT	IDENTIFIER ::= { backup 2 }

	-- dump --

	dmpActives		OBJECT-TYPE
	SYNTAX			INTEGER
	ACCESS			read-only
	STATUS			mandatory
	DESCRIPTION
		"Number of active dump."
	::= { dump 1 }

	dmpAttempts		OBJECT-TYPE
	SYNTAX			Counter
	ACCESS			read-only
	STATUS			mandatory
	DESCRIPTION
		"Number of dump attempted."
	::= { dump 2 }

	dmpSuccesses		OBJECT-TYPE
	SYNTAX			Counter
	ACCESS			read-only
	STATUS			mandatory
	DESCRIPTION
		"Number of dump succeeded."
	::= { dump 3 }

	dmpFailures		OBJECT-TYPE
	SYNTAX			Counter
	ACCESS			read-only
	STATUS			mandatory
	DESCRIPTION
		"Number of dump failed."
	::= { dump 4 }

	dmpTable		OBJECT-TYPE
	SYNTAX			SEQUENCE OF DmpSubtreeEntry
	ACCESS			not-accessible
	STATUS			mandatory
	DESCRIPTION
				"Provides a report of dumps on each
				 dump subtree."
	::= { dump 5 }

	dmpSubtreeEntry		OBJECT-TYPE
	SYNTAX			DmpSubtreeEntry
	ACCESS			not-accessible
	STATUS			mandatory
	DESCRIPTION
				"Shows statistics of dumps on an unique
				 dump subtree."
	INDEX	{ dmpIndex }
	::= { dmpTable 1 }

	DmpSubtreeEntry ::=
	    SEQUENCE {
	    	dmpIndex
			INTEGER,
	    	dmpStPath
			DisplayString,
		dmpStAttempts
			Counter,
		dmpStSuccesses
			Counter,
		dmpStFailures
			Counter,
		lastdump
			OBJECT IDENTIFIER,
		lastsuccess
			OBJECT IDENTIFIER
	    }

	dmpIndex		OBJECT-TYPE
	SYNTAX			INTEGER (1..2147483647)
	ACCESS			read-only
	STATUS			mandatory
	DESCRIPTION
				"Index into the subtree dump table."
	::= { dmpSubtreeEntry 1 }

	dmpStPath		OBJECT-TYPE
	SYNTAX			DisplayString
	ACCESS			read-only
	STATUS			mandatory
	DESCRIPTION
				"The full path to the dump subtree. In the
				 format of /vol/<volname>/..."
	::= { dmpSubtreeEntry 2 }

	dmpStAttempts		OBJECT-TYPE
	SYNTAX			Counter
	ACCESS			read-only
	STATUS			mandatory
	DESCRIPTION
				"No. of dump attempted for the subtree."
	::= { dmpSubtreeEntry 3 }

	dmpStSuccesses		OBJECT-TYPE
	SYNTAX			Counter
	ACCESS			read-only
	STATUS			mandatory
	DESCRIPTION
				"No. of dump succeeded for the subtree."
	::= { dmpSubtreeEntry 4 }

	dmpStFailures		OBJECT-TYPE
	SYNTAX			Counter
	ACCESS			read-only
	STATUS			mandatory
	DESCRIPTION
				"No. of dump failed for the subtree."
	::= { dmpSubtreeEntry 5 }

	lastdump	OBJECT IDENTIFIER ::= { dmpSubtreeEntry 6 }
	lastsuccess	OBJECT IDENTIFIER ::= { dmpSubtreeEntry 7 }

	dmpTime			OBJECT-TYPE
	SYNTAX			INTEGER
	ACCESS			read-only
	STATUS			mandatory
	DESCRIPTION
				"The start time for the last attempt
				 to dump the subtree, including the
				 currently running one. The time in
				 seconds since January 1, 1970."
	::= { lastdump 1 }

	dmpStatus		OBJECT-TYPE
	SYNTAX			INTEGER { active(1), restartable(2), success(3), failed(4) }
	ACCESS			read-only
	STATUS			mandatory
	DESCRIPTION		"The status for the last dump attempt
				 on the subtree."
	::= { lastdump 2 }

	dmpLevel		OBJECT-TYPE
	SYNTAX			INTEGER (0..9)
	ACCESS			read-only
	STATUS			mandatory
	DESCRIPTION
				"The level of the dump."
	::= { lastsuccess 1 }

	dmpNumFiles		OBJECT-TYPE
	SYNTAX			INTEGER
	ACCESS			read-only
	STATUS			mandatory
	DESCRIPTION
				"The number of files dumped."
	::= { lastsuccess 2 }

	dmpDataAmount		OBJECT-TYPE
	SYNTAX			INTEGER
	ACCESS			read-only
	STATUS			mandatory
	DESCRIPTION
				"The amount of data dumped, in Megabytes."
	::= { lastsuccess 3 }

	dmpStartTime		OBJECT-TYPE
	SYNTAX			INTEGER
	ACCESS			read-only
	STATUS			mandatory
	DESCRIPTION
				"The start time of the dump. The time is
				 in seconds since January 1, 1970."
	::= { lastsuccess 4 }

	dmpDuration		OBJECT-TYPE
	SYNTAX			TimeTicks
	ACCESS			read-only
	STATUS			mandatory
	DESCRIPTION
				"The duration of the dump."
	::= { lastsuccess 5 }
		

	-- restore --

	rstActives		OBJECT-TYPE
	SYNTAX			INTEGER
	ACCESS			read-only
	STATUS			mandatory
	DESCRIPTION
		"Number of active restore."
	::= { restore 1 }

	rstAttempts		OBJECT-TYPE
	SYNTAX			Counter
	ACCESS			read-only
	STATUS			mandatory
	DESCRIPTION
		"Number of restore attempted."
	::= { restore 2 }

	rstSuccesses		OBJECT-TYPE
	SYNTAX			Counter
	ACCESS			read-only
	STATUS			mandatory
	DESCRIPTION
		"Number of restore succeeded."
	::= { restore 3 }

	rstFailures		OBJECT-TYPE
	SYNTAX			Counter
	ACCESS			read-only
	STATUS			mandatory
	DESCRIPTION
		"Number of restore failed."
	::= { restore 4 }

	-- -- -- -- -- -- -- --
	-- DAFS Option group --
	-- -- -- -- -- -- -- --

	dafsOptions		OBJECT IDENTIFIER ::= {dafs 1}
	  
	dafsIsLicensed	OBJECT-TYPE
	SYNTAX  INTEGER {
				false(1),
				true(2)
			}
	ACCESS  read-only
	STATUS  optional
	DESCRIPTION
		"Whether the dafs protocol is licensed on the filer.
		Data OnTap Specific"
	::= { dafsOptions 1 }

	dafsMaxRequestsServer OBJECT-TYPE
	SYNTAX	INTEGER
	ACCESS	read-only
	STATUS	optional
	DESCRIPTION
		"Server wide maximum number of concurrent requests
		Data OnTap Specific"
	::= { dafsOptions 2 }

	dafsMaxRequests OBJECT-TYPE
	SYNTAX	INTEGER
	ACCESS	read-only
	STATUS	optional
	DESCRIPTION
		"Server maximum number of concurrent requests per session
		Data OnTap Specific"
	::= { dafsOptions 3 }

	dafsMaxRequestSize OBJECT-TYPE
	SYNTAX	INTEGER
	ACCESS	read-only
	STATUS	mandatory
	DESCRIPTION
		"Server maximum size of an inline request"
	::= { dafsOptions 4 }

	dafsMaxResponseSize OBJECT-TYPE
	SYNTAX	INTEGER
	ACCESS	read-only
	STATUS	mandatory
	DESCRIPTION
		"Server maximum size of an inline response"
	::= { dafsOptions 5 }


	dafsMaxPendingRequestsServer OBJECT-TYPE
	SYNTAX	INTEGER
	ACCESS	read-only
	STATUS	optional
	DESCRIPTION
		"Server wide maximum number of requests that can queue
		waiting for resources Data OnTap Specific"
	::= { dafsOptions 6 }

	dafsUseChecksums OBJECT-TYPE
	SYNTAX	INTEGER	{
				false(1),
				true(2)
			}
	ACCESS	read-only
	STATUS	mandatory
	DESCRIPTION
		"Server uses checksums"
	::= { dafsOptions 7 }

	dafsNicNumRequestDemons OBJECT-TYPE
	SYNTAX	INTEGER
	ACCESS	read-only
	STATUS	optional
	DESCRIPTION
		"Server default number of request demons per Nic.
		Data OnTap Specific"
	::= { dafsOptions 8 }

	dafsAnonymousAuthentication OBJECT-TYPE
	SYNTAX	INTEGER	{
				false(1),
				true(2)
			}
	ACCESS	read-only
	STATUS	mandatory
	DESCRIPTION
		"Allow the server to acception connections with
		authentication type NONE."
	::= { dafsOptions 9 }

	dafsServerEnabled OBJECT-TYPE
	SYNTAX	INTEGER	{
				false(1),
				true(2)
			}
	ACCESS	read-only
	STATUS	mandatory
	DESCRIPTION
		"Current status of the DAFS server. If true, the DAFS
		server is running."
	::= { dafsOptions 10 }

	dafsDefaultUid OBJECT-TYPE
	SYNTAX	INTEGER	
	ACCESS	read-only
	STATUS	mandatory
	DESCRIPTION
		"Default client User ID if anonymously connected."
	::= { dafsOptions 11 }

	dafsDefaultGid OBJECT-TYPE
	SYNTAX	INTEGER	
	ACCESS	read-only
	STATUS	mandatory
	DESCRIPTION
		"Default client Group ID if anonymously connected."
	::= { dafsOptions 12 }

	dafsMaxDisconnectedSessions OBJECT-TYPE
	SYNTAX	INTEGER	
	ACCESS	read-only
	STATUS	mandatory
	DESCRIPTION
		"Maximum number of disconnected sessions for which the
		DAFS server will retain response cache data."
	::= { dafsOptions 13 }

        dafsMaxIdleSeconds OBJECT-TYPE
        SYNTAX  INTEGER
        ACCESS  read-only
        STATUS  mandatory
        DESCRIPTION
                "Maximum number of seconds server will keep a session
                open without hearing from the client."
        ::= { dafsOptions 14 }

	-- the DAFS VI Nic table

	-- The DAFS VI Nic table contains information about this
	-- entity's VI nics attached to DAFS

	dafsNicTable OBJECT-TYPE
	SYNTAX	SEQUENCE OF DafsNicEntry
	ACCESS	not-accessible
	STATUS	mandatory
	DESCRIPTION
                      "A table containing DAFS NIC specific
                      information."
       	::= { dafs 2 }

	dafsNicEntry OBJECT-TYPE
	SYNTAX	DafsNicEntry
	ACCESS	not-accessible
	STATUS	mandatory
	DESCRIPTION
                      "Information about a particular current DAFS
                      nic.  An object of this type is transient,
                      in that it ceases to exist when (or soon after)
                      the nic is detached."
	INDEX   { dafsNicIndex }
              ::= { dafsNicTable 1 }

	DafsNicEntry ::=
	SEQUENCE	{
			dafsNicIndex
				INTEGER,
			dafsNicName
				DisplayString,
			dafsNicDevice
				DisplayString,
			dafsNicState
				INTEGER,
			dafsNicListenAddr
				OCTET STRING,
			dafsNicNumRqstDemons
				INTEGER,
			dafsNicInBytes
				Counter,
			dafsNicDirectInBytes
				Counter,
			dafsNicOutBytes
				Counter,
			dafsNicDirectOutBytes
				Counter
			}

	dafsNicIndex OBJECT-TYPE
	SYNTAX	INTEGER (1..2147483647)
	ACCESS	read-only
	STATUS	mandatory
	DESCRIPTION
                      "A unique value for each interface.  Its value
                      ranges between 1 and the value of DafsNicNumber.  The
                      value for each interface must remain constant at
                      least from one re-initialization of the entity's
                      network management system to the next re-
                      initialization."
	::= { dafsNicEntry 1 }

	dafsNicName OBJECT-TYPE
	SYNTAX	DisplayString (SIZE (0..255))
	ACCESS	read-only
	STATUS	mandatory
	DESCRIPTION
                      "A textual string containing the logical name 
                      under which the nic has been attached."
	::= { dafsNicEntry 2}

	dafsNicDevice OBJECT-TYPE
	SYNTAX	DisplayString (SIZE (0..255))
	ACCESS	read-only
	STATUS	mandatory
	DESCRIPTION
                      "A textual string containing the physical name
                      of the nic that has been attached."
	::= { dafsNicEntry 3}

	dafsNicState OBJECT-TYPE
	SYNTAX	INTEGER	{
				up(1), 	-- ready to pass packets
				down(2),
				testing(3) -- in some test mode
			}
	ACCESS	read-only
	STATUS	mandatory
	DESCRIPTION
		"Current state of DAFS nic"
	::= { dafsNicEntry 4 }

	dafsNicListenAddr OBJECT-TYPE
	SYNTAX	OCTET STRING
	ACCESS	read-only
	STATUS	mandatory
	DESCRIPTION
                      "Transport specific address structure giving the
		      DAFS listen address for this NIC."
	::= { dafsNicEntry 5}


	dafsNicNumRqstDemons OBJECT-TYPE
	SYNTAX	INTEGER
	ACCESS	read-only
	STATUS	optional
	DESCRIPTION
                      "Number of request demons assigned to this Nic
		      to handle Nic related events. Data OnTap Specific"
	::= { dafsNicEntry 6}

	dafsNicInBytes OBJECT-TYPE
	SYNTAX	Counter
	ACCESS	read-only
	STATUS	mandatory
	DESCRIPTION
                      "Total number of bytes, include DMA, received on
		      this interface"
	::= { dafsNicEntry 7}

	dafsNicDirectInBytes OBJECT-TYPE
	SYNTAX	Counter
	ACCESS	read-only
	STATUS	mandatory
	DESCRIPTION
                      "Total number of bytes read directly from the
		      peer memory through this interface"
	::= { dafsNicEntry 8}

	dafsNicOutBytes OBJECT-TYPE
	SYNTAX	Counter
	ACCESS	read-only
	STATUS	mandatory
	DESCRIPTION
                      "Total number of bytes, include DMA, sent on
		      this interface"
	::= { dafsNicEntry 9}

	dafsNicDirectOutBytes OBJECT-TYPE
	SYNTAX	Counter
	ACCESS	read-only
	STATUS	mandatory
	DESCRIPTION
                      "Total number of bytes written directly to the
		      peer memory through this interface"
	::= { dafsNicEntry 10}

	-- -- -- -- -- -- -- -- -- --
	-- DAFS Server Statistics  --
	-- -- -- -- -- -- -- -- -- --

	curDafs	OBJECT IDENTIFIER ::= {dafs 3}

	dafsPendingRequests	OBJECT-TYPE
	SYNTAX	INTEGER
	ACCESS	read-only
	STATUS	optional
	DESCRIPTION
		"Server wide current number of requests that are
		queued waiting for resources Data OnTap Specific"
	::= { curDafs 1 }

	dafsCurrentRequests	OBJECT-TYPE
	SYNTAX	INTEGER
	ACCESS	read-only
	STATUS	optional
	DESCRIPTION
		"Server wide current number of active requests
		Data OnTap Specific"
	::= { curDafs 2 }

	totDafs	OBJECT IDENTIFIER ::= {dafs 4}

	dafsCalls OBJECT-TYPE
	SYNTAX	Counter
	ACCESS	read-only
	STATUS	mandatory
	DESCRIPTION
		"Total number of DAFS calls since last reboot"
	::= { totDafs 1 }

	dafsClientAuths	OBJECT-TYPE
	SYNTAX	Counter
	ACCESS	read-only
	STATUS	mandatory
	DESCRIPTION
		"Total number of Client Auth calls since last reboot"
	::= { totDafs 2 }

	dafsClientConnects	OBJECT-TYPE
	SYNTAX	Counter
	ACCESS	read-only
	STATUS	mandatory
	DESCRIPTION
		"Total number of Client Connect calls since last reboot"
	::= { totDafs 3 }

	dafsClientConnectAuths	OBJECT-TYPE
	SYNTAX	Counter
	ACCESS	read-only
	STATUS	mandatory
	DESCRIPTION
		"Total number of Client Connect Auth calls since last reboot"
	::= { totDafs 4 }

	dafsConnectBinds	OBJECT-TYPE
	SYNTAX	Counter
	ACCESS	read-only
	STATUS	mandatory
	DESCRIPTION
		"Total number of Connect Bind calls since last reboot"
	::= { totDafs 5 }

	dafsDisconnects	OBJECT-TYPE
	SYNTAX	Counter
	ACCESS	read-only
	STATUS	mandatory
	DESCRIPTION
		"Total number of Disconnect calls since last reboot"
	::= { totDafs 6 }

	dafsRegisterCreds	OBJECT-TYPE
	SYNTAX	Counter
	ACCESS	read-only
	STATUS	mandatory
	DESCRIPTION
		"Total number of Register Credential calls since last reboot"
	::= { totDafs 7 }

	dafsReleaseCreds	OBJECT-TYPE
	SYNTAX	Counter
	ACCESS	read-only
	STATUS	mandatory
	DESCRIPTION
		"Total number of Release Credential calls since last reboot"
	::= { totDafs 8 }

	dafsSecinfos	OBJECT-TYPE
	SYNTAX	Counter
	ACCESS	read-only
	STATUS	mandatory
	DESCRIPTION
		"Total number of Secinfo calls since last reboot"
	::= { totDafs 9 }

	dafsServerAuths	OBJECT-TYPE
	SYNTAX	Counter
	ACCESS	read-only
	STATUS	mandatory
	DESCRIPTION
		"Total number of Server Auth calls since last reboot"
	::= { totDafs 10 }

	dafsCheckResponses	OBJECT-TYPE
	SYNTAX	Counter
	ACCESS	read-only
	STATUS	mandatory
	DESCRIPTION
		"Total number of Check Response calls since last reboot"
	::= { totDafs 11 }

	dafsFetchResponses	OBJECT-TYPE
	SYNTAX	Counter
	ACCESS	read-only
	STATUS	mandatory
	DESCRIPTION
		"Total number of Fetch Response calls since last reboot"
	::= { totDafs 12 }

	dafsDiscardResponses	OBJECT-TYPE
	SYNTAX	Counter
	ACCESS	read-only
	STATUS	mandatory
	DESCRIPTION
		"Total number of Discard Responses calls since last reboot"
	::= { totDafs 13 }

	dafsAccesses	OBJECT-TYPE
	SYNTAX	Counter
	ACCESS	read-only
	STATUS	mandatory
	DESCRIPTION
		"Total number of Access calls since last reboot"
	::= { totDafs 14 }

	dafsCacheHints	OBJECT-TYPE
	SYNTAX	Counter
	ACCESS	read-only
	STATUS	mandatory
	DESCRIPTION
		"Total number of Cache Hint calls since last reboot"
	::= { totDafs 15 }

	dafsCloses	OBJECT-TYPE
	SYNTAX	Counter
	ACCESS	read-only
	STATUS	mandatory
	DESCRIPTION
		"Total number of Close calls since last reboot"
	::= { totDafs 16 }

	dafsCommits	OBJECT-TYPE
	SYNTAX	Counter
	ACCESS	read-only
	STATUS	mandatory
	DESCRIPTION
		"Total number of Commit calls since last reboot"
	::= { totDafs 17 }

	dafsCreates	OBJECT-TYPE
	SYNTAX	Counter
	ACCESS	read-only
	STATUS	mandatory
	DESCRIPTION
		"Total number of Create calls since last reboot"
	::= { totDafs 18 }

	dafsDelegPurges	OBJECT-TYPE
	SYNTAX	Counter
	ACCESS	read-only
	STATUS	mandatory
	DESCRIPTION
		"Total number of Delegate Purge calls since last reboot"
	::= { totDafs 19 }

	dafsDelegReturns	OBJECT-TYPE
	SYNTAX	Counter
	ACCESS	read-only
	STATUS	mandatory
	DESCRIPTION
		"Total number of Delegate Return calls since last reboot"
	::= { totDafs 20 }

	dafsGetFsattrs	OBJECT-TYPE
	SYNTAX	Counter
	ACCESS	read-only
	STATUS	mandatory
	DESCRIPTION
		"Total number of Get Fsattr  calls since last reboot"
	::= { totDafs 21 }

	dafsGetRootHandles	OBJECT-TYPE
	SYNTAX	Counter
	ACCESS	read-only
	STATUS	mandatory
	DESCRIPTION
		"Total number of Get Root Handle calls since last reboot"
	::= { totDafs 22 }

	dafsGetattrInlines	OBJECT-TYPE
	SYNTAX	Counter
	ACCESS	read-only
	STATUS	mandatory
	DESCRIPTION
		"Total number of Getattr Inline calls since last reboot"
	::= { totDafs 23 }

	dafsGetattrDirects	OBJECT-TYPE
	SYNTAX	Counter
	ACCESS	read-only
	STATUS	mandatory
	DESCRIPTION
		"Total number of Getattr Direct calls since last reboot"
	::= { totDafs 24 }

	dafsLinks	OBJECT-TYPE
	SYNTAX	Counter
	ACCESS	read-only
	STATUS	mandatory
	DESCRIPTION
		"Total number of Link calls since last reboot"
	::= { totDafs 25 }

	dafsLocks	OBJECT-TYPE
	SYNTAX	Counter
	ACCESS	read-only
	STATUS	mandatory
	DESCRIPTION
		"Total number of Lock calls since last reboot"
	::= { totDafs 26 }

	dafsLockts	OBJECT-TYPE
	SYNTAX	Counter
	ACCESS	read-only
	STATUS	mandatory
	DESCRIPTION
		"Total number of LockT calls since last reboot"
	::= { totDafs 27}

	dafsLockus	OBJECT-TYPE
	SYNTAX	Counter
	ACCESS	read-only
	STATUS	mandatory
	DESCRIPTION
		"Total number of LockU calls since last reboot"
	::= { totDafs 28 }

	dafsLookUps	OBJECT-TYPE
	SYNTAX	Counter
	ACCESS	read-only
	STATUS	mandatory
	DESCRIPTION
		"Total number of LookUp calls since last reboot"
	::= { totDafs 29 }

	dafsLookUpps	OBJECT-TYPE
	SYNTAX	Counter
	ACCESS	read-only
	STATUS	mandatory
	DESCRIPTION
		"Total number of LookUpp calls since last reboot"
	::= { totDafs 30 }

	dafsNulls	OBJECT-TYPE
	SYNTAX	Counter
	ACCESS	read-only
	STATUS	mandatory
	DESCRIPTION
		"Total number of Null calls since last reboot"
	::= { totDafs 31 }

	dafsNverifys	OBJECT-TYPE
	SYNTAX	Counter
	ACCESS	read-only
	STATUS	mandatory
	DESCRIPTION
		"Total number of Nverify calls since last reboot"
	::= { totDafs 32 }

	dafsOpens	OBJECT-TYPE
	SYNTAX	Counter
	ACCESS	read-only
	STATUS	mandatory
	DESCRIPTION
		"Total number of Open calls since last reboot"
	::= { totDafs 33 }

	dafsOpenDowngrades	OBJECT-TYPE
	SYNTAX	Counter
	ACCESS	read-only
	STATUS	mandatory
	DESCRIPTION
		"Total number of Open Downgrade calls since last reboot"
	::= { totDafs 34 }

	dafsOpenattrs	OBJECT-TYPE
	SYNTAX	Counter
	ACCESS	read-only
	STATUS	mandatory
	DESCRIPTION
		"Total number of Openattr calls since last reboot"
	::= { totDafs 35 }

	dafsReadInlines	OBJECT-TYPE
	SYNTAX	Counter
	ACCESS	read-only
	STATUS	mandatory
	DESCRIPTION
		"Total number of Read Inline calls since last reboot"
	::= { totDafs 36 }

	dafsReadDirects	OBJECT-TYPE
	SYNTAX	Counter
	ACCESS	read-only
	STATUS	mandatory
	DESCRIPTION
		"Total number of Read Direct calls since last reboot"
	::= { totDafs 37 }

	dafsReaddirInlines	OBJECT-TYPE
	SYNTAX	Counter
	ACCESS	read-only
	STATUS	mandatory
	DESCRIPTION
		"Total number of Readdir Inline calls since last reboot"
	::= { totDafs 38 }

	dafsReaddirDirects	OBJECT-TYPE
	SYNTAX	Counter
	ACCESS	read-only
	STATUS	mandatory
	DESCRIPTION
		"Total number of Readdir Direct calls since last reboot"
	::= { totDafs 39 }

	dafsReadlinkInlines	OBJECT-TYPE
	SYNTAX	Counter
	ACCESS	read-only
	STATUS	mandatory
	DESCRIPTION
		"Total number of Readlink Inline calls since last reboot"
	::= { totDafs 40 }

	dafsReadlinkDirects	OBJECT-TYPE
	SYNTAX	Counter
	ACCESS	read-only
	STATUS	mandatory
	DESCRIPTION
		"Total number of Readlink Direct calls since last reboot"
	::= { totDafs 41 }

	dafsRemoves	OBJECT-TYPE
	SYNTAX	Counter
	ACCESS	read-only
	STATUS	mandatory
	DESCRIPTION
		"Total number of Remove calls since last reboot"
	::= { totDafs 42 }

	dafsRenames	OBJECT-TYPE
	SYNTAX	Counter
	ACCESS	read-only
	STATUS	mandatory
	DESCRIPTION
		"Total number of Rename calls since last reboot"
	::= { totDafs 43 }

	dafsSetattrInlines	OBJECT-TYPE
	SYNTAX	Counter
	ACCESS	read-only
	STATUS	mandatory
	DESCRIPTION
		"Total number of Setattr Inline calls since last reboot"
	::= { totDafs 44 }

	dafsSetattrDirects	OBJECT-TYPE
	SYNTAX	Counter
	ACCESS	read-only
	STATUS	mandatory
	DESCRIPTION
		"Total number of Setattr Direct calls since last reboot"
	::= { totDafs 45 }

	dafsVerifys	OBJECT-TYPE
	SYNTAX	Counter
	ACCESS	read-only
	STATUS	mandatory
	DESCRIPTION
		"Total number of Verify calls since last reboot"
	::= { totDafs 46 }

	dafsBatchSubmits	OBJECT-TYPE
	SYNTAX	Counter
	ACCESS	read-only
	STATUS	mandatory
	DESCRIPTION
		"Total number of Batch Submit calls since last reboot"
	::= { totDafs 47 }

	dafsWriteInlines	OBJECT-TYPE
	SYNTAX	Counter
	ACCESS	read-only
	STATUS	mandatory
	DESCRIPTION
		"Total number of Write Inline calls since last reboot"
	::= { totDafs 48 }

	dafsWriteDirects	OBJECT-TYPE
	SYNTAX	Counter
	ACCESS	read-only
	STATUS	mandatory
	DESCRIPTION
		"Total number of Write Direct calls since last reboot"
	::= { totDafs 49 }

	dafsBcGetattrs	OBJECT-TYPE
	SYNTAX	Counter
	ACCESS	read-only
	STATUS	mandatory
	DESCRIPTION
		"Total number of BC Getattr calls since last reboot"
	::= { totDafs 50 }

	dafsBcNulls	OBJECT-TYPE
	SYNTAX	Counter
	ACCESS	read-only
	STATUS	mandatory
	DESCRIPTION
		"Total number of BC Null calls since last reboot"
	::= { totDafs 51 }

	dafsBcRecalls	OBJECT-TYPE
	SYNTAX	Counter
	ACCESS	read-only
	STATUS	mandatory
	DESCRIPTION
		"Total number of BC Recall calls since last reboot"
	::= { totDafs 52 }

	dafsBcBatchCompletions	OBJECT-TYPE
	SYNTAX	Counter
	ACCESS	read-only
	STATUS	mandatory
	DESCRIPTION
		"Total number of BC Batch Completion calls since
		last reboot"
	::= { totDafs 53 }

        dafsAppendInlines     OBJECT-TYPE
        SYNTAX  Counter
        ACCESS  read-only
        STATUS  mandatory
        DESCRIPTION
                "Total number of Append Inline calls since
                last reboot"
        ::= { totDafs 54 }

        dafsAppendDirects     OBJECT-TYPE
        SYNTAX  Counter
        ACCESS  read-only
        STATUS  mandatory
        DESCRIPTION
                "Total number of Append Direct calls since
                last reboot"
        ::= { totDafs 55 }

        dafsGetFencingLists     OBJECT-TYPE
        SYNTAX  Counter
        ACCESS  read-only
        STATUS  mandatory
        DESCRIPTION
                "Total number of Get Fencing List calls since
                last reboot"
        ::= { totDafs 56 }

        dafsSetFencingLists     OBJECT-TYPE
        SYNTAX  Counter
        ACCESS  read-only
        STATUS  mandatory
        DESCRIPTION
                "Total number of Set Fencing List calls since
                last reboot"
        ::= { totDafs 57 }

        dafsHurryUps     OBJECT-TYPE
        SYNTAX  Counter
        ACCESS  read-only
        STATUS  mandatory
        DESCRIPTION
                "Total number of Hurry Up calls since
                last reboot"
        ::= { totDafs 58 }

	dafsInBytes	OBJECT-TYPE
	SYNTAX	Counter
	ACCESS	read-only
	STATUS	mandatory
	DESCRIPTION
		"Total number of bytes, including DMA, received since the
		last reboot"
	::= { totDafs 59 }

	dafsDirectInBytes	OBJECT-TYPE
	SYNTAX	Counter
	ACCESS	read-only
	STATUS	mandatory
	DESCRIPTION
		"Total number of bytes received directly into memory
		since last reboot"
	::= { totDafs 60 }

	dafsOutBytes	OBJECT-TYPE
	SYNTAX	Counter
	ACCESS	read-only
	STATUS	mandatory
	DESCRIPTION
		"Total number of bytes, including DMA, sent since the
		last reboot"
	::= { totDafs 61 }

	dafsDirectOutBytes	OBJECT-TYPE
	SYNTAX	Counter
	ACCESS	read-only
	STATUS	mandatory
	DESCRIPTION
		"Total number of bytes sent directly into remote memory since
		the last reboot"
	::= { totDafs 62 }

	dafsSessionTable OBJECT-TYPE
	SYNTAX	SEQUENCE OF DafsSessionEntry
	ACCESS	not-accessible
	STATUS	mandatory
	DESCRIPTION
                      "A table containing current DAFS client session
                      information."
       	::= { dafs 5 }

	dafsSessionEntry OBJECT-TYPE
	SYNTAX	DafsSessionEntry
	ACCESS	not-accessible
	STATUS	mandatory
	DESCRIPTION
                      "Information about a particular DAFS
                      session.  An object of this type is transient,
                      in that it ceases to exist when (or soon after)
                      the client disconnects."
                      
	INDEX   { dafsSessionIndex }
        ::= { dafsSessionTable 1 }

	DafsSessionEntry ::=
            SEQUENCE {
			dafsSessionIndex
				INTEGER,
			dafsSessionId
				OCTET STRING,
			dafsSessionEndian
				INTEGER,
			dafsSessionAllowBackChannel
				INTEGER,
			dafsSessionAllowRdmaReadChannel
				INTEGER,
			dafsSessionUseChecksums
				INTEGER,
			dafsSessionMaxCredentials
				INTEGER,
			dafsSessionMaxRequestSize
				INTEGER,
			dafsSessionMaxResponseSize
				INTEGER,
			dafsSessionMaxRequests
				INTEGER,
			dafsSessionInlineWriteHeaderSize
				INTEGER,
			dafsSessionClientIdString
				OCTET STRING,
			dafsSessionClientVerifier
				OCTET STRING,
			dafsSessionNumCredentials
				INTEGER,
			dafsSessionNumRequests
				INTEGER
	    }

	dafsSessionIndex OBJECT-TYPE
	SYNTAX	INTEGER (1..2147483647)
	ACCESS	read-only
	STATUS	mandatory
	DESCRIPTION
                      "A unique value for each session."
	::= { dafsSessionEntry 1 }

	dafsSessionId	OBJECT-TYPE
	SYNTAX	OCTET STRING
	ACCESS	read-only
	STATUS	mandatory
	DESCRIPTION
		"Session Identifier assigned by the server."
	::= { dafsSessionEntry 2 }

	dafsSessionEndian	OBJECT-TYPE
	SYNTAX	INTEGER {
	    			bigEndian(1),
				littleEndian(2)
	    		}
	ACCESS	read-only
	STATUS	mandatory
	DESCRIPTION
		"Byte order used on this session."
	::= { dafsSessionEntry 3 }

	dafsSessionAllowBackChannel	OBJECT-TYPE
	SYNTAX	INTEGER {
				false(1),
				true(2)
			}
	ACCESS	read-only
	STATUS	mandatory
	DESCRIPTION
		"Session may use a back control channel."
	::= { dafsSessionEntry 4 }

	dafsSessionAllowRdmaReadChannel	OBJECT-TYPE
	SYNTAX	INTEGER {
				false(1),
				true(2)
			}
	ACCESS	read-only
	STATUS	mandatory
	DESCRIPTION
		"Session may use a RDMA read channel."
	::= { dafsSessionEntry 5 }

	dafsSessionUseChecksums	OBJECT-TYPE
	SYNTAX	INTEGER {
				false(1),
				true(2)
			}
	ACCESS	read-only
	STATUS	mandatory
	DESCRIPTION
		"Session uses checksums."
	::= { dafsSessionEntry 6 }

	dafsSessionMaxCredentials	OBJECT-TYPE
	SYNTAX	INTEGER
	ACCESS	read-only
	STATUS	mandatory
	DESCRIPTION
		"Maximum number of credientials that can be registered
		on this session."
	::= { dafsSessionEntry 7 }

	dafsSessionMaxRequestSize	OBJECT-TYPE
	SYNTAX	INTEGER
	ACCESS	read-only
	STATUS	mandatory
	DESCRIPTION
		"Maximum size of a DAFS request."
	::= { dafsSessionEntry 8 }

	dafsSessionMaxResponseSize	OBJECT-TYPE
	SYNTAX	INTEGER
	ACCESS	read-only
	STATUS	mandatory
	DESCRIPTION
		"Maximum size of a DAFS response."
	::= { dafsSessionEntry 9 }

	dafsSessionMaxRequests	OBJECT-TYPE
	SYNTAX	INTEGER
	ACCESS	read-only
	STATUS	mandatory
	DESCRIPTION
		"Maximum number of concurrent requests."
	::= { dafsSessionEntry 10 }

	dafsSessionInlineWriteHeaderSize	OBJECT-TYPE
	SYNTAX	INTEGER
	ACCESS	read-only
	STATUS	mandatory
	DESCRIPTION
		"Size of DAFS headers plus padding to the start of
		data.  Used to better align inline data."
	::= { dafsSessionEntry 11 }

	dafsSessionClientIdString	OBJECT-TYPE
	SYNTAX	OCTET STRING (SIZE (32))
	ACCESS	read-only
	STATUS	mandatory
	DESCRIPTION
		"Client ID string supplied by the client.  Intended to
		uniquely identify that client."
	::= { dafsSessionEntry 12 }

	dafsSessionClientVerifier	OBJECT-TYPE
	SYNTAX	OCTET STRING (SIZE (8))
	ACCESS	read-only
	STATUS	mandatory
	DESCRIPTION
		"Supplied by the client to uniquely identify an
		instnce of a client."
	::= { dafsSessionEntry 13 }

	dafsSessionNumCredentials	OBJECT-TYPE
	SYNTAX	INTEGER
	ACCESS	read-only
	STATUS	mandatory
	DESCRIPTION
		"Current number of credentials registered on this
		session"
	::= { dafsSessionEntry 14 }

	dafsSessionNumRequests	OBJECT-TYPE
	SYNTAX	INTEGER
	ACCESS	read-only
	STATUS	mandatory
	DESCRIPTION
		"Current number of active requests on this session"
	::= { dafsSessionEntry 15 }

	-- the DAFS Export table

	-- The DAFS Export table contains information about this
	-- entity's exported filesystems

	dafsExportTable OBJECT-TYPE
	SYNTAX	SEQUENCE OF DafsExportEntry
	ACCESS	not-accessible
	STATUS	mandatory
	DESCRIPTION
                      "A table containing DAFS Export filesystems."
       	::= { dafs 6 }

	dafsExportEntry OBJECT-TYPE
	SYNTAX	DafsExportEntry
	ACCESS	not-accessible
	STATUS	mandatory
	DESCRIPTION
                      "Information about a particular current DAFS
                      export.  An object of this type is transient,
                      in that it ceases to exist when (or soon after)
                      the export is deleted."
	INDEX   { dafsExportIndex }
              ::= { dafsExportTable 1 }

	DafsExportEntry ::=
	SEQUENCE	{
			dafsExportIndex
				INTEGER,
			dafsExportName
				DisplayString,
			dafsExportPath
				DisplayString,
			dafsExportEnabled
				INTEGER,
			dafsExportRwMode
				INTEGER,
			dafsExportAccessList
				DisplayString
			}

	dafsExportIndex OBJECT-TYPE
	SYNTAX	INTEGER (1..2147483647)
	ACCESS	read-only
	STATUS	mandatory
	DESCRIPTION
                      "A unique value for each export.  Its value
                      ranges between 1 and the number of exports.  The
                      value for each export must remain constant at
                      least from one re-initialization of the entity's
                      network management system to the next re-
                      initialization."
	::= { dafsExportEntry 1 }

	dafsExportName OBJECT-TYPE
	SYNTAX	DisplayString (SIZE (0..255))
	ACCESS	read-only
	STATUS	mandatory
	DESCRIPTION
                      "A textual string containing information about the
                      export.  This is the logical export name."
	::= { dafsExportEntry 2}

	dafsExportPath OBJECT-TYPE
	SYNTAX	DisplayString (SIZE (0..255))
	ACCESS	read-only
	STATUS	mandatory
	DESCRIPTION
                      "A textual string containing information about the
                      export.  This is the local filesystem path to
		      the export."
	::= { dafsExportEntry 3}

	dafsExportEnabled OBJECT-TYPE
	SYNTAX	INTEGER	{
				false(1),
				true(2)
			}
	ACCESS	read-only
	STATUS	mandatory
	DESCRIPTION
		"This export is available for access."
	::= { dafsExportEntry 4 }

	dafsExportRwMode OBJECT-TYPE
	SYNTAX	INTEGER	{
				readwrite(1),
				readmostly(2),
				readonly(3)
			}
	ACCESS	read-only
	STATUS	mandatory
	DESCRIPTION
		"Global export mode. This represents the maximum
		access rights."
	::= { dafsExportEntry 5 }

	dafsExportAccessList OBJECT-TYPE
	SYNTAX	DisplayString (SIZE (0..255))
	ACCESS	read-only
	STATUS	mandatory
	DESCRIPTION
                      "A textual string containing information about the
                      export.  This is the list of hosts that may
		      access the export. If empty, all hosts may
		      access the export."
	::= { dafsExportEntry 6 }

--------------------------
-- VI interface statistics
--------------------------

    viaNodeConnection OBJECT IDENTIFIER ::= { vi 1 }

    viaNodeSystemName   OBJECT-TYPE
    SYNTAX    DisplayString(SIZE (0..255))
    ACCESS    read-only
    STATUS    mandatory
    DESCRIPTION
        "A string by which the node is identified in the cluster."
    ::= { viaNodeConnection 1 }

    viaCreated OBJECT-TYPE
    SYNTAX    INTEGER
    ACCESS    read-only
    STATUS    mandatory
    DESCRIPTION    
        "The number of VIs created."
    ::= { viaNodeConnection 2 }

    viaConnectRequest OBJECT-TYPE
    SYNTAX    Counter
    ACCESS    read-only
    STATUS    mandatory
    DESCRIPTION    
        "The number of times Connect Request call is made."
    ::= { viaNodeConnection 3 }

    viaConnectWait OBJECT-TYPE
    SYNTAX    Counter
    ACCESS    read-only
    STATUS    mandatory
    DESCRIPTION    
        "The number of times Connect wait call is made." 
    ::= { viaNodeConnection 4 }

    viaDisconnect OBJECT-TYPE
    SYNTAX    Counter
    ACCESS    read-only
    STATUS    mandatory
    DESCRIPTION    
        "Number of times VI got disconnected with out any error."
    ::= { viaNodeConnection 5 }

    viaConnectTimeOut OBJECT-TYPE
    SYNTAX    Counter
    ACCESS    read-only
    STATUS    mandatory
    DESCRIPTION    
        "Number of times VI connect request got timed out."
    ::= { viaNodeConnection 6 }

    viaConnected OBJECT-TYPE
    SYNTAX    Counter
    ACCESS    read-only
    STATUS    mandatory
    DESCRIPTION    
        "Number of time VI got connected with out any error."
    ::= { viaNodeConnection 7 }

    viaCurrConnectPending OBJECT-TYPE
    SYNTAX    Gauge
    ACCESS    read-only
    STATUS    mandatory
    DESCRIPTION    
        "The number of VIs for which connect request is pending."
    ::= { viaNodeConnection 8 }

    viaCurrConnectWaitPending OBJECT-TYPE
    SYNTAX    Gauge
    ACCESS    read-only
    STATUS    mandatory
    DESCRIPTION    
        "The number of VIs for which connect wait request is pending." 
    ::= { viaNodeConnection 9 }

    viaCurrConnected OBJECT-TYPE
    SYNTAX    Gauge
    ACCESS    read-only
    STATUS    mandatory
    DESCRIPTION    
        "The number of VIs for which the current state is CONNECTED."
    ::= { viaNodeConnection 10 }

    viaCurrError OBJECT-TYPE
    SYNTAX    Gauge
    ACCESS    read-only
    STATUS    mandatory
    DESCRIPTION    
        "The number of VIs for which the current state is ERROR"
    ::= { viaNodeConnection 11 }

    viaTotalError OBJECT-TYPE
    SYNTAX    Counter
    ACCESS    read-only
    STATUS    mandatory
    DESCRIPTION    
        "The number of VIs which encountered error state."
    ::= { viaNodeConnection 12 }

    viaInMsgs OBJECT-TYPE
    SYNTAX    Counter
    ACCESS    read-only
    STATUS    mandatory
    DESCRIPTION    
        "The total number of incoming Messages received."
    ::= { viaNodeConnection 13 }

    viaInRdma OBJECT-TYPE
    SYNTAX    Counter
    ACCESS    read-only
    STATUS    mandatory
    DESCRIPTION    
        "The total number of incoming RDMA requests received."
    ::= { viaNodeConnection 14 }

    viaInBytes OBJECT-TYPE
    SYNTAX    Counter
    ACCESS    read-only
    STATUS    mandatory
    DESCRIPTION    
        "The total number of incoming bytes received, including those 
        received in error. This count includes bytes received on 
        currently established connections. This corresponds to the sum
        of bytes received through received messages, incoming RDMA writes 
        and RDMA reads issued"
    ::= { viaNodeConnection 15 }

    viaInRDMAReadBytes OBJECT-TYPE
    SYNTAX    Counter
    ACCESS    read-only
    STATUS    mandatory
    DESCRIPTION   
        "The total number of incoming bytes received through RDMA read, 
        including those received in error. This count includes bytes 
        received on currently established connections."
    ::= { viaNodeConnection 16 }

    viaInRDMAWriteBytes OBJECT-TYPE
    SYNTAX    Counter
    ACCESS    read-only
    STATUS    mandatory
    DESCRIPTION   
        "The total number of bytes received through incoming RDMA writes, 
        including those received in error. This count includes bytes 
        received on currently established connections."
    ::= { viaNodeConnection 17 }

    viaOutMsgs OBJECT-TYPE
    SYNTAX    Counter
    ACCESS    read-only
    STATUS    mandatory
    DESCRIPTION    
        "The total number of Messages sent."
    ::= { viaNodeConnection 18 }

    viaOutRdma OBJECT-TYPE
    SYNTAX    Counter
    ACCESS    read-only
    STATUS    mandatory
    DESCRIPTION    
        "The total number of RDMA requests sent."
    ::= { viaNodeConnection 19 }

    viaOutBytes OBJECT-TYPE
    SYNTAX    Counter
    ACCESS    read-only
    STATUS    mandatory
    DESCRIPTION    
        "The total number of bytes sent, including those 
        sent in error. This count includes bytes sent on 
        currently established connections."
    ::= { viaNodeConnection 20 }

    viaOutRDMAReadBytes OBJECT-TYPE
    SYNTAX    Counter
    ACCESS    read-only
    STATUS    mandatory
    DESCRIPTION
        "The total number of bytes sent through an incoming 
        RDMA read request, including those sent in error. 
        This count includes bytes sent on currently established 
        connections."
    ::= { viaNodeConnection 21 }

    viaOutRDMAWriteBytes OBJECT-TYPE
    SYNTAX    Counter
    ACCESS    read-only
    STATUS    mandatory
    DESCRIPTION
        "The total number of bytes sent through a RDMA write
        operation, including those sent in error. This count 
        includes bytes sent on currently established connections."
    ::= { viaNodeConnection 22 }


    viaConnTable OBJECT-TYPE
    SYNTAX    SEQUENCE OF ViaConnEntry
    ACCESS    not-accessible
    STATUS    mandatory
    DESCRIPTION
        "A table containing via connection specific information."
    ::= { viaNodeConnection 23 }        

    viaConnEntry OBJECT-TYPE
    SYNTAX    ViaConnEntry
    ACCESS    not-accessible
    STATUS    mandatory
    DESCRIPTION    
        "A conceptual row of the viaConnTable containing information
        about a particular current via connection. Each row of this
        table is transient, and it ceases to exist when the 
        connection makes transition to the CLOSED state."
     INDEX    { viaConnVINumber 
    }
     ::= { viaConnTable 1 }

ViaConnEntry  ::= SEQUENCE {

    viaConnState                 INTEGER,
    viaConnVINumber              INTEGER,
    viaConnRemoteNetAddress      IpAddress,
    viaConnLocalNetAddress       IpAddress,
    viaConnRemotePortNumber      INTEGER,
    viaConnLocalPortNumber       INTEGER,
    viaConnLocalDescriminator    OCTET STRING,
    viaConnRemoteDescriminator   OCTET STRING,
    viaConnLocalMaxTransferSize  INTEGER,
    viaConnRemoteMaxTransferSize INTEGER,
    viaConnLocalEnableRdmaWrite  INTEGER,
    viaConnLocalEnableRdmaRead   INTEGER,
    viaConnRemoteEnableRdmaWrite INTEGER,
    viaConnRemoteEnableRdmaRead  INTEGER,
    viaConnSentMessages          Counter,
    viaConnSentRdmaReadMessages  Counter,
    viaConnSentRdmaWriteMessages Counter,
    viaConnRcvdMessages          Counter,
    viaConnRcvdRdmaReadMessages  Counter,
    viaConnRcvdRdmaWriteMessages Counter

    }

    viaConnState OBJECT-TYPE
    SYNTAX   INTEGER {
         idle (1),
         pendingConnect(2),
         connected(3),
         error(4)
         }                  
    ACCESS             read-only
    STATUS             mandatory
    DESCRIPTION             
            "The state of this via connection
             Legal States:
                   Idle            1 
                   Pending Connect 2
                   Connected       3
                   Error           4"
    ::= { viaConnEntry 1 }

    viaConnVINumber    OBJECT-TYPE
    SYNTAX        INTEGER (1..2147483647)
    ACCESS        read-only
    STATUS        mandatory
    DESCRIPTION
        "A number which uniquely defines a     connection."
    ::= { viaConnEntry 2 }

    viaConnRemoteNetAddress    OBJECT-TYPE
    SYNTAX        IpAddress
    ACCESS        read-only
    STATUS        mandatory
    DESCRIPTION
        "IP address of the remote system of the connection."
    ::= { viaConnEntry 3 }

    viaConnLocalNetAddress OBJECT-TYPE
    SYNTAX      IpAddress
    ACCESS      read-only
    STATUS      mandatory
    DESCRIPTION
        "Local IPadress of the connection."
    ::= { viaConnEntry 4 }

    viaConnRemotePortNumber    OBJECT-TYPE
    SYNTAX        INTEGER
    ACCESS        read-only
    STATUS        mandatory
    DESCRIPTION
        "Remote TCP portnumber of the connection."
    ::= { viaConnEntry 5 }

    viaConnLocalPortNumber    OBJECT-TYPE
    SYNTAX        INTEGER
    ACCESS        read-only
    STATUS        mandatory
    DESCRIPTION
        "Local TCP Portnumber of the connection."
    ::= { viaConnEntry 6 }

    viaConnLocalDescriminator    OBJECT-TYPE
    SYNTAX        OCTET STRING
    ACCESS        read-only
    STATUS        mandatory
    DESCRIPTION
        "An identifier used by the local process to identify the
        VI connection."
    ::= { viaConnEntry 7 }

    viaConnRemoteDescriminator    OBJECT-TYPE
    SYNTAX        OCTET STRING    
    ACCESS        read-only
    STATUS        mandatory
    DESCRIPTION
        "An identifier used by the remote process to identify the
        VI connection."
    ::= { viaConnEntry 8 }

    viaConnLocalMaxTransferSize    OBJECT-TYPE
    SYNTAX        INTEGER
    ACCESS        read-only
    STATUS        mandatory
    DESCRIPTION
        "The local limit on the maximum packet size that can be 
        transfered through the connection."
    ::= { viaConnEntry 9 }

    viaConnRemoteMaxTransferSize OBJECT-TYPE
    SYNTAX        INTEGER
    ACCESS        read-only
    STATUS        mandatory
    DESCRIPTION
        "The remote limit on the maximum packet size that can be 
        transfered through the connection."
    ::= { viaConnEntry 10 }

    viaConnLocalEnableRdmaWrite    OBJECT-TYPE
    SYNTAX        INTEGER
    ACCESS        read-only
    STATUS        mandatory
    DESCRIPTION
            "The value is 1 if remote DMA write is enabled
            in the local system otherwise, it is 0."
    ::= { viaConnEntry 11 }

    viaConnLocalEnableRdmaRead    OBJECT-TYPE
    SYNTAX        INTEGER
    ACCESS        read-only
    STATUS        mandatory
    DESCRIPTION
            "The value is 1 if remote DMA read is enabled
            in the local system otherwise, it is 0."
    ::= { viaConnEntry 12 }

    viaConnRemoteEnableRdmaWrite    OBJECT-TYPE
    SYNTAX        INTEGER
    ACCESS        read-only
    STATUS        mandatory
    DESCRIPTION
            "The value is 1 if remote DMA write is enabled
            in the remote system otherwise, it is 0."
    ::= { viaConnEntry 13 }

    viaConnRemoteEnableRdmaRead    OBJECT-TYPE
    SYNTAX        INTEGER
    ACCESS        read-only
    STATUS        mandatory
    DESCRIPTION
            "The value is 1 if remote DMA read is enabled
            in the remote system otherwise, it is 0."
    ::= { viaConnEntry 14 }

    viaConnSentMessages    OBJECT-TYPE
    SYNTAX        Counter
    ACCESS        read-only
    STATUS        mandatory
    DESCRIPTION
            "Total number of messages sent through the connection."
    ::= { viaConnEntry 15 }

    viaConnSentRdmaReadMessages    OBJECT-TYPE
    SYNTAX        Counter
    ACCESS        read-only
    STATUS        mandatory
    DESCRIPTION
            "Total number of rdma read messages sent through the 
            connection."
    ::= { viaConnEntry 16 }

    viaConnSentRdmaWriteMessages    OBJECT-TYPE
    SYNTAX        Counter
    ACCESS        read-only
    STATUS        mandatory
    DESCRIPTION
            "Total number of rdma write messages sent through the 
            connection."
    ::= { viaConnEntry 17 }

    viaConnRcvdMessages    OBJECT-TYPE
    SYNTAX        Counter
    ACCESS        read-only
    STATUS        mandatory
    DESCRIPTION
            "Total number of messages received through the connection."
    ::= { viaConnEntry 18 }

    viaConnRcvdRdmaReadMessages    OBJECT-TYPE
    SYNTAX        Counter
    ACCESS        read-only
    STATUS        mandatory
    DESCRIPTION
            "Total number of rdma read messages received through the 
            connection."
    ::= { viaConnEntry 19 }

    viaConnRcvdRdmaWriteMessages    OBJECT-TYPE
    SYNTAX        Counter
    ACCESS        read-only
    STATUS        mandatory
    DESCRIPTION
            "Total number of rdma write messages received through the 
            connection."
    ::= { viaConnEntry 20 }

    viaErrors OBJECT IDENTIFIER ::= { vi 2 }

    viaErrPostDesc        OBJECT-TYPE
    SYNTAX          Counter
    ACCESS          read-only
    STATUS          mandatory
    DESCRIPTION
            "The total number of descriptors completed in error
            by NIC."
    ::= { viaErrors 1 }

    viaErrConnLost        OBJECT-TYPE
    SYNTAX          Counter
    ACCESS          read-only
    STATUS          mandatory
    DESCRIPTION
            "The total number of Lost Connection errors. "
    ::= { viaErrors 2 }

    viaErrRecvQEmpty    OBJECT-TYPE
    SYNTAX          Counter
    ACCESS          read-only
    STATUS          mandatory
    DESCRIPTION
            "The total number of errors due to an empty receive Queue. "
    ::= { viaErrors 3 }

    viaErrRdmawProt        OBJECT-TYPE
    SYNTAX          Counter
    ACCESS          read-only
    STATUS          mandatory
    DESCRIPTION
            "The total number of remote DMA write protection errors. "
    ::= { viaErrors 4 }

    viaErrRdmarProt        OBJECT-TYPE
    SYNTAX          Counter
    ACCESS          read-only
    STATUS          mandatory
    DESCRIPTION
            "The total number of remote DMA read protection errors. "
    ::= { viaErrors 5 }

    viaErrCompProt    OBJECT-TYPE
    SYNTAX          Counter
    ACCESS          read-only
    STATUS          mandatory
    DESCRIPTION
            "The total number of protection errors. "
    ::= { viaErrors 6 }

    viaErrorThreshold OBJECT-TYPE
    SYNTAX            INTEGER
    ACCESS            read-write
    STATUS            mandatory
    DESCRIPTION
        "Setting this threshold will cause a trap to be enabled
        such that if the total error exceeds error threshold set 
        a viaNodeErrorsTrap trap will be generated."
    ::= { viaErrors 7 }    

    viaNicAttributes OBJECT IDENTIFIER ::= { vi 3 }

    viaNicTable        OBJECT-TYPE
    SYNTAX            SEQUENCE OF ViaNicEntry
    ACCESS            not-accessible
    STATUS            mandatory
    DESCRIPTION
            "A table containing via NIC-specific information."
    ::= { viaNicAttributes 1}

    viaNicEntry        OBJECT-TYPE
    SYNTAX            ViaNicEntry
    ACCESS            not-accessible
    STATUS            mandatory
    DESCRIPTION
            "A conceptual row of the viaNicTable containing information
            about a particular present VINic."

    INDEX    {    viaNicIndex }
    ::= { viaNicTable 1 }

    ViaNicEntry ::= SEQUENCE {
            viaNicIndex               INTEGER,
            viaName                   DisplayString,
            viaHardwareVersion        DisplayString,
            viaProviderVersion        DisplayString,
            viaNicAddress             PhysAddress,
            viaThreadSafe             INTEGER,
            viaMaxDiscriminatorLength INTEGER,
            viaMaxRegisterBytes       INTEGER,
            viaMaxRegisterRegions     INTEGER,
            viaMaxRegisterBlockBytes  INTEGER,
            viaMaxVI                  INTEGER,
            viaMaxDescriptorsPerQueue INTEGER,
            viaMaxSegmentsPerDesc     INTEGER,
            viaMaxCQ                  INTEGER,
            viaMaxCQEntries           INTEGER,
            viaMaxTransferSize        INTEGER,
            viaNativeMTU              INTEGER,
            viaMaxPTags               INTEGER,
            viaCurrRegisterBytes      INTEGER,
            viaCurrRegisterRegions    INTEGER,
            viaCurrVI                 INTEGER,
            viaCurrCQ                 INTEGER,
            viaCurrPTags              INTEGER,
            viaConnectionListenPort   INTEGER
    }

    viaNicIndex        OBJECT-TYPE
    SYNTAX        INTEGER (1..2147483647)
    ACCESS        read-only
    STATUS        mandatory
    DESCRIPTION
        "The index of the NIC in the NIC table."
    ::= { viaNicEntry 1 }

    viaName            OBJECT-TYPE
    SYNTAX        DisplayString (SIZE (0..255))
    ACCESS        read-only
    STATUS        mandatory
    DESCRIPTION
        "The symbolic name of the NIC device."
    ::= { viaNicEntry 2 }

    viaHardwareVersion    OBJECT-TYPE
    SYNTAX        DisplayString (SIZE (0..255))
    ACCESS        read-only
    STATUS        mandatory
    DESCRIPTION
        "The version of the VINIC described by this MIB."
    ::= { viaNicEntry 3 }

    viaProviderVersion    OBJECT-TYPE
    SYNTAX        DisplayString (SIZE (0..255))
    ACCESS        read-only
    STATUS        mandatory
    DESCRIPTION
        "The version of the VI provider."
    ::= { viaNicEntry 4 }

    viaNicAddress    OBJECT-TYPE
    SYNTAX        PhysAddress
    ACCESS        read-only
    STATUS        mandatory
    DESCRIPTION
        "The Network address of this NIC."
    ::= { viaNicEntry 5 }

    viaThreadSafe    OBJECT-TYPE
    SYNTAX       INTEGER
    ACCESS       read-only
    STATUS       mandatory
    DESCRIPTION
        "1 if synchronisation model is thread safe else 0."
    ::= { viaNicEntry 6 }

    viaMaxDiscriminatorLength    OBJECT-TYPE
    SYNTAX        INTEGER
    ACCESS        read-only
    STATUS        mandatory
    DESCRIPTION
        "The maximum number of bytes that the VI provider allows
        for a connection descriminator."
    ::= { viaNicEntry 7 }

    viaMaxRegisterBytes    OBJECT-TYPE
    SYNTAX        INTEGER
    ACCESS        read-only
    STATUS        mandatory
    DESCRIPTION
        "Maximum number of bytes that can be registered."
    ::= { viaNicEntry 8 }

    viaMaxRegisterRegions    OBJECT-TYPE
    SYNTAX        INTEGER
    ACCESS        read-only
    STATUS        mandatory
    DESCRIPTION
        "Maximum number of memory regions that can be registered."
    ::= { viaNicEntry 9 }

    viaMaxRegisterBlockBytes    OBJECT-TYPE
    SYNTAX        INTEGER
    ACCESS        read-only
    STATUS        mandatory
    DESCRIPTION
        "Largest contiguous block of memory that can be registered."
    ::= { viaNicEntry 10 }

    viaMaxVI        OBJECT-TYPE
    SYNTAX        INTEGER
    ACCESS        read-only
    STATUS        mandatory
    DESCRIPTION
        "The limit on the total number of VI instances this entity can
        support."
    ::= { viaNicEntry 11 }

    viaMaxDescriptorsPerQueue    OBJECT-TYPE
    SYNTAX        INTEGER
    ACCESS        read-only
    STATUS        mandatory
    DESCRIPTION
        "Maximum Descriptors per VI Work Queue that this VI provider
        can support."
    ::= { viaNicEntry 12 }

    viaMaxSegmentsPerDesc    OBJECT-TYPE
    SYNTAX        INTEGER
    ACCESS        read-only
    STATUS        mandatory
    DESCRIPTION
        "Maximum number of segments per descriptor that this VI provider
        can support."
    ::= { viaNicEntry 13 }

    viaMaxCQ        OBJECT-TYPE
    SYNTAX        INTEGER
    ACCESS        read-only
    STATUS        mandatory
    DESCRIPTION
        "Maximum number of completion queues this VI provider can support."
    ::= { viaNicEntry 14 }

    viaMaxCQEntries        OBJECT-TYPE
    SYNTAX        INTEGER
    ACCESS        read-only
    STATUS        mandatory
    DESCRIPTION
        "Maximum number of Completion queue entries per completion queue
        that this VI provider can support."
    ::= { viaNicEntry 15 }

    viaMaxTransferSize    OBJECT-TYPE
    SYNTAX        INTEGER
    ACCESS        read-only
    STATUS        mandatory
    DESCRIPTION
        "The maximum transfer size supported by the VI Nic. The maximum 
        transfer size is the amount of data that can be described by a 
        single VI descriptor."
    ::= { viaNicEntry 16 }

    viaNativeMTU    OBJECT-TYPE
    SYNTAX        INTEGER
    ACCESS        read-only
    STATUS        mandatory
    DESCRIPTION
        "The native MTU size of the underlying network. For frame-based 
        networks, this could reflect its native frame size. For cell-based 
        networks, it could reflect the MTU of the appropriate abstraction 
        layer that it supports."
    ::= { viaNicEntry 17 }

    viaMaxPTags        OBJECT-TYPE
    SYNTAX        INTEGER
    ACCESS        read-only
    STATUS        mandatory
    DESCRIPTION
        "The maximum number of protection tags that are supported by this
        VI provider."
    ::= { viaNicEntry 18 }

   viaCurrRegisterBytes    OBJECT-TYPE
       SYNTAX        INTEGER
       ACCESS        read-only
       STATUS        mandatory
       DESCRIPTION
           "Number of bytes registered by the VI user for this
           NIC."
       ::= { viaNicEntry 19 }

   viaCurrRegisterRegions    OBJECT-TYPE
       SYNTAX        INTEGER
       ACCESS        read-only
       STATUS        mandatory
       DESCRIPTION
           "Number of memory regions that is registered by VI user
           for this NIC."
       ::= { viaNicEntry 20 }

   viaCurrVI        OBJECT-TYPE
       SYNTAX        INTEGER
       ACCESS        read-only
       STATUS        mandatory
       DESCRIPTION
           "The current number of VI instances for this NIC."
       ::= { viaNicEntry 21 }

   viaCurrCQ        OBJECT-TYPE
       SYNTAX        INTEGER
       ACCESS        read-only
       STATUS        mandatory
       DESCRIPTION
           "Current number of completion queues this VI provider
           has."
       ::= { viaNicEntry 22 }

   viaCurrPTags      OBJECT-TYPE
       SYNTAX        INTEGER
       ACCESS        read-only
       STATUS        mandatory
       DESCRIPTION
           "Current Number of protection tags this VI provider has."
       ::= { viaNicEntry 23 }

    viaConnectionListenPort        OBJECT-TYPE
    SYNTAX        INTEGER
    ACCESS        read-only
    STATUS        mandatory
    DESCRIPTION
        "Port number on which VI server is listening for VI connection
        request."
    ::= { viaNicEntry 24 }


        -- -- -- -- -- -- -- --
	-- VFILER group --
	-- -- -- -- -- -- -- --
	vfilerIsLicensed   OBJECT-TYPE
        SYNTAX          INTEGER {
	                             false(1),
                                     true(2)
                                }
	ACCESS          read-only
        STATUS          mandatory
        DESCRIPTION     
                        "Whether vfiler  is licensed on the
			filer."
        ::= { vfiler 1 }

	vfFilers     OBJECT-TYPE
        SYNTAX          Counter
        ACCESS          read-only
        STATUS          mandatory
        DESCRIPTION
                      "Number of vfilers in the physical Filer."
        ::= { vfiler 2 }

        vfTable        OBJECT-TYPE
	SYNTAX          SEQUENCE OF VfEntry
	ACCESS          not-accessible
	STATUS          mandatory
	DESCRIPTION 
		     "Provide a report of per-vfiler general information "
	::= { vfiler 3 }

	vfEntry        OBJECT-TYPE
        SYNTAX          VfEntry
        ACCESS          not-accessible
        STATUS          mandatory
        DESCRIPTION
                     "Provide a report of per-vfiler information"
 	INDEX   { vfIndex}
        ::= { vfTable 1 }

        VfEntry ::=
       	     SEQUENCE {
	       	 vfIndex
		 	INTEGER,
		 vfName	
		 	DisplayString,
                 vfUuid
                        OCTET STRING (SIZE (0..36)),
                 vfIpAddresses
                        INTEGER,
                 vfStoragePaths
                        INTEGER,
		 vfIpSpace	
		 	DisplayString,
		 vfAllowedProtocols
		 	INTEGER,
		 vfDisallowedProtocols
		 	INTEGER,
		 vfState
		 	INTEGER		       
      	     }

	vfIndex         OBJECT-TYPE
        SYNTAX          INTEGER (1..2147483647)
        ACCESS          read-only
        STATUS          mandatory
        DESCRIPTION
                     "A number that identifies this entry for the referenced vfiler."
        ::= { vfEntry 1 }


	vfName      OBJECT-TYPE
        SYNTAX          DisplayString
        ACCESS          read-only
        STATUS          mandatory
        DESCRIPTION
                      " A textual string that contains the name of the referenced vfiler."
        ::= { vfEntry 2 }

        vfUuid		OBJECT-TYPE
        SYNTAX		OCTET STRING (SIZE (0..36))
        ACCESS		read-only
        STATUS		mandatory

        DESCRIPTION
                      "The UUID of the referenced vfiler."
        ::= { vfEntry 3 }

	vfIpAddresses	OBJECT-TYPE
	SYNTAX          INTEGER 
	ACCESS          read-only
	STATUS          mandatory
	DESCRIPTION
	               "The total number of IP addresses for the referenced vfiler."
        ::= { vfEntry 4 }


        vfStoragePaths	OBJECT-TYPE
	SYNTAX          INTEGER 
        ACCESS          read-only
        STATUS          mandatory
        DESCRIPTION
                       "The total number of storage paths for the referenced vfiler."
        ::= { vfEntry 5 }

        vfIpSpace      OBJECT-TYPE
        SYNTAX          DisplayString
        ACCESS          read-only
        STATUS          mandatory
        DESCRIPTION
                      " A textual string that contains the name of the ipspace that the referenced vfiler belongs to."
        ::= { vfEntry 6 }

        vfAllowedProtocols	OBJECT-TYPE
        SYNTAX          INTEGER 
        ACCESS          read-only
        STATUS          mandatory
        DESCRIPTION
                       "Total number of protocols allowed for the referenced vfiler."
        ::= { vfEntry 7 }

        vfDisallowedProtocols	OBJECT-TYPE
        SYNTAX          INTEGER 
        ACCESS          read-only
        STATUS          mandatory
        DESCRIPTION
                       "Total number of protocols disallowed for the referenced vfiler."
        ::= { vfEntry 8 }

        vfState		OBJECT-TYPE
	SYNTAX   INTEGER {
         stopped (1),
         running (2)
         }                  
        ACCESS          read-only
        STATUS          mandatory
        DESCRIPTION
                       "Status of the vfiler: Running or stopped."
        ::= { vfEntry 9 }

	vfIpTable        OBJECT-TYPE
	SYNTAX          SEQUENCE OF VfIpEntry
	ACCESS          not-accessible
	STATUS          mandatory
	DESCRIPTION 
			"Provide a report of per-vfiler IP addresses information "
        ::= { vfiler 4 }

        vfIpEntry        OBJECT-TYPE
	SYNTAX          VfIpEntry
	ACCESS          not-accessible
	STATUS          mandatory
	DESCRIPTION
	                "Provide a report of per-vfiler IP addresses information"
        INDEX   { vfFiIndex, vfIpIndex }
        ::= { vfIpTable 1 }

        VfIpEntry ::=
 	    SEQUENCE {
        	vfFiIndex
		          INTEGER,
                vfIpIndex
			  INTEGER,
	   	vfIpAddr
	                  IpAddress
            }
        
        vfFiIndex         OBJECT-TYPE
      	SYNTAX          INTEGER (1..2147483647)
        ACCESS          read-only
        STATUS          mandatory
        DESCRIPTION
                     "A number that identifies the referenced vfiler."
        ::= { vfIpEntry 1 }

        vfIpIndex         OBJECT-TYPE
        SYNTAX          INTEGER (1..2147483647)
        ACCESS          read-only
        STATUS          mandatory
        DESCRIPTION
                     "A number that identifies which IP address in the referenced vfiler."
        ::= { vfIpEntry 2 }

        vfIpAddr         OBJECT-TYPE
        SYNTAX          IpAddress
        ACCESS          read-only
        STATUS          mandatory
        DESCRIPTION
                      "A IP address for the referenced vfiler."
        ::= { vfIpEntry 3 }

        vfSpTable        OBJECT-TYPE
        SYNTAX          SEQUENCE OF VfSpEntry
        ACCESS          not-accessible
        STATUS          mandatory
        DESCRIPTION 
                       "Provide a report of per-vfiler storage path information "
        ::= { vfiler 5 }

        vfSpEntry        OBJECT-TYPE
        SYNTAX          VfSpEntry
        ACCESS          not-accessible
        STATUS          mandatory
        DESCRIPTION
                       "Provide a report of per-vfiler storage path information"
        INDEX   { vfFsIndex, vfSpIndex }
        ::= { vfSpTable 1 }

        VfSpEntry ::=
            SEQUENCE {
                vfFsIndex
                          INTEGER,
                vfSpIndex
                          INTEGER,
                vfSpName
	                  OCTET STRING (SIZE (0..1024))
	    }

        vfFsIndex         OBJECT-TYPE
        SYNTAX          INTEGER (1..2147483647)
        ACCESS          read-only
        STATUS          mandatory
        DESCRIPTION
                     "A number that identifies the referenced vfiler."
        ::= { vfSpEntry 1 }

        vfSpIndex         OBJECT-TYPE
        SYNTAX          INTEGER (1..2147483647)
        ACCESS          read-only
        STATUS          mandatory
        DESCRIPTION
                     "A number that identifies which storage path in the referenced vfiler."
        ::= { vfSpEntry 2 }

        vfSpName         OBJECT-TYPE
        SYNTAX         	OCTET STRING (SIZE (0..1024)) 
        ACCESS          read-only
        STATUS          mandatory
        DESCRIPTION
                      "The storage path name  for the referenced vfiler."
        ::= { vfSpEntry 3 }


        vfProTable        OBJECT-TYPE
	SYNTAX          SEQUENCE OF VfProEntry
        ACCESS          not-accessible
        STATUS          mandatory
        DESCRIPTION
                       "Provide a report of per-vfiler protocol information "
        ::= { vfiler 6 }

        vfProEntry        OBJECT-TYPE
        SYNTAX          VfProEntry
        ACCESS          not-accessible
        STATUS          mandatory
        DESCRIPTION
                       "Provide a report of per-vfiler protocol information"
        INDEX   { vfFpIndex, vfProIndex }
        ::= { vfProTable 1 }

        VfProEntry ::=
            SEQUENCE {
       	        vfFpIndex
	                   INTEGER,
                vfProIndex
                           INTEGER,
                vfProName
                           OCTET STRING (SIZE (0..1024)),
		vfProStatus
			   INTEGER
	    }

        vfFpIndex         OBJECT-TYPE
        SYNTAX          INTEGER (1..2147483647)
        ACCESS          read-only
        STATUS          mandatory
        DESCRIPTION
                     "A number that identifies the referenced vfiler."
        ::= { vfProEntry 1 }

        vfProIndex         OBJECT-TYPE
	SYNTAX          INTEGER (1..2147483647)
        ACCESS          read-only
        STATUS          mandatory
        DESCRIPTION
                     "A number that identifies a protocol in the referenced vfiler."
        ::= { vfProEntry 2 }

        vfProName         OBJECT-TYPE
        SYNTAX          OCTET STRING (SIZE (0..1024))
        ACCESS          read-only
        STATUS          mandatory
        DESCRIPTION
                      "A textual string that contains the protocol name  for the referenced vfiler."
        ::= { vfProEntry 3 }

        vfProStatus	OBJECT-TYPE
        SYNTAX		INTEGER {
					false(1),
					true(2)
			}
        ACCESS          read-only
        STATUS          mandatory
        DESCRIPTION
			"Whether the referenced vfiler protocol  is allowed or disallowed."
        ::= { vfProEntry 4 }

        -- -- -- -- -- -- -- --
	-- Block access protocols group --
	-- -- -- -- -- -- -- --
	fcpIsLicensed   OBJECT-TYPE
        SYNTAX          INTEGER {
	                             false(1),
                                     true(2)
                                }
	ACCESS          read-only
        STATUS          mandatory
        DESCRIPTION     
                        "Whether FCP access protocols are licensed on the
			filer."
        ::= { blocks 1 }

	iscsiIsLicensed   OBJECT-TYPE
        SYNTAX          INTEGER {
	                             false(1),
                                     true(2)
                                }
	ACCESS          read-only
        STATUS          mandatory
        DESCRIPTION     
                        "Whether iSCSI access protocols are licensed on the
			filer."
        ::= { blocks 2 }

	fcpLowReadBytes	OBJECT-TYPE
	SYNTAX		Counter
        ACCESS          read-only
        STATUS          mandatory
        DESCRIPTION
			"The total number of bytes read via FCP  
			since the last boot.  This object returns the 
			least significant 32 bits of the 64 bit unsigned 
			integer."
	::= { blocks 3 }

	fcpHighReadBytes	OBJECT-TYPE
	SYNTAX		Counter
        ACCESS          read-only
        STATUS          mandatory
        DESCRIPTION
			"The total number of bytes read via FCP  
			since the last boot.  This object returns the 
			most significant 32 bits of the 64 bit unsigned 
			integer."
	::= { blocks 4 }


	fcpLowWriteBytes	OBJECT-TYPE
	SYNTAX		Counter
        ACCESS          read-only
        STATUS          mandatory
        DESCRIPTION
			"The total number of bytes written via FCP  
			since the last boot.  This object returns the 
			least significant 32 bits of the 64 bit unsigned 
			integer."
	::= { blocks 5 }


	fcpHighWriteBytes	OBJECT-TYPE
	SYNTAX		Counter
        ACCESS          read-only
        STATUS          mandatory
        DESCRIPTION
			"The total number of bytes written via FCP  
			since the last boot.  This object returns the 
			most significant 32 bits of the 64 bit unsigned 
			integer."
	::= { blocks 6 }


	iscsiLowReadBytes	OBJECT-TYPE
	SYNTAX		Counter
        ACCESS          read-only
        STATUS          mandatory
        DESCRIPTION
			"The total number of bytes read via iSCSI  
			since the last boot.  This object returns the 
			least significant 32 bits of the 64 bit unsigned 
			integer."
	::= { blocks 7 }


	iscsiHighReadBytes	OBJECT-TYPE
	SYNTAX		Counter
        ACCESS          read-only
        STATUS          mandatory
        DESCRIPTION
			"The total number of bytes read via iSCSI  
			since the last boot.  This object returns the 
			most significant 32 bits of the 64 bit unsigned 
			integer."
	::= { blocks 8 }


	iscsiLowWriteBytes	OBJECT-TYPE
	SYNTAX		Counter
        ACCESS          read-only
        STATUS          mandatory
        DESCRIPTION
			"The total number of bytes written via iSCSI  
			since the last boot.  This object returns the 
			least significant 32 bits of the 64 bit unsigned 
			integer."
	::= { blocks 9 }


	iscsiHighWriteBytes	OBJECT-TYPE
	SYNTAX		Counter
        ACCESS          read-only
        STATUS          mandatory
        DESCRIPTION
			"The total number of bytes written via iSCSI  
			since the last boot.  This object returns the 
			most significant 32 bits of the 64 bit unsigned 
			integer."
	::= { blocks 10 }


	iscsiHighOps 	OBJECT-TYPE
	SYNTAX		Counter
	ACCESS		read-only
	STATUS		mandatory
	DESCRIPTION
			"The total number of iSCSI ops handled since the
			last boot.  This object returns the most significant
			32 bits of the 64 bit unsigned integer."
	::= {blocks 11}

	iscsiLowOps 	OBJECT-TYPE
	SYNTAX		Counter
	ACCESS		read-only
	STATUS		mandatory
	DESCRIPTION
			"The total number of iSCSI ops handled since the
			last boot.  This object returns the least significant
			32 bits of the 64 bit unsigned integer."
	::= {blocks 12}

	fcpHighOps 	OBJECT-TYPE
	SYNTAX		Counter
	ACCESS		read-only
	STATUS		mandatory
	DESCRIPTION
			"The total number of FCP ops handled since the
			last boot.  This object returns the most significant
			32 bits of the 64 bit unsigned integer."
	::= {blocks 13}

	fcpLowOps 	OBJECT-TYPE
	SYNTAX		Counter
	ACCESS		read-only
	STATUS		mandatory
	DESCRIPTION
			"The total number of FCP ops handled since the
			last boot.  This object returns the least significant
			32 bits of the 64 bit unsigned integer."
	::= {blocks 14}


	lun		OBJECT IDENTIFIER ::= {blocks 15 }
	
	lunCount	OBJECT-TYPE
        SYNTAX          INTEGER
        ACCESS          read-only
        STATUS          mandatory
        DESCRIPTION
                      "Number of LUNs in the Filer."
        ::= { lun 1 }

	lunTable	OBJECT-TYPE
	SYNTAX		SEQUENCE OF LunEntry
	ACCESS		not-accessible
	STATUS		mandatory
	DESCRIPTION
			"Provide a report of per-LUN general information "
	::= {lun 2}

	lunEntry	OBJECT-TYPE
	SYNTAX		LunEntry
	ACCESS		not-accessible
	STATUS		mandatory
	DESCRIPTION	
			"Provide a report of per-LUN information"
	INDEX	{ lunIndex}
	::= { lunTable 1 }

	LunEntry ::=
	    SEQUENCE {
		lunIndex INTEGER,
		lunName DisplayString,
		lunComment DisplayString,
		lunSizeLow INTEGER,
		lunSizeHigh INTEGER,
		lunMapped INTEGER,
		lunSerialNumber DisplayString,
		lunQtreeName DisplayString,
		lunHighOps Counter,
		lunLowOps Counter,
		lunHighReadBytes Counter,
		lunLowReadBytes Counter,
		lunHighWriteBytes Counter,
		lunLowWriteBytes Counter,
		lunHighErrors Counter,
		lunLowErrors Counter,
		lunOnline INTEGER,
		lunSnapStatus	INTEGER,
		lunShareStatus INTEGER,
		lunSpaceReserved INTEGER,
		lunStatsResetTime INTEGER,
		lunHighReadOps Counter,
		lunLowReadOps Counter,
		lunHighWriteOps Counter,
		lunLowWriteOps Counter,
		lunHighOtherOps Counter,
		lunLowOtherOps Counter
		}

	lunIndex      OBJECT-TYPE
        SYNTAX          INTEGER (1..2147483647)
        ACCESS          read-only
        STATUS          mandatory
        DESCRIPTION
                     "A number that identifies the referenced LUN."
        ::= { lunEntry 1 }

	lunName      OBJECT-TYPE
        SYNTAX          DisplayString
        ACCESS          read-only
        STATUS          mandatory
        DESCRIPTION
                      "The name of the LUN.  This is also the path to the LUN
		      on the filer."
        ::= { lunEntry 2 }	

	lunComment      OBJECT-TYPE
        SYNTAX          DisplayString
        ACCESS          read-only
        STATUS          mandatory
        DESCRIPTION
                      "The comment, if any, for this LUN."
        ::= { lunEntry 3 }	

	lunSizeLow	OBJECT-TYPE
        SYNTAX		INTEGER
        ACCESS          read-only
        STATUS          mandatory
        DESCRIPTION
                     "Size of the LUN in bytes.  This object returns the 
		     least significant 32 bits of the 64 bit unsigned integer."
        ::= { lunEntry 4 }

	lunSizeHigh	OBJECT-TYPE
        SYNTAX		INTEGER
        ACCESS          read-only
        STATUS          mandatory
        DESCRIPTION
                     "Size of the LUN in bytes.  This object returns the 
		     most significant 32 bits of the 64 bit unsigned integer."
        ::= { lunEntry 5 }

	lunMapped   OBJECT-TYPE
        SYNTAX          INTEGER {
                                     false(1),
                                     true(2)
                                }
 
        ACCESS          read-only
        STATUS          mandatory
        DESCRIPTION
                     "This LUN has been mapped to at least one initiator group."
        ::= { lunEntry 6 }
	
	lunSerialNumber   OBJECT-TYPE
	SYNTAX		DisplayString
	ACCESS		read-only
	STATUS		mandatory
	DESCRIPTION
		    "The 12 character SCSI serial number of the LUN."
	::= { lunEntry 7 }


	lunQtreeName   OBJECT-TYPE
	SYNTAX		DisplayString
	ACCESS		read-only
	STATUS		mandatory
	DESCRIPTION
		    "A string that indicates which qtree this LUN belongs to."
	::= { lunEntry 8 }

	lunHighOps	OBJECT-TYPE
        SYNTAX		Counter
        ACCESS          read-only
        STATUS          mandatory
        DESCRIPTION
			"The total number of Target side SCSI ops for 
			this LUN since the stats were last reset.  This object 
			returns the most significant 32 bits of the 64 bit 
			unsigned integer."
	::= { lunEntry 9}

	lunLowOps	OBJECT-TYPE
        SYNTAX		Counter
        ACCESS          read-only
        STATUS          mandatory
        DESCRIPTION
			"The total number of Target side SCSI ops for 
			this LUN since the stats were last reset.  This object 
			returns the least significant 32 bits of the 64 bit 
			unsigned integer."
	::= { lunEntry 10 }

	lunHighReadBytes	OBJECT-TYPE
        SYNTAX		Counter
        ACCESS          read-only
        STATUS          mandatory
        DESCRIPTION
			"The total number of bytes read from this LUN 
			since the stats were last reset.  This object returns 
			the most significant 32 bits of the 64 bit unsigned 
			integer."
	::= { lunEntry 11 }

	lunLowReadBytes	OBJECT-TYPE
        SYNTAX		Counter
        ACCESS          read-only
        STATUS          mandatory
        DESCRIPTION
			"The total number of bytes read from this LUN 
			since the stats were last reset.  This object returns 
			the least significant 32 bits of the 64 bit unsigned 
			integer."
	::= { lunEntry 12 }

	
	lunHighWriteBytes	OBJECT-TYPE
        SYNTAX		Counter
        ACCESS          read-only
        STATUS          mandatory
        DESCRIPTION
			"The total number of bytes written to this LUN 
			since the stats were last reset.  This object returns 
			the most significant 32 bits of the 64 bit unsigned 
			integer."
	::= { lunEntry 13 }

	lunLowWriteBytes	OBJECT-TYPE
        SYNTAX		Counter
        ACCESS          read-only
        STATUS          mandatory
        DESCRIPTION
			"The total number of bytes written to this LUN 
			since the stats were last reset.  This object returns 
			the least significant 32 bits of the 64 bit unsigned 
			integer."
	::= { lunEntry 14 }

	lunHighErrors	OBJECT-TYPE
        SYNTAX		Counter
        ACCESS          read-only
        STATUS          mandatory
        DESCRIPTION
			"The total number of errors seen on this LUN 
			since the stats were last reset.  This object 
			returns the most significant 32 bits of the 64 bit 
			unsigned integer."
	::= { lunEntry 15 }

	lunLowErrors	OBJECT-TYPE
        SYNTAX		Counter
        ACCESS          read-only
        STATUS          mandatory
        DESCRIPTION
			"The total number of errors seen on this LUN 
			since the stats were last reset.  This object 
			returns the least significant 32 bits of the 64 bit 
			unsigned integer."
	::= { lunEntry 16 }

	lunOnline	OBJECT-TYPE
	SYNTAX		INTEGER {
				    false(1),
				    true(2)
				}
	ACCESS		read-only
	STATUS		mandatory
	DESCRIPTION
			"Whether the LUN is online."
	::= { lunEntry 17 }

	lunSnapStatus	OBJECT-TYPE
	SYNTAX		INTEGER {
				    false(1),
				    true(2)
				}
	ACCESS		read-only
	STATUS		mandatory
	DESCRIPTION
			"Whether a snapshot of this LUN can be taken."
	::= { lunEntry 18 }

	
	lunShareStatus	OBJECT-TYPE
	SYNTAX		INTEGER {
				    none(1),
				    read(2),
				    write(3),
				    all(4)
				}
	ACCESS		read-only
	STATUS		mandatory
	DESCRIPTION
			"The sharing status for the LUN."
	::= { lunEntry 19 }

	
	lunSpaceReserved	OBJECT-TYPE
	SYNTAX		INTEGER {
				    false(1),
				    true(2)
				}
	ACCESS		read-only
	STATUS		mandatory
	DESCRIPTION
			"Whether the LUN has space reservation enabled."
	::= { lunEntry 20 }
	
	lunStatsResetTime	OBJECT-TYPE
	SYNTAX		INTEGER 
	ACCESS		read-only
	STATUS		mandatory
	DESCRIPTION
			"Number of seconds since this LUN's stats were
			last reset."
	::= { lunEntry 21 }
				

	lunHighReadOps	OBJECT-TYPE
        SYNTAX		Counter
        ACCESS          read-only
        STATUS          mandatory
        DESCRIPTION
			"The total number of Target side SCSI read ops for 
			this LUN since the stats were last reset.  This object 
			returns the least significant 32 bits of the 64 bit 
			unsigned integer."
	::= { lunEntry 22}

	lunLowReadOps	OBJECT-TYPE
        SYNTAX		Counter
        ACCESS          read-only
        STATUS          mandatory
        DESCRIPTION
			"The total number of Target side SCSI read ops for 
			this LUN since the stats were last reset.  This object 
			returns the most significant 32 bits of the 64 bit 
			unsigned integer."
	::= { lunEntry 23 }


	lunHighWriteOps	OBJECT-TYPE
        SYNTAX		Counter
        ACCESS          read-only
        STATUS          mandatory
        DESCRIPTION
			"The total number of Target side SCSI write ops for 
			this LUN since the stats were last reset.  This object 
			returns the least significant 32 bits of the 64 bit 
			unsigned integer."
	::= { lunEntry 24}

	lunLowWriteOps	OBJECT-TYPE
        SYNTAX		Counter
        ACCESS          read-only
        STATUS          mandatory
        DESCRIPTION
			"The total number of Target side SCSI write ops for 
			this LUN since the stats were last reset.  This object 
			returns the most significant 32 bits of the 64 bit 
			unsigned integer."
	::= { lunEntry 25 }


	lunHighOtherOps	OBJECT-TYPE
        SYNTAX		Counter
        ACCESS          read-only
        STATUS          mandatory
        DESCRIPTION
			"The total number of Target side SCSI ops that are not 
			read or write for this LUN since the stats were last 
			reset.  This object returns the least significant 32 
			bits of the 64 bit unsigned integer."
	::= { lunEntry 26}

	lunLowOtherOps	OBJECT-TYPE
        SYNTAX		Counter
        ACCESS          read-only
        STATUS          mandatory
        DESCRIPTION
			"The total number of Target side SCSI ops that are not 
			read or write for this LUN since the stats were last 
			reset. This object returns the most significant 32 
			bits of the 64 bit unsigned integer."
	::= { lunEntry 27 }


	lunMapTable    OBJECT-TYPE
	SYNTAX		SEQUENCE OF LunMapEntry
	ACCESS		not-accessible
	STATUS		mandatory
	DESCRIPTION
			"Provide a table listing the initiator group to 
			Logical Unit Number mapping for each LUN."
	::= { lun 3 }

	lunMapEntry	OBJECT-TYPE
	SYNTAX		LunMapEntry
	ACCESS		not-accessible
	STATUS		mandatory
	DESCRIPTION	
			"Provide a per LUN and Initiator group mapping of 
			SCSI logical unit numbers."
	INDEX	{ lunMapLUNIndex, lunMapInitiatorGroupIndex }
	::= { lunMapTable 1 }

	LunMapEntry ::=
	    SEQUENCE {
		lunMapLUNIndex		INTEGER,
		lunMapInitiatorGroupIndex	INTEGER,
		lunMapLUNName			DisplayString,
		lunMapInitiatorGroupName	DisplayString,
		lunMapLogicalUnitNumber		INTEGER
	    }

	lunMapLUNIndex	OBJECT-TYPE	
        SYNTAX          INTEGER (1..2147483647)
        ACCESS          read-only 
        STATUS          mandatory
        DESCRIPTION
                     "A number that identifies the LUN in the table."
        ::= { lunMapEntry 1 }

	lunMapInitiatorGroupIndex	OBJECT-TYPE
        SYNTAX          INTEGER (1..2147483647)
        ACCESS          read-only
        STATUS          mandatory
        DESCRIPTION
                     "A number that identifies an initiator group in 
		     the table."
        ::= { lunMapEntry 2 }

	lunMapLUNName	OBJECT-TYPE
	SYNTAX		    DisplayString
	ACCESS		    read-only
	STATUS		    mandatory
	DESCRIPTION
		    "The name of the LUN."
	::= { lunMapEntry 3 }

	lunMapInitiatorGroupName	OBJECT-TYPE
	SYNTAX		    DisplayString
	ACCESS		    read-only
	STATUS		    mandatory
	DESCRIPTION
		    "The name of the initiator group that this LUN is 
		    mapped to."
	::= { lunMapEntry 4 }

	lunMapLogicalUnitNumber	OBJECT-TYPE
        SYNTAX          INTEGER
        ACCESS          read-only
        STATUS          mandatory
        DESCRIPTION
                     "SCSI Logical Unit Number that this LUN is mapped to 
		     for this initiator group."
        ::= { lunMapEntry 5 }

	initiator 	OBJECT IDENTIFIER ::= {blocks 16}

	initiatorGroupTable	OBJECT-TYPE
	SYNTAX		SEQUENCE OF InitiatorGroupEntry
	ACCESS		not-accessible
	STATUS		mandatory
	DESCRIPTION
			"Provide a report of per-initiator group general 
			information "
	::= {initiator 1}

	initiatorGroupEntry	OBJECT-TYPE
	SYNTAX		InitiatorGroupEntry
	ACCESS		not-accessible
	STATUS		mandatory
	DESCRIPTION	
			"Provide a report of per-initiator group information"
	INDEX	{ initiatorGroupIndex }
	::= { initiatorGroupTable 1 }
	
	InitiatorGroupEntry ::=
	    SEQUENCE {
		initiatorGroupIndex INTEGER,
		initiatorGroupName  DisplayString,
		initiatorGroupType  INTEGER,
		initiatorGroupOS    INTEGER,
		initiatorGroupThrottleReserve INTEGER,
		initiatorGroupThrottleBorrow  INTEGER,
		initiatorGroupUsePartner  INTEGER,
		initiatorGroupUseALUA	INTEGER
		}

	initiatorGroupIndex      OBJECT-TYPE
        SYNTAX          INTEGER (1..2147483647)
        ACCESS          read-only
        STATUS          mandatory
        DESCRIPTION
                     "A number that identifies a specific initiator group."
        ::= { initiatorGroupEntry 1 }

	initiatorGroupName  OBJECT-TYPE
	SYNTAX		    DisplayString
	ACCESS		    read-only
	STATUS		    mandatory
	DESCRIPTION
		    "The name of the initiator group"
	::= { initiatorGroupEntry 2 }

	initiatorGroupType OBJECT-TYPE
        SYNTAX          INTEGER {
                                     fcp(1),
                                     iSCSI(2)
                                }
	ACCESS		read-only
	STATUS		mandatory
	DESCRIPTION
		    "Type of this initiator group, either iSCSI or FCP"
	::= { initiatorGroupEntry 3 }

	initiatorGroupOS OBJECT-TYPE
	SYNTAX          INTEGER {
                                     default(1),
                                     solaris(2),
				     windows(3),
				     hpux(4),
				     aix(5),
				     linux(6),
				     default-partner(7),
				     netware(8),
				     vmware(9),
				     invalid(256)
                                }
	ACCESS		read-only
	STATUS		mandatory
	DESCRIPTION
		    "Operating system the clients in this initiator
		    group run.  This governs  the finer details of 
		    SCSI protocol interaction with these initiators"
	::= { initiatorGroupEntry 4 }

	initiatorGroupThrottleReserve OBJECT-TYPE
        SYNTAX          INTEGER (0..99) 
	ACCESS		read-only
	STATUS		mandatory
	DESCRIPTION
		    "Percentage of filer scsi command blocks reserved for
		    this initiator group"
	::= { initiatorGroupEntry 5 }


	initiatorGroupThrottleBorrow OBJECT-TYPE
        SYNTAX          INTEGER {
				false(1),
				true(2)
			}
	ACCESS		read-only
	STATUS		mandatory
	DESCRIPTION
		    "True if this inititiator group is allowed to
		    exceed it's throttle settings if more resources
		    are needed and otherwise available.  If
		    initiatorGroupThrottleReserve is 0, this value
		    is meaningless"
	::= { initiatorGroupEntry 6 }

        initiatorGroupUsePartner OBJECT-TYPE
	SYNTAX          INTEGER {
	                        false(1),
				true(2)
                                }
	ACCESS		read-only
	STATUS		mandatory
	DESCRIPTION
		    "The takeover mode for the initiator group.  This is
		    only applicable to FCP initiator groups on clustered
		    filers" 
	::= { initiatorGroupEntry 7 }
	
	initiatorGroupUseALUA	OBJECT-TYPE
	SYNTAX          INTEGER {
	                        false(1),
				true(2)
                                }
	ACCESS		read-only
	STATUS		mandatory
	DESCRIPTION
		    "If true this initiator group supports Asymetric Logical
		    Unit Access."
	::= { initiatorGroupEntry 8 }


	initiatorGroupMemberTable	OBJECT-TYPE
	SYNTAX		SEQUENCE OF InitiatorGroupMemberEntry
	ACCESS		not-accessible
	STATUS		mandatory
	DESCRIPTION
			"Table of individual Initator names in each Initiator 
			group"
	::= {initiator 2}

	initiatorGroupMemberEntry	OBJECT-TYPE
	SYNTAX		InitiatorGroupMemberEntry
	ACCESS		not-accessible
	STATUS		mandatory
	DESCRIPTION	
			"Provide a report of per-initiator group information"
	INDEX	{ initiatorGroupMemberIndex, initiatorGroupMemberNameIndex}
	::= { initiatorGroupMemberTable 1 }
	
	InitiatorGroupMemberEntry ::=
	    SEQUENCE {
		initiatorGroupMemberIndex
			INTEGER,
		initiatorGroupMemberNameIndex
			INTEGER,
		initiatorName	
			DisplayString
		}

	initiatorGroupMemberIndex      OBJECT-TYPE
        SYNTAX          INTEGER (1..2147483647)
        ACCESS          read-only
        STATUS          mandatory
        DESCRIPTION
                     "A number that identifies a specific initiator group."
        ::= { initiatorGroupMemberEntry 1 }

	initiatorGroupMemberNameIndex      OBJECT-TYPE
        SYNTAX          INTEGER (1..2147483647)
        ACCESS          read-only
        STATUS          mandatory
        DESCRIPTION
                      "A number the identifies the initiator in the group."
        ::= { initiatorGroupMemberEntry 2 }

	initiatorName	OBJECT-TYPE
	SYNTAX		DisplayString
        ACCESS          read-only
        STATUS          mandatory
        DESCRIPTION
		    "A textual name for this initiator."
	::= { initiatorGroupMemberEntry 3 }

	initiatorListTable  OBJECT-TYPE
	SYNTAX		SEQUENCE OF InitatorListMemberEntry
	ACCESS		not-accessible
	STATUS		mandatory
	DESCRIPTION
		    "Table of initiators that are connected to the filer."
	::= { initiator 3 }

	initiatorListMemberEntry	OBJECT-TYPE
	SYNTAX		InitatorListMemberEntry
	ACCESS		not-accessible
	STATUS		mandatory
	DESCRIPTION	
		    "Provide a report of per-connected-initiator information."
	INDEX { initiatorListMemberEntryIndex}
	::= { initiatorListTable 1 }

	InitatorListMemberEntry ::=
	    SEQUENCE {
		initiatorListMemberEntryIndex	INTEGER,
		targetAdapterName		DisplayString,
		connectedInitiatorNodeName	DisplayString,
		connectedInitiatorPortName	DisplayString,
		connectedInitiatorType		INTEGER,
		connectedInitiatorIsid		DisplayString,
		connectedInitiatorPortalGroup	INTEGER
	    }

	initiatorListMemberEntryIndex      OBJECT-TYPE
        SYNTAX          INTEGER (1..2147483647)
        ACCESS          read-only
        STATUS          mandatory
        DESCRIPTION
                     "A number that identifies the initiator connected to
		     the target adapter."
        ::= { initiatorListMemberEntry 1 }

	targetAdapterName      OBJECT-TYPE
        SYNTAX		DisplayString 
        ACCESS          read-only
        STATUS          mandatory
        DESCRIPTION
                     "The name of the target adapter in the filer."
        ::= { initiatorListMemberEntry 2 }

	connectedInitiatorNodeName      OBJECT-TYPE
        SYNTAX		DisplayString 
        ACCESS          read-only
        STATUS          mandatory
        DESCRIPTION
                     "A textual name for this initiator node."
        ::= { initiatorListMemberEntry 3 }

	connectedInitiatorPortName      OBJECT-TYPE
        SYNTAX		DisplayString 
        ACCESS          read-only
        STATUS          mandatory
        DESCRIPTION
                     "The FibreChannel device's portname. This is FCP only."
        ::= { initiatorListMemberEntry 4 }

	connectedInitiatorType	    OBJECT-TYPE
        SYNTAX          INTEGER {
                                     fcp(1),
                                     iSCSI(2)
                                }
	ACCESS		read-only
	STATUS		mandatory
	DESCRIPTION
		    "Type of this init group, either iSCSI or FCP"
	::= { initiatorListMemberEntry 5 }

	connectedInitiatorIsid	    OBJECT-TYPE
	SYNTAX		DisplayString
	ACCESS		read-only
	STATUS		mandatory
	DESCRIPTION
		    "The iSCSI isid (initiator session id) for this initiator.
		    This is iSCSI only."
	::= { initiatorListMemberEntry 6 }

	connectedInitiatorPortalGroup	    OBJECT-TYPE
	SYNTAX		INTEGER
	ACCESS		read-only
	STATUS		mandatory
	DESCRIPTION
		    "The iSCSI portal group ID for this initiator. 
		    This is iSCSI only."
	::= { initiatorListMemberEntry 7 }


	fcpTarget	OBJECT IDENTIFIER ::= {blocks 17}

	fcpTargetTable	OBJECT-TYPE
	SYNTAX		SEQUENCE OF FcpTargetTableEntry
	ACCESS		not-accessible
	STATUS		mandatory
	DESCRIPTION
			"Provide a report of fcp target adapter general 
			information "
	::= {fcpTarget 1}

	fcpTargetTableEntry OBJECT-TYPE
	SYNTAX		FcpTargetTableEntry
	ACCESS		not-accessible
	STATUS		mandatory
	DESCRIPTION	
			"Provide a report of per fcp target device information"
	INDEX	{ fcpTargetTableIndex }
	::= { fcpTargetTable 1 }
	
	FcpTargetTableEntry ::=
	    SEQUENCE {
		fcpTargetTableIndex    INTEGER,
		fcpTargetName   DisplayString,
		fcpTargetNN	DisplayString,
		fcpTargetPN	DisplayString,
		fcpTargetSpeed	INTEGER,
		fcpTargetStatus	INTEGER,
		fcpTargetStandby INTEGER,
		fcpTargetTopology INTEGER,
		fcpTargetType	INTEGER
		}

	fcpTargetTableIndex	OBJECT-TYPE
        SYNTAX          INTEGER (1..2147483647)
        ACCESS          read-only
        STATUS          mandatory
        DESCRIPTION
                     "A number that identifies a specific fcp target device."
        ::= { fcpTargetTableEntry 1 }

	fcpTargetName	    OBJECT-TYPE
	SYNTAX		    DisplayString
	ACCESS		    read-only
	STATUS		    mandatory
	DESCRIPTION
		    "The name of the fcp target device" 
	::= { fcpTargetTableEntry 2 }

	fcpTargetNN	    OBJECT-TYPE
	SYNTAX		    DisplayString
	ACCESS		    read-only
	STATUS		    mandatory
	DESCRIPTION
		    "The FC WWNN of the fcp target device" 
	::= { fcpTargetTableEntry 3 }

	fcpTargetPN	    OBJECT-TYPE
	SYNTAX		    DisplayString
	ACCESS		    read-only
	STATUS		    mandatory
	DESCRIPTION
		    "The FC WWPN of the fcp target device" 
	::= { fcpTargetTableEntry 4 }

	fcpTargetSpeed	    OBJECT-TYPE
        SYNTAX          INTEGER
	ACCESS		read-only
	STATUS		mandatory
	DESCRIPTION
		    "speed in gigabits per second. 0 is unknown."
	::= { fcpTargetTableEntry 5 }

	fcpTargetStatus	    OBJECT-TYPE
        SYNTAX          INTEGER {
				startup(1),
				uninitialized(2),
				initializing-fw(3),
				link-not-connected(4),
				waiting-for-link-up(5),
				online(6),
				link-disconnected(7),
				resetting(8),
				offline(9),
				offlined-by-user-system(10),
				unknown(11)
				}
	ACCESS		read-only
	STATUS		mandatory
	DESCRIPTION
		    "Status of the fcp target adapter"
	::= { fcpTargetTableEntry 6 }

	fcpTargetStandby	OBJECT-TYPE
	SYNTAX		INTEGER {
				    false(1),
				    true(2)
				}
	ACCESS		read-only
	STATUS		mandatory
	DESCRIPTION
			"Whether this target adapter is in standby mode."
	::= { fcpTargetTableEntry 7 }

	fcpTargetTopology 	OBJECT-TYPE
	SYNTAX		INTEGER {
				    unknown(1),
				    fabric(2),
				    point-to-point(3),
				    loop(4)
				}
	ACCESS		read-only
	STATUS		mandatory
	DESCRIPTION
			"fibre channel topology for this adapter. "
	::= { fcpTargetTableEntry 8 }

        fcpTargetType		OBJECT-TYPE
	SYNTAX		INTEGER {
	                          physical(1),
				  local(2),
				  standby(3),
				  partner(4),
				  unknown(5)
				 }
	ACCESS          read-only
        STATUS          mandatory
        DESCRIPTION
			"Responsibility/Type for this adapter."
	::= { fcpTargetTableEntry 9 }

        fcpCfMode	OBJECT-TYPE
	SYNTAX		INTEGER {
	                           mixed(1),
				   standby(2),
				   partner(3),
				   partner-proxy(4),
				   partner-standby(5),
				   local-primary(6),
				   dual-fabric(7),
				   ssi(8),
				   unknown(256)
	                        }
        ACCESS          read-only
        STATUS          mandatory
        DESCRIPTION
			"Failover setting for the FCP target cluster."
	::= { blocks 18 }

	
	-- -- -- -- -- -- -- -- -- -- -- -- -- -- -- -- -- --
	-- -- -- -- -- -- -- -- -- -- -- -- -- -- -- -- -- --
	-- Port sets
	-- -- -- -- -- -- -- -- -- -- -- -- -- -- -- -- -- --
	-- -- -- -- -- -- -- -- -- -- -- -- -- -- -- -- -- --
	
	pset 		OBJECT IDENTIFIER ::= {blocks 19}

	psetTable 	OBJECT-TYPE
	SYNTAX		SEQUENCE OF PortSetEntry
	ACCESS		not-accessible
	STATUS		mandatory
	DESCRIPTION
			"Provide a report of portset general 
			information "
	::= {pset 1}

	psetEntry 	OBJECT-TYPE
	SYNTAX		PortSetEntry
	ACCESS		not-accessible
	STATUS		mandatory
	DESCRIPTION	
			"Provide a report of portset information"
	INDEX	{ psetIndex }
	::= { psetTable 1 }
	
	PortSetEntry ::=
	    SEQUENCE {
		psetIndex INTEGER,
		psetName  DisplayString,
		psetType  INTEGER
		}

	psetIndex	OBJECT-TYPE
        SYNTAX          INTEGER (1..2147483647)
        ACCESS          read-only
        STATUS          mandatory
        DESCRIPTION
                     "A number that identifies a specific port set."
        ::= { psetEntry 1 }

	psetName	OBJECT-TYPE
	SYNTAX		DisplayString
	ACCESS		read-only
	STATUS		mandatory
	DESCRIPTION
		    "The name of the port set"
	::= { psetEntry 2 }
	
	psetType 	OBJECT-TYPE
        SYNTAX          INTEGER {
                                     fcp(1),
                                     iSCSI(2)
                                }
	ACCESS		read-only
	STATUS		mandatory
	DESCRIPTION
		    "Type of this port set, either iSCSI or FCP"
	::= { psetEntry 3 }
	
	psetMemberTable	OBJECT-TYPE
	SYNTAX		SEQUENCE OF PsetMemberEntry
	ACCESS		not-accessible
	STATUS		mandatory
	DESCRIPTION
			"Table of individual Port names in each Port
			set"
	::= {pset 2}

	psetMemberEntry	OBJECT-TYPE
	SYNTAX		PsetMemberEntry
	ACCESS		not-accessible
	STATUS		mandatory
	DESCRIPTION	
			"Provide a report of portset port information"
	INDEX	{ psetMemberIndex, psetMemberNameIndex}
	::= { psetMemberTable 1 }
	
	PsetMemberEntry ::=
	    SEQUENCE {
		psetMemberIndex
			INTEGER,
		psetMemberNameIndex
			INTEGER,
		psetPortName	
			DisplayString
		}

	psetMemberIndex OBJECT-TYPE
        SYNTAX          INTEGER (1..2147483647)
        ACCESS          read-only
        STATUS          mandatory
        DESCRIPTION
                     "A number that identifies a specific port set."
        ::= { psetMemberEntry 1 }

	psetMemberNameIndex	OBJECT-TYPE
        SYNTAX          	INTEGER (1..2147483647)
        ACCESS          	read-only
        STATUS          	mandatory
        DESCRIPTION
                      "A number the identifies the port in the set."
        ::= { psetMemberEntry 2 }
	
	psetPortName	OBJECT-TYPE
	SYNTAX		DisplayString
        ACCESS          read-only
        STATUS          mandatory
        DESCRIPTION
		    "A textual name for this port."
	::= { psetMemberEntry 3 }
	

	-- -- -- -- -- -- -- -- -- -- -- -- -- -- -- -- -- --
	-- -- -- -- -- -- -- -- -- -- -- -- -- -- -- -- -- --
	-- NFS caching group 
	-- -- -- -- -- -- -- -- -- -- -- -- -- -- -- -- -- --
	-- -- -- -- -- -- -- -- -- -- -- -- -- -- -- -- -- --


	-- -- -- -- -- -- -- -- -- -- -- -- -- -- -- -- -- --
	-- NFS caching options 
	-- -- -- -- -- -- -- -- -- -- -- -- -- -- -- -- -- --
	nfsCacheOptions		OBJECT IDENTIFIER ::= { nfscache 1 }

	nfsCacheIsEnabled	OBJECT-TYPE
	SYNTAX				INTEGER {
						false(1),
						true(2)
					}
	ACCESS			read-only
	STATUS			mandatory
	DESCRIPTION
				"Whether NFS caching is enabled on this system."
	::= { nfsCacheOptions 1 }

	nfsCacheIsLicensed	OBJECT-TYPE
	SYNTAX				INTEGER {
						false(1),
						true(2)
					}
	ACCESS			read-only
	STATUS			mandatory
	DESCRIPTION
				"Whether NFS caching is licensed on this system."
	::= { nfsCacheOptions 2 }

	-- -- -- -- -- -- -- -- -- -- -- -- -- -- -- -- -- --
	-- NFS caching stats 
	-- -- -- -- -- -- -- -- -- -- -- -- -- -- -- -- -- --

	nfsCacheStats		OBJECT IDENTIFIER ::= { nfscache 2 }

    	-- nfsCacheBytesFromClients is DEPRECATED; use nfsCacheHighBytesFromClients
	-- and nfsCacheLowBytesFromClients

	nfsCacheBytesFromClients	OBJECT-TYPE
	SYNTAX				Counter
	ACCESS				read-only
	STATUS				mandatory
	DESCRIPTION
			"Total NFS bytes received from clients"
	::= { nfsCacheStats 1 }

    	-- nfsCacheBytesToClients is DEPRECATED; use nfsCacheHighBytesToClients
	-- and nfsCacheLowBytesToClients

	nfsCacheBytesToClients		OBJECT-TYPE
	SYNTAX				Counter
	ACCESS				read-only
	STATUS				mandatory
	DESCRIPTION
			"Total NFS bytes sent to clients"
	::= { nfsCacheStats 2 }

    	-- nfsCacheBytesFromServers is DEPRECATED; use nfsCacheHighBytesFromServers
	-- and nfsCacheLowBytesFromServers

	nfsCacheBytesFromServers	OBJECT-TYPE
	SYNTAX				Counter
	ACCESS				read-only
	STATUS				mandatory
	DESCRIPTION
			"Total NFS bytes received from servers"
	::= { nfsCacheStats 3 }

    	-- nfsCacheBytesToServers is DEPRECATED; use nfsCacheHighBytesToServers
	-- and nfsCacheLowBytesToServers

	nfsCacheBytesToServers		OBJECT-TYPE
	SYNTAX				Counter
	ACCESS				read-only
	STATUS				mandatory
	DESCRIPTION
			"Total NFS bytes sent to servers"
	::= { nfsCacheStats 4 }

    	-- nfsCacheTotalRequests is DEPRECATED; use nfsCacheHighTotalRequests
	-- and nfsCacheLowTotalRequests

	nfsCacheTotalRequests		OBJECT-TYPE
	SYNTAX				Counter
	ACCESS				read-only
	STATUS				mandatory
	DESCRIPTION
			"Total NFS requests received"
	::= { nfsCacheStats 5 }

    	-- nfsCacheHitRequests is DEPRECATED; use nfsCacheHighHitRequests
	-- and nfsCacheLowHitRequests

	nfsCacheHitRequests		OBJECT-TYPE
	SYNTAX				Counter
	ACCESS				read-only
	STATUS				mandatory
	DESCRIPTION
			"Total NFS requests resulting in cache hits"
	::= { nfsCacheStats 6 }

    	-- nfsCacheMissRequests is DEPRECATED; use nfsCacheHighMissRequests
	-- and nfsCacheLowMissRequests

	nfsCacheMissRequests		OBJECT-TYPE
	SYNTAX				Counter
	ACCESS				read-only
	STATUS				mandatory
	DESCRIPTION
			"Total NFS requests resulting in cache misses"
	::= { nfsCacheStats 7 }

	nfsCacheMissCacheableRequests	OBJECT-TYPE
	SYNTAX				Counter
	ACCESS				read-only
	STATUS				mandatory
	DESCRIPTION
			"Total NFS requests that were cacheable misses"
	::= { nfsCacheStats 8 }

	nfsCacheMissUnCacheableRequests	OBJECT-TYPE
	SYNTAX				Counter
	ACCESS				read-only
	STATUS				mandatory
	DESCRIPTION
			"Total NFS requests that were uncacheable misses"
	::= { nfsCacheStats 9 }

	nfsCacheEjectRequests		OBJECT-TYPE
	SYNTAX				Counter
	ACCESS				read-only
	STATUS				mandatory
	DESCRIPTION
			"Total NFS requests resulting in object eject due to expiration"
	::= { nfsCacheStats 10 }

	nfsCacheVerifyRequests		OBJECT-TYPE
	SYNTAX				Counter
	ACCESS				read-only
	STATUS				mandatory
	DESCRIPTION
			"Total NFS requests resulting in object verification"
	::= { nfsCacheStats 11 }

	nfsCacheRpcRecords		OBJECT-TYPE
	SYNTAX				Counter
	ACCESS				read-only
	STATUS				mandatory
	DESCRIPTION
			"Total RPC records received"
	::= { nfsCacheStats 12 }

	nfsCacheBWSavings			OBJECT-TYPE
	SYNTAX				INTEGER
	ACCESS				read-only
	STATUS				mandatory
	DESCRIPTION
			"Bandwidth savings for NFS requests"
	::= { nfsCacheStats 13 }

	nfsCacheHighBytesFromClients	OBJECT-TYPE
	SYNTAX				Counter
	ACCESS				read-only
	STATUS				mandatory
	DESCRIPTION
			"Total NFS bytes received from clients.  This object
			 returns the most significant 32 bits of the 64 bit 
			 unsigned integer."
	::= { nfsCacheStats 14 }

	nfsCacheLowBytesFromClients	OBJECT-TYPE
	SYNTAX				Counter
	ACCESS				read-only
	STATUS				mandatory
	DESCRIPTION
			"Total NFS bytes received from clients.  This object
			 returns the least significant 32 bits of the 64 bit 
			 unsigned integer."
	::= { nfsCacheStats 15 }

	nfsCacheHighBytesToClients	OBJECT-TYPE
	SYNTAX				Counter
	ACCESS				read-only
	STATUS				mandatory
	DESCRIPTION
			"Total NFS bytes sent to clients.  This object returns
			 the most significant 32 bits of the 64 bit unsigned 
			 integer."
	::= { nfsCacheStats 16 }

	nfsCacheLowBytesToClients	OBJECT-TYPE
	SYNTAX				Counter
	ACCESS				read-only
	STATUS				mandatory
	DESCRIPTION
			"Total NFS bytes sent to clients.  This object returns
			 the least significant 32 bits of the 64 bit unsigned 
			 integer."
	::= { nfsCacheStats 17 }

	nfsCacheHighBytesFromServers	OBJECT-TYPE
	SYNTAX				Counter
	ACCESS				read-only
	STATUS				mandatory
	DESCRIPTION
			"Total NFS bytes received from servers.  This object
			 returns the most significant 32 bits of the 64 bit 
			 unsigned integer."
	::= { nfsCacheStats 18 }

	nfsCacheLowBytesFromServers	OBJECT-TYPE
	SYNTAX				Counter
	ACCESS				read-only
	STATUS				mandatory
	DESCRIPTION
			"Total NFS bytes received from servers.  This object
			 returns the least significant 32 bits of the 64 bit
			 unsigned integer."
	::= { nfsCacheStats 19 }

	nfsCacheHighBytesToServers		OBJECT-TYPE
	SYNTAX				Counter
	ACCESS				read-only
	STATUS				mandatory
	DESCRIPTION
			"Total NFS bytes sent to servers.  This object
			 returns the most significant 32 bits of the 64 bit 
			 unsigned integer."
	::= { nfsCacheStats 20 }

	nfsCacheLowBytesToServers		OBJECT-TYPE
	SYNTAX				Counter
	ACCESS				read-only
	STATUS				mandatory
	DESCRIPTION
			"Total NFS bytes sent to servers.  This object
			 returns the least significant 32 bits of the 64 bit 
			 unsigned integer."
	::= { nfsCacheStats 21 }

	nfsCacheHighTotalRequests		OBJECT-TYPE
	SYNTAX				Counter
	ACCESS				read-only
	STATUS				mandatory
	DESCRIPTION
			"Total NFS requests received.  This object returns
			 the most significant 32 bits of the 64 bit unsigned 
			 integer."
	::= { nfsCacheStats 22 }

	nfsCacheLowTotalRequests		OBJECT-TYPE
	SYNTAX				Counter
	ACCESS				read-only
	STATUS				mandatory
	DESCRIPTION
			"Total NFS requests received.  This object returns
			 the least significant 32 bits of the 64 bit unsigned 
			 integer."
	::= { nfsCacheStats 23 }

	nfsCacheHighHitRequests		OBJECT-TYPE
	SYNTAX				Counter
	ACCESS				read-only
	STATUS				mandatory
	DESCRIPTION
			"Total NFS requests resulting in cache hits.  This
			 object returns the most significant 32 bits of the 
			 64 bit unsigned integer."
	::= { nfsCacheStats 24 }

	nfsCacheLowHitRequests		OBJECT-TYPE
	SYNTAX				Counter
	ACCESS				read-only
	STATUS				mandatory
	DESCRIPTION
			"Total NFS requests resulting in cache hits.  This
			 object returns the least significant 32 bits of the
			 64 bit unsigned integer."
	::= { nfsCacheStats 25 }

	nfsCacheHighMissRequests		OBJECT-TYPE
	SYNTAX				Counter
	ACCESS				read-only
	STATUS				mandatory
	DESCRIPTION
			"Total NFS requests resulting in cache misses.  This
			 object returns the most significant 32 bits of the 
			 64 bit unsigned integer."
	::= { nfsCacheStats 26 }

	nfsCacheLowMissRequests		OBJECT-TYPE
	SYNTAX				Counter
	ACCESS				read-only
	STATUS				mandatory
	DESCRIPTION
			"Total NFS requests resulting in cache misses.  This
			 object returns the least significant 32 bits of the
			 64 bit unsigned integer."
	::= { nfsCacheStats 27 }


	-- -- -- -- -- -- -- --
	-- the storage group --
	-- -- -- -- -- -- -- --

	enclosure	OBJECT IDENTIFIER ::=	{ storage 1 }

        -- -- -- -- -- -- --
        -- The enclosure group for storage

	enclNumber		OBJECT-TYPE
	SYNTAX			INTEGER
	ACCESS			read-only
	STATUS			mandatory
	DESCRIPTION
	    "The number of storage enclosures in the storage subsystem."
	::= { enclosure 1 }

	enclTable	OBJECT-TYPE
	SYNTAX		SEQUENCE OF EnclEntry
	ACCESS		not-accessible
	STATUS		mandatory
	DESCRIPTION
	    "Display disk enclosure environmental information for fiber
	     channel shelves and NearStore SCSI shelves.  Shelves that do not
	     support SCSI Enclosure Services, such as DEC Storage Shelf,
	     Eurologic XL8 are not supported."
	::= { enclosure 2 }

	enclEntry	OBJECT-TYPE
	SYNTAX		EnclEntry
	ACCESS		not-accessible
	STATUS		mandatory
	DESCRIPTION
	    "Display disk enclosure (shelf) environmental
	     information for the referenced disk enclosure."
	INDEX	{ enclIndex }
	::= { enclTable 1 }

	EnclEntry ::=
	    SEQUENCE {
	        enclIndex
		    INTEGER,
		enclContactState
		    INTEGER,
		enclChannelShelfAddr
		    DisplayString,
		enclProductLogicalID
		    DisplayString,
		enclProductID
		    DisplayString, 
		enclProductVendor
		    DisplayString,
		enclProductModel
		    DisplayString,
		enclProductRevision
		    DisplayString,
		enclProductSerialNo
		    DisplayString,
		enclNumberDiskBays
		    INTEGER,
		enclDisksPresent
		    DisplayString,
		enclPowerSuppliesMaximum
		    INTEGER,
		enclPowerSuppliesPresent
		    DisplayString,
		enclPowerSuppliesSerialNos
		    DisplayString,
		enclPowerSuppliesFailed
		    DisplayString,
		enclFansMaximum
		    INTEGER,
		enclFansPresent
		    DisplayString,
		enclFansFailed
		    DisplayString,
		enclTempSensorsMaximum
		    INTEGER, 
		enclTempSensorsPresent
		    DisplayString, 
		enclTempSensorsOverTempFail
		    DisplayString,
		enclTempSensorsOverTempWarn
		    DisplayString,
		enclTempSensorsUnderTempFail
		    DisplayString,
		enclTempSensorsUnderTempWarn
		    DisplayString,
		enclTempSensorsOverTempFailThr
		    DisplayString,
		enclTempSensorsOverTempWarnThr
		    DisplayString,
		enclTempSensorsUnderTempFailThr
		    DisplayString,
		enclTempSensorsUnderTempWarnThr
		    DisplayString,
		enclTempSensorsCurrentTemp
		    DisplayString,
		enclElectronicsMaximum
		    INTEGER,
		enclElectronicsPresent
		    DisplayString,
		enclElectronicsSerialNos
		    DisplayString,
		enclElectronicsFailed
		    DisplayString,
		enclVoltSensorsMaximum
		    INTEGER,
		enclVoltSensorsPresent
		    DisplayString, 
		enclVoltSensorsOverVoltFail
		    DisplayString,
		enclVoltSensorsOverVoltWarn
		    DisplayString,
		enclVoltSensorsUnderVoltFail
		    DisplayString,
		enclVoltSensorsUnderVoltWarn
		    DisplayString,
		enclVoltSensorsOverVoltFailThr
		    DisplayString,
		enclVoltSensorsOverVoltWarnThr
		    DisplayString,
		enclVoltSensorsUnderVoltFailThr
		    DisplayString,
		enclVoltSensorsUnderVoltWarnThr
		    DisplayString,
		enclVoltSensorsCurrentVolt
		    DisplayString,
		enclCurSensorsMaximum
		    INTEGER,
		enclCurSensorsPresent
		    DisplayString, 
		enclCurSensorsOverCurFail
		    DisplayString,
		enclCurSensorsOverCurWarn
		    DisplayString,
		enclCurSensorsOverCurFailThr
		    DisplayString,
		enclCurSensorsOverCurWarnThr
		    DisplayString,
		enclCurSensorsCurrentCur
		    DisplayString
	    }

	enclIndex	OBJECT-TYPE
	SYNTAX		INTEGER (0..255)
	ACCESS		read-only
	STATUS		mandatory
	DESCRIPTION
			"A number that identifies this enclosure among the
			 possible monitored enclosures.  This number normally
			 uniquely identifies one shelf within one boot,
			 but may it change between boots.  The number may
			 also change within a boot if shelves are removed
			 and added."
	::= { enclEntry 1 }

	enclContactState	OBJECT-TYPE
	SYNTAX			INTEGER {
					initializing(1),
					transitioning(2),
					active(3),
					inactive(4),
					reconfiguring(5),
					nonexistent(6)
				}
	ACCESS			read-only
	STATUS			mandatory
	DESCRIPTION
	    "The state of the communication between the filer or storage
	    engine and the enclosure monitoring device in the enclosure."
	::= { enclEntry 2 }

	enclChannelShelfAddr	OBJECT-TYPE
	SYNTAX			DisplayString
	ACCESS			read-only
	STATUS			mandatory
	DESCRIPTION
	    "The adapter number or switch name and the port number
	    (together, called the channel), and shelf ID of this
	    enclosure.  Examples are 8a.1 and switch:5.1."
	::= { enclEntry 3 }

	enclProductLogicalID	OBJECT-TYPE
	SYNTAX			DisplayString
	ACCESS			read-only
	STATUS			mandatory
	DESCRIPTION
	    "The logical identifier of this enclosure.  This a form of the
	    World-Wide Name (WWN)."
	::= { enclEntry 4 }

	enclProductID	OBJECT-TYPE
	SYNTAX			DisplayString
	ACCESS			read-only
	STATUS			mandatory
	DESCRIPTION
	    "The product ID of the shelf hardware module that provides
	    the enclosure monitoring function.  Example is LRC."
	::= { enclEntry 5 }

	enclProductVendor	OBJECT-TYPE
	SYNTAX			DisplayString
	ACCESS			read-only
	STATUS			mandatory
	DESCRIPTION
	    "The name of the vendor of this enclosure.  Example is Xyratex."
	::= { enclEntry 6 }

	enclProductModel	OBJECT-TYPE
	SYNTAX			DisplayString
	ACCESS			read-only
	STATUS			mandatory
	DESCRIPTION
	    "The model name of this enclosure.  Example is DiskShelf14."
	::= { enclEntry 7 }

	enclProductRevision	OBJECT-TYPE
	SYNTAX			DisplayString
	ACCESS			read-only
	STATUS			mandatory
	DESCRIPTION
	    "The revision number of this enclosure."
	::= { enclEntry 8 }

	enclProductSerialNo	OBJECT-TYPE
	SYNTAX			DisplayString
	ACCESS			read-only
	STATUS			mandatory
	DESCRIPTION
	    "The serial number of this enclosure."
	::= { enclEntry 9 }

	enclNumberDiskBays	OBJECT-TYPE
	SYNTAX			INTEGER 
	ACCESS			read-only
	STATUS			mandatory
	DESCRIPTION
	    "The number of disk bays in this enclosure."
	::= { enclEntry 10 }

	enclDisksPresent	OBJECT-TYPE
	SYNTAX			DisplayString
	ACCESS			read-only
	STATUS			mandatory
	DESCRIPTION
	    "The list of disks present by bay number in this enclosure."
	::= { enclEntry 11 }

	enclPowerSuppliesMaximum	OBJECT-TYPE
	SYNTAX				INTEGER
	ACCESS				read-only
	STATUS				mandatory
	DESCRIPTION
	    "The maximum number of power supplies in this enclosure."
	::= { enclEntry 12 }

	enclPowerSuppliesPresent	OBJECT-TYPE
	SYNTAX				DisplayString
	ACCESS				read-only
	STATUS				mandatory
	DESCRIPTION
	    "The list of power supplies present in the enclosure.  
	     Numbering is from left to right in their intended location
	     in the shelf, while facing the supplies."
	::= { enclEntry 13 }
 
	enclPowerSuppliesSerialNos	OBJECT-TYPE
	SYNTAX				DisplayString
	ACCESS				read-only
	STATUS				mandatory
	DESCRIPTION
	    "The list of serial numbers of power supplies present
	     in the enclosure.  Not all shelves are able to report the
	     power supply serial number.  Communication errors may
	     make the serial number unavailable.  Numbering is from left
	     to right in their intended location in the shelf, while
	     facing the supplies."
	::= { enclEntry 14 }
 
	enclPowerSuppliesFailed	OBJECT-TYPE
	SYNTAX			DisplayString
	ACCESS			read-only
	STATUS			mandatory
	DESCRIPTION
	    "The list of failed power supplies in this enclosure, numbered as
	     in enclPowerSuppliesPresent."
	::= { enclEntry 15 }

	enclFansMaximum	OBJECT-TYPE
	SYNTAX		INTEGER
	ACCESS		read-only
	STATUS		mandatory
	DESCRIPTION
	    "The maximum number of fans or fan modules monitored by this
	     enclosure.  R100/R150 shelf power supply fans are not included
	     in this number."
	::= { enclEntry 16 }

	enclFansPresent	OBJECT-TYPE
	SYNTAX		DisplayString
	ACCESS		read-only
	STATUS		mandatory
	DESCRIPTION
	    "The list of fans or fan modules present and for which status
	     is known in this enclosure.  Fans are numbered left-to-right as
	     facing the fans.  R100/R150 shelf power supply fans are
	     not included in this list."
	::= { enclEntry 17 }

	enclFansFailed	OBJECT-TYPE
	SYNTAX		DisplayString
	ACCESS		read-only
	STATUS		mandatory
	DESCRIPTION
	    "The list of failed fans or fan modules in this enclosure.  Fans
	     are numbered as described in enclFansPresent."
	::= { enclEntry 18 }

	enclTempSensorsMaximum	OBJECT-TYPE
	SYNTAX			INTEGER
	ACCESS			read-only
	STATUS			mandatory
	DESCRIPTION
	    "The maximum number of temperature sensors monitored
	     by this enclosure."
	::= { enclEntry 19 }
 
	enclTempSensorsPresent	OBJECT-TYPE
	SYNTAX			DisplayString
	ACCESS			read-only
	STATUS			mandatory
	DESCRIPTION
	    "The list of temperature sensors present and for which
	     status is known in this enclosure.  Temperature sensors are
	     numbered top-to-bottom and left-to-right, beginning with
	     the front of the enclosure, then the rear, as the modules
	     containing them are faced."
	::= { enclEntry 20 }
 
	enclTempSensorsOverTempFail	OBJECT-TYPE
	SYNTAX				DisplayString
	ACCESS				read-only
	STATUS				mandatory
	DESCRIPTION
	    "The list of temperature sensors reporting
	     overtemperature failure in this enclosure.  Sensors are
	     numbered as in TempSensorsPresent."
	::= { enclEntry 21 }

	enclTempSensorsOverTempWarn	OBJECT-TYPE
	SYNTAX				DisplayString
	ACCESS				read-only
	STATUS				mandatory
	DESCRIPTION
	    "The list of temperature sensors reporting overtemperature
	     warning in this enclosure.  Sensors are numbered as in
	     TempSensorsPresent."
	::= { enclEntry 22 }
 
	enclTempSensorsUnderTempFail	OBJECT-TYPE
	SYNTAX				DisplayString
	ACCESS				read-only
	STATUS				mandatory
	DESCRIPTION
	    "The list of temperature sensors reporting undertemperature
	     failure in this enclosure.  Sensors are numbered as in
	     TempSensorsPresent."
	::= { enclEntry 23 }
 
	enclTempSensorsUnderTempWarn	OBJECT-TYPE
	SYNTAX				DisplayString
	ACCESS				read-only
	STATUS				mandatory
	DESCRIPTION
	    "The list of temperature sensors reporting undertemperature
	     warning in this enclosure.  Sensors are numbered as in
	     TempSensorsPresent."
	::= { enclEntry 24 }
 
	enclTempSensorsCurrentTemp	OBJECT-TYPE
	SYNTAX				DisplayString
	ACCESS				read-only
	STATUS				mandatory
	DESCRIPTION
	    "The list of temperatures reported by all temperature sensors in
	     the enclosure, including the ambient temperature.  Sensors are
	     numbered as in TempSensorsPresent."
	::= { enclEntry 25 }
 
	enclTempSensorsOverTempFailThr	OBJECT-TYPE
	SYNTAX				DisplayString
	ACCESS				read-only
	STATUS				mandatory
	DESCRIPTION
	    "The list of overtemperature failure thresholds for all
	     temperature sensors in the enclosure.  Sensors are
	     numbered as in TempSensorsPresent."
	::= { enclEntry 26 }

	enclTempSensorsOverTempWarnThr	OBJECT-TYPE
	SYNTAX				DisplayString
	ACCESS				read-only
	STATUS				mandatory
	DESCRIPTION
	    "The list of overtemperature warning thresholds for all
	     temperature sensors in the enclosure.  Sensors are
	     numbered as in TempSensorsPresent."
	::= { enclEntry 27 }
 
	enclTempSensorsUnderTempFailThr	OBJECT-TYPE
	SYNTAX				DisplayString
	ACCESS				read-only
	STATUS				mandatory
	DESCRIPTION
	    "The list of undertemperature failure thresholds for all
	     temperature sensors in the enclosure.  Sensors are numbered as
	     in TempSensorsPresent."
	::= { enclEntry 28 }
 
	enclTempSensorsUnderTempWarnThr	OBJECT-TYPE
	SYNTAX				DisplayString
	ACCESS				read-only
	STATUS				mandatory
	DESCRIPTION
	    "The list of undertemperature warning thresholds for all
	     temperature sensors in the enclosure.   Sensors are numbered as
	     in TempSensorsPresent."
	::= { enclEntry 29 }
 
	enclElectronicsMaximum	OBJECT-TYPE
	SYNTAX			INTEGER 
	ACCESS			read-only
	STATUS			mandatory
	DESCRIPTION
	    "The number of enclosure services electronics modules that it is
	     possible for this enclosure to detect and/or monitor."
	::= { enclEntry 30 }
 
	enclElectronicsPresent	OBJECT-TYPE
	SYNTAX			DisplayString
	ACCESS			read-only
	STATUS			mandatory
	DESCRIPTION
	    "The list those enclosure services electronics modules present in
	     this enclosure.  Numbering is from left-to-right or top-to-bottom
	     in their intended location in the shelf, while facing the
	     electronics modules.  It is normal for the R200 FC-AT module to be
	     reported as the second module." 
	::= { enclEntry 31 }
 
	enclElectronicsSerialNos	OBJECT-TYPE
	SYNTAX				DisplayString
	ACCESS				read-only
	STATUS				mandatory
	DESCRIPTION
	    "The list of serial numbers of the enclosure services electronics
	     modules present in this enclosure.  The order follows that of
	     enclElectronicsPresent."
	::= { enclEntry 32 }
 
	enclElectronicsFailed		OBJECT-TYPE
	SYNTAX				DisplayString
	ACCESS				read-only
	STATUS				mandatory
	DESCRIPTION
	    "The list of failed electronics elements.  Valid only if
	     enclElectronicsPresent shows that some are present."
	::= { enclEntry 33 }

	enclVoltSensorsMaximum		OBJECT-TYPE
	SYNTAX			        INTEGER
	ACCESS				read-only
	STATUS				mandatory
	DESCRIPTION
	    "The number of voltage sensors monitored by
	     this enclosure."
	::= { enclEntry 34 }

	enclVoltSensorsPresent	OBJECT-TYPE
	SYNTAX			DisplayString
	ACCESS			read-only
	STATUS			mandatory
	DESCRIPTION
	    "The list of voltage sensors present and for which
	     status is known in this enclosure.  Voltage sensors are
	     numbered top-to-bottom and left-to-right, beginning with
	     the front of the enclosure, then the rear, as the modules
	     containing them are faced."
	::= { enclEntry 35 }
 
	enclVoltSensorsOverVoltFail	OBJECT-TYPE
	SYNTAX				DisplayString
	ACCESS				read-only
	STATUS				mandatory
	DESCRIPTION
	    "The list of voltage sensors reporting
	     overvoltage failure in this enclosure.  Sensors are
	     numbered as in VoltSensorsPresent."
	::= { enclEntry 36 }

	enclVoltSensorsOverVoltWarn	OBJECT-TYPE
	SYNTAX				DisplayString
	ACCESS				read-only
	STATUS				mandatory
	DESCRIPTION
	    "The list of voltage sensors reporting overvoltage
	     warning in this enclosure.  Sensors are numbered as in
	     VoltSensorsPresent."
	::= { enclEntry 37 }
 
	enclVoltSensorsUnderVoltFail	OBJECT-TYPE
	SYNTAX				DisplayString
	ACCESS				read-only
	STATUS				mandatory
	DESCRIPTION
	    "The list of voltage sensors reporting undervoltage
	     failure in this enclosure.  Sensors are numbered as in
	     VoltSensorsPresent."
	::= { enclEntry 38 }
 
	enclVoltSensorsUnderVoltWarn	OBJECT-TYPE
	SYNTAX				DisplayString
	ACCESS				read-only
	STATUS				mandatory
	DESCRIPTION
	    "The list of voltage sensors reporting undervoltage
	     warning in this enclosure.  Sensors are numbered as in
	     VoltSensorsPresent."
	::= { enclEntry 39 }
 
	enclVoltSensorsCurrentVolt	OBJECT-TYPE
	SYNTAX				DisplayString
	ACCESS				read-only
	STATUS				mandatory
	DESCRIPTION
	    "The list of voltages reported by all voltage sensors in
	     the enclosure, Sensors are
	     numbered as in VoltSensorsPresent."
	::= { enclEntry 40 }
 
	enclVoltSensorsOverVoltFailThr	OBJECT-TYPE
	SYNTAX				DisplayString
	ACCESS				read-only
	STATUS				mandatory
	DESCRIPTION
	    "The list of overvoltage failure thresholds for all
	     voltage sensors in the enclosure.  Sensors are
	     numbered as in VoltSensorsPresent."
	::= { enclEntry 41 }

	enclVoltSensorsOverVoltWarnThr	OBJECT-TYPE
	SYNTAX				DisplayString
	ACCESS				read-only
	STATUS				mandatory
	DESCRIPTION
	    "The list of overvoltage warning thresholds for all
	     voltage sensors in the enclosure.  Sensors are
	     numbered as in VoltSensorsPresent."
	::= { enclEntry 42 }
 
	enclVoltSensorsUnderVoltFailThr	OBJECT-TYPE
	SYNTAX				DisplayString
	ACCESS				read-only
	STATUS				mandatory
	DESCRIPTION
	    "The list of undervoltage failure thresholds for all
	     voltage sensors in the enclosure.  Sensors are numbered as
	     in VoltSensorsPresent."
	::= { enclEntry 43 }
 
	enclVoltSensorsUnderVoltWarnThr	OBJECT-TYPE
	SYNTAX				DisplayString
	ACCESS				read-only
	STATUS				mandatory
	DESCRIPTION
	    "The list of undervoltage warning thresholds for all
	     voltage sensors in the enclosure.   Sensors are numbered as
	     in VoltSensorsPresent."
	::= { enclEntry 44 }

	enclCurSensorsMaximum		OBJECT-TYPE
	SYNTAX			        INTEGER
	ACCESS				read-only
	STATUS				mandatory
	DESCRIPTION
	    "The number of current sensors monitored by
	     this enclosure."
	::= { enclEntry 45 }

	enclCurSensorsPresent	OBJECT-TYPE
	SYNTAX			DisplayString
	ACCESS			read-only
	STATUS			mandatory
	DESCRIPTION
	    "The list of current sensors present and for which
	     status is known in this enclosure.  Current sensors are
	     numbered top-to-bottom and left-to-right, beginning with
	     the front of the enclosure, then the rear, as the modules
	     containing them are faced."
	::= { enclEntry 46 }
 
	enclCurSensorsOverCurFail	OBJECT-TYPE
	SYNTAX				DisplayString
	ACCESS				read-only
	STATUS				mandatory
	DESCRIPTION
	    "The list of current sensors reporting
	     overcurrent failure in this enclosure.  Sensors are
	     numbered as in CurSensorsPresent."
	::= { enclEntry 47 }

	enclCurSensorsOverCurWarn	OBJECT-TYPE
	SYNTAX				DisplayString
	ACCESS				read-only
	STATUS				mandatory
	DESCRIPTION
	    "The list of current sensors reporting overcurrent
	     warning in this enclosure.  Sensors are numbered as in
	     CurSensorsPresent."
	::= { enclEntry 48 }
 
	enclCurSensorsCurrentCur	OBJECT-TYPE
	SYNTAX				DisplayString
	ACCESS				read-only
	STATUS				mandatory
	DESCRIPTION
	    "The list of currents reported by all current sensors in
	     the enclosure, Sensors are
	     numbered as in CurSensorsPresent."
	::= { enclEntry 49 }
 
	enclCurSensorsOverCurFailThr	OBJECT-TYPE
	SYNTAX				DisplayString
	ACCESS				read-only
	STATUS				mandatory
	DESCRIPTION
	    "The list of overcurrent failure thresholds for all
	     current sensors in the enclosure.  Sensors are
	     numbered as in CurSensorsPresent."
	::= { enclEntry 50 }

	enclCurSensorsOverCurWarnThr	OBJECT-TYPE
	SYNTAX				DisplayString
	ACCESS				read-only
	STATUS				mandatory
	DESCRIPTION
	    "The list of overcurrent warning thresholds for all
	     current sensors in the enclosure.  Sensors are
	     numbered as in CurSensorsPresent."
	::= { enclEntry 51 }
 
	-- -- -- -- -- -- -- --
	-- the network group
	-- -- -- -- -- -- -- --

	netInterfaces OBJECT IDENTIFIER ::= { network 1 }

	-- The net Interfaces table contains information on the entity's
	-- interfaces.  


	netifNumber OBJECT-TYPE
	SYNTAX  INTEGER
	ACCESS  read-only
	STATUS  mandatory
	DESCRIPTION
                      "The number of network interfaces (regardless of
                      their current state) present on this system."
	::= { netInterfaces 1 }

	netifTable OBJECT-TYPE
	SYNTAX  SEQUENCE OF NetIfEntry
	ACCESS  not-accessible
	STATUS  mandatory
	DESCRIPTION
	        "A list of interface entries.  The number of
                 entries is given by the value of netifNumber."
	::= { netInterfaces 2 }

        netifEntry OBJECT-TYPE
	SYNTAX  NetIfEntry
	ACCESS  not-accessible
	STATUS  mandatory
	DESCRIPTION
                      "An interface entry containing objects at the
                      subnetwork layer and below for a particular
                      interface."
	INDEX   { netifIndex }
	::= { netifTable 1 }

	NetIfEntry ::=
	    SEQUENCE {
		netifIndex
		    INTEGER,
		netifDescr
                      DisplayString,
		ifHighInOctets
                      Counter,
		ifLowInOctets
                      Counter,
	    	ifHighInUcastPkts
                      Counter,
		ifLowInUcastPkts
                      Counter,
		ifHighInNUcastPkts
                      Counter,
		ifLowInNUcastPkts
                      Counter,
		ifHighInDiscards
                      Counter,
		ifLowInDiscards
                      Counter,
		ifHighInErrors
                      Counter,
		ifLowInErrors
                      Counter,
		ifHighInUnknownProtos
                      Counter,
		ifLowInUnknownProtos
                      Counter,
		ifHighOutOctets
                      Counter,
		ifLowOutOctets
                      Counter,
		ifHighOutUcastPkts
                      Counter,
		ifLowOutUcastPkts
                      Counter,
		ifHighOutNUcastPkts
                      Counter,
		ifLowOutNUcastPkts
                      Counter,
		ifHighOutDiscards
                      Counter,
		ifLowOutDiscards
                      Counter,
		ifHighOutErrors
                      Counter,
		ifLowOutErrors
                      Counter
	}
        netifIndex OBJECT-TYPE
	SYNTAX	INTEGER (1..2147483647)
     	ACCESS  read-only
	STATUS  mandatory
	DESCRIPTION
                      "A unique value for each interface.  Its value
                      ranges between 1 and the value of ifNumber.  The
                      value for each interface must remain constant at
                      least from one re-initialization of the entity's
                      network management system to the next re-
                      initialization."
        ::= { netifEntry 1 }

	netifDescr OBJECT-TYPE
	SYNTAX  DisplayString (SIZE (0..255))
       	ACCESS  read-only
	STATUS  mandatory
	DESCRIPTION
                      "A textual string containing information about the
                      interface.  This string should include the name of
                      the manufacturer, the product name and the version
                      of the hardware interface."
	::= { netifEntry 2 }

        ifHighInOctets OBJECT-TYPE
	SYNTAX  Counter
       	ACCESS  read-only
	STATUS  mandatory
	DESCRIPTION
                     "The total number of octets received on the
                      interface, including framing characters.
		      This object returns the most significant 32 bits of
		      the 64 bit unsigned integer."
	::= { netifEntry 3 }

        ifLowInOctets OBJECT-TYPE
	SYNTAX  Counter
       	ACCESS  read-only
	STATUS  mandatory
	DESCRIPTION
                     "The total number of octets received on the
                      interface, including framing characters.
		      This object returns the least significant 32 bits of
		      the 64 bit unsigned integer."
	::= { netifEntry 4 }

	ifHighInUcastPkts OBJECT-TYPE
	SYNTAX  Counter
	ACCESS  read-only
	STATUS  mandatory
	DESCRIPTION
                      "The number of subnetwork-unicast packets
                      delivered to a higher-layer protocol.
		      This object returns the most significant 32 bits of
		      the 64 bit unsigned integer."
	::= { netifEntry 5 }

	ifLowInUcastPkts OBJECT-TYPE
	SYNTAX  Counter
	ACCESS  read-only
	STATUS  mandatory
	DESCRIPTION
                      "The number of subnetwork-unicast packets
                      delivered to a higher-layer protocol.
		      This object returns the least significant 32 bits of
		      the 64 bit unsigned integer."
	::= { netifEntry 6 }


	ifHighInNUcastPkts OBJECT-TYPE
	SYNTAX  Counter
	ACCESS  read-only
	STATUS  mandatory
	DESCRIPTION
                      "The number of non-unicast (i.e., subnetwork-
                      broadcast or subnetwork-multicast) packets
                      delivered to a higher-layer protocol.
		      This object returns the most significant 32 bits of 
		      the 64 bit unsigned integer."
	::= { netifEntry 7 }

	ifLowInNUcastPkts OBJECT-TYPE
	SYNTAX  Counter
	ACCESS  read-only
	STATUS  mandatory
	DESCRIPTION
                      "The number of non-unicast (i.e., subnetwork-
                      broadcast or subnetwork-multicast) packets
                      delivered to a higher-layer protocol.
		      This object returns the least significant 32 bits of
		      the 64 bit unsigned integer."
	::= { netifEntry 8 }

	ifHighInDiscards OBJECT-TYPE
	SYNTAX  Counter
	ACCESS  read-only
	STATUS  mandatory
	DESCRIPTION
                      "The number of inbound packets which were chosen
                      to be discarded even though no errors had been
                      detected to prevent their being deliverable to a
                      higher-layer protocol.  One possible reason for
                      discarding such a packet could be to free up
                      buffer space. This object returns the most 
		      significant 32 bits of the 64 bit unsigned integer."
	::= { netifEntry 9 }

	ifLowInDiscards OBJECT-TYPE
	SYNTAX  Counter
	ACCESS  read-only
	STATUS  mandatory
	DESCRIPTION
                      "The number of inbound packets which were chosen
                      to be discarded even though no errors had been
                      detected to prevent their being deliverable to a
                      higher-layer protocol.  One possible reason for
                      discarding such a packet could be to free up
                      buffer space. This object returns the least 
		      significant 32 bits of the 64 bit unsigned integer."
	::= { netifEntry 10 }

	ifHighInErrors OBJECT-TYPE
	SYNTAX  Counter
	ACCESS  read-only
	STATUS  mandatory
	DESCRIPTION
                      "The number of inbound packets that contained
                      errors preventing them from being deliverable to a
                      higher-layer protocol. This object returns the 
		      most significant 32 bits of the 64 bit unsigned integer."
	::= { netifEntry 11 }

	ifLowInErrors OBJECT-TYPE
	SYNTAX  Counter
	ACCESS  read-only
	STATUS  mandatory
	DESCRIPTION
                      "The number of inbound packets that contained
                      errors preventing them from being deliverable to a
                      higher-layer protocol. This object returns the 
		      least significant 32 bits of the 64 bit unsigned integer."
	::= { netifEntry 12 }

	ifHighInUnknownProtos OBJECT-TYPE
	SYNTAX  Counter
	ACCESS  read-only
	STATUS  mandatory
	DESCRIPTION
                      "The number of packets received via the interface
                      which were discarded because of an unknown or
                      unsupported protocol. This object returns the 
		      most significant 32 bits of the 64 bit unsigned integer."
	::= { netifEntry 13 }

	ifLowInUnknownProtos OBJECT-TYPE
	SYNTAX  Counter
	ACCESS  read-only
	STATUS  mandatory
	DESCRIPTION
                      "The number of packets received via the interface
                      which were discarded because of an unknown or
                      unsupported protocol. This object returns the 
		      least significant 32 bits of the 64 bit unsigned integer."
	::= { netifEntry 14 }

	ifHighOutOctets OBJECT-TYPE
	SYNTAX  Counter
	ACCESS  read-only
	STATUS  mandatory
	DESCRIPTION
                      "The total number of octets transmitted out of the
                      interface, including framing characters.
                      This object returns the most significant 32 bits of the
		      64 bit unsigned integer."
	::= { netifEntry 15 }

	ifLowOutOctets OBJECT-TYPE
	SYNTAX  Counter
	ACCESS  read-only
	STATUS  mandatory
	DESCRIPTION
                      "The total number of octets transmitted out of the
                      interface, including framing characters.
                      This object returns the least significant 32 bits of
		      the 64 bit unsigned integer."
	::= { netifEntry 16 }

	ifHighOutUcastPkts OBJECT-TYPE
	SYNTAX  Counter
	ACCESS  read-only
	STATUS  mandatory
	DESCRIPTION
                      "The total number of packets that higher-level
                      protocols requested be transmitted to a
                      subnetwork-unicast address, including those that
                      were discarded or not sent. This object returns 
		      the most significant 32 bits of the 64 bit unsigned 
		      integer."
	::= { netifEntry 17 }

	ifLowOutUcastPkts OBJECT-TYPE
	SYNTAX  Counter
	ACCESS  read-only
	STATUS  mandatory
	DESCRIPTION
                      "The total number of packets that higher-level
                      protocols requested be transmitted to a
                      subnetwork-unicast address, including those that
                      were discarded or not sent. This object returns 
		      the least significant 32 bits of the 64 bit unsigned 
		      integer."
	::= { netifEntry 18 }

	ifHighOutNUcastPkts OBJECT-TYPE
	SYNTAX  Counter
	ACCESS  read-only
	STATUS  mandatory
	DESCRIPTION
                      "The total number of packets that higher-level
                      protocols requested be transmitted to a non-
                      unicast (i.e., a subnetwork-broadcast or
                      subnetwork-multicast) address, including those
                      that were discarded or not sent. This object returns 
		      the most significant 32 bits of the 64 bit unsigned 
		      integer."
	::= { netifEntry 19 }

	ifLowOutNUcastPkts OBJECT-TYPE
	SYNTAX  Counter
	ACCESS  read-only
	STATUS  mandatory
	DESCRIPTION
                      "The total number of packets that higher-level
                      protocols requested be transmitted to a non-
                      unicast (i.e., a subnetwork-broadcast or
                      subnetwork-multicast) address, including those
                      that were discarded or not sent. This object returns 
		      the least significant 32 bits of the 64 bit unsigned 
		      integer."
	::= { netifEntry 20 }

	ifHighOutDiscards OBJECT-TYPE
	SYNTAX  Counter
	ACCESS  read-only
	STATUS  mandatory
	DESCRIPTION
                      "The number of outbound packets which were chosen
                      to be discarded even though no errors had been
                      detected to prevent their being transmitted.  One
                      possible reason for discarding such a packet could
                      be to free up buffer space. This object returns 
		      the most significant 32 bits of the 64 bit unsigned 
		      integer."
	::= { netifEntry 21 }

	ifLowOutDiscards OBJECT-TYPE
	SYNTAX  Counter
	ACCESS  read-only
	STATUS  mandatory
	DESCRIPTION
                      "The number of outbound packets which were chosen
                      to be discarded even though no errors had been
                      detected to prevent their being transmitted.  One
                      possible reason for discarding such a packet could
                      be to free up buffer space. This object returns 
		      the least significant 32 bits of the 64 bit unsigned 
		      integer."
	::= { netifEntry 22 }

	ifHighOutErrors OBJECT-TYPE
	SYNTAX  Counter
	ACCESS  read-only
	STATUS  mandatory
	DESCRIPTION
                      "The number of outbound packets that could not be
                      transmitted because of errors. This object returns 
		      the most significant 32 bits of the 64 bit unsigned 
		      integer."
	::= { netifEntry 23 }

	ifLowOutErrors OBJECT-TYPE
	SYNTAX  Counter
	ACCESS  read-only
	STATUS  mandatory
	DESCRIPTION
                      "The number of outbound packets that could not be
                      transmitted because of errors. This object returns 
		      the least significant 32 bits of the 64 bit unsigned 
		      integer."
	::= { netifEntry 24 }

	-- -- -- -- -- -- -- --
	-- the sis group
	-- -- -- -- -- -- -- --

	sisIsLicensed	OBJECT-TYPE
	SYNTAX		INTEGER {
				false(1),
				true(2)
			}
	ACCESS		read-only
	STATUS		mandatory
	DESCRIPTION
			"Indicates whether Advanced SIS is licensed on the
			filer."
	::= { sis 1 }
	
	sisTable	OBJECT-TYPE
	SYNTAX		SEQUENCE OF SisEntry
	ACCESS		not-accessible
	STATUS		mandatory
	DESCRIPTION
			"Provide a list of the SIS volumes on the
			 system."

	::= { sis 2 }

	sisEntry	OBJECT-TYPE
	SYNTAX		SisEntry
	ACCESS		not-accessible
	STATUS		mandatory
	DESCRIPTION
			"Provide details about a particular SIS volume."

	INDEX	{ sisIndex }
	::= { sisTable 1 }

	SisEntry ::=
	    SEQUENCE {
	    	sisIndex	
		    INTEGER,
		sisPath
		    DisplayString,
		sisState
		    INTEGER,
		sisStatus
		    INTEGER,
		sisProgress
		    DisplayString,
		sisType
		    INTEGER,
		sisSchedule
		    DisplayString,
		sisLastOpBeginTime
		    DisplayString,
		sisLastOpEndTime
		    DisplayString,
		sisHighLastOpSize
		    INTEGER,
		sisLowLastOpSize
		    INTEGER,
		sisLastOpError
		    DisplayString
	    }

	sisIndex		OBJECT-TYPE
	SYNTAX			INTEGER (1..2147483647)
	ACCESS			read-only
	STATUS			mandatory
	DESCRIPTION
				"A number that identifies this entry for the
				 SIS volume."
	::= { sisEntry 1 }

	sisPath			OBJECT-TYPE
	SYNTAX			DisplayString
	ACCESS			read-only
	STATUS			mandatory
	DESCRIPTION
				"The path to the SIS volume."
	::= { sisEntry 2 }

	sisState		OBJECT-TYPE
	SYNTAX			INTEGER {
					disabled(1),
					enabled(2)
				}	
	ACCESS			read-only
	STATUS			mandatory
	DESCRIPTION
				"Indicates whether SIS is enabled on the
				 volume or not."
	::= { sisEntry 3 }

	sisStatus		OBJECT-TYPE
	SYNTAX			INTEGER {
					idle(1),
					active(2),
					undoing(3),
					pending(4)
				}
	ACCESS			read-only
	STATUS			mandatory
	DESCRIPTION
				"Current status of the SIS volume."
	::= { sisEntry 4 }

	sisProgress		OBJECT-TYPE
	SYNTAX			DisplayString
	ACCESS			read-only
	STATUS			mandatory
	DESCRIPTION
				"The progress of the current SIS operation."
	::= { sisEntry 5 }

	sisType		OBJECT-TYPE
	SYNTAX			INTEGER {
					regular(1),
					snapvault(2)
				}
	ACCESS			read-only
	STATUS			mandatory
	DESCRIPTION
				"Indicates whether it is a regular or
				 snapvaulted SIS volume."
	::= { sisEntry 6 }

	sisSchedule		OBJECT-TYPE
	SYNTAX			DisplayString
	ACCESS			read-only
	STATUS			mandatory
	DESCRIPTION
				"The schedule for the SIS opertions."
	::= { sisEntry 7 }

	sisLastOpBeginTime	OBJECT-TYPE
	SYNTAX			DisplayString
	ACCESS			read-only
	STATUS			mandatory
	DESCRIPTION
				"The starting time of the last completed SIS
				 opertion."
	::= { sisEntry 8 }

	sisLastOpEndTime	OBJECT-TYPE
	SYNTAX			DisplayString
	ACCESS			read-only
	STATUS			mandatory
	DESCRIPTION
				"The ending time of the last completed SIS
				 operation."
	::= { sisEntry 9 }

	sisHighLastOpSize	OBJECT-TYPE
	SYNTAX			INTEGER
	ACCESS			read-only
	STATUS			mandatory
	DESCRIPTION
				"The total amount of data in KBytes that the
				 last completed SIS operation had processed.
				 This object returns the most significant 32
				 bits of the 64 bit unsigned integer."
	::= { sisEntry 10 }

	sisLowLastOpSize	OBJECT-TYPE
	SYNTAX			INTEGER
	ACCESS			read-only
	STATUS			mandatory
	DESCRIPTION
				"The total amount of data in KBytes that the
				 last completed SIS operation had processed.
				 This object returns the least significant 32
				 bits of the 64 bit unsigned integer."
	::= { sisEntry 11 }

	sisLastOpError		OBJECT-TYPE
	SYNTAX			DisplayString
	ACCESS			read-only
	STATUS			mandatory
	DESCRIPTION
				"The error that the last SIS operation
				 encountered if it failed."
	::= { sisEntry 12 }


	-- -- -- -- -- -- -- -- -- -- -- -- -- -- -- -- -- -- 
	-- -- -- -- -- -- -- -- -- -- -- -- -- -- -- -- -- -- 
	-- NetApp trap definitions
	-- See RFC 1215 for instructions on building traps
	-- 
	-- All EnterpiseSpecific Traps of Network Appliance
	-- contain the OIDs 'productTrapData and productSerialNum'
	-- except traps with the trap types - 
	--	globalStatusNonRecoverable
	--	globalStatusCritical
	--	globalStatusNonCritical
	--	globalStatusOk
	-- which contain the OIDs 'miscGlobalStatusMessage and productSerialNum'
	--
	-- The last digit of a trap contains information about the
	-- priority of the trap:
	--
	-- 1 emergency
	-- 2 alert
	-- 3 critical
	-- 4 error
	-- 5 warning
	-- 6 notification
	-- 7 information
	-- 8 debug
	--
	-- -- -- -- -- -- -- -- -- -- -- -- -- -- -- -- -- -- 
	-- -- -- -- -- -- -- -- -- -- -- -- -- -- -- -- -- -- 

	-- -- -- -- -- -- -- -- -- -- -- -- -- -- -- -- -- -- 
	--
	--  A generic, unprioritized, user-defined trap.  These
	--  are generated in releases prior to 5.4.
	--
	-- -- -- -- -- -- -- -- -- -- -- -- -- -- -- -- -- -- 

	userDefined	TRAP-TYPE    
	ENTERPRISE	netapp    
	VARIABLES	{productTrapData, productSerialNum}
	DESCRIPTION
            "A polling-style trap built using the 'snmp traps'
	     command on the filer."    
	    
	::= 2

	-- -- -- -- -- -- -- -- -- -- -- -- -- -- -- -- -- --
        -- -- -- -- -- -- -- -- -- -- -- -- -- -- -- -- -- --
        -- Disk Health Monitor Notices for Disk Fault
        -- -- -- -- -- -- -- -- -- -- -- -- -- -- -- -- -- --
        -- -- -- -- -- -- -- -- -- -- -- -- -- -- -- -- -- --

        dhmNoticeDegradedIO     TRAP-TYPE
        ENTERPRISE              netapp
	VARIABLES               {productTrapData, productSerialNum}
        DESCRIPTION
                "Disk Health Monitor -
                Reported a Disk Degraded-I/O  Event"

        ::= 6

        dhmNoticePFAEvent       TRAP-TYPE
        ENTERPRISE              netapp
	VARIABLES               {productTrapData, productSerialNum}
        DESCRIPTION
                "Disk Health Monitor -
                Reported a Disk Predictive-Failure Event"

        ::= 7

	-- -- -- -- -- -- -- -- -- -- -- -- -- -- -- -- -- -- 
	--
	--  This section contains generic user-defined traps.
	--  All user-defined traps with the same priority
	--  use the trap for that priority level.
	--
	--  For example, all "critical" user-defined traps are
	--  sent with ID 13.  The string data sent with the
	--  trap identifies the specific critical event.
	--
	-- -- -- -- -- -- -- -- -- -- -- -- -- -- -- -- -- -- 

        emergencyTrap     TRAP-TYPE    
        ENTERPRISE        netapp    
	VARIABLES         {productTrapData, productSerialNum}
        DESCRIPTION
            "A user-defined trap indicating an extremely urgent
             situation, usually indicating that the system has
             failed and is shutting down."

        ::= 11

        alertTrap         TRAP-TYPE    
        ENTERPRISE        netapp    
	VARIABLES         {productTrapData, productSerialNum}
        DESCRIPTION
            "A user-defined trap indicating a condition that
             should be corrected immediately, such as a failed disk."

        ::= 12

        criticalTrap      TRAP-TYPE    
        ENTERPRISE        netapp    
	VARIABLES         {productTrapData, productSerialNum}
        DESCRIPTION
            "A user-defined trap indicating a critical condition,
             such as a hard device error."

        ::= 13

        errorTrap         TRAP-TYPE    
        ENTERPRISE        netapp    
	VARIABLES         {productTrapData, productSerialNum}
        DESCRIPTION
            "A user-defined trap indicating an error condition,
             such as a mistake in a configuration file."

        ::= 14

        warningTrap       TRAP-TYPE    
        ENTERPRISE        netapp    
	VARIABLES         {productTrapData, productSerialNum}
        DESCRIPTION
            "A user-defined trap indicating a condition which
            is not an error, but which may require special handling."

        ::= 15

        notificationTrap   TRAP-TYPE    
        ENTERPRISE         netapp    
	VARIABLES          {productTrapData, productSerialNum}
        DESCRIPTION
            "A user-defined trap meant to provide notification,
             such as an hourly uptime message."

        ::= 16

        informationalTrap  TRAP-TYPE    
        ENTERPRISE         netapp    
	VARIABLES          {productTrapData, productSerialNum}
        DESCRIPTION
            "A user-defined trap used for informational purposes."

        ::= 17

        dbgTrap            TRAP-TYPE    
        ENTERPRISE         netapp    
	VARIABLES          {productTrapData, productSerialNum}
        DESCRIPTION
            "A user-defined trap used for debugging purposes.
	     This trap was previously mis-documented as being trap
	     number 17, with the name debugTrap.  It has always,
	     actually, been trap 18.  The name change is to avoid
	     issues with environments that already have a record
	     for debugTrap."

        ::= 18

	-- -- -- -- -- -- -- -- -- -- -- -- -- -- -- -- -- -- 
	--
	--  Specific traps.
	--
	-- -- -- -- -- -- -- -- -- -- -- -- -- -- -- -- -- -- 


	diskFailedShutdown	TRAP-TYPE
	ENTERPRISE		netapp
	VARIABLES		{productTrapData, productSerialNum}
	DESCRIPTION
		"System is shutting down because the system has been
		running in degraded mode for 24 hours.
		The trap includes a string describing the failed disk."
	
	::= 21
	
	diskFailed	TRAP-TYPE
	ENTERPRISE	netapp
	VARIABLES	{productTrapData, productSerialNum}
	DESCRIPTION
		"One or more disks failed.
		The trap includes a string describing the failed disk(s)."
	
	::= 22
	
	diskRepaired	TRAP-TYPE
	ENTERPRISE	netapp
	VARIABLES	{productTrapData, productSerialNum}
	DESCRIPTION
		"The failed disks have been repaired.
		This trap is a placeholder -
		it is not currently sent by ONTAP."
	
	::= 26
	
	-- -- -- -- -- -- -- -- -- -- -- -- -- -- -- -- -- -- 
	--
	--  The fan and power supply traps are not supported
	--  on all platforms.
	--
	-- -- -- -- -- -- -- -- -- -- -- -- -- -- -- -- -- -- 

	fanFailureShutdown	TRAP-TYPE
	ENTERPRISE		netapp
	VARIABLES		{productTrapData, productSerialNum}
	DESCRIPTION
		"Critical chassis or cpu fans have failed and the system
		is shutting down."
	
	::= 31
	
	fanFailed	TRAP-TYPE
	ENTERPRISE	netapp
	VARIABLES	{productTrapData, productSerialNum}
	DESCRIPTION
		"One or more chassis fans failed.
		The trap includes a string describing the failed fan(s)."
	
	::= 33
	
	fanWarning	TRAP-TYPE
	ENTERPRISE	netapp
	VARIABLES	{productTrapData, productSerialNum}
	DESCRIPTION
		"One or more chassis or cpu fans are in warning state.
		The trap includes a string describing the fan(s) in
		the warning state."
	
	::= 35

	fanRepaired	TRAP-TYPE
	ENTERPRISE	netapp
	VARIABLES	{productTrapData, productSerialNum}
	DESCRIPTION
		"All fans are repaired."
	
	::= 36
	
	powerSupplyFailureShutdown	TRAP-TYPE
	ENTERPRISE			netapp
	VARIABLES			{productTrapData, productSerialNum}
	DESCRIPTION
		"Critical power supplies or power rails failed and
		the system is shutting down."
	
	::= 41
	
	powerSupplyFailed	TRAP-TYPE
	ENTERPRISE		netapp
	VARIABLES		{productTrapData, productSerialNum}
	DESCRIPTION
		"One or more redundant power supplies failed.
		Include in the trap a string describing
		the failed power supply(ies)."
	
	::= 43

	powerSupplyWarning	TRAP-TYPE
	ENTERPRISE		netapp
	VARIABLES		{productTrapData, productSerialNum}
	DESCRIPTION
		"One or more power supplies or power rails in
		warning state.  Include in the trap a string describing
		the power supply(ies) or the power rail(s) in the
		warning state."
	
	::= 45
	
	powerSupplyRepaired	TRAP-TYPE
	ENTERPRISE	netapp
	VARIABLES	{productTrapData, productSerialNum}
	DESCRIPTION
		"Previously-failed power supplies or power rails have been
		repaired."
	
	::= 46
	
	cpuTooBusy	TRAP-TYPE
	ENTERPRISE	netapp
	VARIABLES	{productTrapData, productSerialNum}
	DESCRIPTION
		"CPU utilization exceeds 90%.
		This trap is not enabled by default.
		To enable this trap set the registry
		entry options.monitor.cpu.enable to on. 
		Note that as the threshold for this trap is
		checked once a minute it is possible to receive
		multiple instances of this trap in a short time."

	
	::= 55
	
	cpuOk		TRAP-TYPE
	ENTERPRISE	netapp
	VARIABLES	{productTrapData, productSerialNum}
	DESCRIPTION
		"CPU utilization has dropped back below 90%.
		This trap is a placeholder -
		it is not currently sent by ONTAP."
	
	::= 56
	
	nvramBatteryDischarged	TRAP-TYPE
	ENTERPRISE		netapp
	VARIABLES		{productTrapData, productSerialNum}
	DESCRIPTION
		"The NVRAM battery is fully discharged."
	
	::= 62
	
	nvramBatteryLow	TRAP-TYPE
	ENTERPRISE	netapp
	VARIABLES	{productTrapData, productSerialNum}
	DESCRIPTION
		"The charge in the NVRAM battery is low."
	
	::= 63
	
	clusterNodeFailed	TRAP-TYPE
	ENTERPRISE		netapp
	VARIABLES		{productTrapData, productSerialNum}
	DESCRIPTION
		"A node in a Cluster FailOver configuration failed.
		Its partner will assume service for the failed node."
	
	::= 72
	
	clusterNodeTakenOver	TRAP-TYPE
	ENTERPRISE		netapp
	VARIABLES		{productTrapData, productSerialNum}
	DESCRIPTION
		"The partner has taken over for a failed cluster node."
	
	::= 75
	
	clusterNodeRepaired	TRAP-TYPE
	ENTERPRISE		netapp
	VARIABLES		{productTrapData, productSerialNum}
	DESCRIPTION
		"A cluster node has resumed operation."
	
	::= 76
	
	volumeFull	TRAP-TYPE
	ENTERPRISE	netapp
	VARIABLES	{productTrapData, productSerialNum}
	DESCRIPTION
		"At least one volume is more than 98% full.
		The string sent with the trap gives the 
		name of the volume or volumes which exceed
		the volumeFull or volumeNearlyFull thresholds"
	
	::= 82
	
	volumeNearlyFull	TRAP-TYPE
	ENTERPRISE		netapp
	VARIABLES		{productTrapData, productSerialNum}
	DESCRIPTION
		"At least one volume is more than 95% full.
		The string sent with the trap gives the 
		name of the volume or volumes which exceed
		the volumeFull or volumeNearlyFull thresholds"
	
	::= 85
	
	volumeRepaired	TRAP-TYPE
	ENTERPRISE	netapp
	VARIABLES	{productTrapData, productSerialNum}
	DESCRIPTION
		"All volumes are now under 95% full."
	
	::= 86
	
	volumesStillFull	TRAP-TYPE
	ENTERPRISE	        netapp
	VARIABLES	        {productTrapData, productSerialNum}
	DESCRIPTION
		"At least one volume that was full or nearly full is now OK,
		but more volumes still exceed the volumeNearlyFull or
		volumeFull thresholds. This trap is generally sent within
		a short time of when a volume becomes OK, though if two
		volumes become OK within this timeframe, only one trap is
		sent. The string sent with the trap gives the name of the 
		volume or volumes which still exceed the volumeFull or 
		volumeNearlyFull thresholds. It does not send the name of 
		any volume that is OK."
	
	::= 87
	
	overTempShutdown	TRAP-TYPE
	ENTERPRISE		netapp
	VARIABLES		{productTrapData, productSerialNum}
	DESCRIPTION
		"System temperature is too high to continue
		operating.  The system is shutting down."
	
	::= 91
	
	overTemp	TRAP-TYPE
	ENTERPRISE	netapp
	VARIABLES	{productTrapData, productSerialNum}
	DESCRIPTION
		"System temperature is too high and in the
		warning level."
	
	::= 95
	
	overTempRepaired	TRAP-TYPE
	ENTERPRISE		netapp
	VARIABLES		{productTrapData, productSerialNum}
	DESCRIPTION
		"System temperature has returned to an
		acceptable value."
	
	::= 96
	
	shelfFault	TRAP-TYPE
	ENTERPRISE	netapp
	VARIABLES	{productTrapData, productSerialNum}
	DESCRIPTION
		"A disk storage shelf reported a fault, probably due
		to a problem with drive placement, fans, power,
		or temperature."
	
	::= 103
	
	
	shelfRepaired	TRAP-TYPE
	ENTERPRISE	netapp
	VARIABLES	{productTrapData, productSerialNum}
	DESCRIPTION
		"A previously-reported shelf fault is now corrected."
	
	::= 106

	-- -- -- -- -- -- -- -- -- -- -- -- -- -- -- -- -- -- 
	--
	--  This section contains "general health" traps,
	--  based on changes to the miscGlobalStatus 
	--  variable.
	--
	-- -- -- -- -- -- -- -- -- -- -- -- -- -- -- -- -- -- 

	globalStatusNonRecoverable	TRAP-TYPE
	ENTERPRISE			netapp
	VARIABLES			{miscGlobalStatusMessage, 
	                                 productSerialNum}
	DESCRIPTION
		"The appliance's overall status changed to
		'nonRecoverable', indicating a problem so severe
		that the appliance is shutting down."
	
	::= 111

	globalStatusCritical	TRAP-TYPE
	ENTERPRISE		netapp
	VARIABLES		{miscGlobalStatusMessage, productSerialNum}
	DESCRIPTION
		"The appliance's overall status changed to 'critical',
		indicating a problem that needs immediate attention."
	
	::= 113

	globalStatusNonCritical	TRAP-TYPE
	ENTERPRISE		netapp
	VARIABLES		{miscGlobalStatusMessage, productSerialNum}
	DESCRIPTION
		"The appliance's overall status changed to 'nonCritical',
		indicating a problem that needs attention."
	
	::= 115
	
	globalStatusOk	TRAP-TYPE
	ENTERPRISE	netapp
	VARIABLES	{miscGlobalStatusMessage, productSerialNum}
	DESCRIPTION
		"The appliance's overall status returned to normal."
	
	::= 116
	
	-- -- -- -- -- -- -- -- -- -- -- -- -- -- -- -- -- -- 
	--
	--  This section contains traps related to soft quotas.
	--
	-- -- -- -- -- -- -- -- -- -- -- -- -- -- -- -- -- -- 

        softQuotaExceeded	TRAP-TYPE    
        ENTERPRISE		netapp    
	VARIABLES		{productTrapData, productSerialNum}
        DESCRIPTION
            "A user has exceeded their soft quota limit."

        ::= 126

        softQuotaNormal		TRAP-TYPE    
        ENTERPRISE		netapp    
	VARIABLES		{productTrapData, productSerialNum}
        DESCRIPTION
            "A user is safely back under their soft quota limit."

        ::= 127

	-- -- -- -- -- -- -- -- -- -- -- -- -- -- -- -- -- -- 
	--
	--  This section contains traps related to autosupport
	--
	-- -- -- -- -- -- -- -- -- -- -- -- -- -- -- -- -- -- 

	autosupportSendError	TRAP-TYPE
	ENTERPRISE		netapp
	VARIABLES		{productTrapData, productSerialNum}
	DESCRIPTION
		"Unable to send autosupport.
		The trap includes a string describing the reason for the failure."
	
	::= 134

	autosupportConfigurationError	TRAP-TYPE
	ENTERPRISE			netapp
	VARIABLES			{productTrapData, productSerialNum}
	DESCRIPTION
		"Autosupport may be configured incorrectly.
		The trap includes a string describing the mis-configuration."
	
	::= 135
	
	autosupportSent		TRAP-TYPE
	ENTERPRISE		netapp
	VARIABLES		{productTrapData, productSerialNum}
	DESCRIPTION
		"Autosupport was sent successfully."
	
	::= 136
	
	-- -- -- -- -- -- -- -- -- -- -- -- -- -- -- -- -- -- 
	--
	--  This section contains traps related to UPS
	--
	-- -- -- -- -- -- -- -- -- -- -- -- -- -- -- -- -- -- 
	
	upsLinePowerOff		TRAP-TYPE
	ENTERPRISE		netapp
	VARIABLES		{productTrapData, productSerialNum}
	DESCRIPTION
		"UPS: Input line power has failed and UPS is now on battery."

	::= 142

	upsBatteryCritical	TRAP-TYPE
	ENTERPRISE		netapp
	VARIABLES		{productTrapData, productSerialNum}
	DESCRIPTION
		"UPS: Battery is nearly exhausted, starting graceful shutdown."

	::= 143


	upsShuttingDown	TRAP-TYPE
	ENTERPRISE		netapp
	VARIABLES		{productTrapData, productSerialNum}
	DESCRIPTION
		"UPS: Shutting down now: Time left on battery is exhuasted."

	::= 144
	upsBatteryWarning	TRAP-TYPE
	ENTERPRISE		netapp
	VARIABLES		{productTrapData, productSerialNum}
	DESCRIPTION
		"UPS: Warning: Time left on battery is getting critical."

	::= 145

	upsLinePowerRetored	TRAP-TYPE
	ENTERPRISE		netapp
	VARIABLES		{productTrapData, productSerialNum}
	DESCRIPTION
		"UPS:  Input line power has been restored and UPS is now off battery."

	::= 146

	-- -- -- -- -- -- -- -- -- -- -- -- -- -- -- -- -- -- -- -- -- --
	--
	--  This section contains traps related to Client Side Applications.
	--
	-- -- -- -- -- -- -- -- -- -- -- -- -- -- -- -- -- -- -- -- -- --
	
	appEmergency		TRAP-TYPE
	ENTERPRISE		netapp
	VARIABLES		{productTrapData, productSerialNum}
	DESCRIPTION
		"The application encountered an extremely urgent
		situation and requires an immediate response."

	::= 151

	appAlert		TRAP-TYPE
	ENTERPRISE		netapp
	VARIABLES		{productTrapData, productSerialNum}
	DESCRIPTION
		"The application is in a condition that should 
		be corrected immediately."

	::= 152

	appCritical		TRAP-TYPE
	ENTERPRISE		netapp
	VARIABLES		{productTrapData, productSerialNum}
	DESCRIPTION
		"The application encountered a critical condition."

	::= 153

	appError		TRAP-TYPE
	ENTERPRISE		netapp
	VARIABLES		{productTrapData, productSerialNum}
	DESCRIPTION
		"The application encountered an error condition."

	::= 154

	appWarning		TRAP-TYPE
	ENTERPRISE		netapp
	VARIABLES		{productTrapData, productSerialNum}
	DESCRIPTION
		"The application is in a condition which is not an 
		error, but which may require special handling."

        ::= 155

	appNotice		TRAP-TYPE
	ENTERPRISE		netapp
	VARIABLES		{productTrapData, productSerialNum}
	DESCRIPTION
		"The application is notifing of a certain event."

        ::= 156

	appInfo			TRAP-TYPE
	ENTERPRISE		netapp
	VARIABLES		{productTrapData, productSerialNum}
	DESCRIPTION
		"The application's message is meant for informational 
		purposes."

        ::= 157

	appTrap			TRAP-TYPE
	ENTERPRISE		netapp
	VARIABLES		{productTrapData, productSerialNum}
	DESCRIPTION
		"The application requires to be debugged."

        ::= 158

	-- -- -- -- -- -- -- -- -- -- -- -- -- -- -- -- -- -- -- -- -- --
	--
	--  This section contains traps related to Autosaving NT EVT files.
	--
	-- -- -- -- -- -- -- -- -- -- -- -- -- -- -- -- -- -- -- -- -- --
	
	alfFilewrap		TRAP-TYPE
	ENTERPRISE		netapp
	VARIABLES		{productTrapData, productSerialNum}
	DESCRIPTION
		"The internal audit file has wrapped. You are currently losing event
		records.  Warning the user."

        ::= 162
	

	alfFileSaved	TRAP-TYPE
	ENTERPRISE	netapp
	VARIABLES	{productTrapData, productSerialNum}
	DESCRIPTION
		"The internal audit log has been autosaved to an external evt file.
		Notifying the user."

        ::= 166

	alfFileNearlyFull	TRAP-TYPE
	ENTERPRISE		netapp
	VARIABLES		{productTrapData, productSerialNum}
	DESCRIPTION
		"The internal audit log file is nearly full. The file is going to 
		wrap. Notifying the user."

        ::= 167

	-- -- -- -- -- -- -- -- -- -- -- -- -- -- -- -- -- -- -- -- -- --
	--
	--  This section contains traps related to generalized quota events.
	--
	-- -- -- -- -- -- -- -- -- -- -- -- -- -- -- -- -- -- -- -- -- --

        quotaExceeded		TRAP-TYPE    
        ENTERPRISE		netapp    
	VARIABLES		{productTrapData, productSerialNum}
        DESCRIPTION
            "One of the quota limits has been exceeded.
	    The trap includes a string describing the specific event
	    which triggered the trap.  The string is structured
	    in the following form:

		Quota Event: status=exceeded, type={hard|soft|threshold},
		user={username}, volume={volume}, limit_item={files|disk},
		limit_value={#files|#kilobytes}
		[ , treeid={tree-id} ] [ , vfiler={vfiler} ]

	    An example of a complete message would be:

		Quota Event: status=exceeded, type=soft,
		user=admin, volume=vol1, limit_item=disk, limit_value=1000000,
		treeid=8

	    Additional key=value items may, in the future, be appended
	    to this message."

        ::= 176

        quotaNormal		TRAP-TYPE    
        ENTERPRISE		netapp    
	VARIABLES		{productTrapData, productSerialNum}
        DESCRIPTION
            "One of the quota limits has gone back down to a normal level.
	    The trap includes a string describing the specific event
	    which triggered the trap.  The string is structured
	    in the following form:

		Quota Event: status=normal, type={hard|soft|threshold},
		user={username}, volume={volume}, limit_item={files|disk},
		limit_value={#files|#kilobytes}
		[ , treeid={tree-id} ] [ , vfiler={vfiler} ]

	    An example of a complete message would be:

		Quota Event: status=normal, type=soft,
		user=admin, volume=vol1, limit_item=disk, limit_value=1000000,
		treeid=8

	    Additional key=value items may, in the future, be appended
	    to this message."

        ::= 177

        -- -- -- -- -- -- -- -- -- -- -- -- -- -- -- -- -- -- -- -- -- --
	--
	--  This section contains traps related to alerting when 64MB directory
	--  limit is nearly reached or has been reached.
	--
	-- -- -- -- -- -- -- -- -- -- -- -- -- -- -- -- -- -- -- -- -- --

	waflDirFull			TRAP-TYPE
	ENTERPRISE			netapp
	VARIABLES			{productTrapData, productSerialNum}
	DESCRIPTION
		"The directory has been filled to its limit"

        ::= 187

	-- -- -- -- -- -- -- -- -- -- -- -- -- -- -- -- -- -- -- -- -- -- -- --
	--
	--  This section contains traps related to Correctable Memory ECC 
	--  errors
	--
	-- -- -- -- -- -- -- -- -- -- -- -- -- -- -- -- -- -- -- -- -- -- -- --
	
	eccSummary		TRAP-TYPE
	ENTERPRISE		netapp
	VARIABLES		{productTrapData, productSerialNum}
	DESCRIPTION
		"Memory ECC: number of new correctable ECC errors"

	::= 192

	eccMasked		TRAP-TYPE
	ENTERPRISE		netapp
	VARIABLES		{productTrapData, productSerialNum}
	DESCRIPTION
		"Memory ECC: High frequency of ECC errors"

	::= 195

       	-- -- -- -- -- -- -- -- -- -- -- -- -- -- -- -- -- -- -- -- -- --
	--
	--  This section contains traps related to ftpd service
	--
	-- -- -- -- -- -- -- -- -- -- -- -- -- -- -- -- -- -- -- -- -- --

	ftpdError			TRAP-TYPE
	ENTERPRISE			netapp
	VARIABLES			{productTrapData, productSerialNum}
	DESCRIPTION
		"Ftp daemon: service stopped"

        ::= 204

	ftpdMaxConnNotice		TRAP-TYPE
	ENTERPRISE			netapp
	VARIABLES			{productTrapData, productSerialNum}
	DESCRIPTION
		"Ftp daemon: number of connections hits maximum number"

        ::= 206

       	-- -- -- -- -- -- -- -- -- -- -- -- -- -- -- -- -- -- -- -- -- --
	--
	--  This section contains additional traps related to ftpd service
	--
	-- -- -- -- -- -- -- -- -- -- -- -- -- -- -- -- -- -- -- -- -- --

	ftpdMaxConnThresholdNotice	TRAP-TYPE
	ENTERPRISE			netapp
	VARIABLES			{productTrapData, productSerialNum}
	DESCRIPTION
		"Ftp daemon: number of connections nearly hits maximum number"

        ::= 216

	-- -- -- -- -- -- -- -- -- -- -- -- -- -- -- -- -- -- -- -- -- -- -- --
	--
	--  This section contains traps related to SCSI Target 
	--
	-- -- -- -- -- -- -- -- -- -- -- -- -- -- -- -- -- -- -- -- -- -- -- --

	scsitgtFCPLinkBreak TRAP-TYPE
	ENTERPRISE		netapp
	DESCRIPTION
		"SCSI Target: Link Break on FCP adapter"

	::= 222

	scsitgtPartnerPathMisconfigured	TRAP-TYPE
	ENTERPRISE			netapp
	VARIABLES			{productTrapData, productSerialNum}
	DESCRIPTION
		"SCSI Target: FCP Partner Path Misconfigured"

	::= 224

	scsitgtThrottleNotice		TRAP-TYPE
	ENTERPRISE			netapp
	VARIABLES			{productTrapData, productSerialNum}
	DESCRIPTION
		"SCSI Target: Throttle limit event notification"

	::= 226

	-- -- -- -- -- -- -- -- -- -- -- -- -- -- -- -- -- -- -- -- -- -- -- --
	--
	--  This section contains traps related to VIF Failover & Link Status
	--
	-- -- -- -- -- -- -- -- -- -- -- -- -- -- -- -- -- -- -- -- -- -- -- --

	vifPrimaryLinkFailed		TRAP-TYPE
	ENTERPRISE			netapp
	VARIABLES			{productTrapData, productSerialNum}
	DESCRIPTION
		"Vif: The primary Interface on a Single mode vif has failed"

	::= 237

	vifAllLinksFailed		TRAP-TYPE
	ENTERPRISE			netapp
	VARIABLES			{productTrapData, productSerialNum}
	DESCRIPTION
		"Vif: All the links of the vif have failed"

	::= 238

	-- -- -- -- -- -- -- -- -- -- -- -- -- -- -- -- -- -- -- -- -- -- -- --
	--
	--  This section contains traps related to Vfiler status
	--
	-- -- -- -- -- -- -- -- -- -- -- -- -- -- -- -- -- -- -- -- -- -- -- --

        vfStopped       TRAP-TYPE
	ENTERPRISE      netapp
	VARIABLES      	{productTrapData, productSerialNum}
        DESCRIPTION     
		"A vFiler has stopped."
	
	::= 245

        vfStarted       TRAP-TYPE
	ENTERPRISE      netapp
	VARIABLES      	{productTrapData, productSerialNum}
        DESCRIPTION     
		"A vFiler has started."

	::= 246

	-- -- -- -- -- -- -- -- -- -- -- -- -- -- -- -- -- -- -- -- -- -- -- --
	--
	--  This section contains traps related to Virus Scanning
	--
	-- -- -- -- -- -- -- -- -- -- -- -- -- -- -- -- -- -- -- -- -- -- -- --

	vscanVirusDetectedError	TRAP-TYPE
	ENTERPRISE		netapp
	VARIABLES		{productTrapData, productSerialNum}
	DESCRIPTION
		"VScan: A virus scanner has detected a virus on the Filer"

	::= 254

	vscanDisConnection		TRAP-TYPE
	ENTERPRISE			netapp
	VARIABLES			{productTrapData, productSerialNum}
	DESCRIPTION
		"VScan: A virus scanner has dropped its connection from the Filer"

	::= 255	

	vscanConfigurationChange	TRAP-TYPE
	ENTERPRISE			netapp
	VARIABLES			{productTrapData, productSerialNum}
	DESCRIPTION
		"VScan: There has been a change to the vscan configuration"
	::= 256

	vscanConnection		TRAP-TYPE
	ENTERPRISE		netapp
	DESCRIPTION
		"VScan: A virus scanner has made a connection to the Filer"

	::= 257
	-- -- -- -- -- -- -- -- -- -- -- -- -- -- -- -- -- -- -- -- -- -- -- --
	--
	--  This section contains additional traps related to Virus Scanning
	--
	-- -- -- -- -- -- -- -- -- -- -- -- -- -- -- -- -- -- -- -- -- -- -- --

	vscanServerUpgrade	TRAP-TYPE
	ENTERPRISE		netapp
	VARIABLES		{productTrapData, productSerialNum}
	DESCRIPTION
		"VScan: The Vscan server has been upgraded"

	::= 266

        -- -- -- -- -- -- -- -- -- -- -- -- -- -- -- -- -- -- -- -- -- -- -- -
	-- 
	--  This section contains traps related to volume status being offline,
	--  online or restricted
	-- 
	-- -- -- -- -- -- -- -- -- -- -- -- -- -- -- -- -- -- -- -- -- -- -- -

	volumeRestrictedByMirrorBigIo   TRAP-TYPE 
	ENTERPRISE              	netapp 
	VARIABLES              		{productTrapData, productSerialNum}
	DESCRIPTION 
		"A volume that experienced a medium error during reconstruction 
		is restricted and marked wafl-inconsistent, but starting 
		wafliron has failed. This trap is issued to alert operator 
		that a volume is not accessible and wafliron must be started 
		to allow access to it."

	::= 272

	volumeInconsistentUmount        TRAP-TYPE 
	ENTERPRISE              	netapp 
	VARIABLES      	        	{productTrapData, productSerialNum}
	DESCRIPTION 
		"This trap is issued when we unmount a volume due to an 
		inconsistency."

	::= 274

	volumeStateChanged              TRAP-TYPE 
	ENTERPRISE              	netapp 
	VARIABLES       	       	{productTrapData, productSerialNum}
	DESCRIPTION 
		"Volume is being taken offline or being restricted. 
		The string sent with trap specifies name of affected volume 
		and its state."

	::= 275

	volumeOnline           		TRAP-TYPE 
	ENTERPRISE             		netapp 
	VARIABLES             		{productTrapData, productSerialNum}
	DESCRIPTION 
		"Volume is online now. The string sent with trap specifies 
		name of volume which is online now."

	::= 276

	-- -- -- -- -- -- -- -- -- -- -- -- -- -- -- -- -- -- -- -- -- -- -- -
	-- 
	--  This section contains traps related to remote management 
	--  controller (RMC) card status
	-- 
	-- -- -- -- -- -- -- -- -- -- -- -- -- -- -- -- -- -- -- -- -- -- -- -

	rmcCardNeedsReplacement		TRAP-TYPE
	ENTERPRISE             		netapp 
	VARIABLES             		{productTrapData, productSerialNum}
	DESCRIPTION 
		"Remote Management Controller card needs replacement. The trap 
		includes a string specifying the reason for replacement"

	::= 283

	rmcCardMissingCables		TRAP-TYPE
	ENTERPRISE             		netapp 
	VARIABLES             		{productTrapData, productSerialNum}
	DESCRIPTION 
		"Remote Management Controller card is missing its internal 
		cable, or LAN cable or power supply cable. The trap includes 
		a string specifing the missing component."  

	::= 284

        -- -- -- -- -- -- -- -- -- -- -- -- -- -- -- -- -- -- -- -- -- -- -- -
	-- 
	--  This section contains traps related to remote volume 
	-- 
	-- -- -- -- -- -- -- -- -- -- -- -- -- -- -- -- -- -- -- -- -- -- -- -

	volumeRemoteUnreachable		TRAP-TYPE 
	ENTERPRISE             		netapp 
	VARIABLES             		{productTrapData, productSerialNum}
	DESCRIPTION 
		"Local volume encountered an error while communicating
		to remote volume."

	::= 294

	volumeRemoteOk			TRAP-TYPE 
	ENTERPRISE              	netapp 
	VARIABLES              		{productTrapData, productSerialNum}
	DESCRIPTION 
		"The communication between remote volume and local volume 
		returned to normal."

	::= 296

	volumeRemoteRestored		TRAP-TYPE 
	ENTERPRISE              	netapp 
	VARIABLES              		{productTrapData, productSerialNum}
	DESCRIPTION 
		"The data on remote volume has been fully restored to local
		volume."

	::= 297

	volumeRemoteRestoreBegin	TRAP-TYPE 
	ENTERPRISE              	netapp 
	VARIABLES              		{productTrapData, productSerialNum}
	DESCRIPTION 
		"The data on remote volume has started being restored to local
		volume by Restore-on-Demand."

	::= 298

	-- -- -- -- -- -- -- -- -- -- -- -- -- -- -- -- -- -- -- -- -- -- -- -
	-- 
	--  This section contains more traps related to volume status being 
	--  offline, online or restricted
	-- 
	-- -- -- -- -- -- -- -- -- -- -- -- -- -- -- -- -- -- -- -- -- -- -- -

	volumeRestrictedRootConflict        TRAP-TYPE 
	ENTERPRISE              	    netapp 
	VARIABLES            	  	    {productTrapData, productSerialNum}
	DESCRIPTION 
		"Volume is restricted due to a root volume conflict. The 
		string sent with trap specifies name of conflicting volume 
		which is being restricted."

	::= 304
	
	volumeOfflineTooBig       	TRAP-TYPE 
	ENTERPRISE              	netapp 
	VARIABLES              		{productTrapData, productSerialNum}
	DESCRIPTION 
		"Volume can not be brought online because its raw size is 
		larger than maximum allowed size. The string sent with trap 
		specifies name of affected volume and its raw size, and 
		maximum allowed size."

	::= 314

	volumeOffline                   TRAP-TYPE 
	ENTERPRISE              	netapp 
	VARIABLES              		{productTrapData, productSerialNum}
	DESCRIPTION 
		"Volume is being taken offline. The string sent with trap 
		specifies name of affected volume and reason for being 
		taken offline."

	::= 324

	volumeRestricted                TRAP-TYPE 
	ENTERPRISE              	netapp 
	VARIABLES              		{productTrapData, productSerialNum}
	DESCRIPTION 
		"Volume is being restricted. The string sent with trap 
		specifies name of affected volume and reason for being 
		restricted."

	::= 334

	volumeDegradedDirty             TRAP-TYPE 
	ENTERPRISE              	netapp 
	VARIABLES  	            	{productTrapData, productSerialNum}
	DESCRIPTION 
		"Volume is degraded and has dirty parity. WAFL_check must be 
		run on this volume before it can be brought online. The string
		sent with trap specifies name of affected volume."

	::= 344

	volumeError             	TRAP-TYPE 
	ENTERPRISE              	netapp 
	VARIABLES       	       	{productTrapData, productSerialNum}
	DESCRIPTION 
		"This trap is issued when a volume can not be brought online 
		due to an error.  The string sent with trap specifies name of 
		affected volume and error description."

	::= 354
	
	-- -- -- -- -- -- -- -- -- -- -- -- -- -- -- -- -- -- -- -- -- -- -- -
	-- 
	--  This section contains traps related to synchronous SnapMirror
	-- 
	-- -- -- -- -- -- -- -- -- -- -- -- -- -- -- -- -- -- -- -- -- -- -- -
	snapmirrorSyncFailed		TRAP-TYPE
	ENTERPRISE             		netapp    
	VARIABLES             		{productTrapData, productSerialNum}
	DESCRIPTION 
	        "Synchronous SnapMirror failed and went into asynchronous mode."
        ::= 364

	snapmirrorSyncOk		TRAP-TYPE
	ENTERPRISE             		netapp    
	VARIABLES             		{productTrapData, productSerialNum}
	DESCRIPTION 
	        "Synchronous SnapMirror went into synchronous mode."
        ::= 366

	-- -- -- -- -- -- -- -- -- -- -- -- -- -- -- -- -- -- -- -- -- -- -- -
	-- 
	--  New environmental traps
	-- 
	--  A series of new environmental traps are constructed
	--  to disambiguate many of the older traps (which are antiquated
	--  but remain until they are completely removed from EMS usage).
	-- 
	-- -- -- -- -- -- -- -- -- -- -- -- -- -- -- -- -- -- -- -- -- -- -- -

	-- -- -- -- -- -- -- -- -- -- -- -- -- -- -- -- -- -- -- -- -- -- -- -
	-- Chassis Temperature
	-- -- -- -- -- -- -- -- -- -- -- -- -- -- -- -- -- -- -- -- -- -- -- -

	chassisTemperatureShutdown	TRAP-TYPE
	ENTERPRISE			netapp
	VARIABLES			{productTrapData, productSerialNum}
	DESCRIPTION
		"The chassis temperature is extreme.  The appliance has
		initiated a shutdown to protect itself.  The operating
		environment should be monitored and corrected before
		restarting the appliance."

	::= 371

	chassisTemperatureWarning	TRAP-TYPE
	ENTERPRISE			netapp
	VARIABLES			{productTrapData, productSerialNum}
	DESCRIPTION
		"The chassis temperature is either too high or too low.
		The temperature should be monitored and, if possible, corrected."

	::= 372

	chassisTemperatureUnknown	TRAP-TYPE
	ENTERPRISE			netapp
	VARIABLES			{productTrapData, productSerialNum}
	DESCRIPTION
		"The chassis temperature is unknown, because reading can't be
		obtained from the chassis temperature sensor."

	::= 375

	chassisTemperatureOk		TRAP-TYPE
	ENTERPRISE			netapp
	VARIABLES			{productTrapData, productSerialNum}
	DESCRIPTION
		"The chassis temperature is OK."

	::= 376

	-- -- -- -- -- -- -- -- -- -- -- -- -- -- -- -- -- -- -- -- -- -- -- -
	-- CPU Fans
	-- -- -- -- -- -- -- -- -- -- -- -- -- -- -- -- -- -- -- -- -- -- -- -

	chassisCPUFanStopped		TRAP-TYPE
	ENTERPRISE			netapp
	VARIABLES			{productTrapData, productSerialNum}
	DESCRIPTION
		"One or more CPU fans have stopped.  The appliance
		has initiated a shutdown to protect itself.  A new
		motherboard may be required to correct the fan.
		Contact Network Appliance for direction."

	::= 381

	chassisCPUFanSlow		TRAP-TYPE
	ENTERPRISE			netapp
	VARIABLES			{productTrapData, productSerialNum}
	DESCRIPTION
		"A CPU fan is spinning too slowly.  A new motherboard
		may be required to correct the fan.  Contact Network
		Appliance for direction."

	::= 383

	chassisCPUFanOk			TRAP-TYPE
	ENTERPRISE			netapp
	VARIABLES			{productTrapData, productSerialNum}
	DESCRIPTION
		"All CPU fan(s) are properly functioning."

	::= 386

	-- -- -- -- -- -- -- -- -- -- -- -- -- -- -- -- -- -- -- -- -- -- -- -
	-- Power Supplies
	-- -- -- -- -- -- -- -- -- -- -- -- -- -- -- -- -- -- -- -- -- -- -- -

	chassisPowerSuppliesFailed	TRAP-TYPE
	ENTERPRISE			netapp
	VARIABLES			{productTrapData, productSerialNum}
	DESCRIPTION
		"Multiple chassis power supplies failed."

	::= 391

	chassisPowerSupplyDegraded	TRAP-TYPE
	ENTERPRISE			netapp
	VARIABLES			{productTrapData, productSerialNum}
	DESCRIPTION
		"One or more chassis power supplies are degraded.
		A description of the degraded state has been
		logged to the console and message log file."

	::= 392

	chassisPowerSupplyFailed	TRAP-TYPE
	ENTERPRISE			netapp
	VARIABLES			{productTrapData, productSerialNum}
	DESCRIPTION
		"One chassis power supply failed."

	::= 393

	chassisPowerSupplyRemoved	TRAP-TYPE
	ENTERPRISE			netapp
	VARIABLES			{productTrapData, productSerialNum}
	DESCRIPTION
		"One or more chassis power supplies are removed."

	::= 394

	chassisPowerSupplyOff		TRAP-TYPE
	ENTERPRISE			netapp
	VARIABLES			{productTrapData, productSerialNum}
	DESCRIPTION
		"One or more chassis power supplies are off."

	::= 395

	chassisPowerSuppliesOk		TRAP-TYPE
	ENTERPRISE			netapp
	VARIABLES			{productTrapData, productSerialNum}
	DESCRIPTION
		"The chassis power supplies are all functioning properly."

	::= 396

	chassisPowerSupplyOk		TRAP-TYPE
	ENTERPRISE			netapp
	VARIABLES			{productTrapData, productSerialNum}
	DESCRIPTION
		"This chassis power supply is functioning properly." 

	::= 397



	-- -- -- -- -- -- -- -- -- -- -- -- -- -- -- -- -- -- -- -- -- -- -- -
	-- Power Rails
	-- -- -- -- -- -- -- -- -- -- -- -- -- -- -- -- -- -- -- -- -- -- -- -

	chassisPowerDegraded		TRAP-TYPE
	ENTERPRISE			netapp
	VARIABLES			{productTrapData, productSerialNum}
	DESCRIPTION
		"The power within the chassis is degraded.
		A description of the degraded state has been
		logged to the console and message log file."

	::= 403

	chassisPowerOk			TRAP-TYPE
	ENTERPRISE			netapp
	VARIABLES			{productTrapData, productSerialNum}
	DESCRIPTION
		"The power within the chassis is functioning properly."

	::= 406

	-- -- -- -- -- -- -- -- -- -- -- -- -- -- -- -- -- -- -- -- -- -- -- -
	-- Chassis Fans
	-- -- -- -- -- -- -- -- -- -- -- -- -- -- -- -- -- -- -- -- -- -- -- -

	chassisFanDegraded		TRAP-TYPE
	ENTERPRISE			netapp
	VARIABLES			{productTrapData, productSerialNum}
	DESCRIPTION
		"A chassis fan has been degraded."

	::= 412

	chassisFanRemoved		TRAP-TYPE
	ENTERPRISE			netapp
	VARIABLES			{productTrapData, productSerialNum}
	DESCRIPTION
		"A chassis fan FRU has been removed."

	::= 413

	chassisFanStopped		TRAP-TYPE
	ENTERPRISE			netapp
	VARIABLES			{productTrapData, productSerialNum}
	DESCRIPTION
		"One or more chassis fans have stopped."

	::= 414

	chassisFanWarning		TRAP-TYPE
	ENTERPRISE			netapp
	VARIABLES			{productTrapData, productSerialNum}
	DESCRIPTION
		"One or more chassis fans is spinning slowly or too fast."

	::= 415

	chassisFanOk			TRAP-TYPE
	ENTERPRISE			netapp
	VARIABLES			{productTrapData, productSerialNum}
	DESCRIPTION
		"All chassis fans are functioning properly."

	::= 416

	-- -- -- -- -- -- -- -- -- -- -- -- -- -- -- -- -- -- -- -- -- -- -- -
	-- Volume SnapValidator errors
	-- -- -- -- -- -- -- -- -- -- -- -- -- -- -- -- -- -- -- -- -- -- -- -

	writeVerificationFailed		TRAP-TYPE
	ENTERPRISE			netapp
	VARIABLES			{productTrapData, productSerialNum}
	DESCRIPTION
		"A write has failed a verification test 
		on a SnapValidator enabled volume."
	::= 424

	-- -- -- -- -- -- -- -- -- -- -- -- -- -- -- -- -- -- -- -- -- -- -- -
	-- CIFS domain controller-related traps
	-- -- -- -- -- -- -- -- -- -- -- -- -- -- -- -- -- -- -- -- -- -- -- -

	domainControllerDisconnect      TRAP-TYPE
	ENTERPRISE			netapp
	VARIABLES			{productTrapData, productSerialNum}
	DESCRIPTION
		"A CIFS domain controller connection to the filer has failed."
	::= 435
        
        dcPasswdChangeFailed            TRAP-TYPE
        ENTERPRISE                      netapp
        VARIABLES                       {productTrapData, productSerialNum}
        DESCRIPTION
                "An attempt to change the filer's password with the domain
                controller has failed."
        ::= 436        

	-- -- -- -- -- -- -- -- -- -- -- -- -- -- -- -- -- -- -- -- -- -- -- -
	--  This section contains traps related to plex state 
	-- -- -- -- -- -- -- -- -- -- -- -- -- -- -- -- -- -- -- -- -- -- -- -

	plexFailed             		TRAP-TYPE 
	ENTERPRISE              	netapp 
	VARIABLES              		{productTrapData, productSerialNum}
	DESCRIPTION 
		"This trap is issued when one plex of a mirrored 
		traditional volume or aggregate is failed. The string 
		sent with this trap specifies name of affected plex or
		mirrored traditional volume or aggregate."
	::= 444

	plexOffline            		TRAP-TYPE 
	ENTERPRISE              	netapp 
	VARIABLES   	           	{productTrapData, productSerialNum}
	DESCRIPTION 
		"This trap is issued when a plex becomes offline. 
		The string sent with this trap specifies name of 
		affected plex or mirrored traditional volume or aggregate."
	::= 454

	-- -- -- -- -- -- -- -- -- -- -- -- -- -- -- -- -- -- -- -- -- -- -- -
	--  This section contains traps related to shelf Electronics Elements
	--  and intelligent fibre channel interface modules such as LRC,
	--  ESH, AT-FC, and AT-FCX.
	-- -- -- -- -- -- -- -- -- -- -- -- -- -- -- -- -- -- -- -- -- -- -- -

	shelfSESElectronicsFailed	TRAP-TYPE 
	ENTERPRISE			netapp 
	VARIABLES			{productTrapData, productSerialNum}
	DESCRIPTION 
		"One or more of the enclosure services devices in a
		disk shelf has failed.  Some shelf designs combine
		the enclosure monitoring hardware function into the
		module that provides  the storage interface to
		the shelf.  A failure in the enclosure monitoring
		section of these combined modules does not necessarily
		indicate a failure in disk or loop or bus operation,
		which may be able to continue."
	::= 464

	shelfSESElectronicsInfo		TRAP-TYPE 
	ENTERPRISE			netapp 
	VARIABLES			{productTrapData, productSerialNum}
	DESCRIPTION 
		"A previously reported failure of an enclosure
		services device in a disk shelf has been corrected,
		or the device has reported information that does not
		necessarily require customer action."
	::= 467 

	shelfIFModuleFailed		TRAP-TYPE 
	ENTERPRISE			netapp 
	VARIABLES			{productTrapData, productSerialNum}
	DESCRIPTION 
		"One or more of the storage interface modules in a
		disk shelf has failed.  Some shelf designs combine the
		enclosure monitoring hardware function into the module
		that operates the fibre channel loop or SCSI in the
		shelf.  This failure is of the storage interface
		itself, not a failure of the enclosure monitoring,
		which may be able to continue.  This failure may make
		one or more disks in the shelf or in the loop or bus
		unavailable."
	::= 473

 	shelfIFModuleInfo		TRAP-TYPE 
	ENTERPRISE			netapp 
	VARIABLES			{productTrapData, productSerialNum}
	DESCRIPTION
		"A previously reported failure of a disk shelf
		interface module has been corrected, or the module has
		reported information that does not necessarily require
		customer action."
	::= 477

	-- -- -- -- -- -- -- -- -- -- -- -- -- -- -- -- -- -- -- -- -- -- -- -
	--  This section contains traps related to maxdirsize.
	-- -- -- -- -- -- -- -- -- -- -- -- -- -- -- -- -- -- -- -- -- -- -- -

 	maxDirSizeAlert			TRAP-TYPE 
	ENTERPRISE			netapp 
	VARIABLES			{productTrapData, productSerialNum}
	DESCRIPTION
		"A directory has reached it's maxdirsize limit. Either 
		increase the maxdirsize or clean up the directory."
	::= 482

 	maxDirSizeWarning		TRAP-TYPE 
	ENTERPRISE			netapp 
	VARIABLES			{productTrapData, productSerialNum}
	DESCRIPTION
		"A directory is getting close to it's maxdirsize limit. Either
		increase the maxdirsize or clean up the directory."
	::= 485
        
        -- -- -- -- -- -- -- -- -- -- -- -- -- -- -- -- -- -- -- -- -- -- -- -
        -- CIFS statistics related traps
        -- -- -- -- -- -- -- -- -- -- -- -- -- -- -- -- -- -- -- -- -- -- -- -
        
        cifsStatsExhaustMemCtrlBlk      TRAP-TYPE
        ENTERPRISE                      netapp
        VARIABLES                       {productTrapData, productSerialNum}
        DESCRIPTION
                "A request for a CIFS control block can not be granted. All
                control blocks are in use."
        ::= 497

        -- -- -- -- -- -- -- -- -- -- -- -- -- -- -- -- -- -- -- -- -- -- -- -
        -- New Environmental Subsystem Traps 
        -- -- -- -- -- -- -- -- -- -- -- -- -- -- -- -- -- -- -- -- -- -- -- -
        

	chassisPSRemovedxMinShutdown	TRAP-TYPE
	ENTERPRISE			netapp
	VARIABLES			{productTrapData, productSerialNum}
	DESCRIPTION
		"Power Supply Unit is removed from the system. System will 
		be shutdown in x minutes if it is not put back."

	::= 501

	chassisPSUsMismatch		TRAP-TYPE
	ENTERPRISE			netapp
	VARIABLES			{productTrapData, productSerialNum}
	DESCRIPTION
		"Power Supply Units in the system are of different type. 
		 Please replace them with correct Power Supply Units."

	::= 505

	chassisFanFailxMinShutdown	TRAP-TYPE
	ENTERPRISE			netapp
	VARIABLES			{productTrapData, productSerialNum}
	DESCRIPTION
		"Multiple chassis fan failure. System will 
		shut down in a few minutes if not corrected."

	::= 511

	chassisPSUwrongInput		TRAP-TYPE
	ENTERPRISE			netapp
	VARIABLES			{productTrapData, productSerialNum}
	DESCRIPTION
		"Power Supply Unit (PSU) in the system is connected to an
		 incompatible external power source. Please change 
		 the power source being used or replace the PSU 
		 with one that matches the current power source."

	::= 515

	powerSupplyFanFailxMinShutdown	TRAP-TYPE
	ENTERPRISE			netapp
	VARIABLES			{productTrapData, productSerialNum}
	DESCRIPTION
		"Multiple  power supply fans failure.
		System will shut down in a few minutes if not corrected."

	::= 521


        -- -- -- -- -- -- -- -- -- -- -- -- -- -- -- -- -- -- -- -- -- -- -- -
        -- Disk Multipath Traps 
        -- -- -- -- -- -- -- -- -- -- -- -- -- -- -- -- -- -- -- -- -- -- -- -

	diskMultipathOneSwitch		TRAP-TYPE
        ENTERPRISE                      netapp
        VARIABLES                       {productTrapData, productSerialNum}
        DESCRIPTION
                "A multipathed disk is only connected to one switch."

        ::= 562

	diskMultipathNoTakeover		TRAP-TYPE
        ENTERPRISE                      netapp
        VARIABLES                       {productTrapData, productSerialNum}
        DESCRIPTION
                "Multipath disks or luns could not be detected for the partner.
		The node will be unable to takeover correctly."

        ::= 563

	diskMultipathWarning	        TRAP-TYPE
        ENTERPRISE                      netapp
        VARIABLES                       {productTrapData, productSerialNum}
        DESCRIPTION
                "Syncronous mirroring is enabled, even though disks are not 
		multipathed."

        ::= 565

        -- -- -- -- -- -- -- -- -- -- -- -- -- -- -- -- -- -- -- -- -- -- -- -
        -- Disk Disable Traps
        -- -- -- -- -- -- -- -- -- -- -- -- -- -- -- -- -- -- -- -- -- -- -- -

 	driveDisableErr		TRAP-TYPE 
	ENTERPRISE			netapp 
	VARIABLES			{productTrapData, productSerialNum}
	DESCRIPTION
		"A drive has been disabled by the shelf module due to 
		 hardware errors.  If it's the only drive in the shelf 
		 thta is disabled, replace the drive."
	::= 574	

        -- -- -- -- -- -- -- -- -- -- -- -- -- -- -- -- -- -- -- -- -- -- -- -
	-- End of NetApp trap definitions
	-- 
	-- Note: Please update this comment when adding a new TRAP-TYPE.
	--       The next trap set range should be: 58x
	-- 
	--	 The 10xxx trap range is used by DataFabric Manager
	--	     (netappDataFabricManager) see the DFM MIB for further
	--	     information.
	--
	--	 The 20xxx trap range is used by the NetApp Support Console
	--	     (netappSupportConsole) see the NASC MIB for further 
	--	     information.
	--
	-- The 'ones' digit of the trap contains the priority of the trap:
	--
	-- 1 emergency
	-- 2 alert
	-- 3 critical
	-- 4 error
	-- 5 warning
	-- 6 notification
	-- 7 information
	-- 8 debug
	-- 
        -- -- -- -- -- -- -- -- -- -- -- -- -- -- -- -- -- -- -- -- -- -- -- -

	END
