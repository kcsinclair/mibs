OMNI-gx2Rx085BX4-MIB DEFINITIONS ::= BEGIN

    IMPORTS
	IpAddress, TimeTicks            
					      FROM RFC1155-SMI
	OBJECT-TYPE                     
					      FROM RFC-1212
	sysUpTime, DisplayString        
					      FROM RFC1213-MIB
	TRAP-TYPE                       
					      FROM RFC-1215
	gi, motproxies                   
					      FROM NLS-BBNIDENT-MIB
	gx2Rx085BX4
					      FROM GX2HFC-MIB

	trapIdentifier,trapNetworkElemModelNumber,
	trapNetworkElemSerialNum, trapPerceivedSeverity,
	trapNetworkElemOperState, trapNetworkElemAlarmStatus,
	trapNetworkElemAdminState, trapNetworkElemAvailStatus,
	trapText, trapNETrapLastTrapTimeStamp, trapChangedObjectId,
	trapChangedValueInteger, trapChangedValueDisplayString
					      FROM NLSBBN-TRAPS-MIB;



	       -- This MIB module uses the extended OBJECT-TYPE macro as
	       -- defined in RFC1212 and the TRAP-TYPE macro as defined
	       -- in RFC 1215.

		   --REVISION	"1" Oct 3, 2007   Initial Release
		   --REVISION	"2" May 5, 2009   Adds Burst mode to Module configuration OID
		   --REVISION	"3" Sept 10, 2009 Adds Optical power bad traps
		   --DESCRIPTION
		   --			Initial revision derived from RX085BX2

		--    OMNISTAR Quad (High Density) Return Path Receiver Module  MIB MODULE

	-- This MIB module defines information for management of HFC networks
		-- 
		-- The MIB module assumes that all generic (static) network element
		-- information is defined in a different module such as the HFC module
		-- The MIB consists of two groups:
		-- the device type descriptor subgroup and 
		-- gx2Rx085BX4 Network Elements subgroup.
		-- The device type descriptor subgroup is used to define 
		-- parameters specific to gx2Rx085BX4 device type.
		-- These parameters are common across all network elements
		-- from gx2Rx085BX4 device type.
		--
		-- The gx2Rx085BX4 Network Elements subgroup is
		-- a list of gx2Rx085BX4 type elements in the
		-- current network topology with nominal
		-- and current parameter values for the
		-- individual network elements; the individual
		-- network elements are identified by  
		-- index from hfcCommonTable.
		-- That implies what hfcCommonTableIndex and
		-- gx2Rx085BX4TableIndex are equal for each individual
		-- network element.
		-- This table is an extension of the hfcCommonTable
		-- for all elements of gx2Rx085BX4 type.
		--
		-- Both groups are mandatory for management of gx2Rx085BX4 devices.

-- ****************************************************************************
		--
		-- All floating point numbers will be represented by an IEEE 32 Bit number.
		-- Conversion of this number must be done on the user interface to view the 
		-- actual floating point number. 
		--

		Float ::= Counter  -- UNSIGNED (32 BITS) 
		U32Data ::= Counter -- UNSIGNED (32 BITS) 

-- ****************************************************************************

		-- gx2Rx085BX4 Device Descriptor subgroup.

		-- The device type descriptor subgroup is used to define 
		-- parameters specific to gx2Rx085BX4 device type.
		-- These parameters are common across all network elements
		-- from gx2Rx085BX4 device type.


		gx2Rx085BX4Descriptor OBJECT IDENTIFIER ::= {gx2Rx085BX4 1}



--*****************************************************************************
		--              gx2Rx085BX4 Table
		
		-- Contains a list of all gx2Rx085BX4 type devices in
		-- the network. Each device is characterized with
		-- current network topology information, with nominal
		-- and current parameter values for the
		-- individual network elements;
		--
		-- The individual network elements indentified by  
		-- index from hfcCommonTable.
		-- That implies what hfcCommonTableIndex and
		-- gx2Rx085BX4TableIndex are equal for each individual
		-- nettwork element.
		-- This table should be used as an extension of the hfcCommonTable
		-- for all elements of gx2Rx085BX4 type.


	       gx2Rx085BX4AnalogTable                    OBJECT-TYPE
			 SYNTAX             SEQUENCE OF Gx2Rx085BX4AnalogEntry
			 ACCESS             not-accessible
			 STATUS             mandatory
			 DESCRIPTION
			 "This table contains gx2Rx085BX4 specific parameters with
			  nominal and current values."
			 ::= { gx2Rx085BX4 2 }


	       gx2Rx085BX4AnalogEntry               OBJECT-TYPE
			 SYNTAX             Gx2Rx085BX4AnalogEntry
			 ACCESS             not-accessible
			 STATUS             mandatory
			 DESCRIPTION
			 "This list contains digital product class and the
			  associated RF channel parameters and descriptions."
			 INDEX { gx2Rx085BX4AnalogTableIndex }
			 ::= { gx2Rx085BX4AnalogTable  1}

--***********************************************************************
	       gx2Rx085BX4DigitalTable                    OBJECT-TYPE
			 SYNTAX             SEQUENCE OF Gx2Rx085BX4DigitalEntry
			 ACCESS             not-accessible
			 STATUS             mandatory
			 DESCRIPTION
			 "This table contains gx2Rx085BX4 specific parameters with
			  nominal and current values."
			 ::= { gx2Rx085BX4 3 }

	       gx2Rx085BX4DigitalEntry               OBJECT-TYPE
			 SYNTAX             Gx2Rx085BX4DigitalEntry
			 ACCESS             not-accessible
			 STATUS             mandatory
			 DESCRIPTION
			 "This list contains digital product class and the
			  associated RF channel parameters and descriptions."
			 INDEX { gx2Rx085BX4DigitalTableIndex }
			 ::= { gx2Rx085BX4DigitalTable  2}

--***********************************************************************
	       gx2Rx085BX4StatusTable                    OBJECT-TYPE
			 SYNTAX             SEQUENCE OF Gx2Rx085BX4StatusEntry
			 ACCESS             not-accessible
			 STATUS             mandatory
			 DESCRIPTION
			 "This table contains gx2Rx085BX4 specific parameters with
			  nominal and current values."
			 ::= { gx2Rx085BX4 4 }

	       gx2Rx085BX4StatusEntry               OBJECT-TYPE
			 SYNTAX             Gx2Rx085BX4StatusEntry
			 ACCESS             not-accessible
			 STATUS             mandatory
			 DESCRIPTION
			 "This list contains digital product class and the
			  associated RF channel parameters and descriptions."
			 INDEX { gx2Rx085BX4StatusTableIndex }
			 ::= { gx2Rx085BX4StatusTable  3}

--***********************************************************************
	       gx2Rx085BX4FactoryTable                    OBJECT-TYPE
			 SYNTAX             SEQUENCE OF Gx2Rx085BX4FactoryEntry
			 ACCESS             not-accessible
			 STATUS             mandatory
			 DESCRIPTION
			 "This table contains gx2Rx085BX4 specific parameters with
			  nominal and current values."
			 ::= { gx2Rx085BX4 5 }

	       gx2Rx085BX4FactoryEntry               OBJECT-TYPE
			 SYNTAX             Gx2Rx085BX4FactoryEntry
			 ACCESS             not-accessible
			 STATUS             mandatory
			 DESCRIPTION
			 "This list contains digital product class and the
			  associated RF channel parameters and descriptions."
			 INDEX { gx2Rx085BX4FactoryTableIndex }
			 ::= { gx2Rx085BX4FactoryTable  4}

--***********************************************************************


--MM          Rx085BX4AnalogTableIndex
	      Gx2Rx085BX4AnalogEntry    ::= SEQUENCE  
	       {
		gx2Rx085BX4AnalogTableIndex         INTEGER,   
		
		--           Analog Parameters

		rx085labelOptPowerOne			DisplayString (SIZE (0..80)),
		rx085uomOptPowerOne			DisplayString (SIZE (0..80)),
		rx085majorHighOptPowerOne		Float, 
		rx085majorLowOptPowerOne		Float, 
		rx085minorHighOptPowerOne		Float,
		rx085minorLowOptPowerOne		Float, 
		rx085currentValueOptPowerOne	Float, 
		rx085stateFlagOptPowerOne		INTEGER,
		rx085minValueOptPowerOne		Float,
		rx085maxValueOptPowerOne 		Float,
		rx085alarmStateOptPowerOne		INTEGER,

		rx085labelOptPowerTwo			DisplayString (SIZE (0..80)),
		rx085uomOptPowerTwo			DisplayString (SIZE (0..80)),
		rx085majorHighOptPowerTwo		Float, 
		rx085majorLowOptPowerTwo		Float, 
		rx085minorHighOptPowerTwo		Float,
		rx085minorLowOptPowerTwo		Float, 
		rx085currentValueOptPowerTwo	Float, 
		rx085stateFlagOptPowerTwo		INTEGER,
		rx085minValueOptPowerTwo		Float,
		rx085maxValueOptPowerTwo 		Float,
		rx085alarmStateOptPowerTwo		INTEGER,

		rx085labelOptPowerThree			DisplayString (SIZE (0..80)),
		rx085uomOptPowerThree			DisplayString (SIZE (0..80)),
		rx085majorHighOptPowerThree		Float, 
		rx085majorLowOptPowerThree		Float, 
		rx085minorHighOptPowerThree		Float,
		rx085minorLowOptPowerThree		Float, 
		rx085currentValueOptPowerThree	Float, 
		rx085stateFlagOptPowerThree		INTEGER,
		rx085minValueOptPowerThree		Float,
		rx085maxValueOptPowerThree 		Float,
		rx085alarmStateOptPowerThree		INTEGER,

		rx085labelOptPowerFour			DisplayString (SIZE (0..80)),
		rx085uomOptPowerFour			DisplayString (SIZE (0..80)),
		rx085majorHighOptPowerFour		Float, 
		rx085majorLowOptPowerFour		Float, 
		rx085minorHighOptPowerFour		Float,
		rx085minorLowOptPowerFour		Float, 
		rx085currentValueOptPowerFour	Float, 
		rx085stateFlagOptPowerFour		INTEGER,
		rx085minValueOptPowerFour		Float,
		rx085maxValueOptPowerFour 		Float,
		rx085alarmStateOptPowerFour		INTEGER,

		rx085labelModTemp			DisplayString (SIZE (0..80)),
		rx085uomModTemp				DisplayString (SIZE (0..80)),
		rx085majorHighModTemp			Float, 
		rx085majorLowModTemp			Float, 
		rx085minorHighModTemp			Float,
		rx085minorLowModTemp			Float, 
		rx085currentValueModTemp		Float, 
		rx085stateFlagModTemp			INTEGER,
		rx085minValueModTemp			Float,
		rx085maxValueModTemp			Float,
		rx085alarmStateModTemp			INTEGER,

		rx085labelFanCurrent			DisplayString (SIZE (0..80)),
		rx085uomFanCurrent			DisplayString (SIZE (0..80)),
		rx085majorHighFanCurrent		Float, 
		rx085majorLowFanCurrent		Float, 
		rx085minorHighFanCurrent		Float,
		rx085minorLowFanCurrent		Float, 
		rx085currentValueFanCurrent		Float, 
		rx085stateFlagFanCurrent		INTEGER,
		rx085minValueFanCurrent		Float,
		rx085maxValueFanCurrent 		Float,
		rx085alarmStateFanCurrent		INTEGER,

		rx085label12Volt				DisplayString (SIZE (0..80)),
		rx085uom12Volt				DisplayString (SIZE (0..80)),
		rx085majorHigh12Volt			Float, 
		rx085majorLow12Volt			Float, 
		rx085minorHigh12Volt			Float,
		rx085minorLow12Volt			Float, 
		rx085currentValue12Volt		Float, 
		rx085stateFlag12Volt			INTEGER,
		rx085minValue12Volt			Float,
		rx085maxValue12Volt			Float,
		rx085alarmState12Volt			INTEGER

		}

		-- ****************  Digital Parameters ***********************
	      Gx2Rx085BX4DigitalEntry    ::= SEQUENCE  
	       {
		gx2Rx085BX4DigitalTableIndex         INTEGER,   

		rx085labelModeOne	 			DisplayString (SIZE (0..80)),
		rx085valueModeOne				INTEGER,
		rx085enumModeOne				DisplayString (SIZE (0..80)),
		rx085stateFlagModeOne     	    INTEGER,

		rx085labelWavelengthOne	 		DisplayString (SIZE (0..80)),
		rx085valueWavelengthOne			INTEGER,
		rx085enumWavelengthOne			DisplayString (SIZE (0..80)),
		rx085stateFlagWavelengthOne     INTEGER,

		rx085labelAttnSettingOne	 	DisplayString (SIZE (0..80)),
		rx085valueAttnSettingOne		INTEGER,
		rx085enumAttnSettingOne			DisplayString (SIZE (0..80)),
		rx085stateFlagAttnSettingOne    INTEGER,

		rx085labelSwModeSettingOne		DisplayString (SIZE (0..80)),
		rx085valueSwModeSettingOne		INTEGER,
		rx085enumSwModeSettingOne			DisplayString (SIZE (0..80)),
		rx085stateFlagSwModeSettingOne     	INTEGER,

		rx085labelSwModeThresholdOne	 	DisplayString (SIZE (0..80)),
		rx085valueSwModeThresholdOne		INTEGER,
		rx085enumSwModeThresholdOne		DisplayString (SIZE (0..80)),
		rx085stateFlagSwModeThresholdOne     	INTEGER,

		rx085labelModeTwo	 			DisplayString (SIZE (0..80)),
		rx085valueModeTwo				INTEGER,
		rx085enumModeTwo				DisplayString (SIZE (0..80)),
		rx085stateFlagModeTwo     	    	INTEGER,

		rx085labelWavelengthTwo	 		DisplayString (SIZE (0..80)),
		rx085valueWavelengthTwo			INTEGER,
		rx085enumWavelengthTwo			DisplayString (SIZE (0..80)),
		rx085stateFlagWavelengthTwo         	INTEGER,

		rx085labelAttnSettingTwo	 		DisplayString (SIZE (0..80)),
		rx085valueAttnSettingTwo			INTEGER,
		rx085enumAttnSettingTwo			DisplayString (SIZE (0..80)),
		rx085stateFlagAttnSettingTwo        	INTEGER,

		rx085labelSwModeSettingTwo		DisplayString (SIZE (0..80)),
		rx085valueSwModeSettingTwo		INTEGER,
		rx085enumSwModeSettingTwo			DisplayString (SIZE (0..80)),
		rx085stateFlagSwModeSettingTwo     	INTEGER,

		rx085labelSwModeThresholdTwo	 	DisplayString (SIZE (0..80)),
		rx085valueSwModeThresholdTwo		INTEGER,
		rx085enumSwModeThresholdTwo		DisplayString (SIZE (0..80)),
		rx085stateFlagSwModeThresholdTwo     	INTEGER,

		rx085labelModeThree	 			DisplayString (SIZE (0..80)),
		rx085valueModeThree				INTEGER,
		rx085enumModeThree				DisplayString (SIZE (0..80)),
		rx085stateFlagModeThree     	    	INTEGER,

		rx085labelWavelengthThree	 		DisplayString (SIZE (0..80)),
		rx085valueWavelengthThree			INTEGER,
		rx085enumWavelengthThree			DisplayString (SIZE (0..80)),
		rx085stateFlagWavelengthThree         	INTEGER,

		rx085labelAttnSettingThree	 		DisplayString (SIZE (0..80)),
		rx085valueAttnSettingThree			INTEGER,
		rx085enumAttnSettingThree			DisplayString (SIZE (0..80)),
		rx085stateFlagAttnSettingThree        	INTEGER,

		rx085labelSwModeSettingThree		DisplayString (SIZE (0..80)),
		rx085valueSwModeSettingThree		INTEGER,
		rx085enumSwModeSettingThree			DisplayString (SIZE (0..80)),
		rx085stateFlagSwModeSettingThree     	INTEGER,

		rx085labelSwModeThresholdThree	 	DisplayString (SIZE (0..80)),
		rx085valueSwModeThresholdThree		INTEGER,
		rx085enumSwModeThresholdThree		DisplayString (SIZE (0..80)),
		rx085stateFlagSwModeThresholdThree     	INTEGER,

		rx085labelModeFour	 			DisplayString (SIZE (0..80)),
		rx085valueModeFour				INTEGER,
		rx085enumModeFour				DisplayString (SIZE (0..80)),
		rx085stateFlagModeFour     	    	INTEGER,

		rx085labelWavelengthFour	 		DisplayString (SIZE (0..80)),
		rx085valueWavelengthFour			INTEGER,
		rx085enumWavelengthFour			DisplayString (SIZE (0..80)),
		rx085stateFlagWavelengthFour         	INTEGER,

		rx085labelAttnSettingFour	 		DisplayString (SIZE (0..80)),
		rx085valueAttnSettingFour			INTEGER,
		rx085enumAttnSettingFour			DisplayString (SIZE (0..80)),
		rx085stateFlagAttnSettingFour        	INTEGER,

		rx085labelSwModeSettingFour		DisplayString (SIZE (0..80)),
		rx085valueSwModeSettingFour		INTEGER,
		rx085enumSwModeSettingFour			DisplayString (SIZE (0..80)),
		rx085stateFlagSwModeSettingFour     	INTEGER,

		rx085labelSwModeThresholdFour	 	DisplayString (SIZE (0..80)),
		rx085valueSwModeThresholdFour		INTEGER,
		rx085enumSwModeThresholdFour		DisplayString (SIZE (0..80)),
		rx085stateFlagSwModeThresholdFour     	INTEGER,

		rx085labelModuleConfig		DisplayString (SIZE (0..80)),
		rx085valueModuleConfig		INTEGER,
		rx085enumModuleConfig		DisplayString (SIZE (0..80)),
		rx085stateFlagModuleConfig   	INTEGER,

		rx085labelRevertTime		DisplayString (SIZE (0..80)),
		rx085valueRevertTime		INTEGER,
		rx085enumRevertTime		DisplayString (SIZE (0..80)),
		rx085stateFlagRevertTime   	INTEGER,

		rx085labelTestPointSelect	DisplayString (SIZE (0..80)),
		rx085valueTestPointSelect		INTEGER,
		rx085enumTestPointSelect		DisplayString (SIZE (0..80)),
		rx085stateFlagTestPointSelect   	INTEGER,

		rx085labelFactoryDefault		DisplayString (SIZE (0..80)),
		rx085valueFactoryDefault		INTEGER,
		rx085enumFactoryDefault		DisplayString (SIZE (0..80)),
		rx085stateFlagFactoryDefault   	INTEGER

		}
		-- ****************  Status Parameters ************************************
	      Gx2Rx085BX4StatusEntry    ::= SEQUENCE  
	       {

		gx2Rx085BX4StatusTableIndex         INTEGER,   
		rx085labelBoot				DisplayString (SIZE (0..80)),
		rx085valueBoot				INTEGER,
		rx085stateflagBoot			INTEGER,
		
		rx085labelFlash				DisplayString (SIZE (0..80)),
		rx085valueFlash				INTEGER,
		rx085stateflagFlash			INTEGER,

		rx085labelFactoryDataCRC 		DisplayString (SIZE (0..80)),
		rx085valueFactoryDataCRC		INTEGER,
		rx085stateflagFactoryDataCRC		INTEGER,

		rx085labelAlarmDataCRC 		DisplayString (SIZE (0..80)),
		rx085valueAlarmDataCRC			INTEGER,
		rx085stateflagAlarmDataCRC		INTEGER,

		rx085labelCalibrationDataCRC		DisplayString (SIZE (0..80)),
		rx085valueCalibrationDataCRC		INTEGER,
		rx085stateflagCalibrationDataCRC	INTEGER,

		rx085labelHW					DisplayString (SIZE (0..80)),
		rx085valueHW					INTEGER,
		rx085stateflagHW				INTEGER,

		rx085labelOptSigOne			DisplayString (SIZE (0..80)),
		rx085valueOptSigOne			INTEGER,
		rx085stateflagOptSigOne		INTEGER,

		rx085labelOptSigTwo			DisplayString (SIZE (0..80)),
		rx085valueOptSigTwo			INTEGER,
		rx085stateflagOptSigTwo		INTEGER,

		rx085labelOptSigThree			DisplayString (SIZE (0..80)),
		rx085valueOptSigThree			INTEGER,
		rx085stateflagOptSigThree		INTEGER,

		rx085labelOptSigFour			DisplayString (SIZE (0..80)),
		rx085valueOptSigFour			INTEGER,
		rx085stateflagOptSigFour		INTEGER,

		rx085labelBackupCable			DisplayString (SIZE (0..80)),
		rx085valueBackupCable			INTEGER,
		rx085stateflagBackupCable		INTEGER


}
		

		-- ****************  Factory Parameters *************************************
	      Gx2Rx085BX4FactoryEntry    ::= SEQUENCE  
	       {
		gx2Rx085BX4FactoryTableIndex         INTEGER,   
		rx085bootControlByte  			INTEGER,
		rx085bootStatusByte   			INTEGER,
		rx085bank0CRC    			INTEGER,
		rx085bank1CRC    			INTEGER,
		rx085prgEEPROMByte    			INTEGER,
		rx085factoryCRC    			INTEGER,
		rx085calculateCRC    			INTEGER,
		rx085hourMeter    			INTEGER,
		rx085flashPrgCntA    			INTEGER,
		rx085flashPrgCntB    			INTEGER,
		rx085fwRev0	    			DisplayString (SIZE (0..80)),
		rx085fwRev1	    			DisplayString (SIZE (0..80))
		}


		-- ****************  Hold Time Parameters *************************************
--	    Gx2Rx085BX4HoldTimeEntry    ::= SEQUENCE  
--	    {
--		gx2Rx085BX4HoldTimeTableIndex        INTEGER,
--		gx2Rx085BX4HoldTimeSpecIndex         INTEGER,   
--		gx2Rx085BX4HoldTimeData  			INTEGER
--		}
--

        -- ************** Analog Parameters ****************************
		gx2Rx085BX4AnalogTableIndex              OBJECT-TYPE
			   SYNTAX           INTEGER (1..4294967295)
			   ACCESS           read-only
			   STATUS           mandatory
			   DESCRIPTION
			   "The value of this object identifies the network
			    element. This index is equal to the
			    hfcCommonTableIndex for the same element."
			   ::= { gx2Rx085BX4AnalogEntry 1}

-- New Parameter

		rx085labelOptPowerOne             OBJECT-TYPE
			   SYNTAX           DisplayString (SIZE (0..80))
			   ACCESS           read-only
			   STATUS           optional
			   DESCRIPTION
			   "The value of this object provides the label of the
			    Optical Power Analog parameter."
			   ::= { gx2Rx085BX4AnalogEntry 2}

		rx085uomOptPowerOne               OBJECT-TYPE
			   SYNTAX           DisplayString (SIZE (0..80))
			   ACCESS           read-only
			   STATUS           optional
			   DESCRIPTION
			   "The value of this object provides the Unit of Measure of the
			    Optical Power Analog parameter."
			   ::= { gx2Rx085BX4AnalogEntry 3}

		rx085majorHighOptPowerOne         OBJECT-TYPE
			   SYNTAX           Float 
			   ACCESS           read-only
			   STATUS           mandatory
			   DESCRIPTION
			   "The value of this object provides the Major High alarm value
			          of the Optical Power Analog parameter. This value is a floating 
			    point number that is represented as an IEEE 32 bit number."
			   ::= { gx2Rx085BX4AnalogEntry 4}


		rx085majorLowOptPowerOne          OBJECT-TYPE
			   SYNTAX           Float 
			   ACCESS           read-only
			   STATUS           mandatory
			   DESCRIPTION
			   "The value of this object provides the Major Low alarm value
			          of the Optical Power Analog parameter. This value is a floating 
			    point number that is represented as an IEEE 32 bit number."
			   ::= { gx2Rx085BX4AnalogEntry 5}

		rx085minorHighOptPowerOne         OBJECT-TYPE
			   SYNTAX           Float
			   ACCESS           read-only
			   STATUS           mandatory
			   DESCRIPTION
			   "The value of this object provides the Minor High alarm value
			          of the Optical Power Analog parameter. This value is a floating 
			    point number that is represented as an IEEE 32 bit number."
			   ::= { gx2Rx085BX4AnalogEntry 6}

		rx085minorLowOptPowerOne          OBJECT-TYPE
			   SYNTAX           Float 
			   ACCESS           read-only
			   STATUS           mandatory
			   DESCRIPTION
			   "The value of this object provides the Minor Low alarm value
			          of the Optical Power Analog parameter. This value is a floating 
			    point number that is represented as an IEEE 32 bit number."
			   ::= { gx2Rx085BX4AnalogEntry 7}

		rx085currentValueOptPowerOne      OBJECT-TYPE
			   SYNTAX           Float 
			   ACCESS           read-only
			   STATUS           mandatory
			   DESCRIPTION
			   "The value of this object provides the Current value
			          of the Optical Power Analog parameter. This value is a floating 
			    point number that is represented as an IEEE 32 bit number."
			   ::= { gx2Rx085BX4AnalogEntry 8}

		rx085stateFlagOptPowerOne         OBJECT-TYPE
			   SYNTAX           INTEGER
								{
								hidden(1),
								read-only(2),
								updateable(3)
								}
			   ACCESS           read-only
			   STATUS           mandatory
			   DESCRIPTION
			   "The value of this object provides the state
			    of the Optical Power Analog parameter. (0-Hidden	
			          1-Read-Only, 2-Updateable)."
			   ::= { gx2Rx085BX4AnalogEntry 9}

		rx085minValueOptPowerOne          OBJECT-TYPE
			   SYNTAX           Float
			   ACCESS           read-only
			   STATUS           mandatory
			   DESCRIPTION
			   "The value of this object provides the minimum value
			          of the Optical Power Analog parameter. This value is a floating 
			    point number that is represented as an IEEE 32 bit number."
			   ::= { gx2Rx085BX4AnalogEntry 10}

		rx085maxValueOptPowerOne          OBJECT-TYPE
			   SYNTAX           Float
			   ACCESS           read-only
			   STATUS           mandatory
			   DESCRIPTION
			   "The value of this object provides the maximum value
			          of the Optical Power Analog parameter. This value is a floating 
			    point number that is represented as an IEEE 32 bit number."
			   ::= { gx2Rx085BX4AnalogEntry 11}

		rx085alarmStateOptPowerOne        OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Optical Power Analog parameter."
			   ::= { gx2Rx085BX4AnalogEntry 12}

-- New Parameter

		rx085labelOptPowerTwo             OBJECT-TYPE
			   SYNTAX           DisplayString (SIZE (0..80))
			   ACCESS           read-only
			   STATUS           optional
			   DESCRIPTION
			   "The value of this object provides the label of the
			    Optical Power Analog parameter."
			   ::= { gx2Rx085BX4AnalogEntry 13}

		rx085uomOptPowerTwo               OBJECT-TYPE
			   SYNTAX           DisplayString (SIZE (0..80))
			   ACCESS           read-only
			   STATUS           optional
			   DESCRIPTION
			   "The value of this object provides the Unit of Measure of the
			    Optical Power Analog parameter."
			   ::= { gx2Rx085BX4AnalogEntry 14}

		rx085majorHighOptPowerTwo         OBJECT-TYPE
			   SYNTAX           Float 
			   ACCESS           read-only
			   STATUS           mandatory
			   DESCRIPTION
			   "The value of this object provides the Major High alarm value
			          of the Optical Power Analog parameter. This value is a floating 
			    point number that is represented as an IEEE 32 bit number."
			   ::= { gx2Rx085BX4AnalogEntry 15}


		rx085majorLowOptPowerTwo          OBJECT-TYPE
			   SYNTAX           Float 
			   ACCESS           read-only
			   STATUS           mandatory
			   DESCRIPTION
			   "The value of this object provides the Major Low alarm value
			          of the Optical Power Analog parameter. This value is a floating 
			    point number that is represented as an IEEE 32 bit number."
			   ::= { gx2Rx085BX4AnalogEntry 16}

		rx085minorHighOptPowerTwo         OBJECT-TYPE
			   SYNTAX           Float
			   ACCESS           read-only
			   STATUS           mandatory
			   DESCRIPTION
			   "The value of this object provides the Minor High alarm value
			          of the Optical Power Analog parameter. This value is a floating 
			    point number that is represented as an IEEE 32 bit number."
			   ::= { gx2Rx085BX4AnalogEntry 17}

		rx085minorLowOptPowerTwo          OBJECT-TYPE
			   SYNTAX           Float 
			   ACCESS           read-only
			   STATUS           mandatory
			   DESCRIPTION
			   "The value of this object provides the Minor Low alarm value
			          of the Optical Power Analog parameter. This value is a floating 
			    point number that is represented as an IEEE 32 bit number."
			   ::= { gx2Rx085BX4AnalogEntry 18}

		rx085currentValueOptPowerTwo      OBJECT-TYPE
			   SYNTAX           Float 
			   ACCESS           read-only
			   STATUS           mandatory
			   DESCRIPTION
			   "The value of this object provides the Current value
			          of the Optical Power Analog parameter. This value is a floating 
			    point number that is represented as an IEEE 32 bit number."
			   ::= { gx2Rx085BX4AnalogEntry 19}

		rx085stateFlagOptPowerTwo         OBJECT-TYPE
			   SYNTAX           INTEGER
								{
								hidden(1),
								read-only(2),
								updateable(3)
								}
			   ACCESS           read-only
			   STATUS           mandatory
			   DESCRIPTION
			   "The value of this object provides the state
			    of the Optical Power Analog parameter. (0-Hidden	
			          1-Read-Only, 2-Updateable)."
			   ::= { gx2Rx085BX4AnalogEntry 20}

		rx085minValueOptPowerTwo          OBJECT-TYPE
			   SYNTAX           Float
			   ACCESS           read-only
			   STATUS           mandatory
			   DESCRIPTION
			   "The value of this object provides the minimum value
			          of the Optical Power Analog parameter. This value is a floating 
			    point number that is represented as an IEEE 32 bit number."
			   ::= { gx2Rx085BX4AnalogEntry 21}

		rx085maxValueOptPowerTwo          OBJECT-TYPE
			   SYNTAX           Float
			   ACCESS           read-only
			   STATUS           mandatory
			   DESCRIPTION
			   "The value of this object provides the maximum value
			          of the Optical Power Analog parameter. This value is a floating 
			    point number that is represented as an IEEE 32 bit number."
			   ::= { gx2Rx085BX4AnalogEntry 22}

		rx085alarmStateOptPowerTwo        OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Optical Power Analog parameter."
			   ::= { gx2Rx085BX4AnalogEntry 23}

-- New Parameter

		rx085labelOptPowerThree             OBJECT-TYPE
			   SYNTAX           DisplayString (SIZE (0..80))
			   ACCESS           read-only
			   STATUS           optional
			   DESCRIPTION
			   "The value of this object provides the label of the
			    Optical Power Analog parameter."
			   ::= { gx2Rx085BX4AnalogEntry 24}

		rx085uomOptPowerThree               OBJECT-TYPE
			   SYNTAX           DisplayString (SIZE (0..80))
			   ACCESS           read-only
			   STATUS           optional
			   DESCRIPTION
			   "The value of this object provides the Unit of Measure of the
			    Optical Power Analog parameter."
			   ::= { gx2Rx085BX4AnalogEntry 25}

		rx085majorHighOptPowerThree         OBJECT-TYPE
			   SYNTAX           Float 
			   ACCESS           read-only
			   STATUS           mandatory
			   DESCRIPTION
			   "The value of this object provides the Major High alarm value
			          of the Optical Power Analog parameter. This value is a floating 
			    point number that is represented as an IEEE 32 bit number."
			   ::= { gx2Rx085BX4AnalogEntry 26}


		rx085majorLowOptPowerThree          OBJECT-TYPE
			   SYNTAX           Float 
			   ACCESS           read-only
			   STATUS           mandatory
			   DESCRIPTION
			   "The value of this object provides the Major Low alarm value
			          of the Optical Power Analog parameter. This value is a floating 
			    point number that is represented as an IEEE 32 bit number."
			   ::= { gx2Rx085BX4AnalogEntry 27}

		rx085minorHighOptPowerThree         OBJECT-TYPE
			   SYNTAX           Float
			   ACCESS           read-only
			   STATUS           mandatory
			   DESCRIPTION
			   "The value of this object provides the Minor High alarm value
			          of the Optical Power Analog parameter. This value is a floating 
			    point number that is represented as an IEEE 32 bit number."
			   ::= { gx2Rx085BX4AnalogEntry 28}

		rx085minorLowOptPowerThree          OBJECT-TYPE
			   SYNTAX           Float 
			   ACCESS           read-only
			   STATUS           mandatory
			   DESCRIPTION
			   "The value of this object provides the Minor Low alarm value
			          of the Optical Power Analog parameter. This value is a floating 
			    point number that is represented as an IEEE 32 bit number."
			   ::= { gx2Rx085BX4AnalogEntry 29}

		rx085currentValueOptPowerThree      OBJECT-TYPE
			   SYNTAX           Float 
			   ACCESS           read-only
			   STATUS           mandatory
			   DESCRIPTION
			   "The value of this object provides the Current value
			          of the Optical Power Analog parameter. This value is a floating 
			    point number that is represented as an IEEE 32 bit number."
			   ::= { gx2Rx085BX4AnalogEntry 30}

		rx085stateFlagOptPowerThree         OBJECT-TYPE
			   SYNTAX           INTEGER
								{
								hidden(1),
								read-only(2),
								updateable(3)
								}
			   ACCESS           read-only
			   STATUS           mandatory
			   DESCRIPTION
			   "The value of this object provides the state
			    of the Optical Power Analog parameter. (0-Hidden	
			          1-Read-Only, 2-Updateable)."
			   ::= { gx2Rx085BX4AnalogEntry 31}

		rx085minValueOptPowerThree          OBJECT-TYPE
			   SYNTAX           Float
			   ACCESS           read-only
			   STATUS           mandatory
			   DESCRIPTION
			   "The value of this object provides the minimum value
			          of the Optical Power Analog parameter. This value is a floating 
			    point number that is represented as an IEEE 32 bit number."
			   ::= { gx2Rx085BX4AnalogEntry 32}

		rx085maxValueOptPowerThree          OBJECT-TYPE
			   SYNTAX           Float
			   ACCESS           read-only
			   STATUS           mandatory
			   DESCRIPTION
			   "The value of this object provides the maximum value
			          of the Optical Power Analog parameter. This value is a floating 
			    point number that is represented as an IEEE 32 bit number."
			   ::= { gx2Rx085BX4AnalogEntry 33}

		rx085alarmStateOptPowerThree        OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Optical Power Analog parameter."
			   ::= { gx2Rx085BX4AnalogEntry 34}

-- New Parameter

		rx085labelOptPowerFour             OBJECT-TYPE
			   SYNTAX           DisplayString (SIZE (0..80))
			   ACCESS           read-only
			   STATUS           optional
			   DESCRIPTION
			   "The value of this object provides the label of the
			    Optical Power Analog parameter."
			   ::= { gx2Rx085BX4AnalogEntry 35}

		rx085uomOptPowerFour               OBJECT-TYPE
			   SYNTAX           DisplayString (SIZE (0..80))
			   ACCESS           read-only
			   STATUS           optional
			   DESCRIPTION
			   "The value of this object provides the Unit of Measure of the
			    Optical Power Analog parameter."
			   ::= { gx2Rx085BX4AnalogEntry 36}

		rx085majorHighOptPowerFour         OBJECT-TYPE
			   SYNTAX           Float 
			   ACCESS           read-only
			   STATUS           mandatory
			   DESCRIPTION
			   "The value of this object provides the Major High alarm value
			          of the Optical Power Analog parameter. This value is a floating 
			    point number that is represented as an IEEE 32 bit number."
			   ::= { gx2Rx085BX4AnalogEntry 37}


		rx085majorLowOptPowerFour          OBJECT-TYPE
			   SYNTAX           Float 
			   ACCESS           read-only
			   STATUS           mandatory
			   DESCRIPTION
			   "The value of this object provides the Major Low alarm value
			          of the Optical Power Analog parameter. This value is a floating 
			    point number that is represented as an IEEE 32 bit number."
			   ::= { gx2Rx085BX4AnalogEntry 38}

		rx085minorHighOptPowerFour         OBJECT-TYPE
			   SYNTAX           Float
			   ACCESS           read-only
			   STATUS           mandatory
			   DESCRIPTION
			   "The value of this object provides the Minor High alarm value
			          of the Optical Power Analog parameter. This value is a floating 
			    point number that is represented as an IEEE 32 bit number."
			   ::= { gx2Rx085BX4AnalogEntry 39}

		rx085minorLowOptPowerFour          OBJECT-TYPE
			   SYNTAX           Float 
			   ACCESS           read-only
			   STATUS           mandatory
			   DESCRIPTION
			   "The value of this object provides the Minor Low alarm value
			          of the Optical Power Analog parameter. This value is a floating 
			    point number that is represented as an IEEE 32 bit number."
			   ::= { gx2Rx085BX4AnalogEntry 40}

		rx085currentValueOptPowerFour      OBJECT-TYPE
			   SYNTAX           Float 
			   ACCESS           read-only
			   STATUS           mandatory
			   DESCRIPTION
			   "The value of this object provides the Current value
			          of the Optical Power Analog parameter. This value is a floating 
			    point number that is represented as an IEEE 32 bit number."
			   ::= { gx2Rx085BX4AnalogEntry 41}

		rx085stateFlagOptPowerFour         OBJECT-TYPE
			   SYNTAX           INTEGER
								{
								hidden(1),
								read-only(2),
								updateable(3)
								}
			   ACCESS           read-only
			   STATUS           mandatory
			   DESCRIPTION
			   "The value of this object provides the state
			    of the Optical Power Analog parameter. (0-Hidden	
			          1-Read-Only, 2-Updateable)."
			   ::= { gx2Rx085BX4AnalogEntry 42}

		rx085minValueOptPowerFour          OBJECT-TYPE
			   SYNTAX           Float
			   ACCESS           read-only
			   STATUS           mandatory
			   DESCRIPTION
			   "The value of this object provides the minimum value
			          of the Optical Power Analog parameter. This value is a floating 
			    point number that is represented as an IEEE 32 bit number."
			   ::= { gx2Rx085BX4AnalogEntry 43}

		rx085maxValueOptPowerFour          OBJECT-TYPE
			   SYNTAX           Float
			   ACCESS           read-only
			   STATUS           mandatory
			   DESCRIPTION
			   "The value of this object provides the maximum value
			          of the Optical Power Analog parameter. This value is a floating 
			    point number that is represented as an IEEE 32 bit number."
			   ::= { gx2Rx085BX4AnalogEntry 44}

		rx085alarmStateOptPowerFour        OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Optical Power Analog parameter."
			   ::= { gx2Rx085BX4AnalogEntry 45}

-- New Parameter

		rx085labelModTemp              OBJECT-TYPE
			   SYNTAX           DisplayString (SIZE (0..80))
			   ACCESS           read-only
			   STATUS           optional
			   DESCRIPTION
			   "The value of this object provides the label of the
			    Module Temperature Analog parameter."
			   ::= { gx2Rx085BX4AnalogEntry 46}

		rx085uomModTemp                OBJECT-TYPE
			   SYNTAX           DisplayString (SIZE (0..80))
			   ACCESS           read-only
			   STATUS           optional
			   DESCRIPTION
			   "The value of this object provides the Unit of Measure of the
			    Module Temperature Analog parameter."
			   ::= { gx2Rx085BX4AnalogEntry 47}

		rx085majorHighModTemp          OBJECT-TYPE
			   SYNTAX           Float 
			   ACCESS           read-only
			   STATUS           mandatory
			   DESCRIPTION
			   "The value of this object provides the Major High alarm value
			          of the Module Temperature Analog parameter. This value is a floating 
			    point number that is represented as an IEEE 32 bit number."
			   ::= { gx2Rx085BX4AnalogEntry 48}


		rx085majorLowModTemp           OBJECT-TYPE
			   SYNTAX           Float 
			   ACCESS           read-only
			   STATUS           mandatory
			   DESCRIPTION
			   "The value of this object provides the Major Low alarm value
			          of the Module Temperature Analog parameter. This value is a floating 
			    point number that is represented as an IEEE 32 bit number."
			   ::= { gx2Rx085BX4AnalogEntry 49}

		rx085minorHighModTemp          OBJECT-TYPE
			   SYNTAX           Float
			   ACCESS           read-only
			   STATUS           mandatory
			   DESCRIPTION
			   "The value of this object provides the Minor High alarm value
			          of the Module Temperature Analog parameter. This value is a floating 
			    point number that is represented as an IEEE 32 bit number."
			   ::= { gx2Rx085BX4AnalogEntry 50}

		rx085minorLowModTemp           OBJECT-TYPE
			   SYNTAX           Float 
			   ACCESS           read-only
			   STATUS           mandatory
			   DESCRIPTION
			   "The value of this object provides the Minor Low alarm value
			          of the Module Temperature Analog parameter. This value is a floating 
			    point number that is represented as an IEEE 32 bit number."
			   ::= { gx2Rx085BX4AnalogEntry 51}

		rx085currentValueModTemp       OBJECT-TYPE
			   SYNTAX           Float 
			   ACCESS           read-only
			   STATUS           mandatory
			   DESCRIPTION
			   "The value of this object provides the Current value
			          of the Module Temperature Analog parameter. This value is a floating 
			    point number that is represented as an IEEE 32 bit number."
			   ::= { gx2Rx085BX4AnalogEntry 52}

		rx085stateFlagModTemp          OBJECT-TYPE
			   SYNTAX           INTEGER
								{
								hidden(1),
								read-only(2),
								updateable(3)
								}
			   ACCESS           read-only
			   STATUS           mandatory
			   DESCRIPTION
			   "The value of this object provides the state
			    of the Module Temperature Analog parameter. (0-Hidden	
			          1-Read-Only, 2-Updateable)."
			   ::= { gx2Rx085BX4AnalogEntry 53}

		rx085minValueModTemp           OBJECT-TYPE
			   SYNTAX           Float
			   ACCESS           read-only
			   STATUS           mandatory
			   DESCRIPTION
			   "The value of this object provides the minimum value
			          of the Module Temperature Analog parameter. This value is a floating 
			    point number that is represented as an IEEE 32 bit number."
			   ::= { gx2Rx085BX4AnalogEntry 54}

		rx085maxValueModTemp           OBJECT-TYPE
			   SYNTAX           Float
			   ACCESS           read-only
			   STATUS           mandatory
			   DESCRIPTION
			   "The value of this object provides the maximum value
			          of the Module Temperature Analog parameter. This value is a floating 
			    point number that is represented as an IEEE 32 bit number."
			   ::= { gx2Rx085BX4AnalogEntry 55}

		rx085alarmStateModTemp         OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Module Temperature Analog parameter."
			   ::= { gx2Rx085BX4AnalogEntry 56}
-- New Parameter

		rx085labelFanCurrent           OBJECT-TYPE
			   SYNTAX           DisplayString (SIZE (0..80))
			   ACCESS           read-only
			   STATUS           optional
			   DESCRIPTION
			   "The value of this object provides the label of the
			    Fan Current Analog parameter."
			   ::= { gx2Rx085BX4AnalogEntry 57}

		rx085uomFanCurrent             OBJECT-TYPE
			   SYNTAX           DisplayString (SIZE (0..80))
			   ACCESS           read-only
			   STATUS           optional
			   DESCRIPTION
			   "The value of this object provides the Unit of Measure of the
			    Fan Current Analog parameter."
			   ::= { gx2Rx085BX4AnalogEntry 58}

		rx085majorHighFanCurrent       OBJECT-TYPE
			   SYNTAX           Float 
			   ACCESS           read-only
			   STATUS           mandatory
			   DESCRIPTION
			   "The value of this object provides the Major High alarm value
			          of the Fan Current Analog parameter. This value is a floating 
			    point number that is represented as an IEEE 32 bit number."
			   ::= { gx2Rx085BX4AnalogEntry 59}


		rx085majorLowFanCurrent        OBJECT-TYPE
			   SYNTAX           Float 
			   ACCESS           read-only
			   STATUS           mandatory
			   DESCRIPTION
			   "The value of this object provides the Major Low alarm value
			          of the Fan Current Analog parameter. This value is a floating 
			    point number that is represented as an IEEE 32 bit number."
			   ::= { gx2Rx085BX4AnalogEntry 60}

		rx085minorHighFanCurrent       OBJECT-TYPE
			   SYNTAX           Float
			   ACCESS           read-only
			   STATUS           mandatory
			   DESCRIPTION
			   "The value of this object provides the Minor High alarm value
			          of the Fan Current Analog parameter. This value is a floating 
			    point number that is represented as an IEEE 32 bit number."
			   ::= { gx2Rx085BX4AnalogEntry 61}

		rx085minorLowFanCurrent        OBJECT-TYPE
			   SYNTAX           Float 
			   ACCESS           read-only
			   STATUS           mandatory
			   DESCRIPTION
			   "The value of this object provides the Minor Low alarm value
			          of the Fan Current Analog parameter. This value is a floating 
			    point number that is represented as an IEEE 32 bit number."
			   ::= { gx2Rx085BX4AnalogEntry 62}

		rx085currentValueFanCurrent    OBJECT-TYPE
			   SYNTAX           Float 
			   ACCESS           read-only
			   STATUS           mandatory
			   DESCRIPTION
			   "The value of this object provides the Current value
			          of the Fan Current Analog parameter. This value is a floating 
			    point number that is represented as an IEEE 32 bit number."
			   ::= { gx2Rx085BX4AnalogEntry 63}

		rx085stateFlagFanCurrent       OBJECT-TYPE
			   SYNTAX           INTEGER
								{
								hidden(1),
								read-only(2),
								updateable(3)
								}

			   ACCESS           read-only
			   STATUS           mandatory
			   DESCRIPTION
			   "The value of this object provides the state
			    of the Fan Current Analog parameter. (0-Hidden	
			          1-Read-Only, 2-Updateable)."
			   ::= { gx2Rx085BX4AnalogEntry 64}

		rx085minValueFanCurrent        OBJECT-TYPE
			   SYNTAX           Float
			   ACCESS           read-only
			   STATUS           mandatory
			   DESCRIPTION
			   "The value of this object provides the minimum value
			          of the Fan Current Analog parameter. This value is a floating 
			    point number that is represented as an IEEE 32 bit number."
			   ::= { gx2Rx085BX4AnalogEntry 65}

		rx085maxValueFanCurrent        OBJECT-TYPE
			   SYNTAX           Float
			   ACCESS           read-only
			   STATUS           mandatory
			   DESCRIPTION
			   "The value of this object provides the maximum value
			          of the Fan Current Analog parameter. This value is a floating 
			    point number that is represented as an IEEE 32 bit number."
			   ::= { gx2Rx085BX4AnalogEntry 66}

		rx085alarmStateFanCurrent      OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Fan Current Analog parameter."
			   ::= { gx2Rx085BX4AnalogEntry 67}
-- New Parameter

		rx085label12Volt               OBJECT-TYPE
			   SYNTAX           DisplayString (SIZE (0..80))
			   ACCESS           read-only
			   STATUS           optional
			   DESCRIPTION
			   "The value of this object provides the label of the
			    12v Current Analog parameter."
			   ::= { gx2Rx085BX4AnalogEntry 68}

		rx085uom12Volt                 OBJECT-TYPE
			   SYNTAX           DisplayString (SIZE (0..80))
			   ACCESS           read-only
			   STATUS           optional
			   DESCRIPTION
			   "The value of this object provides the Unit of Measure of the
			    12v Current Analog parameter."
			   ::= { gx2Rx085BX4AnalogEntry 69}

		rx085majorHigh12Volt           OBJECT-TYPE
			   SYNTAX           Float 
			   ACCESS           read-only
			   STATUS           mandatory
			   DESCRIPTION
			   "The value of this object provides the Major High alarm value
			          of the 12 Volt Current Analog parameter. This value is a floating 
			    point number that is represented as an IEEE 32 bit number."
			   ::= { gx2Rx085BX4AnalogEntry 70}


		rx085majorLow12Volt            OBJECT-TYPE
			   SYNTAX           Float 
			   ACCESS           read-only
			   STATUS           mandatory
			   DESCRIPTION
			   "The value of this object provides the Major Low alarm value
			          of the 12 Volt Current Analog parameter. This value is a floating 
			    point number that is represented as an IEEE 32 bit number."
			   ::= { gx2Rx085BX4AnalogEntry 71}

		rx085minorHigh12Volt           OBJECT-TYPE
			   SYNTAX           Float
			   ACCESS           read-only
			   STATUS           mandatory
			   DESCRIPTION
			   "The value of this object provides the Minor High alarm value
			          of the 12 Volt Current Analog parameter. This value is a floating 
			    point number that is represented as an IEEE 32 bit number."
			   ::= { gx2Rx085BX4AnalogEntry 72}

		rx085minorLow12Volt            OBJECT-TYPE
			   SYNTAX           Float 
			   ACCESS           read-only
			   STATUS           mandatory
			   DESCRIPTION
			   "The value of this object provides the Minor Low alarm value
			          of the 12 Volt Current Analog parameter. This value is a floating 
			    point number that is represented as an IEEE 32 bit number."
			   ::= { gx2Rx085BX4AnalogEntry 73}

		rx085currentValue12Volt        OBJECT-TYPE
			   SYNTAX           Float 
			   ACCESS           read-only
			   STATUS           mandatory
			   DESCRIPTION
			   "The value of this object provides the Current value
			          of the 12 Volt Current Analog parameter. This value is a floating 
			    point number that is represented as an IEEE 32 bit number."
			   ::= { gx2Rx085BX4AnalogEntry 74}

		rx085stateFlag12Volt           OBJECT-TYPE
			   SYNTAX           INTEGER
								{
								hidden(1),
								read-only(2),
								updateable(3)
								}
			   ACCESS           read-only
			   STATUS           mandatory
			   DESCRIPTION
			   "The value of this object provides the state
			    of the 12v Current Analog parameter. (0-Hidden	
			          1-Read-Only, 2-Updateable)."
			   ::= { gx2Rx085BX4AnalogEntry 75}

		rx085minValue12Volt            OBJECT-TYPE
			   SYNTAX           Float
			   ACCESS           read-only
			   STATUS           mandatory
			   DESCRIPTION
			   "The value of this object provides the minimum value
			          of the 12 Volt Current Analog parameter. This value is a floating 
			    point number that is represented as an IEEE 32 bit number."
			   ::= { gx2Rx085BX4AnalogEntry 76}

		rx085maxValue12Volt            OBJECT-TYPE
			   SYNTAX           Float
			   ACCESS           read-only
			   STATUS           mandatory
			   DESCRIPTION
			   "The value of this object provides the maximum value
			          of the 12 Volt Current Analog parameter. This value is a floating 
			    point number that is represented as an IEEE 32 bit number."
			   ::= { gx2Rx085BX4AnalogEntry 77}

		rx085alarmState12Volt          OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the 12v Current Analog parameter."
			   ::= { gx2Rx085BX4AnalogEntry 78}

-- ************************ Digital parameters **********************************
		gx2Rx085BX4DigitalTableIndex              OBJECT-TYPE
			   SYNTAX           INTEGER (1..4294967295)
			   ACCESS           read-only
			   STATUS           mandatory
			   DESCRIPTION
			   "The value of this object identifies the network
			    element. This index is equal to the
			    hfcCommonTableIndex for the same element."
			   ::= { gx2Rx085BX4DigitalEntry 1}

-- New parameter
		rx085labelModeOne	             	OBJECT-TYPE
			   SYNTAX         	DisplayString (SIZE (0..80))         
			   ACCESS           	read-only
			   STATUS           	optional
			   DESCRIPTION
			   "The value of this object provides the label of the
			    Rx085BX4's Mode  Digital parameter."
			   ::= { gx2Rx085BX4DigitalEntry 2}

		rx085enumModeOne	               	OBJECT-TYPE
			   SYNTAX         	DisplayString (SIZE (0..80))         
			   ACCESS           	read-only
			   STATUS           	optional
			   DESCRIPTION
			   "The value of this object represents the Enumeration values
			    possible for the Digital parameter. Each Enumerated values is
			    separated by a common. The first value has a enumerated value of 1."
			   ::= { gx2Rx085BX4DigitalEntry 3}

		rx085valueModeOne	                OBJECT-TYPE
			   SYNTAX       		INTEGER
					    		{
							off(1),
							manual(2),
							agc(3)
					    		}
			   ACCESS           	read-write
			   STATUS           	mandatory
			   DESCRIPTION
			   "The value of this object is the current value of the parameter."
			   ::= { gx2Rx085BX4DigitalEntry 4}

		rx085stateFlagModeOne	            OBJECT-TYPE
			   SYNTAX         	INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Rx085BX4DigitalEntry 5}
-- New parameter
		rx085labelWavelengthOne             	OBJECT-TYPE
			   SYNTAX         	DisplayString (SIZE (0..80))         
			   ACCESS           	read-only
			   STATUS           	optional
			   DESCRIPTION
			   "The value of this object provides the label of the
			    Rx085BX4's Wavelength  Digital parameter."
			   ::= { gx2Rx085BX4DigitalEntry 6}

		rx085enumWavelengthOne               	OBJECT-TYPE
			   SYNTAX         	DisplayString (SIZE (0..80))         
			   ACCESS           	read-only
			   STATUS           	optional
			   DESCRIPTION
			   "The value of this object represents the Enumeration values
			    possible for the Digital parameter. Each Enumerated values is
			    separated by a common. The first value has a enumerated value of 1."
			   ::= { gx2Rx085BX4DigitalEntry 7}

		rx085valueWavelengthOne               OBJECT-TYPE
			   SYNTAX       		INTEGER
					    		{
							nM1270(1),
							nM1290(2),
							nM1310(3),
							nM1330(4),
							nM1350(5),
							nM1370(6),
							nM1390(7),
							nM1410(8),
							nM1430(9),
							nM1450(10),
							nM1470(11),
							nM1490(12),
							nM1510(13),
							nM1530(14),
							nM1550(15),
							nM1570(16),
							nM1590(17),
							nM1610(18)
								}
			   ACCESS           	read-write
			   STATUS           	mandatory
			   DESCRIPTION
			   "The value of this object is the current value of the parameter."
			   ::= { gx2Rx085BX4DigitalEntry 8}

		rx085stateFlagWavelengthOne	      OBJECT-TYPE
			   SYNTAX         	INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Rx085BX4DigitalEntry 9}
-- New parameter
		rx085labelAttnSettingOne	          	OBJECT-TYPE
			   SYNTAX         	DisplayString (SIZE (0..80))         
			   ACCESS           	read-only
			   STATUS           	optional
			   DESCRIPTION
			   "The value of this object provides the label of the
			    Rx085BX4's AttnSetting  Digital parameter."
			   ::= { gx2Rx085BX4DigitalEntry 10}

		rx085enumAttnSettingOne	          	OBJECT-TYPE
			   SYNTAX         	DisplayString (SIZE (0..80))         
			   ACCESS           	read-only
			   STATUS           	optional
			   DESCRIPTION
			   "The value of this object represents the Enumeration values
			    possible for the Digital parameter. Each Enumerated values is
			    separated by a common. The first value has a enumerated value of 1."
			   ::= { gx2Rx085BX4DigitalEntry 11}

		rx085valueAttnSettingOne	            OBJECT-TYPE
			   SYNTAX       		INTEGER

			   ACCESS           	read-write
			   STATUS           	mandatory
			   DESCRIPTION
			   "The value of this object is the current value of the parameter. It is an integer
                value from 0 to 60. Each increment represents 1/2 dB of attenuation from 0 to 30 dB. 
			    Where 0 = 0db and 60 = 30db"
			   ::= { gx2Rx085BX4DigitalEntry 12}

		rx085stateFlagAttnSettingOne	    	OBJECT-TYPE
			   SYNTAX         	INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Rx085BX4DigitalEntry 13}
-- New parameter
		rx085labelSwModeSettingOne	     	OBJECT-TYPE
			   SYNTAX         	DisplayString (SIZE (0..80))         
			   ACCESS           	read-only
			   STATUS           	optional
			   DESCRIPTION
			   "The value of this object provides the label of the
			    Rx085BX4's Switch Mode Setting  Digital parameter."
			   ::= { gx2Rx085BX4DigitalEntry 14}

		rx085enumSwModeSettingOne	           	OBJECT-TYPE
			   SYNTAX         	DisplayString (SIZE (0..80))         
			   ACCESS           	read-only
			   STATUS           	optional
			   DESCRIPTION
			   "The value of this object represents the Enumeration values
			    possible for the Digital parameter. Each Enumerated values          is
			    separated by a common. The first value has a enumerated value of 1."
			   ::= { gx2Rx085BX4DigitalEntry 15}

		rx085valueSwModeSettingOne	      OBJECT-TYPE
			   SYNTAX       		INTEGER
					    		{
							off(1),
							alarm-only(2),
							alarm-and-switch(3)
					    		}
			   ACCESS           	read-write
			   STATUS           	mandatory
			   DESCRIPTION
			   "The value of this object is the current value of the parameter."
			   ::= { gx2Rx085BX4DigitalEntry 16}

		rx085stateFlagSwModeSettingOne	      OBJECT-TYPE
			   SYNTAX         	INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Rx085BX4DigitalEntry 17}
-- New parameter
		rx085labelSwModeThresholdOne	      OBJECT-TYPE
			   SYNTAX         	DisplayString (SIZE (0..80))         
			   ACCESS           	read-only
			   STATUS           	optional
			   DESCRIPTION
			   "The value of this object provides the label of the
			    Rx085BX4's Switch Mode Threshold  Digital parameter."
			   ::= { gx2Rx085BX4DigitalEntry 18}

		rx085enumSwModeThresholdOne		OBJECT-TYPE
			   SYNTAX         	DisplayString (SIZE (0..80))         
			   ACCESS           	read-only
			   STATUS           	optional
			   DESCRIPTION
			   "The value of this object represents the Enumeration values
			    possible for the Digital parameter. Each Enumerated values is
			    separated by a common. The first value has a enumerated value of 1."
			   ::= { gx2Rx085BX4DigitalEntry 19}

		rx085valueSwModeThresholdOne	      OBJECT-TYPE
			   SYNTAX       		INTEGER
			   ACCESS           	read-write
			   STATUS           	mandatory
			   DESCRIPTION
			   "The value of this object reflects the setting of the threshold at 
			    which the Optical Input Failed signal is sent. It is in 1 dB increments 
                      ranging from -2 to -17 dB. The user can enter a number from 0 to 15,
			    where 0 = -2db and 15= -17db"
			   ::= { gx2Rx085BX4DigitalEntry 20}

		rx085stateFlagSwModeThresholdOne	            OBJECT-TYPE
			   SYNTAX         	INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Rx085BX4DigitalEntry 21}

-- New parameter
		rx085labelModeTwo	             	OBJECT-TYPE
			   SYNTAX         	DisplayString (SIZE (0..80))         
			   ACCESS           	read-only
			   STATUS           	optional
			   DESCRIPTION
			   "The value of this object provides the label of the
			    Rx085BX4's Mode  Digital parameter."
			   ::= { gx2Rx085BX4DigitalEntry 22}

		rx085enumModeTwo	               	OBJECT-TYPE
			   SYNTAX         	DisplayString (SIZE (0..80))         
			   ACCESS           	read-only
			   STATUS           	optional
			   DESCRIPTION
			   "The value of this object represents the Enumeration values
			    possible for the Digital parameter. Each Enumerated values is
			    separated by a common. The first value has a enumerated value of 1."
			   ::= { gx2Rx085BX4DigitalEntry 23}

		rx085valueModeTwo	                OBJECT-TYPE
			   SYNTAX       		INTEGER
					    		{
							off(1),
							manual(2),
							agc(3)
					    		}
			   ACCESS           	read-write
			   STATUS           	mandatory
			   DESCRIPTION
			   "The value of this object is the current value of the parameter."
			   ::= { gx2Rx085BX4DigitalEntry 24}

		rx085stateFlagModeTwo	            OBJECT-TYPE
			   SYNTAX         	INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Rx085BX4DigitalEntry 25}
-- New parameter
		rx085labelWavelengthTwo             	OBJECT-TYPE
			   SYNTAX         	DisplayString (SIZE (0..80))         
			   ACCESS           	read-only
			   STATUS           	optional
			   DESCRIPTION
			   "The value of this object provides the label of the
			    Rx085BX4's Wavelength  Digital parameter."
			   ::= { gx2Rx085BX4DigitalEntry 26}

		rx085enumWavelengthTwo               	OBJECT-TYPE
			   SYNTAX         	DisplayString (SIZE (0..80))         
			   ACCESS           	read-only
			   STATUS           	optional
			   DESCRIPTION
			   "The value of this object represents the Enumeration values
			    possible for the Digital parameter. Each Enumerated values is
			    separated by a common. The first value has a enumerated value of 1."
			   ::= { gx2Rx085BX4DigitalEntry 27}

		rx085valueWavelengthTwo               OBJECT-TYPE
			   SYNTAX       		INTEGER
					    		{
							nM1270(1),
							nM1290(2),
							nM1310(3),
							nM1330(4),
							nM1350(5),
							nM1370(6),
							nM1390(7),
							nM1410(8),
							nM1430(9),
							nM1450(10),
							nM1470(11),
							nM1490(12),
							nM1510(13),
							nM1530(14),
							nM1550(15),
							nM1570(16),
							nM1590(17),
							nM1610(18)
					    		}
			   ACCESS           	read-write
			   STATUS           	mandatory
			   DESCRIPTION
			   "The value of this object is the current value of the parameter."
			   ::= { gx2Rx085BX4DigitalEntry 28}

		rx085stateFlagWavelengthTwo	      OBJECT-TYPE
			   SYNTAX         	INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Rx085BX4DigitalEntry 29}
-- New parameter
		rx085labelAttnSettingTwo	          	OBJECT-TYPE
			   SYNTAX         	DisplayString (SIZE (0..80))         
			   ACCESS           	read-only
			   STATUS           	optional
			   DESCRIPTION
			   "The value of this object provides the label of the
			    Rx085BX4's AttnSetting  Digital parameter."
			   ::= { gx2Rx085BX4DigitalEntry 30}

		rx085enumAttnSettingTwo	          	OBJECT-TYPE
			   SYNTAX         	DisplayString (SIZE (0..80))         
			   ACCESS           	read-only
			   STATUS           	optional
			   DESCRIPTION
			   "The value of this object represents the Enumeration values
			    possible for the Digital parameter. Each Enumerated values is
			    separated by a common. The first value has a enumerated value of 1."
			   ::= { gx2Rx085BX4DigitalEntry 31}

		rx085valueAttnSettingTwo	            OBJECT-TYPE
			   SYNTAX       		INTEGER

			   ACCESS           	read-write
			   STATUS           	mandatory
			   DESCRIPTION
			   "The value of this object is the current value of the parameter. It is an integer 
                      value from 0 to 40. Each increment represents 1/2 dB of attenuation from 0 to 20 dB. 
			    Where 0 = 0db and 40 = 20db"
			   ::= { gx2Rx085BX4DigitalEntry 32}

		rx085stateFlagAttnSettingTwo	    	OBJECT-TYPE
			   SYNTAX         	INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Rx085BX4DigitalEntry 33}
-- New parameter
		rx085labelSwModeSettingTwo	     	OBJECT-TYPE
			   SYNTAX         	DisplayString (SIZE (0..80))         
			   ACCESS           	read-only
			   STATUS           	optional
			   DESCRIPTION
			   "The value of this object provides the label of the
			    Rx085BX4's Switch Mode Setting  Digital parameter."
			   ::= { gx2Rx085BX4DigitalEntry 34}

		rx085enumSwModeSettingTwo	           	OBJECT-TYPE
			   SYNTAX         	DisplayString (SIZE (0..80))         
			   ACCESS           	read-only
			   STATUS           	optional
			   DESCRIPTION
			   "The value of this object represents the Enumeration values
			    possible for the Digital parameter. Each Enumerated values          is
			    separated by a common. The first value has a enumerated value of 1."
			   ::= { gx2Rx085BX4DigitalEntry 35}

		rx085valueSwModeSettingTwo	      OBJECT-TYPE
			   SYNTAX       		INTEGER
					    		{
							off(1),
							alarm-only(2),
							alarm-and-switch(3)
					    		}
			   ACCESS           	read-write
			   STATUS           	mandatory
			   DESCRIPTION
			   "The value of this object is the current value of the parameter."
			   ::= { gx2Rx085BX4DigitalEntry 36}

		rx085stateFlagSwModeSettingTwo	      OBJECT-TYPE
			   SYNTAX         	INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Rx085BX4DigitalEntry 37}
-- New parameter
		rx085labelSwModeThresholdTwo	      OBJECT-TYPE
			   SYNTAX         	DisplayString (SIZE (0..80))         
			   ACCESS           	read-only
			   STATUS           	optional
			   DESCRIPTION
			   "The value of this object provides the label of the
			    Rx085BX4's Switch Mode Threshold  Digital parameter."
			   ::= { gx2Rx085BX4DigitalEntry 38}

		rx085enumSwModeThresholdTwo		OBJECT-TYPE
			   SYNTAX         	DisplayString (SIZE (0..80))         
			   ACCESS           	read-only
			   STATUS           	optional
			   DESCRIPTION
			   "The value of this object represents the Enumeration values
			    possible for the Digital parameter. Each Enumerated values is
			    separated by a common. The first value has a enumerated value of 1."
			   ::= { gx2Rx085BX4DigitalEntry 39}

		rx085valueSwModeThresholdTwo	      OBJECT-TYPE
			   SYNTAX       		INTEGER
			   ACCESS           	read-write
			   STATUS           	mandatory
			   DESCRIPTION
			   "The value of this object reflects the setting of the threshold at 
			    which the Optical Input Failed signal is sent. It is in 1 dB increments 
                      ranging from -2 to -17 dB. The user can enter a number from 0 to 15,
			    where 0 = -2db and 15= -17db"
			   ::= { gx2Rx085BX4DigitalEntry 40}

		rx085stateFlagSwModeThresholdTwo	            OBJECT-TYPE
			   SYNTAX         	INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Rx085BX4DigitalEntry 41}


-- New parameter
		rx085labelModeThree	             	OBJECT-TYPE
			   SYNTAX         	DisplayString (SIZE (0..80))         
			   ACCESS           	read-only
			   STATUS           	optional
			   DESCRIPTION
			   "The value of this object provides the label of the
			    Rx085BX4's Mode  Digital parameter."
			   ::= { gx2Rx085BX4DigitalEntry 42}

		rx085enumModeThree	               	OBJECT-TYPE
			   SYNTAX         	DisplayString (SIZE (0..80))         
			   ACCESS           	read-only
			   STATUS           	optional
			   DESCRIPTION
			   "The value of this object represents the Enumeration values
			    possible for the Digital parameter. Each Enumerated values is
			    separated by a common. The first value has a enumerated value of 1."
			   ::= { gx2Rx085BX4DigitalEntry 43}

		rx085valueModeThree	                OBJECT-TYPE
			   SYNTAX       		INTEGER
					    		{
							off(1),
							manual(2),
							agc(3)
					    		}
			   ACCESS           	read-write
			   STATUS           	mandatory
			   DESCRIPTION
			   "The value of this object is the current value of the parameter."
			   ::= { gx2Rx085BX4DigitalEntry 44}

		rx085stateFlagModeThree	            OBJECT-TYPE
			   SYNTAX         	INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Rx085BX4DigitalEntry 45}
-- New parameter
		rx085labelWavelengthThree             	OBJECT-TYPE
			   SYNTAX         	DisplayString (SIZE (0..80))         
			   ACCESS           	read-only
			   STATUS           	optional
			   DESCRIPTION
			   "The value of this object provides the label of the
			    Rx085BX4's Wavelength  Digital parameter."
			   ::= { gx2Rx085BX4DigitalEntry 46}

		rx085enumWavelengthThree               	OBJECT-TYPE
			   SYNTAX         	DisplayString (SIZE (0..80))         
			   ACCESS           	read-only
			   STATUS           	optional
			   DESCRIPTION
			   "The value of this object represents the Enumeration values
			    possible for the Digital parameter. Each Enumerated values is
			    separated by a common. The first value has a enumerated value of 1."
			   ::= { gx2Rx085BX4DigitalEntry 47}

		rx085valueWavelengthThree               OBJECT-TYPE
			   SYNTAX       		INTEGER
					    		{
							nM1270(1),
							nM1290(2),
							nM1310(3),
							nM1330(4),
							nM1350(5),
							nM1370(6),
							nM1390(7),
							nM1410(8),
							nM1430(9),
							nM1450(10),
							nM1470(11),
							nM1490(12),
							nM1510(13),
							nM1530(14),
							nM1550(15),
							nM1570(16),
							nM1590(17),
							nM1610(18)
					    		}
			   ACCESS           	read-write
			   STATUS           	mandatory
			   DESCRIPTION
			   "The value of this object is the current value of the parameter."
			   ::= { gx2Rx085BX4DigitalEntry 48}

		rx085stateFlagWavelengthThree	      OBJECT-TYPE
			   SYNTAX         	INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Rx085BX4DigitalEntry 49}
-- New parameter
		rx085labelAttnSettingThree	          	OBJECT-TYPE
			   SYNTAX         	DisplayString (SIZE (0..80))         
			   ACCESS           	read-only
			   STATUS           	optional
			   DESCRIPTION
			   "The value of this object provides the label of the
			    Rx085BX4's AttnSetting  Digital parameter."
			   ::= { gx2Rx085BX4DigitalEntry 50}

		rx085enumAttnSettingThree	          	OBJECT-TYPE
			   SYNTAX         	DisplayString (SIZE (0..80))         
			   ACCESS           	read-only
			   STATUS           	optional
			   DESCRIPTION
			   "The value of this object represents the Enumeration values
			    possible for the Digital parameter. Each Enumerated values is
			    separated by a common. The first value has a enumerated value of 1."
			   ::= { gx2Rx085BX4DigitalEntry 51}

		rx085valueAttnSettingThree	            OBJECT-TYPE
			   SYNTAX       		INTEGER

			   ACCESS           	read-write
			   STATUS           	mandatory
			   DESCRIPTION
			   "The value of this object is the current value of the parameter. It is an integer 
                      value from 0 to 40. Each increment represents 1/2 dB of attenuation from 0 to 20 dB. 
			    Where 0 = 0db and 40 = 20db"
			   ::= { gx2Rx085BX4DigitalEntry 52}

		rx085stateFlagAttnSettingThree	    	OBJECT-TYPE
			   SYNTAX         	INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Rx085BX4DigitalEntry 53}
-- New parameter
		rx085labelSwModeSettingThree	     	OBJECT-TYPE
			   SYNTAX         	DisplayString (SIZE (0..80))         
			   ACCESS           	read-only
			   STATUS           	optional
			   DESCRIPTION
			   "The value of this object provides the label of the
			    Rx085BX4's Switch Mode Setting  Digital parameter."
			   ::= { gx2Rx085BX4DigitalEntry 54}

		rx085enumSwModeSettingThree	           	OBJECT-TYPE
			   SYNTAX         	DisplayString (SIZE (0..80))         
			   ACCESS           	read-only
			   STATUS           	optional
			   DESCRIPTION
			   "The value of this object represents the Enumeration values
			    possible for the Digital parameter. Each Enumerated values          is
			    separated by a common. The first value has a enumerated value of 1."
			   ::= { gx2Rx085BX4DigitalEntry 55}

		rx085valueSwModeSettingThree	      OBJECT-TYPE
			   SYNTAX       		INTEGER
					    		{
							off(1),
							alarm-only(2),
							alarm-and-switch(3)
					    		}
			   ACCESS           	read-write
			   STATUS           	mandatory
			   DESCRIPTION
			   "The value of this object is the current value of the parameter."
			   ::= { gx2Rx085BX4DigitalEntry 56}

		rx085stateFlagSwModeSettingThree	      OBJECT-TYPE
			   SYNTAX         	INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Rx085BX4DigitalEntry 57}
-- New parameter
		rx085labelSwModeThresholdThree	      OBJECT-TYPE
			   SYNTAX         	DisplayString (SIZE (0..80))         
			   ACCESS           	read-only
			   STATUS           	optional
			   DESCRIPTION
			   "The value of this object provides the label of the
			    Rx085BX4's Switch Mode Threshold  Digital parameter."
			   ::= { gx2Rx085BX4DigitalEntry 58}

		rx085enumSwModeThresholdThree		OBJECT-TYPE
			   SYNTAX         	DisplayString (SIZE (0..80))         
			   ACCESS           	read-only
			   STATUS           	optional
			   DESCRIPTION
			   "The value of this object represents the Enumeration values
			    possible for the Digital parameter. Each Enumerated values is
			    separated by a common. The first value has a enumerated value of 1."
			   ::= { gx2Rx085BX4DigitalEntry 59}

		rx085valueSwModeThresholdThree	      OBJECT-TYPE
			   SYNTAX       		INTEGER
			   ACCESS           	read-write
			   STATUS           	mandatory
			   DESCRIPTION
			   "The value of this object reflects the setting of the threshold at 
			    which the Optical Input Failed signal is sent. It is in 1 dB increments 
                      ranging from -2 to -17 dB. The user can enter a number from 0 to 15,
			    where 0 = -2db and 15= -17db"
			   ::= { gx2Rx085BX4DigitalEntry 60}

		rx085stateFlagSwModeThresholdThree	            OBJECT-TYPE
			   SYNTAX         	INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Rx085BX4DigitalEntry 61}


-- New parameter
		rx085labelModeFour	             	OBJECT-TYPE
			   SYNTAX         	DisplayString (SIZE (0..80))         
			   ACCESS           	read-only
			   STATUS           	optional
			   DESCRIPTION
			   "The value of this object provides the label of the
			    Rx085BX4's Mode  Digital parameter."
			   ::= { gx2Rx085BX4DigitalEntry 62}

		rx085enumModeFour	               	OBJECT-TYPE
			   SYNTAX         	DisplayString (SIZE (0..80))         
			   ACCESS           	read-only
			   STATUS           	optional
			   DESCRIPTION
			   "The value of this object represents the Enumeration values
			    possible for the Digital parameter. Each Enumerated values is
			    separated by a common. The first value has a enumerated value of 1."
			   ::= { gx2Rx085BX4DigitalEntry 63}

		rx085valueModeFour	                OBJECT-TYPE
			   SYNTAX       		INTEGER
					    		{
							off(1),
							manual(2),
							agc(3)
					    		}
			   ACCESS           	read-write
			   STATUS           	mandatory
			   DESCRIPTION
			   "The value of this object is the current value of the parameter."
			   ::= { gx2Rx085BX4DigitalEntry 64}

		rx085stateFlagModeFour	            OBJECT-TYPE
			   SYNTAX         	INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Rx085BX4DigitalEntry 65}
-- New parameter
		rx085labelWavelengthFour             	OBJECT-TYPE
			   SYNTAX         	DisplayString (SIZE (0..80))         
			   ACCESS           	read-only
			   STATUS           	optional
			   DESCRIPTION
			   "The value of this object provides the label of the
			    Rx085BX4's Wavelength  Digital parameter."
			   ::= { gx2Rx085BX4DigitalEntry 66}

		rx085enumWavelengthFour               	OBJECT-TYPE
			   SYNTAX         	DisplayString (SIZE (0..80))         
			   ACCESS           	read-only
			   STATUS           	optional
			   DESCRIPTION
			   "The value of this object represents the Enumeration values
			    possible for the Digital parameter. Each Enumerated values is
			    separated by a common. The first value has a enumerated value of 1."
			   ::= { gx2Rx085BX4DigitalEntry 67}

		rx085valueWavelengthFour               OBJECT-TYPE
			   SYNTAX       		INTEGER
					    		{
							nM1270(1),
							nM1290(2),
							nM1310(3),
							nM1330(4),
							nM1350(5),
							nM1370(6),
							nM1390(7),
							nM1410(8),
							nM1430(9),
							nM1450(10),
							nM1470(11),
							nM1490(12),
							nM1510(13),
							nM1530(14),
							nM1550(15),
							nM1570(16),
							nM1590(17),
							nM1610(18)
					    		}
			   ACCESS           	read-write
			   STATUS           	mandatory
			   DESCRIPTION
			   "The value of this object is the current value of the parameter."
			   ::= { gx2Rx085BX4DigitalEntry 68}

		rx085stateFlagWavelengthFour	      OBJECT-TYPE
			   SYNTAX         	INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Rx085BX4DigitalEntry 69}
-- New parameter
		rx085labelAttnSettingFour	          	OBJECT-TYPE
			   SYNTAX         	DisplayString (SIZE (0..80))         
			   ACCESS           	read-only
			   STATUS           	optional
			   DESCRIPTION
			   "The value of this object provides the label of the
			    Rx085BX4's AttnSetting  Digital parameter."
			   ::= { gx2Rx085BX4DigitalEntry 70}

		rx085enumAttnSettingFour	          	OBJECT-TYPE
			   SYNTAX         	DisplayString (SIZE (0..80))         
			   ACCESS           	read-only
			   STATUS           	optional
			   DESCRIPTION
			   "The value of this object represents the Enumeration values
			    possible for the Digital parameter. Each Enumerated values is
			    separated by a common. The first value has a enumerated value of 1."
			   ::= { gx2Rx085BX4DigitalEntry 71}

		rx085valueAttnSettingFour	            OBJECT-TYPE
			   SYNTAX       		INTEGER

			   ACCESS           	read-write
			   STATUS           	mandatory
			   DESCRIPTION
			   "The value of this object is the current value of the parameter. It is an integer 
                      value from 0 to 40. Each increment represents 1/2 dB of attenuation from 0 to 20 dB. 
			    Where 0 = 0db and 40 = 20db"
			   ::= { gx2Rx085BX4DigitalEntry 72}

		rx085stateFlagAttnSettingFour	    	OBJECT-TYPE
			   SYNTAX         	INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Rx085BX4DigitalEntry 73}
-- New parameter
		rx085labelSwModeSettingFour	     	OBJECT-TYPE
			   SYNTAX         	DisplayString (SIZE (0..80))         
			   ACCESS           	read-only
			   STATUS           	optional
			   DESCRIPTION
			   "The value of this object provides the label of the
			    Rx085BX4's Switch Mode Setting  Digital parameter."
			   ::= { gx2Rx085BX4DigitalEntry 74}

		rx085enumSwModeSettingFour	           	OBJECT-TYPE
			   SYNTAX         	DisplayString (SIZE (0..80))         
			   ACCESS           	read-only
			   STATUS           	optional
			   DESCRIPTION
			   "The value of this object represents the Enumeration values
			    possible for the Digital parameter. Each Enumerated values          is
			    separated by a common. The first value has a enumerated value of 1."
			   ::= { gx2Rx085BX4DigitalEntry 75}

		rx085valueSwModeSettingFour	      OBJECT-TYPE
			   SYNTAX       		INTEGER
					    		{
							off(1),
							alarm-only(2),
							alarm-and-switch(3)
					    		}
			   ACCESS           	read-write
			   STATUS           	mandatory
			   DESCRIPTION
			   "The value of this object is the current value of the parameter."
			   ::= { gx2Rx085BX4DigitalEntry 76}

		rx085stateFlagSwModeSettingFour	      OBJECT-TYPE
			   SYNTAX         	INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Rx085BX4DigitalEntry 77}
-- New parameter
		rx085labelSwModeThresholdFour	      OBJECT-TYPE
			   SYNTAX         	DisplayString (SIZE (0..80))         
			   ACCESS           	read-only
			   STATUS           	optional
			   DESCRIPTION
			   "The value of this object provides the label of the
			    Rx085BX4's Switch Mode Threshold  Digital parameter."
			   ::= { gx2Rx085BX4DigitalEntry 78}

		rx085enumSwModeThresholdFour		OBJECT-TYPE
			   SYNTAX         	DisplayString (SIZE (0..80))         
			   ACCESS           	read-only
			   STATUS           	optional
			   DESCRIPTION
			   "The value of this object represents the Enumeration values
			    possible for the Digital parameter. Each Enumerated values is
			    separated by a common. The first value has a enumerated value of 1."
			   ::= { gx2Rx085BX4DigitalEntry 79}

		rx085valueSwModeThresholdFour	      OBJECT-TYPE
			   SYNTAX       		INTEGER
			   ACCESS           	read-write
			   STATUS           	mandatory
			   DESCRIPTION
			   "The value of this object reflects the setting of the threshold at 
			    which the Optical Input Failed signal is sent. It is in 1 dB increments 
                      ranging from -2 to -17 dB. The user can enter a number from 0 to 15,
			    where 0 = -2db and 15= -17db"
			   ::= { gx2Rx085BX4DigitalEntry 80}

		rx085stateFlagSwModeThresholdFour	            OBJECT-TYPE
			   SYNTAX         	INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Rx085BX4DigitalEntry 81}

-- New parameter
		rx085labelModuleConfig           OBJECT-TYPE
			   SYNTAX       		DisplayString (SIZE (0..80))         
			   ACCESS           	read-only
			   STATUS           	optional
			   DESCRIPTION
			   "The value of this object provides the label of the
			    Factory Default Reset  Digital parameter."
			   ::= { gx2Rx085BX4DigitalEntry 82}

		rx085enumModuleConfig          	OBJECT-TYPE
			   SYNTAX       		DisplayString (SIZE (0..80))         
			   ACCESS           	read-only
			   STATUS           	optional
			   DESCRIPTION
			   "The value of this object represents the Enumeration values
			    possible for the Digital parameter. Each Enumerated values is
			    separated by a common. The first value has a enumerated value of 1."
			   ::= { gx2Rx085BX4DigitalEntry 83}

		rx085valueModuleConfig         	OBJECT-TYPE
			   SYNTAX       		INTEGER
					    		{
							slave(1),
							master(2),
							burst(3)
					    		}
			   ACCESS           	read-write
			   STATUS           	mandatory
			   DESCRIPTION
			   "The value of this object is the current value of the parameter."
			   ::= { gx2Rx085BX4DigitalEntry 84}

		rx085stateFlagModuleConfig     	OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Rx085BX4DigitalEntry 85}


-- New parameter
		rx085labelRevertTime           OBJECT-TYPE
			   SYNTAX       		DisplayString (SIZE (0..80))         
			   ACCESS           	read-only
			   STATUS           	optional
			   DESCRIPTION
			   "The value of this object provides the label of the
			    Factory Default Reset  Digital parameter."
			   ::= { gx2Rx085BX4DigitalEntry 86}

		rx085enumRevertTime          	OBJECT-TYPE
			   SYNTAX       		DisplayString (SIZE (0..80))         
			   ACCESS           	read-only
			   STATUS           	optional
			   DESCRIPTION
			   "The value of this object represents the Enumeration values
			    possible for the Digital parameter. Each Enumerated values is
			    separated by a common. The first value has a enumerated value of 1."
			   ::= { gx2Rx085BX4DigitalEntry 87}

		rx085valueRevertTime         	OBJECT-TYPE
			   SYNTAX       		INTEGER
					    		{
							one-sec(1),
							ten-sec(2),
							sixty-sec(3),
					    	six-hundred-sec(4)
					    		}
			   ACCESS           	read-write
			   STATUS           	mandatory
			   DESCRIPTION
			   "The value of this object is the current value of the parameter."
			   ::= { gx2Rx085BX4DigitalEntry 88}

		rx085stateFlagRevertTime     	OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Rx085BX4DigitalEntry 89}


-- New parameter
		rx085labelTestPointSelect           OBJECT-TYPE
			   SYNTAX       		DisplayString (SIZE (0..80))         
			   ACCESS           	read-only
			   STATUS           	optional
			   DESCRIPTION
			   "The value of this object provides the label of the
			    Test point Select Digital parameter."
			   ::= { gx2Rx085BX4DigitalEntry 90}

		rx085enumTestPointSelect          	OBJECT-TYPE
			   SYNTAX       		DisplayString (SIZE (0..80))         
			   ACCESS           	read-only
			   STATUS           	optional
			   DESCRIPTION
			   "The value of this object represents the Enumeration values
			    possible for the Digital parameter. Each Enumerated values is
			    separated by a common. The first value has a enumerated value of 1."
			   ::= { gx2Rx085BX4DigitalEntry 91}

		rx085valueTestPointSelect         	OBJECT-TYPE
			   SYNTAX       		INTEGER
					    	{
							one(1),
							two(2),
							three(3),
							four(4)
					    	}
			   ACCESS           	read-write
			   STATUS           	mandatory
			   DESCRIPTION
			   "The value of this object is the current value of the parameter."
			   ::= { gx2Rx085BX4DigitalEntry 92}

		rx085stateFlagTestPointSelect     	OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Rx085BX4DigitalEntry 93}


-- New parameter
		rx085labelFactoryDefault           OBJECT-TYPE
			   SYNTAX       		DisplayString (SIZE (0..80))         
			   ACCESS           	read-only
			   STATUS           	optional
			   DESCRIPTION
			   "The value of this object provides the label of the
			    Factory Default Reset  Digital parameter."
			   ::= { gx2Rx085BX4DigitalEntry 94}

		rx085enumFactoryDefault          	OBJECT-TYPE
			   SYNTAX       		DisplayString (SIZE (0..80))         
			   ACCESS           	read-only
			   STATUS           	optional
			   DESCRIPTION
			   "The value of this object represents the Enumeration values
			    possible for the Digital parameter. Each Enumerated values is
			    separated by a common. The first value has a enumerated value of 1."
			   ::= { gx2Rx085BX4DigitalEntry 95}

		rx085valueFactoryDefault         	OBJECT-TYPE
			   SYNTAX       		INTEGER
					    		{
							off(1),
							on(2)
					    		}
			   ACCESS           	read-write
			   STATUS           	mandatory
			   DESCRIPTION
			   "The value of this object is the current value of the parameter."
			   ::= { gx2Rx085BX4DigitalEntry 96}

		rx085stateFlagFactoryDefault     	OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Rx085BX4DigitalEntry 97}



		--*********** STATUS *****************
		gx2Rx085BX4StatusTableIndex              OBJECT-TYPE
			   SYNTAX           INTEGER (1..4294967295)
			   ACCESS           read-only
			   STATUS           mandatory
			   DESCRIPTION
			   "The value of this object identifies the network
			    element. This index is equal to the
			    hfcCommonTableIndex for the same element."
			   ::= { gx2Rx085BX4StatusEntry 1}

--New Parameter
		rx085labelBoot               	OBJECT-TYPE
			   SYNTAX       		DisplayString (SIZE (0..80))         
			   ACCESS           	read-only
			   STATUS           	optional
			   DESCRIPTION
			   "The value of this object provides the label of the
			    Boot Status  Status parameter."
			   ::= { gx2Rx085BX4StatusEntry 2}

		rx085valueBoot              		OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (0-Ok, 1-Undetermined
			    2-Warning, 3-Minor, 4-Major, 5-Critical)."
			   ::= { gx2Rx085BX4StatusEntry 3}

		rx085stateflagBoot     	OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Rx085BX4StatusEntry  4}


--New Parameter
		rx085labelFlash               	OBJECT-TYPE
			   SYNTAX       		DisplayString (SIZE (0..80))         
			   ACCESS           	read-only
			   STATUS           	optional
			   DESCRIPTION
			   "The value of this object provides the label of the
			    Flash Status  Status parameter."
			   ::= { gx2Rx085BX4StatusEntry 5}

		rx085valueFlash              	OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (0-Ok, 1-Undetermined
			    2-Warning, 3-Minor, 4-Major, 5-Critical)."
			   ::= { gx2Rx085BX4StatusEntry 6}

		rx085stateflagFlash     	OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Rx085BX4StatusEntry 7}


--New Parameter
		rx085labelFactoryDataCRC           OBJECT-TYPE
			   SYNTAX       		DisplayString (SIZE (0..80))         
			   ACCESS           	read-only
			   STATUS           	optional
			   DESCRIPTION
			   "The value of this object provides the label of the
			    Factory Data CRC Status parameter."
			   ::= { gx2Rx085BX4StatusEntry 8}

		rx085valueFactoryDataCRC          	OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (0-Ok, 1-Undetermined
			    2-Warning, 3-Minor, 4-Major, 5-Critical)."
			   ::= { gx2Rx085BX4StatusEntry 9}

		rx085stateflagFactoryDataCRC     	OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Rx085BX4StatusEntry 10}


--New Parameter
		rx085labelAlarmDataCRC             OBJECT-TYPE
			   SYNTAX       		DisplayString (SIZE (0..80))         
			   ACCESS           	read-only
			   STATUS           	optional
			   DESCRIPTION
			   "The value of this object provides the label of the
			    Alarm Data CRC Status parameter."
			   ::= { gx2Rx085BX4StatusEntry 11}

		rx085valueAlarmDataCRC           	OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (0-Ok, 1-Undetermined
			    2-Warning, 3-Minor, 4-Major, 5-Critical)."
			   ::= { gx2Rx085BX4StatusEntry 12}

		rx085stateflagAlarmDataCRC     	OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Rx085BX4StatusEntry 13}


--New Parameter
		rx085labelCalibrationDataCRC       OBJECT-TYPE
			   SYNTAX       		DisplayString (SIZE (0..80))         
			   ACCESS           	read-only
			   STATUS           	optional
			   DESCRIPTION
			   "The value of this object provides the label of the
			    Calibration Data CRC Status parameter."
			   ::= { gx2Rx085BX4StatusEntry 14}

		rx085valueCalibrationDataCRC      	OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (0-Ok, 1-Undetermined
			    2-Warning, 3-Minor, 4-Major, 5-Critical)."
			   ::= { gx2Rx085BX4StatusEntry 15}

		rx085stateflagCalibrationDataCRC     	OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Rx085BX4StatusEntry 16}


--New Parameter
		rx085labelHW               	      OBJECT-TYPE
			   SYNTAX       		DisplayString (SIZE (0..80))         
			   ACCESS           	read-only
			   STATUS           	optional
			   DESCRIPTION
			   "The value of this object provides the label of the
			    Hardware Status parameter."
			   ::= { gx2Rx085BX4StatusEntry 17}

		rx085valueHW              		OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (0-Ok, 1-Undetermined
			    2-Warning, 3-Minor, 4-Major, 5-Critical)."
			   ::= { gx2Rx085BX4StatusEntry 18}

		rx085stateflagHW     	OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Rx085BX4StatusEntry 19}


--New Parameter
		rx085labelOptSigOne		    OBJECT-TYPE
			   SYNTAX       		DisplayString (SIZE (0..80))         
			   ACCESS           	read-only
			   STATUS           	optional
			   DESCRIPTION
			   "The value of this object provides the label of the
			    Optical Signal Status parameter."
			   ::= { gx2Rx085BX4StatusEntry 20}

		rx085valueOptSigOne       	OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (0-Ok, 1-Undetermined
			    2-Warning, 3-Minor, 4-Major, 5-Critical)."
			   ::= { gx2Rx085BX4StatusEntry 21}

		rx085stateflagOptSigOne     	OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Rx085BX4StatusEntry 22}

--New Parameter
		rx085labelOptSigTwo		    OBJECT-TYPE
			   SYNTAX       		DisplayString (SIZE (0..80))         
			   ACCESS           	read-only
			   STATUS           	optional
			   DESCRIPTION
			   "The value of this object provides the label of the
			    Optical Signal Status parameter."
			   ::= { gx2Rx085BX4StatusEntry 23}

		rx085valueOptSigTwo       	OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (0-Ok, 1-Undetermined
			    2-Warning, 3-Minor, 4-Major, 5-Critical)."
			   ::= { gx2Rx085BX4StatusEntry 24}

		rx085stateflagOptSigTwo     	OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Rx085BX4StatusEntry 25}

--New Parameter
		rx085labelOptSigThree		    OBJECT-TYPE
			   SYNTAX       		DisplayString (SIZE (0..80))         
			   ACCESS           	read-only
			   STATUS           	optional
			   DESCRIPTION
			   "The value of this object provides the label of the
			    Optical Signal Status parameter."
			   ::= { gx2Rx085BX4StatusEntry 26}

		rx085valueOptSigThree       	OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (0-Ok, 1-Undetermined
			    2-Warning, 3-Minor, 4-Major, 5-Critical)."
			   ::= { gx2Rx085BX4StatusEntry 27}

		rx085stateflagOptSigThree     	OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Rx085BX4StatusEntry 28}

--New Parameter
		rx085labelOptSigFour		    OBJECT-TYPE
			   SYNTAX       		DisplayString (SIZE (0..80))         
			   ACCESS           	read-only
			   STATUS           	optional
			   DESCRIPTION
			   "The value of this object provides the label of the
			    Optical Signal Status parameter."
			   ::= { gx2Rx085BX4StatusEntry 29}

		rx085valueOptSigFour       	OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (0-Ok, 1-Undetermined
			    2-Warning, 3-Minor, 4-Major, 5-Critical)."
			   ::= { gx2Rx085BX4StatusEntry 30}

		rx085stateflagOptSigFour     	OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Rx085BX4StatusEntry 31}

--New Parameter
		rx085labelBackupCable		    OBJECT-TYPE
			   SYNTAX       		DisplayString (SIZE (0..80))         
			   ACCESS           	read-only
			   STATUS           	optional
			   DESCRIPTION
			   "The value of this object provides the label of the
			    Backup Cable Status parameter."
			   ::= { gx2Rx085BX4StatusEntry 32}

		rx085valueBackupCable       	OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (0-Ok, 1-Undetermined
			    2-Warning, 3-Minor, 4-Major, 5-Critical)."
			   ::= { gx2Rx085BX4StatusEntry 33}

		rx085stateflagBackupCable     	OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Rx085BX4StatusEntry 34}

            -- ************ FACTORY DATA ****************
		gx2Rx085BX4FactoryTableIndex              OBJECT-TYPE
			   SYNTAX           INTEGER (1..4294967295)
			   ACCESS           read-only
			   STATUS           mandatory
			   DESCRIPTION
			   "The value of this object identifies the network
			    element. This index is equal to the
			    hfcCommonTableIndex for the same element."
			   ::= { gx2Rx085BX4FactoryEntry 1}

		rx085bootControlByte          	OBJECT-TYPE
			   SYNTAX       		INTEGER
			   ACCESS           	read-only
			   STATUS           	mandatory
			   DESCRIPTION
			   "The value of this object indicates which bank the firmware
			    is currently being boot from."
			   ::= { gx2Rx085BX4FactoryEntry 2}

		rx085bootStatusByte          	OBJECT-TYPE
			   SYNTAX       		INTEGER
			   ACCESS           	read-only
			   STATUS           	mandatory
			   DESCRIPTION
			   "This object indicates the status of the last boot"
			   ::= { gx2Rx085BX4FactoryEntry 3}

		rx085bank0CRC          		OBJECT-TYPE
			   SYNTAX       		INTEGER
			   ACCESS           	read-only
			   STATUS           	mandatory
			   DESCRIPTION
			   "This object provides the CRC code of bank 0."
			   ::= { gx2Rx085BX4FactoryEntry 4}

		rx085bank1CRC          		OBJECT-TYPE
			   SYNTAX       		INTEGER
			   ACCESS           	read-only
			   STATUS           	mandatory
			   DESCRIPTION
			   "This object provides the CRC code of bank 1."
			   ::= { gx2Rx085BX4FactoryEntry 5}

		rx085prgEEPROMByte          		OBJECT-TYPE
			   SYNTAX       		INTEGER
			   ACCESS           	read-only
			   STATUS           	mandatory
			   DESCRIPTION
			   "This object indicates if the EEPROM has been programmed"
			   ::= { gx2Rx085BX4FactoryEntry 6}

		rx085factoryCRC          		OBJECT-TYPE
			   SYNTAX       		INTEGER
			   ACCESS           	read-only
			   STATUS           	mandatory
			   DESCRIPTION
			   "This object provides the CRC code for the Factory data."
			   ::= { gx2Rx085BX4FactoryEntry 7}

		rx085calculateCRC          		OBJECT-TYPE
			   SYNTAX       		INTEGER
					    		{
							factory(1),
							calibration(2),
							alarm(3),
							tempComp(4)
					    		}
			   ACCESS           	read-only
			   STATUS           	mandatory
			   DESCRIPTION
			   "This object indicates which of the Emnums will have the CRC calculated."
			   ::= { gx2Rx085BX4FactoryEntry 8}

		rx085hourMeter          		OBJECT-TYPE
			   SYNTAX       		INTEGER
			   ACCESS           	read-only
			   STATUS           	mandatory
			   DESCRIPTION
			   "This object provides the hour meter reading of the module."
			   ::= { gx2Rx085BX4FactoryEntry 9}

		rx085flashPrgCntA          		OBJECT-TYPE
			   SYNTAX       		INTEGER
			   ACCESS           	read-only
			   STATUS           	mandatory
			   DESCRIPTION
			   "This object provides the number of times the flash has been 
                      programmed on side A."
			   ::= { gx2Rx085BX4FactoryEntry 10}

		rx085flashPrgCntB          		OBJECT-TYPE
			   SYNTAX       		INTEGER
			   ACCESS           	read-only
			   STATUS           	mandatory
			   DESCRIPTION
			   "This object provides the number of times the flash has been 
                      programmed on side B."
			   ::= { gx2Rx085BX4FactoryEntry 11}

		rx085fwRev0     		     		OBJECT-TYPE
			   SYNTAX       		DisplayString (SIZE (0..80))
			   ACCESS           	read-only
			   STATUS           	mandatory
			   DESCRIPTION
			   "This object provides the Revision of the firmware stores in bank 0."
			   ::= { gx2Rx085BX4FactoryEntry 12}

		rx085fwRev1     		     		OBJECT-TYPE
			   SYNTAX       		DisplayString (SIZE (0..80))
			   ACCESS           	read-only
			   STATUS           	mandatory
			   DESCRIPTION
			   "This object provides the Revision of the firmware stores in bank 1."
			   ::= { gx2Rx085BX4FactoryEntry 13}


-- ****************************************************************
--
-- TRAP DEFINITIONS
--
--
-- Every trap generated by an HFC agents will include first 9 identical
-- fields. If particular variable is not supported in
-- particular TRAP-TYPE then default value will be returned.
--
-- DESCRIPTION will include explanation of use of generic
-- variables (trapAdditionalInfo******.)  If no
-- DESCRIPTION is given then generic variables will contain
-- default values.
--
-- *****************************************************************
-- **************************************************************************
--                              Rx085BX4 Module traps
-- **************************************************************************
   trapRx085BX4ConfigChangeInteger TRAP-TYPE
       ENTERPRISE gx2Rx085BX4
       VARIABLES
	       {       
		trapIdentifier,
		trapNetworkElemModelNumber,
		trapNetworkElemSerialNum,
		trapPerceivedSeverity,
		trapNetworkElemOperState,
		trapNetworkElemAlarmStatus,  
		trapNetworkElemAdminState,
		trapNetworkElemAvailStatus,
		trapText,
		trapChangedObjectId,
		trapChangedValueInteger,
		trapNETrapLastTrapTimeStamp
	       }
       DESCRIPTION
	"This trap is issued if configuration of a single variable
	 with integer type was changed (via ANY interface).  
	 TrapChangedValueInteger variable may contain current reading
	 of that variable.
	 trapPerceivedSeverity - 'indeterminate'"
  ::= 1

   trapRx085BX4ConfigChangeDisplayString TRAP-TYPE
       ENTERPRISE gx2Rx085BX4
       VARIABLES
	       {       
		trapIdentifier,
		trapNetworkElemModelNumber,
		trapNetworkElemSerialNum,
		trapPerceivedSeverity,
		trapNetworkElemOperState,
		trapNetworkElemAlarmStatus,  
		trapNetworkElemAdminState,
		trapNetworkElemAvailStatus,
		trapText,
		trapChangedObjectId,
		trapChangedValueDisplayString,
		trapNETrapLastTrapTimeStamp
	       }
       DESCRIPTION
	"This trap is issued if configuration of a single variable
	 with DispalayString type was changed (via ANY interface).  
	 TrapChangedValueDisplayString variable may contain current reading
	 of that variable.
	 trapPerceivedSeverity - 'indeterminate'"
  ::= 2
  
  trapRx085BX4OpticalPower1Alarm TRAP-TYPE
	ENTERPRISE gx2Rx085BX4
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Receiver's channel 1 Optical Power parameter 
	 goes out of range.
	 trapAdditionalInfoInteger variable contains current reading of 
	 the this parameter."
  ::= 3

  trapRx085BX4OpticalPower2Alarm TRAP-TYPE
	ENTERPRISE gx2Rx085BX4
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Receiver's channel 2  Optical Power parameter 
	 goes out of range.
	 trapAdditionalInfoInteger variable contains current reading of 
	 the this parameter."
  ::= 4

  trapRx085BX4OpticalPower3Alarm TRAP-TYPE
	ENTERPRISE gx2Rx085BX4
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Receiver's channel 3 Optical Power parameter 
	 goes out of range.
	 trapAdditionalInfoInteger variable contains current reading of 
	 the this parameter."
  ::= 5

  trapRx085BX4OpticalPower4Alarm TRAP-TYPE
	ENTERPRISE gx2Rx085BX4
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Receiver's channel 4 Optical Power parameter 
	 goes out of range.
	 trapAdditionalInfoInteger variable contains current reading of 
	 the this parameter."
  ::= 6

  trapRx085BX4ModuleTemperatureAlarm TRAP-TYPE
	ENTERPRISE gx2Rx085BX4
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Rx085BX4 Modules Temperature goes out of range.
	 trapAdditionalInfoInteger variable contains current reading of 
	 the this parameter."
  ::= 7

  trapRx085BX4FanCurrentAlarm TRAP-TYPE
	ENTERPRISE gx2Rx085BX4
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Rx085BX4 Modules Fan Currrent parameter 
	 goes out of range. trapAdditionalInfoInteger variable contains current reading of 
	 the this parameter."
  ::= 8

  trapRx085BX4Plus12CurrentAlarm TRAP-TYPE
	ENTERPRISE gx2Rx085BX4
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Rx085BX4 Modules positive 12 volt current parameter 
	 goes out of range. trapAdditionalInfoInteger variable contains current reading of 
	 the this parameter."
  ::= 9

  trapRx085BX4Boot0Alarm TRAP-TYPE
	ENTERPRISE gx2Rx085BX4
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Rx085BX4 Modules Bank 0 Boot sequence has detected an error.
       trapAdditionalInfoInteger variable contains current reading of 
	 the this parameter."
  ::= 10

  trapRx085BX4Boot1Alarm TRAP-TYPE
	ENTERPRISE gx2Rx085BX4
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Rx085BX4 Modules Bank 1 Boot sequence has detected an error.
       trapAdditionalInfoInteger variable contains current reading of 
	 the this parameter."
  ::= 11

  trapRx085BX4FlashAlarm TRAP-TYPE
	ENTERPRISE gx2Rx085BX4
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Rx085BX4 Modules boot or flash programming sequence has 
       detected a Flash error. trapAdditionalInfoInteger variable contains current reading of 
	 the this parameter."
  ::= 12

  trapRx085BX4AlarmDataCRCAlarm TRAP-TYPE
	ENTERPRISE gx2Rx085BX4
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
      DESCRIPTION
      "This trap is issued when the Rx085BX4 Module detects an error calculating the alarm limit CRC.
       trapAdditionalInfoInteger variable contains current reading of the this parameter."
  ::= 13

  trapRx085BX4FactoryDataCRCAlarm TRAP-TYPE
	ENTERPRISE gx2Rx085BX4
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
      DESCRIPTION
      "This trap is issued when the Rx085BX4 Module detects an error calculating the Factory data CRC.
       trapAdditionalInfoInteger variable contains current reading of the this parameter."
  ::= 14

  trapRx085BX4CalDataCRCAlarm TRAP-TYPE
	ENTERPRISE gx2Rx085BX4
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
      DESCRIPTION
      "This trap is issued when the Rx085BX4 Module detects an error calculating the Calibration data CRC.
       trapAdditionalInfoInteger variable contains current reading of the this parameter."
  ::= 15

  trapRx085BX4DefaultAlarm TRAP-TYPE
	ENTERPRISE gx2Rx085BX4
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
      DESCRIPTION
      "This trap is issued when the Rx085BX4 Module is reset to it's factory default state.
       trapAdditionalInfoInteger variable contains current reading of the this parameter."
  ::= 16

  trapRx085BX4Mode1Alarm TRAP-TYPE
	ENTERPRISE gx2Rx085BX4
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
      DESCRIPTION
      "This trap is issued when the Rx085BX4 Modules receiver 1 mode is changed from manual or AGC to off and back.
       trapAdditionalInfoInteger variable contains current reading of the this parameter."
  ::= 17

  trapRx085BX4Mode2Alarm TRAP-TYPE
	ENTERPRISE gx2Rx085BX4
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
      DESCRIPTION
      "This trap is issued when the Rx085BX4 Modules receiver 1 mode is changed from manual or AGC to off and back.
       trapAdditionalInfoInteger variable contains current reading of the this parameter."
  ::= 18

  trapRx085BX4Mode3Alarm TRAP-TYPE
	ENTERPRISE gx2Rx085BX4
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
      DESCRIPTION
      "This trap is issued when the Rx085BX4 Modules receiver 1 mode is changed from manual or AGC to off and back.
       trapAdditionalInfoInteger variable contains current reading of the this parameter."
  ::= 19

  trapRx085BX4Mode4Alarm TRAP-TYPE
	ENTERPRISE gx2Rx085BX4
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
      DESCRIPTION
      "This trap is issued when the Rx085BX4 Modules receiver 1 mode is changed from manual or AGC to off and back.
       trapAdditionalInfoInteger variable contains current reading of the this parameter."
  ::= 20

  trapRx085BX4Output1SwitchedAlarm TRAP-TYPE
	ENTERPRISE gx2Rx085BX4
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
      DESCRIPTION
      "This trap is issued when the Rx085BX4 Module's receiver 1 output to the RF Switch Module changes state 
       from good to bad or bad to good. trapAdditionalInfoInteger variable contains current reading 
       of the this parameter."
  ::= 21

  trapRx085BX4Output2SwitchedAlarm TRAP-TYPE
	ENTERPRISE gx2Rx085BX4
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
      DESCRIPTION
      "This trap is issued when the Rx085BX4 Module's receiver 2 output to the RF Switch Module changes state 
       from good to bad or bad to good. trapAdditionalInfoInteger variable contains current reading 
       of the this parameter."
  ::= 22

  trapRx085BX4Output3SwitchedAlarm TRAP-TYPE
	ENTERPRISE gx2Rx085BX4
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
      DESCRIPTION
      "This trap is issued when the Rx085BX4 Module's receiver 3 output to the RF Switch Module changes state 
       from good to bad or bad to good. trapAdditionalInfoInteger variable contains current reading 
       of the this parameter."
  ::= 23

  trapRx085BX4Output4SwitchedAlarm TRAP-TYPE
	ENTERPRISE gx2Rx085BX4
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
      DESCRIPTION
      "This trap is issued when the Rx085BX4 Module's receiver 4 output to the RF Switch Module changes state 
       from good to bad or bad to good. trapAdditionalInfoInteger variable contains current reading 
       of the this parameter."
  ::= 24

  trapRx085BX4RX1StatusAlarm TRAP-TYPE
	ENTERPRISE gx2Rx085BX4
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
      DESCRIPTION
      "This trap is issued when receiver 1 of the Rx085BX4 Module output is turned on or off."
  ::= 25

  trapRx085BX4RX2StatusAlarm TRAP-TYPE
	ENTERPRISE gx2Rx085BX4
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
      DESCRIPTION
      "This trap is issued when receiver 2 of the Rx085BX4 Module output is turned on or off."
  ::= 26

  trapRx085BX4RX3StatusAlarm TRAP-TYPE
	ENTERPRISE gx2Rx085BX4
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
      DESCRIPTION
      "This trap is issued when receiver 3 of the Rx085BX4 Module output is turned on or off."
  ::= 27

  trapRx085BX4RX4StatusAlarm TRAP-TYPE
	ENTERPRISE gx2Rx085BX4
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
      DESCRIPTION
      "This trap is issued when receiver 4 of the Rx085BX4 Module output is turned on or off."
  ::= 28

  trapRx085BX4BackupCableAlarm TRAP-TYPE
	ENTERPRISE gx2Rx085BX4
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
      DESCRIPTION
      "This trap is issued when the slave receiver loses connection to the master receiver."
  ::= 29

  trapRx085BX4OptPwr1BadAlarm TRAP-TYPE
	ENTERPRISE gx2Rx085BX4
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
      DESCRIPTION
      "This trap is issued when the receiver 1 optical power level falls below the user set switching threshold."
  ::= 30

trapRx085BX4OptPwr2BadAlarm TRAP-TYPE
	ENTERPRISE gx2Rx085BX4
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
      DESCRIPTION
      "This trap is issued when the receiver 2 optical power level falls below the user set switching threshold."
  ::= 31

trapRx085BX4OptPwr3BadAlarm TRAP-TYPE
	ENTERPRISE gx2Rx085BX4
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
      DESCRIPTION
      "This trap is issued when the receiver 3 optical power level falls below the user set switching threshold."
  ::= 32

trapRx085BX4OptPwr4BadAlarm TRAP-TYPE
	ENTERPRISE gx2Rx085BX4
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
      DESCRIPTION
      "This trap is issued when the receiver 4 optical power level falls below the user set switching threshold."
  ::= 33

  END
