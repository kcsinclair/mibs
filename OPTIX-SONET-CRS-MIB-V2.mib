--
-- OPTIX-SONET-CRS-MIB-V2.mib
-- MIB generated by MG-SOFT Visual MIB Builder Version 3.0 Build 253
-- Monday, July 17, 2006 at 13:45:26
--

	OPTIX-SONET-CRS-MIB-V2 DEFINITIONS ::= BEGIN
 
		IMPORTS
			optixProvisionSonet			
				FROM OPTIX-OID-MIB			
			OBJECT-GROUP, MODULE-COMPLIANCE			
				FROM SNMPv2-CONF			
			OBJECT-TYPE, MODULE-IDENTITY			
				FROM SNMPv2-SMI			
			TEXTUAL-CONVENTION			
				FROM SNMPv2-TC;
	
	
		optixsonetCRS MODULE-IDENTITY 
			LAST-UPDATED "200605232001Z"		-- May 23, 2006 at 20:01 GMT
			ORGANIZATION 
				"Your organization"
			CONTACT-INFO 
				"Your contact info"
			DESCRIPTION 
				"Enter the description for this MIB module."
			::= { optixProvisionSonet 1 }
		
	
--
-- Textual conventions
--
	
		RowStatus ::= TEXTUAL-CONVENTION
			STATUS current
			DESCRIPTION 
				"Enter the description for the RowStatus TEXTUAL-CONVENTION converted from type assignment."
			SYNTAX INTEGER
				{
				active(1),
				notInService(2),
				notReady(3),
				createAndGo(4),
				createAndWait(5),
				destroy(6)
				}
			
	
--
-- Node definitions
--
	
		-- 1.3.6.1.4.1.2011.2.25.4.20.1.3
		optixsonetCrsTable OBJECT-TYPE
			SYNTAX SEQUENCE OF OptixsonetCrsEntry
			MAX-ACCESS not-accessible
			STATUS current
			DESCRIPTION
				"Description."
			::= { optixsonetCRS 3 }
		
		-- 1.3.6.1.4.1.2011.2.25.4.20.1.3.1
		optixsonetCrsEntry OBJECT-TYPE
			SYNTAX OptixsonetCrsEntry
			MAX-ACCESS not-accessible
			STATUS current
			DESCRIPTION
				"Description."
			INDEX { optixsonetCrsMod2, optixsonetCrsFrom, optixsonetCrsTo, optixsonetCrsCct }
			::= { optixsonetCrsTable 1 }
		
		OptixsonetCrsEntry ::=
			SEQUENCE { 
				optixsonetCrsMod2
					INTEGER,
				optixsonetCrsFrom
					OCTET STRING,
				optixsonetCrsTo
					OCTET STRING,
				optixsonetCrsCct
					INTEGER,
				optixsonetCrsCktId
					OCTET STRING,
				optixsonetCrsPreferredPath
					OCTET STRING,
				optixsonetCrsRDLD
					INTEGER,
				optixsonetCrsActivePath
					OCTET STRING,
				optixsonetCrsRowStatus
					RowStatus
			 }

		-- 1.3.6.1.4.1.2011.2.25.4.20.1.3.1.1
		optixsonetCrsMod2 OBJECT-TYPE
			SYNTAX INTEGER
				{
				crsSTS1(9),
				crsSTS3C(10),
				crsSTS6C(11),
				crsSTS9C(12),
				crsSTS12C(13),
				crsSTS24C(15),
				crsSTS48C(16),
				crsSTS192C(17),
				crsVT1(21),
				crsVT2(22)
				}
			MAX-ACCESS read-only
			STATUS current
			DESCRIPTION
				"The modifier that identifies the type of STS and VT path"
			::= { optixsonetCrsEntry 1 }
		
		-- 1.3.6.1.4.1.2011.2.25.4.20.1.3.1.2
		optixsonetCrsFrom OBJECT-TYPE
			SYNTAX OCTET STRING (SIZE (0..32))
			MAX-ACCESS read-only
			STATUS current
			DESCRIPTION
				"Access identifier. It can be source or destination of cross connection, or any one path of source or destination. It can be null, that means retrieve all cross connection with entered rate level. '&' is allowed. "
			::= { optixsonetCrsEntry 2 }
		
		-- 1.3.6.1.4.1.2011.2.25.4.20.1.3.1.3
		optixsonetCrsTo OBJECT-TYPE
			SYNTAX OCTET STRING (SIZE (0..32))
			MAX-ACCESS read-only
			STATUS current
			DESCRIPTION
				"Access identifier identifies the other end of the cross connection. If creating 1-to-N one-way cross-connection, multiple '&' and '&&'are allowed. Else only one '&' is allowed. <TO> cannot be null."
			::= { optixsonetCrsEntry 3 }
		
		-- 1.3.6.1.4.1.2011.2.25.4.20.1.3.1.4
		optixsonetCrsCct OBJECT-TYPE
			SYNTAX INTEGER
				{
				twoWay(1),
				oneWay(2)
				}
			MAX-ACCESS read-only
			STATUS current
			DESCRIPTION
				"Cross connect type."
			::= { optixsonetCrsEntry 4 }
		
		-- 1.3.6.1.4.1.2011.2.25.4.20.1.3.1.5
		optixsonetCrsCktId OBJECT-TYPE
			SYNTAX OCTET STRING (SIZE (0..32))
			MAX-ACCESS read-write
			STATUS current
			DESCRIPTION
				"The circuit identification. It is a string of max length 32 ASCII characters. The circuit identification parameter contains the common language circuit ID or other alias of the circuit being provisioned."
			::= { optixsonetCrsEntry 5 }
		
		-- 1.3.6.1.4.1.2011.2.25.4.20.1.3.1.6
		optixsonetCrsPreferredPath OBJECT-TYPE
			SYNTAX OCTET STRING (SIZE (0..32))
			MAX-ACCESS read-write
			STATUS current
			DESCRIPTION
				"Preferred path. It is only supplied for UPSR. Two values separated by '&' are applicable to only UPSR with 2 sources and 2 destinations."
			::= { optixsonetCrsEntry 6 }
		
		-- 1.3.6.1.4.1.2011.2.25.4.20.1.3.1.7
		optixsonetCrsRDLD OBJECT-TYPE
			SYNTAX INTEGER
				{
				rdld(1),
				rdldDEA(2)
				}
			MAX-ACCESS read-write
			STATUS current
			DESCRIPTION
				"Redline state.Vaild values are RDLD and RDLDDEA.
				RDLD    This value indicates that the entity is a special (red-lined) circuit.
				RDLDDEA Deactive RDLD state."
			::= { optixsonetCrsEntry 7 }
		
		-- 1.3.6.1.4.1.2011.2.25.4.20.1.3.1.8
		optixsonetCrsActivePath OBJECT-TYPE
			SYNTAX OCTET STRING
			MAX-ACCESS read-only
			STATUS current
			DESCRIPTION
				"Active path. It is only supplied for UPSR. Two values separated by '&' are applicable to only UPSR with 2 sources and 2 destinations. "
			::= { optixsonetCrsEntry 8 }
		
		-- 1.3.6.1.4.1.2011.2.25.4.20.1.3.1.10
		optixsonetCrsRowStatus OBJECT-TYPE
			SYNTAX RowStatus
			MAX-ACCESS read-write
			STATUS current
			DESCRIPTION
				"The RowStatus textual convention is used to manage the creation and deletion of conceptual rows, and is used as the
				value of the SYNTAX clause for the status column of a conceptual row.
				The status column has six defined values:
				
				                 - `active', which indicates that the conceptual row is
				                 available for use by the managed device;
				
				                 - `notInService', which indicates that the conceptual
				                 row exists in the agent, but is unavailable for use by
				                 the managed device (see NOTE below);
				
				                 - `notReady', which indicates that the conceptual row
				                 exists in the agent, but is missing information
				                 necessary in order to be available for use by the
				                 managed device;
				
				                 - `createAndGo', which is supplied by a management
				                 station wishing to create a new instance of a
				                 conceptual row and to have its status automatically set
				                 to active, making it available for use by the managed
				                 device;
				
				                 - `createAndWait', which is supplied by a management
				                 station wishing to create a new instance of a
				                 conceptual row (but not make it available for use by
				                 the managed device); and,
				
				                 - `destroy', which is supplied by a management station
				                 wishing to delete all of the instances associated with
				                 an existing conceptual row.
				
				            Whereas five of the six values (all except `notReady') may
				            be specified in a management protocol set operation, only
				            three values will be returned in response to a management
				            protocol retrieval operation:  `notReady', `notInService' or
				            `active'.  That is, when queried, an existing conceptual row
				            has only three states:  it is either available for use by
				            the managed device (the status column has value `active');
				            it is not available for use by the managed device, though
				            the agent has sufficient information to make it so (the
				            status column has value `notInService'); or, it is not
				            available for use by the managed device, and an attempt to
				            make it so would fail because the agent has insufficient
				            information (the state column has value `notReady')."
			::= { optixsonetCrsEntry 10 }
		
		-- 1.3.6.1.4.1.2011.2.25.4.20.1.4
		optixsonetCRSConformance OBJECT IDENTIFIER ::= { optixsonetCRS 4 }
		
		-- 1.3.6.1.4.1.2011.2.25.4.20.1.4.1
		optixsonetCRSGroups OBJECT IDENTIFIER ::= { optixsonetCRSConformance 1 }
		
		-- 1.3.6.1.4.1.2011.2.25.4.20.1.4.1.1
		currentObjectGroup OBJECT-GROUP
			OBJECTS { optixsonetCrsMod2, optixsonetCrsFrom, optixsonetCrsTo, optixsonetCrsCct, optixsonetCrsCktId, 
				optixsonetCrsPreferredPath, optixsonetCrsRDLD, optixsonetCrsActivePath, optixsonetCrsRowStatus }
			STATUS current
			DESCRIPTION 
				"Enter the description of the created OBJECT-GROUP."
			::= { optixsonetCRSGroups 1 }
		
		-- 1.3.6.1.4.1.2011.2.25.4.20.1.4.2
		optixsonetCRSCompliances OBJECT IDENTIFIER ::= { optixsonetCRSConformance 2 }
		
		-- 1.3.6.1.4.1.2011.2.25.4.20.1.4.2.1
		basicCompliance MODULE-COMPLIANCE
			STATUS current
			DESCRIPTION 
				"Enter the description of the created MODULE-COMPLIANCE."
			MODULE -- this module
				MANDATORY-GROUPS { currentObjectGroup }
			::= { optixsonetCRSCompliances 1 }
		
	
	END

--
-- OPTIX-SONET-CRS-MIB-V2.mib
--
