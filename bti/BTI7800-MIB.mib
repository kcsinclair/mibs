BTI7800-MIB DEFINITIONS ::= BEGIN

IMPORTS
    MODULE-IDENTITY, enterprises
        FROM SNMPv2-SMI;

bTI7800-MIB MODULE-IDENTITY
    LAST-UPDATED "201510081200Z"  -- Thursday, October 08, 12:00:00 EST 2015
    ORGANIZATION "BTI Systems Inc."
    CONTACT-INFO "Technical Support
                  BTI Systems Inc.
                  200-1000 Innovation Dr.
                  Kanata, Ontario, Canada  K2K 3E7
                  (613) 287-1700
                  support@btisystems.com"
    DESCRIPTION  "BTI7800-MIB original version"

    ::= { enterprises 18070 2 9 3 }

END
