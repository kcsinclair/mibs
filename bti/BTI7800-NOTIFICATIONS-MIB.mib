BTI7800-NOTIFICATIONS-MIB DEFINITIONS ::= BEGIN

IMPORTS
    enterprises, MODULE-IDENTITY, OBJECT-TYPE, NOTIFICATION-TYPE
        FROM SNMPv2-SMI
    TEXTUAL-CONVENTION, DateAndTime, TruthValue, DisplayString
        FROM SNMPv2-TC;

bTI7800-NOTIFICATIONS-MIB MODULE-IDENTITY
    LAST-UPDATED "201405050000Z"
    ORGANIZATION "BTI Systems Inc."
    CONTACT-INFO "Technical Support
                  BTI Systems Inc.
                  200-1000 Innovation Drive
                  Kanata, Ontario, Canada, K2K 3E7
                  NA Toll Free: +1 866-431-4967
                  International: +1 613-239-4781
                  support@btisystems.com"
    DESCRIPTION "The bti7800-conditions submodule defines the data modeling that supports
                 the retrieval of active alarms and conditions on the BTI7800 system."
    REVISION "201402020000Z"
    DESCRIPTION "Initial revision."
    ::= { enterprises 18070 2 9 2 }

String ::= TEXTUAL-CONVENTION
    DISPLAY-HINT "1t"
    STATUS       current
    DESCRIPTION  "xs:string"
    SYNTAX       OCTET STRING

Severity ::= TEXTUAL-CONVENTION
    STATUS      current
    DESCRIPTION ""
    SYNTAX      INTEGER { critical(1), major(2), minor(3), not-alarmed(4), not-reported(5) }

ConditionCode ::= TEXTUAL-CONVENTION
    STATUS      current
    DESCRIPTION ""
    SYNTAX      INTEGER { eqptMiss(1),
                          eqptUnkn(2),
                          eqptMism(3),
                          eqptFail(4),
                          eqptDgrd(5),
                          eqptComm(6),
                          upgr(7),
                          lpbk(8),
                          los(9),
                          lof(10),
                          loSync(11),
                          lola(12),             --Future Support
                          lom(13),
                          tim(14),
                          sd(15),
                          bdi(16),
                          pyldMism(17),
                          odtgMism(18),         --Future Support
                          ais-l(19),
                          ms-ais(20),
                          otu-ais(21),          --Future Support
                          odu-ais(22),
                          lck(23),
                          oci(24),
                          highBer(25),
                          lf(26),
                          rf(27),
                          rdi-l(28),
                          ms-rdi(29),
                          oprHighTh(30),
                          oprLowTh(31),
                          optHighTh(32),
                          optLowTh(33),
                          laserTempHighTh(34),
                          laserTempLowTh(35),
                          laserFail(36),
                          cfgUnsupp(37),        --Future Support
                          cfgFail(38),          --Future Support
                          lolightRx(39),
                          lolightTx(40),
                          feim(41),
                          feci(42),
                          contComS(43),
                          contComE(44),
                          loSpecRx(45),
                          tLossRxHt(46),
                          iaocp(47),
                          iaocm(48),
                          iaocb(49),
                          apsd(50),
                          pmi(51),
                          uneqO(52),
                          aisO(53),
                          posRx(54),
                          posTx(55),
                          obros(56),
                          chnDfc(57),
                          replUnitDegrade(58),
                          cnxMea(59),
                          cnxVldTmout(60),
                          posRxHigh(61),
                          posRxLow(62),
                          oprHighFail(63),
                          obrHt(64),
                          apr(65),
                          modTempHighTh(66),
                          modTempLowTh(67),
                          modTempShutdown(68),
                          envTempHighTh(69),
                          envTempLowTh(70),
                          envTempFail(71),
                          envVoltHighTh(72),
                          envVoltLowTh(73),
                          envVoltFail(74),
                          scmNmiDown(75),
                          scmNoNmConn(76),
                          eqptLatchOpen(77),
                          powerAbsent(78),
                          fanSpeedLowTh(79),
                          nonCoLocatedController(80),
                          preFecBerTh(81),
                          firmUpgrdReqd(82),
                          otuBerTh(83),         --Future Support
                          oduBerTh(84),         --Future Support
                          pcsBerTh(85),         --Future Support
                          berTh-s(86),          --Future Support
                          berTh-l(87),          --Future Support
                          rs-berTh(88),         --Future Support
                          ms-berTh(89),         --Future Support
                          oneCableDisconnected(90),
                          envCurrentHighTh(91),
                          envCurrentLowTh(92),
                          prbs(93),
                          forced(94),           --Future Support
                          lockout(95),
                          tLossRxLt(96),
                          omsBdi(97),
                          ochAis(98),
                          ochRdi(99),
                          ochUeq(100),
                          ochOci(101),    
                          defRDICCM(102),
                          defMACStatus(103),
                          defRemoteCCM(104),
                          defErrorCCM(105),
                          defXconCCM(106),
                          defBfdDown(107),
                          lf-tx(108),           --Future Support
                          apsData(109),
                          omsAis(110),
                          isisDbOvrld(111),     --Future Support
			              isisXDown(112),       --Future Support
			              isisAdjDown(113),     --Future Support
			              isisAdjRejected(114), --Future Support
			              rsvpAdjDown(115),     --Future Support  
                          diskHighUsage(116),
                          memHighUsage(117),
                          invUnknown(118),
                          airfilterAbsense(119),
                          tx-msais(120),
                          tx-msrdi(121),
                          tx-aisl(122),
                          tx-rdil(123),
                          tx-rf(124),
                          tx-oduAis(125),
                          tx-oduLck(126),
                          tx-oduOci(127),
                          tx-opuCsf(128),
                          firmUpgrdInProg(129),  --Future Support
                          firmUpgrdFail(130),
                          partitionFault(131),
			              oom(132),
			              lolck(133),
			              inventoryUnsupp(134)
                        }


-- Modules ------------------------------------------------------

notificationObjects OBJECT IDENTIFIER ::= { bTI7800-NOTIFICATIONS-MIB 1 }


-- Variables -----------------------------------------------------

variables OBJECT IDENTIFIER ::= { notificationObjects 1 }

entityName OBJECT-TYPE
    SYNTAX         String
    MAX-ACCESS     read-write
    STATUS         current
    DESCRIPTION    "The entityName identifies the system-unique name of the entity against which the condition is raised."
    ::= { variables 1 }

code OBJECT-TYPE
    SYNTAX         ConditionCode
    MAX-ACCESS     read-write
    STATUS         current
    DESCRIPTION    "Identifies the type of condition raised."
    ::= { variables 2 }

reportType OBJECT-TYPE
    SYNTAX         INTEGER { non-alarmed(1), alarmed(2) }
    MAX-ACCESS     read-write
    STATUS         current
    DESCRIPTION    "If set to non-alarmed, the list entry is a non-alarmed condition. If set to alarmed, the entry is an alarmed condition."
    ::= { variables 3 }

timeStamp OBJECT-TYPE
    SYNTAX         DateAndTime
    MAX-ACCESS     read-write
    STATUS         current
    DESCRIPTION    "The date and time at which the condition became active."
    ::= { variables 4 }

severity OBJECT-TYPE
    SYNTAX         Severity
    MAX-ACCESS     read-write
    STATUS         current
    DESCRIPTION    "The severity level of the condition."
    ::= { variables 5 }

serviceAffecting OBJECT-TYPE
    SYNTAX         TruthValue
    MAX-ACCESS     read-write
    STATUS         current
    DESCRIPTION    "If true, the condition is known to disrupt the normal service provided by the entity."
    ::= { variables 6 }

description OBJECT-TYPE
    SYNTAX         String
    MAX-ACCESS     read-write
    STATUS         current
    DESCRIPTION    "Provides a description of the condition raised that may include context specific information."
    ::= { variables 7 }


-- Notifications ----------------------------------------------------

notifications OBJECT IDENTIFIER ::= { notificationObjects 2 }
traps         OBJECT IDENTIFIER ::= { notifications 1 }

-- eqptMiss ----------------------------------------------------

eqptMissRaise NOTIFICATION-TYPE
    OBJECTS { entityName, code, reportType, timeStamp, severity, serviceAffecting, description }
    STATUS  current
    DESCRIPTION
            "Equipment Missing Raise"
    ::= { traps 1 }

eqptMissClear NOTIFICATION-TYPE
    OBJECTS { entityName, code, reportType, timeStamp, severity, serviceAffecting, description }
    STATUS  current
    DESCRIPTION
            "Equipment Missing Clear"
    ::= { traps 2 }

-- eqptUnkn ----------------------------------------------------

eqptUnknRaise NOTIFICATION-TYPE
    OBJECTS { entityName, code, reportType, timeStamp, severity, serviceAffecting, description }
    STATUS  current
    DESCRIPTION
            "Equipment Unknown Raise"
    ::= { traps 3 }

eqptUnknClear NOTIFICATION-TYPE
    OBJECTS { entityName, code, reportType, timeStamp, severity, serviceAffecting, description }
    STATUS  current
    DESCRIPTION
            "Equipment Unknown Clear"
    ::= { traps 4 }

-- eqptMism ----------------------------------------------------

eqptMismRaise NOTIFICATION-TYPE
    OBJECTS { entityName, code, reportType, timeStamp, severity, serviceAffecting, description }
    STATUS  current
    DESCRIPTION
            "Equipment Mismatch Raise"
    ::= { traps 5 }

eqptMismClear NOTIFICATION-TYPE
    OBJECTS { entityName, code, reportType, timeStamp, severity, serviceAffecting, description }
    STATUS  current
    DESCRIPTION
            "Equipment Mismatch Clear"
    ::= { traps 6 }

-- eqptFail ----------------------------------------------------

eqptFailRaise NOTIFICATION-TYPE
    OBJECTS { entityName, code, reportType, timeStamp, severity, serviceAffecting, description }
    STATUS  current
    DESCRIPTION
            "Equipment Failed Raise"
    ::= { traps 7 }

eqptFailClear NOTIFICATION-TYPE
    OBJECTS { entityName, code, reportType, timeStamp, severity, serviceAffecting, description }
    STATUS  current
    DESCRIPTION
            "Equipment Failed Clear"
    ::= { traps 8 }

-- eqptDgrd ----------------------------------------------------

eqptDgrdRaise NOTIFICATION-TYPE
    OBJECTS { entityName, code, reportType, timeStamp, severity, serviceAffecting, description }
    STATUS  current
    DESCRIPTION
            "Equipment Degrade Raise"
    ::= { traps 9 }

eqptDgrdClear NOTIFICATION-TYPE
    OBJECTS { entityName, code, reportType, timeStamp, severity, serviceAffecting, description }
    STATUS  current
    DESCRIPTION
            "Equipment Degrade Clear"
    ::= { traps 10 }

-- eqptComm ----------------------------------------------------

eqptCommRaise NOTIFICATION-TYPE
    OBJECTS { entityName, code, reportType, timeStamp, severity, serviceAffecting, description }
    STATUS  current
    DESCRIPTION
            "Equipment Comms Raise"
    ::= { traps 11 }

eqptCommClear NOTIFICATION-TYPE
    OBJECTS { entityName, code, reportType, timeStamp, severity, serviceAffecting, description }
    STATUS  current
    DESCRIPTION
            "Equipment Comms Clear"
    ::= { traps 12 }

-- upgr----------------------------------------------------

upgrRaise NOTIFICATION-TYPE
    OBJECTS { entityName, code, reportType, timeStamp, severity, serviceAffecting, description }
    STATUS  current
    DESCRIPTION
            "Upgrade Raise"
    ::= { traps 13 }

upgrClear NOTIFICATION-TYPE
    OBJECTS { entityName, code, reportType, timeStamp, severity, serviceAffecting, description }
    STATUS  current
    DESCRIPTION
            "Upgrade Clear"
    ::= { traps 14 }

-- lpbk ----------------------------------------------------

lpbkRaise NOTIFICATION-TYPE
    OBJECTS { entityName, code, reportType, timeStamp, severity, serviceAffecting, description }
    STATUS  current
    DESCRIPTION
            "Loopback Operated Raise"
    ::= { traps 15 }

lpbkClear NOTIFICATION-TYPE
    OBJECTS { entityName, code, reportType, timeStamp, severity, serviceAffecting, description }
    STATUS  current
    DESCRIPTION
            "Loopback Operated Clear"
    ::= { traps 16 }

-- los ----------------------------------------------------

losRaise NOTIFICATION-TYPE
    OBJECTS { entityName, code, reportType, timeStamp, severity, serviceAffecting, description }
    STATUS  current
    DESCRIPTION
            "Loss of Signal Raise"
    ::= { traps 17 }

losClear NOTIFICATION-TYPE
    OBJECTS { entityName, code, reportType, timeStamp, severity, serviceAffecting, description }
    STATUS  current
    DESCRIPTION
            "Loss of Signal Clear"
    ::= { traps 18 }

-- lof ----------------------------------------------------

lofRaise NOTIFICATION-TYPE
    OBJECTS { entityName, code, reportType, timeStamp, severity, serviceAffecting, description }
    STATUS  current
    DESCRIPTION
            "Loss of Frame Raise"
    ::= { traps 19 }

lofClear NOTIFICATION-TYPE
    OBJECTS { entityName, code, reportType, timeStamp, severity, serviceAffecting, description }
    STATUS  current
    DESCRIPTION
            "Loss of Frame Clear"
    ::= { traps 20 }

-- loSync ----------------------------------------------------

loSyncRaise NOTIFICATION-TYPE
    OBJECTS { entityName, code, reportType, timeStamp, severity, serviceAffecting, description }
    STATUS  current
    DESCRIPTION
            "Loss of Synchronization Raise"
    ::= { traps 21 }

loSyncClear NOTIFICATION-TYPE
    OBJECTS { entityName, code, reportType, timeStamp, severity, serviceAffecting, description }
    STATUS  current
    DESCRIPTION
            "Loss of Synchronization Clear"
    ::= { traps 22 }

-- lola ----------------------------------------------------

lolaRaise NOTIFICATION-TYPE
    OBJECTS { entityName, code, reportType, timeStamp, severity, serviceAffecting, description }
    STATUS  current
    DESCRIPTION
            "Loss of Lane Alignment Raise"
    ::= { traps 23 }

lolaClear NOTIFICATION-TYPE
    OBJECTS { entityName, code, reportType, timeStamp, severity, serviceAffecting, description }
    STATUS  current
    DESCRIPTION
            "Loss of Lane Alignment Clear"
    ::= { traps 24 }

-- lom ----------------------------------------------------

lomRaise NOTIFICATION-TYPE
    OBJECTS { entityName, code, reportType, timeStamp, severity, serviceAffecting, description }
    STATUS  current
    DESCRIPTION
            "Loss of Multiframe Raise"
    ::= { traps 25 }

lomClear NOTIFICATION-TYPE
    OBJECTS { entityName, code, reportType, timeStamp, severity, serviceAffecting, description }
    STATUS  current
    DESCRIPTION
            "Loss of Multiframe Clear"
    ::= { traps 26 }

-- tim ----------------------------------------------------

timRaise NOTIFICATION-TYPE
    OBJECTS { entityName, code, reportType, timeStamp, severity, serviceAffecting, description }
    STATUS  current
    DESCRIPTION
            "Trace Identifier Mismatch Raise"
    ::= { traps 27 }

timClear NOTIFICATION-TYPE
    OBJECTS { entityName, code, reportType, timeStamp, severity, serviceAffecting, description }
    STATUS  current
    DESCRIPTION
            "Trace Identifier Mismatch Clear"
    ::= { traps 28 }

-- sd ----------------------------------------------------

sdRaise NOTIFICATION-TYPE
    OBJECTS { entityName, code, reportType, timeStamp, severity, serviceAffecting, description }
    STATUS  current
    DESCRIPTION
            "Signal Degrade Raise"
    ::= { traps 29 }

sdClear NOTIFICATION-TYPE
    OBJECTS { entityName, code, reportType, timeStamp, severity, serviceAffecting, description }
    STATUS  current
    DESCRIPTION
            "Signal Degrade Clear"
    ::= { traps 30 }

-- bdi ----------------------------------------------------

bdiRaise NOTIFICATION-TYPE
    OBJECTS { entityName, code, reportType, timeStamp, severity, serviceAffecting, description }
    STATUS  current
    DESCRIPTION
            "Backward Defect Indication Raise"
    ::= { traps 31 }

bdiClear NOTIFICATION-TYPE
    OBJECTS { entityName, code, reportType, timeStamp, severity, serviceAffecting, description }
    STATUS  current
    DESCRIPTION
            "Backward Defect Indication Clear"
    ::= { traps 32 }

-- pyldMism ----------------------------------------------------

pyldMismRaise NOTIFICATION-TYPE
    OBJECTS { entityName, code, reportType, timeStamp, severity, serviceAffecting, description }
    STATUS  current
    DESCRIPTION
            "Payload Mismatch Raise"
    ::= { traps 33 }

pyldMismClear NOTIFICATION-TYPE
    OBJECTS { entityName, code, reportType, timeStamp, severity, serviceAffecting, description }
    STATUS  current
    DESCRIPTION
            "Payload Mismatch Clear"
    ::= { traps 34 }

-- odtgMism ----------------------------------------------------

odtgMismRaise NOTIFICATION-TYPE
    OBJECTS { entityName, code, reportType, timeStamp, severity, serviceAffecting, description }
    STATUS  current
    DESCRIPTION
            "ODTG Mismatch Raise"
    ::= { traps 35 }

odtgMismClear NOTIFICATION-TYPE
    OBJECTS { entityName, code, reportType, timeStamp, severity, serviceAffecting, description }
    STATUS  current
    DESCRIPTION
            "ODTG Mismatch Clear"
    ::= { traps 36 }

-- ais-l ----------------------------------------------------

ais-lRaise NOTIFICATION-TYPE
    OBJECTS { entityName, code, reportType, timeStamp, severity, serviceAffecting, description }
    STATUS  current
    DESCRIPTION
            "Alarm Indication Signal, Line Raise"
    ::= { traps 37 }

ais-lClear NOTIFICATION-TYPE
    OBJECTS { entityName, code, reportType, timeStamp, severity, serviceAffecting, description }
    STATUS  current
    DESCRIPTION
            "Alarm Indication Signal, Line Clear"
    ::= { traps 38 }

-- ms-ais ----------------------------------------------------

ms-aisRaise NOTIFICATION-TYPE
    OBJECTS { entityName, code, reportType, timeStamp, severity, serviceAffecting, description }
    STATUS  current
    DESCRIPTION
            "Multiplex Section Alarm Indication Signal Raise"
    ::= { traps 39 }

ms-aisClear NOTIFICATION-TYPE
    OBJECTS { entityName, code, reportType, timeStamp, severity, serviceAffecting, description }
    STATUS  current
    DESCRIPTION
            "Multiplex Section Alarm Indication Signal Clear"
    ::= { traps 40 }

-- otu-ais ----------------------------------------------------

otu-aisRaise NOTIFICATION-TYPE
    OBJECTS { entityName, code, reportType, timeStamp, severity, serviceAffecting, description }
    STATUS  current
    DESCRIPTION
            "OTU Alarm Indication Signal Raise"
    ::= { traps 41 }

otu-aisClear NOTIFICATION-TYPE
    OBJECTS { entityName, code, reportType, timeStamp, severity, serviceAffecting, description }
    STATUS  current
    DESCRIPTION
            "OTU Alarm Indication Signal Clear"
    ::= { traps 42 }

-- odu-ais ----------------------------------------------------

odu-aisRaise NOTIFICATION-TYPE
    OBJECTS { entityName, code, reportType, timeStamp, severity, serviceAffecting, description }
    STATUS  current
    DESCRIPTION
            "ODU Alarm Indication Signal Raise"
    ::= { traps 43 }

odu-aisClear NOTIFICATION-TYPE
    OBJECTS { entityName, code, reportType, timeStamp, severity, serviceAffecting, description }
    STATUS  current
    DESCRIPTION
            "ODU Alarm Indication Signal Clear"
    ::= { traps 44 }

-- lck ----------------------------------------------------

lckRaise NOTIFICATION-TYPE
    OBJECTS { entityName, code, reportType, timeStamp, severity, serviceAffecting, description }
    STATUS  current
    DESCRIPTION
            "ODU Locked Raise"
    ::= { traps 45 }

lckClear NOTIFICATION-TYPE
    OBJECTS { entityName, code, reportType, timeStamp, severity, serviceAffecting, description }
    STATUS  current
    DESCRIPTION
            "ODU Locked Clear"
    ::= { traps 46 }

-- oci ----------------------------------------------------

ociRaise NOTIFICATION-TYPE
    OBJECTS { entityName, code, reportType, timeStamp, severity, serviceAffecting, description }
    STATUS  current
    DESCRIPTION
            "ODU Open Connection Indication Raise"
    ::= { traps 47 }

ociClear NOTIFICATION-TYPE
    OBJECTS { entityName, code, reportType, timeStamp, severity, serviceAffecting, description }
    STATUS  current
    DESCRIPTION
            "ODU Open Connection Indication Clear"
    ::= { traps 48 }

-- highBER ----------------------------------------------------

highBerRaise NOTIFICATION-TYPE
    OBJECTS { entityName, code, reportType, timeStamp, severity, serviceAffecting, description }
    STATUS  current
    DESCRIPTION
            "High Bite Error Ratio Raise"
    ::= { traps 49 }

highBerClear NOTIFICATION-TYPE
    OBJECTS { entityName, code, reportType, timeStamp, severity, serviceAffecting, description }
    STATUS  current
    DESCRIPTION
            "High Bit Error Ratio Clear"
    ::= { traps 50 }

-- lf ----------------------------------------------------

lfRaise NOTIFICATION-TYPE
    OBJECTS { entityName, code, reportType, timeStamp, severity, serviceAffecting, description }
    STATUS  current
    DESCRIPTION
            "Local Fault Raise"
    ::= { traps 51 }

lfClear NOTIFICATION-TYPE
    OBJECTS { entityName, code, reportType, timeStamp, severity, serviceAffecting, description }
    STATUS  current
    DESCRIPTION
            "Local Fault Clear"
    ::= { traps 52 }

-- rf ----------------------------------------------------

rfRaise NOTIFICATION-TYPE
    OBJECTS { entityName, code, reportType, timeStamp, severity, serviceAffecting, description }
    STATUS  current
    DESCRIPTION
            "Remote Fault Raise"
    ::= { traps 53 }

rfClear NOTIFICATION-TYPE
    OBJECTS { entityName, code, reportType, timeStamp, severity, serviceAffecting, description }
    STATUS  current
    DESCRIPTION
            "Remote Fault Clear"
    ::= { traps 54 }

-- rdi-l ----------------------------------------------------

rdi-lRaise NOTIFICATION-TYPE
    OBJECTS { entityName, code, reportType, timeStamp, severity, serviceAffecting, description }
    STATUS  current
    DESCRIPTION
            "Remote Defect Indication, Line Raise"
    ::= { traps 55 }

rdi-lClear NOTIFICATION-TYPE
    OBJECTS { entityName, code, reportType, timeStamp, severity, serviceAffecting, description }
    STATUS  current
    DESCRIPTION
            "Remote Defect Indication, Line Clear"
    ::= { traps 56 }

-- ms-rdi ----------------------------------------------------

ms-rdiRaise NOTIFICATION-TYPE
    OBJECTS { entityName, code, reportType, timeStamp, severity, serviceAffecting, description }
    STATUS  current
    DESCRIPTION
            "Multiplex Section Remote Defect Indication Raise"
    ::= { traps 57 }

ms-rdiClear NOTIFICATION-TYPE
    OBJECTS { entityName, code, reportType, timeStamp, severity, serviceAffecting, description }
    STATUS  current
    DESCRIPTION
            "Multiplex Section Remote Defect Indication Clear"
    ::= { traps 58 }

-- oprHighTh ----------------------------------------------------

oprHighThRaise NOTIFICATION-TYPE
    OBJECTS { entityName, code, reportType, timeStamp, severity, serviceAffecting, description }
    STATUS  current
    DESCRIPTION
            "Optical Power Rx High Threshold Raise"
    ::= { traps 59 }

oprHighThClear NOTIFICATION-TYPE
    OBJECTS { entityName, code, reportType, timeStamp, severity, serviceAffecting, description }
    STATUS  current
    DESCRIPTION
            "Optical Power Rx High Threshold Clear"
    ::= { traps 60 }

-- oprLowTh ----------------------------------------------------

oprLowThRaise NOTIFICATION-TYPE
    OBJECTS { entityName, code, reportType, timeStamp, severity, serviceAffecting, description }
    STATUS  current
    DESCRIPTION
            "Optical Power Rx Low Threshold Raise"
    ::= { traps 61 }

oprLowThClear NOTIFICATION-TYPE
    OBJECTS { entityName, code, reportType, timeStamp, severity, serviceAffecting, description }
    STATUS  current
    DESCRIPTION
            "Optical Power Rx Low Threshold Clear"
    ::= { traps 62 }

-- optHighTh ----------------------------------------------------

optHighThRaise NOTIFICATION-TYPE
    OBJECTS { entityName, code, reportType, timeStamp, severity, serviceAffecting, description }
    STATUS  current
    DESCRIPTION
            "Optical Power Tx High Threshold Raise"
    ::= { traps 63 }

optHighThClear NOTIFICATION-TYPE
    OBJECTS { entityName, code, reportType, timeStamp, severity, serviceAffecting, description }
    STATUS  current
    DESCRIPTION
            "Optical Power Tx High Threshold Clear"
    ::= { traps 64 }

-- optLowTh ----------------------------------------------------

optLowThRaise NOTIFICATION-TYPE
    OBJECTS { entityName, code, reportType, timeStamp, severity, serviceAffecting, description }
    STATUS  current
    DESCRIPTION
            "Optical Power Tx Low Threshold Raise"
    ::= { traps 65 }

optLowThClear NOTIFICATION-TYPE
    OBJECTS { entityName, code, reportType, timeStamp, severity, serviceAffecting, description }
    STATUS  current
    DESCRIPTION
            "Optical Power Tx Low Threshold Clear"
    ::= { traps 66 }

-- laserTempHighTh ----------------------------------------------------

laserTempHighThRaise NOTIFICATION-TYPE
    OBJECTS { entityName, code, reportType, timeStamp, severity, serviceAffecting, description }
    STATUS  current
    DESCRIPTION
            "Tx Laser Above High Temperature Threshold Raise"
    ::= { traps 67 }

laserTempHighThClear NOTIFICATION-TYPE
    OBJECTS { entityName, code, reportType, timeStamp, severity, serviceAffecting, description }
    STATUS  current
    DESCRIPTION
            "Tx Laser Above High Temperature Threshold Clear"
    ::= { traps 68 }

-- laserTempLowTh ----------------------------------------------------

laserTempLowThRaise NOTIFICATION-TYPE
    OBJECTS { entityName, code, reportType, timeStamp, severity, serviceAffecting, description }
    STATUS  current
    DESCRIPTION
            "Tx Laser Below Low Temperature Threshold Raise"
    ::= { traps 69 }

laserTempLowThClear NOTIFICATION-TYPE
    OBJECTS { entityName, code, reportType, timeStamp, severity, serviceAffecting, description }
    STATUS  current
    DESCRIPTION
            "Tx Laser Below Low Temperature Threshold Clear"
    ::= { traps 70 }

-- laserFail ----------------------------------------------------

laserFailRaise NOTIFICATION-TYPE
    OBJECTS { entityName, code, reportType, timeStamp, severity, serviceAffecting, description }
    STATUS  current
    DESCRIPTION
            "Tx Laser Fail Raise"
    ::= { traps 71 }

laserFailClear NOTIFICATION-TYPE
    OBJECTS { entityName, code, reportType, timeStamp, severity, serviceAffecting, description }
    STATUS  current
    DESCRIPTION
            "Tx Laser Fail Clear"
    ::= { traps 72 }

-- cfgUnsupp----------------------------------------------------

cfgUnsuppRaise NOTIFICATION-TYPE
    OBJECTS { entityName, code, reportType, timeStamp, severity, serviceAffecting, description }
    STATUS  current
    DESCRIPTION
            "Configuration Unsupported Raise"
    ::= { traps 73 }

cfgUnsuppClear NOTIFICATION-TYPE
    OBJECTS { entityName, code, reportType, timeStamp, severity, serviceAffecting, description }
    STATUS  current
    DESCRIPTION
            "Configuration Unsupported Clear"
    ::= { traps 74 }

-- cfgFail----------------------------------------------------

cfgFailRaise NOTIFICATION-TYPE
    OBJECTS { entityName, code, reportType, timeStamp, severity, serviceAffecting, description }
    STATUS  current
    DESCRIPTION
            "Configuration Failure Raise"
    ::= { traps 75 }

cfgFailClear NOTIFICATION-TYPE
    OBJECTS { entityName, code, reportType, timeStamp, severity, serviceAffecting, description }
    STATUS  current
    DESCRIPTION
            "Configuration Failure Clear"
    ::= { traps 76 }

-- lolightRx-----------------------------------------------------

lolightRxRaise NOTIFICATION-TYPE
    OBJECTS { entityName, code, reportType, timeStamp, severity, serviceAffecting, description }
    STATUS  current
    DESCRIPTION
            "Loss of light, receive Raise"
    ::= { traps 77 }

lolightRxClear NOTIFICATION-TYPE
    OBJECTS { entityName, code, reportType, timeStamp, severity, serviceAffecting, description }
    STATUS  current
    DESCRIPTION
            "Loss of light, receive Clear"
    ::= { traps 78 }

-- lolightTx-----------------------------------------------------

lolightTxRaise NOTIFICATION-TYPE
    OBJECTS { entityName, code, reportType, timeStamp, severity, serviceAffecting, description }
    STATUS  current
    DESCRIPTION
            "Loss of light, transmit Raise"
    ::= { traps 79 }

lolightTxClear NOTIFICATION-TYPE
    OBJECTS { entityName, code, reportType, timeStamp, severity, serviceAffecting, description }
    STATUS  current
    DESCRIPTION
            "Loss of light, transmit Clear"
    ::= { traps 80 }

-- feim-----------------------------------------------------

feimRaise NOTIFICATION-TYPE
    OBJECTS { entityName, code, reportType, timeStamp, severity, serviceAffecting, description }
    STATUS  current
    DESCRIPTION
            "Far-end node identification mismatch Raise"
    ::= { traps 81 }

feimClear NOTIFICATION-TYPE
    OBJECTS { entityName, code, reportType, timeStamp, severity, serviceAffecting, description }
    STATUS  current
    DESCRIPTION
            "Far-end node identification mismatch Clear"
    ::= { traps 82 }

-- feci-----------------------------------------------------

feciRaise NOTIFICATION-TYPE
    OBJECTS { entityName, code, reportType, timeStamp, severity, serviceAffecting, description }
    STATUS  current
    DESCRIPTION
            "Far-end node configuration mismatch Raise"
    ::= { traps 83 }

feciClear NOTIFICATION-TYPE
    OBJECTS { entityName, code, reportType, timeStamp, severity, serviceAffecting, description }
    STATUS  current
    DESCRIPTION
            "Far-end node configuration mismatch Clear"
    ::= { traps 84 }

-- contComS-----------------------------------------------------

contComSRaise NOTIFICATION-TYPE
    OBJECTS { entityName, code, reportType, timeStamp, severity, serviceAffecting, description }
    STATUS  current
    DESCRIPTION
            "Control comms failure, span section Raise"
    ::= { traps 85 }

contComSClear NOTIFICATION-TYPE
    OBJECTS { entityName, code, reportType, timeStamp, severity, serviceAffecting, description }
    STATUS  current
    DESCRIPTION
            "Control comms failure, span section Clear"
    ::= { traps 86 }

-- contComE-----------------------------------------------------

contComERaise NOTIFICATION-TYPE
    OBJECTS { entityName, code, reportType, timeStamp, severity, serviceAffecting, description }
    STATUS  current
    DESCRIPTION
            "Control comms failure, eqlz. section Raise"
    ::= { traps 87 }

contComEClear NOTIFICATION-TYPE
    OBJECTS { entityName, code, reportType, timeStamp, severity, serviceAffecting, description }
    STATUS  current
    DESCRIPTION
            "Control comms failure, eqlz. section Clear"
    ::= { traps 88 }

-- loSpecRx-----------------------------------------------------

loSpecRxRaise NOTIFICATION-TYPE
    OBJECTS { entityName, code, reportType, timeStamp, severity, serviceAffecting, description }
    STATUS  current
    DESCRIPTION
            "Loss out of specification, receive Raise"
    ::= { traps 89 }

loSpecRxClear NOTIFICATION-TYPE
    OBJECTS { entityName, code, reportType, timeStamp, severity, serviceAffecting, description }
    STATUS  current
    DESCRIPTION
            "Loss out of specification, receive Clear"
    ::= { traps 90 }

-- tLossRxHt-----------------------------------------------------

tLossRxHtRaise NOTIFICATION-TYPE
    OBJECTS { entityName, code, reportType, timeStamp, severity, serviceAffecting, description }
    STATUS  current
    DESCRIPTION
            "Loss high threshold exceeded, receive Raise"
    ::= { traps 91 }

tLossRxHtClear NOTIFICATION-TYPE
    OBJECTS { entityName, code, reportType, timeStamp, severity, serviceAffecting, description }
    STATUS  current
    DESCRIPTION
            "Loss high threshold exceeded, receive Clear"
    ::= { traps 92 }

-- iaocp-----------------------------------------------------

iaocpRaise NOTIFICATION-TYPE
    OBJECTS { entityName, code, reportType, timeStamp, severity, serviceAffecting, description }
    STATUS  current
    DESCRIPTION
            "Invalid pre-amplifier operating cfg Raise"
    ::= { traps 93 }

iaocpClear NOTIFICATION-TYPE
    OBJECTS { entityName, code, reportType, timeStamp, severity, serviceAffecting, description }
    STATUS  current
    DESCRIPTION
            "Invalid pre-amplifier operating cfg Clear"
    ::= { traps 94 }

-- iaocm-----------------------------------------------------

iaocmRaise NOTIFICATION-TYPE
    OBJECTS { entityName, code, reportType, timeStamp, severity, serviceAffecting, description }
    STATUS  current
    DESCRIPTION
            "Invalid mid-amplifier operating cfg Raise"
    ::= { traps 95 }

iaocmClear NOTIFICATION-TYPE
    OBJECTS { entityName, code, reportType, timeStamp, severity, serviceAffecting, description }
    STATUS  current
    DESCRIPTION
            "Invalid mid-amplifier operating cfg Clear"
    ::= { traps 96 }

-- iaocb-----------------------------------------------------

iaocbRaise NOTIFICATION-TYPE
    OBJECTS { entityName, code, reportType, timeStamp, severity, serviceAffecting, description }
    STATUS  current
    DESCRIPTION
            "Invalid boost-amp. operating cfg Raise"
    ::= { traps 97 }

iaocbClear NOTIFICATION-TYPE
    OBJECTS { entityName, code, reportType, timeStamp, severity, serviceAffecting, description }
    STATUS  current
    DESCRIPTION
            "Invalid boost-amp. operating cfg Clear"
    ::= { traps 98 }

-- apsd-----------------------------------------------------

apsdRaise NOTIFICATION-TYPE
    OBJECTS { entityName, code, reportType, timeStamp, severity, serviceAffecting, description }
    STATUS  current
    DESCRIPTION
            "Automatic power shutdown Raise"
    ::= { traps 99 }

apsdClear NOTIFICATION-TYPE
    OBJECTS { entityName, code, reportType, timeStamp, severity, serviceAffecting, description }
    STATUS  current
    DESCRIPTION
            "Automatic power shutdown Clear"
    ::= { traps 100 }

-- pmi-----------------------------------------------------

pmiRaise NOTIFICATION-TYPE
    OBJECTS { entityName, code, reportType, timeStamp, severity, serviceAffecting, description }
    STATUS  current
    DESCRIPTION
            "Payload missing indication Raise"
    ::= { traps 101 }

pmiClear NOTIFICATION-TYPE
    OBJECTS { entityName, code, reportType, timeStamp, severity, serviceAffecting, description }
    STATUS  current
    DESCRIPTION
            "Payload missing indication Clear"
    ::= { traps 102 }

-- uneqO-----------------------------------------------------

uneqORaise NOTIFICATION-TYPE
    OBJECTS { entityName, code, reportType, timeStamp, severity, serviceAffecting, description }
    STATUS  current
    DESCRIPTION
            "Optical channel unequipped Raise"
    ::= { traps 103 }

uneqOClear NOTIFICATION-TYPE
    OBJECTS { entityName, code, reportType, timeStamp, severity, serviceAffecting, description }
    STATUS  current
    DESCRIPTION
            "Optical channel unequipped Clear"
    ::= { traps 104 }

-- aisO-----------------------------------------------------

aisORaise NOTIFICATION-TYPE
    OBJECTS { entityName, code, reportType, timeStamp, severity, serviceAffecting, description }
    STATUS  current
    DESCRIPTION
            "Alarm indication signal, optical Raise"
    ::= { traps 105 }

aisOClear NOTIFICATION-TYPE
    OBJECTS { entityName, code, reportType, timeStamp, severity, serviceAffecting, description }
    STATUS  current
    DESCRIPTION
            "Alarm indication signal, optical Clear"
    ::= { traps 106 }

-- posRx-----------------------------------------------------

posRxRaise NOTIFICATION-TYPE
    OBJECTS { entityName, code, reportType, timeStamp, severity, serviceAffecting, description }
    STATUS  current
    DESCRIPTION
            "Power out of specification, receive Raise"
    ::= { traps 107 }

posRxClear NOTIFICATION-TYPE
    OBJECTS { entityName, code, reportType, timeStamp, severity, serviceAffecting, description }
    STATUS  current
    DESCRIPTION
            "Power out of specification, receive Clear"
    ::= { traps 108 }

-- posTx-----------------------------------------------------

posTxRaise NOTIFICATION-TYPE
    OBJECTS { entityName, code, reportType, timeStamp, severity, serviceAffecting, description }
    STATUS  current
    DESCRIPTION
            "Power out of specification, transmit Raise"
    ::= { traps 109 }

posTxClear NOTIFICATION-TYPE
    OBJECTS { entityName, code, reportType, timeStamp, severity, serviceAffecting, description }
    STATUS  current
    DESCRIPTION
            "Power out of specification, transmit Clear"
    ::= { traps 110 }

-- obros-----------------------------------------------------

obrosRaise NOTIFICATION-TYPE
    OBJECTS { entityName, code, reportType, timeStamp, severity, serviceAffecting, description }
    STATUS  current
    DESCRIPTION
            "Optical back reflection out of spec Raise"
    ::= { traps 111 }

obrosClear NOTIFICATION-TYPE
    OBJECTS { entityName, code, reportType, timeStamp, severity, serviceAffecting, description }
    STATUS  current
    DESCRIPTION
            "Optical back reflection out of spec Clear"
    ::= { traps 112 }

-- chnDfc-----------------------------------------------------

chnDfcRaise NOTIFICATION-TYPE
    OBJECTS { entityName, code, reportType, timeStamp, severity, serviceAffecting, description }
    STATUS  current
    DESCRIPTION
            "Channel count deficiency Raise"
    ::= { traps 113 }

chnDfcClear NOTIFICATION-TYPE
    OBJECTS { entityName, code, reportType, timeStamp, severity, serviceAffecting, description }
    STATUS  current
    DESCRIPTION
            "Channel count deficiency Clear"
    ::= { traps 114 }

-- replUnitDegrade-----------------------------------------------------

replUnitDegradeRaise NOTIFICATION-TYPE
    OBJECTS { entityName, code, reportType, timeStamp, severity, serviceAffecting, description }
    STATUS  current
    DESCRIPTION
            "Replaceable unit degrade Raise"
    ::= { traps 115 }

replUnitDegradeClear NOTIFICATION-TYPE
    OBJECTS { entityName, code, reportType, timeStamp, severity, serviceAffecting, description }
    STATUS  current
    DESCRIPTION
            "Replaceable unit degrade Clear"
    ::= { traps 116 }

-- cnxMea-----------------------------------------------------

cnxMeaRaise NOTIFICATION-TYPE
    OBJECTS { entityName, code, reportType, timeStamp, severity, serviceAffecting, description }
    STATUS  current
    DESCRIPTION
            "Connection Mismatch Raise"
    ::= { traps 117 }

cnxMeaClear NOTIFICATION-TYPE
    OBJECTS { entityName, code, reportType, timeStamp, severity, serviceAffecting, description }
    STATUS  current
    DESCRIPTION
            "Connection Mismatch Clear"
    ::= { traps 118 }

-- cnxVldTmout-----------------------------------------------------

cnxVldTmoutRaise NOTIFICATION-TYPE
    OBJECTS { entityName, code, reportType, timeStamp, severity, serviceAffecting, description }
    STATUS  current
    DESCRIPTION
            "Connection Validation Timeout Raise"
    ::= { traps 119 }

cnxVldTmoutClear NOTIFICATION-TYPE
    OBJECTS { entityName, code, reportType, timeStamp, severity, serviceAffecting, description }
    STATUS  current
    DESCRIPTION
            "Connection Validation Timeout Clear"
    ::= { traps 120 }

-- posRxHigh-----------------------------------------------------

posRxHighRaise NOTIFICATION-TYPE
    OBJECTS { entityName, code, reportType, timeStamp, severity, serviceAffecting, description }
    STATUS  current
    DESCRIPTION
            "Receive power out of spec, High Raise"
    ::= { traps 121 }

posRxHighClear NOTIFICATION-TYPE
    OBJECTS { entityName, code, reportType, timeStamp, severity, serviceAffecting, description }
    STATUS  current
    DESCRIPTION
            "Receive power out of spec, High Clear"
    ::= { traps 122 }

-- posRxLow-----------------------------------------------------

posRxLowRaise NOTIFICATION-TYPE
    OBJECTS { entityName, code, reportType, timeStamp, severity, serviceAffecting, description }
    STATUS  current
    DESCRIPTION
            "Receive power out of spec, Low Raise"
    ::= { traps 123 }

posRxLowClear NOTIFICATION-TYPE
    OBJECTS { entityName, code, reportType, timeStamp, severity, serviceAffecting, description }
    STATUS  current
    DESCRIPTION
            "Receive power out of spec, Low Clear"
    ::= { traps 124 }

-- oprHighFail-----------------------------------------------------

oprHighFailRaise NOTIFICATION-TYPE
    OBJECTS { entityName, code, reportType, timeStamp, severity, serviceAffecting, description }
    STATUS  current
    DESCRIPTION
            "Optical Power Received High Fail Raise"
    ::= { traps 125 }

oprHighFailClear NOTIFICATION-TYPE
    OBJECTS { entityName, code, reportType, timeStamp, severity, serviceAffecting, description }
    STATUS  current
    DESCRIPTION
            "Optical Power Received High Fail Clear"
    ::= { traps 126 }

-- obrHt-----------------------------------------------------

obrHtRaise NOTIFICATION-TYPE
    OBJECTS { entityName, code, reportType, timeStamp, severity, serviceAffecting, description }
    STATUS  current
    DESCRIPTION
            "Optical back reflection high threshold exceeded Raise"
    ::= { traps 127 }

obrHtClear NOTIFICATION-TYPE
    OBJECTS { entityName, code, reportType, timeStamp, severity, serviceAffecting, description }
    STATUS  current
    DESCRIPTION
            "Optical back reflection high threshold exceeded Clear"
    ::= { traps 128 }

-- apr-----------------------------------------------------

aprRaise NOTIFICATION-TYPE
    OBJECTS { entityName, code, reportType, timeStamp, severity, serviceAffecting, description }
    STATUS  current
    DESCRIPTION
            "Automatic Power Reduction Raise"
    ::= { traps 129 }

aprClear NOTIFICATION-TYPE
    OBJECTS { entityName, code, reportType, timeStamp, severity, serviceAffecting, description }
    STATUS  current
    DESCRIPTION
            "Automatic Power Reduction Clear"
    ::= { traps 130 }

-- modTempHighTh ----------------------------------------------------

modTempHighThRaise NOTIFICATION-TYPE
    OBJECTS { entityName, code, reportType, timeStamp, severity, serviceAffecting, description }
    STATUS  current
    DESCRIPTION
            "Transceiver Module Above High Temperature Threshold Raise"
    ::= { traps 131 }

modTempHighThClear NOTIFICATION-TYPE
    OBJECTS { entityName, code, reportType, timeStamp, severity, serviceAffecting, description }
    STATUS  current
    DESCRIPTION
            "Transceiver Module Above High Temperature Threshold Clear"
    ::= { traps 132 }

-- modTempLowTh ----------------------------------------------------

modTempLowThRaise NOTIFICATION-TYPE
    OBJECTS { entityName, code, reportType, timeStamp, severity, serviceAffecting, description }
    STATUS  current
    DESCRIPTION
            "Transceiver Module Below Low Temperature Threshold Raise"
    ::= { traps 133 }

modTempLowThClear NOTIFICATION-TYPE
    OBJECTS { entityName, code, reportType, timeStamp, severity, serviceAffecting, description }
    STATUS  current
    DESCRIPTION
            "Transceiver Module Below Low Temperature Threshold Clear"
    ::= { traps 134 }

-- modTempShutdown ----------------------------------------------------

modTempShutdownRaise NOTIFICATION-TYPE
    OBJECTS { entityName, code, reportType, timeStamp, severity, serviceAffecting, description }
    STATUS  current
    DESCRIPTION
            "Transceiver Module Temperature Shutdown Raise"
    ::= { traps 135 }

modTempShutdownClear NOTIFICATION-TYPE
    OBJECTS { entityName, code, reportType, timeStamp, severity, serviceAffecting, description }
    STATUS  current
    DESCRIPTION
            "Transceiver Module Temperature Shutdown Clear"
    ::= { traps 136 }

-- envTempHighTh ----------------------------------------------------

envTempHighThRaise NOTIFICATION-TYPE
    OBJECTS { entityName, code, reportType, timeStamp, severity, serviceAffecting, description }
    STATUS  current
    DESCRIPTION
            "Environment Above High Temperature Threshold Raise"
    ::= { traps 137 }

envTempHighThClear NOTIFICATION-TYPE
    OBJECTS { entityName, code, reportType, timeStamp, severity, serviceAffecting, description }
    STATUS  current
    DESCRIPTION
            "Environment Above High Temperature Threshold Clear"
    ::= { traps 138 }

-- envTempLowTh ----------------------------------------------------

envTempLowThRaise NOTIFICATION-TYPE
    OBJECTS { entityName, code, reportType, timeStamp, severity, serviceAffecting, description }
    STATUS  current
    DESCRIPTION
            "Environment Below Low Temperature Threshold Raise"
    ::= { traps 139 }

envTempLowThClear NOTIFICATION-TYPE
    OBJECTS { entityName, code, reportType, timeStamp, severity, serviceAffecting, description }
    STATUS  current
    DESCRIPTION
            "Environment Below Low Temperature Threshold Clear"
    ::= { traps 140 }

-- envTempFail ----------------------------------------------------

envTempFailRaise NOTIFICATION-TYPE
    OBJECTS { entityName, code, reportType, timeStamp, severity, serviceAffecting, description }
    STATUS  current
    DESCRIPTION
            "Environment temperature failure Raise"
    ::= { traps 141 }

envTempFailClear NOTIFICATION-TYPE
    OBJECTS { entityName, code, reportType, timeStamp, severity, serviceAffecting, description }
    STATUS  current
    DESCRIPTION
            "Environment temperature failure Clear"
    ::= { traps 142 }

-- envVoltHighTh ----------------------------------------------------

envVoltHighThRaise NOTIFICATION-TYPE
    OBJECTS { entityName, code, reportType, timeStamp, severity, serviceAffecting, description }
    STATUS  current
    DESCRIPTION
            "Environment Above High Voltage Threshold Raise"
    ::= { traps 143 }

envVoltHighThClear NOTIFICATION-TYPE
    OBJECTS { entityName, code, reportType, timeStamp, severity, serviceAffecting, description }
    STATUS  current
    DESCRIPTION
            "Environment Above High Voltage Threshold Clear"
    ::= { traps 144 }

-- envVoltLowTh ----------------------------------------------------

envVoltLowThRaise NOTIFICATION-TYPE
    OBJECTS { entityName, code, reportType, timeStamp, severity, serviceAffecting, description }
    STATUS  current
    DESCRIPTION
            "Environment Below Low Voltage Threshold Raise"
    ::= { traps 145 }

envVoltLowThClear NOTIFICATION-TYPE
    OBJECTS { entityName, code, reportType, timeStamp, severity, serviceAffecting, description }
    STATUS  current
    DESCRIPTION
            "Environment Below Low Voltage Threshold Clear"
    ::= { traps 146 }

-- envVoltFail ----------------------------------------------------

envVoltFailRaise NOTIFICATION-TYPE
    OBJECTS { entityName, code, reportType, timeStamp, severity, serviceAffecting, description }
    STATUS  current
    DESCRIPTION
            "Environment voltage failure Raise"
    ::= { traps 147 }

envVoltFailClear NOTIFICATION-TYPE
    OBJECTS { entityName, code, reportType, timeStamp, severity, serviceAffecting, description }
    STATUS  current
    DESCRIPTION
            "Environment voltage failure Clear"
    ::= { traps 148 }

-- scmNmiDown ----------------------------------------------------

scmNmiDownRaise NOTIFICATION-TYPE
    OBJECTS { entityName, code, reportType, timeStamp, severity, serviceAffecting, description }
    STATUS  current
    DESCRIPTION
            "SCM Network Management Interface down Raise"
    ::= { traps 149 }

scmNmiDownClear NOTIFICATION-TYPE
    OBJECTS { entityName, code, reportType, timeStamp, severity, serviceAffecting, description }
    STATUS  current
    DESCRIPTION
            "SCM Network Management Interface down Clear"
    ::= { traps 150 }

-- scmNoNmConn ----------------------------------------------------

scmNoNmConnRaise NOTIFICATION-TYPE
    OBJECTS { entityName, code, reportType, timeStamp, severity, serviceAffecting, description }
    STATUS  current
    DESCRIPTION
            "No Network Management Connectivity on both SCMs Raise"
    ::= { traps 151 }

scmNoNmConnClear NOTIFICATION-TYPE
    OBJECTS { entityName, code, reportType, timeStamp, severity, serviceAffecting, description }
    STATUS  current
    DESCRIPTION
            "No Network Management Connectivity on both SCMs Clear"
    ::= { traps 152 }

-- eqptLatchOpen ----------------------------------------------------

eqptLatchOpenRaise NOTIFICATION-TYPE
    OBJECTS { entityName, code, reportType, timeStamp, severity, serviceAffecting, description }
    STATUS  current
    DESCRIPTION
            "Equipment Latch Open Raise"
    ::= { traps 153 }

eqptLatchOpenClear NOTIFICATION-TYPE
    OBJECTS { entityName, code, reportType, timeStamp, severity, serviceAffecting, description }
    STATUS  current
    DESCRIPTION
            "Equipment Latch Open Clear"
    ::= { traps 154 }

-- powerAbsent ----------------------------------------------------

powerAbsentRaise NOTIFICATION-TYPE
    OBJECTS { entityName, code, reportType, timeStamp, severity, serviceAffecting, description }
    STATUS  current
    DESCRIPTION
            "No Power available Raise"
    ::= { traps 155 }

powerAbsentClear NOTIFICATION-TYPE
    OBJECTS { entityName, code, reportType, timeStamp, severity, serviceAffecting, description }
    STATUS  current
    DESCRIPTION
            "No Power available Clear"
    ::= { traps 156 }

-- fanSpeedLowTh ----------------------------------------------------

fanSpeedLowThRaise NOTIFICATION-TYPE
    OBJECTS { entityName, code, reportType, timeStamp, severity, serviceAffecting, description }
    STATUS  current
    DESCRIPTION
            "Fan speed below low threshold Raise"
    ::= { traps 157 }

fanSpeedLowThClear NOTIFICATION-TYPE
    OBJECTS { entityName, code, reportType, timeStamp, severity, serviceAffecting, description }
    STATUS  current
    DESCRIPTION
            "Fan speed below low threshold Clear"
    ::= { traps 158 }

-- nonCoLocatedController ----------------------------------------------------

nonCoLocatedControllerRaise NOTIFICATION-TYPE
    OBJECTS { entityName, code, reportType, timeStamp, severity, serviceAffecting, description }
    STATUS  current
    DESCRIPTION
            "Controllers are in different chassis Raise"
    ::= { traps 159 }

nonCoLocatedControllerClear NOTIFICATION-TYPE
    OBJECTS { entityName, code, reportType, timeStamp, severity, serviceAffecting, description }
    STATUS  current
    DESCRIPTION
            "Controllers are in different chassis Clear"
    ::= { traps 160 }
-- preFecBerTh ----------------------------------------------------

preFecBerThRaise NOTIFICATION-TYPE
    OBJECTS { entityName, code, reportType, timeStamp, severity, serviceAffecting, description }
    STATUS  current
    DESCRIPTION
            "Pre-FEC Bit Error Ratio Above High Threshold Raise"
    ::= { traps 161 }

preFecBerThClear NOTIFICATION-TYPE
    OBJECTS { entityName, code, reportType, timeStamp, severity, serviceAffecting, description }
    STATUS  current
    DESCRIPTION
            "Pre-FEC Bit Error Ratio Above High Threshold Clear"
    ::= { traps 162 }

-- firmUpgrdReqd ----------------------------------------------------

firmUpgrdReqdRaise NOTIFICATION-TYPE
    OBJECTS { entityName, code, reportType, timeStamp, severity, serviceAffecting, description }
    STATUS  current
    DESCRIPTION
            "Firmware Upgrade Required Raise"
    ::= { traps 163 }

firmUpgrdReqdClear NOTIFICATION-TYPE
    OBJECTS { entityName, code, reportType, timeStamp, severity, serviceAffecting, description }
    STATUS  current
    DESCRIPTION
            "Firmware Upgrade Required Clear"
    ::= { traps 164 }

-- otuBerTh ----------------------------------------------------

otuBerThRaise NOTIFICATION-TYPE
    OBJECTS { entityName, code, reportType, timeStamp, severity, serviceAffecting, description }
    STATUS  current
    DESCRIPTION
            "OTU Bit Error Ratio Above High Threshold Raise"
    ::= { traps 165 }

otuBerThClear NOTIFICATION-TYPE
    OBJECTS { entityName, code, reportType, timeStamp, severity, serviceAffecting, description }
    STATUS  current
    DESCRIPTION
            "OTU Bit Error Ratio Above High Threshold Clear"
    ::= { traps 166 }

-- oduBerTh ----------------------------------------------------

oduBerThRaise NOTIFICATION-TYPE
    OBJECTS { entityName, code, reportType, timeStamp, severity, serviceAffecting, description }
    STATUS  current
    DESCRIPTION
            "ODU Bit Error Ratio Above High Threshold Raise"
    ::= { traps 167 }

oduBerThClear NOTIFICATION-TYPE
    OBJECTS { entityName, code, reportType, timeStamp, severity, serviceAffecting, description }
    STATUS  current
    DESCRIPTION
            "ODU Bit Error Ratio Above High Threshold Clear"
    ::= { traps 168 }

-- pcsBerTh ----------------------------------------------------

pcsBerThRaise NOTIFICATION-TYPE
    OBJECTS { entityName, code, reportType, timeStamp, severity, serviceAffecting, description }
    STATUS  current
    DESCRIPTION
            "PCS Bit Error Ratio Above High Threshold Raise"
    ::= { traps 169 }

pcsBerThClear NOTIFICATION-TYPE
    OBJECTS { entityName, code, reportType, timeStamp, severity, serviceAffecting, description }
    STATUS  current
    DESCRIPTION
            "PCS Bit Error Ratio Above High Threshold Clear"
    ::= { traps 170 }

-- sectBerThRaise ----------------------------------------------------

berTh-sRaise NOTIFICATION-TYPE
    OBJECTS { entityName, code, reportType, timeStamp, severity, serviceAffecting, description }
    STATUS  current
    DESCRIPTION
            "Section Level Bit Error Ratio Above High Threshold Raise"
    ::= { traps 171 }

berTh-sClear NOTIFICATION-TYPE
    OBJECTS { entityName, code, reportType, timeStamp, severity, serviceAffecting, description }
    STATUS  current
    DESCRIPTION
            "Section Level Bit Error Ratio Above High Threshold Clear"
    ::= { traps 172 }

-- lineBerThRaise ----------------------------------------------------

berTh-lRaise NOTIFICATION-TYPE
    OBJECTS { entityName, code, reportType, timeStamp, severity, serviceAffecting, description }
    STATUS  current
    DESCRIPTION
            "Line Level Bit Error Ratio Above High Threshold Raise"
    ::= { traps 173 }

berTh-lClear NOTIFICATION-TYPE
    OBJECTS { entityName, code, reportType, timeStamp, severity, serviceAffecting, description }
    STATUS  current
    DESCRIPTION
            "Line Level Bit Error Ratio Above High Threshold Clear"
    ::= { traps 174 }

-- rsBerThRaise ----------------------------------------------------

rs-berThRaise NOTIFICATION-TYPE
    OBJECTS { entityName, code, reportType, timeStamp, severity, serviceAffecting, description }
    STATUS  current
    DESCRIPTION
            "Regenerator Section Bit Error Ratio Above High Threshold Raise"
    ::= { traps 175 }

rs-berThClear NOTIFICATION-TYPE
    OBJECTS { entityName, code, reportType, timeStamp, severity, serviceAffecting, description }
    STATUS  current
    DESCRIPTION
            "Regenerator Section Bit Error Ratio Above High Threshold Clear"
    ::= { traps 176 }

-- msBerThRaise ----------------------------------------------------

ms-berThRaise NOTIFICATION-TYPE
    OBJECTS { entityName, code, reportType, timeStamp, severity, serviceAffecting, description }
    STATUS  current
    DESCRIPTION
            "Multiplex Section Bit Error Ratio Above High Threshold Raise"
    ::= { traps 177 }

ms-berThClear NOTIFICATION-TYPE
    OBJECTS { entityName, code, reportType, timeStamp, severity, serviceAffecting, description }
    STATUS  current
    DESCRIPTION
            "Multiplex Section Bit Error Ratio Above High Threshold Clear"
    ::= { traps 178 }

-- oneCableDisconnected ----------------------------------------------------

oneCableDisconnectedRaise NOTIFICATION-TYPE
    OBJECTS { entityName, code, reportType, timeStamp, severity, serviceAffecting, description }
    STATUS  current
    DESCRIPTION
            "One Multichassis Cable Disconnected Raise"
    ::= { traps 179 }

oneCableDisconnectedClear NOTIFICATION-TYPE
    OBJECTS { entityName, code, reportType, timeStamp, severity, serviceAffecting, description }
    STATUS  current
    DESCRIPTION
            "One Multichassis Cable Disconnected Clear"
    ::= { traps 180 }

-- envCurrentHighTh ----------------------------------------------------

envCurrentHighThRaise NOTIFICATION-TYPE
    OBJECTS { entityName, code, reportType, timeStamp, severity, serviceAffecting, description }
    STATUS  current
    DESCRIPTION
            "High Current Threshold Required Raise"
    ::= { traps 181 }

envCurrentHighThClear NOTIFICATION-TYPE
    OBJECTS { entityName, code, reportType, timeStamp, severity, serviceAffecting, description }
    STATUS  current
    DESCRIPTION
            "High Current Threshold Requires Clear"
    ::= { traps 182 }


-- envCurrentLowTh ----------------------------------------------------

envCurrentLowThRaise NOTIFICATION-TYPE
    OBJECTS { entityName, code, reportType, timeStamp, severity, serviceAffecting, description }
    STATUS  current
    DESCRIPTION
            "Low Current Threshold Required Raise"
    ::= { traps 183 }

envCurrentLowThClear NOTIFICATION-TYPE
    OBJECTS { entityName, code, reportType, timeStamp, severity, serviceAffecting, description }
    STATUS  current
    DESCRIPTION
            "Low Current Threshold Requires Clear"
    ::= { traps 184 }

-- prbs ----------------------------------------------------

prbsRaise NOTIFICATION-TYPE
    OBJECTS { entityName, code, reportType, timeStamp, severity, serviceAffecting, description }
    STATUS  current
    DESCRIPTION
            "PRBS test active"
    ::= { traps 185 }

prbsClear NOTIFICATION-TYPE
    OBJECTS { entityName, code, reportType, timeStamp, severity, serviceAffecting, description }
    STATUS  current
    DESCRIPTION
            "PRBS test active cleared"
    ::= { traps 186 }

-- forced ----------------------------------------------------

forcedRaise NOTIFICATION-TYPE
    OBJECTS { entityName, code, reportType, timeStamp, severity, serviceAffecting, description }
    STATUS  current
    DESCRIPTION
            "Forced protection switch Raise"
    ::= { traps 187 }

forcedClear NOTIFICATION-TYPE
    OBJECTS { entityName, code, reportType, timeStamp, severity, serviceAffecting, description }
    STATUS  current
    DESCRIPTION
            "Forced protection switch Clear"
    ::= { traps 188 }

-- defRDICCM ----------------------------------------------------

defRDICCMRaise NOTIFICATION-TYPE
    OBJECTS { entityName, code, reportType, timeStamp, severity, serviceAffecting, description }
    STATUS  current
    DESCRIPTION
            "Receiving RDI from remote MEP Raise"
    ::= { traps 189 }

defRDICCMClear NOTIFICATION-TYPE
    OBJECTS { entityName, code, reportType, timeStamp, severity, serviceAffecting, description }
    STATUS  current
    DESCRIPTION
            "Receiving RDI from remote MEP Clear"
    ::= { traps 190 }

-- defMACStatus ----------------------------------------------------

defMACStatusRaise NOTIFICATION-TYPE
    OBJECTS { entityName, code, reportType, timeStamp, severity, serviceAffecting, description }
    STATUS  current
    DESCRIPTION
            "Port status failure of remote MEP Raise"
    ::= { traps 191 }

defMACStatusClear NOTIFICATION-TYPE
    OBJECTS { entityName, code, reportType, timeStamp, severity, serviceAffecting, description }
    STATUS  current
    DESCRIPTION
            "Port status failure of remote MEP Clear"
    ::= { traps 192 }

-- defRemoteCCM ----------------------------------------------------

defRemoteCCMRaise NOTIFICATION-TYPE
    OBJECTS { entityName, code, reportType, timeStamp, severity, serviceAffecting, description }
    STATUS  current
    DESCRIPTION
            "Lost connection with remote MEP Raise"
    ::= { traps 193 }

defRemoteCCMClear NOTIFICATION-TYPE
    OBJECTS { entityName, code, reportType, timeStamp, severity, serviceAffecting, description }
    STATUS  current
    DESCRIPTION
            "Lost connection with remote MEP Clear"
    ::= { traps 194 }

-- defErrorCCM ----------------------------------------------------

defErrorCCMRaise NOTIFICATION-TYPE
    OBJECTS { entityName, code, reportType, timeStamp, severity, serviceAffecting, description }
    STATUS  current
    DESCRIPTION
            "Receiving invalid CCM packet from remote MEP Raise"
    ::= { traps 195 }

defErrorCCMClear NOTIFICATION-TYPE
    OBJECTS { entityName, code, reportType, timeStamp, severity, serviceAffecting, description }
    STATUS  current
    DESCRIPTION
            "Receiving invalid CCM packet from remote MEP Clear"
    ::= { traps 196 }

-- defXconCCM ----------------------------------------------------

defXconCCMRaise NOTIFICATION-TYPE
    OBJECTS { entityName, code, reportType, timeStamp, severity, serviceAffecting, description }
    STATUS  current
    DESCRIPTION
            "Receiving cross connect CCMs Raise"
    ::= { traps 197 }

defXconCCMClear NOTIFICATION-TYPE
    OBJECTS { entityName, code, reportType, timeStamp, severity, serviceAffecting, description }
    STATUS  current
    DESCRIPTION
            "Receiving cross connect CCMs Clear"
    ::= { traps 198 }
	
-- defBfdDown ----------------------------------------------------
defBfdDownRaise NOTIFICATION-TYPE
    OBJECTS { entityName, code, reportType, timeStamp, severity, serviceAffecting, description }
    STATUS  current
    DESCRIPTION
            "BFD session down Raise"
    ::= { traps 199 }
defBfdDownClear NOTIFICATION-TYPE
    OBJECTS { entityName, code, reportType, timeStamp, severity, serviceAffecting, description }
    STATUS  current
    DESCRIPTION
            "BFD session down Clear"
    ::= { traps 200 }	
	
-- isisDbOvrld ----------------------------------------------------

isisDbOvrldRaise NOTIFICATION-TYPE
    OBJECTS { entityName, code, reportType, timeStamp, severity, serviceAffecting, description }
    STATUS  current
    DESCRIPTION
            "ISIS Database Overloaded Raise"
    ::= { traps 201 }

isisDbOvrldClear NOTIFICATION-TYPE
    OBJECTS { entityName, code, reportType, timeStamp, severity, serviceAffecting, description }
    STATUS  current
    DESCRIPTION
            "ISIS Database Overloaded Clear"
    ::= { traps 202 }	
	
-- isisXDown ----------------------------------------------------

isisXDownRaise NOTIFICATION-TYPE
    OBJECTS { entityName, code, reportType, timeStamp, severity, serviceAffecting, description }
    STATUS  current
    DESCRIPTION
            "ISIS Circuit Down Raise"
    ::= { traps 203 }

isisXDownClear NOTIFICATION-TYPE
    OBJECTS { entityName, code, reportType, timeStamp, severity, serviceAffecting, description }
    STATUS  current
    DESCRIPTION
            "ISIS Circuit Down Clear"
    ::= { traps 204 }

-- isisAdjDown ----------------------------------------------------

isisAdjDownRaise NOTIFICATION-TYPE
    OBJECTS { entityName, code, reportType, timeStamp, severity, serviceAffecting, description }
    STATUS  current
    DESCRIPTION
            "ISIS Adjacency Down Raise"
    ::= { traps 205 }

isisAdjDownClear NOTIFICATION-TYPE
    OBJECTS { entityName, code, reportType, timeStamp, severity, serviceAffecting, description }
    STATUS  current
    DESCRIPTION
            "ISIS Adjacency Down Clear"
    ::= { traps 206 }	

-- isisAdjRejected ----------------------------------------------------

isisAdjRejectedRaise NOTIFICATION-TYPE
    OBJECTS { entityName, code, reportType, timeStamp, severity, serviceAffecting, description }
    STATUS  current
    DESCRIPTION
            "ISIS Adjacency Rejected Raise"
    ::= { traps 207 }

isisAdjRejectedClear NOTIFICATION-TYPE
    OBJECTS { entityName, code, reportType, timeStamp, severity, serviceAffecting, description }
    STATUS  current
    DESCRIPTION
            "ISIS Adjacency Rejected  Clear"
    ::= { traps 208 }	

-- rsvpAdjDown ----------------------------------------------------

rsvpAdjDownRaise NOTIFICATION-TYPE
    OBJECTS { entityName, code, reportType, timeStamp, severity, serviceAffecting, description }
    STATUS  current
    DESCRIPTION
            "RSVP Adjacency Down Raise"
    ::= { traps 209 }

rsvpAdjDownClear NOTIFICATION-TYPE
    OBJECTS { entityName, code, reportType, timeStamp, severity, serviceAffecting, description }
    STATUS  current
    DESCRIPTION
            "RSVP Adjacency Down Clear"
    ::= { traps 210 }			

-- diskHighUsage ----------------------------------------------------

diskHighUsageRaise NOTIFICATION-TYPE
    OBJECTS { entityName, code, reportType, timeStamp, severity, serviceAffecting, description }
    STATUS  current
    DESCRIPTION
            "Disk High Usage Raise"
    ::= { traps 211 }

diskHighUsageClear NOTIFICATION-TYPE
    OBJECTS { entityName, code, reportType, timeStamp, severity, serviceAffecting, description }
    STATUS  current
    DESCRIPTION
            "Disk High Usage Clear"
    ::= { traps 212 }	

-- memHighUsage ----------------------------------------------------

memHighUsageRaise NOTIFICATION-TYPE
    OBJECTS { entityName, code, reportType, timeStamp, severity, serviceAffecting, description }
    STATUS  current
    DESCRIPTION
            "Memory High Usage Raise"
    ::= { traps 213 }

memHighUsageClear NOTIFICATION-TYPE
    OBJECTS { entityName, code, reportType, timeStamp, severity, serviceAffecting, description }
    STATUS  current
    DESCRIPTION
            "Memory High Usage Clear"
    ::= { traps 214 }	

-- lockout ----------------------------------------------------

lockoutRaise NOTIFICATION-TYPE
    OBJECTS { entityName, code, reportType, timeStamp, severity, serviceAffecting, description }
    STATUS  current
    DESCRIPTION
            "Lockout protection switch Raise"
    ::= { traps 215 }

lockoutClear NOTIFICATION-TYPE
    OBJECTS { entityName, code, reportType, timeStamp, severity, serviceAffecting, description }
    STATUS  current
    DESCRIPTION
            "Lockout protection switch Clear"
    ::= { traps 216 }

-- invUnknown ----------------------------------------------------
	
invUnknownRaise NOTIFICATION-TYPE
    OBJECTS { entityName, code, reportType, timeStamp, severity, serviceAffecting, description }
    STATUS  current
    DESCRIPTION
            "Inventory Unknown raise"
    ::= { traps 217 }

invUnknownClear NOTIFICATION-TYPE
    OBJECTS { entityName, code, reportType, timeStamp, severity, serviceAffecting, description }
    STATUS  current
    DESCRIPTION
            "Inventory Unknown clear"
    ::= { traps 218 }	

-- airfilterAbsense ----------------------------------------------------
airfilterAbsenseRaise NOTIFICATION-TYPE
    OBJECTS { entityName, code, reportType, timeStamp, severity, serviceAffecting, description }
    STATUS  current
    DESCRIPTION
            "AirFilter Absense Raise"
    ::= { traps 219 }

airfilterAbsenseClear NOTIFICATION-TYPE
    OBJECTS { entityName, code, reportType, timeStamp, severity, serviceAffecting, description }
    STATUS  current
    DESCRIPTION
            "AirFilter Absense Clear"
    ::= { traps 220 }

-- firmUpgrdFail ------------------------------------------------------
firmUpgrdFailRaise NOTIFICATION-TYPE
    OBJECTS { entityName, code, reportType, timeStamp, severity, serviceAffecting, description }
    STATUS  current
    DESCRIPTION
            "Shelf manager firmware upgrade failed Raise"
    ::= { traps 221 }

firmUpgrdFailClear NOTIFICATION-TYPE
    OBJECTS { entityName, code, reportType, timeStamp, severity, serviceAffecting, description }
    STATUS  current
    DESCRIPTION
            "Shelf manager firmware upgrade failed Clear"
    ::= { traps 222 }

-- partitionFault ------------------------------------------------------
partitionFaultRaise NOTIFICATION-TYPE
    OBJECTS { entityName, code, reportType, timeStamp, severity, serviceAffecting, description }
    STATUS  current
    DESCRIPTION
            "Disk partition fault detected Raise"
    ::= { traps 223 }

partitionFaultClear NOTIFICATION-TYPE
    OBJECTS { entityName, code, reportType, timeStamp, severity, serviceAffecting, description }
    STATUS  current
    DESCRIPTION
            "Disk partition fault detected Clear"
    ::= { traps 224 }

-- lolck ------------------------------------------------------
lolckRaise NOTIFICATION-TYPE
    OBJECTS { entityName, code, reportType, timeStamp, severity, serviceAffecting, description }
    STATUS  current
    DESCRIPTION
            "Loss of Lock Raise"
    ::= { traps 225 }

lolckClear NOTIFICATION-TYPE
    OBJECTS { entityName, code, reportType, timeStamp, severity, serviceAffecting, description }
    STATUS  current
    DESCRIPTION
            "Loss of Lock Clear"
    ::= { traps 226 }

-- inventoryUnsupp ------------------------------------------------------
inventoryUnsuppRaise NOTIFICATION-TYPE
    OBJECTS { entityName, code, reportType, timeStamp, severity, serviceAffecting, description }
    STATUS  current
    DESCRIPTION
            "Inventory Item Unsupported Raise"
    ::= { traps 227 }

inventoryUnsuppClear NOTIFICATION-TYPE
    OBJECTS { entityName, code, reportType, timeStamp, severity, serviceAffecting, description }
    STATUS  current
    DESCRIPTION
            "Inventory Item Unsupported Clear"
    ::= { traps 228 }

END
