--
-- she-sync-mib.mib
-- MIB generated by MG-SOFT Visual MIB Builder Version 6.0  Build 88
-- Wednesday, June 03, 2009 at 14:31:00
--

-- Start of ClearCase branch-information of current release:
-- she-sync-mib.mib   /main/she_main_grf/she_r3.0_grf/11
-- End of ClearCase branch-information.
-- 

	SHE-SYNC-MIB DEFINITIONS ::= BEGIN
 
		IMPORTS
			she			
				FROM AN-MIB			
			PhysicalIndex			
				FROM ENTITY-MIB			
			sheAlarmTimeAndDate, sheAlarmReportingSource, sheAlarmReportingSourceType, sheAlarmSeverity, SheAlarmSevProfileIndex			
				FROM SHE-ALARMING-MIB			
			SheControlStatusType			
				FROM SHE-TC-MIB			
			OBJECT-GROUP, MODULE-COMPLIANCE, NOTIFICATION-GROUP			
				FROM SNMPv2-CONF			
			Unsigned32, OBJECT-TYPE, MODULE-IDENTITY, NOTIFICATION-TYPE			
				FROM SNMPv2-SMI			
			TruthValue, TEXTUAL-CONVENTION			
				FROM SNMPv2-TC;
	
	
		sheSync MODULE-IDENTITY 
			LAST-UPDATED "200906031500Z"		-- June 03, 2009 at 15:00 GMT
			ORGANIZATION 
				"Nokia Siemens Networks"
			CONTACT-INFO 
				"Gerd Barchmann
				COO BCS BBA RD HW1
				
				gerd.barchmann@nsn.com
				+49 3834 555654"
			DESCRIPTION 
				"The MIB module for managing the clock sources (timing) of the network element."
			REVISION "200704051511Z"		-- April 05, 2007 at 15:11 GMT
			DESCRIPTION 
				"Initial version - merge from GPON project."
			REVISION "200710161100Z"		-- October 16, 2007 at 11:00 GMT
			DESCRIPTION 
				"New release SHE R2.6P support new types of possible sync sources."
			REVISION "200711271137Z"		-- November 27, 2007 at 11:37 GMT
			DESCRIPTION 
				"Expand support to a configurable sync source table according concept paper SHE R3.0."
			REVISION "200712121357Z"		-- December 12, 2007 at 13:57 GMT
			DESCRIPTION 
				"Correct SSM-Level definitions."
			REVISION "200712201309Z"		-- December 20, 2007 at 13:09 GMT
			DESCRIPTION 
				"Redesign synctables after review by systems."
			REVISION "200803101553Z"		-- March 10, 2008 at 15:53 GMT
			DESCRIPTION 
				"Supported startet now with SHE R2.8."
			REVISION "200807291006Z"		-- July 29, 2008 at 10:06 GMT
			DESCRIPTION 
				"Add new Alarm if no SSM information is detected for selected sync source
				(only for sources who will support SSM like sync ethernet - not for T3)."
			REVISION "200808281114Z"		-- August 28, 2008 at 11:14 GMT
			DESCRIPTION 
				"Correct some descriptions regarding the parameter support started with R2.8 instead of R3.0."
			REVISION "200810080848Z"		-- October 08, 2008 at 08:48 GMT
			DESCRIPTION 
				"Add comment for used syncSources depending on CXU type.
				Modify syntax for sheSyncSourceAvailabilityType."
			REVISION "200902040843Z"		-- February 04, 2009 at 08:43 GMT
			DESCRIPTION 
				"Modify SyncSourceAvailabilityTable - new parameter for configurable clock source types on new power modules.
				New controlRequest types to configure these power modules."
			REVISION "200903030840Z"		-- March 03, 2009 at 08:40 GMT
			DESCRIPTION 
				"Add notification for AvailabilityTable update if HW base was changed."
			REVISION "200903250929Z"		-- March 25, 2009 at 09:29 GMT
			DESCRIPTION 
				"Add new ControlReqResult values for detailed failure codes."
			REVISION "200906031420Z"		-- June 03, 2009 at 14:20 GMT
			DESCRIPTION 
				"Add new ReqResult-Trap for sourceType modification command."
			::= { she 15 }

		
	
--
-- Type definitions
--
	
		SheSyncPriorityType ::= INTEGER (0 | 1..2)

		SheSyncWaitTimeToRestoreType ::= INTEGER (0..2147483647)

		SheSyncSourceAlarmStateType ::= INTEGER
			{
			sheAlarmCleared(0),
			sheAlarmPresent(1)
			}

		SheSyncAvailabilityIndexType ::= INTEGER (0 | 1..10)

		SheSyncControlReqType ::= INTEGER
			{
			noRequest(1),
			sheModifySyncSource(101),
			sheModifySyncWaitTimeToRestore(102),
			sheModifySyncGlobals(103),
			sheModifyUsedSyncSource(104),
			sheSetVaribaleSyncSourceTypeToT3(105),
			sheSetVaribaleSyncSourceTypeToE1(106),
			sheSetVaribaleSyncSourceTypeToBits(107)
			}

	
--
-- Textual conventions
--
	
		SheSyncModeType ::= TEXTUAL-CONVENTION
			STATUS current
			DESCRIPTION 
				"sheSyncMode values"
			SYNTAX INTEGER
				{
				revertive(1),
				nonrevertive(2)
				}

		SheSyncControlReqResultType ::= TEXTUAL-CONVENTION
			STATUS current
			DESCRIPTION 
				"The result type for synchronization control commands."
			SYNTAX INTEGER
				{
				noRequest(1),
				commExecStarted(5),
				paramFaulty(11),
				requestBusy(12),
				setDataFailed(13),
				aswTimeout(14),
				commandFailed(15),
				commandSucceeded(16),
				wrongAlarmSeverityIndex(23),
				clockSourceNotAvailable(24),
				clockSourceNotAccessible(25),
				clockModeNotSupported(26),
				clockSourceTypeModifyNotSupported(27),
				clockSourceTypeModifyNotPossibleForActiveClocks(28)
				}

		SheSyncSourceType ::= TEXTUAL-CONVENTION
			STATUS current
			DESCRIPTION 
				"Used in sheSyncSourceAvailabilityTable to show the type of available clocksources.
				Only external sources will be shown in that table but the internal oscilator is always available
				and will be used if no external clocks could be detected or all of them are down.
				
				"
			SYNTAX INTEGER
				{
				sheInternalSyncSource(1),
				sheT3orE1SyncSource(2),
				sheBitsSyncSource(3),
				sheEthernetSyncSource(4),
				sheTimingOverPacketSyncSource(6),
				sheT3SyncSource(8),
				sheE1SyncSource(9)
				}

	
--
-- Node definitions
--
	
		sheSyncObjects OBJECT IDENTIFIER ::= { sheSync 1 }

		
		sheSyncGlobalObjects OBJECT IDENTIFIER ::= { sheSyncObjects 1 }

		
		sheSyncActiveClockSource OBJECT-TYPE
			SYNTAX SheSyncPriorityType
			MAX-ACCESS read-only
			STATUS current
			DESCRIPTION
				"The current chosen (active) clock source. Identifies an entry in the SyncSourceTable.
				0 means that no syncSource is available or configured and the NE uses the internal clock of the used CXU board.
				"
			::= { sheSyncGlobalObjects 1 }

		
		sheSyncWaitTimeToRestore OBJECT-TYPE
			SYNTAX SheSyncWaitTimeToRestoreType
			UNITS "100 ms"
			MAX-ACCESS read-only
			STATUS current
			DESCRIPTION
				"This time has to expire before switch back to a higher
				clock source after error condition.
				Unit is 100 ms."
			::= { sheSyncGlobalObjects 2 }

		
		sheSyncMode OBJECT-TYPE
			SYNTAX SheSyncModeType
			MAX-ACCESS read-only
			STATUS current
			DESCRIPTION
				"The used sync - mode.
				
				revertive - the highest priority sync source with valid reference is always selected.
				nonrevertive - the active sync source will always remain active while it is valid.
				Only if this sync source will be come invalid, a refence switchover to a valid reference
				with highest priority will be initiated.
				
				New parameter with R2.8."
			DEFVAL { revertive }
			::= { sheSyncGlobalObjects 3 }

		
		sheSyncLocalClockSSMLevel OBJECT-TYPE
			SYNTAX Unsigned32 (0..15)
			MAX-ACCESS read-only
			STATUS current
			DESCRIPTION
				"This parameter defines the configured SSM-Level for the local clock.
				This parameter should be transmitted, if all selected clock sources are failed and the
				NE uses his own internal clock reference (free run).
				The level is defined in 16 steps from 0..15, where 0 is the highest quality level. 
				
				New parameter with R2.8."
			DEFVAL { 15 }
			::= { sheSyncGlobalObjects 4 }

		
		sheSyncSourceTable OBJECT-TYPE
			SYNTAX SEQUENCE OF SheSyncSourceEntry
			MAX-ACCESS not-accessible
			STATUS current
			DESCRIPTION
				"The synchronization source table is used to manage synchronization sources
				and there priorities in the network element.
				"
			::= { sheSyncObjects 2 }

		
		sheSyncSourceEntry OBJECT-TYPE
			SYNTAX SheSyncSourceEntry
			MAX-ACCESS not-accessible
			STATUS current
			DESCRIPTION
				"An entry in the SyncSourceTable. It defines one possible synchronization source
				of the network element and its priority.
				Maximum two sources could be selected from SyncSourceAvailabilityTable if CXU_B3 is used.
				All other CXU types will only accept one table entry!"
			INDEX { sheSyncSourcePriority }
			::= { sheSyncSourceTable 1 }

		
		SheSyncSourceEntry ::=
			SEQUENCE { 
				sheSyncSourcePriority
					SheSyncPriorityType,
				sheSyncSourceType
					SheSyncSourceType,
				sheSyncSourceHwUnitIndex
					INTEGER,
				sheSyncSourceInterfaceNumber
					Unsigned32,
				sheSyncSourceAlarmState
					SheSyncSourceAlarmStateType,
				sheSyncSourceAlarmSeverityIndex
					SheAlarmSevProfileIndex,
				sheSyncSourceSelectedAvailabilityIndex
					SheSyncAvailabilityIndexType,
				sheSyncSourceSSMLevel
					Unsigned32,
				sheSyncSourceSSMLevelRec
					Unsigned32
			 }

		sheSyncSourcePriority OBJECT-TYPE
			SYNTAX SheSyncPriorityType
			MAX-ACCESS read-only
			STATUS current
			DESCRIPTION
				"A unique value to identify the priority of the synchronization source.
				Used as table index. 0 is not an useful index for that table."
			::= { sheSyncSourceEntry 1 }

		
		sheSyncSourceType OBJECT-TYPE
			SYNTAX SheSyncSourceType
			MAX-ACCESS read-only
			STATUS obsolete
			DESCRIPTION
				"The type of the synchronization source of the network element.
				
				NOTE:
				Not longer used with SHE R2.8."
			::= { sheSyncSourceEntry 2 }

		
		sheSyncSourceHwUnitIndex OBJECT-TYPE
			SYNTAX INTEGER (-1 | 1..2147483647)
			MAX-ACCESS read-only
			STATUS obsolete
			DESCRIPTION
				"Identifies the hardware unit that contains the synchronization source.
				If the hardware unit is not equipped, sheSyncSourceHwUnitIndex contains -1. 
				
				NOTE:
				Not longer used with SHE R2.8."
			::= { sheSyncSourceEntry 3 }

		
		sheSyncSourceInterfaceNumber OBJECT-TYPE
			SYNTAX Unsigned32 (1..72)
			MAX-ACCESS read-only
			STATUS obsolete
			DESCRIPTION
				"The number of the physical interface of the hardware unit.
				The interfaces are numbered vendor specific starting with 1
				in ascending order. Synchronization interfaces may not be
				contained in the interface table.
				
				NOTE:
				Not longer used with SHE R2.8."
			::= { sheSyncSourceEntry 4 }

		
		sheSyncSourceAlarmState OBJECT-TYPE
			SYNTAX SheSyncSourceAlarmStateType
			MAX-ACCESS read-only
			STATUS current
			DESCRIPTION
				"An alarm is generated when a clock source can't be used."
			::= { sheSyncSourceEntry 5 }

		
		sheSyncSourceAlarmSeverityIndex OBJECT-TYPE
			SYNTAX SheAlarmSevProfileIndex
			MAX-ACCESS read-only
			STATUS current
			DESCRIPTION
				"This index selects an item in the sheAlarmSeverityProfileTable[]. It is
				used to assign the reported alarm to a severity."
			DEFVAL { 1 }
			::= { sheSyncSourceEntry 6 }

		
		sheSyncSourceSelectedAvailabilityIndex OBJECT-TYPE
			SYNTAX SheSyncAvailabilityIndexType
			MAX-ACCESS read-only
			STATUS current
			DESCRIPTION
				"A unique value to identify a available synchronization source (from sheSyncAvailabilityTable)
				which is used as sync source for the NE.
				An index value 0 means no source is selected. 
				
				New parameter with R2.8."
			::= { sheSyncSourceEntry 7 }

		
		sheSyncSourceSSMLevel OBJECT-TYPE
			SYNTAX Unsigned32 (0..15)
			MAX-ACCESS read-only
			STATUS current
			DESCRIPTION
				"This parameter defines the configured reference or assigned SSM-Level for this sync source.
				It should work as reference level only for source types, which supports SSM OAM messages for
				clock quality evaluation like ToP or syncEthernet.
				For other sourcetypes it is the assigned SSM-Level which should be used by the input selector
				for sourceclock quality comparation.
				The level is defined in 16 steps from 0..15, where 0 is the highest quality level. 
				
				The sync source will be invalid, if the received SSM level is above the configured
				reference level.
				
				New parameter with R2.8."
			::= { sheSyncSourceEntry 8 }

		
		sheSyncSourceSSMLevelRec OBJECT-TYPE
			SYNTAX Unsigned32 (0..15)
			MAX-ACCESS read-only
			STATUS current
			DESCRIPTION
				"This parameter shows the received SSM-Level for this sync source.
				It is only valid for source types, which supports SSM OAM messages for
				clock quality evaluation like syncEthernet or ToP. 
				In case of ToP sync sources, the NE will internaly convert the received stratum number (IEEE1588)
				to an SSM level value according G.781.
				
				The level is defined in 16 steps from 0..15, where 0 is the highest quality level. 
				The sync source will be invalid, if the received SSM level is above the configured
				reference level.
				
				New parameter with R2.8.
				
				"
			::= { sheSyncSourceEntry 9 }

		
		sheSyncControlGroup OBJECT IDENTIFIER ::= { sheSyncObjects 3 }

		
		sheSyncCgControlReq OBJECT-TYPE
			SYNTAX SheSyncControlReqType
			MAX-ACCESS read-write
			STATUS current
			DESCRIPTION
				"sheModifySyncSource (101):
				sheSyncCgSourcePriority
				sheSyncCgSourceAlarmSeverityIndex
				
				sheModifySyncWaitTimeToRestore (102):
				sheSyncCgSourceWaitTimeToRestore 
				
				New commands with R2.8:
				sheModifySyncGlobals (103):
				sheSyncCgMode
				sheSyncCgSourceWaitTimeToRestore
				sheSyncCgSourceSSMLevel  
				
				sheModifyUsedSyncSource (104):  -> Maximum two sources could be selected from SyncSourceAvailabilityTable if CXU_B3 is used.
				                            All other CXU types will only accept one table entry!
				sheSyncCgSourcePriority
				sheSyncCgSourceAvailabilityIndex
				sheSyncCgSourceSSMLevel
				
				
				New commands with R2.8 maintenance:
				Valid only if clock sources with parameter TypeSelectionPossible == TRUE are available in the system.
				More then one trap could be send if more then one clock source was reconfigured by only one command.
				
				sheSetVaribaleSyncSourceTypeToT3 (105):
				sheSetVaribaleSyncSourceTypeToE1 (106):
				sheSetVaribaleSyncSourceTypeToBits (107):"
			::= { sheSyncControlGroup 1 }

		
		sheSyncCgControlStatus OBJECT-TYPE
			SYNTAX SheControlStatusType
			MAX-ACCESS read-only
			STATUS current
			DESCRIPTION
				"Indicates the status of a control request. "
			::= { sheSyncControlGroup 2 }

		
		sheSyncCgControlReqResult OBJECT-TYPE
			SYNTAX SheSyncControlReqResultType
			MAX-ACCESS read-only
			STATUS current
			DESCRIPTION
				"The result of the last user command. "
			::= { sheSyncControlGroup 3 }

		
		sheSyncCgControlTimeStamp OBJECT-TYPE
			SYNTAX Unsigned32
			UNITS "sec"
			MAX-ACCESS read-only
			STATUS current
			DESCRIPTION
				"The time stamp of the last command (end of command). "
			::= { sheSyncControlGroup 4 }

		
		sheSyncCgSourcePriority OBJECT-TYPE
			SYNTAX SheSyncPriorityType
			MAX-ACCESS read-write
			STATUS current
			DESCRIPTION
				"A unique value to identify the synchronization source and its priority.
				Parameter for command sheModifySyncSource and sheModifyUsedSyncSource to select
				the table entry to be modified. 0 is not a useful index value for these commands."
			::= { sheSyncControlGroup 5 }

		
		sheSyncCgSourceAlarmSeverityIndex OBJECT-TYPE
			SYNTAX SheAlarmSevProfileIndex
			MAX-ACCESS read-write
			STATUS current
			DESCRIPTION
				"This index selects an item in the sheAlarmSeverityProfileTable[]. It is
				used to assign the reported alarm (clock source can't be used)
				to a severity."
			::= { sheSyncControlGroup 6 }

		
		sheSyncCgSourceWaitTimeToRestore OBJECT-TYPE
			SYNTAX SheSyncWaitTimeToRestoreType
			UNITS "100 ms"
			MAX-ACCESS read-write
			STATUS current
			DESCRIPTION
				"This time has to expire before switch back to a higher
				clock source after error condition.
				Unit is 100 ms."
			::= { sheSyncControlGroup 7 }

		
		sheSyncCgMode OBJECT-TYPE
			SYNTAX SheSyncModeType
			MAX-ACCESS read-write
			STATUS current
			DESCRIPTION
				"The used sync - mode.
				
				revertive - the highest priority sync source with valid reference is always selected.
				nonrevertive - the active sync source will always remain active while it is valid.
				Only if this sync source will be come invalid, a refence switchover to a valid reference
				with highest priority will be initiated.
				
				New parameter with R2.8."
			::= { sheSyncControlGroup 8 }

		
		sheSyncCgSourceSSMLevel OBJECT-TYPE
			SYNTAX Unsigned32 (0..15)
			MAX-ACCESS read-write
			STATUS current
			DESCRIPTION
				"This parameter defines the configured reference SSM-Level for this sync source.
				The level is defined in 16 steps from 0..15, where 0 is the highest quality level. 
				
				New parameter with R2.8."
			::= { sheSyncControlGroup 9 }

		
		sheSyncCgSourceAvailabilityIndex OBJECT-TYPE
			SYNTAX SheSyncAvailabilityIndexType
			MAX-ACCESS read-write
			STATUS current
			DESCRIPTION
				"Select an entry from sheSyncSourceAvailabilityTable to be used as possible sync source for the NE.
				An index parameter 0 will delete the current used syncSource from the selected priority position without an new entry.
				
				New parameter with R2.8."
			::= { sheSyncControlGroup 10 }

		
		sheSyncNotifications OBJECT IDENTIFIER ::= { sheSyncObjects 4 }

		
		sheSyncEvents OBJECT IDENTIFIER ::= { sheSyncNotifications 1 }

		
		sheSyncControlResult NOTIFICATION-TYPE
			OBJECTS { sheSyncCgControlTimeStamp, sheSyncCgSourcePriority, sheSyncCgControlReq, sheSyncCgControlReqResult }
			STATUS current
			DESCRIPTION 
				"Notification sent at the end of a long running command. "
			::= { sheSyncEvents 1 }

		
		sheSyncClockSourceModified NOTIFICATION-TYPE
			OBJECTS { sheSyncCgControlTimeStamp, sheSyncCgSourcePriority, sheSyncSourceAlarmSeverityIndex }
			STATUS current
			DESCRIPTION 
				"This trap is sent when a clock source (entry in the SyncSourceTable) has been modified."
			::= { sheSyncEvents 2 }

		
		sheSyncWaitTimeToRestoreModified NOTIFICATION-TYPE
			OBJECTS { sheSyncCgControlTimeStamp, sheSyncWaitTimeToRestore }
			STATUS current
			DESCRIPTION 
				"This trap is sent when the WaitTimeToRestore has been modified."
			::= { sheSyncEvents 3 }

		
		sheSyncActiveClockSourceChanged NOTIFICATION-TYPE
			OBJECTS { sheSyncCgControlTimeStamp, sheSyncActiveClockSource }
			STATUS current
			DESCRIPTION 
				"This trap is sent when the active clock source has changed."
			::= { sheSyncEvents 4 }

		
		sheSyncGlobalsModified NOTIFICATION-TYPE
			OBJECTS { sheSyncCgControlTimeStamp, sheSyncWaitTimeToRestore, sheSyncMode, sheSyncLocalClockSSMLevel }
			STATUS current
			DESCRIPTION 
				"This trap is sent when the SyncGlobals has been modified.
				
				New parameter with R2.8."
			::= { sheSyncEvents 5 }

		
		sheSyncUsedSyncSourcesModified NOTIFICATION-TYPE
			OBJECTS { sheSyncCgControlTimeStamp, sheSyncCgSourcePriority, sheSyncCgSourceAvailabilityIndex, sheSyncCgSourceSSMLevel }
			STATUS current
			DESCRIPTION 
				"This trap is sent when the used sync source table was reconfigured.
				
				New parameter with R2.8."
			::= { sheSyncEvents 6 }

		
		sheSyncAvailableSyncSourceTypeModified NOTIFICATION-TYPE
			OBJECTS { sheSyncCgControlTimeStamp, sheSyncSourceAvailabilityType }
			STATUS current
			DESCRIPTION 
				"This trap is sent when the types of some available sources were reconfigured.
				More then one trap could be send if more then one clock source was reconfigured by only one command.
				
				New parameter with R2.8 maintenance."
			::= { sheSyncEvents 7 }

		
		sheSyncAvailabilityTableUpdated NOTIFICATION-TYPE
			OBJECTS { sheSyncCgControlTimeStamp }
			STATUS current
			DESCRIPTION 
				"This trap is sent by the NE if the list of available sync sources change during runtime.
				That could be happened if power modules with sync source interfaces will be replaced.
				
				New parameter with R2.8 maintenance."
			::= { sheSyncEvents 8 }

		
		sheSyncSourceModifiedReqResult NOTIFICATION-TYPE
			OBJECTS { sheSyncCgControlReq, sheSyncCgControlTimeStamp, sheSyncCgControlReqResult }
			STATUS current
			DESCRIPTION 
				"ReqResult trap for long running command's."
			::= { sheSyncEvents 11 }

		
		sheSyncAlarms OBJECT IDENTIFIER ::= { sheSyncNotifications 2 }

		
		sheSyncClockSourceAlarm NOTIFICATION-TYPE
			OBJECTS { sheAlarmTimeAndDate, sheAlarmReportingSource, sheAlarmReportingSourceType, sheAlarmSeverity }
			STATUS current
			DESCRIPTION 
				"An alarm is generated when a clock source can't be used."
			::= { sheSyncAlarms 1 }

		
		sheSyncClockNoSSMInfoAlarm NOTIFICATION-TYPE
			OBJECTS { sheAlarmTimeAndDate, sheAlarmReportingSource, sheAlarmReportingSourceType, sheAlarmSeverity }
			STATUS current
			DESCRIPTION 
				"This alarm is generated when a selected clock source normaly support SSM information,
				but NO SSM data could be detected. The SSMLevelRec will be set to '1111' in this case.
				This is only possible for source types, which supports SSM OAM messages for clock quality
				evaluation like syncEthernet or ToP.
				
				New parameter with R2.8."
			::= { sheSyncAlarms 2 }

		
		sheSyncSourceAvailabilityTable OBJECT-TYPE
			SYNTAX SEQUENCE OF SheSyncSourceAvailabilityEntry
			MAX-ACCESS not-accessible
			STATUS current
			DESCRIPTION
				"The source availability table is used to show the management system which synchronization
				sources are available in the NE element depending on the used hardware configuration.
				The table has a fixed number of entries created by the NE. From these table entrys,
				the list of used clocksources inside the sheSyncSourceTable could be configured.
				
				New table supported with R2.8."
			::= { sheSyncObjects 5 }

		
		sheSyncSourceAvailabilityEntry OBJECT-TYPE
			SYNTAX SheSyncSourceAvailabilityEntry
			MAX-ACCESS not-accessible
			STATUS current
			DESCRIPTION
				"An entry in the SyncSourceAvailabilityTable.
				It defines the possible synchronization sources of the network element, depending on the used HW."
			INDEX { sheSyncSourceAvailabilityIndex }
			::= { sheSyncSourceAvailabilityTable 1 }

		
		SheSyncSourceAvailabilityEntry ::=
			SEQUENCE { 
				sheSyncSourceAvailabilityIndex
					SheSyncAvailabilityIndexType,
				sheSyncSourceAvailabilityType
					SheSyncSourceType,
				sheSyncSourceAvailabilityHwUnitIndex
					PhysicalIndex,
				sheSyncSourceAvailabilityInterfaceNumber
					Unsigned32,
				sheSyncSourceAvailabilityTypeSelectionPossible
					TruthValue
			 }

		sheSyncSourceAvailabilityIndex OBJECT-TYPE
			SYNTAX SheSyncAvailabilityIndexType
			MAX-ACCESS read-only
			STATUS current
			DESCRIPTION
				"A unique value to identify a available synchronization source.
				Used as table index. Value 0 is not a valid index value for this table."
			::= { sheSyncSourceAvailabilityEntry 1 }

		
		sheSyncSourceAvailabilityType OBJECT-TYPE
			SYNTAX SheSyncSourceType
			MAX-ACCESS read-only
			STATUS current
			DESCRIPTION
				"The type of the synchronization source of the network element.
				
				Valid Parameters:
				sheInternalSyncSource         -> always available on CXU board
				sheT3orE1SyncSource           -> depends on used PM module, type could not exactly evaluated by NE
				sheBitsSyncSource             -> depends on used PM module
				sheEthernetSyncSource         -> depends on used CXU board type
				sheTimingOverPacketSyncSource -> depends on used CXU board type  (not supported by R2.8)
				sheT3SyncSource               -> depends on used PM module
				sheE1SyncSource               -> depends on used PM module
				
				The type T3 or E1 normaly depend on the used powermodule HW, but new module support
				both types of clock inputs and the system could not longer distinguish them.
				
				New with R2.8 maintenance:
				New powermoduls support a type selection for used input clock. Check new parameter
				of this table if the current clock support a SourceType switching. "
			::= { sheSyncSourceAvailabilityEntry 2 }

		
		sheSyncSourceAvailabilityHwUnitIndex OBJECT-TYPE
			SYNTAX PhysicalIndex
			MAX-ACCESS read-only
			STATUS current
			DESCRIPTION
				"Identifies the hardware unit that contains the synchronization source. "
			::= { sheSyncSourceAvailabilityEntry 3 }

		
		sheSyncSourceAvailabilityInterfaceNumber OBJECT-TYPE
			SYNTAX Unsigned32 (1..72)
			MAX-ACCESS read-only
			STATUS current
			DESCRIPTION
				"The number of the physical interface of the hardware unit.
				The interfaces are numbered vendor specific starting with 1 in ascending order.
				Synchronization interfaces may not be contained in the interface table."
			::= { sheSyncSourceAvailabilityEntry 4 }

		
		sheSyncSourceAvailabilityTypeSelectionPossible OBJECT-TYPE
			SYNTAX TruthValue
			MAX-ACCESS read-only
			STATUS current
			DESCRIPTION
				"This status parameter shows, if the type of this clock source entry is fix or could be modified 
				by configuration. 
				
				This is a new parameter with R2.8 maintenance, where a new power module was introduced,
				which supports a configurable input selector to choose the SourceClockType out of this range:
				sheBitsSyncSource or 
				sheT3SyncSource (default) or 
				sheE1SyncSource.
				
				Only if clock sources with parameter TypeSelectionPossible == TRUE are available in the system,
				the new controlRequest commands for type switching could be used."
			DEFVAL { false }
			::= { sheSyncSourceAvailabilityEntry 5 }

		
		sheSyncConformance OBJECT IDENTIFIER ::= { sheSyncObjects 6 }

		
		sheSyncCompliances OBJECT IDENTIFIER ::= { sheSyncConformance 1 }

		
--  this module
		sheSyncCompliance MODULE-COMPLIANCE
			STATUS current
			DESCRIPTION 
				"Description."
			MODULE -- this module
				MANDATORY-GROUPS { sheSyncConfigGroup, sheSyncConfigControlGroup, sheSyncNotificationsGroup }
			::= { sheSyncCompliances 1 }

		
		sheSyncGroups OBJECT IDENTIFIER ::= { sheSyncConformance 2 }

		
		sheSyncConfigGroup OBJECT-GROUP
			OBJECTS { sheSyncActiveClockSource, sheSyncWaitTimeToRestore, sheSyncSourcePriority, sheSyncSourceAlarmState, sheSyncSourceAlarmSeverityIndex, 
				sheSyncMode, sheSyncSourceSSMLevel, sheSyncSourceAvailabilityIndex, sheSyncSourceAvailabilityType, sheSyncSourceAvailabilityHwUnitIndex, 
				sheSyncLocalClockSSMLevel, sheSyncSourceAvailabilityTypeSelectionPossible, sheSyncSourceAvailabilityInterfaceNumber, sheSyncSourceSelectedAvailabilityIndex, sheSyncSourceSSMLevelRec
				 }
			STATUS current
			DESCRIPTION 
				"Description."
			::= { sheSyncGroups 1 }

		
		sheSyncConfigControlGroup OBJECT-GROUP
			OBJECTS { sheSyncCgControlReq, sheSyncCgControlStatus, sheSyncCgControlReqResult, sheSyncCgControlTimeStamp, sheSyncCgSourcePriority, 
				sheSyncCgSourceAlarmSeverityIndex, sheSyncCgSourceWaitTimeToRestore, sheSyncCgMode, sheSyncCgSourceSSMLevel, sheSyncCgSourceAvailabilityIndex
				 }
			STATUS current
			DESCRIPTION 
				"Description."
			::= { sheSyncGroups 2 }

		
		sheSyncNotificationsGroup NOTIFICATION-GROUP
			NOTIFICATIONS { sheSyncControlResult, sheSyncClockSourceModified, sheSyncWaitTimeToRestoreModified, sheSyncActiveClockSourceChanged, sheSyncClockSourceAlarm, 
				sheSyncUsedSyncSourcesModified, sheSyncGlobalsModified, sheSyncAvailabilityTableUpdated, sheSyncClockNoSSMInfoAlarm, sheSyncAvailableSyncSourceTypeModified, 
				sheSyncSourceModifiedReqResult }
			STATUS current
			DESCRIPTION 
				"Description."
			::= { sheSyncGroups 3 }

		
		sheSyncObsoleteGroup OBJECT-GROUP
			OBJECTS { sheSyncSourceType, sheSyncSourceHwUnitIndex, sheSyncSourceInterfaceNumber }
			STATUS obsolete
			DESCRIPTION 
				"This parameters are not longer supported by SHE R3.0."
			::= { sheSyncGroups 4 }

		
	
	END

--
-- she-sync-mib.mib
--
