--  Title:    RTDdx_G39v2.MIB 
--  Version:  v3.9 for SNMPv2c
-- 
--  Copyright @ 2011 DPS Inc. All Rights Reserved 
-- 
--  This MIB defines supplemental objects for the RTDdx points
-- 
-- 

DPS-MIB-RTDX-G39-V2 DEFINITIONS ::= BEGIN 

IMPORTS
	dpsRTUv2,
	dpsRTUv2DateTime,
	dpsRTUv2APort,
	dpsRTUv2CAddress,
	dpsRTUv2ADisplay,
	dpsRTUv2APoint,
	dpsRTUv2APntDesc,
	dpsRTUv2AState
		FROM DPS-MIB-V38-V2
	dpsAlarmControl
		FROM DPS-MIB-V38
	sysDescr,
	sysLocation
		FROM SNMPv2-MIB
	MODULE-IDENTITY,
	NOTIFICATION-TYPE
		FROM SNMPv2-SMI;

dpsRTUrtdV2MI	MODULE-IDENTITY
	LAST-UPDATED	"201208081200Z"  --August 8th, 2012 12:00 PDT
	ORGANIZATION	"DPS Telecom"
	CONTACT-INFO	"DPS Support Team 
			Web 	http://dpstele.com/support
			E-Mail 	support@dpstele.com
			Phone	(559)454-1600"
	DESCRIPTION	"Second generation MIB for DPS Telecom products"

	REVISION	"201208081200Z"  --August 8th, 2012 12:00 PDT
	DESCRIPTION	"Modified for proper smi/asn.1 formatting and structure (CBH)"

	::= { dpsAlarmControl 6 }

--RTDdx 1 Channel 1
dpsRTUv2p10001Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 1 Minor Under is set." 
	::= { dpsRTUv2 10001 }

dpsRTUv2p11001Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 1 Minor Under is clear." 
	::= { dpsRTUv2 11001 }
	
dpsRTUv2p10002Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 1 Minor Over is set." 
	::= { dpsRTUv2 10002 }

dpsRTUv2p11002Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 1 Minor Over is clear." 
	::= { dpsRTUv2 11002 }
	
dpsRTUv2p10003Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 1 Major Under is set." 
	::= { dpsRTUv2 10003 }

dpsRTUv2p11003Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 1 Major Under is clear." 
	::= { dpsRTUv2 11003 }

dpsRTUv2p10004Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 1 Major Over is set." 
	::= { dpsRTUv2 10004 }

dpsRTUv2p11004Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 1 Major Over is clear." 
	::= { dpsRTUv2 11004 }

dpsRTUv2p10005Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 1 RTD Sensor is not detected." 
	::= { dpsRTUv2 10005 }

dpsRTUv2p11005Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 1 RTD Sensor is detected." 
	::= { dpsRTUv2 11005 }

--RTDdx 1 Channel 2
dpsRTUv2p10006Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 2 Minor Under is set." 
	::= { dpsRTUv2 10006 }

dpsRTUv2p11006Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 2 Minor Under is clear." 
	::= { dpsRTUv2 11006 }
	
dpsRTUv2p10007Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 2 Minor Over is set." 
	::= { dpsRTUv2 10007 }

dpsRTUv2p11007Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 2 Minor Over is clear." 
	::= { dpsRTUv2 11007 }
	
dpsRTUv2p10008Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 2 Major Under is set." 
	::= { dpsRTUv2 10008 }

dpsRTUv2p11008Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 2 Major Under is clear." 
	::= { dpsRTUv2 11008 }

dpsRTUv2p10009Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 2 Major Over is set." 
	::= { dpsRTUv2 10009 }

dpsRTUv2p11009Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 2 Major Over is clear." 
	::= { dpsRTUv2 11009 }

dpsRTUv2p10010Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 2 RTD Sensor is not detected." 
	::= { dpsRTUv2 10010 }

dpsRTUv2p11010Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 2 RTD Sensor is detected." 
	::= { dpsRTUv2 11010 }

--RTDdx 1 Channel 3
dpsRTUv2p10011Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 3 Minor Under is set." 
	::= { dpsRTUv2 10011 }

dpsRTUv2p11011Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 3 Minor Under is clear." 
	::= { dpsRTUv2 11011 }
	
dpsRTUv2p10012Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 3 Minor Over is set." 
	::= { dpsRTUv2 10012 }

dpsRTUv2p11012Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 3 Minor Over is clear." 
	::= { dpsRTUv2 11012 }
	
dpsRTUv2p10013Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 3 Major Under is set." 
	::= { dpsRTUv2 10013 }

dpsRTUv2p11013Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 3 Major Under is clear." 
	::= { dpsRTUv2 11013 }

dpsRTUv2p10014Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 3 Major Over is set." 
	::= { dpsRTUv2 10014 }

dpsRTUv2p11014Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 3 Major Over is clear." 
	::= { dpsRTUv2 11014 }

dpsRTUv2p10015Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 3 RTD Sensor is not detected." 
	::= { dpsRTUv2 10015 }

dpsRTUv2p11015Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 3 RTD Sensor is detected." 
	::= { dpsRTUv2 11015 }

--RTDdx 1 Channel 4
dpsRTUv2p10016Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 4 Minor Under is set." 
	::= { dpsRTUv2 10016 }

dpsRTUv2p11016Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 4 Minor Under is clear." 
	::= { dpsRTUv2 11016 }
	
dpsRTUv2p10017Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 4 Minor Over is set." 
	::= { dpsRTUv2 10017 }

dpsRTUv2p11017Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 4 Minor Over is clear." 
	::= { dpsRTUv2 11017 }
	
dpsRTUv2p10018Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 4 Major Under is set." 
	::= { dpsRTUv2 10018 }

dpsRTUv2p11018Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 4 Major Under is clear." 
	::= { dpsRTUv2 11018 }

dpsRTUv2p10019Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 4 Major Over is set." 
	::= { dpsRTUv2 10019 }

dpsRTUv2p11019Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 4 Major Over is clear." 
	::= { dpsRTUv2 11019 }

dpsRTUv2p10020Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 4 RTD Sensor is not detected." 
	::= { dpsRTUv2 10020 }

dpsRTUv2p11020Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 4 RTD Sensor is detected." 
	::= { dpsRTUv2 11020 }

--RTDdx 1 Channel 5
dpsRTUv2p10021Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 5 Minor Under is set." 
	::= { dpsRTUv2 10021 }

dpsRTUv2p11021Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 5 Minor Under is clear." 
	::= { dpsRTUv2 11021 }
	
dpsRTUv2p10022Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 5 Minor Over is set." 
	::= { dpsRTUv2 10022 }

dpsRTUv2p11022Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 5 Minor Over is clear." 
	::= { dpsRTUv2 11022 }
	
dpsRTUv2p10023Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 5 Major Under is set." 
	::= { dpsRTUv2 10023 }

dpsRTUv2p11023Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 5 Major Under is clear." 
	::= { dpsRTUv2 11023 }

dpsRTUv2p10024Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 5 Major Over is set." 
	::= { dpsRTUv2 10024 }

dpsRTUv2p11024Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 5 Major Over is clear." 
	::= { dpsRTUv2 11024 }

dpsRTUv2p10025Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 5 RTD Sensor is not detected." 
	::= { dpsRTUv2 10025 }

dpsRTUv2p11025Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 5 RTD Sensor is detected." 
	::= { dpsRTUv2 11025 }

--RTDdx 1 Channel 6
dpsRTUv2p10026Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 6 Minor Under is set." 
	::= { dpsRTUv2 10026 }

dpsRTUv2p11026Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 6 Minor Under is clear." 
	::= { dpsRTUv2 11026 }
	
dpsRTUv2p10027Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 6 Minor Over is set." 
	::= { dpsRTUv2 10027 }

dpsRTUv2p11027Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 6 Minor Over is clear." 
	::= { dpsRTUv2 11027 }
	
dpsRTUv2p10028Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 6 Major Under is set." 
	::= { dpsRTUv2 10028 }

dpsRTUv2p11028Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 6 Major Under is clear." 
	::= { dpsRTUv2 11028 }

dpsRTUv2p10029Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 6 Major Over is set." 
	::= { dpsRTUv2 10029 }

dpsRTUv2p11029Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 6 Major Over is clear." 
	::= { dpsRTUv2 11029 }

dpsRTUv2p10030Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 6 RTD Sensor is not detected." 
	::= { dpsRTUv2 10030 }

dpsRTUv2p11030Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 6 RTD Sensor is detected." 
	::= { dpsRTUv2 11030 }

--RTDdx 1 Channel 7
dpsRTUv2p10031Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 7 Minor Under is set." 
	::= { dpsRTUv2 10031 }

dpsRTUv2p11031Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 7 Minor Under is clear." 
	::= { dpsRTUv2 11031 }
	
dpsRTUv2p10032Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 7 Minor Over is set." 
	::= { dpsRTUv2 10032 }

dpsRTUv2p11032Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 7 Minor Over is clear." 
	::= { dpsRTUv2 11032 }
	
dpsRTUv2p10033Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 7 Major Under is set." 
	::= { dpsRTUv2 10033 }

dpsRTUv2p11033Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 7 Major Under is clear." 
	::= { dpsRTUv2 11033 }

dpsRTUv2p10034Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 7 Major Over is set." 
	::= { dpsRTUv2 10034 }

dpsRTUv2p11034Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 7 Major Over is clear." 
	::= { dpsRTUv2 11034 }

dpsRTUv2p10035Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 7 RTD Sensor is not detected." 
	::= { dpsRTUv2 10035 }

dpsRTUv2p11035Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 7 RTD Sensor is detected." 
	::= { dpsRTUv2 11035 }
	
--RTDdx 1 Channel 8
dpsRTUv2p10036Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 8 Minor Under is set." 
	::= { dpsRTUv2 10036 }

dpsRTUv2p11036Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 8 Minor Under is clear." 
	::= { dpsRTUv2 11036 }
	
dpsRTUv2p10037Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 8 Minor Over is set." 
	::= { dpsRTUv2 10037 }

dpsRTUv2p11037Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 8 Minor Over is clear." 
	::= { dpsRTUv2 11037 }
	
dpsRTUv2p10038Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 8 Major Under is set." 
	::= { dpsRTUv2 10038 }

dpsRTUv2p11038Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 8 Major Under is clear." 
	::= { dpsRTUv2 11038 }

dpsRTUv2p10039Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 8 Major Over is set." 
	::= { dpsRTUv2 10039 }

dpsRTUv2p11039Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 8 Major Over is clear." 
	::= { dpsRTUv2 11039 }

dpsRTUv2p10040Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 8 RTD Sensor is not detected." 
	::= { dpsRTUv2 10040 }

dpsRTUv2p11040Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 8 RTD Sensor is detected." 
	::= { dpsRTUv2 11040 }
	
--RTDdx 1 Channel 9
dpsRTUv2p10041Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 9 Minor Under is set." 
	::= { dpsRTUv2 10041 }

dpsRTUv2p11041Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 9 Minor Under is clear." 
	::= { dpsRTUv2 11041 }
	
dpsRTUv2p10042Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 9 Minor Over is set." 
	::= { dpsRTUv2 10042 }

dpsRTUv2p11042Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 9 Minor Over is clear." 
	::= { dpsRTUv2 11042 }
	
dpsRTUv2p10043Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 9 Major Under is set." 
	::= { dpsRTUv2 10043 }

dpsRTUv2p11043Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 9 Major Under is clear." 
	::= { dpsRTUv2 11043 }

dpsRTUv2p10044Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 9 Major Over is set." 
	::= { dpsRTUv2 10044 }

dpsRTUv2p11044Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 9 Major Over is clear." 
	::= { dpsRTUv2 11044 }

dpsRTUv2p10045Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 9 RTD Sensor is not detected." 
	::= { dpsRTUv2 10045 }

dpsRTUv2p11045Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 9 RTD Sensor is detected." 
	::= { dpsRTUv2 11045 }
	
--RTDdx 1 Channel 10
dpsRTUv2p10046Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 10 Minor Under is set." 
	::= { dpsRTUv2 10046 }

dpsRTUv2p11046Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 10 Minor Under is clear." 
	::= { dpsRTUv2 11046 }
	
dpsRTUv2p10047Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 10 Minor Over is set." 
	::= { dpsRTUv2 10047 }

dpsRTUv2p11047Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 10 Minor Over is clear." 
	::= { dpsRTUv2 11047 }
	
dpsRTUv2p10048Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 10 Major Under is set." 
	::= { dpsRTUv2 10048 }

dpsRTUv2p11048Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 10 Major Under is clear." 
	::= { dpsRTUv2 11048 }

dpsRTUv2p10049Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 10 Major Over is set." 
	::= { dpsRTUv2 10049 }

dpsRTUv2p11049Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 10 Major Over is clear." 
	::= { dpsRTUv2 11049 }

dpsRTUv2p10050Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 10 RTD Sensor is not detected." 
	::= { dpsRTUv2 10050 }

dpsRTUv2p11050Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 10 RTD Sensor is detected." 
	::= { dpsRTUv2 11050 }

--RTDdx 1 Channel 11
dpsRTUv2p10051Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 11 Minor Under is set." 
	::= { dpsRTUv2 10051 }

dpsRTUv2p11051Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 11 Minor Under is clear." 
	::= { dpsRTUv2 11051 }
	
dpsRTUv2p10052Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 11 Minor Over is set." 
	::= { dpsRTUv2 10052 }

dpsRTUv2p11052Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 11 Minor Over is clear." 
	::= { dpsRTUv2 11052 }
	
dpsRTUv2p10053Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 11 Major Under is set." 
	::= { dpsRTUv2 10053 }

dpsRTUv2p11053Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 11 Major Under is clear." 
	::= { dpsRTUv2 11053 }

dpsRTUv2p10054Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 11 Major Over is set." 
	::= { dpsRTUv2 10054 }

dpsRTUv2p11054Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 11 Major Over is clear." 
	::= { dpsRTUv2 11054 }

dpsRTUv2p10055Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 11 RTD Sensor is not detected." 
	::= { dpsRTUv2 10055 }

dpsRTUv2p11055Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 11 RTD Sensor is detected." 
	::= { dpsRTUv2 11055 }
	
--RTDdx 1 Channel 12
dpsRTUv2p10056Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 12 Minor Under is set." 
	::= { dpsRTUv2 10056 }

dpsRTUv2p11056Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 12 Minor Under is clear." 
	::= { dpsRTUv2 11056 }
	
dpsRTUv2p10057Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 12 Minor Over is set." 
	::= { dpsRTUv2 10057 }

dpsRTUv2p11057Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 12 Minor Over is clear." 
	::= { dpsRTUv2 11057 }
	
dpsRTUv2p10058Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 12 Major Under is set." 
	::= { dpsRTUv2 10058 }

dpsRTUv2p11058Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 12 Major Under is clear." 
	::= { dpsRTUv2 11058 }

dpsRTUv2p10059Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 12 Major Over is set." 
	::= { dpsRTUv2 10059 }

dpsRTUv2p11059Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 12 Major Over is clear." 
	::= { dpsRTUv2 11059 }

dpsRTUv2p10060Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 12 RTD Sensor is not detected." 
	::= { dpsRTUv2 10060 }

dpsRTUv2p11060Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 12 RTD Sensor is detected." 
	::= { dpsRTUv2 11060 }
	
--RTDdx 1 Channel 13
dpsRTUv2p10061Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 13 Minor Under is set." 
	::= { dpsRTUv2 10061 }

dpsRTUv2p11061Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 13 Minor Under is clear." 
	::= { dpsRTUv2 11061 }
	
dpsRTUv2p10062Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 13 Minor Over is set." 
	::= { dpsRTUv2 10062 }

dpsRTUv2p11062Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 13 Minor Over is clear." 
	::= { dpsRTUv2 11062 }
	
dpsRTUv2p10063Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 13 Major Under is set." 
	::= { dpsRTUv2 10063 }

dpsRTUv2p11063Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 13 Major Under is clear." 
	::= { dpsRTUv2 11063 }

dpsRTUv2p10064Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 13 Major Over is set." 
	::= { dpsRTUv2 10064 }

dpsRTUv2p11064Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 13 Major Over is clear." 
	::= { dpsRTUv2 11064 }

dpsRTUv2p10065Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 13 RTD Sensor is not detected." 
	::= { dpsRTUv2 10065 }

dpsRTUv2p11065Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 13 RTD Sensor is detected." 
	::= { dpsRTUv2 11065 }
	
--RTDdx 1 Channel 14
dpsRTUv2p10066Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 14 Minor Under is set." 
	::= { dpsRTUv2 10066 }

dpsRTUv2p11066Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 14 Minor Under is clear." 
	::= { dpsRTUv2 11066 }
	
dpsRTUv2p10067Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 14 Minor Over is set." 
	::= { dpsRTUv2 10067 }

dpsRTUv2p11067Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 14 Minor Over is clear." 
	::= { dpsRTUv2 11067 }
	
dpsRTUv2p10068Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 14 Major Under is set." 
	::= { dpsRTUv2 10068 }

dpsRTUv2p11068Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 14 Major Under is clear." 
	::= { dpsRTUv2 11068 }

dpsRTUv2p10069Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 14 Major Over is set." 
	::= { dpsRTUv2 10069 }

dpsRTUv2p11069Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 14 Major Over is clear." 
	::= { dpsRTUv2 11069 }

dpsRTUv2p10070Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 14 RTD Sensor is not detected." 
	::= { dpsRTUv2 10070 }

dpsRTUv2p11070Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 14 RTD Sensor is detected." 
	::= { dpsRTUv2 11070 }

--RTDdx 1 Channel 15
dpsRTUv2p10071Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 15 Minor Under is set." 
	::= { dpsRTUv2 10071 }

dpsRTUv2p11071Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 15 Minor Under is clear." 
	::= { dpsRTUv2 11071 }
	
dpsRTUv2p10072Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 15 Minor Over is set." 
	::= { dpsRTUv2 10072 }

dpsRTUv2p11072Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 15 Minor Over is clear." 
	::= { dpsRTUv2 11072 }
	
dpsRTUv2p10073Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 15 Major Under is set." 
	::= { dpsRTUv2 10073 }

dpsRTUv2p11073Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 15 Major Under is clear." 
	::= { dpsRTUv2 11073 }

dpsRTUv2p10074Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 15 Major Over is set." 
	::= { dpsRTUv2 10074 }

dpsRTUv2p11074Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 15 Major Over is clear." 
	::= { dpsRTUv2 11074 }

dpsRTUv2p10075Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 15 RTD Sensor is not detected." 
	::= { dpsRTUv2 10075 }

dpsRTUv2p11075Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 15 RTD Sensor is detected." 
	::= { dpsRTUv2 11075 }
	
--RTDdx 1 Channel 16
dpsRTUv2p10076Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 16 Minor Under is set." 
	::= { dpsRTUv2 10076 }

dpsRTUv2p11076Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 16 Minor Under is clear." 
	::= { dpsRTUv2 11076 }
	
dpsRTUv2p10077Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 16 Minor Over is set." 
	::= { dpsRTUv2 10077 }

dpsRTUv2p11077Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 16 Minor Over is clear." 
	::= { dpsRTUv2 11077 }
	
dpsRTUv2p10078Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 16 Major Under is set." 
	::= { dpsRTUv2 10078 }

dpsRTUv2p11078Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 16 Major Under is clear." 
	::= { dpsRTUv2 11078 }

dpsRTUv2p10079Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 16 Major Over is set." 
	::= { dpsRTUv2 10079 }

dpsRTUv2p11079Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 16 Major Over is clear." 
	::= { dpsRTUv2 11079 }

dpsRTUv2p10080Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 16 RTD Sensor is not detected." 
	::= { dpsRTUv2 10080 }

dpsRTUv2p11080Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 16 RTD Sensor is detected." 
	::= { dpsRTUv2 11080 }
	
--RTDdx 1 Channel 17
dpsRTUv2p10081Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 17 Minor Under is set." 
	::= { dpsRTUv2 10081 }

dpsRTUv2p11081Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 17 Minor Under is clear." 
	::= { dpsRTUv2 11081 }
	
dpsRTUv2p10082Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 17 Minor Over is set." 
	::= { dpsRTUv2 10082 }

dpsRTUv2p11082Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 17 Minor Over is clear." 
	::= { dpsRTUv2 11082 }
	
dpsRTUv2p10083Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 17 Major Under is set." 
	::= { dpsRTUv2 10083 }

dpsRTUv2p11083Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 17 Major Under is clear." 
	::= { dpsRTUv2 11083 }

dpsRTUv2p10084Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 17 Major Over is set." 
	::= { dpsRTUv2 10084 }

dpsRTUv2p11084Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 17 Major Over is clear." 
	::= { dpsRTUv2 11084 }

dpsRTUv2p10085Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 17 RTD Sensor is not detected." 
	::= { dpsRTUv2 10085 }

dpsRTUv2p11085Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 17 RTD Sensor is detected." 
	::= { dpsRTUv2 11085 }
	
--RTDdx 1 Channel 18
dpsRTUv2p10086Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 18 Minor Under is set." 
	::= { dpsRTUv2 10086 }

dpsRTUv2p11086Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 18 Minor Under is clear." 
	::= { dpsRTUv2 11086 }
	
dpsRTUv2p10087Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 18 Minor Over is set." 
	::= { dpsRTUv2 10087 }

dpsRTUv2p11087Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 18 Minor Over is clear." 
	::= { dpsRTUv2 11087 }
	
dpsRTUv2p10088Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 18 Major Under is set." 
	::= { dpsRTUv2 10088 }

dpsRTUv2p11088Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 18 Major Under is clear." 
	::= { dpsRTUv2 11088 }

dpsRTUv2p10089Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 18 Major Over is set." 
	::= { dpsRTUv2 10089 }

dpsRTUv2p11089Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 18 Major Over is clear." 
	::= { dpsRTUv2 11089 }

dpsRTUv2p10090Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 18 RTD Sensor is not detected." 
	::= { dpsRTUv2 10090 }

dpsRTUv2p11090Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 18 RTD Sensor is detected." 
	::= { dpsRTUv2 11090 }

--RTDdx 1 Channel 19
dpsRTUv2p10091Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 19 Minor Under is set." 
	::= { dpsRTUv2 10091 }

dpsRTUv2p11091Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 19 Minor Under is clear." 
	::= { dpsRTUv2 11091 }
	
dpsRTUv2p10092Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 19 Minor Over is set." 
	::= { dpsRTUv2 10092 }

dpsRTUv2p11092Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 19 Minor Over is clear." 
	::= { dpsRTUv2 11092 }
	
dpsRTUv2p10093Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 19 Major Under is set." 
	::= { dpsRTUv2 10093 }

dpsRTUv2p11093Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 19 Major Under is clear." 
	::= { dpsRTUv2 11093 }

dpsRTUv2p10094Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 19 Major Over is set." 
	::= { dpsRTUv2 10094 }

dpsRTUv2p11094Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 19 Major Over is clear." 
	::= { dpsRTUv2 11094 }

dpsRTUv2p10095Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 19 RTD Sensor is not detected." 
	::= { dpsRTUv2 10095 }

dpsRTUv2p11095Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 19 RTD Sensor is detected." 
	::= { dpsRTUv2 11095 }
	
--RTDdx 1 Channel 20
dpsRTUv2p10096Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 20 Minor Under is set." 
	::= { dpsRTUv2 10096 }

dpsRTUv2p11096Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 20 Minor Under is clear." 
	::= { dpsRTUv2 11096 }
	
dpsRTUv2p10097Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 20 Minor Over is set." 
	::= { dpsRTUv2 10097 }

dpsRTUv2p11097Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 20 Minor Over is clear." 
	::= { dpsRTUv2 11097 }
	
dpsRTUv2p10098Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 20 Major Under is set." 
	::= { dpsRTUv2 10098 }

dpsRTUv2p11098Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 20 Major Under is clear." 
	::= { dpsRTUv2 11098 }

dpsRTUv2p10099Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 20 Major Over is set." 
	::= { dpsRTUv2 10099 }

dpsRTUv2p11099Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 20 Major Over is clear." 
	::= { dpsRTUv2 11099 }

dpsRTUv2p10100Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 20 RTD Sensor is not detected." 
	::= { dpsRTUv2 10100 }

dpsRTUv2p11100Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 20 RTD Sensor is detected." 
	::= { dpsRTUv2 11100 }
	
--RTDdx 1 Channel 21
dpsRTUv2p10101Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 21 Minor Under is set." 
	::= { dpsRTUv2 10101 }

dpsRTUv2p11101Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 21 Minor Under is clear." 
	::= { dpsRTUv2 11101 }
	
dpsRTUv2p10102Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 21 Minor Over is set." 
	::= { dpsRTUv2 10102 }

dpsRTUv2p11102Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 21 Minor Over is clear." 
	::= { dpsRTUv2 11102 }
	
dpsRTUv2p10103Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 21 Major Under is set." 
	::= { dpsRTUv2 10103 }

dpsRTUv2p11103Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 21 Major Under is clear." 
	::= { dpsRTUv2 11103 }

dpsRTUv2p10104Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 21 Major Over is set." 
	::= { dpsRTUv2 10104 }

dpsRTUv2p11104Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 21 Major Over is clear." 
	::= { dpsRTUv2 11104 }

dpsRTUv2p10105Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 21 RTD Sensor is not detected." 
	::= { dpsRTUv2 10105 }

dpsRTUv2p11105Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 21 RTD Sensor is detected." 
	::= { dpsRTUv2 11105 }

--RTDdx 1 Channel 22
dpsRTUv2p10106Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 22 Minor Under is set." 
	::= { dpsRTUv2 10106 }

dpsRTUv2p11106Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 22 Minor Under is clear." 
	::= { dpsRTUv2 11106 }
	
dpsRTUv2p10107Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 22 Minor Over is set." 
	::= { dpsRTUv2 10107 }

dpsRTUv2p11107Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 22 Minor Over is clear." 
	::= { dpsRTUv2 11107 }
	
dpsRTUv2p10108Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 22 Major Under is set." 
	::= { dpsRTUv2 10108 }

dpsRTUv2p11108Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 22 Major Under is clear." 
	::= { dpsRTUv2 11108 }

dpsRTUv2p10109Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 22 Major Over is set." 
	::= { dpsRTUv2 10109 }

dpsRTUv2p11109Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 22 Major Over is clear." 
	::= { dpsRTUv2 11109 }

dpsRTUv2p10110Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 22 RTD Sensor is not detected." 
	::= { dpsRTUv2 10110 }

dpsRTUv2p11110Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 22 RTD Sensor is detected." 
	::= { dpsRTUv2 11110 }
	
--RTDdx 1 Channel 23
dpsRTUv2p10111Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 23 Minor Under is set." 
	::= { dpsRTUv2 10111 }

dpsRTUv2p11111Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 23 Minor Under is clear." 
	::= { dpsRTUv2 11111 }
	
dpsRTUv2p10112Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 23 Minor Over is set." 
	::= { dpsRTUv2 10112 }

dpsRTUv2p11112Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 23 Minor Over is clear." 
	::= { dpsRTUv2 11112 }
	
dpsRTUv2p10113Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 23 Major Under is set." 
	::= { dpsRTUv2 10113 }

dpsRTUv2p11113Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 23 Major Under is clear." 
	::= { dpsRTUv2 11113 }

dpsRTUv2p10114Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 23 Major Over is set." 
	::= { dpsRTUv2 10114 }

dpsRTUv2p11114Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 23 Major Over is clear." 
	::= { dpsRTUv2 11114 }

dpsRTUv2p10115Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 23 RTD Sensor is not detected." 
	::= { dpsRTUv2 10115 }

dpsRTUv2p11115Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 23 RTD Sensor is detected." 
	::= { dpsRTUv2 11115 }
	
--RTDdx 1 Channel 24
dpsRTUv2p10116Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 24 Minor Under is set." 
	::= { dpsRTUv2 10116 }

dpsRTUv2p11116Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 24 Minor Under is clear." 
	::= { dpsRTUv2 11116 }
	
dpsRTUv2p10117Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 24 Minor Over is set." 
	::= { dpsRTUv2 10117 }

dpsRTUv2p11117Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 24 Minor Over is clear." 
	::= { dpsRTUv2 11117 }
	
dpsRTUv2p10118Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 24 Major Under is set." 
	::= { dpsRTUv2 10118 }

dpsRTUv2p11118Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 24 Major Under is clear." 
	::= { dpsRTUv2 11118 }

dpsRTUv2p10119Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 24 Major Over is set." 
	::= { dpsRTUv2 10119 }

dpsRTUv2p11119Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 24 Major Over is clear." 
	::= { dpsRTUv2 11119 }

dpsRTUv2p10120Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 24 RTD Sensor is not detected." 
	::= { dpsRTUv2 10120 }

dpsRTUv2p11120Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 24 RTD Sensor is detected." 
	::= { dpsRTUv2 11120 }
	
--RTDdx 1 Channel 25
dpsRTUv2p10121Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 25 Minor Under is set." 
	::= { dpsRTUv2 10121 }

dpsRTUv2p11121Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 25 Minor Under is clear." 
	::= { dpsRTUv2 11121 }
	
dpsRTUv2p10122Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 25 Minor Over is set." 
	::= { dpsRTUv2 10122 }

dpsRTUv2p11122Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 25 Minor Over is clear." 
	::= { dpsRTUv2 11122 }
	
dpsRTUv2p10123Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 25 Major Under is set." 
	::= { dpsRTUv2 10123 }

dpsRTUv2p11123Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 25 Major Under is clear." 
	::= { dpsRTUv2 11123 }

dpsRTUv2p10124Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 25 Major Over is set." 
	::= { dpsRTUv2 10124 }

dpsRTUv2p11124Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 25 Major Over is clear." 
	::= { dpsRTUv2 11124 }

dpsRTUv2p10125Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 25 RTD Sensor is not detected." 
	::= { dpsRTUv2 10125 }

dpsRTUv2p11125Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 25 RTD Sensor is detected." 
	::= { dpsRTUv2 11125 }
	
--RTDdx 1 Channel 26
dpsRTUv2p10126Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 26 Minor Under is set." 
	::= { dpsRTUv2 10126 }

dpsRTUv2p11126Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 26 Minor Under is clear." 
	::= { dpsRTUv2 11126 }
	
dpsRTUv2p10127Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 26 Minor Over is set." 
	::= { dpsRTUv2 10127 }

dpsRTUv2p11127Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 26 Minor Over is clear." 
	::= { dpsRTUv2 11127 }
	
dpsRTUv2p10128Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 26 Major Under is set." 
	::= { dpsRTUv2 10128 }

dpsRTUv2p11128Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 26 Major Under is clear." 
	::= { dpsRTUv2 11128 }

dpsRTUv2p10129Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 26 Major Over is set." 
	::= { dpsRTUv2 10129 }

dpsRTUv2p11129Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 26 Major Over is clear." 
	::= { dpsRTUv2 11129 }

dpsRTUv2p10130Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 26 RTD Sensor is not detected." 
	::= { dpsRTUv2 10130 }

dpsRTUv2p11130Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 26 RTD Sensor is detected." 
	::= { dpsRTUv2 11130 }
	
--RTDdx 1 Channel 27
dpsRTUv2p10131Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 27 Minor Under is set." 
	::= { dpsRTUv2 10131 }

dpsRTUv2p11131Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 27 Minor Under is clear." 
	::= { dpsRTUv2 11131 }
	
dpsRTUv2p10132Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 27 Minor Over is set." 
	::= { dpsRTUv2 10132 }

dpsRTUv2p11132Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 27 Minor Over is clear." 
	::= { dpsRTUv2 11132 }
	
dpsRTUv2p10133Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 27 Major Under is set." 
	::= { dpsRTUv2 10133 }

dpsRTUv2p11133Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 27 Major Under is clear." 
	::= { dpsRTUv2 11133 }

dpsRTUv2p10134Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 27 Major Over is set." 
	::= { dpsRTUv2 10134 }

dpsRTUv2p11134Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 27 Major Over is clear." 
	::= { dpsRTUv2 11134 }

dpsRTUv2p10135Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 27 RTD Sensor is not detected." 
	::= { dpsRTUv2 10135 }

dpsRTUv2p11135Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 27 RTD Sensor is detected." 
	::= { dpsRTUv2 11135 }
	
--RTDdx 1 Channel 28
dpsRTUv2p10136Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 28 Minor Under is set." 
	::= { dpsRTUv2 10136 }

dpsRTUv2p11136Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 28 Minor Under is clear." 
	::= { dpsRTUv2 11136 }
	
dpsRTUv2p10137Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 28 Minor Over is set." 
	::= { dpsRTUv2 10137 }

dpsRTUv2p11137Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 28 Minor Over is clear." 
	::= { dpsRTUv2 11137 }
	
dpsRTUv2p10138Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 28 Major Under is set." 
	::= { dpsRTUv2 10138 }

dpsRTUv2p11138Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 28 Major Under is clear." 
	::= { dpsRTUv2 11138 }

dpsRTUv2p10139Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 28 Major Over is set." 
	::= { dpsRTUv2 10139 }

dpsRTUv2p11139Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 28 Major Over is clear." 
	::= { dpsRTUv2 11139 }

dpsRTUv2p10140Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 28 RTD Sensor is not detected." 
	::= { dpsRTUv2 10140 }

dpsRTUv2p11140Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 28 RTD Sensor is detected." 
	::= { dpsRTUv2 11140 }
	
--RTDdx 1 Channel 29
dpsRTUv2p10141Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 29 Minor Under is set." 
	::= { dpsRTUv2 10141 }

dpsRTUv2p11141Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 29 Minor Under is clear." 
	::= { dpsRTUv2 11141 }
	
dpsRTUv2p10142Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 29 Minor Over is set." 
	::= { dpsRTUv2 10142 }

dpsRTUv2p11142Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 29 Minor Over is clear." 
	::= { dpsRTUv2 11142 }
	
dpsRTUv2p10143Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 29 Major Under is set." 
	::= { dpsRTUv2 10143 }

dpsRTUv2p11143Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 29 Major Under is clear." 
	::= { dpsRTUv2 11143 }

dpsRTUv2p10144Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 29 Major Over is set." 
	::= { dpsRTUv2 10144 }

dpsRTUv2p11144Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 29 Major Over is clear." 
	::= { dpsRTUv2 11144 }

dpsRTUv2p10145Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 29 RTD Sensor is not detected." 
	::= { dpsRTUv2 10145 }

dpsRTUv2p11145Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 29 RTD Sensor is detected." 
	::= { dpsRTUv2 11145 }

--RTDdx 1 Channel 30
dpsRTUv2p10146Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 30 Minor Under is set." 
	::= { dpsRTUv2 10146 }

dpsRTUv2p11146Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 30 Minor Under is clear." 
	::= { dpsRTUv2 11146 }
	
dpsRTUv2p10147Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 30 Minor Over is set." 
	::= { dpsRTUv2 10147 }

dpsRTUv2p11147Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 30 Minor Over is clear." 
	::= { dpsRTUv2 11147 }
	
dpsRTUv2p10148Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 30 Major Under is set." 
	::= { dpsRTUv2 10148 }

dpsRTUv2p11148Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 30 Major Under is clear." 
	::= { dpsRTUv2 11148 }

dpsRTUv2p10149Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 30 Major Over is set." 
	::= { dpsRTUv2 10149 }

dpsRTUv2p11149Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 30 Major Over is clear." 
	::= { dpsRTUv2 11149 }

dpsRTUv2p10150Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 30 RTD Sensor is not detected." 
	::= { dpsRTUv2 10150 }

dpsRTUv2p11150Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 30 RTD Sensor is detected." 
	::= { dpsRTUv2 11150 }
	
--RTDdx 1 Channel 31
dpsRTUv2p10151Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 31 Minor Under is set." 
	::= { dpsRTUv2 10151 }

dpsRTUv2p11151Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 31 Minor Under is clear." 
	::= { dpsRTUv2 11151 }
	
dpsRTUv2p10152Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 31 Minor Over is set." 
	::= { dpsRTUv2 10152 }

dpsRTUv2p11152Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 31 Minor Over is clear." 
	::= { dpsRTUv2 11152 }
	
dpsRTUv2p10153Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 31 Major Under is set." 
	::= { dpsRTUv2 10153 }

dpsRTUv2p11153Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 31 Major Under is clear." 
	::= { dpsRTUv2 11153 }

dpsRTUv2p10154Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 31 Major Over is set." 
	::= { dpsRTUv2 10154 }

dpsRTUv2p11154Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 31 Major Over is clear." 
	::= { dpsRTUv2 11154 }

dpsRTUv2p10155Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 31 RTD Sensor is not detected." 
	::= { dpsRTUv2 10155 }

dpsRTUv2p11155Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 31 RTD Sensor is detected." 
	::= { dpsRTUv2 11155 }
	
--RTDdx 1 Channel 32
dpsRTUv2p10156Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 32 Minor Under is set." 
	::= { dpsRTUv2 10156 }

dpsRTUv2p11156Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 32 Minor Under is clear." 
	::= { dpsRTUv2 11156 }
	
dpsRTUv2p10157Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 32 Minor Over is set." 
	::= { dpsRTUv2 10157 }

dpsRTUv2p11157Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 32 Minor Over is clear." 
	::= { dpsRTUv2 11157 }
	
dpsRTUv2p10158Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 32 Major Under is set." 
	::= { dpsRTUv2 10158 }

dpsRTUv2p11158Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 32 Major Under is clear." 
	::= { dpsRTUv2 11158 }

dpsRTUv2p10159Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 32 Major Over is set." 
	::= { dpsRTUv2 10159 }

dpsRTUv2p11159Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 32 Major Over is clear." 
	::= { dpsRTUv2 11159 }

dpsRTUv2p10160Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 32 RTD Sensor is not detected." 
	::= { dpsRTUv2 10160 }

dpsRTUv2p11160Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 1 Channel 32 RTD Sensor is detected." 
	::= { dpsRTUv2 11160 }
	
--RTDdx 2 Channel 1
dpsRTUv2p10161Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 1 Minor Under is set." 
	::= { dpsRTUv2 10161 }

dpsRTUv2p11161Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 1 Minor Under is clear." 
	::= { dpsRTUv2 11161 }
	
dpsRTUv2p10162Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 1 Minor Over is set." 
	::= { dpsRTUv2 10162 }

dpsRTUv2p11162Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 1 Minor Over is clear." 
	::= { dpsRTUv2 11162 }
	
dpsRTUv2p10163Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 1 Major Under is set." 
	::= { dpsRTUv2 10163 }

dpsRTUv2p11163Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 1 Major Under is clear." 
	::= { dpsRTUv2 11163 }

dpsRTUv2p10164Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 1 Major Over is set." 
	::= { dpsRTUv2 10164 }

dpsRTUv2p11164Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 1 Major Over is clear." 
	::= { dpsRTUv2 11164 }

dpsRTUv2p10165Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 1 RTD Sensor is not detected." 
	::= { dpsRTUv2 10165 }

dpsRTUv2p11165Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 1 RTD Sensor is detected." 
	::= { dpsRTUv2 11165 }

--RTDdx 2 Channel 2
dpsRTUv2p10166Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 2 Minor Under is set." 
	::= { dpsRTUv2 10166 }

dpsRTUv2p11166Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 2 Minor Under is clear." 
	::= { dpsRTUv2 11166 }
	
dpsRTUv2p10167Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 2 Minor Over is set." 
	::= { dpsRTUv2 10167 }

dpsRTUv2p11167Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 2 Minor Over is clear." 
	::= { dpsRTUv2 11167 }
	
dpsRTUv2p10168Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 2 Major Under is set." 
	::= { dpsRTUv2 10168 }

dpsRTUv2p11168Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 2 Major Under is clear." 
	::= { dpsRTUv2 11168 }

dpsRTUv2p10169Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 2 Major Over is set." 
	::= { dpsRTUv2 10169 }

dpsRTUv2p11169Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 2 Major Over is clear." 
	::= { dpsRTUv2 11169 }

dpsRTUv2p10170Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 2 RTD Sensor is not detected." 
	::= { dpsRTUv2 10170 }

dpsRTUv2p11170Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 2 RTD Sensor is detected." 
	::= { dpsRTUv2 11170 }

--RTDdx 2 Channel 3
dpsRTUv2p10171Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 3 Minor Under is set." 
	::= { dpsRTUv2 10171 }

dpsRTUv2p11171Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 3 Minor Under is clear." 
	::= { dpsRTUv2 11171 }
	
dpsRTUv2p10172Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 3 Minor Over is set." 
	::= { dpsRTUv2 10172 }

dpsRTUv2p11172Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 3 Minor Over is clear." 
	::= { dpsRTUv2 11172 }
	
dpsRTUv2p10173Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 3 Major Under is set." 
	::= { dpsRTUv2 10173 }

dpsRTUv2p11173Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 3 Major Under is clear." 
	::= { dpsRTUv2 11173 }

dpsRTUv2p10174Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 3 Major Over is set." 
	::= { dpsRTUv2 10174 }

dpsRTUv2p11174Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 3 Major Over is clear." 
	::= { dpsRTUv2 11174 }

dpsRTUv2p10175Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 3 RTD Sensor is not detected." 
	::= { dpsRTUv2 10175 }

dpsRTUv2p11175Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 3 RTD Sensor is detected." 
	::= { dpsRTUv2 11175 }

--RTDdx 2 Channel 4
dpsRTUv2p10176Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 4 Minor Under is set." 
	::= { dpsRTUv2 10176 }

dpsRTUv2p11176Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 4 Minor Under is clear." 
	::= { dpsRTUv2 11176 }
	
dpsRTUv2p10177Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 4 Minor Over is set." 
	::= { dpsRTUv2 10177 }

dpsRTUv2p11177Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 4 Minor Over is clear." 
	::= { dpsRTUv2 11177 }
	
dpsRTUv2p10178Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 4 Major Under is set." 
	::= { dpsRTUv2 10178 }

dpsRTUv2p11178Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 4 Major Under is clear." 
	::= { dpsRTUv2 11178 }

dpsRTUv2p10179Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 4 Major Over is set." 
	::= { dpsRTUv2 10179 }

dpsRTUv2p11179Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 4 Major Over is clear." 
	::= { dpsRTUv2 11179 }

dpsRTUv2p10180Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 4 RTD Sensor is not detected." 
	::= { dpsRTUv2 10180 }

dpsRTUv2p11180Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 4 RTD Sensor is detected." 
	::= { dpsRTUv2 11180 }

--RTDdx 2 Channel 5
dpsRTUv2p10181Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 5 Minor Under is set." 
	::= { dpsRTUv2 10181 }

dpsRTUv2p11181Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 5 Minor Under is clear." 
	::= { dpsRTUv2 11181 }
	
dpsRTUv2p10182Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 5 Minor Over is set." 
	::= { dpsRTUv2 10182 }

dpsRTUv2p11182Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 5 Minor Over is clear." 
	::= { dpsRTUv2 11182 }
	
dpsRTUv2p10183Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 5 Major Under is set." 
	::= { dpsRTUv2 10183 }

dpsRTUv2p11183Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 5 Major Under is clear." 
	::= { dpsRTUv2 11183 }

dpsRTUv2p10184Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 5 Major Over is set." 
	::= { dpsRTUv2 10184 }

dpsRTUv2p11184Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 5 Major Over is clear." 
	::= { dpsRTUv2 11184 }

dpsRTUv2p10185Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 5 RTD Sensor is not detected." 
	::= { dpsRTUv2 10185 }

dpsRTUv2p11185Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 5 RTD Sensor is detected." 
	::= { dpsRTUv2 11185 }

--RTDdx 2 Channel 6
dpsRTUv2p10186Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 6 Minor Under is set." 
	::= { dpsRTUv2 10186 }

dpsRTUv2p11186Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 6 Minor Under is clear." 
	::= { dpsRTUv2 11186 }
	
dpsRTUv2p10187Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 6 Minor Over is set." 
	::= { dpsRTUv2 10187 }

dpsRTUv2p11187Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 6 Minor Over is clear." 
	::= { dpsRTUv2 11187 }
	
dpsRTUv2p10188Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 6 Major Under is set." 
	::= { dpsRTUv2 10188 }

dpsRTUv2p11188Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 6 Major Under is clear." 
	::= { dpsRTUv2 11188 }

dpsRTUv2p10189Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 6 Major Over is set." 
	::= { dpsRTUv2 10189 }

dpsRTUv2p11189Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 6 Major Over is clear." 
	::= { dpsRTUv2 11189 }

dpsRTUv2p10190Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 6 RTD Sensor is not detected." 
	::= { dpsRTUv2 10190 }

dpsRTUv2p11190Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 6 RTD Sensor is detected." 
	::= { dpsRTUv2 11190 }

--RTDdx 2 Channel 7
dpsRTUv2p10191Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 7 Minor Under is set." 
	::= { dpsRTUv2 10191 }

dpsRTUv2p11191Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 7 Minor Under is clear." 
	::= { dpsRTUv2 11191 }
	
dpsRTUv2p10192Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 7 Minor Over is set." 
	::= { dpsRTUv2 10192 }

dpsRTUv2p11192Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 7 Minor Over is clear." 
	::= { dpsRTUv2 11192 }
	
dpsRTUv2p10193Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 7 Major Under is set." 
	::= { dpsRTUv2 10193 }

dpsRTUv2p11193Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 7 Major Under is clear." 
	::= { dpsRTUv2 11193 }

dpsRTUv2p10194Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 7 Major Over is set." 
	::= { dpsRTUv2 10194 }

dpsRTUv2p11194Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 7 Major Over is clear." 
	::= { dpsRTUv2 11194 }

dpsRTUv2p10195Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 7 RTD Sensor is not detected." 
	::= { dpsRTUv2 10195 }

dpsRTUv2p11195Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 7 RTD Sensor is detected." 
	::= { dpsRTUv2 11195 }
	
--RTDdx 2 Channel 8
dpsRTUv2p10196Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 8 Minor Under is set." 
	::= { dpsRTUv2 10196 }

dpsRTUv2p11196Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 8 Minor Under is clear." 
	::= { dpsRTUv2 11196 }
	
dpsRTUv2p10197Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 8 Minor Over is set." 
	::= { dpsRTUv2 10197 }

dpsRTUv2p11197Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 8 Minor Over is clear." 
	::= { dpsRTUv2 11197 }
	
dpsRTUv2p10198Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 8 Major Under is set." 
	::= { dpsRTUv2 10198 }

dpsRTUv2p11198Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 8 Major Under is clear." 
	::= { dpsRTUv2 11198 }

dpsRTUv2p10199Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 8 Major Over is set." 
	::= { dpsRTUv2 10199 }

dpsRTUv2p11199Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 8 Major Over is clear." 
	::= { dpsRTUv2 11199 }

dpsRTUv2p10200Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 8 RTD Sensor is not detected." 
	::= { dpsRTUv2 10200 }

dpsRTUv2p11200Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 8 RTD Sensor is detected." 
	::= { dpsRTUv2 11200 }
	
--RTDdx 2 Channel 9
dpsRTUv2p10201Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 9 Minor Under is set." 
	::= { dpsRTUv2 10201 }

dpsRTUv2p11201Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 9 Minor Under is clear." 
	::= { dpsRTUv2 11201 }
	
dpsRTUv2p10202Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 9 Minor Over is set." 
	::= { dpsRTUv2 10202 }

dpsRTUv2p11202Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 9 Minor Over is clear." 
	::= { dpsRTUv2 11202 }
	
dpsRTUv2p10203Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 9 Major Under is set." 
	::= { dpsRTUv2 10203 }

dpsRTUv2p11203Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 9 Major Under is clear." 
	::= { dpsRTUv2 11203 }

dpsRTUv2p10204Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 9 Major Over is set." 
	::= { dpsRTUv2 10204 }

dpsRTUv2p11204Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 9 Major Over is clear." 
	::= { dpsRTUv2 11204 }

dpsRTUv2p10205Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 9 RTD Sensor is not detected." 
	::= { dpsRTUv2 10205 }

dpsRTUv2p11205Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 9 RTD Sensor is detected." 
	::= { dpsRTUv2 11205 }
	
--RTDdx 2 Channel 10
dpsRTUv2p10206Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 10 Minor Under is set." 
	::= { dpsRTUv2 10206 }

dpsRTUv2p11206Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 10 Minor Under is clear." 
	::= { dpsRTUv2 11206 }
	
dpsRTUv2p10207Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 10 Minor Over is set." 
	::= { dpsRTUv2 10207 }

dpsRTUv2p11207Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 10 Minor Over is clear." 
	::= { dpsRTUv2 11207 }
	
dpsRTUv2p10208Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 10 Major Under is set." 
	::= { dpsRTUv2 10208 }

dpsRTUv2p11208Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 10 Major Under is clear." 
	::= { dpsRTUv2 11208 }

dpsRTUv2p10209Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 10 Major Over is set." 
	::= { dpsRTUv2 10209 }

dpsRTUv2p11209Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 10 Major Over is clear." 
	::= { dpsRTUv2 11209 }

dpsRTUv2p10210Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 10 RTD Sensor is not detected." 
	::= { dpsRTUv2 10210 }

dpsRTUv2p11210Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 10 RTD Sensor is detected." 
	::= { dpsRTUv2 11210 }

--RTDdx 2 Channel 11
dpsRTUv2p10211Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 11 Minor Under is set." 
	::= { dpsRTUv2 10211 }

dpsRTUv2p11211Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 11 Minor Under is clear." 
	::= { dpsRTUv2 11211 }
	
dpsRTUv2p10212Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 11 Minor Over is set." 
	::= { dpsRTUv2 10212 }

dpsRTUv2p11212Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 11 Minor Over is clear." 
	::= { dpsRTUv2 11212 }
	
dpsRTUv2p10213Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 11 Major Under is set." 
	::= { dpsRTUv2 10213 }

dpsRTUv2p11213Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 11 Major Under is clear." 
	::= { dpsRTUv2 11213 }

dpsRTUv2p10214Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 11 Major Over is set." 
	::= { dpsRTUv2 10214 }

dpsRTUv2p11214Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 11 Major Over is clear." 
	::= { dpsRTUv2 11214 }

dpsRTUv2p10215Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 11 RTD Sensor is not detected." 
	::= { dpsRTUv2 10215 }

dpsRTUv2p11215Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 11 RTD Sensor is detected." 
	::= { dpsRTUv2 11215 }
	
--RTDdx 2 Channel 12
dpsRTUv2p10216Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 12 Minor Under is set." 
	::= { dpsRTUv2 10216 }

dpsRTUv2p11216Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 12 Minor Under is clear." 
	::= { dpsRTUv2 11216 }
	
dpsRTUv2p10217Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 12 Minor Over is set." 
	::= { dpsRTUv2 10217 }

dpsRTUv2p11217Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 12 Minor Over is clear." 
	::= { dpsRTUv2 11217 }
	
dpsRTUv2p10218Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 12 Major Under is set." 
	::= { dpsRTUv2 10218 }

dpsRTUv2p11218Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 12 Major Under is clear." 
	::= { dpsRTUv2 11218 }

dpsRTUv2p10219Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 12 Major Over is set." 
	::= { dpsRTUv2 10219 }

dpsRTUv2p11219Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 12 Major Over is clear." 
	::= { dpsRTUv2 11219 }

dpsRTUv2p10220Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 12 RTD Sensor is not detected." 
	::= { dpsRTUv2 10220 }

dpsRTUv2p11220Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 12 RTD Sensor is detected." 
	::= { dpsRTUv2 11220 }
	
--RTDdx 2 Channel 13
dpsRTUv2p10221Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 13 Minor Under is set." 
	::= { dpsRTUv2 10221 }

dpsRTUv2p11221Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 13 Minor Under is clear." 
	::= { dpsRTUv2 11221 }
	
dpsRTUv2p10222Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 13 Minor Over is set." 
	::= { dpsRTUv2 10222 }

dpsRTUv2p11222Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 13 Minor Over is clear." 
	::= { dpsRTUv2 11222 }
	
dpsRTUv2p10223Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 13 Major Under is set." 
	::= { dpsRTUv2 10223 }

dpsRTUv2p11223Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 13 Major Under is clear." 
	::= { dpsRTUv2 11223 }

dpsRTUv2p10224Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 13 Major Over is set." 
	::= { dpsRTUv2 10224 }

dpsRTUv2p11224Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 13 Major Over is clear." 
	::= { dpsRTUv2 11224 }

dpsRTUv2p10225Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 13 RTD Sensor is not detected." 
	::= { dpsRTUv2 10225 }

dpsRTUv2p11225Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 13 RTD Sensor is detected." 
	::= { dpsRTUv2 11225 }
	
--RTDdx 2 Channel 14
dpsRTUv2p10226Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 14 Minor Under is set." 
	::= { dpsRTUv2 10226 }

dpsRTUv2p11226Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 14 Minor Under is clear." 
	::= { dpsRTUv2 11226 }
	
dpsRTUv2p10227Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 14 Minor Over is set." 
	::= { dpsRTUv2 10227 }

dpsRTUv2p11227Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 14 Minor Over is clear." 
	::= { dpsRTUv2 11227 }
	
dpsRTUv2p10228Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 14 Major Under is set." 
	::= { dpsRTUv2 10228 }

dpsRTUv2p11228Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 14 Major Under is clear." 
	::= { dpsRTUv2 11228 }

dpsRTUv2p10229Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 14 Major Over is set." 
	::= { dpsRTUv2 10229 }

dpsRTUv2p11229Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 14 Major Over is clear." 
	::= { dpsRTUv2 11229 }

dpsRTUv2p10230Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 14 RTD Sensor is not detected." 
	::= { dpsRTUv2 10230 }

dpsRTUv2p11230Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 14 RTD Sensor is detected." 
	::= { dpsRTUv2 11230 }

--RTDdx 2 Channel 15
dpsRTUv2p10231Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 15 Minor Under is set." 
	::= { dpsRTUv2 10231 }

dpsRTUv2p11231Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 15 Minor Under is clear." 
	::= { dpsRTUv2 11231 }
	
dpsRTUv2p10232Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 15 Minor Over is set." 
	::= { dpsRTUv2 10232 }

dpsRTUv2p11232Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 15 Minor Over is clear." 
	::= { dpsRTUv2 11232 }
	
dpsRTUv2p10233Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 15 Major Under is set." 
	::= { dpsRTUv2 10233 }

dpsRTUv2p11233Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 15 Major Under is clear." 
	::= { dpsRTUv2 11233 }

dpsRTUv2p10234Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 15 Major Over is set." 
	::= { dpsRTUv2 10234 }

dpsRTUv2p11234Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 15 Major Over is clear." 
	::= { dpsRTUv2 11234 }

dpsRTUv2p10235Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 15 RTD Sensor is not detected." 
	::= { dpsRTUv2 10235 }

dpsRTUv2p11235Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 15 RTD Sensor is detected." 
	::= { dpsRTUv2 11235 }
	
--RTDdx 2 Channel 16
dpsRTUv2p10236Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 16 Minor Under is set." 
	::= { dpsRTUv2 10236 }

dpsRTUv2p11236Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 16 Minor Under is clear." 
	::= { dpsRTUv2 11236 }
	
dpsRTUv2p10237Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 16 Minor Over is set." 
	::= { dpsRTUv2 10237 }

dpsRTUv2p11237Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 16 Minor Over is clear." 
	::= { dpsRTUv2 11237 }
	
dpsRTUv2p10238Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 16 Major Under is set." 
	::= { dpsRTUv2 10238 }

dpsRTUv2p11238Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 16 Major Under is clear." 
	::= { dpsRTUv2 11238 }

dpsRTUv2p10239Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 16 Major Over is set." 
	::= { dpsRTUv2 10239 }

dpsRTUv2p11239Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 16 Major Over is clear." 
	::= { dpsRTUv2 11239 }

dpsRTUv2p10240Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 16 RTD Sensor is not detected." 
	::= { dpsRTUv2 10240 }

dpsRTUv2p11240Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 16 RTD Sensor is detected." 
	::= { dpsRTUv2 11240 }
	
--RTDdx 2 Channel 17
dpsRTUv2p10241Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 17 Minor Under is set." 
	::= { dpsRTUv2 10241 }

dpsRTUv2p11241Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 17 Minor Under is clear." 
	::= { dpsRTUv2 11241 }
	
dpsRTUv2p10242Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 17 Minor Over is set." 
	::= { dpsRTUv2 10242 }

dpsRTUv2p11242Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 17 Minor Over is clear." 
	::= { dpsRTUv2 11242 }
	
dpsRTUv2p10243Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 17 Major Under is set." 
	::= { dpsRTUv2 10243 }

dpsRTUv2p11243Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 17 Major Under is clear." 
	::= { dpsRTUv2 11243 }

dpsRTUv2p10244Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 17 Major Over is set." 
	::= { dpsRTUv2 10244 }

dpsRTUv2p11244Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 17 Major Over is clear." 
	::= { dpsRTUv2 11244 }

dpsRTUv2p10245Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 17 RTD Sensor is not detected." 
	::= { dpsRTUv2 10245 }

dpsRTUv2p11245Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 17 RTD Sensor is detected." 
	::= { dpsRTUv2 11245 }
	
--RTDdx 2 Channel 18
dpsRTUv2p10246Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 18 Minor Under is set." 
	::= { dpsRTUv2 10246 }

dpsRTUv2p11246Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 18 Minor Under is clear." 
	::= { dpsRTUv2 11246 }
	
dpsRTUv2p10247Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 18 Minor Over is set." 
	::= { dpsRTUv2 10247 }

dpsRTUv2p11247Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 18 Minor Over is clear." 
	::= { dpsRTUv2 11247 }
	
dpsRTUv2p10248Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 18 Major Under is set." 
	::= { dpsRTUv2 10248 }

dpsRTUv2p11248Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 18 Major Under is clear." 
	::= { dpsRTUv2 11248 }

dpsRTUv2p10249Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 18 Major Over is set." 
	::= { dpsRTUv2 10249 }

dpsRTUv2p11249Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 18 Major Over is clear." 
	::= { dpsRTUv2 11249 }

dpsRTUv2p10250Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 18 RTD Sensor is not detected." 
	::= { dpsRTUv2 10250 }

dpsRTUv2p11250Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 18 RTD Sensor is detected." 
	::= { dpsRTUv2 11250 }

--RTDdx 2 Channel 19
dpsRTUv2p10251Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 19 Minor Under is set." 
	::= { dpsRTUv2 10251 }

dpsRTUv2p11251Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 19 Minor Under is clear." 
	::= { dpsRTUv2 11251 }
	
dpsRTUv2p10252Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 19 Minor Over is set." 
	::= { dpsRTUv2 10252 }

dpsRTUv2p11252Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 19 Minor Over is clear." 
	::= { dpsRTUv2 11252 }
	
dpsRTUv2p10253Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 19 Major Under is set." 
	::= { dpsRTUv2 10253 }

dpsRTUv2p11253Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 19 Major Under is clear." 
	::= { dpsRTUv2 11253 }

dpsRTUv2p10254Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 19 Major Over is set." 
	::= { dpsRTUv2 10254 }

dpsRTUv2p11254Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 19 Major Over is clear." 
	::= { dpsRTUv2 11254 }

dpsRTUv2p10255Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 19 RTD Sensor is not detected." 
	::= { dpsRTUv2 10255 }

dpsRTUv2p11255Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 19 RTD Sensor is detected." 
	::= { dpsRTUv2 11255 }
	
--RTDdx 2 Channel 20
dpsRTUv2p10256Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 20 Minor Under is set." 
	::= { dpsRTUv2 10256 }

dpsRTUv2p11256Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 20 Minor Under is clear." 
	::= { dpsRTUv2 11256 }
	
dpsRTUv2p10257Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 20 Minor Over is set." 
	::= { dpsRTUv2 10257 }

dpsRTUv2p11257Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 20 Minor Over is clear." 
	::= { dpsRTUv2 11257 }
	
dpsRTUv2p10258Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 20 Major Under is set." 
	::= { dpsRTUv2 10258 }

dpsRTUv2p11258Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 20 Major Under is clear." 
	::= { dpsRTUv2 11258 }

dpsRTUv2p10259Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 20 Major Over is set." 
	::= { dpsRTUv2 10259 }

dpsRTUv2p11259Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 20 Major Over is clear." 
	::= { dpsRTUv2 11259 }

dpsRTUv2p10260Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 20 RTD Sensor is not detected." 
	::= { dpsRTUv2 10260 }

dpsRTUv2p11260Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 20 RTD Sensor is detected." 
	::= { dpsRTUv2 11260 }
	
--RTDdx 2 Channel 21
dpsRTUv2p10261Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 21 Minor Under is set." 
	::= { dpsRTUv2 10261 }

dpsRTUv2p11261Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 21 Minor Under is clear." 
	::= { dpsRTUv2 11261 }
	
dpsRTUv2p10262Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 21 Minor Over is set." 
	::= { dpsRTUv2 10262 }

dpsRTUv2p11262Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 21 Minor Over is clear." 
	::= { dpsRTUv2 11262 }
	
dpsRTUv2p10263Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 21 Major Under is set." 
	::= { dpsRTUv2 10263 }

dpsRTUv2p11263Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 21 Major Under is clear." 
	::= { dpsRTUv2 11263 }

dpsRTUv2p10264Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 21 Major Over is set." 
	::= { dpsRTUv2 10264 }

dpsRTUv2p11264Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 21 Major Over is clear." 
	::= { dpsRTUv2 11264 }

dpsRTUv2p10265Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 21 RTD Sensor is not detected." 
	::= { dpsRTUv2 10265 }

dpsRTUv2p11265Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 21 RTD Sensor is detected." 
	::= { dpsRTUv2 11265 }

--RTDdx 2 Channel 22
dpsRTUv2p10266Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 22 Minor Under is set." 
	::= { dpsRTUv2 10266 }

dpsRTUv2p11266Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 22 Minor Under is clear." 
	::= { dpsRTUv2 11266 }
	
dpsRTUv2p10267Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 22 Minor Over is set." 
	::= { dpsRTUv2 10267 }

dpsRTUv2p11267Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 22 Minor Over is clear." 
	::= { dpsRTUv2 11267 }
	
dpsRTUv2p10268Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 22 Major Under is set." 
	::= { dpsRTUv2 10268 }

dpsRTUv2p11268Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 22 Major Under is clear." 
	::= { dpsRTUv2 11268 }

dpsRTUv2p10269Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 22 Major Over is set." 
	::= { dpsRTUv2 10269 }

dpsRTUv2p11269Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 22 Major Over is clear." 
	::= { dpsRTUv2 11269 }

dpsRTUv2p10270Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 22 RTD Sensor is not detected." 
	::= { dpsRTUv2 10270 }

dpsRTUv2p11270Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 22 RTD Sensor is detected." 
	::= { dpsRTUv2 11270 }
	
--RTDdx 2 Channel 23
dpsRTUv2p10271Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 23 Minor Under is set." 
	::= { dpsRTUv2 10271 }

dpsRTUv2p11271Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 23 Minor Under is clear." 
	::= { dpsRTUv2 11271 }
	
dpsRTUv2p10272Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 23 Minor Over is set." 
	::= { dpsRTUv2 10272 }

dpsRTUv2p11272Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 23 Minor Over is clear." 
	::= { dpsRTUv2 11272 }
	
dpsRTUv2p10273Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 23 Major Under is set." 
	::= { dpsRTUv2 10273 }

dpsRTUv2p11273Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 23 Major Under is clear." 
	::= { dpsRTUv2 11273 }

dpsRTUv2p10274Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 23 Major Over is set." 
	::= { dpsRTUv2 10274 }

dpsRTUv2p11274Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 23 Major Over is clear." 
	::= { dpsRTUv2 11274 }

dpsRTUv2p10275Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 23 RTD Sensor is not detected." 
	::= { dpsRTUv2 10275 }

dpsRTUv2p11275Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 23 RTD Sensor is detected." 
	::= { dpsRTUv2 11275 }
	
--RTDdx 2 Channel 24
dpsRTUv2p10276Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 24 Minor Under is set." 
	::= { dpsRTUv2 10276 }

dpsRTUv2p11276Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 24 Minor Under is clear." 
	::= { dpsRTUv2 11276 }
	
dpsRTUv2p10277Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 24 Minor Over is set." 
	::= { dpsRTUv2 10277 }

dpsRTUv2p11277Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 24 Minor Over is clear." 
	::= { dpsRTUv2 11277 }
	
dpsRTUv2p10278Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 24 Major Under is set." 
	::= { dpsRTUv2 10278 }

dpsRTUv2p11278Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 24 Major Under is clear." 
	::= { dpsRTUv2 11278 }

dpsRTUv2p10279Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 24 Major Over is set." 
	::= { dpsRTUv2 10279 }

dpsRTUv2p11279Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 24 Major Over is clear." 
	::= { dpsRTUv2 11279 }

dpsRTUv2p10280Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 24 RTD Sensor is not detected." 
	::= { dpsRTUv2 10280 }

dpsRTUv2p11280Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 24 RTD Sensor is detected." 
	::= { dpsRTUv2 11280 }
	
--RTDdx 2 Channel 25
dpsRTUv2p10281Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 25 Minor Under is set." 
	::= { dpsRTUv2 10281 }

dpsRTUv2p11281Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 25 Minor Under is clear." 
	::= { dpsRTUv2 11281 }
	
dpsRTUv2p10282Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 25 Minor Over is set." 
	::= { dpsRTUv2 10282 }

dpsRTUv2p11282Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 25 Minor Over is clear." 
	::= { dpsRTUv2 11282 }
	
dpsRTUv2p10283Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 25 Major Under is set." 
	::= { dpsRTUv2 10283 }

dpsRTUv2p11283Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 25 Major Under is clear." 
	::= { dpsRTUv2 11283 }

dpsRTUv2p10284Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 25 Major Over is set." 
	::= { dpsRTUv2 10284 }

dpsRTUv2p11284Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 25 Major Over is clear." 
	::= { dpsRTUv2 11284 }

dpsRTUv2p10285Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 25 RTD Sensor is not detected." 
	::= { dpsRTUv2 10285 }

dpsRTUv2p11285Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 25 RTD Sensor is detected." 
	::= { dpsRTUv2 11285 }
	
--RTDdx 2 Channel 26
dpsRTUv2p10286Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 26 Minor Under is set." 
	::= { dpsRTUv2 10286 }

dpsRTUv2p11286Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 26 Minor Under is clear." 
	::= { dpsRTUv2 11286 }
	
dpsRTUv2p10287Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 26 Minor Over is set." 
	::= { dpsRTUv2 10287 }

dpsRTUv2p11287Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 26 Minor Over is clear." 
	::= { dpsRTUv2 11287 }
	
dpsRTUv2p10288Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 26 Major Under is set." 
	::= { dpsRTUv2 10288 }

dpsRTUv2p11288Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 26 Major Under is clear." 
	::= { dpsRTUv2 11288 }

dpsRTUv2p10289Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 26 Major Over is set." 
	::= { dpsRTUv2 10289 }

dpsRTUv2p11289Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 26 Major Over is clear." 
	::= { dpsRTUv2 11289 }

dpsRTUv2p10290Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 26 RTD Sensor is not detected." 
	::= { dpsRTUv2 10290 }

dpsRTUv2p11290Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 26 RTD Sensor is detected." 
	::= { dpsRTUv2 11290 }
	
--RTDdx 2 Channel 27
dpsRTUv2p10291Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 27 Minor Under is set." 
	::= { dpsRTUv2 10291 }

dpsRTUv2p11291Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 27 Minor Under is clear." 
	::= { dpsRTUv2 11291 }
	
dpsRTUv2p10292Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 27 Minor Over is set." 
	::= { dpsRTUv2 10292 }

dpsRTUv2p11292Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 27 Minor Over is clear." 
	::= { dpsRTUv2 11292 }
	
dpsRTUv2p10293Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 27 Major Under is set." 
	::= { dpsRTUv2 10293 }

dpsRTUv2p11293Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 27 Major Under is clear." 
	::= { dpsRTUv2 11293 }

dpsRTUv2p10294Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 27 Major Over is set." 
	::= { dpsRTUv2 10294 }

dpsRTUv2p11294Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 27 Major Over is clear." 
	::= { dpsRTUv2 11294 }

dpsRTUv2p10295Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 27 RTD Sensor is not detected." 
	::= { dpsRTUv2 10295 }

dpsRTUv2p11295Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 27 RTD Sensor is detected." 
	::= { dpsRTUv2 11295 }
	
--RTDdx 2 Channel 28
dpsRTUv2p10296Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 28 Minor Under is set." 
	::= { dpsRTUv2 10296 }

dpsRTUv2p11296Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 28 Minor Under is clear." 
	::= { dpsRTUv2 11296 }
	
dpsRTUv2p10297Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 28 Minor Over is set." 
	::= { dpsRTUv2 10297 }

dpsRTUv2p11297Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 28 Minor Over is clear." 
	::= { dpsRTUv2 11297 }
	
dpsRTUv2p10298Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 28 Major Under is set." 
	::= { dpsRTUv2 10298 }

dpsRTUv2p11298Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 28 Major Under is clear." 
	::= { dpsRTUv2 11298 }

dpsRTUv2p10299Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 28 Major Over is set." 
	::= { dpsRTUv2 10299 }

dpsRTUv2p11299Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 28 Major Over is clear." 
	::= { dpsRTUv2 11299 }

dpsRTUv2p10300Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 28 RTD Sensor is not detected." 
	::= { dpsRTUv2 10300 }

dpsRTUv2p11300Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 28 RTD Sensor is detected." 
	::= { dpsRTUv2 11300 }
	
--RTDdx 2 Channel 29
dpsRTUv2p10301Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 29 Minor Under is set." 
	::= { dpsRTUv2 10301 }

dpsRTUv2p11301Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 29 Minor Under is clear." 
	::= { dpsRTUv2 11301 }
	
dpsRTUv2p10302Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 29 Minor Over is set." 
	::= { dpsRTUv2 10302 }

dpsRTUv2p11302Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 29 Minor Over is clear." 
	::= { dpsRTUv2 11302 }
	
dpsRTUv2p10303Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 29 Major Under is set." 
	::= { dpsRTUv2 10303 }

dpsRTUv2p11303Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 29 Major Under is clear." 
	::= { dpsRTUv2 11303 }

dpsRTUv2p10304Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 29 Major Over is set." 
	::= { dpsRTUv2 10304 }

dpsRTUv2p11304Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 29 Major Over is clear." 
	::= { dpsRTUv2 11304 }

dpsRTUv2p10305Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 29 RTD Sensor is not detected." 
	::= { dpsRTUv2 10305 }

dpsRTUv2p11305Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 29 RTD Sensor is detected." 
	::= { dpsRTUv2 11305 }

--RTDdx 2 Channel 30
dpsRTUv2p10306Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 30 Minor Under is set." 
	::= { dpsRTUv2 10306 }

dpsRTUv2p11306Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 30 Minor Under is clear." 
	::= { dpsRTUv2 11306 }
	
dpsRTUv2p10307Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 30 Minor Over is set." 
	::= { dpsRTUv2 10307 }

dpsRTUv2p11307Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 30 Minor Over is clear." 
	::= { dpsRTUv2 11307 }
	
dpsRTUv2p10308Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 30 Major Under is set." 
	::= { dpsRTUv2 10308 }

dpsRTUv2p11308Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 30 Major Under is clear." 
	::= { dpsRTUv2 11308 }

dpsRTUv2p10309Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 30 Major Over is set." 
	::= { dpsRTUv2 10309 }

dpsRTUv2p11309Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 30 Major Over is clear." 
	::= { dpsRTUv2 11309 }

dpsRTUv2p10310Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 30 RTD Sensor is not detected." 
	::= { dpsRTUv2 10310 }

dpsRTUv2p11310Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 30 RTD Sensor is detected." 
	::= { dpsRTUv2 11310 }
	
--RTDdx 2 Channel 31
dpsRTUv2p10311Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 31 Minor Under is set." 
	::= { dpsRTUv2 10311 }

dpsRTUv2p11311Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 31 Minor Under is clear." 
	::= { dpsRTUv2 11311 }
	
dpsRTUv2p10312Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 31 Minor Over is set." 
	::= { dpsRTUv2 10312 }

dpsRTUv2p11312Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 31 Minor Over is clear." 
	::= { dpsRTUv2 11312 }
	
dpsRTUv2p10313Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 31 Major Under is set." 
	::= { dpsRTUv2 10313 }

dpsRTUv2p11313Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 31 Major Under is clear." 
	::= { dpsRTUv2 11313 }

dpsRTUv2p10314Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 31 Major Over is set." 
	::= { dpsRTUv2 10314 }

dpsRTUv2p11314Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 31 Major Over is clear." 
	::= { dpsRTUv2 11314 }

dpsRTUv2p10315Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 31 RTD Sensor is not detected." 
	::= { dpsRTUv2 10315 }

dpsRTUv2p11315Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 31 RTD Sensor is detected." 
	::= { dpsRTUv2 11315 }
	
--RTDdx 2 Channel 32
dpsRTUv2p10316Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 32 Minor Under is set." 
	::= { dpsRTUv2 10316 }

dpsRTUv2p11316Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 32 Minor Under is clear." 
	::= { dpsRTUv2 11316 }
	
dpsRTUv2p10317Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 32 Minor Over is set." 
	::= { dpsRTUv2 10317 }

dpsRTUv2p11317Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 32 Minor Over is clear." 
	::= { dpsRTUv2 11317 }
	
dpsRTUv2p10318Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 32 Major Under is set." 
	::= { dpsRTUv2 10318 }

dpsRTUv2p11318Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 32 Major Under is clear." 
	::= { dpsRTUv2 11318 }

dpsRTUv2p10319Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 32 Major Over is set." 
	::= { dpsRTUv2 10319 }

dpsRTUv2p11319Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 32 Major Over is clear." 
	::= { dpsRTUv2 11319 }

dpsRTUv2p10320Set NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 32 RTD Sensor is not detected." 
	::= { dpsRTUv2 10320 }

dpsRTUv2p11320Clr NOTIFICATION-TYPE 
	OBJECTS	 {	sysDescr, sysLocation, dpsRTUv2DateTime, 
					dpsRTUv2APort, dpsRTUv2CAddress, dpsRTUv2ADisplay, dpsRTUv2APoint, 
					dpsRTUv2APntDesc, dpsRTUv2AState } 
	STATUS		current
	DESCRIPTION "Generated when RTDdx 2 Channel 32 RTD Sensor is detected." 
	::= { dpsRTUv2 11320 }
	
END
