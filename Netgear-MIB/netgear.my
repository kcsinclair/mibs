-- ***************************************************************************
-- Netgear enterprise MIB for sysObjectID
-- 
-- To add new sysOID, please find the product category your product belong to 
-- (e.g. switch, router or ap), and increment the last number of the existing 
-- device that your product will go after.
-- All new products should be added after "new post-NMS100 SNMP products" session
--
-- Date: 7/11/2007
-- 
-- 
-- History:
-- - 5/12, correct chassis model name. Shuenn Hwang
-- - 7/14, add sysOID for rel I ver of GSM7324, GSM7312, FSM7326P, and GSM7224
-- - 7/14, add sysOID for new FS728TS and FS752TS
-- - 7/28, add sysOID for WPN802
-- - 8/16, add sysOID for FS752TPS
-- - 8/19, add sysOID for FVS124G
-- - 9/2, correct fsm7352ps name
-- - 10/13, change fs728ts/fs752ts/fs752tsp to new category "Stacksmartswitch"
-- - 10/13, add wg312 and wag312 
-- - 12/7/2005, add fvs318v3. Mike Shields
-- - 02/02/2006, add wg302v2, wag302v2. Stephen Tsai
-- - 05/11/2006, add GS724TS, GS748TS
-- - 7/18/2006, add dgfv338
-- - 7/20/2006, change GS724TS and GS748TS to GS724TSR and GS748TSR
-- - 8/14/2006, change GS724TSR and GS748TSR back to GS724TS and GS748TS
-- - 8/14/2006, add FS728TP
-- - 10/21/2006, add GSM7328FS 
-- - 11/17/2006, add GS108T, GS108TP, GS724TP, and GS748TP
-- - 5/2/2007, add GS724TR and GS748TR
-- - 5/15/2007, added FVS336G
-- - 7/12/2007, add GSM7200R/RP
-- - 11/02/2009, add GS716Tv2 and GS724Tv3
-- - 12/08/2009, add GS108Tv2 and GS110TP
--
-- iso                  OBJECT IDENTIFIER ::= { 1 }
-- org                  OBJECT IDENTIFIER ::= { iso 3 }
-- dod                  OBJECT IDENTIFIER ::= { org 6 }
-- internet             OBJECT IDENTIFIER ::= { dod 1 }
-- private              OBJECT IDENTIFIER ::= { internet 4 }
-- enterprises          OBJECT IDENTIFIER ::= { private 1 }
-- netgear              OBJECT IDENTIFIER ::= { enterprises 4526 }
-- 
-- There are already MIB files defined
-- for quite a few managed switches, as well as access point. Those devices
-- did not follow the structure defined in this file. Instead, they put the
-- product ID right under major product category as followed:
--
--
-- This structure is wrong in that all the features/functions are defined under
-- each product repeatly. This makes the NMS difficult to collect MIB data
--
-- The new structure adds a product category right under netgear and put all product id there
--

NETGEAR-REF-MIB DEFINITIONS ::= BEGIN
    IMPORTS
        enterprises FROM RFC1155-SMI;

netgear                 OBJECT IDENTIFIER ::= { enterprises 4526 }

--
-- below are products that defined prior to NMS100 release that they have product code
-- defined directly above the functions objects
--
managedSwitch           OBJECT IDENTIFIER ::= { netgear 1 } 
vPNRouter               OBJECT IDENTIFIER ::= { netgear 2 }
carrier		        OBJECT IDENTIFIER ::= { netgear 3 }
wireless		OBJECT IDENTIFIER ::= { netgear 4 }
rPS			OBJECT IDENTIFIER ::= { netgear 5 }
wLANswitch		OBJECT IDENTIFIER ::= { netgear 6 }

---
--- 700 series L2 managed switch
---
fsm726s                 OBJECT IDENTIFIER ::= { managedSwitch 1 }
fsm750s                 OBJECT IDENTIFIER ::= { managedSwitch 2 }
gsm712                  OBJECT IDENTIFIER ::= { managedSwitch 3 }
fsm726                  OBJECT IDENTIFIER ::= { managedSwitch 4 }  
gsm712f                 OBJECT IDENTIFIER ::= { managedSwitch 5 }
fsm726v2		OBJECT IDENTIFIER ::= { managedSwitch 10 }

---
--- AP
---
me103			OBJECT IDENTIFIER ::= { wireless 1 }
wg302			OBJECT IDENTIFIER ::= { wireless 2 }
wg102			OBJECT IDENTIFIER ::= { wireless 3 }
wag302			OBJECT IDENTIFIER ::= { wireless 4 }
wag102			OBJECT IDENTIFIER ::= { wireless 5 }
---
--- Added by Stephen Tsai 2-06-2006
---
wg302v2			OBJECT IDENTIFIER ::= { wireless 6 }
wag302v2		OBJECT IDENTIFIER ::= { wireless 7 }



---
--- WLAN Switch
---
wls538			OBJECT IDENTIFIER ::= { wLANswitch 1 }

---
--- 7000 series L2/L3 managed switch
---
gsm7312                 OBJECT IDENTIFIER ::= { managedSwitch 6 }
gsm7324                 OBJECT IDENTIFIER ::= { managedSwitch 7 }
gsm7224                 OBJECT IDENTIFIER ::= { managedSwitch 8 }
fsm7326p                OBJECT IDENTIFIER ::= { managedSwitch 9 }

---********************************************************************
--- new post-NMS100 SNMP products 
---

--
-- new post-NMS100 SNMP-enabled products. These products will have their 
-- functions defined under each generic product category.
--
ng7000managedswitch   	OBJECT IDENTIFIER ::= { netgear 10 }
ng700smartswitch        OBJECT IDENTIFIER ::= { netgear 11 }
ngrouter		OBJECT IDENTIFIER ::= { netgear 12 }
ngfirewall		OBJECT IDENTIFIER ::= { netgear 13 }
ngap			OBJECT IDENTIFIER ::= { netgear 14 }
ngwlan			OBJECT IDENTIFIER ::= { netgear 15 }
ng9000chassisswitch     OBJECT IDENTIFIER ::= { netgear 16 }
ng700stacksmartswitch   OBJECT IDENTIFIER ::= { netgear 17 } 

--
-- and their sysObjectID will be under a branch on their own
--
productID               OBJECT IDENTIFIER ::= { netgear 100 }

stackswitch             OBJECT IDENTIFIER ::= { productID 1 }
l2switch                OBJECT IDENTIFIER ::= { productID 2 }
l3switch		OBJECT IDENTIFIER ::= { productID 3 }
smartswitch             OBJECT IDENTIFIER ::= { productID 4 }
l2Rswitch		OBJECT IDENTIFIER ::= { productID 11 }

router                  OBJECT IDENTIFIER ::= { productID 5 }
firewall                OBJECT IDENTIFIER ::= { productID 6 }
accesspoint             OBJECT IDENTIFIER ::= { productID 7 }
wirelessLAN             OBJECT IDENTIFIER ::= { productID 8 }
chassisswitch           OBJECT IDENTIFIER ::= { productID 9 }
stacksmartswitch        OBJECT IDENTIFIER ::= { productID 10 }

--
-- Managed switches
--
fsm7328s                OBJECT IDENTIFIER ::= { stackswitch 1 }
fsm7352s                OBJECT IDENTIFIER ::= { stackswitch 2 }
gsm7328s                OBJECT IDENTIFIER ::= { stackswitch 3 }
gsm7352s                OBJECT IDENTIFIER ::= { stackswitch 4 }
fsm7352ps               OBJECT IDENTIFIER ::= { stackswitch 5 }
fsm7328ps               OBJECT IDENTIFIER ::= { stackswitch 8 }
gsm7328fs               OBJECT IDENTIFIER ::= { stackswitch 7 }
gsm7328ps		OBJECT IDENTIFIER ::= { stackswitch 9 }
gsm7352ps		OBJECT IDENTIFIER ::= { stackswitch 10 }

gsm7312v2               OBJECT IDENTIFIER ::= { l3switch 1 }
gsm7324v2               OBJECT IDENTIFIER ::= { l3switch 2 }
xsm7312	                OBJECT IDENTIFIER ::= { l3switch 3 }
gsm7324p                OBJECT IDENTIFIER ::= { l3switch 4 }

gsm7224r		OBJECT IDENTIFIER ::= { l2Rswitch 1 }
gsm7248r		OBJECT IDENTIFIER ::= { l2Rswitch 2 }
gsm7224rp		OBJECT IDENTIFIER ::= { l2Rswitch 3 }
gsm7248rp		OBJECT IDENTIFIER ::= { l2Rswitch 4 }

-- 
-- GSM7324, GSM7312, FSM7326P, and GSM7224, are using two different styles
-- of FP private MIB: dedicate and generic. For those using dedicated one, the sysOID
-- are assigned to "gsm7324", "gsm7312, "fsm7326p", and "gsm7224". For the one using 
-- generic MIB, the new OIDs are has a "i" in the end.
--
gsm7312i                OBJECT IDENTIFIER ::= { l3switch 5 }
gsm7324i                OBJECT IDENTIFIER ::= { l3switch 6 }
fsm7326pi               OBJECT IDENTIFIER ::= { l3switch 7 }

gsm7248                 OBJECT IDENTIFIER ::= { l2switch 1 }
gsm7212                 OBJECT IDENTIFIER ::= { l2switch 2 }
gsm7224i                OBJECT IDENTIFIER ::= { l2switch 3 }

gcm9000	                OBJECT IDENTIFIER ::= { chassisswitch 1 }

---
--- new SNMP-enabled Smartswitch
---
gs748t                  OBJECT IDENTIFIER ::= { smartswitch 1 }
fs726t	                OBJECT IDENTIFIER ::= { smartswitch 2 }
gs716t	                OBJECT IDENTIFIER ::= { smartswitch 3 }
fs750t                  OBJECT IDENTIFIER ::= { smartswitch 4 }
gs724t	                OBJECT IDENTIFIER ::= { smartswitch 5 }
fs726tp                 OBJECT IDENTIFIER ::= { smartswitch 6 }
fs728tp	                OBJECT IDENTIFIER ::= { smartswitch 7 }  
gs108t                  OBJECT IDENTIFIER ::= { smartswitch 8 }
gs108tp                 OBJECT IDENTIFIER ::= { smartswitch 9 }
gs724tp                 OBJECT IDENTIFIER ::= { smartswitch 10 }
gs748tp                 OBJECT IDENTIFIER ::= { smartswitch 11 }
gs724tr                 OBJECT IDENTIFIER ::= { smartswitch 12 }
gs748tr                 OBJECT IDENTIFIER ::= { smartswitch 13 }
gs716tv2                OBJECT IDENTIFIER ::= { smartswitch 16 }
gs724tv3                OBJECT IDENTIFIER ::= { smartswitch 17 }
gs108tv2                OBJECT IDENTIFIER ::= { smartswitch 18 }
gs110tp                 OBJECT IDENTIFIER ::= { smartswitch 19 }
fs752tp	                OBJECT IDENTIFIER ::= { smartswitch 22 }
gs110t                  OBJECT IDENTIFIER ::= { smartswitch 23 }
gs510tp                 OBJECT IDENTIFIER ::= { smartswitch 24 }


fs728ts	                OBJECT IDENTIFIER ::= { stacksmartswitch 1 }
fs752ts	                OBJECT IDENTIFIER ::= { stacksmartswitch 2 }
fs752tps                OBJECT IDENTIFIER ::= { stacksmartswitch 3 }
gs724ts	                OBJECT IDENTIFIER ::= { stacksmartswitch 4 }
gs748ts	                OBJECT IDENTIFIER ::= { stacksmartswitch 5 }

---
--- new SNMP-enabled business router/firewall
---
fvx538	                OBJECT IDENTIFIER ::= { router 1 }
fvs338	                OBJECT IDENTIFIER ::= { router 2 }
fvg318	                OBJECT IDENTIFIER ::= { router 3 }
fvs336g			OBJECT IDENTIFIER ::= { router 4 }

---
--- new SNMP-enabled firewall
---
fwag114	                OBJECT IDENTIFIER ::= { firewall 3 }
fvs124g	                OBJECT IDENTIFIER ::= { firewall 4 }
fvs318v3                OBJECT IDENTIFIER ::= { firewall 5 }
dgfv338	                OBJECT IDENTIFIER ::= { firewall 6 }

---
--- new SNMP-enabled AP
---
wpn802	                OBJECT IDENTIFIER ::= { accesspoint 1 }
wg312	                OBJECT IDENTIFIER ::= { accesspoint 2 }
wag312	                OBJECT IDENTIFIER ::= { accesspoint 3 }

---
--- new WLAN
---


END
