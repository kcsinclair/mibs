--
-- OPTIX-SONET-SYSTEM-MIB-V2.mib
-- MIB generated by MG-SOFT Visual MIB Builder Version 3.0 Build 253
-- Monday, July 17, 2006 at 13:49:18
--

	OPTIX-SONET-SYSTEM-MIB-V2 DEFINITIONS ::= BEGIN
 
		IMPORTS
			optixProvisionSonet			
				FROM OPTIX-OID-MIB			
			OBJECT-GROUP, MODULE-COMPLIANCE			
				FROM SNMPv2-CONF			
			OBJECT-TYPE, MODULE-IDENTITY			
				FROM SNMPv2-SMI;
	
	
		optixsonetSysAttribute MODULE-IDENTITY 
			LAST-UPDATED "200605232007Z"		-- May 23, 2006 at 20:07 GMT
			ORGANIZATION 
				"Your organization"
			CONTACT-INFO 
				"Your contact info"
			DESCRIPTION 
				"Enter the description for this MIB module."
			::= { optixProvisionSonet 4 }
		
	
--
-- Node definitions
--
	
		-- 1.3.6.1.4.1.2011.2.25.4.20.4.1
		optixsonetNeType OBJECT IDENTIFIER ::= { optixsonetSysAttribute 1 }
		
		-- 1.3.6.1.4.1.2011.2.25.4.20.4.1.1
		optixsonetVendId OBJECT-TYPE
			SYNTAX OCTET STRING
			MAX-ACCESS read-only
			STATUS current
			DESCRIPTION
				"The vendor identifier of the equipment. Valid value is a string."
			::= { optixsonetNeType 1 }
		
		-- 1.3.6.1.4.1.2011.2.25.4.20.4.1.2
		optixsonetDeviceType OBJECT-TYPE
			SYNTAX OCTET STRING
			MAX-ACCESS read-only
			STATUS current
			DESCRIPTION
				"Device type"
			::= { optixsonetNeType 2 }
		
		-- 1.3.6.1.4.1.2011.2.25.4.20.4.1.3
		optixsonetEquipType OBJECT-TYPE
			SYNTAX OCTET STRING
			MAX-ACCESS read-only
			STATUS current
			DESCRIPTION
				"Equipment type.It is a 40 bytes string.Valid value is ADM,MUX or MSPP. 
				ADM means Multi Add/Drop Multiplexer.
				MUX means Multiplexer.
				MSPP means Multi-Service Transport Platform.
				"
			::= { optixsonetNeType 3 }
		
		-- 1.3.6.1.4.1.2011.2.25.4.20.4.1.4
		optixsonetNeVersion OBJECT-TYPE
			SYNTAX OCTET STRING
			MAX-ACCESS read-only
			STATUS current
			DESCRIPTION
				"The software release version of the NE. It is a 40 bytes string."
			::= { optixsonetNeType 4 }
		
		-- 1.3.6.1.4.1.2011.2.25.4.20.4.2
		optixsonetSysAttributeConformance OBJECT IDENTIFIER ::= { optixsonetSysAttribute 2 }
		
		-- 1.3.6.1.4.1.2011.2.25.4.20.4.2.1
		optixsonetSysAttributeGroups OBJECT IDENTIFIER ::= { optixsonetSysAttributeConformance 1 }
		
		-- 1.3.6.1.4.1.2011.2.25.4.20.4.2.1.1
		currentObjectGroup OBJECT-GROUP
			OBJECTS { optixsonetVendId, optixsonetDeviceType, optixsonetEquipType, optixsonetNeVersion }
			STATUS current
			DESCRIPTION 
				"Enter the description of the created OBJECT-GROUP."
			::= { optixsonetSysAttributeGroups 1 }
		
		-- 1.3.6.1.4.1.2011.2.25.4.20.4.2.2
		optixsonetSysAttributeCompliances OBJECT IDENTIFIER ::= { optixsonetSysAttributeConformance 2 }
		
		-- 1.3.6.1.4.1.2011.2.25.4.20.4.2.2.1
		basicCompliance MODULE-COMPLIANCE
			STATUS current
			DESCRIPTION 
				"Enter the description of the created MODULE-COMPLIANCE."
			MODULE -- this module
				MANDATORY-GROUPS { currentObjectGroup }
			::= { optixsonetSysAttributeCompliances 1 }
		
	
	END

--
-- OPTIX-SONET-SYSTEM-MIB-V2.mib
--
