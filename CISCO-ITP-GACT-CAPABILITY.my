-- *****************************************************************
-- CISCO-ITP-GACT-CAPABILITY.my: ITP Gateway Signalling Point
-- Accounting Agent capability MIB
--   
-- May 2003, John Linton
--   
-- Copyright (c) 2003-2007 by cisco Systems Inc.
--   
-- All rights reserved.
-- ***************************************************************

CISCO-ITP-GACT-CAPABILITY DEFINITIONS ::= BEGIN

IMPORTS
    MODULE-IDENTITY
        FROM SNMPv2-SMI
    AGENT-CAPABILITIES
        FROM SNMPv2-CONF
    ciscoAgentCapability
        FROM CISCO-SMI;


ciscoGactCapability MODULE-IDENTITY
    LAST-UPDATED    "200704260000Z"
    ORGANIZATION    "Cisco Systems, Inc."
    CONTACT-INFO
            "Cisco Systems
            Customer Service

            Postal: 170 West Tasman Drive
            San Jose, CA  95134
            USA

            Tel: +1 800 553-NETS

            E-mail: cs-ss7@cisco.com"
    DESCRIPTION
        "Agent capabilities for the CISCO-ITP-GACT-MIB."
    REVISION        "200704260000Z"
    DESCRIPTION
        "Added ciscoGactCapabilityV12R0218IXA and
        ciscoGactCapabilityV12R0411SW capability statements."
    REVISION        "200312080000Z"
    DESCRIPTION
        "Support for cross instance global title
        translation.  Added agent capability
        ciscoGactCapabilityV12R022004SW statement for 
        IOS 12.2(20.4) and replaced 
        ciscoGactGttGroup object group with
        ciscoGactGttGroupRev1."
    REVISION        "200307170000Z"
    DESCRIPTION
        "Initial version of this MIB module."
    ::= { ciscoAgentCapability 304 }



ciscoGactCapabilityV12R0204MB10 AGENT-CAPABILITIES
    PRODUCT-RELEASE "Cisco IOS 12.2(4)MB10"
    STATUS          obsolete
    DESCRIPTION
        "CISCO-ITP-GACT-MIB.my agent capabilities."

    SUPPORTS        CISCO-ITP-GACT-MIB
    INCLUDES        {
                        ciscoGactMtp3Group,
                        ciscoGactGttGroup
                    }
    ::= { ciscoGactCapability 1 }

ciscoGactCapabilityV12R022004SW AGENT-CAPABILITIES
    PRODUCT-RELEASE "Cisco IOS 12.2(20.4)SW"
    STATUS          current
    DESCRIPTION
        "CISCO-ITP-GACT-MIB.my agent capabilities."

    SUPPORTS        CISCO-ITP-GACT-MIB
    INCLUDES        {
                        ciscoGactMtp3Group,
                        ciscoGactGttGroupRev1
                    }
    ::= { ciscoGactCapability 2 }

ciscoGactCapabilityV12R0218IXA AGENT-CAPABILITIES
    PRODUCT-RELEASE "Cisco IOS 12.2(18)IXA"
    STATUS          current
    DESCRIPTION
        "CISCO-ITP-GACT-MIB.my agent capabilities."

    SUPPORTS        CISCO-ITP-GACT-MIB
    INCLUDES        {
                        ciscoGactMtp3Group,
                        ciscoGactGttGroupRev1
                    }
    ::= { ciscoGactCapability 3 }

ciscoGactCapabilityV12R0411SW AGENT-CAPABILITIES
    PRODUCT-RELEASE "Cisco IOS 12.4(11)SW"
    STATUS          current
    DESCRIPTION
        "CISCO-ITP-GACT-MIB.my agent capabilities."

    SUPPORTS        CISCO-ITP-GACT-MIB
    INCLUDES        {
                        ciscoGactMtp3Group,
                        ciscoGactGttGroupRev1
                    }
    ::= { ciscoGactCapability 4 }

END
