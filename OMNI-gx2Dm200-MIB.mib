OMNI-gx2Dm200-MIB DEFINITIONS ::= BEGIN

    IMPORTS

	OBJECT-TYPE                     
					      FROM RFC-1212
	DisplayString        
					      FROM RFC1213-MIB
	TRAP-TYPE                       
					      FROM RFC-1215
	gx2Dm200
					      FROM GX2HFC-MIB

	trapIdentifier,trapNetworkElemModelNumber,
	trapNetworkElemSerialNum, trapPerceivedSeverity,
	trapNetworkElemOperState, trapNetworkElemAlarmStatus,
	trapNetworkElemAdminState, trapNetworkElemAvailStatus,
	trapText, trapNETrapLastTrapTimeStamp, trapChangedObjectId,
	trapChangedValueInteger, trapChangedValueDisplayString
					      FROM NLSBBN-TRAPS-MIB;



	       -- This MIB module uses the extended OBJECT-TYPE macro as
	       -- defined in RFC1212 and the TRAP-TYPE macro as defined
	       -- in RFC 1215.

		   --REVISION	"0" Sept 1, 2003
		   --DESCRIPTION
		   --			Added revision and description comment section


		--    OMNISTAR DM 1550 Laser Module (Return Path Transmetter)  MIB MODULE

	-- This MIB module defines information for management of HFC networks
		-- 
		-- The MIB module assumes that all generic (static) network element
		-- information is defined in a different module such as the HFC module
		-- The MIB consists of two groups:
		-- the device type descriptor subgroup and 
		-- gx2Dm200 Network Elements subgroup.
		-- The device type descriptor subgroup is used to define 
		-- parameters specific to gx2Dm200 device type.
		-- These parameters are common across all network elements
		-- from gx2Dm200 device type.
		--
		-- The gx2Dm200 Network Elements subgroup is
		-- a list of gx2Dm200 type elements in the
		-- current network topology with nominal
		-- and current parameter values for the
		-- individual network elements; the individual
		-- network elements are identified by  
		-- index from hfcCommonTable.
		-- That implies what hfcCommonTableIndex and
		-- gx2Dm200TableIndex are equal for each individual
		-- network element.
		-- This table is an extension of the hfcCommonTable
		-- for all elements of gx2Dm200 type.
		--
		-- Both groups are mandatory for management of gx2Dm200 devices.

-- ****************************************************************************
		--
		-- All floating point numbers will be represented by an IEEE 32 Bit number.
		-- Conversion of this number must be done on the user interface to view the 
		-- actual floating point number. 
		--

		Float ::= Counter  -- UNSIGNED (32 BITS) 

-- ****************************************************************************

		-- gx2Dm200 Device Descriptor subgroup.

		-- The device type descriptor subgroup is used to define 
		-- parameters specific to gx2Dm200 device type.
		-- These parameters are common across all network elements
		-- from gx2Dm200 device type.


		gx2Dm200Descriptor OBJECT IDENTIFIER ::= {gx2Dm200 1}



--*****************************************************************************
		--              gx2Dm200 Table
		
		-- The individual network elements indentified by  
		-- index from hfcCommonTable.
		-- That implies what hfcCommonTableIndex and
		-- gx2Dm200TableIndex are equal for each individual
		-- nettwork element.
		-- This table should be used as an extension of the hfcCommonTable
		-- for all elements of gx2Dm200 type.


	       gx2Dm200AnalogTable                    OBJECT-TYPE
			 SYNTAX             SEQUENCE OF Gx2Dm200AnalogEntry
			 ACCESS             not-accessible
			 STATUS             mandatory
			 DESCRIPTION
			 "This table contains gx2Dm200 specific parameters with
			  nominal and current values."
			 ::= { gx2Dm200 2 }


	       gx2Dm200AnalogEntry               OBJECT-TYPE
			 SYNTAX             Gx2Dm200AnalogEntry
			 ACCESS             not-accessible
			 STATUS             mandatory
			 DESCRIPTION
			 "This list contains the analog parameters and descriptions."
			 INDEX { gx2Dm200AnalogTableIndex }
			 ::= { gx2Dm200AnalogTable  1}

--*************************************************************************
	       gx2Dm200DigitalTable                    OBJECT-TYPE
			 SYNTAX             SEQUENCE OF Gx2Dm200DigitalEntry
			 ACCESS             not-accessible
			 STATUS             mandatory
			 DESCRIPTION
			 "This table contains gx2Dm200m specific parameters with
			  nominal and current values."
			 ::= { gx2Dm200 3 }

	       gx2Dm200DigitalEntry               OBJECT-TYPE
			 SYNTAX             Gx2Dm200DigitalEntry
			 ACCESS             not-accessible
			 STATUS             mandatory
			 DESCRIPTION
			 "This list contains digital parameters and descriptions."
			 INDEX { gx2Dm200DigitalTableIndex }
			 ::= { gx2Dm200DigitalTable  2}

--*************************************************************************
	       gx2Dm200StatusTable                    OBJECT-TYPE
			 SYNTAX             SEQUENCE OF Gx2Dm200StatusEntry
			 ACCESS             not-accessible
			 STATUS             mandatory
			 DESCRIPTION
			 "This table contains gx2Dm200 specific parameters with
			  nominal and current values."
			 ::= { gx2Dm200 4 }

	       gx2Dm200StatusEntry               OBJECT-TYPE
			 SYNTAX             Gx2Dm200StatusEntry
			 ACCESS             not-accessible
			 STATUS             mandatory
			 DESCRIPTION
			 "This list contains Status parameters and descriptions."
			 INDEX { gx2Dm200StatusTableIndex }
			 ::= { gx2Dm200StatusTable  3}

--*************************************************************************
	       gx2Dm200FactoryTable                    OBJECT-TYPE
			 SYNTAX             SEQUENCE OF Gx2Dm200FactoryEntry
			 ACCESS             not-accessible
			 STATUS             mandatory
			 DESCRIPTION
			 "This table contains gx2Dm200 specific parameters with
			  nominal and current values."
			 ::= { gx2Dm200 5 }

	       gx2Dm200FactoryEntry               OBJECT-TYPE
			 SYNTAX             Gx2Dm200FactoryEntry
			 ACCESS             not-accessible
			 STATUS             mandatory
			 DESCRIPTION
			 "This list contains Factory parameters and descriptions."
			 INDEX { gx2Dm200FactoryTableIndex }
			 ::= { gx2Dm200FactoryTable  4}
--*************************************************************************

	      Gx2Dm200AnalogEntry    ::= SEQUENCE  
	       {
		gx2Dm200AnalogTableIndex         INTEGER,
		
		--           Analog Parameters

		dm200labelOffsetNomMonitor			DisplayString (SIZE (0..80)),
		dm200uomOffsetNomMonitor			DisplayString (SIZE (0..80)),
		dm200majorHighOffsetNomMonitor 		Float, 
		dm200majorLowOffsetNomMonitor 		Float, 
		dm200minorHighOffsetNomMonitor 		Float,
		dm200minorLowOffsetNomMonitor 		Float, 
		dm200currentValueOffsetNomMonitor 	Float, 
		dm200stateFlagOffsetNomMonitor 		INTEGER,
		dm200minValueOffsetNomMonitor 		Float,
		dm200maxValueOffsetNomMonitor  		Float,
		dm200alarmStateOffsetNomMonitor 	INTEGER,

		dm200labelAttenSetting				DisplayString (SIZE (0..80)),
		dm200uomAttenSetting				DisplayString (SIZE (0..80)),
		dm200majorHighAttenSetting			Float, 
		dm200majorLowAttenSetting			Float, 
		dm200minorHighAttenSetting			Float,
		dm200minorLowAttenSetting			Float, 
		dm200currentValueAttenSetting		Float, 
		dm200stateFlagAttenSetting			INTEGER,
		dm200minValueAttenSetting			Float,
		dm200maxValueAttenSetting 			Float,
		dm200alarmStateAttenSetting			INTEGER,

		dm200labelLaserPower				DisplayString (SIZE (0..80)),
		dm200uomLaserPower					DisplayString (SIZE (0..80)),
		dm200majorHighLaserPower			Float, 
		dm200majorLowLaserPower				Float, 
		dm200minorHighLaserPower			Float,
		dm200minorLowLaserPower				Float, 
		dm200currentValueLaserPower			Float, 
		dm200stateFlagLaserPower			INTEGER,
		dm200minValueLaserPower				Float,
		dm200maxValueLaserPower 			Float,
		dm200alarmStateLaserPower			INTEGER,

		dm200labelLaserTemp					DisplayString (SIZE (0..80)),
		dm200uomLaserTemp					DisplayString (SIZE (0..80)),
		dm200majorHighLaserTemp				Float, 
		dm200majorLowLaserTemp				Float, 
		dm200minorHighLaserTemp				Float,
		dm200minorLowLaserTemp				Float, 
		dm200currentValueLaserTemp			Float, 
		dm200stateFlagLaserTemp				INTEGER,
		dm200minValueLaserTemp				Float,
		dm200maxValueLaserTemp 				Float,
		dm200alarmStateLaserTemp			INTEGER,

		dm200labelLaserCurrent				DisplayString (SIZE (0..80)),
		dm200uomLaserCurrent				DisplayString (SIZE (0..80)),
		dm200majorHighLaserCurrent			Float, 
		dm200majorLowLaserCurrent			Float, 
		dm200minorHighLaserCurrent			Float,
		dm200minorLowLaserCurrent			Float, 
		dm200currentValueLaserCurrent		Float, 
		dm200stateFlagLaserCurrent			INTEGER,
		dm200minValueLaserCurrent			Float,
		dm200maxValueLaserCurrent 			Float,
		dm200alarmStateLaserCurrent			INTEGER,

		dm200labelTecCurrent				DisplayString (SIZE (0..80)),
		dm200uomTecCurrent					DisplayString (SIZE (0..80)),
		dm200majorHighTecCurrent			Float, 
		dm200majorLowTecCurrent				Float, 
		dm200minorHighTecCurrent			Float,
		dm200minorLowTecCurrent				Float, 
		dm200currentValueTecCurrent			Float, 
		dm200stateFlagTecCurrent			INTEGER,
		dm200minValueTecCurrent				Float,
		dm200maxValueTecCurrent				Float,
		dm200alarmStateTecCurrent			INTEGER,

		dm200labelModTemp					DisplayString (SIZE (0..80)),
		dm200uomModTemp						DisplayString (SIZE (0..80)),
		dm200majorHighModTemp				Float, 
		dm200majorLowModTemp				Float, 
		dm200minorHighModTemp				Float,
		dm200minorLowModTemp				Float, 
		dm200currentValueModTemp			Float, 
		dm200stateFlagModTemp				INTEGER,
		dm200minValueModTemp				Float,
		dm200maxValueModTemp 				Float,
		dm200alarmStateModTemp				INTEGER,

		dm200labelFanCurrent				DisplayString (SIZE (0..80)),
		dm200uomFanCurrent					DisplayString (SIZE (0..80)),
		dm200majorHighFanCurrent			Float, 
		dm200majorLowFanCurrent				Float, 
		dm200minorHighFanCurrent			Float,
		dm200minorLowFanCurrent				Float, 
		dm200currentValueFanCurrent			Float, 
		dm200stateFlagFanCurrent			INTEGER,
		dm200minValueFanCurrent				Float,
		dm200maxValueFanCurrent				Float,
		dm200alarmStateFanCurrent			INTEGER
		}

		-- ****************  Digital Parameters ***********************

      Gx2Dm200DigitalEntry    ::= SEQUENCE  
      {
		gx2Dm200DigitalTableIndex         INTEGER,

		dm200labelRfInput				DisplayString (SIZE (0..80)),
		dm200enumRfInput				DisplayString (SIZE (0..80)),
		dm200valueRfInput				INTEGER,
		dm200stateflagRfInput  			INTEGER,

		dm200labelOptOutput				DisplayString (SIZE (0..80)),
		dm200enumOptOutput				DisplayString (SIZE (0..80)),
		dm200valueOptOutput				INTEGER,
		dm200stateflagOptOutput         INTEGER,

		dm200labelSbsControl			DisplayString (SIZE (0..80)),
		dm200enumSbsControl				DisplayString (SIZE (0..80)),
		dm200valueSbsControl			INTEGER,
		dm200stateflagSbsControl        INTEGER,

		dm200labelFactoryDefault		DisplayString (SIZE (0..80)),
		dm200enumFactoryDefault			DisplayString (SIZE (0..80)),
		dm200valueFactoryDefault		INTEGER,
		dm200stateflagFactoryDefault   	INTEGER
		}


		-- ****************  Status Parameters ************************************
	    Gx2Dm200StatusEntry    ::= SEQUENCE  
	    {
		gx2Dm200StatusTableIndex		INTEGER,

		dm200labelBoot					DisplayString (SIZE (0..80)),
		dm200valueBoot					INTEGER,
		dm200stateflagBoot				INTEGER,
		
		dm200labelFlash					DisplayString (SIZE (0..80)),
		dm200valueFlash					INTEGER,
		dm200stateflagFlash				INTEGER,

		dm200labelFactoryDataCRC 		DisplayString (SIZE (0..80)),
		dm200valueFactoryDataCRC		INTEGER,
		dm200stateflagFactoryDataCRC	INTEGER,

		dm200labelLaserDataCRC 			DisplayString (SIZE (0..80)),
		dm200valueLaserDataCRC 			INTEGER,
		dm200stateflagLaserDataCRC 		INTEGER,

		dm200labelAlarmDataCrc			DisplayString (SIZE (0..80)),
		dm200valueAlarmDataCrc			INTEGER,
		dm200stateflagAlarmDataCrc		INTEGER,

		dm200labelRFInputStatus			DisplayString (SIZE (0..80)),
		dm200valueRFInputStatus			INTEGER,
		dm200stateflagRFInputStatus		INTEGER
		}


		-- ****************  Factory Parameters *************************************
	    Gx2Dm200FactoryEntry    ::= SEQUENCE  
	    {
		gx2Dm200FactoryTableIndex		INTEGER,
		dm200bootControlByte  			INTEGER,
		dm200bootStatusByte   			INTEGER,
		dm200bank1CRC    				INTEGER,
		dm200bank2CRC    				INTEGER,
		dm200prgEEPROMByte    			INTEGER,
		dm200factoryCRC    				INTEGER,
		dm200calculateCRC    			INTEGER,
		dm200hourMeter    				INTEGER,
		dm200flashPrgCntA    			INTEGER,
		dm200flashPrgCntB    			INTEGER,
		dm200flashBankARev    			DisplayString (SIZE (0..80)),
		dm200flashBankBRev    			DisplayString (SIZE (0..80))


		}
            -- ************** Analog Parameters ****************************
		gx2Dm200AnalogTableIndex			OBJECT-TYPE
			   SYNTAX				INTEGER (1..2147483647)
			   ACCESS				read-only
			   STATUS				mandatory
			   DESCRIPTION			
			   "The value of this object identifies the network
			    element. This index is equal to the
			    hfcCommonTableIndex for the same element."
			   ::= { gx2Dm200AnalogEntry 1}

-- New Parameter

		dm200labelOffsetNomMonitor              OBJECT-TYPE
			   SYNTAX           DisplayString (SIZE (0..80))
			   ACCESS           read-only
			   STATUS           optional
			   DESCRIPTION
			   "The value of this object provides the label of the
			    Offset Monitor Analog parameter."
			   ::= { gx2Dm200AnalogEntry 2}

		dm200uomOffsetNomMonitor                OBJECT-TYPE
			   SYNTAX           DisplayString (SIZE (0..80))
			   ACCESS           read-only
			   STATUS           optional
			   DESCRIPTION
			   "The value of this object provides the Unit of Measure of the
			    Offset Monitor Analog parameter. The unit of measure for 
			    this parameter is dB"
			   ::= { gx2Dm200AnalogEntry 3}

		dm200majorHighOffsetNomMonitor          OBJECT-TYPE
			   SYNTAX           Float 
			   ACCESS           read-only
			   STATUS           obsolete
			   DESCRIPTION
			   "The value of this object provides the Major High alarm value
			   of the Offset Monitor Analog parameter.
			   This object is not used by this module and always returns invalid 
			   float value of 0xFFFFFFFF . This object is kept here for persistence."
			   ::= { gx2Dm200AnalogEntry 4}


		dm200majorLowOffsetNomMonitor           OBJECT-TYPE
			   SYNTAX           Float 
			   ACCESS           read-only
			   STATUS           obsolete
			   DESCRIPTION
			   "The value of this object provides the Major Low alarm value
			    of the Offset Monitor Power Analog parameter.
			   This object is not used by this module and always returns invalid 
			   float value of 0xFFFFFFFF . This object is kept here for persistence."
			   ::= { gx2Dm200AnalogEntry 5}

		dm200minorHighOffsetNomMonitor          OBJECT-TYPE
			   SYNTAX           Float
			   ACCESS           read-only
			   STATUS           obsolete
			   DESCRIPTION
			   "The value of this object provides the Minor High alarm value
			    of the Offset Monitor Power Analog parameter.
			   This object is not used by this module and always returns invalid 
			   float value of 0xFFFFFFFF . This object is kept here for persistence."
			   ::= { gx2Dm200AnalogEntry 6}

		dm200minorLowOffsetNomMonitor           OBJECT-TYPE
			   SYNTAX           Float 
			   ACCESS           read-only
			   STATUS           obsolete
			   DESCRIPTION
			   "The value of this object provides the Minor Low alarm value
			    of the Offset Monitor Power Analog parameter.
			   This object is not used by this module and always returns invalid 
			   float value of 0xFFFFFFFF . This object is kept here for persistence."
			   ::= { gx2Dm200AnalogEntry 7}

		dm200currentValueOffsetNomMonitor       OBJECT-TYPE
			   SYNTAX           Float 
			   ACCESS           read-only
			   STATUS           mandatory
			   DESCRIPTION
			   "The value of this object provides the Current value
			    of the Offset Monitor Power Analog parameter."
			   ::= { gx2Dm200AnalogEntry 8}

		dm200stateFlagOffsetNomMonitor          OBJECT-TYPE
			   SYNTAX           INTEGER
								{
								hidden(1),
								read-only(2),
								updateable(3)
								}
			   ACCESS           read-only
			   STATUS           mandatory
			   DESCRIPTION
			   "The value of this object provides the state
			    of the Offset Monitor Power Analog parameter. (1-hidden	
			          2-read-only, 3-updateable)."
			   ::= { gx2Dm200AnalogEntry 9}

		dm200minValueOffsetNomMonitor           OBJECT-TYPE
			   SYNTAX           Float
			   ACCESS           read-only
			   STATUS           mandatory
			   DESCRIPTION
			   "The value of this object provides the minimum value
			    the Offset Monitor Power Analog parameter can achive."
			   ::= { gx2Dm200AnalogEntry 10}

		dm200maxValueOffsetNomMonitor           OBJECT-TYPE
			   SYNTAX           Float
			   ACCESS           read-only
			   STATUS           mandatory
			   DESCRIPTION
			   "The value of this object provides the maximum value
			    the Offset Monitor Power Analog parameter can achive."
			   ::= { gx2Dm200AnalogEntry 11}

		dm200alarmStateOffsetNomMonitor         OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Offset Monitor Power Analog parameter."
			   ::= { gx2Dm200AnalogEntry 12}
			   
-- New Parameter

		dm200labelAttenSetting            OBJECT-TYPE
			   SYNTAX           DisplayString (SIZE (0..80))
			   ACCESS           read-only
			   STATUS           optional
			   DESCRIPTION
			   "The value of this object provides the label of the
			    Attenuator Setting Current Analog parameter."
			   ::= { gx2Dm200AnalogEntry 13}

		dm200uomAttenSetting              OBJECT-TYPE
			   SYNTAX           DisplayString (SIZE (0..80))
			   ACCESS           read-only
			   STATUS           optional
			   DESCRIPTION
			   "The value of this object provides the Unit of Measure of the
			    Attenuator Setting Analog parameter. The unit of measure for 
			    this parameter is dB"
			   ::= { gx2Dm200AnalogEntry 14}

		dm200majorHighAttenSetting        OBJECT-TYPE
			   SYNTAX           Float 
			   ACCESS           read-only
			   STATUS           obsolete
			   DESCRIPTION
			   "The value of this object provides the Major High alarm value
			    of the Attenuator Setting Analog parameter.
			   This object is not used by this module and always returns invalid 
			   float value of 0xFFFFFFFF . This object is kept here for persistence."
			   ::= { gx2Dm200AnalogEntry 15}


		dm200majorLowAttenSetting         OBJECT-TYPE
			   SYNTAX           Float 
			   ACCESS           read-only
			   STATUS           obsolete
			   DESCRIPTION
			   "The value of this object provides the Major Low alarm value
			    of the Attenuator Setting Analog parameter.
			   This object is not used by this module and always returns invalid 
			   float value of 0xFFFFFFFF . This object is kept here for persistence."
			   ::= { gx2Dm200AnalogEntry 16}

		dm200minorHighAttenSetting        OBJECT-TYPE
			   SYNTAX           Float
			   ACCESS           read-only
			   STATUS           obsolete
			   DESCRIPTION
			   "The value of this object provides the Minor High alarm value
			    of the Attenuator Setting Analog parameter.
			   This object is not used by this module and always returns invalid 
			   float value of 0xFFFFFFFF . This object is kept here for persistence."
			   ::= { gx2Dm200AnalogEntry 17}

		dm200minorLowAttenSetting         OBJECT-TYPE
			   SYNTAX           Float 
			   ACCESS           read-only
			   STATUS           obsolete
			   DESCRIPTION
			   "The value of this object provides the Minor Low alarm value
			    of the Attenuator Setting Analog parameter.
			   This object is not used by this module and always returns invalid 
			   float value of 0xFFFFFFFF . This object is kept here for persistence."
			   ::= { gx2Dm200AnalogEntry 18}

		dm200currentValueAttenSetting     OBJECT-TYPE
			   SYNTAX           Float 
			   ACCESS           read-write
			   STATUS           mandatory
			   DESCRIPTION
			   "The value of this object provides the Current value
			    of the Attenuator Setting Analog parameter.
			   This value is a floating point number that is represented as an 
			   IEEE 32 bit number."
			   ::= { gx2Dm200AnalogEntry 19}

		dm200stateFlagAttenSetting        OBJECT-TYPE
			   SYNTAX           INTEGER
								{
								hidden(1),
								read-only(2),
								updateable(3)
								}
			   ACCESS           read-only
			   STATUS           mandatory
			   DESCRIPTION
			   "The value of this object provides the state
			    of the Attenuator Setting Analog parameter.  (1-hidden	
			          2-read-only, 3-updateable)."
			   ::= { gx2Dm200AnalogEntry 20}

		dm200minValueAttenSetting         OBJECT-TYPE
			   SYNTAX           Float
			   ACCESS           read-only
			   STATUS           mandatory
			   DESCRIPTION
			   "The value of this object provides the minimum value
			    the Attenuator Setting Analog parameter can achive.
			   This value is a floating point number that is represented as 
			   an IEEE 32 bit number."
			   ::= { gx2Dm200AnalogEntry 21}

		dm200maxValueAttenSetting         OBJECT-TYPE
			   SYNTAX           Float
			   ACCESS           read-only
			   STATUS           mandatory
			   DESCRIPTION
			   "The value of this object provides the maximum value
			    the Attenuator Setting Analog parameter can achive.
   			   This value is a floating point number that is represented as 
			   an IEEE 32 bit number."
			   ::= { gx2Dm200AnalogEntry 22}

		dm200alarmStateAttenSetting       OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Attenuator Setting Analog parameter."
			   ::= { gx2Dm200AnalogEntry 23}


-- New Parameter

		dm200labelLaserPower            OBJECT-TYPE
			   SYNTAX           DisplayString (SIZE (0..80))
			   ACCESS           read-only
			   STATUS           optional
			   DESCRIPTION
			   "The value of this object provides the label of the
			    Laser Optical Power Analog parameter."
			   ::= { gx2Dm200AnalogEntry 24}

		dm200uomLaserPower              OBJECT-TYPE
			   SYNTAX           DisplayString (SIZE (0..80))
			   ACCESS           read-only
			   STATUS           optional
			   DESCRIPTION
			   "The value of this object provides the Unit of Measure of the
			    Laser Optical Power Analog parameter. The unit of measure for 
			    this parameter is dBm"
			   ::= { gx2Dm200AnalogEntry 25}

		dm200majorHighLaserPower        OBJECT-TYPE
			   SYNTAX           Float 
			   ACCESS           read-only
			   STATUS           mandatory
			   DESCRIPTION
			   "The value of this object provides the Major High alarm value
			    of the Laser Optical Power Analog parameter."
			   ::= { gx2Dm200AnalogEntry 26}


		dm200majorLowLaserPower         OBJECT-TYPE
			   SYNTAX           Float 
			   ACCESS           read-only
			   STATUS           mandatory
			   DESCRIPTION
			   "The value of this object provides the Major Low alarm value
			    of the Laser Optical Power Analog parameter."
			   ::= { gx2Dm200AnalogEntry 27}

		dm200minorHighLaserPower        OBJECT-TYPE
			   SYNTAX           Float
			   ACCESS           read-only
			   STATUS           obsolete
			   DESCRIPTION
			   "The value of this object provides the Minor High alarm value
			    of the Laser Optical Power Analog parameter.
			   This object is not used by this module and always returns invalid 
			   float value of 0xFFFFFFFF . This object is kept here for persistence."
			   ::= { gx2Dm200AnalogEntry 28}

		dm200minorLowLaserPower         OBJECT-TYPE
			   SYNTAX           Float 
			   ACCESS           read-only
			   STATUS           obsolete
			   DESCRIPTION
			   "The value of this object provides the Minor Low alarm value
			    of the Laser Optical Power Analog parameter.
			   This object is not used by this module and always returns invalid 
			   float value of 0xFFFFFFFF . This object is kept here for persistence."
			   ::= { gx2Dm200AnalogEntry 29}

		dm200currentValueLaserPower     OBJECT-TYPE
			   SYNTAX           Float 
			   ACCESS           read-only
			   STATUS           mandatory
			   DESCRIPTION
			   "The value of this object provides the Current value
			    of the Laser Optical Power Analog parameter.
			   This value is a floating point number that is represented as 
			   an IEEE 32 bit number."
			   ::= { gx2Dm200AnalogEntry 30}

		dm200stateFlagLaserPower        OBJECT-TYPE
			   SYNTAX           INTEGER
								{
								hidden(1),
								read-only(2),
								updateable(3)
								}
			   ACCESS           read-only
			   STATUS           mandatory
			   DESCRIPTION
			   "The value of this object provides the state
			    of the Laser Optical Power Analog parameter.  (1-hidden	
			          2-read-only, 3-updateable)."
			   ::= { gx2Dm200AnalogEntry 31}

		dm200minValueLaserPower         OBJECT-TYPE
			   SYNTAX           Float
			   ACCESS           read-only
			   STATUS           mandatory
			   DESCRIPTION
			   "The value of this object provides the minimum value
			    the Laser Optical Power Analog parameter can achive."
			   ::= { gx2Dm200AnalogEntry 32}

		dm200maxValueLaserPower         OBJECT-TYPE
			   SYNTAX           Float
			   ACCESS           read-only
			   STATUS           mandatory
			   DESCRIPTION
			   "The value of this object provides the maximum value
			    the Laser Optical Power Analog parameter can achive."
			   ::= { gx2Dm200AnalogEntry 33}

		dm200alarmStateLaserPower       OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Laser Optical Power Analog parameter."
			   ::= { gx2Dm200AnalogEntry 34}

-- New Parameter


		dm200labelLaserTemp           OBJECT-TYPE
			   SYNTAX           DisplayString (SIZE (0..80))
			   ACCESS           read-only
			   STATUS           optional
			   DESCRIPTION
			   "The value of this object provides the label of the
			    Laser Temperature Analog parameter."
			   ::= { gx2Dm200AnalogEntry 35}

		dm200uomLaserTemp             OBJECT-TYPE
			   SYNTAX           DisplayString (SIZE (0..80))
			   ACCESS           read-only
			   STATUS           optional
			   DESCRIPTION
			   "The value of this object provides the Unit of Measure of the
			    Laser Temperature Analog parameter. The unit of measure for 
			    this parameter is degrees C"
			   ::= { gx2Dm200AnalogEntry 36}

		dm200majorHighLaserTemp       OBJECT-TYPE
			   SYNTAX           Float 
			   ACCESS           read-only
			   STATUS           mandatory
			   DESCRIPTION
			   "The value of this object provides the Major High alarm value
			    of the Laser Temperature Analog parameter."
			   ::= { gx2Dm200AnalogEntry 37}


		dm200majorLowLaserTemp        OBJECT-TYPE
			   SYNTAX           Float 
			   ACCESS           read-only
			   STATUS           mandatory
			   DESCRIPTION
			   "The value of this object provides the Major Low alarm value
			    of the Laser Temperature Analog parameter."
			   ::= { gx2Dm200AnalogEntry 38}

		dm200minorHighLaserTemp       OBJECT-TYPE
			   SYNTAX           Float
			   ACCESS           read-only
			   STATUS           obsolete
			   DESCRIPTION
			   "The value of this object provides the Minor High alarm value
			    of the Laser Temperature Analog parameter."
			   ::= { gx2Dm200AnalogEntry 39}

		dm200minorLowLaserTemp        OBJECT-TYPE
			   SYNTAX           Float 
			   ACCESS           read-only
			   STATUS           obsolete
			   DESCRIPTION
			   "The value of this object provides the Minor Low alarm value
			    of the Laser Temperature Analog parameter."
			   ::= { gx2Dm200AnalogEntry 40}

		dm200currentValueLaserTemp    OBJECT-TYPE
			   SYNTAX           Float 
			   ACCESS           read-only
			   STATUS           mandatory
			   DESCRIPTION
			   "The value of this object provides the Current value
			    of the Laser Temperature Analog parameter."
			   ::= { gx2Dm200AnalogEntry 41}

		dm200stateFlagLaserTemp       OBJECT-TYPE
			   SYNTAX           INTEGER
								{
								hidden(1),
								read-only(2),
								updateable(3)
								}
			   ACCESS           read-only
			   STATUS           mandatory
			   DESCRIPTION
			   "The value of this object provides the state
			    of the Laser Temperature Analog parameter.  (1-hidden	
			          2-read-only, 3-updateable)."
			   ::= { gx2Dm200AnalogEntry 42}

		dm200minValueLaserTemp        OBJECT-TYPE
			   SYNTAX           Float
			   ACCESS           read-only
			   STATUS           mandatory
			   DESCRIPTION
			   "The value of this object provides the minimum value
			    the Laser Temperature Analog parameter can achive."
			   ::= { gx2Dm200AnalogEntry 43}

		dm200maxValueLaserTemp        OBJECT-TYPE
			   SYNTAX           Float
			   ACCESS           read-only
			   STATUS           mandatory
			   DESCRIPTION
			   "The value of this object provides the maximum value
			    the Laser Temperature Analog parameter can achive."
			   ::= { gx2Dm200AnalogEntry 44}

		dm200alarmStateLaserTemp      OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Laser Temperature Analog parameter."
			   ::= { gx2Dm200AnalogEntry 45}

-- New Parameter

		dm200labelLaserCurrent            OBJECT-TYPE
			   SYNTAX           DisplayString (SIZE (0..80))
			   ACCESS           read-only
			   STATUS           optional
			   DESCRIPTION
			   "The value of this object provides the label of the
			    Laser Bias Current Analog parameter."
			   ::= { gx2Dm200AnalogEntry 46}

		dm200uomLaserCurrent              OBJECT-TYPE
			   SYNTAX           DisplayString (SIZE (0..80))
			   ACCESS           read-only
			   STATUS           optional
			   DESCRIPTION
			   "The value of this object provides the Unit of Measure of the
			    Laser Bias Current Analog parameter. The unit of measure for 
			    this parameter is mA"
			   ::= { gx2Dm200AnalogEntry 47}

		dm200majorHighLaserCurrent        OBJECT-TYPE
			   SYNTAX           Float 
			   ACCESS           read-only
			   STATUS           mandatory
			   DESCRIPTION
			   "The value of this object provides the Major High alarm value
			    of the Laser Bias Current Analog parameter."
			   ::= { gx2Dm200AnalogEntry 48}


		dm200majorLowLaserCurrent         OBJECT-TYPE
			   SYNTAX           Float 
			   ACCESS           read-only
			   STATUS           mandatory
			   DESCRIPTION
			   "The value of this object provides the Major Low alarm value
			    of the Laser Bias Current Analog parameter."
			   ::= { gx2Dm200AnalogEntry 49}

		dm200minorHighLaserCurrent        OBJECT-TYPE
			   SYNTAX           Float
			   ACCESS           read-only
			   STATUS           obsolete
			   DESCRIPTION
			   "The value of this object provides the Minor High alarm value
			    of the Laser Bias Current Analog parameter.
			   This object is not used by this module and always returns invalid 
			   float value of 0xFFFFFFFF . This object is kept here for persistence."
			   ::= { gx2Dm200AnalogEntry 50}

		dm200minorLowLaserCurrent         OBJECT-TYPE
			   SYNTAX           Float 
			   ACCESS           read-only
			   STATUS           obsolete
			   DESCRIPTION
			   "The value of this object provides the Minor Low alarm value
			    of the Laser Bias Current Analog parameter.
			   This object is not used by this module and always returns invalid 
			   float value of 0xFFFFFFFF . This object is kept here for persistence."
			   ::= { gx2Dm200AnalogEntry 51}

		dm200currentValueLaserCurrent     OBJECT-TYPE
			   SYNTAX           Float 
			   ACCESS           read-only
			   STATUS           mandatory
			   DESCRIPTION
			   "The value of this object provides the Current value
			    of the Laser Bias Current Analog parameter."
			   ::= { gx2Dm200AnalogEntry 52}

		dm200stateFlagLaserCurrent        OBJECT-TYPE
			   SYNTAX           INTEGER
								{
								hidden(1),
								read-only(2),
								updateable(3)
								}
			   ACCESS           read-only
			   STATUS           mandatory
			   DESCRIPTION
			   "The value of this object provides the state
			    of the Laser Bias Current Analog parameter.  (1-hidden	
			          2-read-only, 3-updateable)."
			   ::= { gx2Dm200AnalogEntry 53}

		dm200minValueLaserCurrent         OBJECT-TYPE
			   SYNTAX           Float
			   ACCESS           read-only
			   STATUS           mandatory
			   DESCRIPTION
			   "The value of this object provides the minimum value
			    the Laser Bias Current Analog parameter can achive."
			   ::= { gx2Dm200AnalogEntry 54}

		dm200maxValueLaserCurrent         OBJECT-TYPE
			   SYNTAX           Float
			   ACCESS           read-only
			   STATUS           mandatory
			   DESCRIPTION
			   "The value of this object provides the maximum value
			    the Laser Bias Current Analog parameter can achive."
			   ::= { gx2Dm200AnalogEntry 55}

		dm200alarmStateLaserCurrent       OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Laser Bias Current Analog parameter."
			   ::= { gx2Dm200AnalogEntry 56}

-- New Parameter

		dm200labelTecCurrent              OBJECT-TYPE
			   SYNTAX           DisplayString (SIZE (0..80))
			   ACCESS           read-only
			   STATUS           optional
			   DESCRIPTION
			   "The value of this object provides the label of the
			    TEC Current Analog parameter."
			   ::= { gx2Dm200AnalogEntry 57}

		dm200uomTecCurrent                OBJECT-TYPE
			   SYNTAX           DisplayString (SIZE (0..80))
			   ACCESS           read-only
			   STATUS           optional
			   DESCRIPTION
			   "The value of this object provides the Unit of Measure of the
			    TEC Current Analog parameter. The unit of measure for 
			    this parameter is mA"
			   ::= { gx2Dm200AnalogEntry 58}

		dm200majorHighTecCurrent          OBJECT-TYPE
			   SYNTAX           Float 
			   ACCESS           read-only
			   STATUS           mandatory
			   DESCRIPTION
			   "The value of this object provides the Major High alarm value
			    of the TEC Current Analog parameter."
			   ::= { gx2Dm200AnalogEntry 59}


		dm200majorLowTecCurrent           OBJECT-TYPE
			   SYNTAX           Float 
			   ACCESS           read-only
			   STATUS           mandatory
			   DESCRIPTION
			   "The value of this object provides the Major Low alarm value
			    of the TEC Current Analog parameter."
			   ::= { gx2Dm200AnalogEntry 60}

		dm200minorHighTecCurrent          OBJECT-TYPE
			   SYNTAX           Float
			   ACCESS           read-only
			   STATUS           obsolete
			   DESCRIPTION
			   "The value of this object provides the Minor High alarm value
			    of the TEC Current Analog parameter.
			   This object is not used by this module and always returns invalid 
			   float value of 0xFFFFFFFF . This object is kept here for persistence."
			   ::= { gx2Dm200AnalogEntry 61}

		dm200minorLowTecCurrent           OBJECT-TYPE
			   SYNTAX           Float 
			   ACCESS           read-only
			   STATUS           obsolete
			   DESCRIPTION
			   "The value of this object provides the Minor Low alarm value
			    of the TEC Current Analog parameter.
			   This object is not used by this module and always returns invalid 
			   float value of 0xFFFFFFFF . This object is kept here for persistence."
			   ::= { gx2Dm200AnalogEntry 62}

		dm200currentValueTecCurrent       OBJECT-TYPE
			   SYNTAX           Float 
			   ACCESS           read-only
			   STATUS           mandatory
			   DESCRIPTION
			   "The value of this object provides the Current value
			    of the TEC Current Analog parameter."
			   ::= { gx2Dm200AnalogEntry 63}

		dm200stateFlagTecCurrent          OBJECT-TYPE
			   SYNTAX           INTEGER
								{
								hidden(1),
								read-only(2),
								updateable(3)
								}
			   ACCESS           read-only
			   STATUS           mandatory
			   DESCRIPTION
			   "The value of this object provides the state
			    of the TEC Current Analog parameter.  (1-hidden	
			          2-read-only, 3-updateable)."
			   ::= { gx2Dm200AnalogEntry 64}

		dm200minValueTecCurrent           OBJECT-TYPE
			   SYNTAX           Float
			   ACCESS           read-only
			   STATUS           mandatory
			   DESCRIPTION
			   "The value of this object provides the minimum value
			    the TEC Current Analog parameter can achive."
			   ::= { gx2Dm200AnalogEntry 65}

		dm200maxValueTecCurrent           OBJECT-TYPE
			   SYNTAX           Float
			   ACCESS           read-only
			   STATUS           mandatory
			   DESCRIPTION
			   "The value of this object provides the maximum value
			    the TEC Current Analog parameter can achive."
			   ::= { gx2Dm200AnalogEntry 66}

		dm200alarmStateTecCurrent         OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the TEC Current Analog parameter."
			   ::= { gx2Dm200AnalogEntry 67}

-- New Parameter

		dm200labelModTemp           OBJECT-TYPE
			   SYNTAX           DisplayString (SIZE (0..80))
			   ACCESS           read-only
			   STATUS           optional
			   DESCRIPTION
			   "The value of this object provides the label of the
			    Module Temperature Analog parameter."
			   ::= { gx2Dm200AnalogEntry 68}

		dm200uomModTemp             OBJECT-TYPE
			   SYNTAX           DisplayString (SIZE (0..80))
			   ACCESS           read-only
			   STATUS           optional
			   DESCRIPTION
			   "The value of this object provides the Unit of Measure of the
			    Module Temperature Analog parameter. The unit of measure for 
			    this parameter is degrees C"
			   ::= { gx2Dm200AnalogEntry 69}

		dm200majorHighModTemp       OBJECT-TYPE
			   SYNTAX           Float 
			   ACCESS           read-only
			   STATUS           mandatory
			   DESCRIPTION
			   "The value of this object provides the Major High alarm value
			    of the Module Temperature Analog parameter."
			   ::= { gx2Dm200AnalogEntry 70}


		dm200majorLowModTemp        OBJECT-TYPE
			   SYNTAX           Float 
			   ACCESS           read-only
			   STATUS           mandatory
			   DESCRIPTION
			   "The value of this object provides the Major Low alarm value
			    of the Module Temperature Analog parameter."
			   ::= { gx2Dm200AnalogEntry 71}

		dm200minorHighModTemp       OBJECT-TYPE
			   SYNTAX           Float
			   ACCESS           read-only
			   STATUS           mandatory
			   DESCRIPTION
			   "The value of this object provides the Minor High alarm value
			    of the Module Temperature Analog parameter."
			   ::= { gx2Dm200AnalogEntry 72}

		dm200minorLowModTemp        OBJECT-TYPE
			   SYNTAX           Float 
			   ACCESS           read-only
			   STATUS           mandatory
			   DESCRIPTION
			   "The value of this object provides the Minor Low alarm value
			    of the Module Temperature Analog parameter."
			   ::= { gx2Dm200AnalogEntry 73}

		dm200currentValueModTemp    OBJECT-TYPE
			   SYNTAX           Float 
			   ACCESS           read-only
			   STATUS           mandatory
			   DESCRIPTION
			   "The value of this object provides the Current value
			    of the Module Temperature Analog parameter."
			   ::= { gx2Dm200AnalogEntry 74}

		dm200stateFlagModTemp       OBJECT-TYPE
			   SYNTAX           INTEGER
								{
								hidden(1),
								read-only(2),
								updateable(3)
								}
			   ACCESS           read-only
			   STATUS           mandatory
			   DESCRIPTION
			   "The value of this object provides the state
			    of the Module Temperature Analog parameter.  (1-hidden	
			          2-read-only, 3-updateable)."
			   ::= { gx2Dm200AnalogEntry 75}

		dm200minValueModTemp        OBJECT-TYPE
			   SYNTAX           Float
			   ACCESS           read-only
			   STATUS           mandatory
			   DESCRIPTION
			   "The value of this object provides the minimum value  
			    the Module Temperature Analog parameter can achive."
			   ::= { gx2Dm200AnalogEntry 76}

		dm200maxValueModTemp        OBJECT-TYPE
			   SYNTAX           Float
			   ACCESS           read-only
			   STATUS           mandatory
			   DESCRIPTION
			   "The value of this object provides the maximum value
			    the Module Temperature Analog parameter can achive."
			   ::= { gx2Dm200AnalogEntry 77}

		dm200alarmStateModTemp      OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Module Temperature Analog parameter."
			   ::= { gx2Dm200AnalogEntry 78}

-- New Parameter

		dm200labelFanCurrent               OBJECT-TYPE
			   SYNTAX           DisplayString (SIZE (0..80))
			   ACCESS           read-only
			   STATUS           optional
			   DESCRIPTION
			   "The value of this object provides the label of the
			    Fan Current Analog parameter."
			   ::= { gx2Dm200AnalogEntry 79}

		dm200uomFanCurrent                 OBJECT-TYPE
			   SYNTAX           DisplayString (SIZE (0..80))
			   ACCESS           read-only
			   STATUS           optional
			   DESCRIPTION
			   "The value of this object provides the Unit of Measure of the
			    Fan Current Analog parameter. The unit of measure for 
			    this parameter is mA"
			   ::= { gx2Dm200AnalogEntry 80}

		dm200majorHighFanCurrent           OBJECT-TYPE
			   SYNTAX           Float 
			   ACCESS           read-only
			   STATUS           mandatory
			   DESCRIPTION
			   "The value of this object provides the Major High alarm value
			    of the Fan Current Analog parameter."
			   ::= { gx2Dm200AnalogEntry 81}


		dm200majorLowFanCurrent            OBJECT-TYPE
			   SYNTAX           Float 
			   ACCESS           read-only
			   STATUS           mandatory
			   DESCRIPTION
			   "The value of this object provides the Major Low alarm value
			    of the Fan Current Analog parameter."
			   ::= { gx2Dm200AnalogEntry 82}

		dm200minorHighFanCurrent           OBJECT-TYPE
			   SYNTAX           Float
			   ACCESS           read-only
			   STATUS           obsolete
			   DESCRIPTION
			   "The value of this object provides the Minor High alarm value
			    of the Fan Current Analog parameter.
			   This object is not used by this module and always returns invalid 
			   float value of 0xFFFFFFFF . This object is kept here for persistence."
			   ::= { gx2Dm200AnalogEntry 83}

		dm200minorLowFanCurrent            OBJECT-TYPE
			   SYNTAX           Float 
			   ACCESS           read-only
			   STATUS           obsolete
			   DESCRIPTION
			   "The value of this object provides the Minor Low alarm value
			    of the Fan Current Analog parameter.
			   This object is not used by this module and always returns invalid 
			   float value of 0xFFFFFFFF . This object is kept here for persistence."
			   ::= { gx2Dm200AnalogEntry 84}

		dm200currentValueFanCurrent        OBJECT-TYPE
			   SYNTAX           Float 
			   ACCESS           read-only
			   STATUS           mandatory
			   DESCRIPTION
			   "The value of this object provides the Current value
			    of the Fan Current Analog parameter."
			   ::= { gx2Dm200AnalogEntry 85}

		dm200stateFlagFanCurrent           OBJECT-TYPE
			   SYNTAX           INTEGER
								{
								hidden(1),
								read-only(2),
								updateable(3)
								}
			   ACCESS           read-only
			   STATUS           mandatory
			   DESCRIPTION
			   "The value of this object provides the state
			    of the Fan Current Analog parameter.  (1-hidden	
			          2-read-only, 3-updateable)."
			   ::= { gx2Dm200AnalogEntry 86}

		dm200minValueFanCurrent            OBJECT-TYPE
			   SYNTAX           Float
			   ACCESS           read-only
			   STATUS           mandatory
			   DESCRIPTION
			   "The value of this object provides the minimum value
			    the Fan Current Analog parameter can achive."
			   ::= { gx2Dm200AnalogEntry 87}

		dm200maxValueFanCurrent            OBJECT-TYPE
			   SYNTAX           Float
			   ACCESS           read-only
			   STATUS           mandatory
			   DESCRIPTION
			   "The value of this object provides the maximum value
			    the Fan Current Analog parameter can achive."
			   ::= { gx2Dm200AnalogEntry 88}

		dm200alarmStateFanCurrent          OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Fan Current Analog parameter."
			   ::= { gx2Dm200AnalogEntry 89}

-- ************************ Digital parameters **********************************

		gx2Dm200DigitalTableIndex              OBJECT-TYPE
			   SYNTAX           INTEGER (1..2147483647)
			   ACCESS           read-only
			   STATUS           mandatory
			   DESCRIPTION
			   "The value of this object identifies the network
			    element. This index is equal to the
			    hfcCommonTableIndex for the same element."
			   ::= { gx2Dm200DigitalEntry 1}

-- New parameter
		dm200labelRfInput                	OBJECT-TYPE
			   SYNTAX       		DisplayString (SIZE (0..80))         
			   ACCESS           	read-only
			   STATUS           	optional
			   DESCRIPTION
			   "The value of this object provides the label of the
			    RF Input Control  Digital parameter."
			   ::= { gx2Dm200DigitalEntry 2}

		dm200enumRfInput               		OBJECT-TYPE
			   SYNTAX       		DisplayString (SIZE (0..80))         
			   ACCESS           	read-only
			   STATUS           	optional
			   DESCRIPTION
			   "The value of this object represents the Enumeration values
			    possible for the Digital parameter. Each Enumerated values is
			    separated by a common. The first value has a enumerated value of 1."
			   ::= { gx2Dm200DigitalEntry 3}

		dm200valueRfInput                	OBJECT-TYPE
			   SYNTAX       		INTEGER
					    		{
							off(1),
							on(2)
					    		}
			   ACCESS           	read-write
			   STATUS           	mandatory
			   DESCRIPTION
			   "The value of this object is the current value of the parameter."
			   ::= { gx2Dm200DigitalEntry 4}

		dm200stateflagRfInput              OBJECT-TYPE
			   SYNTAX       		INTEGER
								{
								hidden(1),
								read-only(2),
								updateable(3)
								}
			   ACCESS           	read-only
			   STATUS           	mandatory
			   DESCRIPTION
			   "The value of this object provides the state
			    of the RF Input Control  Digital parameter.  (1-hidden	
			          2-read-only, 3-updateable)."
			   ::= { gx2Dm200DigitalEntry 5}

-- New parameter
		dm200labelOptOutput                OBJECT-TYPE
			   SYNTAX       		DisplayString (SIZE (0..80))         
			   ACCESS           	read-only
			   STATUS           	optional
			   DESCRIPTION
			   "The value of this object provides the label of the
			    Optical Output Control  Digital parameter."
			   ::= { gx2Dm200DigitalEntry 6}

		dm200enumOptOutput               	      OBJECT-TYPE
			   SYNTAX          	DisplayString (SIZE (0..80))         
			   ACCESS           	read-only
			   STATUS           	optional
			   DESCRIPTION
			   "The value of this object represents the Enumeration values
			    possible for the Digital parameter. Each Enumerated values is
			    separated by a common. The first value has a enumerated value of 1."
			   ::= { gx2Dm200DigitalEntry 7}

		dm200valueOptOutput                OBJECT-TYPE
			   SYNTAX       		INTEGER
					    		{
							off(1),
							on(2)
					    		}
			   ACCESS           	read-write
			   STATUS           	mandatory
			   DESCRIPTION
			   "The value of this object is the current value of the parameter."
			   ::= { gx2Dm200DigitalEntry 8}

		dm200stateflagOptOutput            OBJECT-TYPE
			   SYNTAX      		INTEGER
								{
								hidden(1),
								read-only(2),
								updateable(3)
								}
			   ACCESS           	read-only
			   STATUS           	mandatory
			   DESCRIPTION
			   "The value of this object provides the state
			    of the the parameter.  (1-hidden, 2-read-only, 3-updateable)."
			   ::= { gx2Dm200DigitalEntry 9}
-- New parameter
		dm200labelSbsControl                OBJECT-TYPE
			   SYNTAX         	DisplayString (SIZE (0..80))         
			   ACCESS           	read-only
			   STATUS           	optional
			   DESCRIPTION
			   "The value of this object provides the label of the
			    SBS Control Digital parameter."
			   ::= { gx2Dm200DigitalEntry 10}

		dm200enumSbsControl               	OBJECT-TYPE
			   SYNTAX         	DisplayString (SIZE (0..80))         
			   ACCESS           	read-only
			   STATUS           	optional
			   DESCRIPTION
			   "The value of this object represents the Enumeration values
			    possible for the Digital parameter. Each Enumerated values is
			    separated by a common. The first value has a enumerated value of 1."
			   ::= { gx2Dm200DigitalEntry 11}

		dm200valueSbsControl                OBJECT-TYPE
			   SYNTAX       		INTEGER
					    		{
							off(1),
							on(2)
					    		}
			   ACCESS           	read-write
			   STATUS           	mandatory
			   DESCRIPTION
			   "The value of this object is the current value of the parameter."
			   ::= { gx2Dm200DigitalEntry 12}

		dm200stateflagSbsControl            OBJECT-TYPE
			   SYNTAX         	INTEGER
								{
								hidden(1),
								read-only(2),
								updateable(3)
								}
			   ACCESS           	read-only
			   STATUS           	mandatory
			   DESCRIPTION
			   "The value of this object provides the state
			    of the the parameter. (1-hidden, 2-read-only, 3-updateable)."
			   ::= { gx2Dm200DigitalEntry 13}
-- New parameter
		dm200labelFactoryDefault            	OBJECT-TYPE
			   SYNTAX       	      DisplayString (SIZE (0..80))         
			   ACCESS           	read-only
			   STATUS           	optional
			   DESCRIPTION
			   "The value of this object provides the label of the
			    Factory Default Digital parameter."
			   ::= { gx2Dm200DigitalEntry 14}

		dm200enumFactoryDefault               	OBJECT-TYPE
			   SYNTAX       	      DisplayString (SIZE (0..80))         
			   ACCESS           	read-only
			   STATUS           	optional
			   DESCRIPTION
			   "The value of this object represents the Enumeration values
			    possible for the Digital parameter. Each Enumerated values is
			    separated by a common. The first value has a enumerated value 
				of 1.."
			   ::= { gx2Dm200DigitalEntry 15}

		dm200valueFactoryDefault              OBJECT-TYPE
			   SYNTAX       		INTEGER
					    		{
							off(1),
							on(2)
					    		}
			   ACCESS           	read-write
			   STATUS           	mandatory
			   DESCRIPTION
			   "The value of this object is the current value of the parameter.
			   Return value is meaningless"
			   ::= { gx2Dm200DigitalEntry 16}

		dm200stateflagFactoryDefault        	OBJECT-TYPE
			   SYNTAX       		INTEGER
								{
								hidden(1),
								read-only(2),
								updateable(3)
								}
			   ACCESS           	read-only
			   STATUS           	mandatory
			   DESCRIPTION
			   "The value of this object provides the state
			    of the the parameter. (1-hidden, 2-read-only, 3-updateable)."
			   ::= { gx2Dm200DigitalEntry 17}

-- *********** STATUS *****************
		gx2Dm200StatusTableIndex			OBJECT-TYPE
			   SYNTAX				INTEGER (1..2147483647)
			   ACCESS				read-only
			   STATUS				mandatory
			   DESCRIPTION			
			   "The value of this object identifies the network
			    element. This index is equal to the
			    hfcCommonTableIndex for the same element."
			   ::= { gx2Dm200StatusEntry 1}

--New Parameter
		dm200labelBoot               	OBJECT-TYPE
			   SYNTAX       		DisplayString (SIZE (0..80))         
			   ACCESS           	read-only
			   STATUS           	optional
			   DESCRIPTION
			   "The value of this object provides the label of the
			    Boot Status  Status parameter."
			   ::= { gx2Dm200StatusEntry 2}

		dm200valueBoot              		OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (1-ok, 2-undetermined
			    3-warning, 4-minor, 5-major, 6-critical)."
			   ::= { gx2Dm200StatusEntry 3}

		dm200stateflagBoot     	OBJECT-TYPE
			   SYNTAX       		INTEGER
								{
								hidden(1),
								read-only(2),
								updateable(3)
								}
			   ACCESS           	read-only
			   STATUS           	mandatory
			   DESCRIPTION
			   "The value of this object provides the state
			    of the the parameter. (1-hidden, 2-read-only, 3-updateable)."
			   ::= { gx2Dm200StatusEntry  4}



--New Parameter
		dm200labelFlash               	OBJECT-TYPE
			   SYNTAX       		DisplayString (SIZE (0..80))         
			   ACCESS           	read-only
			   STATUS           	optional
			   DESCRIPTION
			   "The value of this object provides the label of the
			    Flash Status  Status parameter."
			   ::= { gx2Dm200StatusEntry 5}

		dm200valueFlash              	OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (1-ok, 2-undetermined
			    3-warning, 4-minor, 5-major, 6-critical)."
			   ::= { gx2Dm200StatusEntry 6}

		dm200stateflagFlash     	OBJECT-TYPE
			   SYNTAX       		INTEGER
								{
								hidden(1),
								read-only(2),
								updateable(3)
								}
			   ACCESS           	read-only
			   STATUS           	mandatory
			   DESCRIPTION
			   "The value of this object provides the state
			    of the the parameter. (1-hidden, 2-read-only, 3-updateable)."
			   ::= { gx2Dm200StatusEntry  7}

--New Parameter
		dm200labelFactoryDataCRC           OBJECT-TYPE
			   SYNTAX       		DisplayString (SIZE (0..80))         
			   ACCESS           	read-only
			   STATUS           	optional
			   DESCRIPTION
			   "The value of this object provides the label of the
			    Factory Data CRC Status parameter."
			   ::= { gx2Dm200StatusEntry 8}

		dm200valueFactoryDataCRC          	OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (1-ok, 2-undetermined
			    3-warning, 4-minor, 5-major, 6-critical)."
			   ::= { gx2Dm200StatusEntry 9}

		dm200stateflagFactoryDataCRC     	OBJECT-TYPE
			   SYNTAX       		INTEGER
								{
								hidden(1),
								read-only(2),
								updateable(3)
								}
			   ACCESS           	read-only
			   STATUS           	mandatory
			   DESCRIPTION
			   "The value of this object provides the state
			    of the the parameter. (1-hidden, 2-read-only, 3-updateable)."
			   ::= { gx2Dm200StatusEntry  10}


--New Parameter
		dm200labelLaserDataCRC           OBJECT-TYPE
			   SYNTAX       		DisplayString (SIZE (0..80))         
			   ACCESS           	read-only
			   STATUS           	optional
			   DESCRIPTION
			   "The value of this object provides the label of the
			    Laser Data CRC Status parameter."
			   ::= { gx2Dm200StatusEntry 11}

		dm200valueLaserDataCRC          	OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (1-ok, 2-undetermined
			    3-warning, 4-minor, 5-major, 6-critical)."
			   ::= { gx2Dm200StatusEntry 12}

		dm200stateflagLaserDataCRC     	OBJECT-TYPE
			   SYNTAX       		INTEGER
								{
								hidden(1),
								read-only(2),
								updateable(3)
								}
			   ACCESS           	read-only
			   STATUS           	mandatory
			   DESCRIPTION
			   "The value of this object provides the state
			    of the the parameter. (1-hidden, 2-read-only, 3-updateable)."
			   ::= { gx2Dm200StatusEntry  13}



--New Parameter
		dm200labelAlarmDataCrc               	      OBJECT-TYPE
			   SYNTAX       		DisplayString (SIZE (0..80))         
			   ACCESS           	read-only
			   STATUS           	optional
			   DESCRIPTION
			   "The value of this object provides the label of the
			    Alarm Data Crc parameter."
			   ::= { gx2Dm200StatusEntry 14}

		dm200valueAlarmDataCrc              		OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (1-ok, 2-undetermined
			    3-warning, 4-minor, 5-major, 6-critical)."
			   ::= { gx2Dm200StatusEntry 15}

		dm200stateflagAlarmDataCrc     	OBJECT-TYPE
			   SYNTAX       		INTEGER
								{
								hidden(1),
								read-only(2),
								updateable(3)
								}
			   ACCESS           	read-only
			   STATUS           	mandatory
			   DESCRIPTION
			   "The value of this object provides the state
			    of the the parameter. (1-hidden, 2-read-only, 3-updateable)."
			   ::= { gx2Dm200StatusEntry  16}

 
 --New Parameter
		dm200labelRFInputStatus               	      OBJECT-TYPE
			   SYNTAX       		DisplayString (SIZE (0..80))         
			   ACCESS           	read-only
			   STATUS           	optional
			   DESCRIPTION
			   "The value of this object provides the label of the
			    Alarm Data Crc parameter."
			   ::= { gx2Dm200StatusEntry 17}

		dm200valueRFInputStatus              		OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (1-ok, 2-undetermined
			    3-warning, 4-minor, 5-major, 6-critical)."
			   ::= { gx2Dm200StatusEntry 18}

		dm200stateflagRFInputStatus     	OBJECT-TYPE
			   SYNTAX       		INTEGER
								{
								hidden(1),
								read-only(2),
								updateable(3)
								}
			   ACCESS           	read-only
			   STATUS           	mandatory
			   DESCRIPTION
			   "The value of this object provides the state
			    of the the parameter. (1-hidden, 2-read-only, 3-updateable)."
			   ::= { gx2Dm200StatusEntry  19}        
			   
            -- ************ FACTORY DATA ****************
		gx2Dm200FactoryTableIndex			OBJECT-TYPE
			   SYNTAX				INTEGER (1..2147483647)
			   ACCESS				read-only
			   STATUS				mandatory
			   DESCRIPTION			
			   "The value of this object identifies the network
			    element. This index is equal to the
			    hfcCommonTableIndex for the same element."
			   ::= { gx2Dm200FactoryEntry 1}

		dm200bootControlByte          	OBJECT-TYPE
			   SYNTAX       		INTEGER
			   ACCESS           	read-only
			   STATUS           	mandatory
			   DESCRIPTION
			   "The value of this object indicates which bank the firmware
			    is currently being boot from."
			   ::= { gx2Dm200FactoryEntry 2}

		dm200bootStatusByte          	OBJECT-TYPE
			   SYNTAX       		INTEGER
			   ACCESS           	read-only
			   STATUS           	mandatory
			   DESCRIPTION
			   "This object indicates the status of the last boot.  Bit 2 = 
			   Bank 0/1 Active (0 = Bank 0, 1 = Bank 1), Bit 1 = Bank 1 Fail 
			   and Bit 0 = Bank 0 Fail (0 = Pass, 1 = Fail)"
			   ::= { gx2Dm200FactoryEntry 3}

		dm200bank1CRC          		OBJECT-TYPE
			   SYNTAX       		INTEGER
			   ACCESS           	read-only
			   STATUS           	mandatory
			   DESCRIPTION
			   "This object provides the CRC code of bank 0.  The display 
			   formate for the data is Hex."
			   ::= { gx2Dm200FactoryEntry 4}

		dm200bank2CRC          		OBJECT-TYPE
			   SYNTAX       		INTEGER
			   ACCESS           	read-only
			   STATUS           	mandatory
			   DESCRIPTION
			   "This object provides the CRC code of bank 1.The display 
			   formate for the data is Hex."
			   ::= { gx2Dm200FactoryEntry 5}

		dm200prgEEPROMByte          		OBJECT-TYPE
			   SYNTAX       		INTEGER
			   ACCESS           	read-only
			   STATUS           	mandatory
			   DESCRIPTION
			   "This object indicates if the EEPROM has been programmed"
			   ::= { gx2Dm200FactoryEntry 6}

		dm200factoryCRC          		OBJECT-TYPE
			   SYNTAX       		INTEGER
			   ACCESS           	read-only
			   STATUS           	mandatory
			   DESCRIPTION
			   "This object provides the CRC code for the Factory data."
			   ::= { gx2Dm200FactoryEntry 7}

		dm200calculateCRC          		OBJECT-TYPE
			   SYNTAX       		INTEGER
					    		{
							factory(1),
							na(2),
							alarm(3)
					    		}
			   ACCESS           	read-only
			   STATUS           	obsolete
			   DESCRIPTION
			   "This object indicates which of the Enums will have the CRC 
			   calculated."
			   ::= { gx2Dm200FactoryEntry 8}

		dm200hourMeter          		OBJECT-TYPE
			   SYNTAX       		INTEGER
			   ACCESS           	read-only
			   STATUS           	mandatory
			   DESCRIPTION
			   "This object provides the hour meter reading of the module."
			   ::= { gx2Dm200FactoryEntry 9}

		dm200flashPrgCntA          		OBJECT-TYPE
			   SYNTAX       		INTEGER
			   ACCESS           	read-only
			   STATUS           	mandatory
			   DESCRIPTION
			   "This object provides the number of times Bank 1 flash has been 
                      programmed."
			   ::= { gx2Dm200FactoryEntry 10}

		dm200flashPrgCntB          		OBJECT-TYPE
			   SYNTAX       		INTEGER
			   ACCESS           	read-only
			   STATUS           	mandatory
			   DESCRIPTION
			   "This object provides the number of times Bank 1 flash has been 
                      programmed."
			   ::= { gx2Dm200FactoryEntry 11}

		dm200flashBankARev          		OBJECT-TYPE
			   SYNTAX       		DisplayString (SIZE (0..80))
			   ACCESS           	read-only
			   STATUS           	mandatory
			   DESCRIPTION
			   "This object provides the revision of flash bank 0.  The rev is
			   2 characters."
			   ::= { gx2Dm200FactoryEntry 12}

		dm200flashBankBRev          		OBJECT-TYPE
			   SYNTAX       		DisplayString (SIZE (0..80))
			   ACCESS           	read-only
			   STATUS           	mandatory
			   DESCRIPTION
			   "This object provides the revision of flash bank 1.  The rev is
			   2 characters."
			   ::= { gx2Dm200FactoryEntry 13}



-- ****************************************************************
--
-- TRAP DEFINITIONS
--
--
-- Every trap generated by an HFC agents will include first 9 identical
-- fields. If particular variable is not supported in
-- particular TRAP-TYPE then default value will be returned.
--
-- DESCRIPTION will include explanation of use of generic
-- variables (trapAdditionalInfo******.)  If no
-- DESCRIPTION is given then generic variables will contain
-- default values.
--
-- *****************************************************************

-- **************************************************************************
--                        DM200 Module traps
-- **************************************************************************
   trapDM200ConfigChangeInteger TRAP-TYPE
       ENTERPRISE gx2Dm200
       VARIABLES
	       {       
		trapIdentifier,
		trapNetworkElemModelNumber,
		trapNetworkElemSerialNum,
		trapPerceivedSeverity,
		trapNetworkElemOperState,
		trapNetworkElemAlarmStatus,  
		trapNetworkElemAdminState,
		trapNetworkElemAvailStatus,
		trapText,
		trapChangedObjectId,
		trapChangedValueInteger,
		trapNETrapLastTrapTimeStamp
	       }
       DESCRIPTION
	"This trap is issued if configuration of a single variable
	 with integer type was changed (via ANY interface).  
	 TrapChangedValueInteger variable may contain current reading
	 of that variable.
	 trapPerceivedSeverity - 'indeterminate'"
  ::= 1

   trapDM200ConfigChangeDisplayString TRAP-TYPE
       ENTERPRISE gx2Dm200
       VARIABLES
	       {       
		trapIdentifier,
		trapNetworkElemModelNumber,
		trapNetworkElemSerialNum,
		trapPerceivedSeverity,
		trapNetworkElemOperState,
		trapNetworkElemAlarmStatus,  
		trapNetworkElemAdminState,
		trapNetworkElemAvailStatus,
		trapText,
		trapChangedObjectId,
		trapChangedValueDisplayString,
		trapNETrapLastTrapTimeStamp
	       }
       DESCRIPTION
	"This trap is issued if configuration of a single variable
	 with DispalayString type was changed (via ANY interface).  
	 TrapChangedValueDisplayString variable may contain current reading
	 of that variable.
	 trapPerceivedSeverity - 'indeterminate'"
  ::= 2

  trapDM200fanCurrentAlarm TRAP-TYPE
	ENTERPRISE gx2Dm200
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Fan Current 
	 parameter goes out of range.
	 trapAdditionalInfoInteger variable contains current reading of 
	 the this parameter."
  ::= 3

  trapDM200ModuleTempAlarm TRAP-TYPE
	ENTERPRISE gx2Dm200
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Module Temperature parameter goes out of range.
	 trapAdditionalInfoInteger variable contains current reading of 
	 the this parameter."
  ::= 4

  trapDM200omiOffsetAlarm TRAP-TYPE
	ENTERPRISE gx2Dm200
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the OMI Offset goes out of range."
  ::= 5

  trapDM200tecCurrentAlarm TRAP-TYPE
	ENTERPRISE gx2Dm200
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the TEC Current parameter 
	 goes out of range.
	 trapAdditionalInfoInteger variable contains current reading of 
	 the this parameter."
  ::= 6

  trapDM200LaserCurrentAlarm TRAP-TYPE
	ENTERPRISE gx2Dm200
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Laser Current parameter 
	 goes out of range.
	 trapAdditionalInfoInteger variable contains current reading of 
	 the this parameter."
  ::= 7

  trapDM200LaserTempAlarm TRAP-TYPE
	ENTERPRISE gx2Dm200
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Laser Temp parameter 
	 goes out of range.
	 trapAdditionalInfoInteger variable contains current reading of 
	 the this parameter."
  ::= 8

  trapDM200LaserPowerAlarm TRAP-TYPE
	ENTERPRISE gx2Dm200
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Laser Power parameter 
	 goes out of range.
	 trapAdditionalInfoInteger variable contains current reading of 
	 the this parameter."
  ::= 9

  trapDM200FlashAlarm TRAP-TYPE
	ENTERPRISE gx2Dm200
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Laser Modules detects an error during
	Flash memory operations."
  ::= 10

  trapDM200BankBootAlarm TRAP-TYPE
	ENTERPRISE gx2Dm200
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Laser Modules detects an error while booting
	from bank 0 or bank 1."
  ::= 11

	trapDM200AlarmDataCRCAlarm TRAP-TYPE
	ENTERPRISE gx2Dm200
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Alarm Data CRC is incorrect."
  ::= 12

	trapDM200FactoryDataCRCAlarm TRAP-TYPE
	ENTERPRISE gx2Dm200
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Factory Data CRC is incorrect."
  ::= 13

	trapDM200CalDataCRCAlarm TRAP-TYPE
	ENTERPRISE gx2Dm200
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Cal Data CRC is incorrect."
  ::= 14


    trapDM200ResetFacDefault TRAP-TYPE
	ENTERPRISE gx2Dm200
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
      DESCRIPTION
      "This trap is issued when the DM200 resets to factory defaults"
  ::= 15

 	trapDM200UserRFOffAlarm TRAP-TYPE
	ENTERPRISE gx2Dm200
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the the User RF is turned off."
  ::= 16

	trapDM200UserOpticalOffAlarm TRAP-TYPE
	ENTERPRISE gx2Dm200
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the User Optical Power is turned off."
  ::= 17

	trapDM200UserSBSOffAlarm TRAP-TYPE
	ENTERPRISE gx2Dm200
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the User SBS is turned off."
  ::= 18

  trapDM200RFInputAlarm TRAP-TYPE
	ENTERPRISE gx2Dm200
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Laser Modules RF input parameter 
	 goes out of range.
	 trapAdditionalInfoInteger variable contains current reading of 
	 the this parameter."
  ::= 19
  
  trapDM200RFOverloadAlarm TRAP-TYPE
	ENTERPRISE gx2Dm200
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Laser Modules RF overload parameter 
	 goes out of range.
	 trapAdditionalInfoInteger variable contains current reading of 
	 the this parameter."
  ::= 20

  END
