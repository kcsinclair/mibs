--
-- RADWIN Management Information Base (MIB)
-- Generated 01/05/16 14:23:32 Version: 10.2.40_b9653
--
	RADWIN-MIB-WINLINK1000 DEFINITIONS ::= BEGIN

	IMPORTS 
		enterprises, IpAddress, Counter, Gauge, TimeTicks
			FROM RFC1155-SMI
		OBJECT-TYPE
			FROM RFC-1212
		DisplayString, ifIndex
			FROM RFC1213-MIB
		TRAP-TYPE
		    FROM RFC-1215;
	

	radwin			OBJECT IDENTIFIER ::= { enterprises 4458 }
	winlink1000		OBJECT IDENTIFIER ::= { radwin 1000 }

	-- ###########################################################
	--                      ODU
	-- ###########################################################

	winlink1000Odu OBJECT IDENTIFIER ::= { winlink1000 1 }

	-- ###########################################################
	--                      ODU Admin
	-- ###########################################################

	winlink1000OduAdmin OBJECT IDENTIFIER ::= { winlink1000Odu 1 }

	winlink1000OduAdmProductType OBJECT-TYPE
		SYNTAX  DisplayString
		ACCESS  read-only
		STATUS  mandatory
		DESCRIPTION
		"ODU configuration description."
		::= { winlink1000OduAdmin 1 }

	winlink1000OduAdmHwRev OBJECT-TYPE
		SYNTAX  DisplayString
		ACCESS  read-only
		STATUS  mandatory
		DESCRIPTION
		"ODU Hardware Version."
		::= { winlink1000OduAdmin 2 }

	winlink1000OduAdmSwRev OBJECT-TYPE
		SYNTAX  DisplayString
		ACCESS  read-only
		STATUS  mandatory
		DESCRIPTION
		"ODU Software Version."
		::= { winlink1000OduAdmin 3 }

	winlink1000OduAdmLinkName OBJECT-TYPE
		SYNTAX  DisplayString
		ACCESS  read-write
		STATUS  mandatory
		DESCRIPTION
		"Link Name. A change is effective immediately."
		::= { winlink1000OduAdmin 4 }

	winlink1000OduAdmResetCmd OBJECT-TYPE
		SYNTAX  INTEGER
		ACCESS  read-write
		STATUS  mandatory
		DESCRIPTION
		"Reset Command. 
		A set command with a value of 3 will cause a device reset.
		HBS only: A set command with a value of 4 will cause a device reset for the entire sector.
		The read value is always 0."
		::= { winlink1000OduAdmin 5 }

	winlink1000OduAdmAddres OBJECT-TYPE
		SYNTAX  IpAddress
		ACCESS  read-write
		STATUS  mandatory
		DESCRIPTION
		"ODU IP address. A change is effective after reset.
		 The parameter is kept for backward compatibility.
		 Using the alternative parameter: winlink1000OduAdmIpParamsCnfg is recommended."
		::= { winlink1000OduAdmin 6 }

	winlink1000OduAdmMask OBJECT-TYPE
		SYNTAX  IpAddress
		ACCESS  read-write
		STATUS  mandatory
		DESCRIPTION
		"ODU Subnet Mask. A change is effective after reset.
		 The parameter is kept for backward compatibility.
		 Using the alternative parameter: winlink1000OduAdmIpParamsCnfg is recommended."
		::= { winlink1000OduAdmin 7 }

	winlink1000OduAdmGateway OBJECT-TYPE
		SYNTAX  IpAddress
		ACCESS  read-write
		STATUS  mandatory
		DESCRIPTION
		"ODU default gateway. A change is effective after reset.
		 The parameter is kept for backward compatibility.
		 Using the alternative parameter: winlink1000OduAdmIpParamsCnfg is recommended."
		::= { winlink1000OduAdmin 8 }	

	winlink1000OduAdmBroadcast OBJECT-TYPE
		SYNTAX  INTEGER
		ACCESS  read-write
		STATUS  mandatory
		DESCRIPTION
		"This parameter is reserved for the Manager application provided with the product."
		::= { winlink1000OduAdmin 10 }
	
	-- ###########################################################
	--                      ODU Admin Hosts Table
	-- ###########################################################

	winlink1000OduAdmHostsTable OBJECT-TYPE
		SYNTAX  SEQUENCE OF Winlink1000OduAdmHostsEntry
		ACCESS  not-accessible
		STATUS  mandatory
		DESCRIPTION
		"Trap destinations table. Each trap destination is defined by an IP address and a UDP port.
		Up to 10 addresses can be configured."
		::= { winlink1000OduAdmin 12 }

	winlink1000OduAdmHostsEntry OBJECT-TYPE
		SYNTAX  Winlink1000OduAdmHostsEntry
		ACCESS  not-accessible
		STATUS  mandatory
		DESCRIPTION
		"Trap destinations table entry."
		INDEX { winlink1000OduAdmHostsIndex }
		::= { winlink1000OduAdmHostsTable 1 }

	Winlink1000OduAdmHostsEntry ::= SEQUENCE {
		winlink1000OduAdmHostsIndex
			INTEGER,
		winlink1000OduAdmHostsIp
			IpAddress,
		winlink1000OduAdmHostsPort
			INTEGER,
		winlink1000OduAdmHostsSecurityModel
			INTEGER,
		winlink1000OduAdmHostsUserName
			DisplayString,
		winlink1000OduAdmHostsPassword
			DisplayString,
		winlink1000OduAdmHostsIPv6
			DisplayString
		}

	winlink1000OduAdmHostsIndex OBJECT-TYPE
		SYNTAX  INTEGER
		ACCESS  read-only
		STATUS  mandatory
		DESCRIPTION
		"Trap destinations table index."
		::= { winlink1000OduAdmHostsEntry 1 }

	winlink1000OduAdmHostsIp OBJECT-TYPE
		SYNTAX  IpAddress
		ACCESS  read-write
		STATUS  mandatory
		DESCRIPTION
		"Trap destination IP address. A change is effective immediately."
		::= { winlink1000OduAdmHostsEntry 2 }

	winlink1000OduAdmHostsPort OBJECT-TYPE
		SYNTAX  INTEGER (1..65535)
		ACCESS  read-write
		STATUS  mandatory
		DESCRIPTION
		"UDP port of the trap destination. A change is effective immediately."
		::= { winlink1000OduAdmHostsEntry 3 }
		
	winlink1000OduAdmHostsSecurityModel OBJECT-TYPE
		SYNTAX  INTEGER {
			snmpv1(1),
			snmpv3(3)		
		}
		ACCESS  read-write
		STATUS  mandatory
		DESCRIPTION
		"Security model used for this trap generation."
		::= { winlink1000OduAdmHostsEntry 4 }
		
	winlink1000OduAdmHostsUserName OBJECT-TYPE
		SYNTAX  DisplayString
		ACCESS  read-write
		STATUS  mandatory
		DESCRIPTION
		"User name used to generate the snmpv3 trap."
		::= { winlink1000OduAdmHostsEntry 5 }
		
	winlink1000OduAdmHostsPassword OBJECT-TYPE
		SYNTAX  DisplayString
		ACCESS  read-write
		STATUS  mandatory
		DESCRIPTION
		"Password used to generate the snmpv3 trap."
		::= { winlink1000OduAdmHostsEntry 6 }

	winlink1000OduAdmHostsIPv6 OBJECT-TYPE
		SYNTAX  DisplayString
		ACCESS  read-write
		STATUS  mandatory
		DESCRIPTION
		"Trap destination IPv6 address. A change is effective immediately."
		::= { winlink1000OduAdmHostsEntry 7 }
		
	winlink1000OduBuzzerAdminState OBJECT-TYPE
		SYNTAX  INTEGER
		ACCESS  read-write
		STATUS  mandatory
		DESCRIPTION
		"This parameter controls the activation of the buzzer while the unit is in install mode.
		A change is effective immediately. The valid values are: disabled (0), enabledAuto (1), enabledConstantly(2), advancedAuto (3)."
		::= { winlink1000OduAdmin 13 }

	winlink1000OduProductId OBJECT-TYPE
		SYNTAX  DisplayString
		ACCESS  read-only
		STATUS  mandatory
		DESCRIPTION
		"This parameter is reserved for the Manager application provided with the product."
		::= { winlink1000OduAdmin 14 }

	winlink1000OduReadCommunity OBJECT-TYPE
		SYNTAX  DisplayString
		ACCESS  read-write
		STATUS  mandatory
		DESCRIPTION
		"Read Community String. This parameter always returns ***** when retrieving its value.
		It is used by the Manager application to change the Read Community String.
		The SNMP agent accepts only encrypted values."
		::= { winlink1000OduAdmin 15 }

	winlink1000OduReadWriteCommunity OBJECT-TYPE
		SYNTAX  DisplayString
		ACCESS  read-write
		STATUS  mandatory
		DESCRIPTION
		"Read/Write Community String. This parameter always returns ***** when retrieving its value.
		It is used by the Manager application to change the Read/Write Community String.
		The SNMP agent accepts only encrypted values."
		::= { winlink1000OduAdmin 16 }

	winlink1000OduTrapCommunity OBJECT-TYPE
		SYNTAX  DisplayString
		ACCESS  read-write
		STATUS  mandatory
		DESCRIPTION
		"Trap Community String. This parameter is used by the Manager application to change the Trap Community String.
		The SNMP agent accepts only encrypted values."
		::= { winlink1000OduAdmin 17 }

	winlink1000OduAdmSnmpAgentVersion OBJECT-TYPE
		SYNTAX  INTEGER
		ACCESS  read-only
		STATUS  mandatory
		DESCRIPTION
		"Major version of the SNMP agent."
		::= { winlink1000OduAdmin 18 }

	winlink1000OduAdmRemoteSiteName OBJECT-TYPE
		SYNTAX  DisplayString
		ACCESS  read-only
		STATUS  mandatory
		DESCRIPTION
		"Remote site name. Returns the same value as sysLocation parameter of the remote site."
		::= { winlink1000OduAdmin 19 }

	winlink1000OduAdmSnmpAgentMinorVersion OBJECT-TYPE
		SYNTAX  INTEGER
		ACCESS  read-only
		STATUS  mandatory
		DESCRIPTION
		"Minor version of the SNMP agent."
		::= { winlink1000OduAdmin 20 }

	winlink1000OduAdmLinkPassword OBJECT-TYPE
		SYNTAX  DisplayString
		ACCESS  read-write
		STATUS  mandatory
		DESCRIPTION
		"Link Password. This parameter always returns ***** when retrieving its value.
		It is used by the Manager application to change the Link Password.
		The SNMP agent accepts only encrypted values."
		::= { winlink1000OduAdmin 21 }

	winlink1000OduAdmSiteLinkPassword OBJECT-TYPE
		SYNTAX  DisplayString
		ACCESS  read-write
		STATUS  mandatory
		DESCRIPTION
		"Site Link Password. This parameter always returns ***** when retrieving its value.
		It is used by the Manager application to change the Link Password of the site.
		The SNMP agent accepts only encrypted values."
		::= { winlink1000OduAdmin 22 }

	winlink1000OduAdmDefaultPassword OBJECT-TYPE
		SYNTAX  INTEGER {
			default(1),
			nonDefault(2)
			}
		ACCESS  read-only
		STATUS  mandatory
		DESCRIPTION
		"This parameter indicates if the current Link Password is the default password."
		::= { winlink1000OduAdmin 23 }

	winlink1000OduAdmConnectionType OBJECT-TYPE
		SYNTAX  INTEGER {
			directConnection(1),
			indirectConnection(2),
			unknown(3)
			}
		ACCESS  read-only
		STATUS  mandatory
		DESCRIPTION
		"This parameter indicates if the Manager application is connected to the local ODU
		or to the remote ODU over the air. A value of 'unknown' indicates community string mismatch."
		::= { winlink1000OduAdmin 24 }

	winlink1000OduAdmBackToFactorySettingsCmd OBJECT-TYPE
		SYNTAX  INTEGER {
			withIP(1),
			withoutIP(2)
			}
		ACCESS  read-write
		STATUS  mandatory
		DESCRIPTION
		"Back to factory settings Command. A change is effective after reset. 
		The read value is always 0."
		::= { winlink1000OduAdmin 25 }
		
	winlink1000OduAdmIpParamsCnfg OBJECT-TYPE
		SYNTAX  DisplayString
		ACCESS  read-write
		STATUS  mandatory
		DESCRIPTION
		"ODU IP address Configuration. The format is: <IP_Address>|<Subnet_Mask>|<Default_Gateway>|"
		::= { winlink1000OduAdmin 26 }

	winlink1000OduAdmVlanID OBJECT-TYPE
		SYNTAX INTEGER (0..4094)
		ACCESS  read-write
		STATUS mandatory
		DESCRIPTION
		"VLAN ID. Valid values are 1 to 4094.
		Initial value is 0 meaning VLAN unaware."
		::= { winlink1000OduAdmin 27 }  

	winlink1000OduAdmVlanPriority OBJECT-TYPE
		SYNTAX INTEGER (0..7)
		ACCESS  read-write
		STATUS mandatory
		DESCRIPTION
		"VLAN Priority. 0 is lowest priority, 7 is highest priority."
		::= { winlink1000OduAdmin 28 }  
		
	winlink1000OduAdmSN OBJECT-TYPE
        SYNTAX  DisplayString
		ACCESS  read-only
		STATUS  mandatory
        DESCRIPTION
        "ODU Serial Number"
        ::= { winlink1000OduAdmin 29 }

	winlink1000OduAdmProductName OBJECT-TYPE
		SYNTAX DisplayString
		ACCESS  read-only
		STATUS mandatory
		DESCRIPTION
		"This is the product name as it exists at EC"
		::= { winlink1000OduAdmin 30 }
		
	winlink1000OduAdmActivationKey OBJECT-TYPE
		SYNTAX  DisplayString
		ACCESS  read-write
		STATUS  mandatory
		DESCRIPTION
		"Activates a general key."
		::= { winlink1000OduAdmin 31 }
		
	winlink1000OduAdmRmtPermittedOduType OBJECT-TYPE
		SYNTAX  DisplayString
		ACCESS  read-write
		STATUS  mandatory
		DESCRIPTION
		"Mobile Application: permitted partner OduType."
		::= { winlink1000OduAdmin 32 }
		
	winlink1000OduAdmCpuID OBJECT-TYPE
		SYNTAX  INTEGER (0..64)
		ACCESS  read-only
		STATUS  mandatory
		DESCRIPTION
		"CPU ID"
		::= { winlink1000OduAdmin 33 }
		
	winlink1000OduAdmOvrdCmd OBJECT-TYPE
		SYNTAX  DisplayString
		ACCESS  read-write
		STATUS  mandatory
		DESCRIPTION
		"Ability to perform special command in the ODU."
		::= { winlink1000OduAdmin 34 }
				
	winlink1000OduAdmLinkMode OBJECT-TYPE
		SYNTAX  INTEGER {
			pmpHbs (1),
			pmpHsu (2),
			pmpHsuHyb (3),
			pmpHbsHyb (4)
			}
		ACCESS  read-write
		STATUS  mandatory
		DESCRIPTION
		"Unit PMP operation mode."
		::= { winlink1000OduAdmin 35 }
		
	winlink1000OduAdmActualConnectMode OBJECT-TYPE
		SYNTAX  INTEGER {
			none (1),
			ptp (2),
			ptmp (3)
			}
		ACCESS  read-only
		STATUS  mandatory
		DESCRIPTION
		"Unit connected as part to ptp or ptmp."
		::= { winlink1000OduAdmin 36 }
		
	winlink1000OduAdmAES256Support OBJECT-TYPE
		SYNTAX  INTEGER {
			notSupported (1),
			supported (2)
			}
		ACCESS  read-only
		STATUS  mandatory
		DESCRIPTION
		"AES-256 security support indication."
		::= { winlink1000OduAdmin 37 }
		
	winlink1000OduAdmAES256State OBJECT-TYPE
		SYNTAX  INTEGER {
			disabled (1),
			enabled (2)
			}
		ACCESS  read-write
		STATUS  mandatory
		DESCRIPTION
		"Enable/Disable AES-256 security mode over the air link."
		::= { winlink1000OduAdmin 38 }
		
	winlink1000OduAdmAES256Status OBJECT-TYPE
		SYNTAX  INTEGER {
			notOperating (1),
			partiallyOperating (2),
			operating (3)
			}
		ACCESS  read-only
		STATUS  mandatory
		DESCRIPTION
		"AES256 operating status"
		::= { winlink1000OduAdmin 39 }

	winlink1000OduAdmBatterySavingShutdownTime OBJECT-TYPE
		SYNTAX  INTEGER (0..1000)
		ACCESS  read-write
		STATUS  mandatory
		DESCRIPTION
		"Battery Saving Shutdown Time in minutes, 0 till battery run out, -1 if not supported."
		::= { winlink1000OduAdmin 40 }

	winlink1000OduAdmWiFiPowerMode OBJECT-TYPE
		SYNTAX  INTEGER {
			undefined (1),
			powerON (2),
			powerOFF (3),
			alwaysON (4)
			}
		ACCESS  read-write
		STATUS  mandatory
		DESCRIPTION
		"WIFI unit power mode."
		::= { winlink1000OduAdmin 41 }
	
	winlink1000OduAdmShutdownTimer OBJECT-TYPE
		SYNTAX  INTEGER (0..2147483647)
		ACCESS  read-only
		STATUS  mandatory
		DESCRIPTION
		"Shutdown Timer in seconds."
		::= { winlink1000OduAdmin 42 }
	
	winlink1000OduAdmGPSState OBJECT-TYPE
		SYNTAX  INTEGER {
			undefined (1),
			notSynchronized (2),
			fixed (3),
			shortCircuit (4),
			faulty (5),
			synchronized (6),
			synchronizedGlonass (7)
			}
		ACCESS  read-only
		STATUS  mandatory
		DESCRIPTION
		"GPS state"
		::= { winlink1000OduAdmin 43 }
		
	winlink1000OduAdmTemperatureC OBJECT-TYPE
		SYNTAX  INTEGER
		ACCESS  read-only
		STATUS  mandatory
		DESCRIPTION
		"The temperature (Celsius) inside the Board."
		::= { winlink1000OduAdmin 44 }	
	
	winlink1000OduAdmIPStackMode OBJECT-TYPE
		SYNTAX  INTEGER {
			v4 (1),
			v6 (2),
			v4andv6 (3)
			}
		ACCESS  read-write
		STATUS  mandatory
		DESCRIPTION
		"The IP stack mode."
		::= { winlink1000OduAdmin 45 }	
		
	winlink1000OduAdmIPv6ParamsCnfg OBJECT-TYPE
		SYNTAX  DisplayString
		ACCESS  read-write
		STATUS  mandatory
		DESCRIPTION
		"ODU IPv6 address Configuration. The format is: <IP_Address>|<Subnet_Mask>|<Default_Gateway>|"
		::= { winlink1000OduAdmin 46 }

	winlink1000OduAdmIPv6Address OBJECT-TYPE
		SYNTAX  DisplayString
		ACCESS  read-only
		STATUS  mandatory
		DESCRIPTION
		"ODU IPv6 address."
		::= { winlink1000OduAdmin 47 }

	winlink1000OduAdmIPv6Prefix OBJECT-TYPE
		SYNTAX  INTEGER
		ACCESS  read-only
		STATUS  mandatory
		DESCRIPTION
		"ODU IPv6 subnet mask."
		::= { winlink1000OduAdmin 48 }	

	winlink1000OduAdmIPv6DefaultGateWay OBJECT-TYPE
		SYNTAX  DisplayString
		ACCESS  read-only
		STATUS  mandatory
		DESCRIPTION
		"ODU IPv6 default gateway."
		::= { winlink1000OduAdmin 49 }
					
	winlink1000OduAdmPowerConsumption OBJECT-TYPE
		SYNTAX  INTEGER
		ACCESS  read-only
		STATUS  mandatory
		DESCRIPTION
		"Power Consumption (mWatt)"
		::= { winlink1000OduAdmin 50 }	
	
	-- ###########################################################
	--                      ODU Wifi
	-- ###########################################################
	
	winlink1000OduAdmWifi OBJECT IDENTIFIER ::= { winlink1000OduAdmin 51 }
	
	winlink1000OduAdmWifiChannel OBJECT-TYPE
		SYNTAX  INTEGER (1..11)
		ACCESS  read-write
		STATUS  mandatory
		DESCRIPTION
		"Wifi Channel"
		::= { winlink1000OduAdmWifi 1 }	

	winlink1000OduAdmWifiTxPower OBJECT-TYPE
		SYNTAX  INTEGER (11..15)
		ACCESS  read-write
		STATUS  mandatory
		DESCRIPTION
		"Wifi TX Power"
		::= { winlink1000OduAdmWifi 2 }				

	winlink1000OduAdmWifiSSID OBJECT-TYPE
		SYNTAX  DisplayString
		ACCESS  read-only
		STATUS  mandatory
		DESCRIPTION
		"Wifi SSID"
		::= { winlink1000OduAdmWifi 3 }		

	winlink1000OduAdmWifiSecurityType OBJECT-TYPE
		SYNTAX  INTEGER {
			open (1),
			wep (2),
			wpa2 (3)
			}
		ACCESS  read-only
		STATUS  mandatory
		DESCRIPTION
		"Wifi Security type"
		::= { winlink1000OduAdmWifi 4 }			

	winlink1000OduAdmWifiPassword OBJECT-TYPE
		SYNTAX  DisplayString
		ACCESS  read-write
		STATUS  mandatory
		DESCRIPTION
		"Wifi Password"
		::= { winlink1000OduAdmWifi 5 }		
		
	winlink1000OduAdmWifiNetwork OBJECT-TYPE
		SYNTAX  IpAddress
		ACCESS  read-write
		STATUS  mandatory
		DESCRIPTION
		"Wifi Network"
		::= { winlink1000OduAdmWifi 6 }	

	winlink1000OduAdmWifiRssi OBJECT-TYPE
		SYNTAX  INTEGER
		ACCESS  read-only
		STATUS  mandatory
		DESCRIPTION
		"Wifi RSSI"
		::= { winlink1000OduAdmWifi 7 }	

	winlink1000OduAdmWifiStationMAC OBJECT-TYPE
		SYNTAX  DisplayString
		ACCESS  read-only
		STATUS  mandatory
		DESCRIPTION
		"Wifi Station MAC"
		::= { winlink1000OduAdmWifi 8 }		

	winlink1000OduAdmWifiRestart OBJECT-TYPE
		SYNTAX  INTEGER (1)
		ACCESS  read-write
		STATUS  mandatory
		DESCRIPTION
		"A set command with a value of 1 will cause a Wifi restart.
		The read value is always 0."
		::= { winlink1000OduAdmWifi 9 }		

	winlink1000OduAdmWifiApStatus OBJECT-TYPE
		SYNTAX  INTEGER {
			off (1),
			on (2),
			connected (3)
			}
		ACCESS  read-only
		STATUS  mandatory
		DESCRIPTION
		"Wifi AP Status"
		::= { winlink1000OduAdmWifi 10 }

	winlink1000OduAdmBsaOperationMode OBJECT-TYPE
		SYNTAX  INTEGER {
			inactive (1),
			hbsTracking (2),
			hsuAlignment (3)
			}
		ACCESS  read-only
		STATUS  mandatory
		DESCRIPTION
		"BSA Operation Mode"
		::= { winlink1000OduAdmin 52 }
		
	winlink1000OduAdmMngConnection OBJECT-TYPE
		SYNTAX  DisplayString
		ACCESS  read-write
		STATUS  mandatory
		DESCRIPTION
		"Management Connection"
		::= { winlink1000OduAdmin 53 }
		
	winlink1000OduAdm1588TCSupport OBJECT-TYPE
		SYNTAX  INTEGER {
			notSupported (1),
			supported (2)
			}
		ACCESS  read-only
		STATUS  mandatory
		DESCRIPTION
		"Indicates that 1588TC license activated"
		::= { winlink1000OduAdmin 54 }

	winlink1000OduAdmSyncESupport OBJECT-TYPE
		SYNTAX  INTEGER {
			notSupported (1),
			supported (2)
			}
		ACCESS  read-only
		STATUS  mandatory
		DESCRIPTION
		"ndicates that SyncE license activated"
		::= { winlink1000OduAdmin 55 }

	winlink1000OduAdmRadioRev OBJECT-TYPE
		SYNTAX  DisplayString
		ACCESS  read-only
		STATUS  mandatory
		DESCRIPTION
		"Radio Revision"
		::= { winlink1000OduAdmin 56 }
		
	winlink1000OduAdmProductRev OBJECT-TYPE
		SYNTAX  DisplayString
		ACCESS  read-only
		STATUS  mandatory
		DESCRIPTION
		"Product Revision"
		::= { winlink1000OduAdmin 57 }		
		
	winlink1000OduAdmPMPSUSupport OBJECT-TYPE
		SYNTAX  INTEGER {
			notSupported (1),
			supported (2)
			}
		ACCESS  read-only
		STATUS  mandatory
		DESCRIPTION
		"Indicates that PMP SU license is activated"
		::= { winlink1000OduAdmin 58 }	
		
	winlink1000OduAdmManagerDownloadURL OBJECT-TYPE
		SYNTAX  DisplayString
		ACCESS  read-write
		STATUS  mandatory
		DESCRIPTION
		"This is the URL from which management tool can be downloaded"
		::= { winlink1000OduAdmin 59 }
		
	winlink1000OduAdmAntennaDescription OBJECT-TYPE
		SYNTAX  DisplayString
		ACCESS  read-only
		STATUS  mandatory
		DESCRIPTION
		"The is a description of the antenna connected to the ODU"
		::= { winlink1000OduAdmin 60 }
		
	winlink1000OduAdmSwCapabilities OBJECT-TYPE
		SYNTAX  DisplayString
		ACCESS  read-only
		STATUS  mandatory
		DESCRIPTION
		"This is used to describe which Software Capabilities the current ODU supports"
		::= { winlink1000OduAdmin 61 }
		
	-- ###########################################################
	--                      ODU Service
	-- ###########################################################

	winlink1000OduService OBJECT IDENTIFIER ::= { winlink1000Odu 2 }

	winlink1000OduSrvMode OBJECT-TYPE
		SYNTAX  INTEGER {
			installMode (1),
			normalMode (2),
			slaveMode (3),
			tempInstallMode (4),
			inactiveMode (5)
			}
		ACCESS  read-write
		STATUS  mandatory
		DESCRIPTION
		"System mode. The only values that can be set are installMode and slaveMode;
		normalMode reserved to the Manager application provided with the product.
		A change is effective after link re-synchronization."
		::= { winlink1000OduService 1 }

	winlink1000OduSrvBridging OBJECT-TYPE
		SYNTAX  INTEGER
		ACCESS  read-only
		STATUS  mandatory
		DESCRIPTION
		"Bridging Mode. Valid values are: disabled (0), enabled (1)."
		::= { winlink1000OduService 3 }
		
	-- ###########################################################
	--                      ODU Ring Topology
	-- ###########################################################
	
	winlink1000OduServiceRingTopology OBJECT IDENTIFIER ::= { winlink1000OduService 4 }
	
	winlink1000OduSrvRingLinkMode OBJECT-TYPE
		SYNTAX  INTEGER {
			independentLink (1),				
			nonRpl (2),
			rpl (3)	
			}
		ACCESS  read-write
		STATUS  mandatory
		DESCRIPTION
		"Mode of the link regarding ring topology."
		::= { winlink1000OduServiceRingTopology 1 }		

	winlink1000OduSrvRingTopologySupported OBJECT-TYPE
		SYNTAX  INTEGER {
			notSupported (1),
			supported (2)			
			}
		ACCESS  read-only
		STATUS  mandatory
		DESCRIPTION
		"Ring Topology, options are: supported, not supported"
		::= { winlink1000OduServiceRingTopology 2 }
		
	winlink1000OduSrvRingVlanIdTable OBJECT-TYPE
		SYNTAX  SEQUENCE OF Winlink1000OduSrvRingVlanIdEntry
		ACCESS  not-accessible
		STATUS  mandatory
		DESCRIPTION
		"Ring VLAN IDs table."
		::= { winlink1000OduServiceRingTopology 3 }

	winlink1000OduSrvRingVlanIdEntry OBJECT-TYPE
		SYNTAX  Winlink1000OduSrvRingVlanIdEntry
		ACCESS  not-accessible
		STATUS  mandatory
		DESCRIPTION
		"VLAN ID of the internal ring messages. Valid values are 1 to 4094.
		Initial value is 0 meaning VLAN unaware."
		INDEX { winlink1000OduSrvRingVlanIdIndex }
		::= { winlink1000OduSrvRingVlanIdTable 1 }

	Winlink1000OduSrvRingVlanIdEntry ::= SEQUENCE {
		winlink1000OduSrvRingVlanIdIndex
			INTEGER,
		winlink1000OduSrvRingVlanId
			INTEGER
		}

	winlink1000OduSrvRingVlanIdIndex OBJECT-TYPE
		SYNTAX  INTEGER (0..3)
		ACCESS  read-only
		STATUS  mandatory
		DESCRIPTION
		"Index of VLAN ID of the internal ring messages."			
		::= { winlink1000OduSrvRingVlanIdEntry 1 }

	winlink1000OduSrvRingVlanId OBJECT-TYPE
		SYNTAX  INTEGER (0..4094)
		ACCESS  read-write
		STATUS  mandatory
		DESCRIPTION
		"VLAN ID of the internal ring messages. Valid values are 1 to 4094.
		Initial value is 0 meaning VLAN unaware."
		::= { winlink1000OduSrvRingVlanIdEntry 2 }
		
		
	winlink1000OduSrvRingEthStatus OBJECT-TYPE
		SYNTAX  INTEGER {				
			unblocked(1),				
			blocked(2),
			notApplicable(3)
			}
		ACCESS  read-only
		STATUS  mandatory
		DESCRIPTION
		"Represents the Ethernet service blocking state of a Rings link"
		::= { winlink1000OduServiceRingTopology 4 } 			
			
	winlink1000OduSrvRingMaxAllowedTimeFromLastRpm OBJECT-TYPE
		SYNTAX  INTEGER 
		ACCESS  read-write
		STATUS  mandatory
		DESCRIPTION
		"Defines the minimal time (in ms) required for determination of ring failure."
		::= { winlink1000OduServiceRingTopology 5 }			
			
	winlink1000OduSrvRingWTR OBJECT-TYPE
		SYNTAX  INTEGER 
		ACCESS  read-write
		STATUS  mandatory
		DESCRIPTION
		"Defines the minimal time (in ms) required for ring recovery."
		::= { winlink1000OduServiceRingTopology 6 }			
		-- ###########################################################
		--                      ODU QoS
		-- ###########################################################
		
		winlink1000OduServiceQoS OBJECT IDENTIFIER ::= { winlink1000OduService 5 }
		
		winlink1000OduSrvQoSMode OBJECT-TYPE
			SYNTAX  INTEGER {
				notSupported (1),				
				notActive (2),
				classVlan (3),
				classDiffserv (4)
				}
			ACCESS  read-write
			STATUS  mandatory
			DESCRIPTION
			"Mode of QoS feature."
			::= { winlink1000OduServiceQoS 1 }
			
		winlink1000OduSrvQoSConfTable OBJECT-TYPE
			SYNTAX  SEQUENCE OF Winlink1000OduSrvQoSConfEntry
			ACCESS  not-accessible
			STATUS  mandatory
			DESCRIPTION
			"QoS configuration table."
			::= { winlink1000OduServiceQoS 2 }
			
		winlink1000OduSrvQoSConfEntry OBJECT-TYPE
			SYNTAX  Winlink1000OduSrvQoSConfEntry
			ACCESS  not-accessible
			STATUS  mandatory
			DESCRIPTION
			"QoS configuration table."
			INDEX { winlink1000OduSrvQoSConfIndex }
			::= { winlink1000OduSrvQoSConfTable 1 }
			
		Winlink1000OduSrvQoSConfEntry ::= SEQUENCE {
			winlink1000OduSrvQoSConfIndex
				INTEGER,
			winlink1000OduSrvConfVlanQGroups
				INTEGER,
			winlink1000OduSrvConfDiffservQGroups
				INTEGER,
			winlink1000OduSrvConfQueMir
				INTEGER,
			winlink1000OduSrvConfQueWeight
				INTEGER
			}
			
		winlink1000OduSrvQoSConfIndex OBJECT-TYPE
			SYNTAX  INTEGER (0..3)
			ACCESS  read-only
			STATUS  mandatory
			DESCRIPTION
			"Index of QoS Configuration."			
			::= { winlink1000OduSrvQoSConfEntry 1 }
			
		winlink1000OduSrvConfVlanQGroups OBJECT-TYPE
			SYNTAX  INTEGER (0..7)
			ACCESS  read-only
			STATUS  mandatory
			DESCRIPTION
			"Frames classification according to VLAN Priority IDs."			
			::= { winlink1000OduSrvQoSConfEntry 2 }
			
		winlink1000OduSrvConfDiffservQGroups OBJECT-TYPE
			SYNTAX  INTEGER (0..48)
			ACCESS  read-only
			STATUS  mandatory
			DESCRIPTION
			"Frames classification according to Diffserv."			
			::= { winlink1000OduSrvQoSConfEntry 3 }
			
		winlink1000OduSrvConfQueMir OBJECT-TYPE
			SYNTAX  INTEGER 
			ACCESS  read-write
			STATUS  mandatory
			DESCRIPTION
			"Desired Private MIR."			
			::= { winlink1000OduSrvQoSConfEntry 4 }
			
		winlink1000OduSrvConfQueWeight OBJECT-TYPE
			SYNTAX  INTEGER (0..100)
			ACCESS  read-write
			STATUS  mandatory
			DESCRIPTION
			"QoS queueu's weights in percent."			
			::= { winlink1000OduSrvQoSConfEntry 5 }		
			
		winlink1000OduSrvQoSVlanQGroupsSetStr OBJECT-TYPE
			SYNTAX  DisplayString
			ACCESS  read-write
			STATUS  mandatory
			DESCRIPTION
			"Frames classification according to VLAN IDs string for set."
			::= { winlink1000OduServiceQoS 3 }
			
		winlink1000OduSrvQoSDiffservQGroupsSetStr OBJECT-TYPE
			SYNTAX  DisplayString
			ACCESS  read-write
			STATUS  mandatory
			DESCRIPTION
			"Frames classification according to Diffserv IDs string for set."
			::= { winlink1000OduServiceQoS 4 }
			
		winlink1000OduSrvQoSMaxRTQuePercent OBJECT-TYPE
			SYNTAX  INTEGER (0..100)				
			ACCESS  read-only
			STATUS  mandatory
			DESCRIPTION
			"Maximal percent for RT & NRT queues."
			::= { winlink1000OduServiceQoS 5 }
		
		-- ###########################################################
		--                      ODU VLAN Configuration
		-- ###########################################################
		
		winlink1000OduServiceVlan OBJECT IDENTIFIER ::= { winlink1000OduService 6 }
		
		winlink1000OduSrvVlanSupport OBJECT-TYPE
			SYNTAX  INTEGER {
				notSupported (1),				
				supported(2),
				available(3)
				}
			ACCESS  read-only
			STATUS  mandatory
			DESCRIPTION
			"ODU Ethernet port VLAN support and configuration availability indication.
			1 - ODU VLAN Functionality Not Supported
			2 - ODU VLAN Functionality Supported
			3 - ODU VLAN Functionality Supported and Available"
			::= { winlink1000OduServiceVlan 1 }
			
		winlink1000OduSrvVlanIngressMode OBJECT-TYPE
			SYNTAX  INTEGER {
				transparent (1),				
				untagAll    (2),
				filter      (3)
				}
			ACCESS  read-write
			STATUS  mandatory
			DESCRIPTION
			"ODU Ethernet port ingress VLAN mode."
			::= { winlink1000OduServiceVlan 2 }
			
		winlink1000OduSrvVlanEgressMode OBJECT-TYPE
			SYNTAX  INTEGER {
				transparent (1),				
				tag (2),
				provider (3)
				}
			ACCESS  read-write
			STATUS  mandatory
			DESCRIPTION
			"ODU Ethernet port egress VLAN mode."
			::= { winlink1000OduServiceVlan 3 }
			
		winlink1000OduSrvEgressTag OBJECT-TYPE
			SYNTAX  INTEGER (0..40947)
			ACCESS  read-write
			STATUS  mandatory
			DESCRIPTION
			"ODU ethernet port egress VLAN tag.
			Right most digit is Vlan priority (0-7), 
			other digits compose Vlan Id (2-4094)"
			::= { winlink1000OduServiceVlan 4 }
			
		winlink1000OduSrvEgressProviderTag OBJECT-TYPE
			SYNTAX  INTEGER (0..40947)
			ACCESS  read-write
			STATUS  mandatory
			DESCRIPTION
			"ODU ethernet port egress Provider VLAN tag.
			Right most digit is Vlan priority (0-7), 
			other digits compose Vlan Id (2-4094)"
			::= { winlink1000OduServiceVlan 5 }
			
		winlink1000OduSrvVlanIngressAllowedVIDs OBJECT-TYPE
			SYNTAX  DisplayString
			ACCESS  read-write
			STATUS  mandatory
			DESCRIPTION
			"ODU ethernet port VLAN IDs that will not be filtered on ingress.
			w|w|w|w|w|w|w|w| ( where w = {0-4094} and w != 1 )"
			::= { winlink1000OduServiceVlan 6 }
			
		winlink1000OduSrvVlanDisable OBJECT-TYPE
			SYNTAX  INTEGER
			ACCESS  read-write
			STATUS  mandatory
			DESCRIPTION
			"Disable VLAN functionality. The following values can be set:
			3 - Disable ODU & IDU VLAN Configurations."
			::= { winlink1000OduServiceVlan 7 }	
			
		winlink1000OduServiceVlanProviderListTPIDstr OBJECT-TYPE
			SYNTAX  DisplayString
			ACCESS  read-only
			STATUS  mandatory
			DESCRIPTION
			"Holds the possible Provider TPIDs."
			::= { winlink1000OduServiceVlan 8 }
			
	-- ###########################################################
	--                      ODU Ethernet
	-- ###########################################################

	winlink1000OduEthernet OBJECT IDENTIFIER ::= { winlink1000Odu 3 }

	winlink1000OduEthernetRemainingRate OBJECT-TYPE
		SYNTAX  INTEGER
		ACCESS  read-only
		STATUS  mandatory
		DESCRIPTION
		"Current Ethernet bandwidth in bps."
		::= { winlink1000OduEthernet 1 }	

	-- ###########################################################
	--                      ODU Ethernet Interface Table
	-- ###########################################################

	winlink1000OduEthernetIfTable OBJECT-TYPE
		SYNTAX  SEQUENCE OF Winlink1000OduEthernetIfEntry
		ACCESS  not-accessible
		STATUS  mandatory
		DESCRIPTION
		"ODU Ethernet Interface table."
		::= { winlink1000OduEthernet 2 }

	winlink1000OduEthernetIfEntry OBJECT-TYPE
		SYNTAX  Winlink1000OduEthernetIfEntry
		ACCESS  not-accessible
		STATUS  mandatory
		DESCRIPTION
		"ODU Ethernet Interface table entry."
		INDEX { winlink1000OduEthernetIfIndex }
		::= { winlink1000OduEthernetIfTable 1 }

	Winlink1000OduEthernetIfEntry ::= SEQUENCE {
		winlink1000OduEthernetIfIndex
			INTEGER,
		winlink1000OduEthernetIfAddress
			DisplayString,
		winlink1000OduEthernetIfAdminStatus
			INTEGER,
		winlink1000OduEthernetIfOperStatus
			INTEGER,
		winlink1000OduEthernetIfFailAction
			INTEGER,
		winlink1000OduEthernetIf1588v2PTPEventRXRate
			INTEGER,
		winlink1000OduEthernetIf1588v2PTPEventTXRate
			INTEGER
		}

	winlink1000OduEthernetIfIndex OBJECT-TYPE
		SYNTAX  INTEGER
		ACCESS  read-only
		STATUS  mandatory
		DESCRIPTION
		"ODU Ethernet Interface Index." 
		::= { winlink1000OduEthernetIfEntry 1 }	

	winlink1000OduEthernetIfAddress OBJECT-TYPE
		SYNTAX  DisplayString
		ACCESS  read-only
		STATUS  mandatory
		DESCRIPTION
		"ODU MAC address."
		::= { winlink1000OduEthernetIfEntry 5 }

	winlink1000OduEthernetIfAdminStatus OBJECT-TYPE
		SYNTAX  INTEGER {
			portAutoSense(1),
			portAutoSense100Mbps(5),			
			forceHalfDuplex10Mbps(10),			
			forceFullDuplex10Mbps(11),
			forceHalfDuplex100Mbps(15),
			forceFullDuplex100Mbps(16),
			forceFullDuplex1000Mbps(21),
			disablePoePort(254),			
			disablePort(255)
			}
		ACCESS  read-write
		STATUS  mandatory
		DESCRIPTION
		"Required state of the interface."
		::= { winlink1000OduEthernetIfEntry 6 }	

	winlink1000OduEthernetIfOperStatus OBJECT-TYPE
		SYNTAX  INTEGER {
			notConnected(1),
			connectedHalfDuplex10Mbps(10),
			connectedFullDuplex10Mbps(11),
			connectedHalfDuplex100Mbps(15),
			connectedFullDuplex100Mbps(16),
			connectedHalfDuplex1000Mbps(20),
			connectedFullDuplex1000Mbps(21),
			unknown(65535)
			}
		ACCESS  read-only
		STATUS  mandatory
		DESCRIPTION
		"Current operational state of the interface."
		::= { winlink1000OduEthernetIfEntry 7 }
		
	winlink1000OduEthernetIfFailAction OBJECT-TYPE
		SYNTAX  INTEGER {
			faNoAction(1),
			faForceHalfDuplex10Mbps(10),			
			faForceFullDuplex10Mbps(11),
			faDisablePort(255)
			}
		ACCESS  read-write
		STATUS  mandatory
		DESCRIPTION
		"Failure action of the interface."
		::= { winlink1000OduEthernetIfEntry 8 }			
		
	winlink1000OduEthernetIf1588v2PTPEventRXRate OBJECT-TYPE
		SYNTAX  INTEGER
		ACCESS  read-only
		STATUS  mandatory
		DESCRIPTION
		"For debug use"
		::= { winlink1000OduEthernetIfEntry 9 }
		
	winlink1000OduEthernetIf1588v2PTPEventTXRate OBJECT-TYPE
		SYNTAX  INTEGER
		ACCESS  read-only
		STATUS  mandatory
		DESCRIPTION
		"For debug use"
		::= { winlink1000OduEthernetIfEntry 10 }		

	winlink1000OduEthernetNumOfPorts OBJECT-TYPE
		SYNTAX  INTEGER
		ACCESS  read-only
		STATUS  mandatory
		DESCRIPTION
		"Number of ODU network interfaces."
		::= { winlink1000OduEthernet 3 }
		
	
	winlink1000OduEthernetGbeSupported OBJECT-TYPE
		SYNTAX  INTEGER {notSupported(1), supported(2)}
		ACCESS  read-only
		STATUS  mandatory
		DESCRIPTION
		"Supported Giga bit Ethernet in ODU."
		::= { winlink1000OduEthernet 4 }

	winlink1000OduEthernetSfpProperties OBJECT-TYPE
		SYNTAX  DisplayString
		ACCESS  read-only
		STATUS  mandatory
		DESCRIPTION
		"Sfp port properties."
		::= { winlink1000OduEthernet 5 }			

	-- ###########################################################
	--                      ODU Bridge
	-- ###########################################################

	winlink1000OduBridge OBJECT IDENTIFIER ::= { winlink1000Odu 4 }

	-- ###########################################################
	--                      ODU Bridge Base
	-- ###########################################################

	winlink1000OduBridgeBase OBJECT IDENTIFIER ::= { winlink1000OduBridge 1 }

	-- ###########################################################
	--                      ODU Bridge Ports Table
	-- ###########################################################

	winlink1000OduBridgeBasePortTable OBJECT-TYPE
		SYNTAX  SEQUENCE OF Winlink1000OduBridgeBasePortEntry
		ACCESS  not-accessible
		STATUS  mandatory
		DESCRIPTION
		"ODU Bridge Ports table."
		::= { winlink1000OduBridgeBase 4 }

	winlink1000OduBridgeBasePortEntry OBJECT-TYPE
		SYNTAX  Winlink1000OduBridgeBasePortEntry
		ACCESS  not-accessible
		STATUS  mandatory
		DESCRIPTION
		"ODU Bridge Ports table entry."
		INDEX { winlink1000OduBridgeBasePortIndex }
		::= { winlink1000OduBridgeBasePortTable 1 }

	Winlink1000OduBridgeBasePortEntry ::= SEQUENCE {
		winlink1000OduBridgeBasePortIndex
			INTEGER,
		winlink1000OduBridgeBaseIfIndex
			INTEGER
		}

	winlink1000OduBridgeBasePortIndex OBJECT-TYPE
		SYNTAX  INTEGER
		ACCESS  read-only
		STATUS  mandatory
		DESCRIPTION
		"ODU Bridge Port Number."
		::= { winlink1000OduBridgeBasePortEntry 1 }

	winlink1000OduBridgeBaseIfIndex OBJECT-TYPE
		SYNTAX  INTEGER
		ACCESS  read-only
		STATUS  mandatory
		DESCRIPTION
		"IfIndex corresponding to ODU Bridge port."
		::= { winlink1000OduBridgeBasePortEntry 2 }

	-- ###########################################################
	--                      ODU Bridge Tp
	-- ###########################################################

	winlink1000OduBridgeTp OBJECT IDENTIFIER ::= { winlink1000OduBridge 4 }

	winlink1000OduBridgeTpMode OBJECT-TYPE
		SYNTAX  INTEGER
		ACCESS  read-write
		STATUS  mandatory
		DESCRIPTION
		"ODU bridge mode. 
		A change is effective after reset. Valid values: hubMode (0), bridgeMode (1)."
		::= { winlink1000OduBridgeTp 101 }

	-- ###########################################################
	--                      ODU Transparent Bridge Ports Table
	-- ###########################################################

	winlink1000OduBridgeTpPortTable OBJECT-TYPE
		SYNTAX  SEQUENCE OF Winlink1000OduBridgeTpPortEntry
		ACCESS  not-accessible
		STATUS  mandatory
		DESCRIPTION
		"ODU Transparent Bridge Ports table."
		::= { winlink1000OduBridgeTp 3 }

	winlink1000OduBridgeTpPortEntry OBJECT-TYPE
		SYNTAX  Winlink1000OduBridgeTpPortEntry
		ACCESS  not-accessible
		STATUS  mandatory
		DESCRIPTION
		"ODU Transparent Bridge Ports table entry."
		INDEX { winlink1000OduBridgeTpPortIndex }
		::= { winlink1000OduBridgeTpPortTable 1 }

	Winlink1000OduBridgeTpPortEntry ::= SEQUENCE {
		winlink1000OduBridgeTpPortIndex
			INTEGER,
		winlink1000OduBridgeTpPortInFrames
			Counter,
		winlink1000OduBridgeTpPortOutFrames
			Counter,
		winlink1000OduBridgeTpPortInBytes
			Counter,
		winlink1000OduBridgeTpPortOutBytes
			Counter
		}

	winlink1000OduBridgeTpPortIndex OBJECT-TYPE
		SYNTAX  INTEGER
		ACCESS  read-only
		STATUS  mandatory
		DESCRIPTION
		"ODU Transparent Bridge Port Number."
		::= { winlink1000OduBridgeTpPortEntry 1 }

	winlink1000OduBridgeTpPortInFrames OBJECT-TYPE
		SYNTAX  Counter
		ACCESS  read-only
		STATUS  mandatory
		DESCRIPTION
		"Number of frames received by this port."
		::= { winlink1000OduBridgeTpPortEntry 3 }

	winlink1000OduBridgeTpPortOutFrames OBJECT-TYPE
		SYNTAX  Counter
		ACCESS  read-only
		STATUS  mandatory
		DESCRIPTION
		"Number of frames transmitted by this port."
		::= { winlink1000OduBridgeTpPortEntry 4 }

	winlink1000OduBridgeTpPortInBytes OBJECT-TYPE
		SYNTAX  Counter
		ACCESS  read-only
		STATUS  mandatory
		DESCRIPTION
		"Number of bytes received by this port."
		::= { winlink1000OduBridgeTpPortEntry 101 }

	winlink1000OduBridgeTpPortOutBytes OBJECT-TYPE
		SYNTAX  Counter
		ACCESS  read-only
		STATUS  mandatory
		DESCRIPTION
		"Number of bytes transmitted by this port."
		::= { winlink1000OduBridgeTpPortEntry 102 }
		
	winlink1000OduBridgeConfigMode OBJECT-TYPE
		SYNTAX  INTEGER{
			enable (1),
			disable (2)
			}
		ACCESS  read-only
		STATUS  mandatory
		DESCRIPTION
		"ODU bridge configuration mode"
		::= { winlink1000OduBridgeTp 102 }

	-- ###########################################################
	--                      ODU Air
	-- ###########################################################

	winlink1000OduAir OBJECT IDENTIFIER ::= { winlink1000Odu 5 }

	winlink1000OduAirFreq OBJECT-TYPE
		SYNTAX  INTEGER
		ACCESS  read-write
		STATUS  mandatory
		DESCRIPTION
		"Installation Center Frequency. Valid values are product dependent. A change is effective after link re-synchronization."
		::= { winlink1000OduAir 1 }

	winlink1000OduAirDesiredRate OBJECT-TYPE
		SYNTAX  INTEGER
		ACCESS  read-write
		STATUS  deprecated
		DESCRIPTION
		"Deprecated parameter, actual behavior is read-only. 
		Required Air Rate. For Channel Bandwidth of 20, 10, 5 MHz divide the value by 1, 2, 4 respectively."
		::= { winlink1000OduAir 2 }

	winlink1000OduAirSSID OBJECT-TYPE
		SYNTAX  DisplayString
		ACCESS  read-write
		STATUS  mandatory
		DESCRIPTION
		"Reserved for the Manager application provided with the product.
		 The Sector ID in Point-To-Multi-Point systems."
		::= { winlink1000OduAir 3 }

	winlink1000OduAirTxPower OBJECT-TYPE
		SYNTAX  INTEGER
		ACCESS  read-write
		STATUS  mandatory
		DESCRIPTION
		"Required Transmit power in dBm . This is a nominal value while the actual transmit power includes additional attenuation.
		The min and max values are product specific. A change is effective immediately."
		::= { winlink1000OduAir 4 }

	winlink1000OduAirSesState OBJECT-TYPE
		SYNTAX  INTEGER {
			sessionDown (1),
			basicRate (2),
			active (3),
			installation (4),
			scanning (5),
			probing (6),
			transmitting (7),
			activeWithDefaultEncryptionKey (8),
			installationWithDefaultEncryptionKey (9),
			bitFailed (10),
			activeWithVersionsMismatch (11),
			installationWithVersionsMismatch (12),
			inactive (13),
			iduIncompatible (14),
			spectrumAnalysis (15)
			}
		ACCESS  read-only
		STATUS  mandatory
		DESCRIPTION
		"Current Link State. The value is active (3) during normal operation." 
		::= { winlink1000OduAir 5 }

	winlink1000OduAirMstrSlv OBJECT-TYPE
		SYNTAX  INTEGER
		ACCESS  read-only
		STATUS  mandatory
		DESCRIPTION
		"This parameter indicates if the device was automatically selected into the radio link master or slave. 
		The value is undefined if there is no link.
		The value is relevant only for point to point systems."
		::= { winlink1000OduAir 6 }	

	winlink1000OduAirResync OBJECT-TYPE
		SYNTAX  INTEGER
		ACCESS  read-write
		STATUS  mandatory
		DESCRIPTION
		"Setting this parameter to 1 will cause the link to restart the synchronization process."
		::= { winlink1000OduAir 8 }

	-- ###########################################################
	--                      ODU Air Perf
	-- ###########################################################

	winlink1000OduAirPerf OBJECT IDENTIFIER ::= { winlink1000OduAir 9 }

	winlink1000OduAirRxPower OBJECT-TYPE
		SYNTAX  INTEGER
		ACCESS  read-only
		STATUS  mandatory
		DESCRIPTION
		"Received Signal Strength in dBm. Relevant only for point to point systems."
		::= { winlink1000OduAirPerf 1 }

	winlink1000OduAirTotalFrames OBJECT-TYPE
		SYNTAX  Counter
		ACCESS  read-only
		STATUS  mandatory
		DESCRIPTION
		"Total number of radio frames."
		::= { winlink1000OduAirPerf 2 }

	winlink1000OduAirBadFrames OBJECT-TYPE
		SYNTAX  Counter
		ACCESS  read-only
		STATUS  mandatory
		DESCRIPTION
		"Total number of received radio frames with CRC error. The value is relevant only for point to point systems ."
		::= { winlink1000OduAirPerf 3 }

	winlink1000OduAirCurrentRate OBJECT-TYPE
		SYNTAX  INTEGER
		ACCESS  read-only
		STATUS  deprecated
		DESCRIPTION
		"Deprecated parameter. Actual rate of the air interface in Mbps. 
		For Channel Bandwidth of 20, 10, 5 MHz divide the value by 1, 2, 4 respectively."
		::= { winlink1000OduAirPerf 4 }

	winlink1000OduAirCurrentRateIdx OBJECT-TYPE
		SYNTAX  INTEGER 
		ACCESS  read-only
		STATUS  mandatory
		DESCRIPTION
		"Index of current air rate."
		::= { winlink1000OduAirPerf 5 }
		
	winlink1000OduAirChainsRxPower OBJECT-TYPE
		SYNTAX  OCTET STRING
		ACCESS  read-only
		STATUS  mandatory
		DESCRIPTION
		"Received Signal Strength of Cpe chains in dBm.
		Chain 1 RSS: (1 Byte)
		Chain 2 RSS: (1 Byte)
		Chain 3 RSS: (1 Byte)"
		::= { winlink1000OduAirPerf 6 }

	winlink1000OduAirCurrentRateCBW OBJECT-TYPE
		SYNTAX  INTEGER 
		ACCESS  read-only
		STATUS  mandatory
		DESCRIPTION
		"CBW of current air rate."
		::= { winlink1000OduAirPerf 7 }
		
	winlink1000OduAirCurrentRateGI OBJECT-TYPE
		SYNTAX  INTEGER 
		ACCESS  read-only
		STATUS  mandatory
		DESCRIPTION
		"GI of current air rate."
		::= { winlink1000OduAirPerf 8 }
		
	winlink1000OduAirTxPower36 OBJECT-TYPE
		SYNTAX  INTEGER
		ACCESS  read-write
		STATUS  deprecated
		DESCRIPTION
		"Deprecated parameter. Actual behavior is read-only."
		::= { winlink1000OduAir 10 }

	winlink1000OduAirTxPower48 OBJECT-TYPE
		SYNTAX  INTEGER
		ACCESS  read-write
		STATUS  deprecated
		DESCRIPTION
		"Deprecated parameter. Actual behavior is read-only."
		::= { winlink1000OduAir 11 }

	winlink1000OduAirCurrentTxPower OBJECT-TYPE
		SYNTAX  INTEGER
		ACCESS  read-only
		STATUS  mandatory
		DESCRIPTION
		"Current Transmit Power in dBm. This is a nominal value while the actual transmit power includes additional attenuation."
		::= { winlink1000OduAir 12 }

	winlink1000OduAirMinFrequency OBJECT-TYPE
		SYNTAX  INTEGER
		ACCESS  read-only
		STATUS  mandatory
		DESCRIPTION
		"Minimum center frequency in MHz."
		::= { winlink1000OduAir 13 }

	winlink1000OduAirMaxFrequency OBJECT-TYPE
		SYNTAX  INTEGER
		ACCESS  read-only
		STATUS  mandatory
		DESCRIPTION
		"Maximum center frequency in MHz."
		::= { winlink1000OduAir 14 }

	winlink1000OduAirFreqResolution OBJECT-TYPE
		SYNTAX  INTEGER
		ACCESS  read-only
		STATUS  mandatory
		DESCRIPTION
		"Center Frequency resolution. 
		Measured in MHz if value < 100, otherwise in KHz."
		::= { winlink1000OduAir 15 }

	winlink1000OduAirCurrentFreq OBJECT-TYPE
		SYNTAX  INTEGER
		ACCESS  read-only
		STATUS  mandatory
		DESCRIPTION
		"Current Center Frequency.
		Measured in MHz if center frequency resolution value < 100, otherwise in KHz."
		::= { winlink1000OduAir 16 }

	winlink1000OduAirNumberOfChannels OBJECT-TYPE
		SYNTAX  INTEGER
		ACCESS  read-only
		STATUS  mandatory
		DESCRIPTION
		"Number of channels that can be used."
		::= { winlink1000OduAir 17 }

	-- ###########################################################
	--                      Channels Table
	-- ###########################################################

	winlink1000OduAirChannelsTable OBJECT-TYPE
		SYNTAX  SEQUENCE OF Winlink1000OduAirChannelsEntry
		ACCESS  not-accessible
		STATUS  mandatory
		DESCRIPTION
		"Table of channels used by automatic channels selection (ACS)."
		::= { winlink1000OduAir 18 }

	winlink1000OduAirChannelsEntry OBJECT-TYPE
		SYNTAX  Winlink1000OduAirChannelsEntry
		ACCESS  not-accessible
		STATUS  mandatory
		DESCRIPTION
		"ACS channels table entry."
		INDEX { winlink1000OduAirChannelsIndex }
		::= { winlink1000OduAirChannelsTable 1 }

	Winlink1000OduAirChannelsEntry ::= SEQUENCE {
		winlink1000OduAirChannelsIndex
			INTEGER,
		winlink1000OduAirChannelsFrequency
			INTEGER,
		winlink1000OduAirChannelsOperState
			INTEGER,
		winlink1000OduAirChannelsAvail
			INTEGER,
		winlink1000OduAirChannelsDefaultFreq
			INTEGER
		}

	winlink1000OduAirChannelsIndex OBJECT-TYPE
		SYNTAX  INTEGER
		ACCESS  read-only
		STATUS  mandatory
		DESCRIPTION
		"Channel Index."
		::= { winlink1000OduAirChannelsEntry 1 }

	winlink1000OduAirChannelsFrequency OBJECT-TYPE
		SYNTAX  INTEGER
		ACCESS  read-only
		STATUS  mandatory
		DESCRIPTION
		"Channel frequency in MHz."
		::= { winlink1000OduAirChannelsEntry 2 }

	winlink1000OduAirChannelsOperState OBJECT-TYPE
		SYNTAX  INTEGER
		ACCESS  read-write
		STATUS  mandatory
		DESCRIPTION
		"Channel state. Can be set by the user. 
		 Automatic Channel Selection uses channels that are AirChannelsOperState enabled and AirChannelsAvail enabled. 
		 A change is effective after link re-synchronization. Valid values: disabled (0), enabled (1).
		 Rewriteable only in Point-To-Point products."
		::= { winlink1000OduAirChannelsEntry 3 }

	winlink1000OduAirChannelsAvail OBJECT-TYPE
		SYNTAX  INTEGER
		ACCESS  read-only
		STATUS  mandatory
		DESCRIPTION
		"Channel state. Product specific and cannot be changed by the user. 
		Automatic Channel Selection uses channels that are AirChannelsOperState enabled and AirChannelsAvail enabled. 
		Valid values: disabled (0), enabled (1)."
		::= { winlink1000OduAirChannelsEntry 4 }

	winlink1000OduAirChannelsDefaultFreq OBJECT-TYPE
		SYNTAX  INTEGER
		ACCESS  read-only
		STATUS  mandatory
		DESCRIPTION
		"Default channel's availability for all CBWs.
		The valid values are: forbidden (0), available (1)."
		::= { winlink1000OduAirChannelsEntry 5 }

	winlink1000OduAirDfsState OBJECT-TYPE
		SYNTAX  INTEGER
		ACCESS  read-only
		STATUS  mandatory
		DESCRIPTION
		"Radar detection state. Valid values: disabled (0), enabled (1)."
		::= { winlink1000OduAir 19 }

	winlink1000OduAirAutoChannelSelectionState OBJECT-TYPE
		SYNTAX  INTEGER
		ACCESS  read-only
		STATUS  deprecated
		DESCRIPTION
		"Deprecated parameter. Indicating Automatic Channel Selection availability at current channel bandwidth. 
		Valid values: disabled (0), enabled (1)."
		::= { winlink1000OduAir 20 }

	winlink1000OduAirEnableTxPower OBJECT-TYPE
		SYNTAX  INTEGER {
			enabled (1),
			disabled (2)
			}
		ACCESS  read-only
		STATUS  mandatory
		DESCRIPTION
		"Indicating Transmit power configuration enabled or disabled."
		::= { winlink1000OduAir 21 }

	winlink1000OduAirMinTxPower OBJECT-TYPE
		SYNTAX  INTEGER
		ACCESS  read-only
		STATUS  mandatory
		DESCRIPTION
		"Minimum Transmit power in dBm."
		::= { winlink1000OduAir 22 }

	-- ###########################################################
	--                      Max Tx Power Table
	-- ###########################################################

	winlink1000OduAirMaxTxPowerTable OBJECT-TYPE
		SYNTAX  SEQUENCE OF Winlink1000OduAirMaxTxPowerEntry
		ACCESS  not-accessible
		STATUS  mandatory
		DESCRIPTION
		"Table of Maximum transmit power per air rate, in dBm."
		::= { winlink1000OduAir 23 }

	winlink1000OduAirMaxTxPowerEntry OBJECT-TYPE
		SYNTAX  Winlink1000OduAirMaxTxPowerEntry
		ACCESS  not-accessible
		STATUS  mandatory
		DESCRIPTION
		"Maximum Transmit power table entry."
		INDEX { winlink1000OduAirMaxTxPowerIndex }
		::= { winlink1000OduAirMaxTxPowerTable 1 }

	Winlink1000OduAirMaxTxPowerEntry ::= SEQUENCE {
		winlink1000OduAirMaxTxPowerIndex
			INTEGER,
		winlink1000OduAirMaxTxPower
			INTEGER
		}

	winlink1000OduAirMaxTxPowerIndex OBJECT-TYPE
		SYNTAX  INTEGER
		ACCESS  read-only
		STATUS  mandatory
		DESCRIPTION
		"Air interface rate index."
		::= { winlink1000OduAirMaxTxPowerEntry 1 }

	winlink1000OduAirMaxTxPower OBJECT-TYPE
		SYNTAX  INTEGER
		ACCESS  read-only
		STATUS  mandatory
		DESCRIPTION
		"Maximum Transmit power in dBm."
		::= { winlink1000OduAirMaxTxPowerEntry 2 }

	winlink1000OduAirChannelBandwidth OBJECT-TYPE
		SYNTAX  INTEGER
		ACCESS  read-write
		STATUS  mandatory
		DESCRIPTION
		"Channel bandwidth in KHz. A change is effective after reset."
		::= { winlink1000OduAir 24 }

	-- ###########################################################
	--                      Channel BW Table
	-- ###########################################################

	winlink1000OduAirChannelBWTable OBJECT-TYPE
		SYNTAX  SEQUENCE OF Winlink1000OduAirChannelBWEntry
		ACCESS  not-accessible
		STATUS  mandatory
		DESCRIPTION
		"Channel Bandwidths table."
		::= { winlink1000OduAir 25 }

	winlink1000OduAirChannelBWEntry OBJECT-TYPE
		SYNTAX  Winlink1000OduAirChannelBWEntry
		ACCESS  not-accessible
		STATUS  mandatory
		DESCRIPTION
		"Channel Bandwidth table entry."
		INDEX { winlink1000OduAirChannelBWIndex }
		::= { winlink1000OduAirChannelBWTable 1 }

	Winlink1000OduAirChannelBWEntry ::= SEQUENCE {
		winlink1000OduAirChannelBWIndex
			INTEGER,
		winlink1000OduAirChannelBWAvail
			INTEGER,
		winlink1000OduAirChannelsAdminState
			DisplayString,
		winlink1000OduAirChannelBWHSSATDDConflictPerCBW
			INTEGER,
		winlink1000OduAirChannelBWMinRatioForSupporting
			INTEGER,
		winlink1000OduAirChannelBWMaxRatioForSupporting
			INTEGER	
		}

	winlink1000OduAirChannelBWIndex OBJECT-TYPE
		SYNTAX  INTEGER {
				channelBW5MHz(1),
				channelBW10MHz(2),
				channelBW20MHz(3),
				channelBW40MHz(4),
				channelBW80MHz(5),
				channelBW7MHz(6),
				channelBW14MHz(7)				
		}
		ACCESS  read-only
		STATUS  mandatory
		DESCRIPTION
		"Channel Bandwidth index."
		::= { winlink1000OduAirChannelBWEntry 1 }

	winlink1000OduAirChannelBWAvail OBJECT-TYPE
		SYNTAX  INTEGER {
			notSupported(1),
			supportedManual(2),
			supportedWithACS(3)
		}
		ACCESS  read-only
		STATUS  mandatory
		DESCRIPTION
		"Channel Bandwidth availability, product specific.
		Options are: Not supported, supported with manual channel selection, supported with Automatic Channel Selection."
		::= { winlink1000OduAirChannelBWEntry 2 }

	winlink1000OduAirChannelsAdminState OBJECT-TYPE
		SYNTAX  DisplayString
		ACCESS  read-only
		STATUS  mandatory
		DESCRIPTION
		"Channels' availability per CBW."
		::= { winlink1000OduAirChannelBWEntry 3 }

	winlink1000OduAirChannelBWHSSATDDConflictPerCBW OBJECT-TYPE
		SYNTAX  INTEGER {
			noConflict(1),
			conflictSingle(2),
			conflictDual(3)
		}
		ACCESS  read-only
		STATUS  mandatory
		DESCRIPTION
		"Indication for possible Link drop per CBW due to conflict between HSS and ATDD."
		::= { winlink1000OduAirChannelBWEntry 4 }

	winlink1000OduAirChannelBWMinRatioForSupporting OBJECT-TYPE
		SYNTAX  INTEGER
		ACCESS  read-only
		STATUS  mandatory
		DESCRIPTION
		"Minimal TX ratio that may be used by the HSM and still enable proper operation of the aforementioned CBW."
		::= { winlink1000OduAirChannelBWEntry 5 }

	winlink1000OduAirChannelBWMaxRatioForSupporting OBJECT-TYPE
		SYNTAX  INTEGER
		ACCESS  read-only
		STATUS  mandatory
		DESCRIPTION
		"Maximal TX ratio that may be used by the HSM and still enable proper operation of the aforementioned CBW."
		::= { winlink1000OduAirChannelBWEntry 6 }

	winlink1000OduAirRFD OBJECT-TYPE
		SYNTAX  INTEGER
		ACCESS  read-only
		STATUS  mandatory
		DESCRIPTION
		"Current radio frame duration in microseconds."
		::= { winlink1000OduAir 26 }

	-- ###########################################################
	--                      Available Rates Table
	-- ###########################################################

	winlink1000OduAirRatesTable OBJECT-TYPE
		SYNTAX  SEQUENCE OF Winlink1000OduAirRatesEntry
		ACCESS  not-accessible
		STATUS  mandatory
		DESCRIPTION
		"Air Rate indexes table for current channel bandwidth."
		::= { winlink1000OduAir 27 }

	winlink1000OduAirRatesEntry OBJECT-TYPE
		SYNTAX  Winlink1000OduAirRatesEntry
		ACCESS  not-accessible
		STATUS  mandatory
		DESCRIPTION
		"Air Rate indexes table entry."
		INDEX { winlink1000OduAirRatesIndex }
		::= { winlink1000OduAirRatesTable 1 }

	Winlink1000OduAirRatesEntry ::= SEQUENCE {
		winlink1000OduAirRatesIndex
			INTEGER,
		winlink1000OduAirRatesAvail
			INTEGER
		}

	winlink1000OduAirRatesIndex OBJECT-TYPE
		SYNTAX  INTEGER 
		ACCESS  read-only
		STATUS  mandatory
		DESCRIPTION
		"Air Rate index."
		::= { winlink1000OduAirRatesEntry 1 }

	winlink1000OduAirRatesAvail OBJECT-TYPE
		SYNTAX  INTEGER {
			rateNotAvailable(1),
			rateAvailable(2)
		}
		ACCESS  read-only
		STATUS  mandatory
		DESCRIPTION
		"Air Rate availability, depending on air interface conditions."
		::= { winlink1000OduAirRatesEntry 2 }

	winlink1000OduAirDesiredRateIdx OBJECT-TYPE
		SYNTAX  INTEGER
		ACCESS  read-write
		STATUS  mandatory
		DESCRIPTION
		"Required Air Rate index. 0 reserved for Adaptive Rate.
		A change is effective immediately after Set operation to the master side
		while the link is up."
		::= { winlink1000OduAir 28 }

	winlink1000OduAirLinkDistance OBJECT-TYPE
		SYNTAX  INTEGER
		ACCESS  read-only
		STATUS  mandatory
		DESCRIPTION
		"Link distance in meters. 
		A value of -1 indicates an illegal value and is also used when a link is not established."
		::= { winlink1000OduAir 29 }

	winlink1000OduAirLinkWorkingMode OBJECT-TYPE
		SYNTAX  INTEGER {
			unknown(1),
			normal(2),
			fullCompatibilityRemoteUpgradeAvailable(3),
			fullCompatibilityLocalUpgradeAvailable(4),
			restrictedCompatibilityRemoteUpgradeRecomended(5),
			restrictedCompatibilityLocalUpgradeRecomended(6),
			softwareUpgradeRemoteUpgradeRequired(7),
			softwareUpgradeLocalUpgradeRequired(8),
			versionsIncompatibilityRemoteUpgradeRequired(9),
			versionsIncompatibilityLocalUpgradeRequired(10)
		}
		ACCESS  read-only
		STATUS  mandatory
		DESCRIPTION
		"Link working mode as a result of comparing versions of both sides of the link. 
		Possible modes are: Unknown - no link, Normal - versions on both sides are identical with full compatibility, 
		with restricted compatibility, or versions on both sides are different with software upgrade or versions incompatibility."
		::= { winlink1000OduAir 30 }

	winlink1000OduAirMajorLinkIfVersion OBJECT-TYPE
		SYNTAX  INTEGER
		ACCESS  read-only
		STATUS  mandatory
		DESCRIPTION
		"Major link interface version"
		::= { winlink1000OduAir 31 }

	winlink1000OduAirMinorLinkIfVersion OBJECT-TYPE
		SYNTAX  INTEGER
		ACCESS  read-only
		STATUS  mandatory
		DESCRIPTION
		"Minor link interface version"
		::= { winlink1000OduAir 32 }

	winlink1000OduAirHss OBJECT IDENTIFIER ::= { winlink1000OduAir 40 }

	winlink1000OduAirHssDesiredOpState OBJECT-TYPE
		SYNTAX  INTEGER {
			notSupported(1),
			independentUnit(2),
			hubSyncMaster(3),
			hubSyncClientContinueTx(4),
			hubSyncClientDisableTx(5),
			gpsSync(6),
			independentSyncUnit-ISU(7)
		}
		ACCESS  read-write
		STATUS  mandatory
		DESCRIPTION
		"Required Hub Site Synchronization operating state.
		For HssSyncUnits : 	For hssISU :[2,7] ,For hssGSU :[2,6]
		For HBS:			[2,3,4,5]"		
		::= { winlink1000OduAirHss 1 }

	winlink1000OduAirHssCurrentOpState OBJECT-TYPE
		SYNTAX  INTEGER {
			notSupported(1),
			independentUnit(2),
			hubSyncMaster(3),
			hubSyncClientContinueTx(4),
			hubSyncClientDisableTx(5),
			gpsSync(6),
			independentSyncUnit-ISU(7)
		}
		ACCESS  read-only
		STATUS  mandatory
		DESCRIPTION
		"Current Hub Site Synchronization operating state."		
		::= { winlink1000OduAirHss 2 }

	winlink1000OduAirHssSyncStatus OBJECT-TYPE
		SYNTAX  INTEGER {
			notApplicable(1),
			notSynchronized(2),
			synchronized(3)
		}
		ACCESS  read-only
		STATUS  mandatory
		DESCRIPTION
		"Hub Site Synchronization sync status."		
		::= { winlink1000OduAirHss 3 }

	winlink1000OduAirHssExtPulseStatus OBJECT-TYPE
		SYNTAX  INTEGER {
			notDetected(1),
			generating(2),
			generatingAndDetected(3),
			generatingAndImproperDetected(4),
			detected(5),
			improperDetected(6),
			multipleSourcesDetected(7)
		}
		ACCESS  read-only
		STATUS  mandatory
		DESCRIPTION
		"Hub Site Synchronization external pulse detection status.
		In GSS mode: 
		if generating then 1PSP is auto generated by the GSS Unit.
		if generatingAndDetecting then 1PSP is generated by GPS satellites signal."		
		::= { winlink1000OduAirHss 4 }

	winlink1000OduAirHssExtPulseType OBJECT-TYPE
		SYNTAX  INTEGER {
			notApplicable(1),
			typeA(2),
			typeB(3),
			typeC(4),
			typeD(5),
			typeE(6),
			typeF(7)
		}
		ACCESS  read-only
		STATUS  mandatory
		DESCRIPTION
		"Hub Site Synchronization external pulse type."		
		::= { winlink1000OduAirHss 5 }
		
	winlink1000OduAirHssDesiredExtPulseType OBJECT-TYPE
		SYNTAX  INTEGER {
			notApplicable(1),
			typeA(2),
			typeB(3),
			typeC(4),
			typeD(5),
			typeE(6),
			typeF(7)
		}
		ACCESS  read-write
		STATUS  mandatory
		DESCRIPTION
		"Hub Site Synchronization required external pulse type. Valid values for read write:
		 {typeA(2),typeB(3),typeC(4),typeD(5),typeE(6),typeF(7)}. Valid value for read only:
		 {notApplicable(1)}."		
		::= { winlink1000OduAirHss 6 }
		
	-- ###########################################################
	--                      HSS Radio Frame Pattern Table
	-- ###########################################################
	winlink1000OduAirHssRfpTable OBJECT-TYPE
		SYNTAX  SEQUENCE OF Winlink1000OduAirHssRfpEntry
		ACCESS  not-accessible
		STATUS  mandatory
		DESCRIPTION
		"ODU Radio Frame Patterns (RFP) Table."
		::= { winlink1000OduAirHss 7 }

	winlink1000OduAirHssRfpEntry OBJECT-TYPE
		SYNTAX  Winlink1000OduAirHssRfpEntry
		ACCESS  not-accessible
		STATUS  mandatory
		DESCRIPTION
		"ODU RFP Table entry."
		INDEX { winlink1000OduAirHssRfpIndex }
		::= { winlink1000OduAirHssRfpTable 1 }

	Winlink1000OduAirHssRfpEntry ::= SEQUENCE {
		winlink1000OduAirHssRfpIndex
			INTEGER,
		winlink1000OduAirHssRfpEthChannelBW5MHz
			INTEGER,
		winlink1000OduAirHssRfpTdmChannelBW5MHz
			INTEGER,
		winlink1000OduAirHssRfpEthChannelBW10MHz
			INTEGER,
		winlink1000OduAirHssRfpTdmChannelBW10MHz
			INTEGER,
		winlink1000OduAirHssRfpEthChannelBW20MHz
			INTEGER,
		winlink1000OduAirHssRfpTdmChannelBW20MHz
			INTEGER,
		winlink1000OduAirHssRfpEthChannelBW40MHz
			INTEGER,
		winlink1000OduAirHssRfpTdmChannelBW40MHz
			INTEGER,
		winlink1000OduAirHssRfpEthChannelBW80MHz
			INTEGER,
		winlink1000OduAirHssRfpEthChannelBW7MHz
			INTEGER,
		winlink1000OduAirHssRfpEthChannelBW14MHz
			INTEGER
		}
		
	winlink1000OduAirHssRfpIndex OBJECT-TYPE
		SYNTAX  INTEGER (2..7)
		ACCESS  read-only
		STATUS  mandatory
		DESCRIPTION
		"ODU RFP Table index. The index represent the Radio Frame Pattern:
		 typeA(2), typeB(3), typeC(4), typeD(5),typeE(6),typeF(7)."
		::= { winlink1000OduAirHssRfpEntry 1 }
		
	winlink1000OduAirHssRfpEthChannelBW5MHz OBJECT-TYPE
		SYNTAX  INTEGER {
			bestFit(1),
			nonOptimal(2),
			notAvailable(3)
		}
		ACCESS  read-only
		STATUS  mandatory
		DESCRIPTION
		"Represents the compatibility of Ethernet service under Channel BW of 5MHz 
		 in the specific Radio Frame Pattern."
		::= { winlink1000OduAirHssRfpEntry 2 }
		
	winlink1000OduAirHssRfpTdmChannelBW5MHz OBJECT-TYPE
		SYNTAX  INTEGER {
			bestFit(1),
			nonOptimal(2),
			notAvailable(3)
		}
		ACCESS  read-only
		STATUS  mandatory
		DESCRIPTION
		"Represents the compatibility of TDM service under Channel BW of 5MHz 
		 in the specific Radio Frame Pattern."
		::= { winlink1000OduAirHssRfpEntry 3 }
		
		winlink1000OduAirHssRfpEthChannelBW10MHz OBJECT-TYPE
		SYNTAX  INTEGER {
			bestFit(1),
			nonOptimal(2),
			notAvailable(3)
		}
		ACCESS  read-only
		STATUS  mandatory
		DESCRIPTION
		"Represents the compatibility of Ethernet service under Channel BW of 10MHz 
		 in the specific Radio Frame Pattern."
		::= { winlink1000OduAirHssRfpEntry 4 }
		
	winlink1000OduAirHssRfpTdmChannelBW10MHz OBJECT-TYPE
		SYNTAX  INTEGER {
			bestFit(1),
			nonOptimal(2),
			notAvailable(3)
		}
		ACCESS  read-only
		STATUS  mandatory
		DESCRIPTION
		"Represents the compatibility of TDM service under Channel BW of 10MHz 
		 in the specific Radio Frame Pattern."
		::= { winlink1000OduAirHssRfpEntry 5 }
		
	winlink1000OduAirHssRfpEthChannelBW20MHz OBJECT-TYPE
		SYNTAX  INTEGER {
			bestFit(1),
			nonOptimal(2),
			notAvailable(3)
		}
		ACCESS  read-only
		STATUS  mandatory
		DESCRIPTION
		"Represents the compatibility of Ethernet service under Channel BW of 20MHz 
		 in the specific Radio Frame Pattern."
		::= { winlink1000OduAirHssRfpEntry 6 }
		
	winlink1000OduAirHssRfpTdmChannelBW20MHz OBJECT-TYPE
		SYNTAX  INTEGER {
			bestFit(1),
			nonOptimal(2),
			notAvailable(3)
		}
		ACCESS  read-only
		STATUS  mandatory
		DESCRIPTION
		"Represents the compatibility of TDM service under Channel BW of 20MHz 
		 in the specific Radio Frame Pattern."
		::= { winlink1000OduAirHssRfpEntry 7 }
		
	winlink1000OduAirHssRfpEthChannelBW40MHz OBJECT-TYPE
		SYNTAX  INTEGER {
			bestFit(1),
			nonOptimal(2),
			notAvailable(3)
		}
		ACCESS  read-only
		STATUS  mandatory
		DESCRIPTION
		"Represents the compatibility of Ethernet service under Channel BW of 40MHz 
		 in the specific Radio Frame Pattern."
		::= { winlink1000OduAirHssRfpEntry 8 }
		
	winlink1000OduAirHssRfpTdmChannelBW40MHz OBJECT-TYPE
		SYNTAX  INTEGER {
			bestFit(1),
			nonOptimal(2),
			notAvailable(3)
		}
		ACCESS  read-only
		STATUS  mandatory
		DESCRIPTION
		"Represents the compatibility of TDM service under Channel BW of 40MHz 
		 in the specific Radio Frame Pattern."
		::= { winlink1000OduAirHssRfpEntry 9 }
	
	winlink1000OduAirHssRfpEthChannelBW80MHz OBJECT-TYPE
		SYNTAX  INTEGER {
			bestFit(1),
			nonOptimal(2),
			notAvailable(3)
		}
		ACCESS  read-only
		STATUS  mandatory
		DESCRIPTION
		"Represents the compatibility of Ethernet service under Channel BW of 80MHz 
		 in the specific Radio Frame Pattern."
		::= { winlink1000OduAirHssRfpEntry 10 }
		
	winlink1000OduAirHssRfpEthChannelBW7MHz OBJECT-TYPE
		SYNTAX  INTEGER {
			bestFit(1),
			nonOptimal(2),
			notAvailable(3)
		}
		ACCESS  read-only
		STATUS  mandatory
		DESCRIPTION
		"Represents the compatibility of Ethernet service under Channel BW of 7MHz 
		 in the specific Radio Frame Pattern."
		::= { winlink1000OduAirHssRfpEntry 11 }
	
	winlink1000OduAirHssRfpEthChannelBW14MHz OBJECT-TYPE
		SYNTAX  INTEGER {
			bestFit(1),
			nonOptimal(2),
			notAvailable(3)
		}
		ACCESS  read-only
		STATUS  mandatory
		DESCRIPTION
		"Represents the compatibility of Ethernet service under Channel BW of 14MHz 
		 in the specific Radio Frame Pattern."
		::= { winlink1000OduAirHssRfpEntry 12 }
	
	winlink1000OduAirHssRfpStr OBJECT-TYPE
		SYNTAX  DisplayString
		ACCESS  read-only
		STATUS  mandatory
		DESCRIPTION
		"Hub Site Synchronization supported patterns"
		::= { winlink1000OduAirHss 8 }
		
	winlink1000OduAirHssHsmID OBJECT-TYPE
		SYNTAX  INTEGER
		ACCESS  read-only
		STATUS  mandatory
		DESCRIPTION
		"A  unique ID which is common to the HSM and all its collocated ODUs"
		::= { winlink1000OduAirHss 9 }
		
	winlink1000OduAirHssTime OBJECT-TYPE
		SYNTAX  DisplayString
		ACCESS  read-only
		STATUS  mandatory
		DESCRIPTION
		"Hub Site Synchronization GPS time"
		::= { winlink1000OduAirHss 10 }
		
	winlink1000OduAirHssLatitude OBJECT-TYPE
		SYNTAX  DisplayString
		ACCESS  read-only
		STATUS  mandatory
		DESCRIPTION
		"Hub Site Synchronization GPS Latitude"
		::= { winlink1000OduAirHss 11 }
		
	winlink1000OduAirHssNSIndicator OBJECT-TYPE
		SYNTAX  DisplayString
		ACCESS  read-only
		STATUS  mandatory
		DESCRIPTION
		"Hub Site Synchronization GPS N/S Indicator"
		::= { winlink1000OduAirHss 12 }
		
	winlink1000OduAirHssLongitude OBJECT-TYPE
		SYNTAX  DisplayString
		ACCESS  read-only
		STATUS  mandatory
		DESCRIPTION
		"Hub Site Synchronization GPS Longitude"
		::= { winlink1000OduAirHss 13 }
		
	winlink1000OduAirHssEWIndicator OBJECT-TYPE
		SYNTAX  DisplayString
		ACCESS  read-only
		STATUS  mandatory
		DESCRIPTION
		"Hub Site Synchronization GPS E/W Indicator"
		::= { winlink1000OduAirHss 14 }
		
	winlink1000OduAirHssNumSatellites OBJECT-TYPE
		SYNTAX  DisplayString
		ACCESS  read-only
		STATUS  mandatory
		DESCRIPTION
		"Hub Site Synchronization GPS Number of satellites"
		::= { winlink1000OduAirHss 15 }
		
	winlink1000OduAirHssAltitude OBJECT-TYPE
		SYNTAX  DisplayString
		ACCESS  read-only
		STATUS  mandatory
		DESCRIPTION
		"Hub Site Synchronization GPS Altitude"
		::= { winlink1000OduAirHss 16 }
		
	winlink1000OduAirHssRfpPhase OBJECT-TYPE
		SYNTAX  INTEGER {
			rfpNormalPhase(1),
			rfpShiftedPhase(2)
		}
		ACCESS  read-write
		STATUS  mandatory
		DESCRIPTION
		"Hub Site Synchronization GPS RFP phase"
		::= { winlink1000OduAirHss 17 }
		
	winlink1000OduAirHssInterSiteSynchronizationMode OBJECT-TYPE
		SYNTAX  INTEGER {
			independent(1),
			synchronized(2)
		}
		ACCESS  read-write
		STATUS  mandatory
		DESCRIPTION
		"Inter-Site Synchronization Mode - independent / synchronized"
		::= { winlink1000OduAirHss 18 }
		
	winlink1000OduAirHssInterSiteSynchronizationAvailability OBJECT-TYPE
		SYNTAX  INTEGER {
			notAvailable(1),
			available(2)
		}
		ACCESS  read-only
		STATUS  mandatory
		DESCRIPTION
		"Inter-Site Synchronization Availability"
		::= { winlink1000OduAirHss 19 }
		
	winlink1000OduAirHssSatellitesSatSyncRequired OBJECT-TYPE
		SYNTAX  INTEGER {
			notRequired(1),
			required(2)
		}
		ACCESS  read-write
		STATUS  mandatory
		DESCRIPTION
		"Satellites Synchronization Is Required"
		::= { winlink1000OduAirHss 20 }
		
	winlink1000OduAirHssDomainID OBJECT-TYPE
		SYNTAX  DisplayString
		ACCESS  read-write
		STATUS  mandatory
		DESCRIPTION
		"EHSS domain. Indentify set of CUs with same HSS synchronization"
		::= { winlink1000OduAirHss 21 }
		
	winlink1000OduAirHssSupportedSynchronizationProtocol OBJECT-TYPE
		SYNTAX  INTEGER {
			serialOnly(1),
			ethOnly(2),
			both(3),
			ghssAndEth(4),
			ghssEthSerial(5)
		}
		ACCESS  read-only
		STATUS  mandatory
		DESCRIPTION
		"Supported Synchronization Protocols"
		::= { winlink1000OduAirHss 22 }
		
	winlink1000OduAirHssDesiredSynchronizationProtocol OBJECT-TYPE
		SYNTAX  INTEGER {
			serialOnly(1),
			ethOnly(2),
			both(3),
			ghssOnly(4)
		}
		ACCESS  read-write
		STATUS  mandatory
		DESCRIPTION
		"Desired Synchronization Protocols"
		::= { winlink1000OduAirHss 23 }
		
	winlink1000OduAirHssDiscover OBJECT-TYPE
		SYNTAX  INTEGER {
			startAll(1),
			startAllMstr(2),
			startMyDmn(3),
			startMyMstr(4)
		}
		ACCESS  read-write
		STATUS  mandatory
		DESCRIPTION
		"Initiate Discovery process of ODUs on the network."
		::= { winlink1000OduAirHss 24 }
		
	winlink1000OduAirHssNumberOfDiscoveredODUs OBJECT-TYPE
		SYNTAX  INTEGER (0..1000)
		ACCESS  read-only
		STATUS  mandatory
		DESCRIPTION
		"Number OF Discovered ODUs in network."
		::= { winlink1000OduAirHss 25 }
		
	-- ###########################################################
	--                      HSS Discover Table
	-- ###########################################################
	
	winlink1000OduAirHssDiscoverTable OBJECT-TYPE
		SYNTAX  SEQUENCE OF Winlink1000OduAirHssDiscoverEntry
		ACCESS  not-accessible
		STATUS  mandatory
		DESCRIPTION
		"HSS Discover Table."
		::= { winlink1000OduAirHss 26 }

	winlink1000OduAirHssDiscoverEntry OBJECT-TYPE
		SYNTAX  Winlink1000OduAirHssDiscoverEntry
		ACCESS  not-accessible
		STATUS  mandatory
		DESCRIPTION
		"ODU Discover Table entry."
		INDEX { winlink1000OduAirHssDiscoverIndex }
		::= { winlink1000OduAirHssDiscoverTable 1 }

	Winlink1000OduAirHssDiscoverEntry ::= SEQUENCE {
		winlink1000OduAirHssDiscoverIndex
			INTEGER,
		winlink1000OduAirHssDiscoverODUDescription
			DisplayString
		}
		
	winlink1000OduAirHssDiscoverIndex OBJECT-TYPE
		SYNTAX  INTEGER (1..256)
		ACCESS  read-only
		STATUS  mandatory
		DESCRIPTION
		"HSS Discover Table Index."
		::= { winlink1000OduAirHssDiscoverEntry 1 }
		
	winlink1000OduAirHssDiscoverODUDescription OBJECT-TYPE
		SYNTAX  DisplayString
		ACCESS  read-only
		STATUS  mandatory
		DESCRIPTION
		"Hold ODU HSS status in compress format:
		Domain,IP,HSS Role,Hss support,
		Enabled HSS protocol,Sync Status,
		Location, IPv6."
		::= { winlink1000OduAirHssDiscoverEntry 2 }
		
	-- ###################### End of Discover Table ###################
	
	winlink1000OduAirHssMasterSlaveCompatibility OBJECT-TYPE
		SYNTAX  INTEGER {
			compatible(1),
			notCompatible(2)
		}
		ACCESS  read-only
		STATUS  mandatory
		DESCRIPTION
		"EHSM version compatibility. Relevant to Ethernet HSS Clients only."
		::= { winlink1000OduAirHss 27 }
		
	winlink1000OduAirHssNumberOfAssociatedCU OBJECT-TYPE
		SYNTAX  INTEGER (0..256)
		ACCESS  read-only
		STATUS  mandatory
		DESCRIPTION
		"Number of associated Ethernet HSS Clients. Relevant to Ethernet HSS Masters only"
		::= { winlink1000OduAirHss 28 }
		
	-- ###########################################################
	--                      HSS Associated CU Table
	-- ###########################################################
		
	winlink1000OduAirHssAssociatedCUTable OBJECT-TYPE
		SYNTAX  SEQUENCE OF Winlink1000OduAirHssAssociatedCUTableEntry
		ACCESS  not-accessible
		STATUS  mandatory
		DESCRIPTION
		"Associated Ethernet HSS Clients Table. Releant for Ethernet HSS Masters only."
		::= { winlink1000OduAirHss 29 }

	winlink1000OduAirHssAssociatedCUTableEntry OBJECT-TYPE
		SYNTAX  Winlink1000OduAirHssAssociatedCUTableEntry
		ACCESS  not-accessible
		STATUS  mandatory
		DESCRIPTION
		"Associated Ethernet HSS Clients Table Entry. Releant for Ethernet HSS Masters only."
		INDEX { winlink1000OduAirHssAssociatedCUIndex }
		::= { winlink1000OduAirHssAssociatedCUTable 1 }

	Winlink1000OduAirHssAssociatedCUTableEntry ::= SEQUENCE {
		winlink1000OduAirHssAssociatedCUIndex
			INTEGER,
		winlink1000OduAirHssAssociatedCUDescription
			DisplayString
		}
		
	winlink1000OduAirHssAssociatedCUIndex OBJECT-TYPE
		SYNTAX  INTEGER (1..256)
		ACCESS  read-only
		STATUS  mandatory
		DESCRIPTION
		"Associated Ethernet HSS Clients Table Index. Releant for Ethernet HSS Masters only."
		::= { winlink1000OduAirHssAssociatedCUTableEntry 1 }
		
	winlink1000OduAirHssAssociatedCUDescription OBJECT-TYPE
		SYNTAX  DisplayString
		ACCESS  read-only
		STATUS  mandatory
		DESCRIPTION
		"Holds Associated Ethernet HSS Clients Description in compress format:
		IP,Delay,Compatibility,Ethernet Speed, Ethernet Rx rate, IPv6"
		::= { winlink1000OduAirHssAssociatedCUTableEntry 2 }
		
	-- ###################### End of Associated CU Table ###################
		
	winlink1000OduAirHssSyncStatusEth OBJECT-TYPE
		SYNTAX  INTEGER {
			notApplicable(1),
			notSynchronized(2),
			goodSynchronizationLevel(3),
			mediumSynchronizationLevel(4),
			badSynchronizationLevel(5),
			startSynchronization(6)
		}
		ACCESS  read-only
		STATUS  mandatory
		DESCRIPTION
		"Ethernet HSS Client Synchronization Level"
		::= { winlink1000OduAirHss 30 }
		
	winlink1000OduAirHssEthVLANTag OBJECT-TYPE
		SYNTAX  INTEGER (1..40947)
		ACCESS  read-write
		STATUS  mandatory
		DESCRIPTION
		"Ethernet HSS VLan Tag: 
		The least significate decimal digit is the VLan Priority(0-6) 
		and the rest of the digits represents VLan ID (2-4094)"
		::= { winlink1000OduAirHss 31 }
	
	winlink1000OduAirHssHSMIPAddress OBJECT-TYPE
		SYNTAX  IpAddress
		ACCESS  read-only
		STATUS  mandatory
		DESCRIPTION
		"HSMs IP address. Relevant for HSC synchronized over Ethernet."
		::= { winlink1000OduAirHss 32 }

	winlink1000OduAirHssDelayToHSM OBJECT-TYPE
		SYNTAX  INTEGER (0..1000000)
		ACCESS  read-only
		STATUS  mandatory
		DESCRIPTION
		"Delay in microseconds to HSM. Relevant for HSC synchronized over Ethernet."
		::= { winlink1000OduAirHss 33 }

	winlink1000OduAirHssSyncAcquisitionSeconds OBJECT-TYPE
		SYNTAX  INTEGER
		ACCESS  read-write
		STATUS  mandatory
		DESCRIPTION
		"Accumulated quantity of seconds in clock acquisition while connected to current HSM"
		::= { winlink1000OduAirHss 34 }
		
	winlink1000OduAirHssHSMIPv6Address OBJECT-TYPE
		SYNTAX  DisplayString
		ACCESS  read-only
		STATUS  mandatory
		DESCRIPTION
		"HSMs IPv6 address. Relevant for HSC synchronized over Ethernet."
		::= { winlink1000OduAirHss 35 }
		
	-- ###################### End of HSS Section ###################
	
	winlink1000OduAirLockRemote OBJECT-TYPE
		SYNTAX  INTEGER {
			unlock(1),
			lock(2)
			}
		ACCESS  read-write
		STATUS  mandatory
		DESCRIPTION
		"This parameter enables locking the link with a specific ODU.
		 The following values can be set:
		 Unlock (default) - The ODU is not locked on a specific remote ODU. Unlock can only be performed when the link is not connected.
		 Lock - The ODU is locked on a specific remote ODU. Lock can only be performed when the link is active."
		::= { winlink1000OduAir 41 }

	winlink1000OduAirAntennaGain OBJECT-TYPE
		SYNTAX  INTEGER
		ACCESS  read-write
		STATUS  mandatory
		DESCRIPTION
		"Current Antenna Gain in 0.1 dBi resolution. User defined value for 
		external antenna.
		Legal range: MinAntennaGain<AntennaGain<MaxAntennaGain."
		::= { winlink1000OduAir 42 }

	winlink1000OduAirFeederLoss OBJECT-TYPE
		SYNTAX  INTEGER
		ACCESS  read-write
		STATUS  mandatory
		DESCRIPTION
		"Current Feeder Loss in 0.1 dBm resolution. User defined value for 
		external antenna."
		::= { winlink1000OduAir 43 }

	winlink1000OduAirMaxAntennaGain OBJECT-TYPE
		SYNTAX  INTEGER
		ACCESS  read-only
		STATUS  mandatory
		DESCRIPTION
		"Maximum allowed Antenna Gain in 0.1 dBi resolution."
		::= { winlink1000OduAir 44 }

	winlink1000OduAirMinAntennaGain OBJECT-TYPE
		SYNTAX  INTEGER
		ACCESS  read-only
		STATUS  mandatory
		DESCRIPTION
		"Minimum allowed Antenna Gain in 0.1 dBi resolution."
		::= { winlink1000OduAir 45 }

	winlink1000OduAirMaxEIRP OBJECT-TYPE
		SYNTAX  INTEGER
		ACCESS  read-only
		STATUS  mandatory
		DESCRIPTION
		"Maximum EIRP value as defined by regulation in 0.1 dBm resolution."
		::= { winlink1000OduAir 46 }

	winlink1000OduAirAntennaGainConfigSupport OBJECT-TYPE
		SYNTAX  INTEGER {
			supported(1),
			notSupported(2)
			}
		ACCESS  read-only
		STATUS  mandatory
		DESCRIPTION
		"Antenna Gain Configurability, options are product specific: supported, not supported."
		::= { winlink1000OduAir 47 }

	winlink1000OduAirAntennaType OBJECT-TYPE
		SYNTAX  INTEGER {
			single(1),
			dual(2),
			unDefined(3),
			triple(4)
			}
		ACCESS  read-write
		STATUS  mandatory
		DESCRIPTION
		"External Antenna Type: Monopolar or Bipolar."
		::= { winlink1000OduAir 48 }

	winlink1000OduAirRssBalance OBJECT-TYPE
		SYNTAX  INTEGER (-2..2)
		ACCESS  read-only
		STATUS  mandatory
		DESCRIPTION
		"RSS balance. Relation between RSS in radio 1 and RSS in radio 2.
		-2 : Radio 2 RSS is much stronger than Radio 1 RSS.
		-1 : Radio 2 RSS is stronger than Radio 1 RSS.
		-0 : Radio 2 RSS is equal to Radio 1 RSS.
		1  : Radio 1 RSS is stronger than Radio 2 RSS.
		2  : Radio 1 RSS is much stronger than Radio 2 RSS."
		::= { winlink1000OduAir 49 }

	winlink1000OduAirTotalTxPower OBJECT-TYPE
		SYNTAX  INTEGER
		ACCESS  read-only
		STATUS  mandatory
		DESCRIPTION
		"Total Transmit Power in dBm. This is a nominal value While the actual transmit power includes additional attenuation."
		::= { winlink1000OduAir 50 }

	winlink1000OduAirInstallFreqAndCBW OBJECT-TYPE
		SYNTAX  DisplayString 
		ACCESS  read-write
		STATUS  mandatory
		DESCRIPTION
		"Installation frequency , Channel BW. Relevant in point to point systems."
		::= { winlink1000OduAir 51 }

	winlink1000OduAirDFStype OBJECT-TYPE
		SYNTAX  INTEGER {
			dfs01(1),
			dfs02(2),
			dfs04(4),
			dfs40(40),
			dfs50(50),
			dfs51(51)
			}
		ACCESS  read-only
		STATUS  mandatory
		DESCRIPTION
		"DFS regulation type."
		::= { winlink1000OduAir 52 }

	winlink1000OduAirCombo OBJECT IDENTIFIER ::= { winlink1000OduAir 53 }

	-- ###########################################################
	--                      Multi-band Sub Bands Table
	-- ###########################################################
	winlink1000OduAirComboSubBandTable OBJECT-TYPE
		SYNTAX  SEQUENCE OF Winlink1000OduAirComboSubBandEntry
		ACCESS  not-accessible
		STATUS  mandatory
		DESCRIPTION
		"ODU Multi-band Sub Bands Table."
		::= { winlink1000OduAirCombo 1 }

	winlink1000OduAirComboSubBandEntry OBJECT-TYPE
		SYNTAX  Winlink1000OduAirComboSubBandEntry
		ACCESS  not-accessible
		STATUS  mandatory
		DESCRIPTION
		"ODU Multi-band Sub Bands Table entry."
		INDEX { winlink1000OduAirComboSubBandIndex }
		::= { winlink1000OduAirComboSubBandTable 1 }

	Winlink1000OduAirComboSubBandEntry ::= SEQUENCE {
		winlink1000OduAirComboSubBandIndex
			INTEGER,
		winlink1000OduAirComboSubBandId
			DisplayString,
		winlink1000OduAirComboSubBandDescription
			DisplayString,
		winlink1000OduAirComboSubBandInstallFreq
			INTEGER,
		winlink1000OduAirComboSubBandAdminState
			INTEGER,
		winlink1000OduAirComboSubBandInstallationAllowed
			INTEGER,
		winlink1000OduAirComboFrequencyBandId
			INTEGER,
		winlink1000OduAirComboSubBandChannelBW5AdminState
			DisplayString,
		winlink1000OduAirComboSubBandChannelBW10AdminState
			DisplayString,
		winlink1000OduAirComboSubBandChannelBW20AdminState
			DisplayString,
		winlink1000OduAirComboSubBandChannelBW40AdminState
			DisplayString,			
		winlink1000OduAirComboSubBandAllowableChannels
			DisplayString,	
		winlink1000OduAirComboSubBandChannelBWAvail
			DisplayString,
		winlink1000OduAirComboSubBandChannelBandwidth
			INTEGER,
		winlink1000OduAirComboSubBandMinFreq
			INTEGER,
		winlink1000OduAirComboSubBandMaxFreq
			INTEGER,
		winlink1000OduAirComboSubBandFrequencyResolution
			INTEGER,
		winlink1000OduAirComboSubBandDefaultChannelList
			DisplayString,
		winlink1000OduAirComboSubBandDfsState
			INTEGER,
		winlink1000OduAirComboSubBandChannelBW80AdminState
			DisplayString,
		winlink1000OduAirComboSubBandChannelBW7AdminState
			DisplayString,
		winlink1000OduAirComboSubBandChannelBW14AdminState
			DisplayString
		}
		
	winlink1000OduAirComboSubBandIndex OBJECT-TYPE
		SYNTAX  INTEGER
		ACCESS  read-only
		STATUS  mandatory
		DESCRIPTION
		"ODU Multi-band sub bands table index."
		::= { winlink1000OduAirComboSubBandEntry 1 }
		
	winlink1000OduAirComboSubBandId OBJECT-TYPE
		SYNTAX  DisplayString
		ACCESS  read-only
		STATUS  mandatory
		DESCRIPTION
		"Represents the Multi-band sub band ID."
		::= { winlink1000OduAirComboSubBandEntry 2 }

	winlink1000OduAirComboSubBandDescription OBJECT-TYPE
		SYNTAX  DisplayString
		ACCESS  read-only
		STATUS  mandatory
		DESCRIPTION
		"Multi-band sub band description."
		::= { winlink1000OduAirComboSubBandEntry 3 }

	winlink1000OduAirComboSubBandInstallFreq OBJECT-TYPE
		SYNTAX  INTEGER
		ACCESS  read-only
		STATUS  mandatory
		DESCRIPTION
		"Represents the Multi-band sub band installation frequency in KHz."
		::= { winlink1000OduAirComboSubBandEntry 4 }

	winlink1000OduAirComboSubBandAdminState OBJECT-TYPE
		SYNTAX  INTEGER {
			enabled (1),
			disabled (2)
		}
		ACCESS  read-only
		STATUS  mandatory
		DESCRIPTION
		"Represents the Multi-band sub band administrative state."
		::= { winlink1000OduAirComboSubBandEntry 5 }

	winlink1000OduAirComboSubBandInstallationAllowed OBJECT-TYPE
		SYNTAX  INTEGER {
			yes (1),
			no (2),
			inactive(3)
		}
		ACCESS  read-only
		STATUS  mandatory
		DESCRIPTION
		"Reflects if the Multi-band sub band allowes installtion."
		::= { winlink1000OduAirComboSubBandEntry 6 }

	winlink1000OduAirComboFrequencyBandId OBJECT-TYPE
		SYNTAX  INTEGER
		ACCESS  read-only
		STATUS  mandatory
		DESCRIPTION
		"Reflects the frequency band Id."
		::= { winlink1000OduAirComboSubBandEntry 7 }
	
	winlink1000OduAirComboSubBandChannelBW5AdminState OBJECT-TYPE
		SYNTAX	DisplayString
		ACCESS  read-only
		STATUS  mandatory
		DESCRIPTION
		"Reflects the CBW 5MHz admin state vector."
		::= { winlink1000OduAirComboSubBandEntry 8 }
		
	winlink1000OduAirComboSubBandChannelBW10AdminState OBJECT-TYPE
		SYNTAX	DisplayString
		ACCESS  read-only
		STATUS  mandatory
		DESCRIPTION
		"Reflects the CBW 10MHz admin state vector."
		::= { winlink1000OduAirComboSubBandEntry 9 }
		
	winlink1000OduAirComboSubBandChannelBW20AdminState OBJECT-TYPE
		SYNTAX	DisplayString
		ACCESS  read-only
		STATUS  mandatory
		DESCRIPTION
		"Reflects the CBW 20MHz admin state vector."
		::= { winlink1000OduAirComboSubBandEntry 10 }
		
	winlink1000OduAirComboSubBandChannelBW40AdminState OBJECT-TYPE
		SYNTAX	DisplayString
		ACCESS  read-only
		STATUS  mandatory
		DESCRIPTION
		"Reflects the CBW 40MHz admin state vector."
		::= { winlink1000OduAirComboSubBandEntry 11 }
		
	winlink1000OduAirComboSubBandAllowableChannels OBJECT-TYPE
		SYNTAX	DisplayString
		ACCESS  read-only
		STATUS  mandatory
		DESCRIPTION
		"Reflects the allowable channels vector."
		::= { winlink1000OduAirComboSubBandEntry 12 }
		
	winlink1000OduAirComboSubBandChannelBWAvail OBJECT-TYPE
		SYNTAX	DisplayString
		ACCESS  read-only
		STATUS  mandatory
		DESCRIPTION
		"Reflects the available CBWs vector."
		::= { winlink1000OduAirComboSubBandEntry 13 }
		
	winlink1000OduAirComboSubBandChannelBandwidth OBJECT-TYPE
		SYNTAX  INTEGER
		ACCESS  read-only
		STATUS  mandatory
		DESCRIPTION
		"Reflects the sub-band default channel bandwidth."
		::= { winlink1000OduAirComboSubBandEntry 14 }
		
	winlink1000OduAirComboSubBandMinFreq OBJECT-TYPE
		SYNTAX  INTEGER
		ACCESS  read-only
		STATUS  mandatory
		DESCRIPTION
		"Reflects the sub-band default minimal frequency."
		::= { winlink1000OduAirComboSubBandEntry 15 }
		
	winlink1000OduAirComboSubBandMaxFreq OBJECT-TYPE
		SYNTAX  INTEGER
		ACCESS  read-only
		STATUS  mandatory
		DESCRIPTION
		"Reflects the sub-band default maximal frequency."
		::= { winlink1000OduAirComboSubBandEntry 16 }
		
	winlink1000OduAirComboSubBandFrequencyResolution OBJECT-TYPE
		SYNTAX  INTEGER
		ACCESS  read-only
		STATUS  mandatory
		DESCRIPTION
		"Reflects the sub-band frequency resolution."
		::= { winlink1000OduAirComboSubBandEntry 17 }
			
	winlink1000OduAirComboSubBandDefaultChannelList OBJECT-TYPE
		SYNTAX	DisplayString
		ACCESS  read-only
		STATUS  mandatory
		DESCRIPTION
		"Reflects the default channel list vector."
		::= { winlink1000OduAirComboSubBandEntry 18 }
		
	winlink1000OduAirComboSubBandDfsState OBJECT-TYPE
		SYNTAX  INTEGER
		ACCESS  read-only
		STATUS  mandatory
		DESCRIPTION
		"Reflects the sub-band DFS state."
		::= { winlink1000OduAirComboSubBandEntry 19 }

	winlink1000OduAirComboSubBandChannelBW80AdminState OBJECT-TYPE
		SYNTAX	DisplayString
		ACCESS  read-only
		STATUS  mandatory
		DESCRIPTION
		"Reflects the CBW 80MHz admin state vector."
		::= { winlink1000OduAirComboSubBandEntry 20 }
		
	winlink1000OduAirComboSubBandChannelBW7AdminState OBJECT-TYPE
		SYNTAX	DisplayString
		ACCESS  read-only
		STATUS  mandatory
		DESCRIPTION
		"Reflects the CBW 7MHz admin state vector."
		::= { winlink1000OduAirComboSubBandEntry 21 }
		
	winlink1000OduAirComboSubBandChannelBW14AdminState OBJECT-TYPE
		SYNTAX	DisplayString
		ACCESS  read-only
		STATUS  mandatory
		DESCRIPTION
		"Reflects the CBW 80MHz admin state vector."
		::= { winlink1000OduAirComboSubBandEntry 22 }
		
	winlink1000OduAirComboNumberOfSubBands OBJECT-TYPE
		SYNTAX  INTEGER
		ACCESS  read-only
		STATUS  mandatory
		DESCRIPTION
		"Represents the number of Multi-band sub bands."
		::= { winlink1000OduAirCombo 2 }

	winlink1000OduAirComboSwitchSubBand OBJECT-TYPE
		SYNTAX  DisplayString
		ACCESS  read-write
		STATUS  mandatory
		DESCRIPTION
		"Switch sub band operation with a given sub band ID. 
		The get operation retrieves the current sub band ID."
		::= { winlink1000OduAirCombo 3 }
		
	winlink1000OduAirComboCurrentSubBandDesc OBJECT-TYPE
		SYNTAX  DisplayString
		ACCESS  read-only
		STATUS  mandatory
		DESCRIPTION
		"Current Sub Band description."
		::= { winlink1000OduAirCombo 4 }		

	winlink1000OduAirComboCurrentFrequencyBandID OBJECT-TYPE
		SYNTAX  INTEGER
		ACCESS  read-only
		STATUS  mandatory
		DESCRIPTION
		"Current Frequency Band Id Number."
		::= { winlink1000OduAirCombo 5 }	
		
	-- ###########################################################
	--                      Video Surveillance
	-- ###########################################################
			
	winlink1000OduAirInternalMaxRate OBJECT-TYPE
		SYNTAX  INTEGER
		ACCESS  read-only
		STATUS  mandatory
		DESCRIPTION
		"Max Ethernet throughput of the site (in Kpbs)."
		::= { winlink1000OduAir 54 }

	winlink1000OduAirCapacityDirection OBJECT-TYPE
		SYNTAX  INTEGER {
			undefined (1),
			low (2), 
			high(3)
		}
		ACCESS  read-write
		STATUS  mandatory
		DESCRIPTION
		"Capacity direction of the site."
		::= { winlink1000OduAir 55 }

	-- ###########################################################
	--                      Spectrum Analysis
	-- ###########################################################
	
	winlink1000OduAirSpectrumAnalysis OBJECT IDENTIFIER ::= { winlink1000OduAir 56 }
	
	winlink1000OduAirSpectrumAnalysisOperState OBJECT-TYPE
		SYNTAX  INTEGER {
			notSupported (1),
			stopSpectrumAnalysis (2),
			startSpectrumAnalysis (3),
			restartSpectrumAnalysis (4)
		}
		ACCESS  read-write
		STATUS  mandatory
		DESCRIPTION
		"Spectrum Analysis operation state.
		 The configurable values are Spectrum Analysis Stop, Start and Restart.
		 Not Supported value indicates that the feature is not supported on the device.
		 Not Supported is not a configurable state."
		::= { winlink1000OduAirSpectrumAnalysis 1 }	

	winlink1000OduAirRxPowerAntennaA OBJECT-TYPE
		SYNTAX  INTEGER
		ACCESS  read-only
		STATUS  mandatory
		DESCRIPTION
		"Received Signal Strength in dBm of Antenna A."
		::= { winlink1000OduAirSpectrumAnalysis 2 }
		
	winlink1000OduAirRxPowerAntennaB OBJECT-TYPE
		SYNTAX  INTEGER
		ACCESS  read-only
		STATUS  mandatory
		DESCRIPTION
		"Received Signal Strength in dBm of Antenna B."
		::= { winlink1000OduAirSpectrumAnalysis 3 }
		
	winlink1000OduAirNumberOfSpectrumChannels OBJECT-TYPE
		SYNTAX  INTEGER
		ACCESS  read-only
		STATUS  mandatory
		DESCRIPTION
		"Represents the number of Spectrum Channels."
		::= { winlink1000OduAirSpectrumAnalysis 4 }
		
		
	-- ###########################################################
	--                      Spectrum Channel Table
	-- ###########################################################
	
	winlink1000OduAirSpectrumChannelTable OBJECT-TYPE
		SYNTAX  SEQUENCE OF Winlink1000OduAirSpectrumChannelTableEntry
		ACCESS  not-accessible
		STATUS  mandatory
		DESCRIPTION
		"ODU Spectrum Analysis Channel Table."
		::= { winlink1000OduAirSpectrumAnalysis 5 }
		
	winlink1000OduAirSpectrumChannelTableEntry OBJECT-TYPE
		SYNTAX  Winlink1000OduAirSpectrumChannelTableEntry
		ACCESS  not-accessible
		STATUS  mandatory
		DESCRIPTION
		"ODU Spectrum Analysis Channel Table entry."
		INDEX { winlink1000OduAirSpectrumChannelIndex }
		::= { winlink1000OduAirSpectrumChannelTable 1 }

	Winlink1000OduAirSpectrumChannelTableEntry ::= SEQUENCE {
		winlink1000OduAirSpectrumChannelIndex
			INTEGER,
		winlink1000OduAirSpectrumChannelFrequency
			INTEGER,
		winlink1000OduAirSpectrumChannelScanned
			INTEGER,
		winlink1000OduAirSpectrumChannelScanningTimestamp
			TimeTicks,
		winlink1000OduAirSpectrumChannelLastNFAntennaA
			INTEGER,
		winlink1000OduAirSpectrumChannelLastNFAntennaB
			INTEGER,
		winlink1000OduAirSpectrumChannelAverageNFAntennaA
			INTEGER,
		winlink1000OduAirSpectrumChannelAverageNFAntennaB
			INTEGER,
		winlink1000OduAirSpectrumChannelMaxNFAntennaA
			INTEGER,
		winlink1000OduAirSpectrumChannelMaxNFAntennaB
			INTEGER,
		winlink1000OduAirSpectrumChannelCACPerformed
			INTEGER,
		winlink1000OduAirSpectrumChannelLastCACTimestamp
			TimeTicks,
		winlink1000OduAirSpectrumChannelRadarDetected
			INTEGER,
		winlink1000OduAirSpectrumChannelRadarDetectionTimestamp
			TimeTicks,
		winlink1000OduAirSpectrumChannelAvailable
			INTEGER,
		winlink1000OduAirSpectrumChannelMaxBeaconRss
			INTEGER,
		winlink1000OduAirSpectrumChannelCompressed
			OCTET STRING		
		}
		
	winlink1000OduAirSpectrumChannelIndex OBJECT-TYPE
		SYNTAX  INTEGER (1..1000000)
		ACCESS  read-only
		STATUS  mandatory
		DESCRIPTION
		"ODU Spectrum Channel index."
		::= { winlink1000OduAirSpectrumChannelTableEntry 1 }

	winlink1000OduAirSpectrumChannelFrequency OBJECT-TYPE
		SYNTAX  INTEGER
		ACCESS  read-only
		STATUS  mandatory
		DESCRIPTION
		"ODU Spectrum Channel frequency in MHz."
		::= { winlink1000OduAirSpectrumChannelTableEntry 2 }	

	winlink1000OduAirSpectrumChannelScanned OBJECT-TYPE
		SYNTAX  INTEGER {notScanned (1),
						 scanned (2)}
		ACCESS  read-only
		STATUS  mandatory
		DESCRIPTION
		"An indication of the vaildity of the channel's data.
		 If the channel was scanned the data is valid, else not."
		::= { winlink1000OduAirSpectrumChannelTableEntry 3 }

	winlink1000OduAirSpectrumChannelScanningTimestamp OBJECT-TYPE
		SYNTAX  TimeTicks
		ACCESS  read-only
		STATUS  mandatory
		DESCRIPTION
		"Channel last scan timestamp, in hundredths of a second, since device up time.
		 If the channel was not scanned than the return value will be 0."
		::= { winlink1000OduAirSpectrumChannelTableEntry 4 }

	winlink1000OduAirSpectrumChannelLastNFAntennaA OBJECT-TYPE
		SYNTAX  INTEGER
		ACCESS  read-only
		STATUS  mandatory
		DESCRIPTION
		"Normalized Noise Floor value in dBm - of Antenna A - (including 2 neighbor frequencies)."
		::= { winlink1000OduAirSpectrumChannelTableEntry 5 }

	winlink1000OduAirSpectrumChannelLastNFAntennaB OBJECT-TYPE
		SYNTAX  INTEGER
		ACCESS  read-only
		STATUS  mandatory
		DESCRIPTION
		"Normalized Noise Floor value in dBm - of Antenna B - (including 2 neighbor frequencies)."
		::= { winlink1000OduAirSpectrumChannelTableEntry 6 }

	winlink1000OduAirSpectrumChannelAverageNFAntennaA OBJECT-TYPE
		SYNTAX  INTEGER
		ACCESS  read-only
		STATUS  mandatory
		DESCRIPTION
		"Average normalized Noise Floor value in dBm - of Antenna A -  over all dwells."
		::= { winlink1000OduAirSpectrumChannelTableEntry 7 }
	
	winlink1000OduAirSpectrumChannelAverageNFAntennaB OBJECT-TYPE
		SYNTAX  INTEGER
		ACCESS  read-only
		STATUS  mandatory
		DESCRIPTION
		"Average normalized Noise Floor value in dBm - of Antenna B -  over all dwells."
		::= { winlink1000OduAirSpectrumChannelTableEntry 8 }

	winlink1000OduAirSpectrumChannelMaxNFAntennaA OBJECT-TYPE
		SYNTAX  INTEGER
		ACCESS  read-only
		STATUS  mandatory
		DESCRIPTION
		"Max normalized Noise Floor value in dBm - of Antenna A -  over all dwells."
		::= { winlink1000OduAirSpectrumChannelTableEntry 9 }
		
	winlink1000OduAirSpectrumChannelMaxNFAntennaB OBJECT-TYPE
		SYNTAX  INTEGER
		ACCESS  read-only
		STATUS  mandatory
		DESCRIPTION
		"Max normalized Noise Floor value in dBm - of Antenna B -  over all dwells."
		::= { winlink1000OduAirSpectrumChannelTableEntry 10 }
		
	winlink1000OduAirSpectrumChannelCACPerformed OBJECT-TYPE
		SYNTAX  INTEGER {notPerformed (1),
						 performed (2)}
		ACCESS  read-only
		STATUS  mandatory
		DESCRIPTION
		"Was CAC performed on the channel."
		::= { winlink1000OduAirSpectrumChannelTableEntry 11 }
		
	winlink1000OduAirSpectrumChannelLastCACTimestamp OBJECT-TYPE
		SYNTAX  TimeTicks
		ACCESS  read-only
		STATUS  mandatory
		DESCRIPTION
		"Last CAC performed timestamp, in hundredths of a second, since device up time.
		 If no CAC has performed on the channel, the return value will be 0."
		::= { winlink1000OduAirSpectrumChannelTableEntry 12 }
						
	winlink1000OduAirSpectrumChannelRadarDetected OBJECT-TYPE
		SYNTAX  INTEGER {notDetected (1),
						 detected (2)}
		ACCESS  read-only
		STATUS  mandatory
		DESCRIPTION
		"Was Radar detected on the channel."
		::= { winlink1000OduAirSpectrumChannelTableEntry 13 }
		
	winlink1000OduAirSpectrumChannelRadarDetectionTimestamp OBJECT-TYPE
		SYNTAX  TimeTicks
		ACCESS  read-only
		STATUS  mandatory
		DESCRIPTION
		"Last Radar Detection timestamp, in hundredths of a second, since device up time.
		 If no Radar has detected on the channel, the return value will be 0."
		::= { winlink1000OduAirSpectrumChannelTableEntry 14 }
	
	winlink1000OduAirSpectrumChannelAvailable OBJECT-TYPE
		SYNTAX  INTEGER {notAvailable (1),
						 available (2)}
		ACCESS  read-only
		STATUS  mandatory
		DESCRIPTION
		"Is the channel available for use."
		::= { winlink1000OduAirSpectrumChannelTableEntry 15 }	

	winlink1000OduAirSpectrumChannelMaxBeaconRss OBJECT-TYPE
		SYNTAX  INTEGER
		ACCESS  read-only
		STATUS  mandatory
		DESCRIPTION
		"The max RSS value of a received beacon on the specific channel in dBm."
		::= { winlink1000OduAirSpectrumChannelTableEntry 16 }

	winlink1000OduAirSpectrumChannelCompressed OBJECT-TYPE
		SYNTAX	OCTET STRING
		ACCESS  read-only
		STATUS  mandatory
		DESCRIPTION
		"Compress all the Spectrum data per channel into one variable.
		Frequency (4 bytes)
		Scanned (1 byte)
		Timestamp (4 bytes)
		Last NF Antenna A (1 byte)
		Last NF Antenna B (1 byte)
		Avg NF Antenna A (1 byte)
		Avg NF Antenna B (1 byte)
		Max NF Antenna A (1 byte)
		Max NF Antenna B (1 byte)
		CAC Performed (1 byte)
		Last CAC Timestamp (4 bytes)
		Radar Detected (1 byte)
		Radar Detected Timestamp (4 bytes)
		Channel Available (1 byte)
		Max Beacon RSS (1 byte)."
		::= { winlink1000OduAirSpectrumChannelTableEntry 17 }
	
	winlink1000OduAirChipMinMaxFreq OBJECT-TYPE
		SYNTAX  DisplayString
		ACCESS  read-only
		STATUS  mandatory
		DESCRIPTION
		"The minimum and maximum frequencies in MHz which the chip supports."
		::= { winlink1000OduAirSpectrumAnalysis 6 }	

	winlink1000OduAirSpectrumAnalysisTimeout OBJECT-TYPE
		SYNTAX  INTEGER
		ACCESS  read-write
		STATUS  mandatory
		DESCRIPTION
		"Spectrum analysis timeout in seconds."
		::= { winlink1000OduAirSpectrumAnalysis 7 }
		
	winlink1000OduAirAntConfAndRatesStatus OBJECT-TYPE
		SYNTAX  INTEGER {
			srsr(1),
			drdr(2),
			drsr(3)
		}
		ACCESS  read-only
		STATUS  mandatory
		DESCRIPTION
		"Description: Antenna configuration and Rates status (1 = Single antenna with single data 	stream, 2 = Dual antenna with single data stream, 3 = Dual antenna with dual data 	stream)."
		::= { winlink1000OduAir 57 }

	winlink1000OduAirDualAntTxMode OBJECT-TYPE
		SYNTAX  INTEGER {
			mimo(1),
			diversity(2)
		}
		ACCESS  read-write
		STATUS  mandatory
		DESCRIPTION
		"Description: Transmission type when using Dual radios (MIMO or AdvancedDiversity using  one stream of data)."
		::= { winlink1000OduAir 58 }		
				
	winlink1000OduAirTxOperationMode OBJECT-TYPE
		SYNTAX  INTEGER {
			regularMode(1),
			measurementMode (2)

		}
		ACCESS  read-write
		STATUS  mandatory
		DESCRIPTION
		"This parameter controls the Operation mode of frames sent over the air. 
		The Operation mode is either normal (1) for regular transmission where frame size is determined by the traffic or throughput test (2) when the user requests an actual over the air throughput estimation using full frames. 
		The latter lasts no more than a predetermined interval (default 30 sec)."
		::= { winlink1000OduAir 59 }		
				
				
	winlink1000OduAirAsymmetricTdd OBJECT IDENTIFIER ::= { winlink1000OduAir 60 }

	-- ###########################################################
	--                      A-Symmetric Table
	-- ###########################################################	
	
	winlink1000OduAirDesiredNetMasterTxRatio OBJECT-TYPE
		SYNTAX  INTEGER(0..1000)
		ACCESS  read-write
		STATUS  mandatory
		DESCRIPTION
		"This parameter is reserved to the element manager provided with the product."
		::= { winlink1000OduAirAsymmetricTdd 1 }

	winlink1000OduAirCurrentNetMasterTxRatio OBJECT-TYPE
		SYNTAX  INTEGER
		ACCESS  read-only
		STATUS  mandatory
		DESCRIPTION
		"Represents the actual Net Master Tx RAtio."
		::= { winlink1000OduAirAsymmetricTdd 2 }

	winlink1000OduAirMinUsableMasterTxRatio OBJECT-TYPE
		SYNTAX  INTEGER
		ACCESS  read-only
		STATUS  mandatory
		DESCRIPTION
		"Represents the minimal value the user can configure for Desired net mAster Tx Ratio."
		::= { winlink1000OduAirAsymmetricTdd 3 }

	winlink1000OduAirMaxUsableMasterTxRatio OBJECT-TYPE
		SYNTAX  INTEGER
		ACCESS  read-only
		STATUS  mandatory
		DESCRIPTION
		"Represents the maximal value the user can configure for Desired net mAster Tx Ratio."
		::= { winlink1000OduAirAsymmetricTdd 4 }

	winlink1000OduAirAccumulatedUAS OBJECT-TYPE
		SYNTAX  INTEGER
		ACCESS  read-only
		STATUS  mandatory
		DESCRIPTION
		"Accumulates the Unavailable seconds of the Air Interface. Relevant for point to point systems."
		::= { winlink1000OduAir 61 }
		
	winlink1000OduAirDistStr OBJECT-TYPE
		SYNTAX  DisplayString
		ACCESS  read-only
		STATUS  mandatory
		DESCRIPTION
		" Possibilities of the link according to RFP and CBW "
		::= { winlink1000OduAir  62}
	
	winlink1000OduAirChannelsDefaultFreqStr OBJECT-TYPE
		SYNTAX  DisplayString
		ACCESS  read-only
		STATUS  mandatory
		DESCRIPTION
		"A string representing the channels available. 
		Each character represents one frequency, when '1' means its available, and '0' means its not."
		::= { winlink1000OduAir 63 }		

	winlink1000OduAirAntConnectionType OBJECT-TYPE
		SYNTAX  INTEGER {
			external(1),
			integrated(2),
			embeddedExternal(3),
			embeddedIntegrated(4),
			integratedBSA(5)
			}
		ACCESS  read-write
		STATUS  mandatory
		DESCRIPTION
		"Antenna connection type (External(1), Integrated(2), Embedded_External(3), Embedded_Integrated(4), Integrated_BSA(5))."
		::= { winlink1000OduAir 64 }
		
	winlink1000OduAirAllowableChannelsStr OBJECT-TYPE
		SYNTAX  DisplayString
		ACCESS  read-write
		STATUS  mandatory
		DESCRIPTION
		"A string representing the allowable channels. 
		Each character represents one channel, when '1' means its available, and '0' means its not."
		::= { winlink1000OduAir 65 }
		
	winlink1000OduAirDfs OBJECT IDENTIFIER ::= { winlink1000OduAir 66 }
		
	winlink1000OduAirDfsAlgorithmTypeState OBJECT-TYPE
		SYNTAX  INTEGER
		ACCESS  read-write
		STATUS  mandatory
		DESCRIPTION
		"Bitmap for state of Radar Algorithm Type. Filters by bit's position:  
		0 = Zero PW,
		1 = Fixed,
		2 = Variable,
		3 = Staggered,
		4 = Long."
		::= { winlink1000OduAirDfs 1 }
		
	-- ###########################################################
	--                 Dfs Last Detected Radars Table
	-- ###########################################################
	winlink1000OduAirDfsLastDetectedTbl OBJECT-TYPE
		SYNTAX  SEQUENCE OF Winlink1000OduAirDfsLastDetectedEntry
		ACCESS  not-accessible
		STATUS  mandatory
		DESCRIPTION
		"Last detected radars table."
		::= { winlink1000OduAirDfs 2 }

	winlink1000OduAirDfsLastDetectedEntry OBJECT-TYPE
		SYNTAX  Winlink1000OduAirDfsLastDetectedEntry
		ACCESS  not-accessible
		STATUS  mandatory
		DESCRIPTION
		"ODU Multi-band Sub Bands Table entry."
		INDEX { winlink1000OduAirDfsLastDetectedIndex }
		::= { winlink1000OduAirDfsLastDetectedTbl 1 }

	Winlink1000OduAirDfsLastDetectedEntry ::= SEQUENCE {
		winlink1000OduAirDfsLastDetectedIndex
			INTEGER,
		winlink1000OduAirDfsLastDetectedTime
			TimeTicks,
		winlink1000OduAirDfsLastDetectedAlgorithmType
			INTEGER,
		winlink1000OduAirDfsLastDetectedFrequency
			INTEGER
		}
		
	winlink1000OduAirDfsLastDetectedIndex OBJECT-TYPE
		SYNTAX  INTEGER
		ACCESS  read-only
		STATUS  mandatory
		DESCRIPTION
		"Dfs Last Detected Radars Table Index."
		::= { winlink1000OduAirDfsLastDetectedEntry 1 }
		
	winlink1000OduAirDfsLastDetectedTime OBJECT-TYPE
		SYNTAX  TimeTicks
		ACCESS  read-only
		STATUS  mandatory
		DESCRIPTION
		"Dfs time of the last detected radar."
		::= { winlink1000OduAirDfsLastDetectedEntry 2 }
		
	winlink1000OduAirDfsLastDetectedAlgorithmType OBJECT-TYPE
		SYNTAX  INTEGER
		ACCESS  read-only
		STATUS  mandatory
		DESCRIPTION
		"Dfs type of the last detected radar."
		::= { winlink1000OduAirDfsLastDetectedEntry 3 }
		
	winlink1000OduAirDfsLastDetectedFrequency OBJECT-TYPE
		SYNTAX  INTEGER
		ACCESS  read-only
		STATUS  mandatory
		DESCRIPTION
		"Dfs frequency of the last detected radar."
		::= { winlink1000OduAirDfsLastDetectedEntry 4 }

	winlink1000OduAirPreferredChannelsStr OBJECT-TYPE
		SYNTAX  DisplayString
		ACCESS  read-write
		STATUS  mandatory
		DESCRIPTION
		"A string representing the preferred channels. 
		Each character represents one channel, when '1' means its preferred, and '0' means its not."
		::= { winlink1000OduAir 67 }
		
	winlink1000OduAirSyncLossThreshold OBJECT-TYPE
		SYNTAX  INTEGER
		ACCESS  read-write
		STATUS  mandatory
		DESCRIPTION
		"When the current throughput is below this threshold (in Kbps), sync loss will occur."
		::= { winlink1000OduAir 68 }
	
	winlink1000OduAirGeoLocation OBJECT-TYPE
		SYNTAX  DisplayString
		ACCESS  read-write
		STATUS  mandatory
		DESCRIPTION
		"Geographic device location in format: 	latitude,longitude."
		::= { winlink1000OduAir 69 }

	winlink1000OduAirAggregateCapacity OBJECT-TYPE
		SYNTAX  INTEGER
		ACCESS  read-only
		STATUS  mandatory
		DESCRIPTION
		"Aggregate Capacity of the ODU in Mbps."
		::= { winlink1000OduAir 70 }
		
	winlink1000OduAirALPM OBJECT IDENTIFIER ::= { winlink1000OduAir 71 }
		
	winlink1000OduAirALPMDataBufferStr OBJECT-TYPE
		SYNTAX  OCTET STRING
		ACCESS  read-write
		STATUS  mandatory
		DESCRIPTION
		"A string that holds all of the ALPM events data"
		::= { winlink1000OduAirALPM 1 }
	
	winlink1000OduAirCurrentManualAngle OBJECT-TYPE
		SYNTAX  INTEGER
		ACCESS  read-only
		STATUS  mandatory
		DESCRIPTION
		"Absolute (manual) angle (Deg.) of the unit."
		::= { winlink1000OduAir 72 }

	winlink1000OduAirCurrentManualElevAngle OBJECT-TYPE
		SYNTAX  INTEGER
		ACCESS  read-only
		STATUS  mandatory
		DESCRIPTION
		"Absolute Elevation angle (Deg.) of the unit."
		::= { winlink1000OduAir 73 }

	winlink1000OduAirAntennaTemperatureC  OBJECT-TYPE
		SYNTAX  INTEGER
		ACCESS  read-only
		STATUS  mandatory
		DESCRIPTION
		"Antenna Temperature (C)"
		::= { winlink1000OduAir 74 }
		
	winlink1000OduAirGPSAntennaType OBJECT-TYPE
		SYNTAX  INTEGER {
			configurableIntegrated(1),
			configurableExternal(2),
			integrated(3),
			external(4),
			none(5)
			}
		ACCESS  read-write
		STATUS  mandatory
		DESCRIPTION
		"GPS Antenna type."
		::= { winlink1000OduAir 75 }
		
	-- ###########################################################
	--                      ODU Perf Monitor
	-- ###########################################################

	winlink1000OduPerfMon OBJECT IDENTIFIER ::= { winlink1000Odu 6 }

	-- ###########################################################
	--                      PM Current Table
	-- ###########################################################

	winlink1000OduPerfMonCurrTable OBJECT-TYPE
		SYNTAX  SEQUENCE OF Winlink1000OduPerfMonCurrEntry
		ACCESS  not-accessible
		STATUS  mandatory
		DESCRIPTION
		"This table defines/keeps the counters of the current 15 min interval."
		::= { winlink1000OduPerfMon 1 }

	winlink1000OduPerfMonCurrEntry OBJECT-TYPE
		SYNTAX  Winlink1000OduPerfMonCurrEntry
		ACCESS  not-accessible
		STATUS  mandatory
		DESCRIPTION
		"This is an entry in the Current Interval Table."
		INDEX {ifIndex }
		::= { winlink1000OduPerfMonCurrTable 1 }

	Winlink1000OduPerfMonCurrEntry ::= SEQUENCE {
		winlink1000OduPerfMonCurrUAS
	      Gauge,
   		winlink1000OduPerfMonCurrES
	      Gauge,
		winlink1000OduPerfMonCurrSES
	      Gauge,
		winlink1000OduPerfMonCurrBBE
	      Gauge,
		winlink1000OduPerfMonCurrIntegrity
	      INTEGER,
		winlink1000OduPerfMonCurrCompressed
	      OCTET STRING
	}

	winlink1000OduPerfMonCurrUAS OBJECT-TYPE
		SYNTAX  Gauge (0..900)
		ACCESS  read-only
		STATUS  mandatory
		DESCRIPTION
		" The current number of Unavailable Seconds starting from the present 15 minutes period."
		::= { winlink1000OduPerfMonCurrEntry 1 }

	winlink1000OduPerfMonCurrES OBJECT-TYPE
		SYNTAX  Gauge (0..900)
		ACCESS  read-only
		STATUS  mandatory
		DESCRIPTION
		"Current number of Errored Seconds starting from the present 15 minutes period."
		::= { winlink1000OduPerfMonCurrEntry 2 }

	winlink1000OduPerfMonCurrSES OBJECT-TYPE
		SYNTAX  Gauge (0..900)
		ACCESS  read-only
		STATUS  mandatory
		DESCRIPTION
		"Current number of Severely Errored Seconds starting from the present 15 minutes period."
		::= { winlink1000OduPerfMonCurrEntry 3 }

	winlink1000OduPerfMonCurrBBE OBJECT-TYPE
		SYNTAX  Gauge (0..1800000)
		ACCESS  read-only
		STATUS  mandatory
		DESCRIPTION
		"Current number of Background Block Errors starting from the present 15 minutes period."
		::= { winlink1000OduPerfMonCurrEntry 4 }

	winlink1000OduPerfMonCurrIntegrity OBJECT-TYPE
		SYNTAX  INTEGER {
			true(1),
			false(2)
			}
		ACCESS  read-only
		STATUS  mandatory
		DESCRIPTION
		"Indicates the integrity of the entry."
		::= { winlink1000OduPerfMonCurrEntry 5 }
		
	winlink1000OduPerfMonCurrCompressed OBJECT-TYPE
		SYNTAX  OCTET STRING
		ACCESS  read-only
		STATUS  mandatory
		DESCRIPTION
		"Holds a compressed string of all data per interface.
		
		Compressed Air Interface Structure (size in brackets):
			UAS (4), ES (4), SES (4), BBE (4), Integrity (1), 
			MinRSL (1), MaxRSL (1), RSLThresh1Exceeded (4), 
			RSLThresh2Exceeded (4), MinTSL (1), MaxTSL (1),
			TSLThresh1Exceed (4), BBERThresh1Exceed (4), RxMBytes (4)
			TxMBytes (4), EthCapacityThreshUnder (4), HighTrafficThreshExceed (4)
			
		Compressed Etherent ODU	interface (size in brackets):
			UAS (4), ES (4), SES (4), BBE (4), Integrity (1), 
			RxMBytes (4), TxMBytes (4), EthCapacityThreshUnder (4), 
			HighTrafficThreshExceed (4), ActiveSeconds (4)
		"
		::= { winlink1000OduPerfMonCurrEntry 6}
		
	-- ###########################################################
	--                      PM Interval Table
	-- ###########################################################	

	winlink1000OduPerfMonIntervalTable OBJECT-TYPE
		SYNTAX  SEQUENCE OF Winlink1000OduPerfMonIntervalEntry
		ACCESS  not-accessible
		STATUS  mandatory
		DESCRIPTION
		"This table defines/keeps the counters of the last day (in resolution of 15 min intervals)."
		::= { winlink1000OduPerfMon 2 }

	winlink1000OduPerfMonIntervalEntry OBJECT-TYPE
		SYNTAX  Winlink1000OduPerfMonIntervalEntry
		ACCESS  not-accessible
		STATUS  mandatory
		DESCRIPTION
		"This is an entry in the Interval Table."
		INDEX {ifIndex, winlink1000OduPerfMonIntervalIdx }
		::= { winlink1000OduPerfMonIntervalTable 1 }

	Winlink1000OduPerfMonIntervalEntry ::= SEQUENCE {
		winlink1000OduPerfMonIntervalIdx
	      INTEGER,
		winlink1000OduPerfMonIntervalUAS
	      Gauge,
   		winlink1000OduPerfMonIntervalES
	      Gauge,
		winlink1000OduPerfMonIntervalSES
	      Gauge,
		winlink1000OduPerfMonIntervalBBE
	      Gauge,
		winlink1000OduPerfMonIntervalIntegrity
	      INTEGER,
		winlink1000OduPerfMonIntervalCompressed
	      OCTET STRING		  		
	}

	winlink1000OduPerfMonIntervalIdx OBJECT-TYPE
		SYNTAX  INTEGER (1..96)
		ACCESS  read-only
		STATUS  mandatory
		DESCRIPTION
		"This table is indexed per interval number. Each interval
		is of 15 minutes and the oldest is 96."
	::= { winlink1000OduPerfMonIntervalEntry 1 }

	winlink1000OduPerfMonIntervalUAS OBJECT-TYPE
		SYNTAX  Gauge (0..900)
		ACCESS  read-only
		STATUS  mandatory
		DESCRIPTION
		" The current number of Unavailable Seconds per interval."
		::= { winlink1000OduPerfMonIntervalEntry 2 }

	winlink1000OduPerfMonIntervalES OBJECT-TYPE
		SYNTAX  Gauge (0..900)
		ACCESS  read-only
		STATUS  mandatory
		DESCRIPTION
		"Current number of Errored Seconds per interval."
		::= { winlink1000OduPerfMonIntervalEntry 3 }

	winlink1000OduPerfMonIntervalSES OBJECT-TYPE
		SYNTAX  Gauge (0..900)
		ACCESS  read-only
		STATUS  mandatory
		DESCRIPTION
		"Current number of Severely Errored Seconds per interval."
		::= { winlink1000OduPerfMonIntervalEntry 4 }

	winlink1000OduPerfMonIntervalBBE OBJECT-TYPE
		SYNTAX  Gauge (0..1800000)
		ACCESS  read-only
		STATUS  mandatory
		DESCRIPTION
		"Current number of Background Block Errors per interval."
		::= { winlink1000OduPerfMonIntervalEntry 5 }

	winlink1000OduPerfMonIntervalIntegrity OBJECT-TYPE
		SYNTAX  INTEGER {
			true(1),
			false(2)
			}
		ACCESS  read-only
		STATUS  mandatory
		DESCRIPTION
		"Indicates the integrity of the entry per interval."
		::= { winlink1000OduPerfMonIntervalEntry 6 }

	winlink1000OduPerfMonIntervalCompressed OBJECT-TYPE
		SYNTAX  OCTET STRING
		ACCESS  read-only
		STATUS  mandatory
		DESCRIPTION
		"Holds a compressed string of all data per interface.
		
		Compressed Air Interface Structure (size in brackets):
			UAS (4), ES (4), SES (4), BBE (4), Integrity (1), 
			MinRSL (1), MaxRSL (1), RSLThresh1Exceeded (4), 
			RSLThresh2Exceeded (4), MinTSL (1), MaxTSL (1),
			TSLThresh1Exceed (4), BBERThresh1Exceed (4), RxMBytes (4)
			TxMBytes (4), EthCapacityThreshUnder (4), HighTrafficThreshExceed (4)
			
		Compressed Etherent ODU	interface (size in brackets):
			UAS (4), ES (4), SES (4), BBE (4), Integrity (1), 
			RxMBytes (4), TxMBytes (4), EthCapacityThreshUnder (4), 
			HighTrafficThreshExceed (4), ActiveSeconds (1)
		"
		::= { winlink1000OduPerfMonIntervalEntry 7}

	-- ###########################################################
	--                      PM Day Table
	-- ###########################################################	

	winlink1000OduPerfMonDayTable OBJECT-TYPE
		SYNTAX  SEQUENCE OF Winlink1000OduPerfMonDayEntry
		ACCESS  not-accessible
		STATUS  mandatory
		DESCRIPTION
		"This table defines/keeps the counters of the last month (in resolution of days)."
		::= { winlink1000OduPerfMon 3 }

	winlink1000OduPerfMonDayEntry OBJECT-TYPE
		SYNTAX  Winlink1000OduPerfMonDayEntry
		ACCESS  not-accessible
		STATUS  mandatory
		DESCRIPTION
		"This is an entry in the Days Table."
		INDEX {ifIndex, winlink1000OduPerfMonDayIdx }
		::= { winlink1000OduPerfMonDayTable 1 }

	Winlink1000OduPerfMonDayEntry ::= SEQUENCE {
		winlink1000OduPerfMonDayIdx
	      INTEGER,
		winlink1000OduPerfMonDayUAS
	      Gauge,
   		winlink1000OduPerfMonDayES
	      Gauge,
		winlink1000OduPerfMonDaySES
	      Gauge,
		winlink1000OduPerfMonDayBBE
	      Gauge,
		winlink1000OduPerfMonDayIntegrity
	      INTEGER,
		winlink1000OduPerfMonDayCompressed
	      OCTET STRING		  		  		
	}

	winlink1000OduPerfMonDayIdx OBJECT-TYPE
		SYNTAX  INTEGER (1..30)
		ACCESS  read-only
		STATUS  mandatory
		DESCRIPTION
		"This table is indexed per interval number. Each interval
		is of 24 hours and the oldest is 30."
	::= { winlink1000OduPerfMonDayEntry 1 }

	winlink1000OduPerfMonDayUAS OBJECT-TYPE
		SYNTAX  Gauge (0..86400)
		ACCESS  read-only
		STATUS  mandatory
		DESCRIPTION
		"The current number of Unavailable Seconds per interval of 24 hours."
		::= { winlink1000OduPerfMonDayEntry 2 }

	winlink1000OduPerfMonDayES OBJECT-TYPE
		SYNTAX  Gauge (0..86400)
		ACCESS  read-only
		STATUS  mandatory
		DESCRIPTION
		"Current number of Errored Seconds per interval of 24 hours."
		::= { winlink1000OduPerfMonDayEntry 3 }

	winlink1000OduPerfMonDaySES OBJECT-TYPE
		SYNTAX  Gauge (0..86400)
		ACCESS  read-only
		STATUS  mandatory
		DESCRIPTION
		"Current number of Severely Errored Seconds per interval of 24 hours."
		::= { winlink1000OduPerfMonDayEntry 4 }

	winlink1000OduPerfMonDayBBE OBJECT-TYPE
		SYNTAX  Gauge (0..172800000)
		ACCESS  read-only
		STATUS  mandatory
		DESCRIPTION
		"Current number of Background Block Errors per interval of 24 hours."
		::= { winlink1000OduPerfMonDayEntry 5 }

	winlink1000OduPerfMonDayIntegrity OBJECT-TYPE
		SYNTAX  INTEGER {
			true(1),
			false(2)
			}
		ACCESS  read-only
		STATUS  mandatory
		DESCRIPTION
		"Indicates the integrity of the entry per interval of 24 hours."
		::= { winlink1000OduPerfMonDayEntry 6 }

	winlink1000OduPerfMonDayCompressed OBJECT-TYPE
		SYNTAX  OCTET STRING
		ACCESS  read-only
		STATUS  mandatory
		DESCRIPTION
		"Holds a compressed string of all data per interface.
		
		Compressed Air Interface Structure (size in brackets):
			UAS (4), ES (4), SES (4), BBE (4), Integrity (1), 
			MinRSL (1), MaxRSL (1), RSLThresh1Exceeded (4), 
			RSLThresh2Exceeded (4), MinTSL (1), MaxTSL (1),
			TSLThresh1Exceed (4), BBERThresh1Exceed (4), RxMBytes (4)
			TxMBytes (4), EthCapacityThreshUnder (4), HighTrafficThreshExceed (4)
			
		Compressed Etherent ODU	interface (size in brackets):
			UAS (4), ES (4), SES (4), BBE (4), Integrity (1), 
			RxMBytes (4), TxMBytes (4), EthCapacityThreshUnder (4), 
			HighTrafficThreshExceed (4), ActiveSeconds (1)
		"
		::= { winlink1000OduPerfMonDayEntry 7}

	-- ###########################################################
	--                      PM Air Current Table
	-- ###########################################################

	winlink1000OduPerfMonAirCurrTable OBJECT-TYPE
		SYNTAX  SEQUENCE OF Winlink1000OduPerfMonAirCurrEntry
		ACCESS  not-accessible
		STATUS  mandatory
		DESCRIPTION
		"This table defines/keeps the air counters of the current 15 min interval."
		::= { winlink1000OduPerfMon 4 }

	winlink1000OduPerfMonAirCurrEntry OBJECT-TYPE
		SYNTAX  Winlink1000OduPerfMonAirCurrEntry
		ACCESS  not-accessible
		STATUS  mandatory
		DESCRIPTION
		"This is an entry in the Current Interval Table."
		INDEX {ifIndex }
		::= { winlink1000OduPerfMonAirCurrTable 1 }

	Winlink1000OduPerfMonAirCurrEntry ::= SEQUENCE {
		winlink1000OduPerfMonAirCurrMinRSL
	      INTEGER,
   		winlink1000OduPerfMonAirCurrMaxRSL
	      INTEGER,
		winlink1000OduPerfMonAirCurrRSLThresh1Exceed
	      Gauge,
		winlink1000OduPerfMonAirCurrRSLThresh2Exceed
	      Gauge,
		winlink1000OduPerfMonAirCurrMinTSL
		  INTEGER,
		winlink1000OduPerfMonAirCurrMaxTSL
		  INTEGER,
		winlink1000OduPerfMonAirCurrTSLThresh1Exceed
		  Gauge,		
		winlink1000OduPerfMonAirCurrBBERThresh1Exceed
		  Gauge
	}

	winlink1000OduPerfMonAirCurrMinRSL OBJECT-TYPE
		SYNTAX  INTEGER (-100..0)
		ACCESS  read-only
		STATUS  mandatory
		DESCRIPTION
		"Current Min Received Level Reference starting from the present 15 minutes period."
		::= { winlink1000OduPerfMonAirCurrEntry 1 }		

	winlink1000OduPerfMonAirCurrMaxRSL OBJECT-TYPE
		SYNTAX  INTEGER (-100..0)
		ACCESS  read-only
		STATUS  mandatory
		DESCRIPTION
		"Current Max Received Level Reference starting from the present 15 minutes period."
		::= { winlink1000OduPerfMonAirCurrEntry 2 }

	winlink1000OduPerfMonAirCurrRSLThresh1Exceed OBJECT-TYPE
		SYNTAX  Gauge (0..900)
		ACCESS  read-only
		STATUS  mandatory
		DESCRIPTION
		"Number of seconds Receive Signal Level exceeded the RSL1 threshold in the last 15 minutes."
		::= { winlink1000OduPerfMonAirCurrEntry 3 }

	winlink1000OduPerfMonAirCurrRSLThresh2Exceed OBJECT-TYPE
		SYNTAX  Gauge (0..900)
		ACCESS  read-only
		STATUS  mandatory
		DESCRIPTION
		"Number of seconds Receive Signal Level exceeded the RSL2 threshold in the last 15 minutes."
		::= { winlink1000OduPerfMonAirCurrEntry 4 }

	winlink1000OduPerfMonAirCurrMinTSL OBJECT-TYPE
		SYNTAX  INTEGER (-10..25)
		ACCESS  read-only
		STATUS  mandatory
		DESCRIPTION
		"Current Min Transmit Signal Level starting from the present 15 minutes period."
		::= { winlink1000OduPerfMonAirCurrEntry 5 }

	winlink1000OduPerfMonAirCurrMaxTSL OBJECT-TYPE
		SYNTAX  INTEGER (-10..25)
		ACCESS  read-only
		STATUS  mandatory
		DESCRIPTION
		"Current Max Transmit Signal Level starting from the present 15 minutes period."
		::= { winlink1000OduPerfMonAirCurrEntry 6 }

	winlink1000OduPerfMonAirCurrTSLThresh1Exceed OBJECT-TYPE
		SYNTAX  Gauge (0..900)
		ACCESS  read-only
		STATUS  mandatory
		DESCRIPTION
		"Number of seconds Transmit Signal Level exceeded the TSL1 threshold in the last 15 minutes."
		::= { winlink1000OduPerfMonAirCurrEntry 7 }

	winlink1000OduPerfMonAirCurrBBERThresh1Exceed OBJECT-TYPE
		SYNTAX  Gauge (0..900)
		ACCESS  read-only
		STATUS  mandatory
		DESCRIPTION
		"Number of seconds Background Block Error Ratio exceeded the BBER1 threshold in the last 15 minutes."
		::= { winlink1000OduPerfMonAirCurrEntry 8 }	
		
	-- ###########################################################
	--                      PM Air Interval Table
	-- ###########################################################	

	winlink1000OduPerfMonAirIntervalTable OBJECT-TYPE
		SYNTAX  SEQUENCE OF Winlink1000OduPerfMonAirIntervalEntry
		ACCESS  not-accessible
		STATUS  mandatory
		DESCRIPTION
		"This table defines/keeps the air counters of the last day (in resolution of 15 min intervals)."
		::= { winlink1000OduPerfMon 5 }

	winlink1000OduPerfMonAirIntervalEntry OBJECT-TYPE
		SYNTAX  Winlink1000OduPerfMonAirIntervalEntry
		ACCESS  not-accessible
		STATUS  mandatory
		DESCRIPTION
		"This is an entry in the Interval Table."
		INDEX {ifIndex, winlink1000OduPerfMonAirIntervalIdx }
		::= { winlink1000OduPerfMonAirIntervalTable 1 }

	Winlink1000OduPerfMonAirIntervalEntry ::= SEQUENCE {
		winlink1000OduPerfMonAirIntervalIdx
	      INTEGER,
		winlink1000OduPerfMonAirIntervalMinRSL
	      INTEGER,
   		winlink1000OduPerfMonAirIntervalMaxRSL
	      INTEGER,
		winlink1000OduPerfMonAirIntervalRSLThresh1Exceed
	      Gauge,
		winlink1000OduPerfMonAirIntervalRSLThresh2Exceed
	      Gauge,
		winlink1000OduPerfMonAirIntervalMinTSL
		  INTEGER,
		winlink1000OduPerfMonAirIntervalMaxTSL
		  INTEGER,
		winlink1000OduPerfMonAirIntervalTSLThresh1Exceed
		  Gauge,		
		winlink1000OduPerfMonAirIntervalBBERThresh1Exceed
		  Gauge
	}

	winlink1000OduPerfMonAirIntervalIdx OBJECT-TYPE
		SYNTAX  INTEGER (1..96)
		ACCESS  read-only
		STATUS  mandatory
		DESCRIPTION
		"This table is indexed per interval number. Each interval
		is of 15 minutes and the oldest is 96."
	::= { winlink1000OduPerfMonAirIntervalEntry 1 }

	winlink1000OduPerfMonAirIntervalMinRSL OBJECT-TYPE
		SYNTAX  INTEGER (-100..0)
		ACCESS  read-only
		STATUS  mandatory
		DESCRIPTION
		"Current Min Received Level Reference per interval."
		::= { winlink1000OduPerfMonAirIntervalEntry 2 }		

	winlink1000OduPerfMonAirIntervalMaxRSL OBJECT-TYPE
		SYNTAX  INTEGER (-100..0)
		ACCESS  read-only
		STATUS  mandatory
		DESCRIPTION
		"Current Max Received Level Reference per interval."
		::= { winlink1000OduPerfMonAirIntervalEntry 3 }

	winlink1000OduPerfMonAirIntervalRSLThresh1Exceed OBJECT-TYPE
		SYNTAX  Gauge (0..900)
		ACCESS  read-only
		STATUS  mandatory
		DESCRIPTION
		"Number of seconds Receive Signal Level exceeded the RSL1 threshold per interval."
		::= { winlink1000OduPerfMonAirIntervalEntry 4 }

	winlink1000OduPerfMonAirIntervalRSLThresh2Exceed OBJECT-TYPE
		SYNTAX  Gauge (0..900)
		ACCESS  read-only
		STATUS  mandatory
		DESCRIPTION
		"Number of seconds Receive Signal Level exceeded the RSL2 threshold
		ACCESS  read-only per interval."
		::= { winlink1000OduPerfMonAirIntervalEntry 5 }

	winlink1000OduPerfMonAirIntervalMinTSL OBJECT-TYPE
		SYNTAX  INTEGER (-10..25)
		ACCESS  read-only
		STATUS  mandatory
		DESCRIPTION
		"Current Min Transmit Signal Level per interval."
		::= { winlink1000OduPerfMonAirIntervalEntry 6 }

	winlink1000OduPerfMonAirIntervalMaxTSL OBJECT-TYPE
		SYNTAX  INTEGER (-10..25)
		ACCESS  read-only
		STATUS  mandatory
		DESCRIPTION
		"Current Max Transmit Signal Level per interval."
		::= { winlink1000OduPerfMonAirIntervalEntry 7 }

	winlink1000OduPerfMonAirIntervalTSLThresh1Exceed OBJECT-TYPE
		SYNTAX  Gauge (0..900)
		ACCESS  read-only
		STATUS  mandatory
		DESCRIPTION
		"Number of seconds Transmit Signal Level exceeded the TSL1 threshold per interval."
		::= { winlink1000OduPerfMonAirIntervalEntry 8 }

	winlink1000OduPerfMonAirIntervalBBERThresh1Exceed OBJECT-TYPE
		SYNTAX  Gauge (0..900)
		ACCESS  read-only
		STATUS  mandatory
		DESCRIPTION
		"Number of seconds Background Block Error Ratio exceeded the BBER1 threshold per interval."
		::= { winlink1000OduPerfMonAirIntervalEntry 9 }

	-- ###########################################################
	--                      PM Air Day Table
	-- ###########################################################	

	winlink1000OduPerfMonAirDayTable OBJECT-TYPE
		SYNTAX  SEQUENCE OF Winlink1000OduPerfMonAirDayEntry
		ACCESS  not-accessible
		STATUS  mandatory
		DESCRIPTION
		"This table defines/keeps the air counters of the last month (in resolution of days)."
		::= { winlink1000OduPerfMon 6 }

	winlink1000OduPerfMonAirDayEntry OBJECT-TYPE
		SYNTAX  Winlink1000OduPerfMonAirDayEntry
		ACCESS  not-accessible
		STATUS  mandatory
		DESCRIPTION
		"This is an entry in the Days Table."
		INDEX {ifIndex, winlink1000OduPerfMonAirDayIdx }
		::= { winlink1000OduPerfMonAirDayTable 1 }

	Winlink1000OduPerfMonAirDayEntry ::= SEQUENCE {
		winlink1000OduPerfMonAirDayIdx
	      INTEGER,
		winlink1000OduPerfMonAirDayMinRSL
	      INTEGER,
   		winlink1000OduPerfMonAirDayMaxRSL
	      INTEGER,
		winlink1000OduPerfMonAirDayRSLThresh1Exceed
	      Gauge,
		winlink1000OduPerfMonAirDayRSLThresh2Exceed
	      Gauge,
		winlink1000OduPerfMonAirDayMinTSL
		  INTEGER,
		winlink1000OduPerfMonAirDayMaxTSL
		  INTEGER,
		winlink1000OduPerfMonAirDayTSLThresh1Exceed
		  Gauge,		
		winlink1000OduPerfMonAirDayBBERThresh1Exceed
		  Gauge
	}

	winlink1000OduPerfMonAirDayIdx OBJECT-TYPE
		SYNTAX  INTEGER (1..96)
		ACCESS  read-only
		STATUS  mandatory
		DESCRIPTION
		"This table is indexed per Day number. Each Day
		is of 15 minutes and the oldest is 96."
	::= { winlink1000OduPerfMonAirDayEntry 1 }

	winlink1000OduPerfMonAirDayMinRSL OBJECT-TYPE
		SYNTAX  INTEGER (-100..0)
		ACCESS  read-only
		STATUS  mandatory
		DESCRIPTION
		"Current Min Received Level Reference per Day."
		::= { winlink1000OduPerfMonAirDayEntry 2 }		

	winlink1000OduPerfMonAirDayMaxRSL OBJECT-TYPE
		SYNTAX  INTEGER (-100..0)
		ACCESS  read-only
		STATUS  mandatory
		DESCRIPTION
		"Current Max Received Level Reference per Day."
		::= { winlink1000OduPerfMonAirDayEntry 3 }

	winlink1000OduPerfMonAirDayRSLThresh1Exceed OBJECT-TYPE
		SYNTAX  Gauge (0..86400)
		ACCESS  read-only
		STATUS  mandatory
		DESCRIPTION
		"Number of seconds Receive Signal Level exceeded the RSL1 threshold per Day."
		::= { winlink1000OduPerfMonAirDayEntry 4 }

	winlink1000OduPerfMonAirDayRSLThresh2Exceed OBJECT-TYPE
		SYNTAX  Gauge (0..86400)
		ACCESS  read-only
		STATUS  mandatory
		DESCRIPTION
		"Number of seconds Receive Signal Level exceeded the RSL2 threshold per Day."
		::= { winlink1000OduPerfMonAirDayEntry 5 }

	winlink1000OduPerfMonAirDayMinTSL OBJECT-TYPE
		SYNTAX  INTEGER (-10..25)
		ACCESS  read-only
		STATUS  mandatory
		DESCRIPTION
		"Current Min Transmit Signal Level per Day."
		::= { winlink1000OduPerfMonAirDayEntry 6 }

	winlink1000OduPerfMonAirDayMaxTSL OBJECT-TYPE
		SYNTAX  INTEGER (-10..25)
		ACCESS  read-only
		STATUS  mandatory
		DESCRIPTION
		"Current Max Transmit Signal Level per Day."
		::= { winlink1000OduPerfMonAirDayEntry 7 }

	winlink1000OduPerfMonAirDayTSLThresh1Exceed OBJECT-TYPE
		SYNTAX  Gauge (0..86400)
		ACCESS  read-only
		STATUS  mandatory
		DESCRIPTION
		"Number of seconds Transmit Signal Level exceeded the TSL1 threshold per Day."
		::= { winlink1000OduPerfMonAirDayEntry 8 }

	winlink1000OduPerfMonAirDayBBERThresh1Exceed OBJECT-TYPE
		SYNTAX  Gauge (0..86400)
		ACCESS  read-only
		STATUS  mandatory
		DESCRIPTION
		"Number of seconds Background Block Error Ratio exceeded the BBER1 threshold per Day."
		::= { winlink1000OduPerfMonAirDayEntry 9 }

	-- ###########################################################
	--                      PM Eth Current Table
	-- ###########################################################

	winlink1000OduPerfMonEthCurrTable OBJECT-TYPE
		SYNTAX  SEQUENCE OF Winlink1000OduPerfMonEthCurrEntry
		ACCESS  not-accessible
		STATUS  mandatory
		DESCRIPTION
		"This table defines/keeps the ethernet counters of the current 15 min interval."
		::= { winlink1000OduPerfMon 7 }

	winlink1000OduPerfMonEthCurrEntry OBJECT-TYPE
		SYNTAX  Winlink1000OduPerfMonEthCurrEntry
		ACCESS  not-accessible
		STATUS  mandatory
		DESCRIPTION
		"This is an entry in the Current Interval Table."
		INDEX {ifIndex }
		::= { winlink1000OduPerfMonEthCurrTable 1 }

	Winlink1000OduPerfMonEthCurrEntry ::= SEQUENCE {
		winlink1000OduPerfMonEthCurrRxMBytes
	      Gauge,
   		winlink1000OduPerfMonEthCurrTxMBytes
	      Gauge,
		winlink1000OduPerfMonEthCurrEthCapacityThreshUnder
	      Gauge,
		winlink1000OduPerfMonEthCurrHighTrafficThreshExceed
	      Gauge,
		winlink1000OduPerfMonEthCurrActiveSeconds
	      Gauge
	}

	winlink1000OduPerfMonEthCurrRxMBytes OBJECT-TYPE
		SYNTAX  Gauge (0..11250)
		ACCESS  read-only
		STATUS  mandatory
		DESCRIPTION
		"Current RX Mega Bytes starting from the present 15 minutes period."
		::= { winlink1000OduPerfMonEthCurrEntry 1 }		

	winlink1000OduPerfMonEthCurrTxMBytes OBJECT-TYPE
		SYNTAX  Gauge (0..11250)
		ACCESS  read-only
		STATUS  mandatory
		DESCRIPTION
		"Current Transmit Mega Bytes starting from the present 15 minutes period."
		::= { winlink1000OduPerfMonEthCurrEntry 2 }	
		
	winlink1000OduPerfMonEthCurrEthCapacityThreshUnder OBJECT-TYPE
		SYNTAX  Gauge (0..900)
		ACCESS  read-only
		STATUS  mandatory
		DESCRIPTION
		"The number of times throughput was below threshold in the present 15 minutes period.
		Relevant for point to point systems."
		::= { winlink1000OduPerfMonEthCurrEntry 3 }
	
	winlink1000OduPerfMonEthCurrHighTrafficThreshExceed OBJECT-TYPE
		SYNTAX  Gauge (0..900)
		ACCESS  read-only
		STATUS  mandatory
		DESCRIPTION
		"The number of times actual traffic was above threshold in the present 15 minutes period."
		::= { winlink1000OduPerfMonEthCurrEntry 4 }
		
	winlink1000OduPerfMonEthCurrActiveSeconds OBJECT-TYPE
		SYNTAX  Gauge (0..900)
		ACCESS  read-only
		STATUS  mandatory
		DESCRIPTION
		"The number of seconds in which RPL Ethernet swervice was not blocked in the present 15 minutes period."
		::= { winlink1000OduPerfMonEthCurrEntry 5 }	

	-- ###########################################################
	--                      PM Eth Interval Table
	-- ###########################################################	

	winlink1000OduPerfMonEthIntervalTable OBJECT-TYPE
		SYNTAX  SEQUENCE OF Winlink1000OduPerfMonEthIntervalEntry
		ACCESS  not-accessible
		STATUS  mandatory
		DESCRIPTION
		"This table defines/keeps the ethernet counters of the last day (in resolution of 15 min intervals)."
		::= { winlink1000OduPerfMon 8 }

	winlink1000OduPerfMonEthIntervalEntry OBJECT-TYPE
		SYNTAX  Winlink1000OduPerfMonEthIntervalEntry
		ACCESS  not-accessible
		STATUS  mandatory
		DESCRIPTION
		"This is an entry in the Interval Table."
		INDEX {ifIndex, winlink1000OduPerfMonEthIntervalIdx }
		::= { winlink1000OduPerfMonEthIntervalTable 1 }

	Winlink1000OduPerfMonEthIntervalEntry ::= SEQUENCE {
		winlink1000OduPerfMonEthIntervalIdx
	      INTEGER,
		winlink1000OduPerfMonEthIntervalRxMBytes
	      Gauge,
   		winlink1000OduPerfMonEthIntervalTxMBytes
	      Gauge,
		winlink1000OduPerfMonEthIntervalEthCapacityThreshUnder
	      Gauge,
		winlink1000OduPerfMonEthIntervalHighTrafficThreshExceed
	      Gauge,
		winlink1000OduPerfMonEthIntervalActiveSeconds
	      Gauge
	}

	winlink1000OduPerfMonEthIntervalIdx OBJECT-TYPE
		SYNTAX  INTEGER (1..96)
		ACCESS  read-only
		STATUS  mandatory
		DESCRIPTION
		"This table is indexed per interval number. Each interval
		is of 15 minutes and the oldest is 96."
		::= { winlink1000OduPerfMonEthIntervalEntry 1 }

	winlink1000OduPerfMonEthIntervalRxMBytes OBJECT-TYPE
		SYNTAX  Gauge (0..11250)
		ACCESS  read-only
		STATUS  mandatory
		DESCRIPTION
		"Current RX Mega Bytes per interval."
		::= { winlink1000OduPerfMonEthIntervalEntry 2 }		

	winlink1000OduPerfMonEthIntervalTxMBytes OBJECT-TYPE
		SYNTAX  Gauge (0..11250)
		ACCESS  read-only
		STATUS  mandatory
		DESCRIPTION
		"Current Transmit Mega Bytes per interval."
		::= { winlink1000OduPerfMonEthIntervalEntry 3 }	
		
	winlink1000OduPerfMonEthIntervalEthCapacityThreshUnder OBJECT-TYPE
		SYNTAX  Gauge (0..900)
		ACCESS  read-only
		STATUS  mandatory
		DESCRIPTION
		"The number of times throughput was below threshold in the each interval.
		Relevant for point to point systems."
		::= { winlink1000OduPerfMonEthIntervalEntry 4 }	
		
	winlink1000OduPerfMonEthIntervalHighTrafficThreshExceed OBJECT-TYPE
		SYNTAX  Gauge (0..900)
		ACCESS  read-only
		STATUS  mandatory
		DESCRIPTION
		"The number of times actual traffic was above threshold in the each interval."
		::= { winlink1000OduPerfMonEthIntervalEntry 5 }	
		
	winlink1000OduPerfMonEthIntervalActiveSeconds OBJECT-TYPE
		SYNTAX  Gauge (0..900)
		ACCESS  read-only
		STATUS  mandatory
		DESCRIPTION
		"The number of seconds in which RPL Ethernet service was not blocked in the each interval."
		::= { winlink1000OduPerfMonEthIntervalEntry 6 }	

	-- ###########################################################
	--                      PM Eth Day Table
	-- ###########################################################	

	winlink1000OduPerfMonEthDayTable OBJECT-TYPE
		SYNTAX  SEQUENCE OF Winlink1000OduPerfMonEthDayEntry
		ACCESS  not-accessible
		STATUS  mandatory
		DESCRIPTION
		"This table defines/keeps the ethernet counters of the last month (in resolution of days)."
		::= { winlink1000OduPerfMon 9 }

	winlink1000OduPerfMonEthDayEntry OBJECT-TYPE
		SYNTAX  Winlink1000OduPerfMonEthDayEntry
		ACCESS  not-accessible
		STATUS  mandatory
		DESCRIPTION
		"This is an entry in the Days Table."
		INDEX {ifIndex, winlink1000OduPerfMonEthDayIdx }
		::= { winlink1000OduPerfMonEthDayTable 1 }

	Winlink1000OduPerfMonEthDayEntry ::= SEQUENCE {
		winlink1000OduPerfMonEthDayIdx
	      INTEGER,
		winlink1000OduPerfMonEthDayRxMBytes
	      Gauge,
   		winlink1000OduPerfMonEthDayTxMBytes
	      Gauge,
		winlink1000OduPerfMonEthDayEthCapacityThreshUnder
	      Gauge,
		winlink1000OduPerfMonEthDayHighTrafficThreshExceed
	      Gauge,
		winlink1000OduPerfMonEthDayActiveSeconds
	      Gauge
	}

	winlink1000OduPerfMonEthDayIdx OBJECT-TYPE
		SYNTAX  INTEGER (1..96)
		ACCESS  read-only
		STATUS  mandatory
		DESCRIPTION
		"This table is indexed per Day number. Each interval
		is of 15 minutes and the oldest is 96."
		::= { winlink1000OduPerfMonEthDayEntry 1 }

	winlink1000OduPerfMonEthDayRxMBytes OBJECT-TYPE
		SYNTAX  Gauge (0..1080000)
		ACCESS  read-only
		STATUS  mandatory
		DESCRIPTION
		"Current RX Mega Bytes per day."
		::= { winlink1000OduPerfMonEthDayEntry 2 }		

	winlink1000OduPerfMonEthDayTxMBytes OBJECT-TYPE
		SYNTAX  Gauge (0..1080000)
		ACCESS  read-only
		STATUS  mandatory
		DESCRIPTION
		"Current Transmit Mega Bytes per day."
		::= { winlink1000OduPerfMonEthDayEntry 3 }
		
	winlink1000OduPerfMonEthDayEthCapacityThreshUnder OBJECT-TYPE
		SYNTAX  Gauge (0..86400)
		ACCESS  read-only
		STATUS  mandatory
		DESCRIPTION
		"The number of times throughput was below threshold each day.
		Relevant for point to point systems."
		::= { winlink1000OduPerfMonEthDayEntry 4 }
		
	winlink1000OduPerfMonEthDayHighTrafficThreshExceed OBJECT-TYPE
		SYNTAX  Gauge (0..86400)
		ACCESS  read-only
		STATUS  mandatory
		DESCRIPTION
		"The number of times actual traffic was above threshold each day."
		::= { winlink1000OduPerfMonEthDayEntry 5 }
		
	winlink1000OduPerfMonEthDayActiveSeconds OBJECT-TYPE
		SYNTAX  Gauge (0..86400)
		ACCESS  read-only
		STATUS  mandatory
		DESCRIPTION
		"The number of seconds in which RPL Ethernet service was not blocked each day."
		::= { winlink1000OduPerfMonEthDayEntry 6 }	
		

	-- ###########################################################
	--                      PM Tdm Current Table
	-- ###########################################################

	winlink1000OduPerfMonTdmCurrTable OBJECT-TYPE
		SYNTAX  SEQUENCE OF Winlink1000OduPerfMonTdmCurrEntry
		ACCESS  not-accessible
		STATUS  mandatory
		DESCRIPTION
		"This table defines/keeps the TDM counters of the current 15 min interval."
		::= { winlink1000OduPerfMon 10 }

	winlink1000OduPerfMonTdmCurrEntry OBJECT-TYPE
		SYNTAX  Winlink1000OduPerfMonTdmCurrEntry
		ACCESS  not-accessible
		STATUS  mandatory
		DESCRIPTION
		"This is an entry in the Current Interval Table."
		INDEX {ifIndex }
		::= { winlink1000OduPerfMonTdmCurrTable 1 }

	Winlink1000OduPerfMonTdmCurrEntry ::= SEQUENCE {
		winlink1000OduPerfMonTdmCurrActiveSeconds
	      Gauge
	}

	winlink1000OduPerfMonTdmCurrActiveSeconds OBJECT-TYPE
		SYNTAX  Gauge (0..900)
		ACCESS  read-only
		STATUS  mandatory
		DESCRIPTION
		"Parameter indicating whether the TDM service was active.
		 Under TDM backup link, the parameter indicates whether 
		 the backup link was active."
		::= { winlink1000OduPerfMonTdmCurrEntry 1 }
		
	-- ###########################################################
	--                      PM Tdm Interval Table
	-- ###########################################################	

	winlink1000OduPerfMonTdmIntervalTable OBJECT-TYPE
		SYNTAX  SEQUENCE OF Winlink1000OduPerfMonTdmIntervalEntry
		ACCESS  not-accessible
		STATUS  mandatory
		DESCRIPTION
		"This table defines/keeps the TDM counters of the last day (in resolution of 15 min intervals)."
		::= { winlink1000OduPerfMon 11 }

	winlink1000OduPerfMonTdmIntervalEntry OBJECT-TYPE
		SYNTAX  Winlink1000OduPerfMonTdmIntervalEntry
		ACCESS  not-accessible
		STATUS  mandatory
		DESCRIPTION
		"This is an entry in the Interval Table."
		INDEX {ifIndex, winlink1000OduPerfMonTdmIntervalIdx }
		::= { winlink1000OduPerfMonTdmIntervalTable 1 }

	Winlink1000OduPerfMonTdmIntervalEntry ::= SEQUENCE {
		winlink1000OduPerfMonTdmIntervalIdx
	      INTEGER,
		winlink1000OduPerfMonTdmIntervalActiveSeconds
	      Gauge
	}

	winlink1000OduPerfMonTdmIntervalIdx OBJECT-TYPE
		SYNTAX  INTEGER (1..96)
		ACCESS  read-only
		STATUS  mandatory
		DESCRIPTION
		"This table is indexed per interval number. Each interval
		is of 15 minutes and the oldest is 96."
		::= { winlink1000OduPerfMonTdmIntervalEntry 1 }

	winlink1000OduPerfMonTdmIntervalActiveSeconds OBJECT-TYPE
		SYNTAX  Gauge (0..900)
		ACCESS  read-only
		STATUS  mandatory
		DESCRIPTION
		"Parameter indicating whether the TDM service was active.
		Under TDM backup link, the parameter indicates whether 
		the backup link was active."
		::= { winlink1000OduPerfMonTdmIntervalEntry 2 }		

	-- ###########################################################
	--                      PM Tdm Day Table
	-- ###########################################################	

	winlink1000OduPerfMonTdmDayTable OBJECT-TYPE
		SYNTAX  SEQUENCE OF Winlink1000OduPerfMonTdmDayEntry
		ACCESS  not-accessible
		STATUS  mandatory
		DESCRIPTION
		"This table defines/keeps the TDM counters of the last month (in resolution of days)."
		::= { winlink1000OduPerfMon 12 }

	winlink1000OduPerfMonTdmDayEntry OBJECT-TYPE
		SYNTAX  Winlink1000OduPerfMonTdmDayEntry
		ACCESS  not-accessible
		STATUS  mandatory
		DESCRIPTION
		"This is an entry in the Days Table."
		INDEX {ifIndex, winlink1000OduPerfMonTdmDayIdx }
		::= { winlink1000OduPerfMonTdmDayTable 1 }

	Winlink1000OduPerfMonTdmDayEntry ::= SEQUENCE {
		winlink1000OduPerfMonTdmDayIdx
	      INTEGER,
		winlink1000OduPerfMonTdmDayActiveSeconds
	      Gauge
	}

	winlink1000OduPerfMonTdmDayIdx OBJECT-TYPE
		SYNTAX  INTEGER (1..96)
		ACCESS  read-only
		STATUS  mandatory
		DESCRIPTION
		"This table is indexed per Day number. Each interval
		is of 15 minutes and the oldest is 96."
		::= { winlink1000OduPerfMonTdmDayEntry 1 }

	winlink1000OduPerfMonTdmDayActiveSeconds OBJECT-TYPE
		SYNTAX  Gauge (0..86400)
		ACCESS  read-only
		STATUS  mandatory
		DESCRIPTION
		"Parameter indicating whether the TDM service was active.
		Under TDM backup link, the parameter indicates whether 
		the backup link was active."
		::= { winlink1000OduPerfMonTdmDayEntry 2 }

	-- ###########################################################
	--                      PM Configuration thresholds
	-- ###########################################################	

	winlink1000OduPerfMonTxThresh1 OBJECT-TYPE
		SYNTAX  INTEGER (-10..25)
		ACCESS  read-write
		STATUS  mandatory
		DESCRIPTION
		"When the Transmit power exceeds this threshold, a performance monitoring TSL1 counter is incremented."
		::= { winlink1000OduPerfMon 20 }

	winlink1000OduPerfMonRxThresh1 OBJECT-TYPE
		SYNTAX  INTEGER (-100..0)
		ACCESS  read-write
		STATUS  mandatory
		DESCRIPTION
		"When the RX power exceeds this threshold, a performance monitoring RSL1 counter is incremented."
		::= { winlink1000OduPerfMon 21 }

	winlink1000OduPerfMonRxThresh2 OBJECT-TYPE
		SYNTAX  INTEGER (-100..0)
		ACCESS  read-write
		STATUS  mandatory
		DESCRIPTION
		"When the RX power exceeds this threshold, a performance monitoring RSL2 counter is incremented."
		::= { winlink1000OduPerfMon 22 }

	winlink1000OduPerfMonBBERThresh1 OBJECT-TYPE
		SYNTAX  INTEGER (0..500)
		ACCESS  read-write
		STATUS  mandatory
		DESCRIPTION
		"When the BBER exceeds this threshold, a performance monitoring BBER counter is incremented. The units are 1/10 of a percent."
		::= { winlink1000OduPerfMon 23 }
		
	winlink1000OduPerfMonEthCapacityThreshKbps OBJECT-TYPE
		SYNTAX  INTEGER (0..100000)
		ACCESS  read-write
		STATUS  mandatory
		DESCRIPTION
		"When the current throughput is below this threshold, the corresponding counter is incremented"
		::= { winlink1000OduPerfMon 24 }
		
	winlink1000OduPerfMonHighTrafficThreshKbps OBJECT-TYPE
		SYNTAX  INTEGER (0..100000)
		ACCESS  read-write
		STATUS  mandatory
		DESCRIPTION
		"When the current traffic is above this threshold, then corresponding counter is incremented."
		::= { winlink1000OduPerfMon 25 }
	
	-- ###########################################################
	--                      ODU SNMP Agent
	-- ###########################################################

	winlink1000OduAgent OBJECT IDENTIFIER ::= { winlink1000Odu 7 }

	winlink1000OduAgnGeneral  OBJECT IDENTIFIER ::= { winlink1000OduAgent 1 }

	winlink1000OduAgnGenAddTrapExt OBJECT-TYPE
		SYNTAX  INTEGER {
			no(1),
			yes(2)
		}
		ACCESS  read-write
		STATUS  mandatory
		DESCRIPTION
		"If 'yes' is chosen, the ifIndex, Unit, Severity, Time_T and Alarm Id from the winlink1000OduAgnCurrAlarmTable
		will be bind to the end of each private trap."		
		::= { winlink1000OduAgnGeneral 1 }

	winlink1000OduAgnGenSetMode OBJECT-TYPE
		SYNTAX  INTEGER{
			enabled(1),
			disabledSWU(2),
			disabledSpectrumAnalysis(3),
			disabledBeforeResetAfterSWU(4),
			disabledUpdateConfigurationFiles(5),
			disabledSWK(6)
			}
		ACCESS  read-write
		STATUS  mandatory
		DESCRIPTION
		"This parameter is reserved to the element manager provided with the product."		
		::= { winlink1000OduAgnGeneral 2 }
		
	winlink1000OduAgnGenLocalConnectionMode OBJECT-TYPE
		SYNTAX  INTEGER{
			readWrite(1),
			readOnly(2)
			}
		ACCESS  read-write
		STATUS  mandatory
		DESCRIPTION
		"Local Connection (Broadcast) Configuration Mode. Options are:
		1 - SNMP Read-Write,
		2 - SNMP Read-Only."		
		::= { winlink1000OduAgnGeneral 3 }	

	winlink1000OduAgnNTPCfg  OBJECT IDENTIFIER ::= { winlink1000OduAgent 2 }	

	winlink1000OduAgnNTPCfgTimeServerIP OBJECT-TYPE
		SYNTAX  IpAddress
		ACCESS  read-write
		STATUS  mandatory
		DESCRIPTION
		"IP address of the server from which the current time is loaded."
		::= { winlink1000OduAgnNTPCfg 1 }

	winlink1000OduAgnNTPCfgTimeOffsetFromUTC OBJECT-TYPE
		SYNTAX  INTEGER (-1440..1440)
		ACCESS  read-write
		STATUS  mandatory
		DESCRIPTION
		"Offset from Coordinated Universal Time (minutes). Possible values: -1440..1440."
		::= { winlink1000OduAgnNTPCfg 2 }

	winlink1000OduAgnRealTimeAndDate OBJECT-TYPE
		SYNTAX OCTET STRING(SIZE(8))
		ACCESS  read-write
		STATUS mandatory
		DESCRIPTION
		"This parameter specifies the real time and date
        Format 'YYYY-MM-DD,HH:MM:SS' (Hexadecimal).        
		A date-time specification:

        field  octets  contents                  range
        -----  ------  --------                  -----
          1      1-2   year                      0..65536
          2       3    month                     1..12
          3       4    day                       1..31
          4       5    hour                      0..23
          5       6    minutes                   0..59
    	  6       7    seconds                   0..60
                       (use 60 for leap-second)
          7       8    deci-seconds              0..9
        
        For example, Tuesday May 26, 1992 at 1:30:15 PM EDT
        would be displayed as:	07 c8 05 1a 0d 1e 0f 00
							  ( 1992 -5 -26,13:30:15 )"
		::= { winlink1000OduAgnNTPCfg 3 }

	winlink1000OduAdmNTPCfgTimeServerIPv6 OBJECT-TYPE
		SYNTAX  DisplayString
		ACCESS  read-write
		STATUS  mandatory
		DESCRIPTION
		"IPv6 address of the server from which the current time is loaded."
		::= { winlink1000OduAgnNTPCfg 4 }
		
	winlink1000OduAgnCurrAlarm OBJECT IDENTIFIER ::= { winlink1000OduAgent 3 }

	winlink1000OduAgnCurrAlarmLastChange OBJECT-TYPE
		SYNTAX INTEGER
		ACCESS  read-only
		STATUS mandatory
		DESCRIPTION
		"This counter is initialized to 0 after a device reset and is incremented upon each change in the winlink1000OduAgnCurrAlarmTable
		(either an addition or removal of an entry)."
		::= { winlink1000OduAgnCurrAlarm 1 }  

	-- ###########################################################
	--                      Active Alarm Table
	-- ###########################################################	

	winlink1000OduAgnCurrAlarmTable  OBJECT-TYPE
       	SYNTAX  SEQUENCE OF Winlink1000OduAgnCurrAlarmEntry
       	ACCESS  not-accessible
       	STATUS  mandatory
       	DESCRIPTION
       	"This table includes the currently active alarms. When a RAISED trap is 
       	sent, an alarm entry is added to the table. When a CLEAR trap is sent, 
       	the entry is removed."
      	::= { winlink1000OduAgnCurrAlarm 2 } 

	winlink1000OduAgnCurrAlarmEntry OBJECT-TYPE
		SYNTAX  Winlink1000OduAgnCurrAlarmEntry
		ACCESS  not-accessible
		STATUS  mandatory
		DESCRIPTION
		"Entry containing the details of a currently RAISED trap."
		INDEX { winlink1000OduAgnCurrAlarmCounter }
		::= { winlink1000OduAgnCurrAlarmTable  1 }

	Winlink1000OduAgnCurrAlarmEntry ::=	SEQUENCE {
   		winlink1000OduAgnCurrAlarmCounter
			INTEGER,
		winlink1000OduAgnCurrAlarmSeverity
			INTEGER,
		winlink1000OduAgnCurrAlarmId
			INTEGER,
   		winlink1000OduAgnCurrAlarmIfIndex
			INTEGER,
		winlink1000OduAgnCurrAlarmUnit
			INTEGER,
   		winlink1000OduAgnCurrAlarmTrapID
			INTEGER,
		winlink1000OduAgnCurrAlarmTimeT
			INTEGER,
		winlink1000OduAgnCurrAlarmText
			DisplayString
	} 

	winlink1000OduAgnCurrAlarmCounter OBJECT-TYPE
		SYNTAX  INTEGER
		ACCESS  read-only
		STATUS  mandatory
		DESCRIPTION
		"A running counter of active alarms. The counter is incremented for every new RAISED trap.
		It is cleared after a device reset."
		::= { winlink1000OduAgnCurrAlarmEntry 1 }

	winlink1000OduAgnCurrAlarmSeverity OBJECT-TYPE
		SYNTAX  INTEGER	{
			event		(1),
			normal		(2),
			warning		(4),
			minor		(8),
			major		(16),
			critical	(32)
			}
		ACCESS  read-only
		STATUS  mandatory
		DESCRIPTION
		"Current Alarm severity."
		::= { winlink1000OduAgnCurrAlarmEntry 2 }

	winlink1000OduAgnCurrAlarmId OBJECT-TYPE
		SYNTAX  INTEGER
		ACCESS  read-only
		STATUS  mandatory
		DESCRIPTION
		"Unique Alarm Identifier (combines alarm type and interface). The same AlarmId is used for RAISED and CLEARED alarms."
		::= { winlink1000OduAgnCurrAlarmEntry 3 }

	winlink1000OduAgnCurrAlarmIfIndex OBJECT-TYPE
		SYNTAX  INTEGER
		ACCESS  read-only
		STATUS  mandatory
		DESCRIPTION
		"Interface Index where the alarm occurred. Alarms that are
  		not associated with a specific interface will have the following value: 65535."
		::= { winlink1000OduAgnCurrAlarmEntry 4 }	

	winlink1000OduAgnCurrAlarmUnit OBJECT-TYPE
		SYNTAX  INTEGER {
			idu(1),
			odu(2)
		}
		ACCESS  read-only
		STATUS  mandatory
		DESCRIPTION
		"Unit associated with the alarm."
		::= { winlink1000OduAgnCurrAlarmEntry 5 }

	winlink1000OduAgnCurrAlarmTrapID OBJECT-TYPE
		SYNTAX  INTEGER 
		ACCESS  read-only
		STATUS  mandatory
		DESCRIPTION
		"ID of the raised trap that was sent when this alarm was raised."
		::= { winlink1000OduAgnCurrAlarmEntry 6 }

	winlink1000OduAgnCurrAlarmTimeT OBJECT-TYPE
		SYNTAX  INTEGER
		ACCESS  read-only
		STATUS  mandatory
		DESCRIPTION
		"Timestamp of this alarm. This number is in seconds from Midnight January 1st, 1970."
		::= { winlink1000OduAgnCurrAlarmEntry 7 }

	winlink1000OduAgnCurrAlarmText OBJECT-TYPE
		SYNTAX  DisplayString
		ACCESS  read-only
		STATUS  mandatory
		DESCRIPTION
		"Alarm display text (same as the text in the sent trap)."
		::= { winlink1000OduAgnCurrAlarmEntry 8 }


	winlink1000OduAgnLastEvents OBJECT IDENTIFIER ::= { winlink1000OduAgent 4 }

	winlink1000OduAgnLastEventsNumber OBJECT-TYPE
		SYNTAX INTEGER
		ACCESS  read-only
		STATUS mandatory
		DESCRIPTION
		"This counter indicates the size of the winlink1000OduAgnLastEventsTable"
		::= { winlink1000OduAgnLastEvents 1 }  

	-- ###########################################################
	--                      Last Events Table
	-- ###########################################################	

	winlink1000OduAgnLastEventsTable OBJECT-TYPE
       	SYNTAX  SEQUENCE OF Winlink1000OduAgnLastEventsEntry
       	ACCESS  not-accessible
       	STATUS  mandatory
       	DESCRIPTION
       	"This table includes the last events. When a trap is 
       	sent, an event entry is added to the table."
      	::= { winlink1000OduAgnLastEvents 2 } 

	winlink1000OduAgnLastEventsEntry OBJECT-TYPE
		SYNTAX  Winlink1000OduAgnLastEventsEntry
		ACCESS  not-accessible
		STATUS  mandatory
		DESCRIPTION
		"Entry containing the details of last traps."
		INDEX { winlink1000OduAgnLastEventsIndex }
		::= { winlink1000OduAgnLastEventsTable  1 }

	Winlink1000OduAgnLastEventsEntry ::= SEQUENCE {
   		winlink1000OduAgnLastEventsIndex
			INTEGER,
		winlink1000OduAgnLastEventsSeverity
			INTEGER,
   		winlink1000OduAgnLastEventsIfIndex
			INTEGER,
		winlink1000OduAgnLastEventsTimeT
			INTEGER,
		winlink1000OduAgnLastEventsText
			DisplayString
	} 

	winlink1000OduAgnLastEventsIndex OBJECT-TYPE
		SYNTAX  INTEGER
		ACCESS  read-only
		STATUS  mandatory
		DESCRIPTION
		"The index of the table"
		::= { winlink1000OduAgnLastEventsEntry 1 }

	winlink1000OduAgnLastEventsSeverity OBJECT-TYPE
		SYNTAX  INTEGER	{
			event		(1),
			normal		(2),
			warning		(4),
			minor		(8),
			major		(16),
			critical	(32)
			}
		ACCESS  read-only
		STATUS  mandatory
		DESCRIPTION
		"Current Trap severity."
		::= { winlink1000OduAgnLastEventsEntry 2 }

	winlink1000OduAgnLastEventsIfIndex OBJECT-TYPE
		SYNTAX  INTEGER
		ACCESS  read-only
		STATUS  mandatory
		DESCRIPTION
		"Interface Index where the event occurred. Traps that are
  		not associated with a specific interface will have the following value: 65535."
		::= { winlink1000OduAgnLastEventsEntry 3 }	

	winlink1000OduAgnLastEventsTimeT OBJECT-TYPE
		SYNTAX  INTEGER
		ACCESS  read-only
		STATUS  mandatory
		DESCRIPTION
		"Timestamp of this trap. This number is in seconds from Midnight January 1st, 1970."
		::= { winlink1000OduAgnLastEventsEntry 4 }

	winlink1000OduAgnLastEventsText OBJECT-TYPE
		SYNTAX  DisplayString
		ACCESS  read-only
		STATUS  mandatory
		DESCRIPTION
		"Trap display text (same as the text in the sent trap)."
		::= { winlink1000OduAgnLastEventsEntry 5 }


	-- ###########################################################
	--                      ODU Agent Users Table
	-- ###########################################################

	winlink1000OduAgnUsersTable OBJECT-TYPE
		SYNTAX  SEQUENCE OF Winlink1000OduAgnUsersEntry
		ACCESS  not-accessible
		STATUS  mandatory
		DESCRIPTION
		"SNMP users table. Each user is defined by name, password and profile."
		::= { winlink1000OduAgent 5 }

	winlink1000OduAgnUsersEntry OBJECT-TYPE
		SYNTAX  Winlink1000OduAgnUsersEntry
		ACCESS  not-accessible
		STATUS  mandatory
		DESCRIPTION
		"SNMP users table entry."
		INDEX { winlink1000OduAgnUsersIndex }
		::= { winlink1000OduAgnUsersTable 1 }

	Winlink1000OduAgnUsersEntry ::= SEQUENCE {
		winlink1000OduAgnUsersIndex
			INTEGER,
		winlink1000OduAgnUsersUserName
			DisplayString,
		winlink1000OduAgnUsersPassword
			DisplayString,
		winlink1000OduAgnUsersProfile
			INTEGER,
		winlink1000OduAgnUsersLastAccessTime
			INTEGER
		}

	winlink1000OduAgnUsersIndex OBJECT-TYPE
		SYNTAX  INTEGER
		ACCESS  read-only
		STATUS  mandatory
		DESCRIPTION
		"SNMP users table index."
		::= { winlink1000OduAgnUsersEntry 1 }
		
	winlink1000OduAgnUsersUserName OBJECT-TYPE
		SYNTAX  DisplayString
		ACCESS  read-write
		STATUS  mandatory
		DESCRIPTION
		"SNMP users user names."
		::= { winlink1000OduAgnUsersEntry 2 }
		
	winlink1000OduAgnUsersPassword OBJECT-TYPE
		SYNTAX  DisplayString
		ACCESS  read-write
		STATUS  mandatory
		DESCRIPTION
		"SNMP users passwords."
		::= { winlink1000OduAgnUsersEntry 3 }
		
	winlink1000OduAgnUsersProfile OBJECT-TYPE
		SYNTAX  INTEGER {
			disabled(1),
			readonly(2),
			readwrite(3)
			}
		ACCESS  read-write
		STATUS  mandatory
		DESCRIPTION
		"SNMP users profile (1=Disabled, 2=ReadOnly, 3=ReadWrite)."
		::= { winlink1000OduAgnUsersEntry 4 }
		
	winlink1000OduAgnUsersLastAccessTime OBJECT-TYPE
		SYNTAX  INTEGER
		ACCESS  read-only
		STATUS  mandatory
		DESCRIPTION
		"SNMP users last access time."
		::= { winlink1000OduAgnUsersEntry 5 }
		
	-- ###########################################################
	--                      IDU
	-- ###########################################################

	winlink1000Idu OBJECT IDENTIFIER ::= { winlink1000 2 }

	-- ###########################################################
	--                      IDU Admin
	-- ###########################################################

	winlink1000IduAdmin OBJECT IDENTIFIER ::= { winlink1000Idu 1 }

	winlink1000IduAdmProductType OBJECT-TYPE
		SYNTAX  DisplayString
		ACCESS  read-only
		STATUS  mandatory
		DESCRIPTION
		"IDU configuration description."
		::= { winlink1000IduAdmin 1 }

	winlink1000IduAdmHwRev OBJECT-TYPE
		SYNTAX  DisplayString
		ACCESS  read-only
		STATUS  mandatory
		DESCRIPTION
		"IDU Hardware Revision."
		::= { winlink1000IduAdmin 2 }

	winlink1000IduAdmSwRev OBJECT-TYPE
		SYNTAX  DisplayString
		ACCESS  read-only
		STATUS  mandatory
		DESCRIPTION
		"IDU Software Revision."
		::= { winlink1000IduAdmin 3 }

	winlink1000OduAdmNumOfExternalAlarmIn OBJECT-TYPE
		SYNTAX  INTEGER
		ACCESS  read-only
		STATUS  mandatory
		DESCRIPTION
		"Indicates the number of currently available External Alarm Inputs."
		::= { winlink1000IduAdmin 4 }	

	winlink1000OduAdmExternAlarmInTable   OBJECT-TYPE
        SYNTAX  SEQUENCE OF Winlink1000OduAdmExternAlarmInEntry
        ACCESS  not-accessible
        STATUS  mandatory
        DESCRIPTION
        "This is the External Alarm Inputs table."
        ::= { winlink1000IduAdmin 5 }

	winlink1000OduAdmExternAlarmInEntry OBJECT-TYPE
        SYNTAX  Winlink1000OduAdmExternAlarmInEntry
        ACCESS  not-accessible
        STATUS  mandatory
		DESCRIPTION
		"Entry containing the elements of a single External Alarm Input."
        INDEX { winlink1000OduAdmExternAlarmInIndex}
        ::= { winlink1000OduAdmExternAlarmInTable   1 }
	
	Winlink1000OduAdmExternAlarmInEntry ::= SEQUENCE {
		winlink1000OduAdmExternAlarmInIndex
             INTEGER,		
		winlink1000OduAdmExternAlarmInText
       	     DisplayString,
		winlink1000OduAdmExternAlarmInAdminState
             INTEGER,
		winlink1000OduAdmExternAlarmInStatus
             INTEGER
		}	

	winlink1000OduAdmExternAlarmInIndex OBJECT-TYPE
        SYNTAX  INTEGER(1..2)
        ACCESS  read-only
   		STATUS  mandatory
        DESCRIPTION
        "This value indicates the index of the External Alarm Input entry."
        ::= { winlink1000OduAdmExternAlarmInEntry 1 }

	winlink1000OduAdmExternAlarmInText OBJECT-TYPE
		SYNTAX  DisplayString
        ACCESS  read-write
        STATUS  mandatory
        DESCRIPTION
        "This field describes the External Alarm Input. It is an optional string of no more than 64 characters,
		which will be used in the event being sent as a result of a change in the status of the External Alarm Input."
		DEFVAL {"Alarm Description"}
        ::= { winlink1000OduAdmExternAlarmInEntry 2 }

	winlink1000OduAdmExternAlarmInAdminState OBJECT-TYPE
		SYNTAX  INTEGER {
			enabled(1),
			disabled(2)
			}
        ACCESS  read-write
   		STATUS  mandatory
        DESCRIPTION
        "This value indicates if this External Alarm Input is enabled or disabled."
        ::= { winlink1000OduAdmExternAlarmInEntry 3 }

	winlink1000OduAdmExternAlarmInStatus OBJECT-TYPE
		SYNTAX  INTEGER {
			clear(1),
			alarm(2),
			unknown(3)
			}
        ACCESS  read-only
   		STATUS  mandatory
        DESCRIPTION
        "This value indicates the current status of the External Alarm Input."
        ::= { winlink1000OduAdmExternAlarmInEntry 4 }

	winlink1000IduAdmSN OBJECT-TYPE
        SYNTAX  DisplayString
		ACCESS  read-only
		STATUS  mandatory
        DESCRIPTION
        "IDU Serial Number"
        ::= { winlink1000IduAdmin 6 }

	winlink1000IduAdmIduDetectionMode OBJECT-TYPE
		SYNTAX  INTEGER {
			mandatoryDisabled(1),
			mandatoryEnabled(2),
			userDisabled(3),
			userEnabled(4)
			}
		ACCESS  read-write
		STATUS  mandatory
		DESCRIPTION
		"The parameter defines whether to send Ethernet frames to detect an IDU. 
		The valid writable values are: userDisabled (3), userEnabled (4). 
		A change requires a reset and is effective after reset."
		::= { winlink1000IduAdmin 7 }

	winlink1000IduAdmMountedTrunks   OBJECT-TYPE
	SYNTAX  INTEGER
		ACCESS  read-only
		STATUS  mandatory
		DESCRIPTION
		"Number of mounted trunks in the IDU "
		::= { winlink1000IduAdmin 8 }

	winlink1000IduAdmLicensedTrunks   OBJECT-TYPE
	SYNTAX  INTEGER
		ACCESS  read-only
		STATUS  mandatory
		DESCRIPTION
		"Number of Licensed Trunks in the IDU "
		::= { winlink1000IduAdmin 9 }

	winlink1000IduAdmVlanSupported   OBJECT-TYPE
	SYNTAX  INTEGER {
		notSupported(1),
		supported(2),
		supportedLimited(3)
		}
		ACCESS  read-only
		STATUS  mandatory
		DESCRIPTION
		"Identifies if the local IDU supports VLAN tag/untag"
		::= { winlink1000IduAdmin 10 }
	
	
	winlink1000IduAdmVlanEgressMode   OBJECT-TYPE
		SYNTAX  DisplayString
		ACCESS  read-write
		STATUS  mandatory
		DESCRIPTION
		"VLAN tag/untag egress values"
		::= { winlink1000IduAdmin 11 }

	winlink1000IduAdmVlanIngressMode   OBJECT-TYPE
		SYNTAX  DisplayString
		ACCESS  read-write
		STATUS  mandatory
		DESCRIPTION
		"VLAN tag/untag ingress values"
		::= { winlink1000IduAdmin 12 }

	winlink1000IduAdmVlanDefaultPortVIDs   OBJECT-TYPE
		SYNTAX  DisplayString
		ACCESS  read-write
		STATUS  mandatory
		DESCRIPTION
		"VLAN tag/untag default VLAN ids for each port - Right most digit is Vlan priority (0-6), other digits compose Vlan Id (1-4094)"
		::= { winlink1000IduAdmin 13 }

	winlink1000IduAdmVlanLan1UntaggedVIDs   OBJECT-TYPE
		SYNTAX  DisplayString
		ACCESS  read-write
		STATUS  mandatory
		DESCRIPTION
		"VLAN untagged VIDs for LAN1 port"
		::= { winlink1000IduAdmin 14 }
		
	winlink1000IduAdmVlanLan2UntaggedVIDs   OBJECT-TYPE
		SYNTAX  DisplayString
		ACCESS  read-write
		STATUS  mandatory
		DESCRIPTION
		"VLAN untagged VIDs for LAN2 port"
		::= { winlink1000IduAdmin 15 }

	winlink1000IduAdmVlanSfpUntaggedVIDs   OBJECT-TYPE
		SYNTAX  DisplayString
		ACCESS  read-write
		STATUS  mandatory
		DESCRIPTION
		"VLAN untagged VIDs for Sfp port"
		::= { winlink1000IduAdmin 16 }

	winlink1000IduAdmVlanLan1FilteredVIDs   OBJECT-TYPE
		SYNTAX  DisplayString
		ACCESS  read-write
		STATUS  mandatory
		DESCRIPTION
		"VLAN filtered VIDs for LAN1 port"
		::= { winlink1000IduAdmin 17 }
		
	winlink1000IduAdmVlanLan2FilteredVIDs   OBJECT-TYPE
		SYNTAX  DisplayString
		ACCESS  read-write
		STATUS  mandatory
		DESCRIPTION
		"VLAN filtered VIDs for LAN2 port"
		::= { winlink1000IduAdmin 18 }

	winlink1000IduAdmVlanSfpFilteredVIDs   OBJECT-TYPE
		SYNTAX  DisplayString
		ACCESS  read-write
		STATUS  mandatory
		DESCRIPTION
		"VLAN filtered VIDs for Sfp port"
		::= { winlink1000IduAdmin 19 }
		
	winlink1000IduAdmPortsConnection   OBJECT-TYPE
		SYNTAX  INTEGER
		ACCESS  read-write
		STATUS  mandatory
		DESCRIPTION
		"IDU ports connection bitmap.
		 bit 0 - LAN1-LAN2
		 bit 1 - SFP-LAN1
		 bit 2 - SFP-LAN2
		 bit values:
		 0 - ports are disconnected.
		 1 - ports are connected."
		::= { winlink1000IduAdmin 20 }

	winlink1000IduAdmVlanMode   OBJECT-TYPE
		SYNTAX  INTEGER {
			normal(1),
			membership(2)
		}
		ACCESS  read-write
		STATUS  mandatory
		DESCRIPTION
		"Local IDU Vlan Mode."
		::= { winlink1000IduAdmin 21 }

	winlink1000IduAdmVlanMembershipVIDs   OBJECT-TYPE
		SYNTAX  OCTET STRING
		ACCESS  read-write
		STATUS  mandatory
		DESCRIPTION
		"VLAN Membership VLAN IDs list."
		::= { winlink1000IduAdmin 22 }

	winlink1000IduAdmVlanMembershipPortsCode   OBJECT-TYPE
		SYNTAX  OCTET STRING
		ACCESS  read-write
		STATUS  mandatory
		DESCRIPTION
		"VLAN Membership ports code. Each value represent the relation (bitmap) 
		 Between the suitable VID to the IDU ports.
		 bit 0 - LAN1
		 bit 1 - LAN2
		 bit 2 - SFP
		 bit value 0 - not member of appropriate VID
		 bit value 1 - member of appropriate VID"
		::= { winlink1000IduAdmin 23 }

	winlink1000IduAdmVlanMembershipUntaggedHandle   OBJECT-TYPE
		SYNTAX  DisplayString
		ACCESS  read-write
		STATUS  mandatory
		DESCRIPTION
		"VLAN Membership Untagged frames handling.
		 The 3 values representing LAN1, LAN2 and SFP accordingly.
		 For each port, the optional values are:
		 1 - Discard
		 2 - Tag
		 3 - Leave Unmodified"
		::= { winlink1000IduAdmin 24 }

	winlink1000IduAdmVlanMembershipTagUntagged   OBJECT-TYPE
		SYNTAX  DisplayString
		ACCESS  read-write
		STATUS  mandatory
		DESCRIPTION
		"VLAN Membership Untagged frames tagging.
		 The 3 values representing LAN1, LAN2 and SFP accordingly.
		 The value on each port entry represent the tagging value which is built of:
		 VLAN ID & VLAN Priority."
		::= { winlink1000IduAdmin 25 }
				
	-- ###########################################################
	--                      IDU Service
	-- ###########################################################

	winlink1000IduService OBJECT IDENTIFIER ::= { winlink1000Idu 2 }

	winlink1000IduSrvDesiredTrunks OBJECT-TYPE
		SYNTAX  INTEGER
		ACCESS  read-write
		STATUS  mandatory
		DESCRIPTION
		"Required trunks bitmap. 
		Note that the number of possible trunks that can be configured may vary, based on the IDU hardware 
		configuration, the selected air interface rate and the range of the installation. 
		The provided Manager application enables the user to select only available configurations.
		A change is effective immediately if applied to a master unit and the link is in service mode."
		::= { winlink1000IduService 2 }

	winlink1000IduSrvServices OBJECT-TYPE
		SYNTAX  OBJECT IDENTIFIER
		ACCESS  read-only
		STATUS  mandatory
		DESCRIPTION
		"This parameter is reserved to the Manager application provided with the product."
		::= { winlink1000IduService 4 }

	winlink1000IduSrvActiveTrunks OBJECT-TYPE
		SYNTAX  INTEGER
		ACCESS  read-only
		STATUS  mandatory
		DESCRIPTION
		"A bitmap describing the currently open TDM trunks."
		::= { winlink1000IduService 6 }

	winlink1000IduSrvAvailableTrunks OBJECT-TYPE
		SYNTAX INTEGER
		ACCESS  read-only
		STATUS  mandatory
		DESCRIPTION
		"A bitmap describing the number of TDM trunks that can be opened in the current configuration.
		 The values take into account the IDU hardware configuration, the air rate and the installation range."
		::= { winlink1000IduService 8 }

	-- ###########################################################
	--                      IDU Possible Services Table (old)
	-- ###########################################################

	winlink1000IduSrvPossibleServicesTable OBJECT-TYPE
		SYNTAX  SEQUENCE OF Winlink1000IduSrvPossibleServicesEntry
		ACCESS  not-accessible
		STATUS  mandatory
		DESCRIPTION
		"IDU Possible Services table."
		::= { winlink1000IduService 10 }

	winlink1000IduSrvPossibleServicesEntry OBJECT-TYPE
		SYNTAX  Winlink1000IduSrvPossibleServicesEntry
		ACCESS  not-accessible
		STATUS  mandatory
		DESCRIPTION
		"IDU Services table entry."
		INDEX { winlink1000IduSrvPossibleServicesIndex }
		::= { winlink1000IduSrvPossibleServicesTable 1 }

	Winlink1000IduSrvPossibleServicesEntry ::= SEQUENCE {
		winlink1000IduSrvPossibleServicesIndex
			INTEGER,
		winlink1000IduSrvPossibleTdmServices
			INTEGER,
		winlink1000IduSrvPossibleEthServices
			INTEGER,
		winlink1000IduSrvRemainingRate
			INTEGER,
		winlink1000IduSrvTrunkCost
			INTEGER
		}

	winlink1000IduSrvPossibleServicesIndex OBJECT-TYPE
		SYNTAX  INTEGER
		ACCESS  read-only
		STATUS  mandatory
		DESCRIPTION
		"Table index, Rate index of the air interface."
		::= { winlink1000IduSrvPossibleServicesEntry 1 }

	winlink1000IduSrvPossibleTdmServices OBJECT-TYPE
		SYNTAX  INTEGER
		ACCESS  read-only
		STATUS  deprecated
		DESCRIPTION
		"Deprecated parameter.
		A bitmap describing the TDM trunks that can be opened in the corresponding Air Rate."
		::= { winlink1000IduSrvPossibleServicesEntry 2 }

	winlink1000IduSrvPossibleEthServices OBJECT-TYPE
		SYNTAX  INTEGER
		ACCESS  read-only
		STATUS  deprecated
		DESCRIPTION
		"Deprecated parameter.
		This parameter describes if the Ethernet Service can be opened
		in the corresponding Air Rate. The valid values are: disabled (0), enabled (1)."
		::= { winlink1000IduSrvPossibleServicesEntry 3 }

	winlink1000IduSrvRemainingRate OBJECT-TYPE
		SYNTAX  INTEGER
		ACCESS  read-only
		STATUS  mandatory
		DESCRIPTION
		"Current Ethernet bandwidth in bps per air rate."
		::= { winlink1000IduSrvPossibleServicesEntry 4 }

	winlink1000IduSrvTrunkCost OBJECT-TYPE
		SYNTAX  INTEGER
		ACCESS  read-only
		STATUS  mandatory
		DESCRIPTION
		"Cost of the TDM Service in bps."
		::= { winlink1000IduSrvPossibleServicesEntry 5 }

	-- ###########################################################
	--                      IDU Possible Services Table (new)
	-- ###########################################################

	winlink1000IduSrvAvailServicesTable OBJECT-TYPE
		SYNTAX  SEQUENCE OF Winlink1000IduSrvAvailServicesEntry
		ACCESS  not-accessible
		STATUS  mandatory
		DESCRIPTION
		"ODU Possible TDM Services table."
		::= { winlink1000IduService 11 }

	winlink1000IduSrvAvailServicesEntry OBJECT-TYPE
		SYNTAX  Winlink1000IduSrvAvailServicesEntry
		ACCESS  not-accessible
		STATUS  mandatory
		DESCRIPTION
		"ODU TDM Services table entry."
		INDEX { winlink1000IduSrvAvailServicesIndex }
		::= { winlink1000IduSrvAvailServicesTable 1 }

	Winlink1000IduSrvAvailServicesEntry ::= SEQUENCE {
		winlink1000IduSrvAvailServicesIndex
			INTEGER,
		winlink1000IduSrvAvailServicesState
			INTEGER,
		winlink1000IduSrvAvailServicesMinRateIdx
			INTEGER,
		winlink1000IduSrvAvailServicesMaxRateIdx
			INTEGER,
		winlink1000IduSrvAvailServicesReason
			INTEGER
		}

	winlink1000IduSrvAvailServicesIndex OBJECT-TYPE
		SYNTAX  INTEGER
		ACCESS  read-only
		STATUS  mandatory
		DESCRIPTION
		"Table index. The index is the bit mask of the TDM service."
		::= { winlink1000IduSrvAvailServicesEntry 1 }

	winlink1000IduSrvAvailServicesState OBJECT-TYPE
		SYNTAX  INTEGER {
			unavailable(1),
			available(2)
		}
		ACCESS  read-only
		STATUS  mandatory
		DESCRIPTION
		"Represents the TDM service availability."
		::= { winlink1000IduSrvAvailServicesEntry 2 }

	winlink1000IduSrvAvailServicesMinRateIdx OBJECT-TYPE
		SYNTAX  INTEGER 
		ACCESS  read-only
		STATUS  mandatory
		DESCRIPTION
		"Minimum rate index of the air interface which make the service possible."
		::= { winlink1000IduSrvAvailServicesEntry 3 }

	winlink1000IduSrvAvailServicesMaxRateIdx OBJECT-TYPE 
		SYNTAX  INTEGER 
		ACCESS  read-only
		STATUS  mandatory
		DESCRIPTION
		"Maximum rate index of the air interface which make the service possible."
		::= { winlink1000IduSrvAvailServicesEntry 4 }
		
	winlink1000IduSrvAvailServicesReason OBJECT-TYPE 
		SYNTAX  INTEGER {
				notApplicable(1),
				insufficientThroughput(2),
				notSupportedIDUHw(3),
				inconsistentLinkParams(4),
				improperExtPulseType(5),
				incompatibleSWVersion(6),
				asymmetricTDD(7)
		}
		ACCESS  read-only
		STATUS  mandatory
		DESCRIPTION
		"Information about the TDM Service availability.
		 - Not Applicable if the service is available.
		 The reasons for TDM Service unavailability:
		 - The available throughput isn't sufficient for Service demands;
		 - The IDU HW doesn't support the service;
		 - A Link Password mismatch was detected;
		 - The external pulse type detected is improper for TDM services;
		 - A Software versions mismatch was detected.
		 - A-Symetric TDD Mode Is Obligated."
		::= { winlink1000IduSrvAvailServicesEntry 5 }

	winlink1000IduSrvEthActive OBJECT-TYPE
		SYNTAX  INTEGER {
			inactive(1),
			active(2)
		}
		ACCESS  read-only
		STATUS  mandatory
		DESCRIPTION
		"Represents the Ethernet service activation state."
		::= { winlink1000IduService 12 }

	winlink1000IduSrvEthAvailable OBJECT-TYPE
		SYNTAX  INTEGER {
			unavailable(1),
			available(2)
		}
		ACCESS  read-only
		STATUS  mandatory
		DESCRIPTION
		"Represents the Ethernet service availability state."
		::= { winlink1000IduService 13 }

	winlink1000IduSrvEthThroughput OBJECT-TYPE
		SYNTAX  Gauge
		ACCESS  read-only
		STATUS  mandatory
		DESCRIPTION
		"Current available Ethernet service throughput in bps."
		::= { winlink1000IduService 14 }

	winlink1000IduSrvEthMaxInfoRate OBJECT-TYPE
		SYNTAX  INTEGER (0..122880)
		ACCESS  read-write
		STATUS  mandatory
		DESCRIPTION
		"Holds the maximum bandwidth (kbps) to be allocated for Ethernet service.
		 Value of zero means that Ethernet service works as best effort.
		 The maximum value is product specific. Refer to the user manual."
		::= { winlink1000IduService 15 }

	winlink1000IduSrvAvailableTrunksT1 OBJECT-TYPE
		SYNTAX INTEGER
		ACCESS  read-only
		STATUS  mandatory
		DESCRIPTION
		"A bitmap describing the TDM trunks that can be opened under T1 configuration. 
		The values take into account the IDU hardware configuration, the air rate and the installation range."
		::= { winlink1000IduService 16 }
	
	-- ###########################################################
	--                      IDU Ethernet
	-- ###########################################################

	winlink1000IduEthernet OBJECT IDENTIFIER ::= { winlink1000Idu 3 }

	-- ###########################################################
	--                      IDU Ethernet Interface Table
	-- ###########################################################

	winlink1000IduEthernetIfTable OBJECT-TYPE
		SYNTAX  SEQUENCE OF Winlink1000IduEthernetIfEntry
		ACCESS  not-accessible
		STATUS  mandatory
		DESCRIPTION
		"IDU Ethernet Interface table."
		::= { winlink1000IduEthernet 1 }

	winlink1000IduEthernetIfEntry OBJECT-TYPE
		SYNTAX  Winlink1000IduEthernetIfEntry
		ACCESS  not-accessible
		STATUS  mandatory
		DESCRIPTION
		"IDU Ethernet Interface table entry."
		INDEX { winlink1000IduEthernetIfIndex }
		::= { winlink1000IduEthernetIfTable 1 }

	Winlink1000IduEthernetIfEntry ::= SEQUENCE {
		winlink1000IduEthernetIfIndex
			INTEGER,
		winlink1000IduEthernetIfAddress
			DisplayString
		}

	winlink1000IduEthernetIfIndex OBJECT-TYPE
		SYNTAX  INTEGER
		ACCESS  read-only
		STATUS  mandatory
		DESCRIPTION
		"If Index corresponding to this Interface."
		::= { winlink1000IduEthernetIfEntry 1 }
	
	winlink1000IduEthernetIfAddress OBJECT-TYPE
		SYNTAX  DisplayString
		ACCESS  read-only
		STATUS  mandatory
		DESCRIPTION
		"IDU MAC address."
		::= { winlink1000IduEthernetIfEntry 5 }	

	winlink1000IduEthernetNumOfLanPorts OBJECT-TYPE
		SYNTAX  INTEGER
		ACCESS  read-only
		STATUS  mandatory
		DESCRIPTION
		"Number of LAN interfaces in the IDU."
		::= { winlink1000IduEthernet 3 }

	winlink1000IduEthernetNumOfSfpPorts OBJECT-TYPE
		SYNTAX  INTEGER
		ACCESS  read-only
		STATUS  mandatory
		DESCRIPTION
		"The number of SFP interfaces in the IDU."
		::= { winlink1000IduEthernet 4 }

	winlink1000IduEthernetSfpProperties OBJECT-TYPE
		SYNTAX  DisplayString
		ACCESS  read-only
		STATUS  mandatory
		DESCRIPTION
		"SFP venfor properties : Vendor Name, PN and Revision."
		::= { winlink1000IduEthernet 5 }

	winlink1000IduEthernetGbeSupported OBJECT-TYPE
		SYNTAX  INTEGER {notSupported(1), supported(2)}
		ACCESS  read-only
		STATUS  mandatory
		DESCRIPTION
		"Supported Giga bit Ethernet in IDU."
		::= { winlink1000IduEthernet 6 }		

	winlink1000IduEthernetOduInErrors OBJECT-TYPE
		SYNTAX  Counter
		ACCESS  read-only
		STATUS  mandatory
		DESCRIPTION
		"The number of inbound packets that contained errors preventing them from being deliverable to a higher-layer protocol."
		::= { winlink1000IduEthernet 7 }			
	
	-- ###########################################################
	--                      IDU Bridge
	-- ###########################################################

	winlink1000IduBridge OBJECT IDENTIFIER ::= { winlink1000Idu 4 }

	-- ###########################################################
	--                      IDU Bridge Tp
	-- ###########################################################

	winlink1000IduBridgeTp OBJECT IDENTIFIER ::= { winlink1000IduBridge 4 }	
												   
	winlink1000IduBridgeTpAging OBJECT-TYPE
		SYNTAX  INTEGER (1..1048575)
		ACCESS  read-write
		STATUS  mandatory
		DESCRIPTION
		"Timeout in seconds for aging. Note that for this parameter to be effective,
		the ODU must be configured to HUB mode. A change is effective immediately."
		::= { winlink1000IduBridgeTp 2 }

	-- ###########################################################
	--                      IDU TDM
	-- ###########################################################

	winlink1000IduTdm OBJECT IDENTIFIER ::= { winlink1000Idu 6 }

	winlink1000IduTdmTxClock OBJECT IDENTIFIER ::= { winlink1000IduTdm 1 }

	winlink1000IduTdmTxClockAvailStates OBJECT-TYPE
		SYNTAX  INTEGER (0..62)
		ACCESS  read-only
		STATUS  mandatory
		DESCRIPTION
		"Available states of the TDM Transmit Clock Control, each input status is represented by a bit.
		When the state is available, the bit value is 1. When the state is unavailable, the bit 
		value is 0.
		The available states are:		
		bit 2 = Transparent
		bit 3 = Local Loop Timed
		bit 4 = Remote Loop Timed
		bit 5 = Local Internal
		bit 6 = Remote Internal"
		::= { winlink1000IduTdmTxClock 1 }

	winlink1000IduTdmTxClockDesiredState OBJECT-TYPE
		SYNTAX  INTEGER {
			transparent(2),
			localLT(4),
			remoteLT(8),
			localInternal(16),
			remoteInternal(32),
			multipleClock(64)
			}
		ACCESS  read-write
		STATUS  mandatory
		DESCRIPTION
		"Required state of the TDM Transmit Clock Control. A change is effective after re-activation of the TDM service."
		::= { winlink1000IduTdmTxClock 2 }

	winlink1000IduTdmTxClockActualState OBJECT-TYPE
		SYNTAX  INTEGER {
			notAvailable(1),
			transparent(2),
			localLT(4),
			remoteLT(8),
			localInternal(16),
			remoteInternal(32),
			multipleClock(64)
			}
		ACCESS  read-only
		STATUS  mandatory
		DESCRIPTION
		"Actual state of the TDM Transmit Clock Control."
		::= { winlink1000IduTdmTxClock 3 }

	winlink1000IduTdmMasterClock OBJECT IDENTIFIER ::= { winlink1000IduTdm 2 }

	winlink1000IduTdmMasterClockAvailOptions OBJECT-TYPE
		SYNTAX  INTEGER (0..62)
		ACCESS  read-only
		STATUS  mandatory
		DESCRIPTION
		"Available options of the TDM Master Clock Control, each input status is represented by a bit.
		When the option is available, the bit value is 1. When the option is unavailable, the bit value is 0.
		The available options are:		
		bit 2 = Automatic
		bit 3 = Trunk #1
		bit 4 = Trunk #2
		bit 5 = Trunk #3
		bit 6 = Trunk #4
		When no options are available the returned value is: 1"
		::= { winlink1000IduTdmMasterClock 1 }

	winlink1000IduTdmMasterClockDesired OBJECT-TYPE
		SYNTAX  INTEGER {
			automatic(2),
			trunk1(4),
			trunk2(8),
			trunk3(16),
			trunk4(32),
			multipleClocks(64)
			}
		ACCESS  read-write
		STATUS  mandatory
		DESCRIPTION
		"Required TDM Master Clock. A change is effective after re-activation of the TDM service."
		::= { winlink1000IduTdmMasterClock 2 }

	winlink1000IduTdmMasterClockActual OBJECT-TYPE
		SYNTAX  INTEGER {
			notAvailable(1),
			trunk1(4),
			trunk2(8),
			trunk3(16),
			trunk4(32),
			multipleClocks(64)
			}
		ACCESS  read-only
		STATUS  mandatory
		DESCRIPTION
		"Actual Trunk used for TDM Master Clock."
		::= { winlink1000IduTdmMasterClock 3 }

	-- ###########################################################
	--                      IDU TDM Links Configuration Table
	-- ###########################################################

	winlink1000IduTdmConfigTable OBJECT-TYPE
		SYNTAX  SEQUENCE OF Winlink1000IduTdmConfigEntry
		ACCESS  not-accessible
		STATUS  mandatory
		DESCRIPTION
		"IDU TDM Links Configuration table."
		::= { winlink1000IduTdm 6 }

	winlink1000IduTdmConfigEntry OBJECT-TYPE
		SYNTAX  Winlink1000IduTdmConfigEntry
		ACCESS  not-accessible
		STATUS  mandatory
		DESCRIPTION
		"IDU TDM Links Configuration table entry."
		INDEX { winlink1000IduTdmConfigIndex }
		::= { winlink1000IduTdmConfigTable 1 }

	Winlink1000IduTdmConfigEntry ::= SEQUENCE {
		winlink1000IduTdmConfigIndex
			INTEGER,
		winlink1000IduTdmIfIndex
			INTEGER,
		winlink1000IduTdmLineCoding
			INTEGER,
		winlink1000IduTdmLoopbackConfig
			INTEGER,
		winlink1000IduTdmLineStatus
			INTEGER
		}

	winlink1000IduTdmConfigIndex OBJECT-TYPE
		SYNTAX  INTEGER
		ACCESS  read-only
		STATUS  mandatory
		DESCRIPTION
		"Table index."
		::= { winlink1000IduTdmConfigEntry 1 }

	winlink1000IduTdmIfIndex OBJECT-TYPE
		SYNTAX  INTEGER
		ACCESS  read-only
		STATUS  mandatory
		DESCRIPTION
		"Link index in the interface table."
		::= { winlink1000IduTdmConfigEntry 2 }

	winlink1000IduTdmLineCoding OBJECT-TYPE
		SYNTAX  INTEGER {
			b8zs (2),
			ami (5)
			}
		ACCESS  read-write
		STATUS  mandatory
		DESCRIPTION
		"This parameter applies to T1 trunks only. The parameter controls the line coding.
		Setting the value to each of the indices applies to all.
		A change is effective after the next open of the TDM service."
		::= { winlink1000IduTdmConfigEntry 6 }

	winlink1000IduTdmLoopbackConfig OBJECT-TYPE
		SYNTAX  INTEGER
			{ normal (1),
			  lineLoopBack (3),
			  revereseLineLoopBack (4)
			}
		ACCESS  read-write
		STATUS  mandatory
		DESCRIPTION
		"Loop back configuration table. Each of the trunks can be set Normal, Line loop back or Reverse line loop back.
		A change is effective immediately."
		::= { winlink1000IduTdmConfigEntry 9 }

	winlink1000IduTdmLineStatus OBJECT-TYPE
		SYNTAX  INTEGER 
			{ normal (1),
		 	  ais (8),
			  los (64),
			  loopback (128)
			}
		ACCESS  read-only
		STATUS  mandatory
		DESCRIPTION
		"Line status."
		::= { winlink1000IduTdmConfigEntry 10 }	

	-- ###########################################################
	--                      IDU TDM Links Statistics Table
	-- ###########################################################

	winlink1000IduTdmCurrentTable OBJECT-TYPE
		SYNTAX  SEQUENCE OF Winlink1000IduTdmCurrentEntry
		ACCESS  not-accessible
		STATUS  mandatory
		DESCRIPTION
		"IDU TDM Links Statistics table."
		::= { winlink1000IduTdm 7 }

	winlink1000IduTdmCurrentEntry OBJECT-TYPE
		SYNTAX  Winlink1000IduTdmCurrentEntry
		ACCESS  not-accessible
		STATUS  mandatory
		DESCRIPTION
		"IDU TDM Links Statistics table entry."
		INDEX { winlink1000IduTdmCurrentIndex }
		::= { winlink1000IduTdmCurrentTable 1 }

	Winlink1000IduTdmCurrentEntry ::= SEQUENCE {
		winlink1000IduTdmCurrentIndex
			INTEGER,
		winlink1000IduTdmCurrentBlocks
			Counter,
		winlink1000IduTdmCurrentDrops
			Counter,
		winlink1000IduTdmCurrentTxClock
			INTEGER,
		winlink1000IduTdmCurrentBlocksHigh
			Counter
		}

	winlink1000IduTdmCurrentIndex OBJECT-TYPE
		SYNTAX  INTEGER
		ACCESS  read-only
		STATUS  mandatory
		DESCRIPTION
		"Table index (Same as winlink1000IduTdmLineIndex)."
		::= { winlink1000IduTdmCurrentEntry 1 }

	winlink1000IduTdmCurrentBlocks OBJECT-TYPE
		SYNTAX  Counter
		ACCESS  read-only
		STATUS  mandatory
		DESCRIPTION
		"Number of correct blocks transmitted to the line."
		::= { winlink1000IduTdmCurrentEntry 101 }

	winlink1000IduTdmCurrentDrops OBJECT-TYPE
		SYNTAX  Counter
		ACCESS  read-only
		STATUS  mandatory
		DESCRIPTION
		"Number of error blocks transmitted to the line."
		::= { winlink1000IduTdmCurrentEntry 102 }

	winlink1000IduTdmCurrentTxClock OBJECT-TYPE
		SYNTAX  INTEGER {
			transparent(2),
			localLT(4),
			remoteLT(8),
			localInternal(16),
			remoteInternal(32)
			}
		ACCESS  read-write
		STATUS  mandatory
		DESCRIPTION
		"TDM Transmit Clock. A change is effective after re-activation of the TDM service."
		::= { winlink1000IduTdmCurrentEntry 103 }
		
	winlink1000IduTdmCurrentBlocksHigh OBJECT-TYPE
		SYNTAX  Counter
		ACCESS  read-only
		STATUS  mandatory
		DESCRIPTION
		"High part of the 64 bits counter Current Blocks"
		::= { winlink1000IduTdmCurrentEntry 104 }

	winlink1000IduTdmRemoteQual OBJECT-TYPE
		SYNTAX  INTEGER
		ACCESS  read-only
		STATUS  mandatory
		DESCRIPTION
		"Estimated average interval between error second events. 
		The valid values are 1-2^31 where a value of -1 is used to indicate an undefined state."
		::= { winlink1000IduTdm 8 }

	winlink1000IduTdmRemoteQualEval OBJECT-TYPE
		SYNTAX  INTEGER
		ACCESS  read-only
		STATUS  mandatory
		DESCRIPTION
		"Estimated average interval between error second events during evaluation process.
		The valid values are 1-2^31 where a value of -1 is used to indicate an undefined state."
		::= { winlink1000IduTdm 9 }

	winlink1000IduTdmSrvEval OBJECT-TYPE
		SYNTAX  INTEGER
		ACCESS  read-write
		STATUS  mandatory
		DESCRIPTION
		"Evaluated TDM service bit mask.
		Setting this parameter to value that is bigger than the activated TDM service bit mask 
		will execute the evaluation process for 30 seconds. 
		Setting this parameter to 0 will stop the evaluation process immediately."
		::= { winlink1000IduTdm 10 }

	winlink1000IduTdmBackupAvailableLinks OBJECT-TYPE
		SYNTAX  INTEGER
		ACCESS  read-only
		STATUS  mandatory
		DESCRIPTION
		"Number of TDM backup trunks."
		::= { winlink1000IduTdm 11 }

	-- ###########################################################
	--                      IDU TDM Backup Links Table
	-- ###########################################################

	winlink1000IduTdmBackupTable OBJECT-TYPE
		SYNTAX  SEQUENCE OF Winlink1000IduTdmBackupEntry
		ACCESS  not-accessible
		STATUS  mandatory
		DESCRIPTION
		"IDU TDM Links Statistics table."
		::= { winlink1000IduTdm 12 }

	winlink1000IduTdmBackupEntry OBJECT-TYPE
		SYNTAX  Winlink1000IduTdmBackupEntry
		ACCESS  not-accessible
		STATUS  mandatory
		DESCRIPTION
		"IDU TDM Links Statistics table entry."
		INDEX { winlink1000IduTdmBackupIndex }
		::= { winlink1000IduTdmBackupTable 1 }

	Winlink1000IduTdmBackupEntry ::= SEQUENCE {
		winlink1000IduTdmBackupIndex
			INTEGER,
		winlink1000IduTdmBackupMode
			INTEGER,
		winlink1000IduTdmBackupCurrentActiveLink
			INTEGER
		}

	winlink1000IduTdmBackupIndex OBJECT-TYPE
		SYNTAX  INTEGER (1..16)
		ACCESS  read-only
		STATUS  mandatory
		DESCRIPTION
		"Table index."
		::= { winlink1000IduTdmBackupEntry 1 }

	winlink1000IduTdmBackupMode OBJECT-TYPE
		SYNTAX  INTEGER {
			enableUseAirLinkAsBackupLink(1),
			enableUseExternalLinkAsBackupLink(2),			
			disableUseExternalLinkAsMainLink(3),
			disableUseAirLinkAsMainLink(4)
			}
		ACCESS  read-write
		STATUS  mandatory
		DESCRIPTION
		"TDM backup mode: Enable or Disable, where the 
		 main link is the air link or the external link.
		 Changes will be effective immediatly."
		::= { winlink1000IduTdmBackupEntry 2 }

	winlink1000IduTdmBackupCurrentActiveLink OBJECT-TYPE
		SYNTAX  INTEGER {
			notAvailable(1),
			airLinkIsActive(2),
			externalLinkIsActive(3),
			noLinkIsActive(4)
			}
		ACCESS  read-only
		STATUS  mandatory
		DESCRIPTION
		"TDM backup current active link: N/A, 
		 air link is active or external link is active."
		::= { winlink1000IduTdmBackupEntry 3 }
		
	winlink1000IduTdmJitterBufferSize OBJECT-TYPE
		SYNTAX  INTEGER
		ACCESS  read-write
		STATUS  mandatory
		DESCRIPTION
		"TDM Jitter Buffer Size.
		 The value must be between the minimum and the maximum TDM Jitter Buffer Size.  
		 The units are 0.1 x millisecond."
		::= { winlink1000IduTdm 13 }
		
	winlink1000IduTdmJitterBufferDefaultSize OBJECT-TYPE
		SYNTAX  INTEGER
		ACCESS  read-only
		STATUS  mandatory
		DESCRIPTION
		"TDM Jitter Buffer Default Size. The units are 0.1 x millisecond."
		::= { winlink1000IduTdm 14 }
		
	winlink1000IduTdmJitterBufferMinSize OBJECT-TYPE
		SYNTAX  INTEGER
		ACCESS  read-only
		STATUS  mandatory
		DESCRIPTION
		"TDM Jitter Buffer Minimum Size. The units are 0.1 x millisecond."
		::= { winlink1000IduTdm 15 }
		
	winlink1000IduTdmJitterBufferMaxSize OBJECT-TYPE
		SYNTAX  INTEGER
		ACCESS  read-only
		STATUS  mandatory
		DESCRIPTION
		"TDM Jitter Buffer Maximum Size. The units are 0.1 x millisecond."
		::= { winlink1000IduTdm 16 }
		
	winlink1000IduTdmJitterBufferSizeEval OBJECT-TYPE
		SYNTAX  INTEGER
		ACCESS  read-write
		STATUS  mandatory
		DESCRIPTION
		"TDM Jitter Buffer Size for evaluation. 
		 The value must be between the minimum and the maximum TDM Jitter Buffer Size. 
		 The units are 0.1 x millisecond."
		::= { winlink1000IduTdm 17 }

	winlink1000IduTdmType OBJECT-TYPE
		SYNTAX  INTEGER{
			unDefined(1),
			e1(2),
			t1(3)
			}
		ACCESS  read-write
		STATUS  mandatory
		DESCRIPTION
		"TDM Type (The value undefined is read-only)."
		::= { winlink1000IduTdm 18 }

	winlink1000IduTdmTypeEval OBJECT-TYPE
		SYNTAX  INTEGER{
			unDefined(1),
			e1(2),
			t1(3)
			}
		ACCESS  read-write
		STATUS  mandatory
		DESCRIPTION
		"TDM Type for evaluation."
		::= { winlink1000IduTdm 19 }

	winlink1000IduTdmLineStatusStr OBJECT-TYPE
		SYNTAX  DisplayString
		ACCESS  read-only
		STATUS  mandatory
		DESCRIPTION
		"Line status."
		::= { winlink1000IduTdm 20 }	

	winlink1000IduTdmHotStandbySupport OBJECT-TYPE
		SYNTAX  INTEGER{
			supported(1),
			notSupported(2)
			}
		ACCESS  read-only
		STATUS  mandatory
		DESCRIPTION
		"Indicates if Hot Standby is supported."
		::= { winlink1000IduTdm 21 }

	winlink1000IduTdmDesiredHotStandbyMode OBJECT-TYPE
		SYNTAX  INTEGER{
			primary(1),
			secondary(2),
			disabled(3)
			}
		ACCESS  read-write
		STATUS  mandatory
		DESCRIPTION
		"Desired Hot Standby Mode."
		::= { winlink1000IduTdm 22 }	

	winlink1000IduTdmHotStandbyOperationStatus OBJECT-TYPE
		SYNTAX  INTEGER{
			active(1),
			notActive(2)
			}
		ACCESS  read-only
		STATUS  mandatory
		DESCRIPTION
		"The Link Actual Status."
		::= { winlink1000IduTdm 23 }		
		
	winlink1000IduTdmBackupLinkConfiguration OBJECT-TYPE
		SYNTAX  INTEGER{
			independent(1),
			repeaterEnd(2),
			lineEnd(3)
			}
		ACCESS  read-write
		STATUS  mandatory
		DESCRIPTION
		"The current configuration of the backup link."
		::= { winlink1000IduTdm 24 }


	winlink1000IduTdmLineInterfaceConfiguration OBJECT-TYPE
		SYNTAX  INTEGER{
			balanced(1),
			unBalanced(2)
			}
		ACCESS  read-write
		STATUS  mandatory
		DESCRIPTION
		"TDM Line interface configuration."
		::= { winlink1000IduTdm 25 }

		
	winlink1000IduTdmLineImpedanceConfiguration OBJECT-TYPE
        	SYNTAX  INTEGER{
			standardT1(1),
			nonStandardT1(2)
            		}
        	ACCESS  read-write
        	STATUS  mandatory
        	DESCRIPTION
        	"TDM line impedance configuration (standardT1 - 100Ohm, nonStandardT1 - 110Ohm)
        	Applicable only for T1 TDM type."
        	::= { winlink1000IduTdm 26 }

		
	-- ###########################################################
	--                      HBS
	-- ###########################################################

	winlink1000Hbs OBJECT IDENTIFIER ::= { winlink1000 3 }

	-- ###########################################################
	--                      HBS Air
	-- ###########################################################

	winlink1000HbsAir OBJECT IDENTIFIER ::= { winlink1000Hbs 1 }
	
	winlink1000HbsAirState OBJECT-TYPE
		SYNTAX  INTEGER	{
			init				(1),
			bitFailed			(2),
			inactive			(3),
			spectrumMeasurement	(4),
			scanning			(5),
			cac					(6),
			transceiving		(7),
			standBy				(8)
			}
		ACCESS  read-only
		STATUS  mandatory
		DESCRIPTION
		"Holds the state of the HBS."
		::= { winlink1000HbsAir 1 }
		
	winlink1000HbsAirOpMode OBJECT-TYPE
		SYNTAX  INTEGER	{
			inactive			(1),
			active				(2)
			}
		ACCESS  read-write
		STATUS  mandatory
		DESCRIPTION
		"Holds the operation mode of the HBS."
		::= { winlink1000HbsAir 2 }
		
	winlink1000HbsAirAvailTimeSlots OBJECT-TYPE
		SYNTAX  INTEGER
		ACCESS  read-only
		STATUS  mandatory
		DESCRIPTION
		"This parameter holds the number of available time slots (not in use) in the air interface."
		::= { winlink1000HbsAir 3 }

	winlink1000HbsAirSectorCbwSupportedStr OBJECT-TYPE
		SYNTAX  DisplayString
		ACCESS  read-only
		STATUS  mandatory
		DESCRIPTION
		"Represents the channel bandwidth which is supported by the HBS and all connected HSUs."
		::= { winlink1000HbsAir 4 }
				
	winlink1000HbsAirCompressedMon OBJECT-TYPE
		SYNTAX  OCTET STRING
		ACCESS  read-only
		STATUS  mandatory
		DESCRIPTION
		"Holds HBS monitor data in compressed format:
		HBS Traffic Monitor
		In Bytes(4)
		Out Bytes(4)
		In Frames(4)
		Out Frames(4)
		HBS State (1)
		HBS Freq (4)
		Number of Links (2)
		EC Change Counter (4)
		Current Ratio (2)
		Total Air Frames (4)
		HBS Rx Rate in Kbps (4)
		HBS Tx Rate in Kbps (4)
		HBS Rx Rate in Fps (4)
		HBS Tx Rate in Fps (4)
		HBS Set Mode (1)
		HBS LAN 1 Rx Rate in Kbps (4)
		HBS LAN 1 Tx Rate in Kbps (4)
		HBS LAN 1 Rx Rate in Fps (4)
		HBS LAN 1 Tx Rate in Fps (4)
		HBS LAN 2 Rx Rate in Kbps (4)
		HBS LAN 2 Tx Rate in Kbps (4)
		HBS LAN 2 Rx Rate in Fps (4)
		HBS LAN 2 Tx Rate in Fps (4)
		SyncE Performance (1)."
		::= { winlink1000HbsAir 5 }		
		
	winlink1000HbsAirConf OBJECT IDENTIFIER ::= { winlink1000HbsAir 6 }	
			
	winlink1000HbsAirConfChanges OBJECT-TYPE
		SYNTAX	OCTET STRING(SIZE(16))
		ACCESS  read-only
		STATUS  mandatory
		DESCRIPTION
		"16 characters that represent 16 HSUs.
		Each time a configuration is been changed, increment the relevant character."
		::= { winlink1000HbsAirConf 1 }
		
	-- ###########################################################
	--                      HSUs Configuration Table
	-- ###########################################################		
	
	winlink1000HbsAirConfTable OBJECT-TYPE
		SYNTAX  SEQUENCE OF Winlink1000HbsAirConfEntry
		ACCESS  not-accessible
		STATUS  mandatory
		DESCRIPTION
		"Holds the table for all registered HSUs in the sector (16 entries)."
		::= { winlink1000HbsAirConf 2 }

	winlink1000HbsAirConfEntry OBJECT-TYPE
		SYNTAX  Winlink1000HbsAirConfEntry
		ACCESS  not-accessible
		STATUS  mandatory
		DESCRIPTION
		"HSUs configuration table entry."
		INDEX { winlink1000HbsAirConfIndex }
		::= { winlink1000HbsAirConfTable 1 }

	Winlink1000HbsAirConfEntry ::= SEQUENCE {
		winlink1000HbsAirConfIndex
			INTEGER,	
		winlink1000HbsAirConfUpMir
			INTEGER,
		winlink1000HbsAirConfDownMir
			INTEGER,		
		winlink1000HbsAirConfHsuName
			DisplayString,
		winlink1000HbsAirConfHsuLocation
			DisplayString,
		winlink1000HbsAirConfDualAntTxMode
			INTEGER,
		winlink1000HbsAirConfNumOfTs
			INTEGER,
		winlink1000HbsAirConfGeoLocation
			DisplayString,
		winlink1000HbsAirConfHsuType
			INTEGER,
		winlink1000HbsAirConfHsuLevel
			INTEGER,
		winlink1000HbsAirConfDesiredRateIndex
			INTEGER,
		winlink1000HbsAirConfMacAddress
			DisplayString,
		winlink1000HbsAirConfNumOfTsUp
			INTEGER,
		winlink1000HbsAirConfLanPortsConnection
			INTEGER,
		winlink1000HbsAirConfServiceCategory
			INTEGER,
		winlink1000HbsAirConfAutoRealignmentConfiguration
			DisplayString,
		winlink1000HbsAirConfBeaconRssSyncLossThreshold
			INTEGER
		}
		
	winlink1000HbsAirConfIndex OBJECT-TYPE
		SYNTAX  INTEGER
		ACCESS  read-only
		STATUS  mandatory
		DESCRIPTION
		"HSUs configuration table index."
		::= { winlink1000HbsAirConfEntry 1 }
		
	winlink1000HbsAirConfUpMir OBJECT-TYPE
		SYNTAX  INTEGER
		ACCESS  read-write
		STATUS  mandatory
		DESCRIPTION
		"Uplink MIR towards specific HSU in units of kbps."
		::= { winlink1000HbsAirConfEntry 2 }
		
	winlink1000HbsAirConfDownMir OBJECT-TYPE
		SYNTAX  INTEGER
		ACCESS  read-write
		STATUS  mandatory
		DESCRIPTION
		"Downlink MIR towards specific HSU in units of kbps."
		::= { winlink1000HbsAirConfEntry 3 }
			
	winlink1000HbsAirConfHsuName OBJECT-TYPE
		SYNTAX  DisplayString
		ACCESS  read-write
		STATUS  mandatory
		DESCRIPTION
		"HSU name."
		::= { winlink1000HbsAirConfEntry 4 }
		
	winlink1000HbsAirConfHsuLocation OBJECT-TYPE
		SYNTAX  DisplayString
		ACCESS  read-write
		STATUS  mandatory
		DESCRIPTION
		"HSU location."
		::= { winlink1000HbsAirConfEntry 5 }
		
	winlink1000HbsAirConfDualAntTxMode OBJECT-TYPE
		SYNTAX  INTEGER	{
			mimo			(1),
			diversity		(2),
			autoSelection	(3)
			}
		ACCESS  read-write
		STATUS  mandatory
		DESCRIPTION
		"Transmission type when using Dual Antenna on both link's sides. 
		 spatial Multiplexing, Diversity (using a single spatial stream), and
		 Auto Selection (OMS control)."
		::= { winlink1000HbsAirConfEntry 6 }
		
	winlink1000HbsAirConfNumOfTs OBJECT-TYPE
		SYNTAX  INTEGER
		ACCESS  read-write
		STATUS  mandatory
		DESCRIPTION
		"Number of time slot which are allocated to specific HSU."
		::= { winlink1000HbsAirConfEntry 7 }
		
	winlink1000HbsAirConfGeoLocation OBJECT-TYPE
		SYNTAX  DisplayString
		ACCESS  read-write
		STATUS  mandatory
		DESCRIPTION
		"Geographic device location in format: 	latitude,longitude."
		::= { winlink1000HbsAirConfEntry 8 }

	winlink1000HbsAirConfHsuType OBJECT-TYPE
		SYNTAX  INTEGER	{
			fixed		(1),
			stationary	(2),
			mobile		(3),
			transport	(4)
			}
		ACCESS  read-write
		STATUS  mandatory
		DESCRIPTION
		"HSU type (1 = Fixed, 2 = Stationary, 3 = Mobile, 4 = Transport)"
		::= { winlink1000HbsAirConfEntry 9 }
		
	winlink1000HbsAirConfHsuLevel OBJECT-TYPE
		SYNTAX  INTEGER
		ACCESS  read-write
		STATUS  mandatory
		DESCRIPTION
		"HSU level (1 .. 4)"
		::= { winlink1000HbsAirConfEntry 10 }
		
	winlink1000HbsAirConfDesiredRateIndex OBJECT-TYPE
		SYNTAX  INTEGER
		ACCESS  read-write
		STATUS  mandatory
		DESCRIPTION
		"The rate index of both sides of the link to this HSU."
		::= { winlink1000HbsAirConfEntry 11 }
		
	winlink1000HbsAirConfMacAddress OBJECT-TYPE
		SYNTAX  DisplayString
		ACCESS  read-only
		STATUS  mandatory
		DESCRIPTION
		"HSU MAC Address."
		::= { winlink1000HbsAirConfEntry 12 }
		
	winlink1000HbsAirConfNumOfTsUp OBJECT-TYPE
		SYNTAX  INTEGER
		ACCESS  read-write
		STATUS  mandatory
		DESCRIPTION
		"Number of UL time slot which are allocated to specific HSU."
		::= { winlink1000HbsAirConfEntry 13 }
		
	winlink1000HbsAirConfLanPortsConnection OBJECT-TYPE
		SYNTAX  INTEGER	{
				enabled (1),
				disabled (2)
			}
		ACCESS  read-write
		STATUS  mandatory
		DESCRIPTION
		"Indicates if the connection between LAN 1 and LAN 2 is enabled. 1- Enabled , 2- Disabled."
		::= { winlink1000HbsAirConfEntry 14 }
		
	winlink1000HbsAirConfServiceCategory OBJECT-TYPE
		SYNTAX  INTEGER
		ACCESS  read-only
		STATUS  mandatory
		DESCRIPTION
		"Indicates Service Category received from Radius server,values can be from 1 to 8 , 0 - undefined"
		::= { winlink1000HbsAirConfEntry 15 }
		
	winlink1000HbsAirConfAutoRealignmentConfiguration OBJECT-TYPE
		SYNTAX  DisplayString
		ACCESS  read-write
		STATUS  mandatory
		DESCRIPTION
		"Configuration Parameters For Auto Realignment."
		::= { winlink1000HbsAirConfEntry 16 }
		
	
	winlink1000HbsAirConfBeaconRssSyncLossThreshold OBJECT-TYPE
		SYNTAX  INTEGER
		ACCESS  read-write
		STATUS  mandatory
		DESCRIPTION
		"RSS Threshold For Syncloss In Mobile Units"
		::= { winlink1000HbsAirConfEntry 17 }
	
	-- ###########################################################
	--     Beacon Rss SyncLoss Threshold Table
	-- ###########################################################
	
	winlink1000HbsAirConfBeaconRssSyncLossInterval OBJECT-TYPE
		SYNTAX  INTEGER
		ACCESS  read-write
		STATUS  mandatory
		DESCRIPTION
		"Interval over which the RSS value is below the threshold."
		::= { winlink1000HbsAirConf 3 }
		

	-- ###########################################################
	--                      Sector Links Table
	-- ###########################################################			
	winlink1000HbsAirLink OBJECT IDENTIFIER ::= { winlink1000HbsAir 7 }
	
	winlink1000HbsAirLinkNumOfLinks OBJECT-TYPE
		SYNTAX  INTEGER
		ACCESS  read-only
		STATUS  mandatory
		DESCRIPTION
		"Number of links in the links table."
		::= { winlink1000HbsAirLink 1 }
		
	winlink1000HbsAirLinkTable OBJECT-TYPE
		SYNTAX  SEQUENCE OF Winlink1000HbsAirLinkEntry
		ACCESS  not-accessible
		STATUS  mandatory
		DESCRIPTION
		"Holds the table for all links in the sector."
		::= { winlink1000HbsAirLink 2 }		
		
	winlink1000HbsAirLinkEntry OBJECT-TYPE
		SYNTAX  Winlink1000HbsAirLinkEntry
		ACCESS  not-accessible
		STATUS  mandatory
		DESCRIPTION
		"Link table entry."
		INDEX { winlink1000HbsAirLinkIndex }
		::= { winlink1000HbsAirLinkTable 1 }

	Winlink1000HbsAirLinkEntry ::= SEQUENCE {
		winlink1000HbsAirLinkIndex
			INTEGER,
		winlink1000HbsAirLinkHsuId
			INTEGER,
		winlink1000HbsAirLinkState
			INTEGER,
		winlink1000HbsAirLinkWorkingMode
			INTEGER,
		winlink1000HbsAirLinkSessionId
			INTEGER,
		winlink1000HbsAirLinkHbsEstTput
			INTEGER,
		winlink1000HbsAirLinkHsuEstTput
			INTEGER,
		winlink1000HbsAirLinkRange
			INTEGER,
		winlink1000HbsAirLinkHbsRss
			INTEGER,
		winlink1000HbsAirLinkHbsRssBal
			INTEGER,
		winlink1000HbsAirLinkHsuRss
			INTEGER,
		winlink1000HbsAirLinkHsuRssBal
			INTEGER,
		winlink1000HbsAirLinkHsuSerial
			DisplayString,
		winlink1000HbsAirLinkTxOperMode
			INTEGER,
		winlink1000HbsAirHsuInBytes
			INTEGER,
		winlink1000HbsAirHsuOutBytes
			INTEGER,
		winlink1000HbsAirHsuInFrames
			INTEGER,
		winlink1000HbsAirHsuOutFrames
			INTEGER,
		winlink1000HbsAirHsuMacAddress
			DisplayString,
		winlink1000HbsAirMaxTputDown
			INTEGER,
		winlink1000HbsAirMaxTputUp
			INTEGER,
		winlink1000HbsAirLinkCompressedMon
			OCTET STRING,
		winlink1000HbsAirLinkCompressedStatic
			DisplayString,
		winlink1000HbsAirCpeCapacityLimit
			INTEGER,
		winlink1000HbsAirLinkAntennaType
			INTEGER,
		winlink1000HbsAirHsuRxRateInKbps
			INTEGER,
		winlink1000HbsAirHsuTxRateInKbps
			INTEGER,
		winlink1000HbsAirHsuRxRateInFps
			INTEGER,
		winlink1000HbsAirHsuTxRateInFps
			INTEGER,
		winlink1000HbsAirLinkPeakTputDown
			INTEGER,
		winlink1000HbsAirLinkPeakTputUp
			INTEGER,
		winlink1000HbsAirLinkUtilDownSecRelMill
			INTEGER,
		winlink1000HbsAirLinkUtilUpSecRelMill
			INTEGER,
		winlink1000HbsAirLinkUtilDownAllocRelMill
			INTEGER,
		winlink1000HbsAirLinkUtilUpAllocRelMill
			INTEGER,
		winlink1000HbsAirLinkUtilDownTrafficKbps
			INTEGER,
		winlink1000HbsAirLinkUtilUpTrafficKbps
			INTEGER,
		winlink1000HbsAirLinkUtilCompressedMon
			OCTET STRING,
		winlink1000HbsAirLinkBsaAzimuth
			INTEGER,
		winlink1000HbsAirLink1588TCPerformance
			INTEGER,
		winlink1000HbsAirLinkSyncEPerformance
			INTEGER
		}
		
	winlink1000HbsAirLinkIndex OBJECT-TYPE
		SYNTAX  INTEGER
		ACCESS  read-only
		STATUS  mandatory
		DESCRIPTION
		"HSUs configuration table index."
		::= { winlink1000HbsAirLinkEntry 1 }
		
	winlink1000HbsAirLinkHsuId OBJECT-TYPE
		SYNTAX  INTEGER
		ACCESS  read-only
		STATUS  mandatory
		DESCRIPTION
		"HSU ID of specific link (if registered). Unregistered links have -1."
		::= { winlink1000HbsAirLinkEntry 2 }
		
	winlink1000HbsAirLinkState OBJECT-TYPE
		SYNTAX  INTEGER	{
			noSync 				(1),
			violated			(2),
			syncUnregistered		(3),
			syncRegistered			(4),
			authenticationError		(5),
			swUpgradeRequired		(6),
			syncRegisteredPassive		(7)
			}
		ACCESS  read-only
		STATUS  mandatory
		DESCRIPTION
		"Holds the state of specific link."
		::= { winlink1000HbsAirLinkEntry 3 }
		
	winlink1000HbsAirLinkWorkingMode OBJECT-TYPE
		SYNTAX  INTEGER {
			unknown(1),
			normal(2),
			fullCompatibilityRemoteUpgradeAvailable(3),
			fullCompatibilityLocalUpgradeAvailable(4),
			restrictedCompatibilityRemoteUpgradeRecomended(5),
			restrictedCompatibilityLocalUpgradeRecomended(6),
			softwareUpgradeRemoteUpgradeRequired(7),
			softwareUpgradeLocalUpgradeRequired(8),
			versionsIncompatibilityRemoteUpgradeRequired(9),
			versionsIncompatibilityLocalUpgradeRequired(10)
		}
		ACCESS  read-only
		STATUS  mandatory
		DESCRIPTION
		"Indicates the sub-state within the version compatibility."
		::= { winlink1000HbsAirLinkEntry 4 }
				
	winlink1000HbsAirLinkSessionId OBJECT-TYPE
		SYNTAX  INTEGER
		ACCESS  read-only
		STATUS  mandatory
		DESCRIPTION
		"Holds the Session ID of the link."
		::= { winlink1000HbsAirLinkEntry 5 }
		
	winlink1000HbsAirLinkHbsEstTput OBJECT-TYPE
		SYNTAX  INTEGER
		ACCESS  read-only
		STATUS  mandatory
		DESCRIPTION
		"Holds the Estimated throughput from the HBS to the HSU."
		::= { winlink1000HbsAirLinkEntry 6 }
		
	winlink1000HbsAirLinkHsuEstTput OBJECT-TYPE
		SYNTAX  INTEGER
		ACCESS  read-only
		STATUS  mandatory
		DESCRIPTION
		"Holds the Estimated throughput from the HSU to the HBS."
		::= { winlink1000HbsAirLinkEntry 7 }		

	winlink1000HbsAirLinkRange OBJECT-TYPE
		SYNTAX  INTEGER
		ACCESS  read-only
		STATUS  mandatory
		DESCRIPTION
		"Holds the range of specific link."
		::= { winlink1000HbsAirLinkEntry 8 }		
	
	winlink1000HbsAirLinkHbsRss OBJECT-TYPE
		SYNTAX  INTEGER
		ACCESS  read-only
		STATUS  mandatory
		DESCRIPTION
		"Holds the RSS of specific link (HBS side)."
		::= { winlink1000HbsAirLinkEntry 9 }
	
	winlink1000HbsAirLinkHbsRssBal OBJECT-TYPE
		SYNTAX  INTEGER
		ACCESS  read-only
		STATUS  mandatory
		DESCRIPTION
		"Holds the RSS Balance of specific link (HBS side).
		-2 : Radio 2 RSS is much stronger than Radio 1 RSS.
		-1 : Radio 2 RSS is stronger than Radio 1 RSS.
		-0 : Radio 2 RSS is equal to Radio 1 RSS.
		1  : Radio 1 RSS is stronger than Radio 2 RSS.
		2  : Radio 1 RSS is much stronger than Radio 2 RSS."
		::= { winlink1000HbsAirLinkEntry 10 }
		
	winlink1000HbsAirLinkHsuRss OBJECT-TYPE
		SYNTAX  INTEGER
		ACCESS  read-only
		STATUS  mandatory
		DESCRIPTION
		"Holds the RSS of specific link (HSU side)."
		::= { winlink1000HbsAirLinkEntry 11 }
	
	winlink1000HbsAirLinkHsuRssBal OBJECT-TYPE
		SYNTAX  INTEGER
		ACCESS  read-only
		STATUS  mandatory
		DESCRIPTION
		"Holds the RSS Balance of specific link (HSU side).
		-2 : Radio 2 RSS is much stronger than Radio 1 RSS.
		-1 : Radio 2 RSS is stronger than Radio 1 RSS.
		-0 : Radio 2 RSS is equal to Radio 1 RSS.
		1  : Radio 1 RSS is stronger than Radio 2 RSS.
		2  : Radio 1 RSS is much stronger than Radio 2 RSS."
		::= { winlink1000HbsAirLinkEntry 12 }
		
	winlink1000HbsAirLinkHsuSerial OBJECT-TYPE
		SYNTAX  DisplayString
		ACCESS  read-only
		STATUS  mandatory
		DESCRIPTION
		"Holds the serial number for specific HSU."
		::= { winlink1000HbsAirLinkEntry 13 }		

	winlink1000HbsAirLinkTxOperMode OBJECT-TYPE
		SYNTAX  INTEGER	{
			regularMode (1),
			measurementMode	(2)
			}
		ACCESS  read-only
		STATUS  mandatory
		DESCRIPTION
		"Holds the TX operation mode."
		::= { winlink1000HbsAirLinkEntry 14 }
		
	winlink1000HbsAirHsuInBytes OBJECT-TYPE
		SYNTAX  INTEGER
		ACCESS  read-only
		STATUS  mandatory
		DESCRIPTION
		"Number of frames received in the HSU Lan port."
		::= { winlink1000HbsAirLinkEntry 15 }
		
	winlink1000HbsAirHsuOutBytes OBJECT-TYPE
		SYNTAX  INTEGER
		ACCESS  read-only
		STATUS  mandatory
		DESCRIPTION
		"Number of frames transmitted from the HSU Lan port."
		::= { winlink1000HbsAirLinkEntry 16 }
		
	winlink1000HbsAirHsuInFrames OBJECT-TYPE
		SYNTAX  INTEGER
		ACCESS  read-only
		STATUS  mandatory
		DESCRIPTION
		"Number of bytes received in the HSU Lan port."
		::= { winlink1000HbsAirLinkEntry 17 }
		
	winlink1000HbsAirHsuOutFrames OBJECT-TYPE
		SYNTAX  INTEGER
		ACCESS  read-only
		STATUS  mandatory
		DESCRIPTION
		"Number of bytes transmitted from the HSU Lan port."
		::= { winlink1000HbsAirLinkEntry 18 }		
		
	winlink1000HbsAirHsuMacAddress OBJECT-TYPE
		SYNTAX  DisplayString
		ACCESS  read-only
		STATUS  mandatory
		DESCRIPTION
		"HSU MAC Address."
		::= { winlink1000HbsAirLinkEntry 19 }
		
	winlink1000HbsAirMaxTputDown OBJECT-TYPE
		SYNTAX  INTEGER
		ACCESS  read-only
		STATUS  mandatory
		DESCRIPTION
		"Max Throughput Downlink."
		::= { winlink1000HbsAirLinkEntry 20 }
		
	winlink1000HbsAirMaxTputUp OBJECT-TYPE
		SYNTAX  INTEGER
		ACCESS  read-only
		STATUS  mandatory
		DESCRIPTION
		"Max Throughput Uplink."
		::= { winlink1000HbsAirLinkEntry 21 }	

	winlink1000HbsAirLinkCompressedMon OBJECT-TYPE
		SYNTAX	OCTET STRING
		ACCESS  read-only
		STATUS  mandatory
		DESCRIPTION
		"Holds all the link information in compressed binary (Bytes/octets).
		Fields included (size in bytes):
		Link State(1)										
		Link Working Mode(1)								
		Session Id(4)										
		HBS Est. Tput(4)									
		HSU Est. Tput(4)									
		HBS Rss(1)											
		HBS Rss Balance(1)									
		HSU Rss(1)											
		HSU Rss Balance(1)									
		Tx Operation Mode(1)								
		HSU In Bytes(4)										
		HSU Out Bytes(4)									
		HSU In Frames(4)									
		HSU Out Frames(4)									
		HSU ID (1 bytes)
		HSU Rx Rate In Kbps (4)
		HSU Tx Rate In Kbps (4)
		HSU Rx Rate In Fps (4)
		HSU Tx Rate In Fps (4)
		Peak throughput in the DL direction (4)
		Peak throughput in the UL direction (4)
		Number of local changes at HSU(1)
		Alignment Status(1)
		HBS Chain 1 Rss(1)
		HBS Chain 2 Rss(1)
		HBS Chain 3 Rss(1)
		HSU Chain 1 Rss(1)
		HSU Chain 2 Rss(1)
		HSU Chain 3 Rss(1)
		HSU Current Rate Index (2 bytes)
		HSU Current Rate CBW (1 bytes)
		HSU Current Rate GI (1 bytes)
		HBS Current Rate Index (2 bytes)
		HBS Current Rate CBW (1 bytes)
		HBS Current Rate GI (1 bytes)
		Bsa Azimuth(2)
		HSU LAN 1 Rx Rate In Kbps (4)
		HSU LAN 1 Tx Rate In Kbps (4)
		HSU LAN 1 Rx Rate In Fps (4)
		HSU LAN 1 Tx Rate In Fps (4)
		HSU LAN 2 Rx Rate In Kbps (4)
		HSU LAN 2 Tx Rate In Kbps (4)
		HSU LAN 2 Rx Rate In Fps (4)
		HSU LAN 2 Tx Rate In Fps (4)
		1588TC Performance(1)
		SyncE Performance(1)
		ATPC status (1)
		"
		::= { winlink1000HbsAirLinkEntry 22 }
		
	winlink1000HbsAirLinkCompressedStatic OBJECT-TYPE
		SYNTAX	DisplayString
		ACCESS  read-only
		STATUS  mandatory
		DESCRIPTION
		"Holds all the configuration data of this link in compressed format.
		Helps the NMS to get info regarding new Unregistered links.
		Fields Included:
		SessionID (4 bytes)
		HSU IP address (4 bytes)
		HSU Name (32 bytes)
		HSU Location (32 bytes)
		HSU Serial number (16 bytes)		
		HSU MAC Address (12 bytes)
		Air Link Range
		Max Throughput Down (4 bytes)
		Max Throughput Up. (4 bytes)
		Cpacity Limit (4 bytes)
		HSU Antenna type (1 byte)
		Aggregate Capacity (4 bytes)
		1588TC supported (1 byte)
		SyncE supported (1 byte)"
		::= { winlink1000HbsAirLinkEntry 23 }				
		
				
	winlink1000HbsAirCpeCapacityLimit OBJECT-TYPE
		SYNTAX  INTEGER
		ACCESS  read-only
		STATUS  mandatory
		DESCRIPTION
		"Capacity Limit in Kilo bit per second."
		::= { winlink1000HbsAirLinkEntry 24 }

	winlink1000HbsAirLinkAntennaType OBJECT-TYPE
		SYNTAX  INTEGER {
			single(1), 
			dual(2), 
			undefined(3),
			triple(4)
			}
		ACCESS  read-only
		STATUS  mandatory
		DESCRIPTION
		"HSU External Antenna Type: Monopolar or Bipolar."
		::= { winlink1000HbsAirLinkEntry 25 }
		
	winlink1000HbsAirHsuRxRateInKbps OBJECT-TYPE
		SYNTAX  INTEGER
		ACCESS  read-only
		STATUS  mandatory
		DESCRIPTION
		"HSU Rx Rate in Kbps."
		::= { winlink1000HbsAirLinkEntry 26 }

	winlink1000HbsAirHsuTxRateInKbps OBJECT-TYPE
		SYNTAX  INTEGER
		ACCESS  read-only
		STATUS  mandatory
		DESCRIPTION
		"HSU Tx Rate in Kbps."
		::= { winlink1000HbsAirLinkEntry 27 }
		
	winlink1000HbsAirHsuRxRateInFps OBJECT-TYPE
		SYNTAX  INTEGER
		ACCESS  read-only
		STATUS  mandatory
		DESCRIPTION
		"HSU Tx Rate in Fps."
		::= { winlink1000HbsAirLinkEntry 28 }
	
	winlink1000HbsAirHsuTxRateInFps OBJECT-TYPE
		SYNTAX  INTEGER
		ACCESS  read-only
		STATUS  mandatory
		DESCRIPTION
		"HSU Tx Rate in Fps."
		::= { winlink1000HbsAirLinkEntry 29 }		
	
	winlink1000HbsAirLinkPeakTputDown OBJECT-TYPE
		SYNTAX  INTEGER
		ACCESS  read-only
		STATUS  mandatory
		DESCRIPTION
		"Peak throughput in the DL direction (kbps)."
		::= { winlink1000HbsAirLinkEntry 30 }
		
	winlink1000HbsAirLinkPeakTputUp OBJECT-TYPE
		SYNTAX  INTEGER
		ACCESS  read-only
		STATUS  mandatory
		DESCRIPTION
		"Peak throughput in the UL direction (kbps)."
		::= { winlink1000HbsAirLinkEntry 31 }
		
	winlink1000HbsAirLinkUtilDownSecRelMill OBJECT-TYPE
		SYNTAX  INTEGER
		ACCESS  read-only
		STATUS  mandatory
		DESCRIPTION
		"The average time percentage (in thousandths), out of the BTS DL capability,
		that was used for transmitting data to the SU."
		::= { winlink1000HbsAirLinkEntry 32 }
	
	winlink1000HbsAirLinkUtilUpSecRelMill OBJECT-TYPE
		SYNTAX  INTEGER
		ACCESS  read-only
		STATUS  mandatory
		DESCRIPTION
		"The average time percentage (in thousandths), out of the BTS UL capability,
		that was used for receiving data from the SU."
		::= { winlink1000HbsAirLinkEntry 33 }	
		
	winlink1000HbsAirLinkUtilDownAllocRelMill OBJECT-TYPE
		SYNTAX  INTEGER
		ACCESS  read-only
		STATUS  mandatory
		DESCRIPTION
		"The time percentage (in thousandths), relative to the SU DL allocation,
		that was used for transmitting data to the SU."
		::= { winlink1000HbsAirLinkEntry 34 }
		
	winlink1000HbsAirLinkUtilUpAllocRelMill OBJECT-TYPE
		SYNTAX  INTEGER
		ACCESS  read-only
		STATUS  mandatory
		DESCRIPTION
		"The time percentage (in thousandths), relative to the SU UL allocation,
		that was used for receiving data from the SU."
		::= { winlink1000HbsAirLinkEntry 35 }	
		
	winlink1000HbsAirLinkUtilDownTrafficKbps OBJECT-TYPE
		SYNTAX  INTEGER
		ACCESS  read-only
		STATUS  mandatory
		DESCRIPTION
		"Average data throughput (Exported in Kbps) transmitted in the DL
		towards the SU during the last second."
		::= { winlink1000HbsAirLinkEntry 36 }
		
	winlink1000HbsAirLinkUtilUpTrafficKbps OBJECT-TYPE
		SYNTAX  INTEGER
		ACCESS  read-only
		STATUS  mandatory
		DESCRIPTION
		"Average data throughput (Exported in Kbps) received in the UL
		from the SU during the last second."
		::= { winlink1000HbsAirLinkEntry 37 }
		
	winlink1000HbsAirLinkUtilCompressedMon OBJECT-TYPE
		SYNTAX	OCTET STRING
		ACCESS  read-only
		STATUS  mandatory
		DESCRIPTION
		"One string that holds the 6 Utilization per link values:
		DownSecRel     (2 bytes)
		UpSecRel       (2 bytes)
		DownAllocRel   (4 bytes)
		UpAllocRel     (4 bytes)
		DownTraffic    (4 bytes)
		UpTraffic      (4 bytes)."
		::= { winlink1000HbsAirLinkEntry 38 }
		
	winlink1000HbsAirLinkBsaAzimuth OBJECT-TYPE
		SYNTAX  INTEGER
		ACCESS  read-only
		STATUS  mandatory
		DESCRIPTION
		"Absolute (geographical) azimuth of the HSU (looking from HBS site)."
		::= { winlink1000HbsAirLinkEntry 39 }
		
	winlink1000HbsAirLink1588TCPerformance OBJECT-TYPE
		SYNTAX  INTEGER {
			high (1),
			low (2),
			notApplicable (3)
		}
		ACCESS  read-only
		STATUS  mandatory
		DESCRIPTION
		"TC  performance."
		::= { winlink1000HbsAirLinkEntry 40 }
		
	winlink1000HbsAirLinkSyncEPerformance OBJECT-TYPE
		SYNTAX  INTEGER {
			high (1),
			low (2),
			holdover (3),
			syncEFailure (4),
			notApplicable (5),
			refClk (6)
		}
		ACCESS  read-only
		STATUS  mandatory
		DESCRIPTION
		"SyncE  performance."
		::= { winlink1000HbsAirLinkEntry 41 }
			
	winlink1000HbsAirComboSwitchSectorFreqBandId OBJECT-TYPE
		SYNTAX  INTEGER
		ACCESS  read-write
		STATUS  mandatory
		DESCRIPTION
		"Switch Frequency band for the whole sector."
		::= { winlink1000HbsAir 8 }
		
	winlink1000HbsAirGeoAzimuth OBJECT-TYPE
		SYNTAX  INTEGER
		ACCESS  read-write
		STATUS  mandatory
		DESCRIPTION
		"Geographic sector azimuth in degrees * 10."
		::= { winlink1000HbsAir 9 }
		
	winlink1000HbsAirGeoBeamwidth OBJECT-TYPE
		SYNTAX  INTEGER
		ACCESS  read-write
		STATUS  mandatory
		DESCRIPTION
		"Geographic sector beamwidth in degrees * 10."
		::= { winlink1000HbsAir 10 }
		
	winlink1000HbsAirMaxDistanceMetersMobility OBJECT-TYPE
		SYNTAX  INTEGER
		ACCESS  read-write
		STATUS  mandatory
		DESCRIPTION
		"Maximum distance in meters. Used by Mobility links only."
		::= { winlink1000HbsAir 11 }
		
	winlink1000HbsAirComboSwitchSectorFreqBandIdStr OBJECT-TYPE
		SYNTAX  DisplayString
		ACCESS  read-write
		STATUS  mandatory
		DESCRIPTION
		"Switch Frequency band for the whole sector, overriding some of the Combo parameters."
		::= { winlink1000HbsAir 12 }
		
	winlink1000HbsAirTimeSlotAllocationBitmap OBJECT-TYPE
		SYNTAX  DisplayString
		ACCESS  read-write
		STATUS  mandatory
		DESCRIPTION
		"Time Slots Allocation Bitmap for the entire sector (Hex Value)."
		::= { winlink1000HbsAir 13 }
		
	winlink1000HbsAirAvailTimeSlotsUp OBJECT-TYPE
		SYNTAX  INTEGER
		ACCESS  read-only
		STATUS  mandatory
		DESCRIPTION
		"This parameter holds the number of available UL time slots (not in use) in the air interface."
		::= { winlink1000HbsAir 14 }

	winlink1000HbsAirDownUtilMill OBJECT-TYPE
		SYNTAX  INTEGER
		ACCESS  read-only
		STATUS  mandatory
		DESCRIPTION
		"Sector Air Interface utilization in the Downlink direction (thousandths).
		Average time percentage, out of the entire BTS DL capability,
		that was used for transmitting data to all the SUs."
		::= { winlink1000HbsAir 15 }
		
	winlink1000HbsAirUpUtilMill OBJECT-TYPE
		SYNTAX  INTEGER
		ACCESS  read-only
		STATUS  mandatory
		DESCRIPTION
		"Sector Air Interface utilization in the Uplink direction (thousandths).
		The average number of timeslots that were used in the UL (by all the links)
		out of the entire number of timeslots."
		::= { winlink1000HbsAir 16 }
		
	winlink1000HbsAirDownTrafficKbps OBJECT-TYPE
		SYNTAX  INTEGER
		ACCESS  read-only
		STATUS  mandatory
		DESCRIPTION
		"Average data throughput (expressed in Kbps) transmitted in the DL
		towards all the SUs during the last second."
		::= { winlink1000HbsAir 17 }
		
	winlink1000HbsAirUpTrafficKbps OBJECT-TYPE
		SYNTAX  INTEGER
		ACCESS  read-only
		STATUS  mandatory
		DESCRIPTION
		"Average data throughput (expressed in Kbps) received in the UL
		from all the SUs during the last second."
		::= { winlink1000HbsAir 18 }
		
	winlink1000HbsAirCompressedMonSec OBJECT-TYPE
		SYNTAX  DisplayString
		ACCESS  read-only
		STATUS  mandatory
		DESCRIPTION
		"One string that holds the 4 Utilization per Sector values:
		DownUtil	(2 bytes),
		UpUtil  	(2 bytes),
		DownTraffic (4 bytes),
		UpTraffic 	(4 bytes)."
		::= { winlink1000HbsAir 19 }
		
	winlink1000HbsAirDelayVsTputOpt OBJECT-TYPE
		SYNTAX  INTEGER {
			delaySensitivity(1),
			throughputOptimized(2)
			}
		ACCESS  read-write
		STATUS  mandatory
		DESCRIPTION
		"Delay vs. Throughput optimization type:
		 1 = Delay sensitivity
		 2 = Throughput optimized"
		::= { winlink1000HbsAir 20 }

	winlink1000HbsAirUCBP OBJECT IDENTIFIER ::= { winlink1000HbsAir 21 }
	
	-- ###########################################################
	--                      UCBP section
	-- ###########################################################			
			
	winlink1000HbsAirUCBPMinCS OBJECT-TYPE
		SYNTAX  INTEGER
		ACCESS  read-write
		STATUS  mandatory
		DESCRIPTION
		"Minimal contention slot length used for UCBP algorithm (in ms.) between 5-20ms."
		::= { winlink1000HbsAirUCBP 1 }
		
	winlink1000HbsAirUCBPSharingPercentage OBJECT-TYPE
		SYNTAX  INTEGER
		ACCESS  read-write
		STATUS  mandatory
		DESCRIPTION
		"Sharing percentage used by UCBP algorithm (15-75)"
		::= { winlink1000HbsAirUCBP 2 }
			
		winlink1000HbsAirSingleHsuMode OBJECT-TYPE   
		SYNTAX  INTEGER {
			notApplicable(1),
			singleHsu(2),
			multipleHsus(3)
			}
		ACCESS  read-write
		STATUS  mandatory
		DESCRIPTION
		"Single HSU mode:
		 1 = Not Applicable
		 2 = Single HSU
		 3 = Multiple HSUs"
		::= { winlink1000HbsAir 22 }
		
	winlink1000HbsAirMobilityAzTrack OBJECT-TYPE
		SYNTAX  INTEGER
		ACCESS  read-only
		STATUS  mandatory
		DESCRIPTION
		"Azimuth tracking for mobility status:
		1 = Not applicable
		2 = Active
		3 = Impossible"
		::= { winlink1000HbsAir 23 }
		
	winlink1000HbsAirSyncEPerformance OBJECT-TYPE
		SYNTAX  INTEGER {
			high (1),
			low (2),
			holdover (3),
			syncEFailure (4),
			notApplicable (5),
			refClk (6)
		}
		ACCESS  read-only
		STATUS  mandatory
		DESCRIPTION
		"SyncE performance when HBS is not reference clock"
		::= { winlink1000HbsAir 24 }	
		
	winlink1000HbsAirAtpcEnable OBJECT-TYPE
		SYNTAX  INTEGER {
			off (1),
			static (2),
			dynamic (3),
			notSupported (4)
		}
		ACCESS  read-write
		STATUS  mandatory
		DESCRIPTION
		"ATPC mode (off, static or dynamic) status"
		::= { winlink1000HbsAir 25 }	
		
	winlink1000HbsAirAtpcTargetMCS OBJECT-TYPE
		SYNTAX  INTEGER
		ACCESS  read-write
		STATUS  mandatory
		DESCRIPTION
		"targetRate for ATPC operation (100-309)"
		::= { winlink1000HbsAir 26 }	
		
		
	winlink1000HbsAirAtpcMaxAllowedRate OBJECT-TYPE
		SYNTAX  INTEGER
		ACCESS  read-only
		STATUS  mandatory
		DESCRIPTION
		"Max allowed rate (will be 207 for N products and 209 for AC products)"
		::= { winlink1000HbsAir 27 }

	
	-- ###########################################################
	--                      ATPC target Rss Per Rate
	-- ###########################################################

	winlink1000HbsAirAtpcTargetRSSPerRateTable OBJECT-TYPE
		SYNTAX  SEQUENCE OF Winlink1000HbsAirAtpcMaxAllowedRateEntry
		ACCESS  not-accessible
		STATUS  mandatory
		DESCRIPTION
		"Table of Atpc Target Rss Per Rate."
		::= { winlink1000HbsAir 28 }

	winlink1000HbsAirAtpcMaxAllowedRateEntry OBJECT-TYPE
		SYNTAX  Winlink1000HbsAirAtpcMaxAllowedRateEntry
		ACCESS  not-accessible
		STATUS  mandatory
		DESCRIPTION
		"Atpc Target Rss Per Rate table entry."
		INDEX { winlink1000HbsAirAtpcTargetRSSPerRateIndex }
		::= { winlink1000HbsAirAtpcTargetRSSPerRateTable 1 }

	Winlink1000HbsAirAtpcMaxAllowedRateEntry ::= SEQUENCE {
		winlink1000HbsAirAtpcTargetRSSPerRateIndex
			INTEGER,
		winlink1000HbsAirAtpcTargetRSSPerRate
			INTEGER
		}

	winlink1000HbsAirAtpcTargetRSSPerRateIndex OBJECT-TYPE
		SYNTAX  INTEGER
		ACCESS  read-only
		STATUS  mandatory
		DESCRIPTION
		"Atpc Target Rss Per Rate Index."
		::= { winlink1000HbsAirAtpcMaxAllowedRateEntry 1 }

	winlink1000HbsAirAtpcTargetRSSPerRate OBJECT-TYPE
		SYNTAX  INTEGER
		ACCESS  read-only
		STATUS  mandatory
		DESCRIPTION
		"Atpc Target Rss Per Rate value."
		::= { winlink1000HbsAirAtpcMaxAllowedRateEntry 2 }

	winlink1000HbsAirMinimalTimeBetweenAutoRealignment OBJECT-TYPE   
		SYNTAX  INTEGER
		ACCESS  read-write
		STATUS  mandatory
		DESCRIPTION
		"Minimal time in seconds between two Automatic Realignment Processes"
		::= { winlink1000HbsAir 29 }
		
	-- ###########################################################
	--                      HBS Bridge
	-- ###########################################################

	winlink1000HbsBridge OBJECT IDENTIFIER ::= { winlink1000Hbs 2 }
	
	winlink1000HbsBridgeAgingTime OBJECT-TYPE
		SYNTAX  INTEGER
		ACCESS  read-write
		STATUS  mandatory
		DESCRIPTION
		"Timeout in seconds for aging."
		::= { winlink1000HbsBridge 1 }
		
	-- ###########################################################
	--                      HBS Bridge Vlan Table
	-- ###########################################################		
	
	winlink1000HbsBridgeVlanTable OBJECT-TYPE
		SYNTAX  SEQUENCE OF Winlink1000HbsBridgeVlanEntry
		ACCESS  not-accessible
		STATUS  mandatory
		DESCRIPTION
		"Holds the bridge Vlan operations towards all the registered HSUs."
		::= { winlink1000HbsBridge 2 }

	winlink1000HbsBridgeVlanEntry OBJECT-TYPE
		SYNTAX  Winlink1000HbsBridgeVlanEntry
		ACCESS  not-accessible
		STATUS  mandatory
		DESCRIPTION
		"HBS bridge Vlan table entry."
		INDEX { winlink1000HbsBridgeVlanIndex }
		::= { winlink1000HbsBridgeVlanTable 1 }

	Winlink1000HbsBridgeVlanEntry ::= SEQUENCE {
		winlink1000HbsBridgeVlanIndex
			INTEGER,	
		winlink1000HbsBridgeVlanIngress
			INTEGER,
		winlink1000HbsBridgeVlanEgress
			INTEGER,
		winlink1000HbsBridgeVlanFilterIn
			INTEGER,
		winlink1000HbsBridgeVlanFilterOut
			INTEGER,
		winlink1000HbsBridgeVlanDoubleTag
			INTEGER,
		winlink1000HbsBridgeVlanDefaultId
			INTEGER		
		}
		
	winlink1000HbsBridgeVlanIndex OBJECT-TYPE
		SYNTAX  INTEGER
		ACCESS  read-only
		STATUS  mandatory
		DESCRIPTION
		"HBS bridge Vlan table index."
		::= { winlink1000HbsBridgeVlanEntry 1 }
		
	winlink1000HbsBridgeVlanIngress OBJECT-TYPE
		SYNTAX  INTEGER	{
			transparent (1),
			tag	(2)
			}
		ACCESS  read-write
		STATUS  mandatory
		DESCRIPTION
		"HBS bridge Vlan ingress."
		::= { winlink1000HbsBridgeVlanEntry 2 }
		
	winlink1000HbsBridgeVlanEgress OBJECT-TYPE
		SYNTAX  INTEGER	{
			transparent (1),
			unTag	(2)
			}
		ACCESS  read-write
		STATUS  mandatory
		DESCRIPTION
		"HBS bridge Vlan egress."
		::= { winlink1000HbsBridgeVlanEntry 3 }
		
	winlink1000HbsBridgeVlanFilterIn OBJECT-TYPE
		SYNTAX  INTEGER	{
			on (1),
			off	(2)
			}
		ACCESS  read-write
		STATUS  mandatory
		DESCRIPTION
		"HBS bridge Vlan filter in."
		::= { winlink1000HbsBridgeVlanEntry 4 }
		
	winlink1000HbsBridgeVlanFilterOut OBJECT-TYPE
		SYNTAX  INTEGER	{
			on (1),
			off	(2)
			}
		ACCESS  read-write
		STATUS  mandatory
		DESCRIPTION
		"HBS bridge Vlan filter out."
		::= { winlink1000HbsBridgeVlanEntry 5 }
		
	winlink1000HbsBridgeVlanDoubleTag OBJECT-TYPE
		SYNTAX  INTEGER	{
			on (1),
			off	(2)
			}
		ACCESS  read-write
		STATUS  mandatory
		DESCRIPTION
		"HBS bridge Vlan double tag."
		::= { winlink1000HbsBridgeVlanEntry 6 }
		
	winlink1000HbsBridgeVlanDefaultId OBJECT-TYPE
		SYNTAX  INTEGER
		ACCESS  read-write
		STATUS  mandatory
		DESCRIPTION
		"HBS bridge Vlan default id."
		::= { winlink1000HbsBridgeVlanEntry 7 }
		
	-- ###########################################################
	--                      HBS Bridge Membership Table
	-- ###########################################################		
	
	winlink1000HbsBridgeMembershipTable OBJECT-TYPE
		SYNTAX  SEQUENCE OF Winlink1000HbsBridgeMembershipEntry
		ACCESS  not-accessible
		STATUS  mandatory
		DESCRIPTION
		"Holds the bridge membership relations for all the registered HSUs."
		::= { winlink1000HbsBridge 3 }

	winlink1000HbsBridgeMembershipEntry OBJECT-TYPE
		SYNTAX  Winlink1000HbsBridgeMembershipEntry
		ACCESS  not-accessible
		STATUS  mandatory
		DESCRIPTION
		"HBS bridge membership table entry."
		INDEX { winlink1000HbsBridgeMembershipIndex }
		::= { winlink1000HbsBridgeMembershipTable 1 }

	Winlink1000HbsBridgeMembershipEntry ::= SEQUENCE {
		winlink1000HbsBridgeMembershipIndex
			INTEGER,	
		winlink1000HbsBridgeMembershipState
			Gauge,
		winlink1000HbsBridgeMembershipState2nd
			Gauge
		}
		
	winlink1000HbsBridgeMembershipIndex OBJECT-TYPE
		SYNTAX  INTEGER
		ACCESS  read-only
		STATUS  mandatory
		DESCRIPTION
		"HBS bridge membership table index."
		::= { winlink1000HbsBridgeMembershipEntry 1 }
		
	winlink1000HbsBridgeMembershipState OBJECT-TYPE
		SYNTAX  Gauge
		ACCESS  read-write
		STATUS  mandatory
		DESCRIPTION
		"HBS bridge membership state bitmap.
		Each bit represents Blocked/Opened relation (membership) between two HSUs.
		Blocked=0 (bit), Opened=1 (bit). This object holds the relation to 32 HSUs."
		::= { winlink1000HbsBridgeMembershipEntry 2 }
	
	winlink1000HbsBridgeMembershipState2nd OBJECT-TYPE
		SYNTAX  Gauge
		ACCESS  read-write
		STATUS  mandatory
		DESCRIPTION
		"HBS bridge membership state bitmap.
		Each bit represents Blocked/Opened relation (membership) between HSU and LAN/Stack port of the HBS.
		Blocked=0 (bit), Opened=1 (bit). Only 2 bits are used."
		::= { winlink1000HbsBridgeMembershipEntry 3 }

	winlink1000HbsBridgeFloodOverloadProtect OBJECT-TYPE
		SYNTAX  INTEGER	{
				enabled (1),
				disabled (2)
			}
		ACCESS  read-write
		STATUS  mandatory
		DESCRIPTION
		"Flood overload protection 1- Enabled 2- Disabled."
		::= { winlink1000HbsBridge 4 }		
												
	-- ###########################################################
	--                      HBS Service
	-- ###########################################################

	winlink1000HbsService OBJECT IDENTIFIER ::= { winlink1000Hbs 3 }
	
	winlink1000HbsServiceCommandStr OBJECT-TYPE
		SYNTAX  DisplayString
		ACCESS  read-write
		STATUS  mandatory
		DESCRIPTION
		"Ability to perform special command in the HBS.
		Format (string): Operation, Index, Session, Param1, Param2,....| ParamN
		The index and SessionID can be uniting to one parameter.
		On registered HSU it is HSU-ID and on Unregistered it is Session-ID."
		::= { winlink1000HbsService 1 }	
		
	-- ###########################################################
	--                      HBS Service Vlan
	-- ###########################################################
	
	winlink1000HbsServiceVlan OBJECT IDENTIFIER ::= { winlink1000HbsService 2 }
	
	winlink1000HbsServiceVlanTable OBJECT-TYPE
		SYNTAX  SEQUENCE OF Winlink1000HbsServiceVlanEntry
		ACCESS  not-accessible
		STATUS  mandatory
		DESCRIPTION
		"Holds the Vlan operations towards all the registered HSUs."
		::= { winlink1000HbsServiceVlan 1 }
		
	winlink1000HbsServiceVlanEntry OBJECT-TYPE
		SYNTAX  Winlink1000HbsServiceVlanEntry
		ACCESS  not-accessible
		STATUS  mandatory
		DESCRIPTION
		"HBS service Vlan table entry."
		INDEX { winlink1000HbsServiceVlanIndex }
		::= { winlink1000HbsServiceVlanTable 1 }
		
	Winlink1000HbsServiceVlanEntry ::= SEQUENCE {
		winlink1000HbsServiceVlanIndex
			INTEGER,	
		winlink1000OduServiceVlanTblTag
			INTEGER,
		winlink1000OduServiceVlanTblPri
			INTEGER,
		winlink1000OduServiceVlanTblMajorMode
			INTEGER,
		winlink1000OduServiceVlanTblEgressMode
			INTEGER,
		winlink1000OduServiceVlanTblIngressMode
			INTEGER,
		winlink1000OduServiceVlanTblEgressFilter1
			INTEGER,
		winlink1000OduServiceVlanTblEgressFilter2
			INTEGER,
		winlink1000OduServiceVlanTblEgressFilter3
			INTEGER,
		winlink1000OduServiceVlanTblEgressFilter4
			INTEGER,
		winlink1000OduServiceVlanTblUntagFilteredBitmap
			INTEGER,
		winlink1000OduServiceVlanTblProviderTPID
			DisplayString,	
		winlink1000OduServiceVlan2TblTag
			INTEGER,
		winlink1000OduServiceVlan2TblPri
			INTEGER,
		winlink1000OduServiceVlan2TblMajorMode
			INTEGER,
		winlink1000OduServiceVlan2TblEgressMode
			INTEGER,
		winlink1000OduServiceVlan2TblIngressMode
			INTEGER,
		winlink1000OduServiceVlan2TblEgressFilter1
			INTEGER,
		winlink1000OduServiceVlan2TblEgressFilter2
			INTEGER,
		winlink1000OduServiceVlan2TblEgressFilter3
			INTEGER,
		winlink1000OduServiceVlan2TblEgressFilter4
			INTEGER,
		winlink1000OduServiceVlan2TblUntagFilteredBitmap
			INTEGER,
		winlink1000OduServiceVlan2TblProviderTPID
			DisplayString
		}
		
	winlink1000HbsServiceVlanIndex OBJECT-TYPE
		SYNTAX  INTEGER
		ACCESS  read-only
		STATUS  mandatory
		DESCRIPTION
		"HBS service Vlan table index."
		::= { winlink1000HbsServiceVlanEntry 1 }
		
	winlink1000OduServiceVlanTblTag OBJECT-TYPE
		SYNTAX  INTEGER	
		ACCESS  read-write
		STATUS  mandatory
		DESCRIPTION
		"The VID to be used when adding TAG or adding Provider"
		::= { winlink1000HbsServiceVlanEntry 2 }
		
	winlink1000OduServiceVlanTblPri OBJECT-TYPE
		SYNTAX  INTEGER	
		ACCESS  read-write
		STATUS  mandatory
		DESCRIPTION
		"The Vlan priority 0-7 to be used when adding TAG or adding Provider"
		::= { winlink1000HbsServiceVlanEntry 3 }
		
	winlink1000OduServiceVlanTblMajorMode OBJECT-TYPE
		SYNTAX  INTEGER	{
			none (1),
			tag	(2),
			provider(3)
			}
		ACCESS  read-write
		STATUS  mandatory
		DESCRIPTION
		"The Vlan major mode"
		::= { winlink1000HbsServiceVlanEntry 4 }
		
	winlink1000OduServiceVlanTblEgressMode OBJECT-TYPE
		SYNTAX  INTEGER	{
			none (1),
			untag(2),
			filter(3),
			untagFiltered(4)
			}
		ACCESS  read-write
		STATUS  mandatory
		DESCRIPTION
		"The Vlan mode in the Egress direction"
		::= { winlink1000HbsServiceVlanEntry 5 }
		
	winlink1000OduServiceVlanTblIngressMode OBJECT-TYPE
		SYNTAX  INTEGER	{
			none (1),
			tag(2)
			}	
		ACCESS  read-write
		STATUS  mandatory
		DESCRIPTION
		"The Vlan mode in the Ingress direction"
		::= { winlink1000HbsServiceVlanEntry 6 }
		
	winlink1000OduServiceVlanTblEgressFilter1 OBJECT-TYPE
		SYNTAX  INTEGER	
		ACCESS  read-write
		STATUS  mandatory
		DESCRIPTION
		"VLAN Filter1 VID "
		::= { winlink1000HbsServiceVlanEntry 7 }								
		
	winlink1000OduServiceVlanTblEgressFilter2 OBJECT-TYPE
		SYNTAX  INTEGER	
		ACCESS  read-write
		STATUS  mandatory
		DESCRIPTION
		"VLAN Filter2 VID "
		::= { winlink1000HbsServiceVlanEntry 8 }	
		
	winlink1000OduServiceVlanTblEgressFilter3 OBJECT-TYPE
		SYNTAX  INTEGER	
		ACCESS  read-write
		STATUS  mandatory
		DESCRIPTION
		"VLAN Filter3 VID "
		::= { winlink1000HbsServiceVlanEntry 9 }	
		
	winlink1000OduServiceVlanTblEgressFilter4 OBJECT-TYPE
		SYNTAX  INTEGER	
		ACCESS  read-write
		STATUS  mandatory
		DESCRIPTION
		"VLAN Filter4 VID "
		::= { winlink1000HbsServiceVlanEntry 10 }	
	
	winlink1000OduServiceVlanTblUntagFilteredBitmap OBJECT-TYPE
		SYNTAX  INTEGER	
		ACCESS  read-write
		STATUS  mandatory
		DESCRIPTION
		"Represents (in bitmap) if to Untag a frame after it is filtered (Egress direction) [4 bits represent 4 filters]."
		::= { winlink1000HbsServiceVlanEntry 11 }
		
	winlink1000OduServiceVlanTblProviderTPID OBJECT-TYPE
		SYNTAX  DisplayString	
		ACCESS  read-write
		STATUS  mandatory
		DESCRIPTION
		"Holds the Provider TPID that is used in all provider operations."
		::= { winlink1000HbsServiceVlanEntry 12 }
		
	winlink1000OduServiceVlan2TblTag OBJECT-TYPE
		SYNTAX  INTEGER	
		ACCESS  read-write
		STATUS  mandatory
		DESCRIPTION
		"The VID 2 to be used when adding TAG or adding Provider"
		::= { winlink1000HbsServiceVlanEntry 13 }
		
	winlink1000OduServiceVlan2TblPri OBJECT-TYPE
		SYNTAX  INTEGER	
		ACCESS  read-write
		STATUS  mandatory
		DESCRIPTION
		"The Vlan 2 priority 0-7 to be used when adding TAG or adding Provider"
		::= { winlink1000HbsServiceVlanEntry 14 }
		
	winlink1000OduServiceVlan2TblMajorMode OBJECT-TYPE
		SYNTAX  INTEGER	{
			none (1),
			tag	(2),
			provider(3)
			}
		ACCESS  read-write
		STATUS  mandatory
		DESCRIPTION
		"The Vlan 2 major mode"
		::= { winlink1000HbsServiceVlanEntry 15 }
		
	winlink1000OduServiceVlan2TblEgressMode OBJECT-TYPE
		SYNTAX  INTEGER	{
			none (1),
			untag(2),
			filter(3),
			untagFiltered(4)
			}
		ACCESS  read-write
		STATUS  mandatory
		DESCRIPTION
		"The Vlan 2 mode in the Egress direction"
		::= { winlink1000HbsServiceVlanEntry 16 }
		
	winlink1000OduServiceVlan2TblIngressMode OBJECT-TYPE
		SYNTAX  INTEGER	{
			none (1),
			tag(2)
			}	
		ACCESS  read-write
		STATUS  mandatory
		DESCRIPTION
		"The Vlan 2 mode in the Ingress direction"
		::= { winlink1000HbsServiceVlanEntry 17 }
		
	winlink1000OduServiceVlan2TblEgressFilter1 OBJECT-TYPE
		SYNTAX  INTEGER	
		ACCESS  read-write
		STATUS  mandatory
		DESCRIPTION
		"VLAN 2 Filter1 VID "
		::= { winlink1000HbsServiceVlanEntry 18 }								
		
	winlink1000OduServiceVlan2TblEgressFilter2 OBJECT-TYPE
		SYNTAX  INTEGER	
		ACCESS  read-write
		STATUS  mandatory
		DESCRIPTION
		"VLAN 2 Filter2 VID "
		::= { winlink1000HbsServiceVlanEntry 19 }	
		
	winlink1000OduServiceVlan2TblEgressFilter3 OBJECT-TYPE
		SYNTAX  INTEGER	
		ACCESS  read-write
		STATUS  mandatory
		DESCRIPTION
		"VLAN 2 Filter3 VID "
		::= { winlink1000HbsServiceVlanEntry 20 }	
		
	winlink1000OduServiceVlan2TblEgressFilter4 OBJECT-TYPE
		SYNTAX  INTEGER	
		ACCESS  read-write
		STATUS  mandatory
		DESCRIPTION
		"VLAN 2 Filter4 VID "
		::= { winlink1000HbsServiceVlanEntry 21 }	
	
	winlink1000OduServiceVlan2TblUntagFilteredBitmap OBJECT-TYPE
		SYNTAX  INTEGER	
		ACCESS  read-write
		STATUS  mandatory
		DESCRIPTION
		"Represents (in bitmap) if to Untag a frame after it is filtered (Egress direction) [4 bits represent 4 filters]."
		::= { winlink1000HbsServiceVlanEntry 22 }
		
	winlink1000OduServiceVlan2TblProviderTPID OBJECT-TYPE
		SYNTAX  DisplayString	
		ACCESS  read-write
		STATUS  mandatory
		DESCRIPTION
		"Holds the Provider TPID that is used in all provider operations."
		::= { winlink1000HbsServiceVlanEntry 23 }
		
	-- ###########################################################
	--                      HBS Service QoS
	-- ###########################################################
	
	winlink1000HbsServiceQoS OBJECT IDENTIFIER ::= { winlink1000HbsService 3 }
	
	winlink1000HbsServiceQoSMode OBJECT-TYPE
		SYNTAX  INTEGER {
			notSupported (1),
			notActive (2),
			classVlan (3),
			classDiffserv (4)
			}
		ACCESS  read-write
		STATUS  mandatory
		DESCRIPTION
		"Quality of Service mode."
		::= { winlink1000HbsServiceQoS 1 }
		
	winlink1000HbsServiceQoSVlanQGroupsStr OBJECT-TYPE
		SYNTAX  DisplayString
		ACCESS  read-write
		STATUS  mandatory
		DESCRIPTION
		"Frame classification according to VLAN priority (all 4 groups separated by comma)."
		::= { winlink1000HbsServiceQoS 2 }
	
	winlink1000HbsServiceQoSDiffservQGroupsStr OBJECT-TYPE
		SYNTAX  DisplayString
		ACCESS  read-write
		STATUS  mandatory
		DESCRIPTION
		"Frame classification according to Diffserv (all 4 groups separated by comma)."
		::= { winlink1000HbsServiceQoS 3 }
	
	winlink1000HbsServiceQoSMaxRtQuePct OBJECT-TYPE
		SYNTAX  INTEGER
		ACCESS  read-only
		STATUS  mandatory
		DESCRIPTION
		"Maximal percent for RT and NRT queues."
		::= { winlink1000HbsServiceQoS 4 }
		
	winlink1000HbsServiceQoSTable OBJECT-TYPE
		SYNTAX  SEQUENCE OF Winlink1000HbsServiceQoSEntry
		ACCESS  not-accessible
		STATUS  mandatory
		DESCRIPTION
		"Holds the QoS operations towards all the registered HSUs."
		::= { winlink1000HbsServiceQoS 5 }
		
	winlink1000HbsServiceQoSEntry OBJECT-TYPE
		SYNTAX  Winlink1000HbsServiceQoSEntry
		ACCESS  not-accessible
		STATUS  mandatory
		DESCRIPTION
		"HBS service QoS table entry."
		INDEX { winlink1000HbsServiceQoSIndex }
		::= { winlink1000HbsServiceQoSTable 1 }
		
	Winlink1000HbsServiceQoSEntry ::= SEQUENCE {
		winlink1000HbsServiceQoSIndex
			INTEGER,	
		winlink1000HbsServiceQoSConfAdminState
			INTEGER,
		winlink1000HbsServiceQoSConfUpQueMir
			DisplayString,
		winlink1000HbsServiceQoSConfUpQueWeight
			DisplayString,
		winlink1000HbsServiceQoSConfDownQueMir
			DisplayString,
		winlink1000HbsServiceQoSConfDownQueWeight
			DisplayString,
		winlink1000HbsServiceQoSUpTtlMs
			DisplayString,
		winlink1000HbsServiceQoSDownTtlMs
			DisplayString,
		winlink1000HbsServiceQoSUpStrict
			DisplayString,
		winlink1000HbsServiceQoSDownStrict
			DisplayString			
		}
		
	winlink1000HbsServiceQoSIndex OBJECT-TYPE
		SYNTAX  INTEGER
		ACCESS  read-only
		STATUS  mandatory
		DESCRIPTION
		"HBS service QoS table index."
		::= { winlink1000HbsServiceQoSEntry 1 }
		
	winlink1000HbsServiceQoSConfAdminState OBJECT-TYPE
		SYNTAX  INTEGER	{
				enabled (1),
				disabled (2)
			}
		ACCESS  read-write
		STATUS  mandatory
		DESCRIPTION
		"QoS administrative state. The valid values are: enabled (1), disabled (2)."
		::= { winlink1000HbsServiceQoSEntry 2 }
	
	winlink1000HbsServiceQoSConfUpQueMir OBJECT-TYPE
		SYNTAX  DisplayString	
		ACCESS  read-write
		STATUS  mandatory
		DESCRIPTION
		"Private MIR for each QoS group of the Uplink direction (4 values separated by comma)."
		::= { winlink1000HbsServiceQoSEntry 3 }
	
	winlink1000HbsServiceQoSConfUpQueWeight OBJECT-TYPE
		SYNTAX  DisplayString	
		ACCESS  read-write
		STATUS  mandatory
		DESCRIPTION
		"Weight in percent for each QoS group of the Uplink direction (4 values separated by comma)."
		::= { winlink1000HbsServiceQoSEntry 4 }
	
	winlink1000HbsServiceQoSConfDownQueMir OBJECT-TYPE
		SYNTAX  DisplayString	
		ACCESS  read-write
		STATUS  mandatory
		DESCRIPTION
		"Private MIR for each QoS group of the Downlink direction (4 values separated by comma)."
		::= { winlink1000HbsServiceQoSEntry 5 }
		
	winlink1000HbsServiceQoSConfDownQueWeight OBJECT-TYPE
		SYNTAX  DisplayString	
		ACCESS  read-write
		STATUS  mandatory
		DESCRIPTION
		"Weight in percent for each QoS group of the Downlink direction (4 values separated by comma)."
		::= { winlink1000HbsServiceQoSEntry 6 }
				
	winlink1000HbsServiceQoSUpTtlMs OBJECT-TYPE
		SYNTAX  DisplayString	
		ACCESS  read-write
		STATUS  mandatory
		DESCRIPTION
		"TTL in mili second for each QoS group of the Uplink direction (4 values separated by comma)."
		::= { winlink1000HbsServiceQoSEntry 7 }
						
	winlink1000HbsServiceQoSDownTtlMs  OBJECT-TYPE
		SYNTAX  DisplayString	
		ACCESS  read-write
		STATUS  mandatory
		DESCRIPTION
		"TTL in mili second for each QoS group of the Downlink direction (4 values separated by comma)."
		::= { winlink1000HbsServiceQoSEntry 8 }
		
	winlink1000HbsServiceQoSUpStrict OBJECT-TYPE
		SYNTAX  DisplayString	
		ACCESS  read-write
		STATUS  mandatory
		DESCRIPTION
		"Strict QOS Boolean indication for each QOS group of the Uplink direction (4 values separated by comma)."
		::= { winlink1000HbsServiceQoSEntry 9 }
		
	winlink1000HbsServiceQoSDownStrict OBJECT-TYPE
		SYNTAX  DisplayString	
		ACCESS  read-write
		STATUS  mandatory
		DESCRIPTION
		"Strict QOS Boolean indication for each QOS group of the Downlink direction (4 values separated by comma)."
		::= { winlink1000HbsServiceQoSEntry 10 }
		
	winlink1000HbsServiceMobilitySupported OBJECT-TYPE
		SYNTAX  INTEGER	{
			notSupported (1),
			supported (2),
			transportSupported (3)
		}
		ACCESS  read-only
		STATUS  mandatory
		DESCRIPTION
		"Mobility Support (1 = Not supported, 2 = Supported, 3 - Transport supported)"
		::= { winlink1000HbsService 4 }	
		
	winlink1000HbsServiceMaxNumOfHSUs OBJECT-TYPE
		SYNTAX  INTEGER
		ACCESS  read-only
		STATUS  mandatory
		DESCRIPTION
		"Holds the maximum number of registered HSUs in the HBS."
		::= { winlink1000HbsService 5 }
		
	-- ###########################################################
	--                      HBS Service Synchronization
	-- ###########################################################
	
	winlink1000HbsServiceSynchronization OBJECT IDENTIFIER ::= { winlink1000HbsService 6 }
	
	winlink1000HbsServiceSynchronization1588TCEnable OBJECT-TYPE
		SYNTAX  INTEGER {
			mandatoryDisabled (1),
			disabled (2),
			enabled (3)
		}
		ACCESS  read-write
		STATUS  mandatory
		DESCRIPTION
		"Enable/Disable PTP TC support. Value Mandatory Disabled is unchangeable."
		::= { winlink1000HbsServiceSynchronization 1 }
		
	winlink1000HbsServiceSynchronizationSyncEEnable OBJECT-TYPE
		SYNTAX  INTEGER {
			mandatoryDisabled (1),
			disabled (2),
			enabled (3)
		}
		ACCESS  read-write
		STATUS  mandatory
		DESCRIPTION
		"Enable/Disable SyncE support. Value Mandatory Disabled is unchangeable."
		::= { winlink1000HbsServiceSynchronization 2 }
		
	winlink1000HbsServiceSynchronizationSyncESSMGeneration OBJECT-TYPE
		SYNTAX  INTEGER {			
			disabled (1),
			enabled (2)
		}
		ACCESS  read-write
		STATUS  mandatory
		DESCRIPTION
		"Enable/Disable SyncE SSM Generation."
		::= { winlink1000HbsServiceSynchronization 3 }
		
	winlink1000HbsServiceSynchronizationSyncESupportedReferenceClock OBJECT-TYPE
		SYNTAX  DisplayString
		ACCESS  read-only
		STATUS  mandatory
		DESCRIPTION
		"List of valid Reference Clk HBS/HSU + Port ID."
		::= { winlink1000HbsServiceSynchronization 4 }
		
	winlink1000HbsServiceSynchronizationSyncEDesiredReferenceClock OBJECT-TYPE
		SYNTAX  DisplayString
		ACCESS  read-write
		STATUS  mandatory
		DESCRIPTION
		"Desired Reference Clk HBS/HSU + Port ID."
		::= { winlink1000HbsServiceSynchronization 5 }

	-- ###########################################################
	--                      HBS Radius
	-- ###########################################################
	
	winlink1000HbsServiceRadius OBJECT IDENTIFIER ::= { winlink1000HbsService 7 }
	
	winlink1000HbsServiceRadiusAuthorizationMode OBJECT-TYPE
		SYNTAX  INTEGER {
			disabled (1),
			enabled (2)
		}
		ACCESS  read-write
		STATUS  mandatory
		DESCRIPTION
		"Enables/Disables Radius Authorization, 1 - disable 2- enable"
		::= { winlink1000HbsServiceRadius 1 }
		
	winlink1000HbsServiceRadiusUserName OBJECT-TYPE
		SYNTAX  DisplayString
		ACCESS  read-write
		STATUS  mandatory
		DESCRIPTION
		"Radius client user Name"
		::= { winlink1000HbsServiceRadius 2 }
		
	winlink1000HbsServiceRadiusPassword OBJECT-TYPE
		SYNTAX  DisplayString
		ACCESS  read-write
		STATUS  mandatory
		DESCRIPTION
		"Radius client password"
		::= { winlink1000HbsServiceRadius 3 }
		
	winlink1000HbsServiceRadiusServerTable OBJECT-TYPE
		SYNTAX  SEQUENCE OF Winlink1000HbsServiceRadiusServerEntry
		ACCESS  not-accessible
		STATUS  mandatory
		DESCRIPTION
		"Holds the Radius Server configurations"
		::= { winlink1000HbsServiceRadius 4 }
		
	winlink1000HbsServiceRadiusServerEntry OBJECT-TYPE
		SYNTAX  Winlink1000HbsServiceRadiusServerEntry
		ACCESS  not-accessible
		STATUS  mandatory
		DESCRIPTION
		"HBS service Radius server table entry."
		INDEX { winlink1000HbsServiceRadiusServerIndex }
		::= { winlink1000HbsServiceRadiusServerTable 1 }
		
	Winlink1000HbsServiceRadiusServerEntry ::= SEQUENCE {
		winlink1000HbsServiceRadiusServerIndex
			INTEGER,
		winlink1000HbsServiceRadiusServerIpAddr
			IpAddress,
		winlink1000HbsServiceRadiusServerPort
			INTEGER,
		winlink1000HbsServiceRadiusServerSecret
			DisplayString,
		winlink1000HbsServiceRadiusServerConnectivity
			INTEGER,
		winlink1000HbsServiceRadiusServerNumberOfRetries
			INTEGER,
		winlink1000HbsServiceRadiusServerTimeout
			INTEGER			
		}
		
	winlink1000HbsServiceRadiusServerIndex OBJECT-TYPE
		SYNTAX  INTEGER
		ACCESS  read-only
		STATUS  mandatory
		DESCRIPTION
		"Radius Server table index."
		::= { winlink1000HbsServiceRadiusServerEntry 1 }
		
	winlink1000HbsServiceRadiusServerIpAddr OBJECT-TYPE
		SYNTAX  IpAddress
		ACCESS  read-write
		STATUS  mandatory
		DESCRIPTION
		"Radius server IP"
		::= { winlink1000HbsServiceRadiusServerEntry 2 }
		
	winlink1000HbsServiceRadiusServerPort OBJECT-TYPE
		SYNTAX  INTEGER
		ACCESS  read-write
		STATUS  mandatory
		DESCRIPTION
		"Radius server Port"
		::= { winlink1000HbsServiceRadiusServerEntry 3 }
		
	winlink1000HbsServiceRadiusServerSecret OBJECT-TYPE
		SYNTAX  DisplayString
		ACCESS  read-write
		STATUS  mandatory
		DESCRIPTION
		"Radius server Secret"
		::= { winlink1000HbsServiceRadiusServerEntry 4 }
		
	winlink1000HbsServiceRadiusServerConnectivity OBJECT-TYPE
		SYNTAX  INTEGER {
			success (1),
			noServerResponse (2),
			noServer (3),
			testing (4),
			badSecret (5),
			timeout (6)
		}
		ACCESS  read-write
		STATUS  mandatory
		DESCRIPTION
		"Radius server connectivity status"
		::= { winlink1000HbsServiceRadiusServerEntry 5 }
		
	winlink1000HbsServiceRadiusServerNumberOfRetries OBJECT-TYPE
		SYNTAX  INTEGER
		ACCESS  read-write
		STATUS  mandatory
		DESCRIPTION
		"Radius server number of retries"
		::= { winlink1000HbsServiceRadiusServerEntry 6 }
	
	winlink1000HbsServiceRadiusServerTimeout OBJECT-TYPE
		SYNTAX  INTEGER
		ACCESS  read-write
		STATUS  mandatory
		DESCRIPTION
		"Radius server timeout"
		::= { winlink1000HbsServiceRadiusServerEntry 7 }
	
	-- ###########################################################
	--                      HBS ServiceCategory
	-- ###########################################################
	
	winlink1000HbsServiceCategoryTable OBJECT-TYPE
		SYNTAX  SEQUENCE OF Winlink1000HbsServiceCategoryEntry
		ACCESS  not-accessible
		STATUS  mandatory
		DESCRIPTION
		"Holds the Radius Service Category profiles"
		::= { winlink1000HbsService 8 }
		
	winlink1000HbsServiceCategoryEntry OBJECT-TYPE
		SYNTAX  Winlink1000HbsServiceCategoryEntry
		ACCESS  not-accessible
		STATUS  mandatory
		DESCRIPTION
		"HBS service Radius Service Category table entry."
		INDEX { winlink1000HbsServiceCategoryIndex }
		::= { winlink1000HbsServiceCategoryTable 1 }
		
	Winlink1000HbsServiceCategoryEntry ::= SEQUENCE {
		winlink1000HbsServiceCategoryIndex
			INTEGER,
		winlink1000HbsServiceCategoryName
			DisplayString,
		winlink1000HbsServiceCategoryULResources
			INTEGER,
		winlink1000HbsServiceCategoryDLResources
			INTEGER,
		winlink1000HbsServiceCategoryULMir
			INTEGER,
		winlink1000HbsServiceCategoryDLMir
			INTEGER,
		winlink1000HbsServiceCategoryQoSUpQueMir
			DisplayString,
		winlink1000HbsServiceCategoryQoSUpQueWeight
			DisplayString,
		winlink1000HbsServiceCategoryQoSDownQueMir
			DisplayString,
		winlink1000HbsServiceCategoryQoSDownQueWeight
			DisplayString,
		winlink1000HbsServiceCategoryQoSUpTtlMs
			DisplayString,
		winlink1000HbsServiceCategoryQoSDownTtlMs
			DisplayString,
		winlink1000HbsServiceCategoryQoSUpStrict
			DisplayString,
		winlink1000HbsServiceCategoryQoSDownStrict
			DisplayString			
		}

	winlink1000HbsServiceCategoryIndex OBJECT-TYPE
		SYNTAX  INTEGER	
		ACCESS  read-write
		STATUS  mandatory
		DESCRIPTION
		"Service Category Index"
		::= { winlink1000HbsServiceCategoryEntry 1 }
		
	winlink1000HbsServiceCategoryName OBJECT-TYPE
		SYNTAX  DisplayString	
		ACCESS  read-write
		STATUS  mandatory
		DESCRIPTION
		"Service Category Name"
		::= { winlink1000HbsServiceCategoryEntry 2 }

	winlink1000HbsServiceCategoryULResources OBJECT-TYPE
		SYNTAX  INTEGER	
		ACCESS  read-write
		STATUS  mandatory
		DESCRIPTION
		"Service Category Uplink Resources"
		::= { winlink1000HbsServiceCategoryEntry 3 }
		
	winlink1000HbsServiceCategoryDLResources OBJECT-TYPE
		SYNTAX  INTEGER	
		ACCESS  read-write
		STATUS  mandatory
		DESCRIPTION
		"Service Category Downlink Resources"
		::= { winlink1000HbsServiceCategoryEntry 4 }
	
	winlink1000HbsServiceCategoryULMir OBJECT-TYPE
		SYNTAX  INTEGER	
		ACCESS  read-write
		STATUS  mandatory
		DESCRIPTION
		"Service Category Uplink MIR"
		::= { winlink1000HbsServiceCategoryEntry 5 }
		
	winlink1000HbsServiceCategoryDLMir OBJECT-TYPE
		SYNTAX  INTEGER	
		ACCESS  read-write
		STATUS  mandatory
		DESCRIPTION
		"Service Category Downlink MIR"
		::= { winlink1000HbsServiceCategoryEntry 6 }
	
	winlink1000HbsServiceCategoryQoSUpQueMir OBJECT-TYPE
		SYNTAX  DisplayString	
		ACCESS  read-write
		STATUS  mandatory
		DESCRIPTION
		"Private MIR for each QoS group of the Uplink direction (4 values separated by comma)."
		::= { winlink1000HbsServiceCategoryEntry 7 }
	
	winlink1000HbsServiceCategoryQoSUpQueWeight OBJECT-TYPE
		SYNTAX  DisplayString	
		ACCESS  read-write
		STATUS  mandatory
		DESCRIPTION
		"Weight in percent for each QoS group of the Uplink direction (4 values separated by comma)."
		::= { winlink1000HbsServiceCategoryEntry 8 }
	
	winlink1000HbsServiceCategoryQoSDownQueMir OBJECT-TYPE
		SYNTAX  DisplayString	
		ACCESS  read-write
		STATUS  mandatory
		DESCRIPTION
		"Private MIR for each QoS group of the Downlink direction (4 values separated by comma)."
		::= { winlink1000HbsServiceCategoryEntry 9 }
		
	winlink1000HbsServiceCategoryQoSDownQueWeight OBJECT-TYPE
		SYNTAX  DisplayString	
		ACCESS  read-write
		STATUS  mandatory
		DESCRIPTION
		"Weight in percent for each QoS group of the Downlink direction (4 values separated by comma)."
		::= { winlink1000HbsServiceCategoryEntry 10 }
				
	winlink1000HbsServiceCategoryQoSUpTtlMs OBJECT-TYPE
		SYNTAX  DisplayString	
		ACCESS  read-write
		STATUS  mandatory
		DESCRIPTION
		"TTL in mili second for each QoS group of the Uplink direction (4 values separated by comma)."
		::= { winlink1000HbsServiceCategoryEntry 11 }
						
	winlink1000HbsServiceCategoryQoSDownTtlMs  OBJECT-TYPE
		SYNTAX  DisplayString	
		ACCESS  read-write
		STATUS  mandatory
		DESCRIPTION
		"TTL in mili second for each QoS group of the Downlink direction (4 values separated by comma)."
		::= { winlink1000HbsServiceCategoryEntry 12 }
		
	winlink1000HbsServiceCategoryQoSUpStrict OBJECT-TYPE
		SYNTAX  DisplayString	
		ACCESS  read-write
		STATUS  mandatory
		DESCRIPTION
		"Strict QOS Boolean indication for each QOS group of the Uplink direction (4 values separated by comma)."
		::= { winlink1000HbsServiceCategoryEntry 13 }
		
	winlink1000HbsServiceCategoryQoSDownStrict OBJECT-TYPE
		SYNTAX  DisplayString	
		ACCESS  read-write
		STATUS  mandatory
		DESCRIPTION
		"Strict QOS Boolean indication for each QOS group of the Downlink direction (4 values separated by comma)."
		::= { winlink1000HbsServiceCategoryEntry 14 }
		
	-- ###########################################################
	--                      HBS PerfMon
	-- ###########################################################

	winlink1000HbsPerfMon OBJECT IDENTIFIER ::= { winlink1000Hbs 4 }
	
	-- ###########################################################
	--                      HBS PerfMon Threshold Table
	-- ###########################################################		
	
	winlink1000HbsPerfMonThreshTable OBJECT-TYPE
		SYNTAX  SEQUENCE OF Winlink1000HbsPerfMonThreshEntry
		ACCESS  not-accessible
		STATUS  mandatory
		DESCRIPTION
		"Holds the performance monitor thresholds towards all the registered HSUs."
		::= { winlink1000HbsPerfMon 1 }

	winlink1000HbsPerfMonThreshEntry OBJECT-TYPE
		SYNTAX  Winlink1000HbsPerfMonThreshEntry
		ACCESS  not-accessible
		STATUS  mandatory
		DESCRIPTION
		"HBS performance monitor threshold table entry."
		INDEX { winlink1000HbsPerfMonThreshIndex }
		::= { winlink1000HbsPerfMonThreshTable 1 }

	Winlink1000HbsPerfMonThreshEntry ::= SEQUENCE {
		winlink1000HbsPerfMonThreshIndex
			INTEGER,	
		winlink1000HbsPerfMonTxThresh1
			INTEGER,
		winlink1000HbsPerfMonRxThresh1
			INTEGER,
		winlink1000HbsPerfMonRxThresh2
			INTEGER,
		winlink1000HbsPerfMonBBERThresh1
			INTEGER,
		winlink1000HbsPerfMonEstThroughputThreshKbps
			INTEGER,
		winlink1000HbsPerfMonHighTrafficThreshKbps
			INTEGER		
		}
		
	winlink1000HbsPerfMonThreshIndex OBJECT-TYPE
		SYNTAX  INTEGER
		ACCESS  read-only
		STATUS  mandatory
		DESCRIPTION
		"HBS performance monitor threshold table index."
		::= { winlink1000HbsPerfMonThreshEntry 1 }
		
	winlink1000HbsPerfMonTxThresh1 OBJECT-TYPE
		SYNTAX  INTEGER
		ACCESS  read-write
		STATUS  mandatory
		DESCRIPTION
		"HBS performance monitor transmit power threshold."
		::= { winlink1000HbsPerfMonThreshEntry 2 }
		
	winlink1000HbsPerfMonRxThresh1 OBJECT-TYPE
		SYNTAX  INTEGER
		ACCESS  read-write
		STATUS  mandatory
		DESCRIPTION
		"HBS performance monitor receive power threshold 1."
		::= { winlink1000HbsPerfMonThreshEntry 3 }			
		
	winlink1000HbsPerfMonRxThresh2 OBJECT-TYPE
		SYNTAX  INTEGER
		ACCESS  read-write
		STATUS  mandatory
		DESCRIPTION
		"HBS performance monitor receive power threshold 2."
		::= { winlink1000HbsPerfMonThreshEntry 4 }	
		
	winlink1000HbsPerfMonBBERThresh1 OBJECT-TYPE
		SYNTAX  INTEGER
		ACCESS  read-write
		STATUS  mandatory
		DESCRIPTION
		"HBS performance monitor BBER threshold."
		::= { winlink1000HbsPerfMonThreshEntry 5 }	
		
	winlink1000HbsPerfMonEstThroughputThreshKbps OBJECT-TYPE
		SYNTAX  INTEGER
		ACCESS  read-write
		STATUS  mandatory
		DESCRIPTION
		"HBS performance monitor estimated throughput Threshold."
		::= { winlink1000HbsPerfMonThreshEntry 6 }	
		
	winlink1000HbsPerfMonHighTrafficThreshKbps OBJECT-TYPE
		SYNTAX  INTEGER
		ACCESS  read-write
		STATUS  mandatory
		DESCRIPTION
		"HBS performance monitor high traffic threshold."
		::= { winlink1000HbsPerfMonThreshEntry 7 }
		
		
	-- ###########################################################
	--                      PM Air General Current Table
	-- ###########################################################

	winlink1000HbsPerfMonAirGenCurrTable OBJECT-TYPE
		SYNTAX  SEQUENCE OF Winlink1000HbsPerfMonAirGenCurrEntry
		ACCESS  not-accessible
		STATUS  mandatory
		DESCRIPTION
		"This table defines/keeps the ethernet counters of the current 15 min interval."
		::= { winlink1000HbsPerfMon 2 }

	winlink1000HbsPerfMonAirGenCurrEntry OBJECT-TYPE
		SYNTAX  Winlink1000HbsPerfMonAirGenCurrEntry
		ACCESS  not-accessible
		STATUS  mandatory
		DESCRIPTION
		"This is an entry in the Current Interval Table."
		INDEX {ifIndex }
		::= { winlink1000HbsPerfMonAirGenCurrTable 1 }

	Winlink1000HbsPerfMonAirGenCurrEntry ::= SEQUENCE {
		winlink1000HbsPerfMonAirGenCurrRxMBytes
	      Gauge,
   		winlink1000HbsPerfMonAirGenCurrTxMBytes
	      Gauge,
		winlink1000HbsPerfMonAirGenCurrEthCapacityThreshUnder
	      Gauge,
		winlink1000HbsPerfMonAirGenCurrHighTrafficThreshExceed
	      Gauge,
		winlink1000HbsPerfMonAirGenCurrActiveSeconds
	      Gauge
	}

	winlink1000HbsPerfMonAirGenCurrRxMBytes OBJECT-TYPE
		SYNTAX  Gauge (0..11250)
		ACCESS  read-only
		STATUS  mandatory
		DESCRIPTION
		"Current RX Mega Bytes starting from the present 15 minutes period.
		(Represents the LAN traffic, RX direction, toward the HSU)"
		::= { winlink1000HbsPerfMonAirGenCurrEntry 1 }		

	winlink1000HbsPerfMonAirGenCurrTxMBytes OBJECT-TYPE
		SYNTAX  Gauge (0..11250)
		ACCESS  read-only
		STATUS  mandatory
		DESCRIPTION
		"Current Transmit Mega Bytes starting from the present 15 minutes period.
		(Represents the LAN traffic, TX direction, from the HSU)"
		::= { winlink1000HbsPerfMonAirGenCurrEntry 2 }	
		
	winlink1000HbsPerfMonAirGenCurrEthCapacityThreshUnder OBJECT-TYPE
		SYNTAX  Gauge (0..900)
		ACCESS  read-only
		STATUS  mandatory
		DESCRIPTION
		"The number of times throughput was below threshold in the present 15 minutes period.
		Relevant for point to point systems."
		::= { winlink1000HbsPerfMonAirGenCurrEntry 3 }
	
	winlink1000HbsPerfMonAirGenCurrHighTrafficThreshExceed OBJECT-TYPE
		SYNTAX  Gauge (0..900)
		ACCESS  read-only
		STATUS  mandatory
		DESCRIPTION
		"The number of times actual traffic was above threshold in the present 15 minutes period."
		::= { winlink1000HbsPerfMonAirGenCurrEntry 4 }
		
	winlink1000HbsPerfMonAirGenCurrActiveSeconds OBJECT-TYPE
		SYNTAX  Gauge (0..900)
		ACCESS  read-only
		STATUS  mandatory
		DESCRIPTION
		"The number of seconds in which RPL Ethernet swervice was not blocked in the present 15 minutes period."
		::= { winlink1000HbsPerfMonAirGenCurrEntry 5 }
	
	-- ###########################################################
	--                      PM Air General Interval Table
	-- ###########################################################	

	winlink1000HbsPerfMonAirGenIntervalTable OBJECT-TYPE
		SYNTAX  SEQUENCE OF Winlink1000HbsPerfMonAirGenIntervalEntry
		ACCESS  not-accessible
		STATUS  mandatory
		DESCRIPTION
		"This table defines/keeps the ethernet counters of the last day (in resolution of 15 min intervals)."
		::= { winlink1000HbsPerfMon 3 }

	winlink1000HbsPerfMonAirGenIntervalEntry OBJECT-TYPE
		SYNTAX  Winlink1000HbsPerfMonAirGenIntervalEntry
		ACCESS  not-accessible
		STATUS  mandatory
		DESCRIPTION
		"This is an entry in the Interval Table."
		INDEX {ifIndex, winlink1000HbsPerfMonAirGenIntervalIdx }
		::= { winlink1000HbsPerfMonAirGenIntervalTable 1 }

	Winlink1000HbsPerfMonAirGenIntervalEntry ::= SEQUENCE {
		winlink1000HbsPerfMonAirGenIntervalIdx
	      INTEGER,
		winlink1000HbsPerfMonAirGenIntervalRxMBytes
	      Gauge,
   		winlink1000HbsPerfMonAirGenIntervalTxMBytes
	      Gauge,
		winlink1000HbsPerfMonAirGenIntervalEthCapacityThreshUnder
	      Gauge,
		winlink1000HbsPerfMonAirGenIntervalHighTrafficThreshExceed
	      Gauge,
		winlink1000HbsPerfMonAirGenIntervalActiveSeconds
	      Gauge
	}

	winlink1000HbsPerfMonAirGenIntervalIdx OBJECT-TYPE
		SYNTAX  INTEGER (1..96)
		ACCESS  read-only
		STATUS  mandatory
		DESCRIPTION
		"This table is indexed per interval number. Each interval
		is of 15 minutes and the oldest is 96."
		::= { winlink1000HbsPerfMonAirGenIntervalEntry 1 }

	winlink1000HbsPerfMonAirGenIntervalRxMBytes OBJECT-TYPE
		SYNTAX  Gauge (0..11250)
		ACCESS  read-only
		STATUS  mandatory
		DESCRIPTION
		"Current RX Mega Bytes per interval.
		(Represents the LAN traffic, RX direction, toward the HSU)."
		::= { winlink1000HbsPerfMonAirGenIntervalEntry 2 }		

	winlink1000HbsPerfMonAirGenIntervalTxMBytes OBJECT-TYPE
		SYNTAX  Gauge (0..11250)
		ACCESS  read-only
		STATUS  mandatory
		DESCRIPTION
		"Current Transmit Mega Bytes per interval.
		(Represents the LAN traffic, TX direction, from the HSU)"
		::= { winlink1000HbsPerfMonAirGenIntervalEntry 3 }	
		
	winlink1000HbsPerfMonAirGenIntervalEthCapacityThreshUnder OBJECT-TYPE
		SYNTAX  Gauge (0..900)
		ACCESS  read-only
		STATUS  mandatory
		DESCRIPTION
		"The number of times throughput was below threshold in the each interval.
		Relevant for point to point systems."
		::= { winlink1000HbsPerfMonAirGenIntervalEntry 4 }	
		
	winlink1000HbsPerfMonAirGenIntervalHighTrafficThreshExceed OBJECT-TYPE
		SYNTAX  Gauge (0..900)
		ACCESS  read-only
		STATUS  mandatory
		DESCRIPTION
		"The number of times actual traffic was above threshold in the each interval."
		::= { winlink1000HbsPerfMonAirGenIntervalEntry 5 }	
		
	winlink1000HbsPerfMonAirGenIntervalActiveSeconds OBJECT-TYPE
		SYNTAX  Gauge (0..900)
		ACCESS  read-only
		STATUS  mandatory
		DESCRIPTION
		"The number of seconds in which RPL Ethernet service was not blocked in the each interval."
		::= { winlink1000HbsPerfMonAirGenIntervalEntry 6 }	
	
	-- ###########################################################
	--                      PM Air General Day Table
	-- ###########################################################	

	winlink1000HbsPerfMonAirGenDayTable OBJECT-TYPE
		SYNTAX  SEQUENCE OF Winlink1000HbsPerfMonAirGenDayEntry
		ACCESS  not-accessible
		STATUS  mandatory
		DESCRIPTION
		"This table defines/keeps the ethernet counters of the last month (in resolution of days)."
		::= { winlink1000HbsPerfMon 4 }

	winlink1000HbsPerfMonAirGenDayEntry OBJECT-TYPE
		SYNTAX  Winlink1000HbsPerfMonAirGenDayEntry
		ACCESS  not-accessible
		STATUS  mandatory
		DESCRIPTION
		"This is an entry in the Days Table."
		INDEX {ifIndex, winlink1000HbsPerfMonAirGenDayIdx }
		::= { winlink1000HbsPerfMonAirGenDayTable 1 }

	Winlink1000HbsPerfMonAirGenDayEntry ::= SEQUENCE {
		winlink1000HbsPerfMonAirGenDayIdx
	      INTEGER,
		winlink1000HbsPerfMonAirGenDayRxMBytes
	      Gauge,
   		winlink1000HbsPerfMonAirGenDayTxMBytes
	      Gauge,
		winlink1000HbsPerfMonAirGenDayEthCapacityThreshUnder
	      Gauge,
		winlink1000HbsPerfMonAirGenDayHighTrafficThreshExceed
	      Gauge,
		winlink1000HbsPerfMonAirGenDayActiveSeconds
	      Gauge
	}

	winlink1000HbsPerfMonAirGenDayIdx OBJECT-TYPE
		SYNTAX  INTEGER (1..96)
		ACCESS  read-only
		STATUS  mandatory
		DESCRIPTION
		"This table is indexed per Day number. Each interval
		is of 15 minutes and the oldest is 96."
		::= { winlink1000HbsPerfMonAirGenDayEntry 1 }

	winlink1000HbsPerfMonAirGenDayRxMBytes OBJECT-TYPE
		SYNTAX  Gauge (0..1080000)
		ACCESS  read-only
		STATUS  mandatory
		DESCRIPTION
		"Current RX Mega Bytes per day.
		(Represents the LAN traffic, RX direction, toward the HSU)"
		::= { winlink1000HbsPerfMonAirGenDayEntry 2 }		

	winlink1000HbsPerfMonAirGenDayTxMBytes OBJECT-TYPE
		SYNTAX  Gauge (0..1080000)
		ACCESS  read-only
		STATUS  mandatory
		DESCRIPTION
		"Current Transmit Mega Bytes per day.
		(Represents the LAN traffic, TX direction, from the HSU)"
		::= { winlink1000HbsPerfMonAirGenDayEntry 3 }
		
	winlink1000HbsPerfMonAirGenDayEthCapacityThreshUnder OBJECT-TYPE
		SYNTAX  Gauge (0..86400)
		ACCESS  read-only
		STATUS  mandatory
		DESCRIPTION
		"The number of times throughput was below threshold each day.
		Relevant for point to point systems."
		::= { winlink1000HbsPerfMonAirGenDayEntry 4 }
		
	winlink1000HbsPerfMonAirGenDayHighTrafficThreshExceed OBJECT-TYPE
		SYNTAX  Gauge (0..86400)
		ACCESS  read-only
		STATUS  mandatory
		DESCRIPTION
		"The number of times actual traffic was above threshold each day."
		::= { winlink1000HbsPerfMonAirGenDayEntry 5 }
		
	winlink1000HbsPerfMonAirGenDayActiveSeconds OBJECT-TYPE
		SYNTAX  Gauge (0..86400)
		ACCESS  read-only
		STATUS  mandatory
		DESCRIPTION
		"The number of seconds in which RPL Ethernet service was not blocked each day."
		::= { winlink1000HbsPerfMonAirGenDayEntry 6 }	
	
	-- ###########################################################
	--                      HBS Admin
	-- ###########################################################
	
	winlink1000HbsAdmin OBJECT IDENTIFIER ::= { winlink1000Hbs 5 }
	
	winlink1000HbsAdminInstallationConfirmationRequired OBJECT-TYPE
		SYNTAX  INTEGER 
		{
			true (1),
			false (2)
		}
		ACCESS  read-write
		STATUS  mandatory
		DESCRIPTION
		"Installation Confirmation required for Radius mode. 1- true 2- false"
		::= { winlink1000HbsAdmin 1 }
		
	winlink1000HbsAdminRemoteTrapGenerationMode OBJECT-TYPE
		SYNTAX  INTEGER	{
			off (1),
			on (2)		
		}
		ACCESS  read-write
		STATUS  mandatory
		DESCRIPTION
		"HBS generation of remote traps (1=Off, 2=On)"
		::= { winlink1000HbsAdmin 2 }
	
	-- ###########################################################
	--                      HSU
	-- ###########################################################

	winlink1000Hsu OBJECT IDENTIFIER ::= { winlink1000 4 }

	-- ###########################################################
	--                      HSU Air
	-- ###########################################################

	winlink1000HsuAir OBJECT IDENTIFIER ::= { winlink1000Hsu 1 }
	
	winlink1000HsuAirState OBJECT-TYPE
		SYNTAX  INTEGER	{
			init				(1),
			bitFailed			(2),
			spectrumMeasurement	(4),
			transceiving		(7),
			standBy				(8)
			}
		ACCESS  read-only
		STATUS  mandatory
		DESCRIPTION
		"Holds the state of the HSU."
		::= { winlink1000HsuAir 1 }
		
	winlink1000HsuAirLinkState OBJECT-TYPE
		SYNTAX  INTEGER	{
			noSync 				(1),
			violated			(2),
			syncUnregistered		(3),
			syncRegistered			(4),
			authenticationError		(5),
			swUpgradeRequired		(6),
			syncRegisteredPassive	        (7)
			}
		ACCESS  read-only
		STATUS  mandatory
		DESCRIPTION
		"Holds the state of the HSU link."
		::= { winlink1000HsuAir 2 }
		
	winlink1000HsuAirHsuId OBJECT-TYPE
		SYNTAX  INTEGER
		ACCESS  read-only
		STATUS  mandatory
		DESCRIPTION
		"Holds the HSU ID as sent by the HBS."
		::= { winlink1000HsuAir 3 }
		
	winlink1000HsuAirLocalDeregister OBJECT-TYPE
		SYNTAX  INTEGER
		ACCESS  read-write
		STATUS  mandatory
		DESCRIPTION
		"Performs Local HSU Deregistration when - only when the link is off."
		::= { winlink1000HsuAir 5 }
		
	winlink1000HsuAirRemoteCompressedMon OBJECT-TYPE
		SYNTAX  OCTET STRING
		ACCESS  read-only
		STATUS  mandatory
		DESCRIPTION
		"Holds all the configuration data of The HBS in compressed format.		
		Fields Included:
		Rss (1 byte)											
		Rss Balance (1 byte)
		Est. Tput (4 bytes)	
		In Bytes of the whole sector (4 bytes)										
		Out Bytes of the whole sector (4 bytes)									
		In Frames of the whole sector (4 bytes)									
		Out Frames of the whole sector (4 bytes)
		Max Throughput DownLink (4 bytes)
		Max Throughput UpLink (4 bytes)
		Rx Rate In Kbps of the whole sector (4 bytes)
		Tx Rate In Kbps of the whole sector (4 bytes)
		Rx Rate In Fps of the whole sector (4 bytes)
		Tx Rate In Fps of the whole sector (4 bytes)
		Peak Throughput in the DL direction in Kbps (4 bytes)
		Peak Throughput in the UL direction in Kbps (4 bytes)
		Tx Ratio (2 bytes)
		Chain 1 Rss (1 byte)
		Chain 2 Rss (1 byte)
		Chain 3 Rss (1 byte)
		HBS Current Rate Index (2 bytes)
		HBS Current Rate CBW (1 bytes)
		HBS Current Rate GI (1 bytes)
		Rx LAN 1 Rate In Kbps of the whole sector (4 bytes)
		Tx LAN 1 Rate In Kbps of the whole sector (4 bytes)
		Rx LAN 1 Rate In Fps of the whole sector (4 bytes)
		Tx LAN 1 Rate In Fps of the whole sector (4 bytes)
		Rx LAN 2 Rate In Kbps of the whole sector (4 bytes)
		Tx LAN 2 Rate In Kbps of the whole sector (4 bytes)
		Rx LAN 2 Rate In Fps of the whole sector (4 bytes)
		Tx LAN 2 Rate In Fps of the whole sector (4 bytes)
		SyncE Performance (1 byte)
		HBS EC Changes Counter (1 byte)"
		::= { winlink1000HsuAir 6 }		
		
	winlink1000HsuAirRemoteCompressedStatic OBJECT-TYPE
		SYNTAX  DisplayString
		ACCESS  read-only
		STATUS  mandatory
		DESCRIPTION
		"Holds all the configuration data of the HBS in a compressed format.
		Helps the NMS to get info regarding new Unregistered links.
		Fields Included:
		Location			(32 bytes)
		IP address			(8 bytes in hexa)
		Subnet mask			(8 bytes in hexa)
		HBS Antenna type		(1 byte)
		HBS Agent Version (4 bytes)
		HBS Name (32 bytes)"
		::= { winlink1000HsuAir 7 }	
		
	winlink1000HsuAirRssThreshSync OBJECT-TYPE
		SYNTAX  INTEGER
		ACCESS  read-write
		STATUS  mandatory
		DESCRIPTION
		"HSUs will be sychnornized immediately if RSS is better than threshold."
		::= { winlink1000HsuAir 8 }
		
	-- ###########################################################
	--                      HSU Air Alignment
	-- ###########################################################

	winlink1000HsuAirAlignment OBJECT IDENTIFIER ::= { winlink1000HsuAir 9 }

	winlink1000HsuAirAlignmentCmd OBJECT-TYPE
		SYNTAX  INTEGER	{
			startAlignmentProcess      (1),
			evaluateCurrentManualAngle (2),
			finishAlignmentProcess	   (3),
			abortAlignmentProcess      (4),
			evaluteBestManualAngle     (5),
			stopAlignmentProcess       (6)
			}
		ACCESS  read-write
		STATUS  mandatory
		DESCRIPTION
		"1 Start Alignment process and initialize the GIRO
		 2 Evaluate current manual angle
		 3 Finish Alignment process
		 4 Abort Alignment process
		 5 Evaluate best manual angle
		 6 Stop Alignment process"
		::= { winlink1000HsuAirAlignment 1 }

	winlink1000HsuAirAlignmentStatus OBJECT-TYPE
		SYNTAX  INTEGER	{
		        na                    (-1),
			iss		      (1),
			csa		      (2),
			biDirectionalLink     (3),
			evaluate2x2	      (4),
			evaluate3x3	      (5),
			alignmentFinished     (6)
			}
		ACCESS  read-only
		STATUS  mandatory
		DESCRIPTION
		"Antenna Alignment status:
		 -1 N/A (for non BSA products)
		  1 ISS (scanning for HBS)
		  2 CSA (Sync to HBS, waiting for Evaluation command)
		  3 Bi-directional link
		  4 Evaluate 2x2
		  5 Evaluate 3x3
		  6 Alignment Finished."
		::= { winlink1000HsuAirAlignment 2 }

	winlink1000HsuAirAlignment3x3Step OBJECT-TYPE
		SYNTAX  INTEGER
		ACCESS  read-only
		STATUS  mandatory
		DESCRIPTION
		"Step number out of total steps in Throughput evaluation for 3x3 scenario."
		::= { winlink1000HsuAirAlignment 3 }

	winlink1000HsuAirAlignment3x3TotalSteps OBJECT-TYPE
		SYNTAX  INTEGER
		ACCESS  read-only
		STATUS  mandatory
		DESCRIPTION
		"Total  steps in Throughput evaluation for 3x3 scenario."
		::= { winlink1000HsuAirAlignment 4 }

	winlink1000HsuAirAlignmentEvalTo OBJECT-TYPE
		SYNTAX  INTEGER
		ACCESS  read-write
		STATUS  mandatory
		DESCRIPTION
		"Evaluation timeout."
		::= { winlink1000HsuAirAlignment 5 }

	-- ###########################################################
	--                      HSU Air Alignment Last Report
	-- ###########################################################

	winlink1000HsuAirAlignmentLastReport OBJECT IDENTIFIER ::= { winlink1000HsuAirAlignment 6 }

	winlink1000HsuAirAlignmentLastReportManualAngle OBJECT-TYPE
		SYNTAX  INTEGER
		ACCESS  read-only
		STATUS  mandatory
		DESCRIPTION
		"The angle of the antenna. Used in the alignment process."
		::= { winlink1000HsuAirAlignmentLastReport 1 }

	winlink1000HsuAirAlignmentLastReportTputUpSector OBJECT-TYPE
		SYNTAX  INTEGER
		ACCESS  read-only
		STATUS  mandatory
		DESCRIPTION
		"Expected throughput for the whole sector in the Uplink direction in this angle."
		::= { winlink1000HsuAirAlignmentLastReport 2 }

	winlink1000HsuAirAlignmentLastReportTputDownSector OBJECT-TYPE
		SYNTAX  INTEGER
		ACCESS  read-only
		STATUS  mandatory
		DESCRIPTION
		"Expected throughput for the whole sector in the Downlink direction in this angle."
		::= { winlink1000HsuAirAlignmentLastReport 3 }

	winlink1000HsuAirAlignmentLastReportMcsIndexUp OBJECT-TYPE
		SYNTAX  INTEGER
		ACCESS  read-only
		STATUS  mandatory
		DESCRIPTION
		"MCS index of the link in the uplink direction."
		::= { winlink1000HsuAirAlignmentLastReport 4 }
		
	winlink1000HsuAirAlignmentLastReportMcsIndexDown OBJECT-TYPE
		SYNTAX  INTEGER
		ACCESS  read-only
		STATUS  mandatory
		DESCRIPTION
		"MCS index of the link in the downlink direction."
		::= { winlink1000HsuAirAlignmentLastReport 5 }		

	winlink1000HsuAirAlignmentLastReportState OBJECT-TYPE
		SYNTAX  INTEGER	{
			finishedSuccessfully		     (1),
			partialEvaluationTimeoutExceeded (2),
			evaluationAbortedTimeoutExceeded (3),
			evaluationAbortedUnstableAntenna (4),
			evaluationAbortedSyncLost	     (5),
			evaluationAbortedExternalCommand (6),
			evaluating                       (7)
			}
		ACCESS  read-only
		STATUS  mandatory
		DESCRIPTION
		"State of the Evaluation
		 1 Finished successfully
		 2 Partial Evaluation (Timeout Exceeded)
		 3 Evaluation Aborted (Timeout Exceeded)
		 4 Evaluation aborted (Unstable Antenna)
		 5 Evaluation aborted (Sync Lost)
		 6 Evaluation aborted (External command)
		 7 Evaluating."
		::= { winlink1000HsuAirAlignmentLastReport 6 }

	winlink1000HsuAirAlignmentLastReportElectronicAnglesHsu OBJECT-TYPE
		SYNTAX  DisplayString
		ACCESS  read-only
		STATUS  mandatory
		DESCRIPTION
		"Electronic angles of 3 chains in the HSU side separated by comma."
		::= { winlink1000HsuAirAlignmentLastReport 7 }
		
	winlink1000HsuAirAlignmentLastReportElectronicAnglesHbs OBJECT-TYPE
		SYNTAX  DisplayString
		ACCESS  read-only
		STATUS  mandatory
		DESCRIPTION
		"Electronic angles of 3 chains in the HBS side separated by comma."
		::= { winlink1000HsuAirAlignmentLastReport 8 }

	winlink1000HsuAirAlignmentLastReportRss  OBJECT-TYPE
		SYNTAX  DisplayString
		ACCESS  read-only
		STATUS  mandatory
		DESCRIPTION
		"RSS on chain 1, 2 and 3 (separated by comma)"
		::= { winlink1000HsuAirAlignmentLastReport 9 }
		
	winlink1000HsuAirCompressedMon OBJECT-TYPE
		SYNTAX OCTET STRING
		ACCESS  read-only
		STATUS  mandatory
		DESCRIPTION
		"Holds HSU monitor data in compressed format:
		HSU Rx Rate in Kbps (4)
		HSU Tx Rate in Kbps (4)
		HSU Rx Rate in Fps (4)
		HSU Tx Rate in Fps (4)
		HSU LAN 1 Rx Rate in Kbps (4)
		HSU LAN 1 Tx Rate in Kbps (4)
		HSU LAN 1 Rx Rate in Fps (4)
		HSU LAN 1 Tx Rate in Fps (4)
		HSU LAN 2 Rx Rate in Kbps (4)
		HSU LAN 2 Tx Rate in Kbps (4)
		HSU LAN 2 Rx Rate in Fps (4)
		HSU LAN 2 Tx Rate in Fps (4)
		1588TC Performance (1)
		SyncE Performance (1)
		ATPC status (1)
		Installation confirmation required (1)"
		::= { winlink1000HsuAir 10 }
		
	winlink1000HsuAirReAlignmentOnStartupEnable OBJECT-TYPE
		SYNTAX  INTEGER {
			disable(1),
			enable(2)
			}
		ACCESS  read-write
		STATUS  mandatory
		DESCRIPTION
		"Should HSU perform Realignment every syncloss."
		::= { winlink1000HsuAir 11 }
		
	winlink1000HsuService OBJECT IDENTIFIER ::= { winlink1000Hsu 2 }
	
	winlink1000HsuServiceCommandStr OBJECT-TYPE
		SYNTAX  DisplayString
		ACCESS  read-write
		STATUS  mandatory
		DESCRIPTION
		"Ability to perform special command in the HSU.
		Format (string): Operation, Param1, Param2,....| ParamN."
		::= { winlink1000HsuService 1 }		
		
	winlink1000HsuServiceHsuType OBJECT-TYPE
		SYNTAX  INTEGER	{
			fixed		(1),
			stationary	(2),
			mobile		(3),
			transport	(4)
			}
		ACCESS  read-write
		STATUS  mandatory
		DESCRIPTION
		"HSU type (1 = Fixed, 2 = Stationary, 3 = Mobile, 4 = Transport)"
		::= { winlink1000HsuService 2 }
		
	winlink1000HsuServiceHsuLevel OBJECT-TYPE
		SYNTAX  INTEGER
		ACCESS  read-write
		STATUS  mandatory
		DESCRIPTION
		"HSU level (1 .. 4)"
		::= { winlink1000HsuService 3 }
		
	-- ###########################################################
	--                      HSU Ethernet 
	-- ###########################################################
	
	winlink1000HsuEthernet OBJECT IDENTIFIER ::= { winlink1000Hsu 3 }
	
	winlink1000HsuEthernetPoE OBJECT IDENTIFIER ::= { winlink1000HsuEthernet 1 }
	
	winlink1000HsuEthernetPoESupported OBJECT-TYPE
		SYNTAX  INTEGER {notSupported(1), supported(2)}
		ACCESS  read-only
		STATUS  mandatory
		DESCRIPTION
		"Indicated if this HSU has special port for PoE devices."
		::= { winlink1000HsuEthernetPoE 1 }
		
	winlink1000HsuEthernetPoETemperature OBJECT-TYPE
		SYNTAX  INTEGER
		ACCESS  read-only
		STATUS  mandatory
		DESCRIPTION
		"Holds the temperature (Celsius) of the POE component."
		::= { winlink1000HsuEthernetPoE 2 }
		
	winlink1000HsuEthernetPoEEquConsumption OBJECT-TYPE
		SYNTAX  INTEGER
		ACCESS  read-only
		STATUS  mandatory
		DESCRIPTION
		"Holds the consumption of the connected equipment (milliampere)."
		::= { winlink1000HsuEthernetPoE 3 }
		
	winlink1000HsuEthernetPoEEquVoltage OBJECT-TYPE
		SYNTAX  INTEGER
		ACCESS  read-only
		STATUS  mandatory
		DESCRIPTION
		"Holds the voltage of the connected equipment (Volt)."
		::= { winlink1000HsuEthernetPoE 4 }
		
	-- ###########################################################
	--                      HSU Admin
	-- ###########################################################	
	
	winlink1000HsuAdmin OBJECT IDENTIFIER ::= { winlink1000Hsu 4 }

	winlink1000HsuAdminInstallationConfirmationRequired OBJECT-TYPE
		SYNTAX  INTEGER 
		{
			true (1),
			false (2)
		}
		ACCESS  read-only
		STATUS  mandatory
		DESCRIPTION
		"Installation Confirmation required for Radius mode. 1- true 2- false"
		::= { winlink1000HsuAdmin 1 }

	winlink1000HsuAdminSiteSurveySupport OBJECT-TYPE
		SYNTAX  INTEGER {
			notSupported(1),
			supported(2)
			}
		ACCESS  read-only
		STATUS  mandatory
		DESCRIPTION
		"This value indicates if site survey is supported or not supported."
		::= { winlink1000HsuAdmin 2 }
		
	winlink1000HsuAdminSiteSurveyMode OBJECT-TYPE
		SYNTAX  INTEGER {
			notActivated(1),
			activated(2)
			}
		ACCESS  read-write
		STATUS  mandatory
		DESCRIPTION
		"This value indicates if site survey is activated or not activated."
		::= { winlink1000HsuAdmin 3 }
	
	-- ###########################################################
	--                      General
	-- ###########################################################

	winlink1000General OBJECT IDENTIFIER ::= { winlink1000 100 }

	winlink1000GeneralTrapDescription OBJECT-TYPE
		SYNTAX  DisplayString
		ACCESS  read-only
		STATUS  mandatory
		DESCRIPTION
		"Trap's Description. Used for Trap parameters."
		::= { winlink1000General 1 }

	winlink1000GeneralTrapSeverity OBJECT-TYPE
		SYNTAX  INTEGER	{
			event		(1),
			normal		(2),
			warning		(4),
			minor		(8),
			major		(16),
			critical	(32)
			}
		ACCESS  read-only
		STATUS  mandatory
		DESCRIPTION
		"Trap's Severity. Used for Trap parameters."
		::= { winlink1000General 2 }
		
	winlink1000GeneralCookie OBJECT-TYPE
		SYNTAX  DisplayString
		ACCESS  read-write
		STATUS  mandatory
		DESCRIPTION
		"Reserved for the Manager application provided with the product, used for saving user preferences affecting ODU operation."
		::= { winlink1000General 3 }

	winlink1000GeneralEcChangesCounter OBJECT-TYPE
		SYNTAX INTEGER
		ACCESS  read-only
		STATUS mandatory
		DESCRIPTION
		"This counter is initialized to 0 after a device reset and is incremented upon each element constant write operation
		via SNMP or Telnet."
		::= { winlink1000General 4 }  
		
	winlink1000GeneralTelnetSupport OBJECT-TYPE
		SYNTAX  INTEGER	{
			enable		(1),
			disable		(2)
			}
		ACCESS  read-write
		STATUS  mandatory
		DESCRIPTION
		"Enable/Disable Telnet protocol."
		::= { winlink1000General 5 }

	winlink1000GeneralWISupport OBJECT-TYPE
		SYNTAX  INTEGER	{
			mandatoryDisabled(1),
			mandatoryEnabled(2),
			disabled(3),
			enabled	(4)
			}
		ACCESS  read-write
		STATUS  mandatory
		DESCRIPTION
		"Enable/Disable Web Interface protocol.
		  Mandatory Disabled - No option to enable the feature.
		  Mandatory Enabled - No option to disable the feature."
		::= { winlink1000General 6 }
			
	winlink1000GeneralSNMPSupport OBJECT-TYPE
		SYNTAX  INTEGER	{
			enabled(1),
			snmpv1Only(2),
			snmpv3Only(3)
			}
		ACCESS  read-write
		STATUS  mandatory
		DESCRIPTION
		"Enable/Disable SNMP protocols"
		::= { winlink1000General 7 }

	winlink1000GeneralSSHSupport OBJECT-TYPE
		SYNTAX  INTEGER	{
			enabled(1),
			disabled(2),
			unsupported(3)
			}
		ACCESS  read-write
		STATUS  mandatory
		DESCRIPTION
		"Enable/Disable SSH protocols"
		::= { winlink1000General 8 }

	-- ###########################################################
	--                 Traps Section
	-- ###########################################################

	--
	--	The ifIndex, Unit, Time_T and Alarm Id will be bind to the Trap only if
	--	winlink1000OduAgnGenAddTrapExt	= 'yes'.
	--

	trunkStateChanged TRAP-TYPE
		ENTERPRISE winlink1000
		VARIABLES { winlink1000GeneralTrapDescription, winlink1000OduAgnCurrAlarmSeverity, winlink1000IduTdmIfIndex,
		winlink1000IduTdmLineStatus, winlink1000OduAgnCurrAlarmIfIndex, winlink1000OduAgnCurrAlarmUnit,
		winlink1000OduAgnCurrAlarmTimeT, winlink1000OduAgnCurrAlarmId }
		--&ACTIONS  { normal }
		--&MESG "$'1"
		DESCRIPTION
		"
		Indicates a change in the state of one of the TDM trunks.
		Raised by both sides of the link.
		Contains 3 parameters:
		1 - Description: TDM Interface %n - %x
		2 - %n: Is the trunk number
		3 - %x: Is the alarm type and can be one of the following: Normal, AIS, LOS, Loopback
		"
		::= 1

	linkUp TRAP-TYPE
		ENTERPRISE winlink1000
		VARIABLES { winlink1000GeneralTrapDescription, winlink1000OduAgnCurrAlarmSeverity, winlink1000OduAgnCurrAlarmIfIndex, 
		winlink1000OduAgnCurrAlarmUnit, winlink1000OduAgnCurrAlarmTimeT, winlink1000OduAgnCurrAlarmId  }
		--&ACTIONS  { normal }
		--&CLEARS   { 3 }
		--&MESG "$'1"
		DESCRIPTION
		"
		Indicates that the radio link is up.
		Contains a single parameter, which is its description:
		1 - Description: Radio Link - Sync on channel %n GHz.
		%n Is the channel frequency in GHz.
		"
		::= 2

	linkDown TRAP-TYPE
		ENTERPRISE winlink1000
		VARIABLES { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { critical }
		--&MESG "$'1"
		DESCRIPTION
		"
		Indicates that the radio link is down.
		Contains a single parameter, which is its description:
		1 - Description: Radio Link - Out of Sync. The reason is: %s.
		%s Is the reason.
		"
		::= 3

	detectIDU TRAP-TYPE
		ENTERPRISE winlink1000
		VARIABLES { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { normal }
		--&CLEARS   { 5 }
		--&MESG "$'1"
		DESCRIPTION
		"
		Indicates that the IDU was detected.
		Raised by both sides of the link.
		Contains a single parameter, which is its description:
		1 - Description: IDU of Type %s was Detected.
		%s Is the type of the IDU.
		"
		::= 4

	disconnectIDU TRAP-TYPE
		ENTERPRISE winlink1000
		VARIABLES { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { major }
		--&MESG "$'1"
		DESCRIPTION
		"
		Indicates that the IDU was disconnected.
		Raised by both sides of the link.
		Contains a single parameter, which is its description:
		1 - Description: IDU Disconnected.
		"
		::= 5

	mismatchIDU TRAP-TYPE
		ENTERPRISE winlink1000
		VARIABLES { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { major }
		--&MESG "$'1"
		DESCRIPTION
		"
		Indicates a mismatch between the IDUs.
		Raised by the master only.
		Contains a single parameter, which is its description:
		1 - Description: IDUs Mismatch: One Side is %s and the Other is %s.
		%s Is the type of the IDU.
		"
		::= 6

	openedServices TRAP-TYPE
		ENTERPRISE winlink1000
		VARIABLES { winlink1000GeneralTrapDescription, winlink1000OduAgnCurrAlarmSeverity, winlink1000IduSrvDesiredTrunks,
		winlink1000IduSrvActiveTrunks, winlink1000OduAgnCurrAlarmIfIndex, winlink1000OduAgnCurrAlarmUnit,
		winlink1000OduAgnCurrAlarmTimeT, winlink1000OduAgnCurrAlarmId }
		--&ACTIONS  { normal }
		--&MESG "$'1"
		DESCRIPTION
		"
		Indicates that services were opened. Raised by the master only.
		Contains 3 parameters:
		1 - Description: %n2 out of %n1 Requested TDM Trunks have been Opened
		2 - %n1: Is the requested number of TDM truncks
		3 - %n2: Is the actual number of TDM trunks that were opened
		"
		::= 7

	closedServices TRAP-TYPE
		ENTERPRISE winlink1000
		VARIABLES { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { normal }	
		--&CLEARS   { 100 }
		--&MESG "$'1"
		DESCRIPTION
		"
		Indicates that services were closed.
		Raised by the master only.
		Contains a single parameter, which is its description:
		1 - Description: TDM Service has been closed. The reason is: %s.
		%s Is the reason.
		"
		::= 8

	incompatibleODUs TRAP-TYPE
		ENTERPRISE winlink1000
		VARIABLES { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { critical }
		--&MESG "$'1"
		DESCRIPTION
		"
		Indicates that the ODUs are incompatible.
		Contains a single parameter, which is its description:
		1 - Description: Incompatible ODUs.
		"
		::= 9

	incompatibleIDUs TRAP-TYPE
		ENTERPRISE winlink1000
		VARIABLES { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { major }
		--&MESG "$'1"
		DESCRIPTION
		"
		Indicates that the IDUs are incompatible.
		Contains a single parameter, which is its description:
		1 - Description: Incompatible IDUs.
		"
		::= 10

	incompatibleOduIdu TRAP-TYPE
		ENTERPRISE winlink1000
		VARIABLES   { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { major }
		--&MESG     "$'1"
		DESCRIPTION
		"
		Indicates that the ODU and IDU are incompatible.
		Contains a single parameter, which is its description:
		1 - Description: The IDU could not be loaded. The reason is: %s.
		%s Is the incompatibility type.
		"
		::= 11

	probingChannel TRAP-TYPE
		ENTERPRISE winlink1000
		VARIABLES   { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { normal }
		--&MESG     "$'1"
		DESCRIPTION
		"
		Indicates that the ODU is monitoring radar activity.			
		Contains a single parameter, which is its description:
		1 - Description: Monitoring for radar activity on channel %n GHz.
		%n is the channel frequency in GHz.
		"
		::= 12

	radarDetected TRAP-TYPE
		ENTERPRISE winlink1000
		VARIABLES   { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { normal }
		--&MESG     "$'1"
		DESCRIPTION
		"
		Indicates that radar activity was detected.
		Contains a single parameter, which is its description:
		1 - Description: Radar activity was detected in %s, on channel %n GHz.
		%s Is the site name.
		%n Is the channel frequency in GHz.
		"
		::= 13
		
	transmittingOnChannel TRAP-TYPE
		ENTERPRISE winlink1000
		VARIABLES   { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { normal }
		--&MESG     "$'1"
		DESCRIPTION
		"
		Indicates that the ODU is transmitting on channel.
		Contains a single parameter, which is its description:
		1 - Description: Transmitting on channel %n GHz.
		%n Is the channel frequency in GHz.
		"
		::= 14

	scanningChannels TRAP-TYPE
		ENTERPRISE winlink1000
		VARIABLES   { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { normal }
		--&MESG     "$'1"
		DESCRIPTION
		"
		Indicates that the ODU is scanning channels.
		Contains a single parameter, which is its description:
		1 - Description: Channel scanning in progress.
		"
		::= 15
		
	incompatiblePartner TRAP-TYPE
		ENTERPRISE winlink1000
		VARIABLES   { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { critical }
		--&MESG     "$'1"
		DESCRIPTION
		"
		Indicates that configuration problem was detected and that link installation is required in order to fix it.
		Contains a single parameter, which is its description:
		1 - Description: Configuration problem detected. Link installation required.
		"
		::= 16

	timeClockSet TRAP-TYPE
		ENTERPRISE winlink1000
		VARIABLES   { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { normal }
		--&MESG     "$'1"
		DESCRIPTION
		"
		Indicates that the ODU time clock was set.
		Contains a single parameter, which is its description:
		1 - Description: The time was set to: %p.
		%p Is the date and time.
		"
		::= 17

	configurationChanged TRAP-TYPE
		ENTERPRISE winlink1000
		VARIABLES { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { normal }
		--&MESG "$'1"
		DESCRIPTION
		"
		Indicates that the ODU recovered from an error, but there are configuration changes.
		Contains two parameters:
		1 - Description: Configuration changed. Error code is: %n.
		2 - %n number.
		"
		::= 18

	hssOpStateChangedToINU TRAP-TYPE
		ENTERPRISE winlink1000
		VARIABLES   { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { normal }
		--&CLEARS   { 119 }
		--&MESG     "$'1"
		DESCRIPTION
		"
		Indicates that the HSS operating state was changed to INU type.
		Contains a single parameter, which is its description:
		1 - Description: HSS operating state was changed to: INU.
		"
		::= 19

	hssOpStateChangedToHSM TRAP-TYPE
		ENTERPRISE winlink1000
		VARIABLES   { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { normal }
		--&CLEARS   { 119 }
		--&MESG     "$'1"
		DESCRIPTION
		"
		Indicates that the HSS operating state was changed to HSM type.
		Contains a single parameter, which is its description:
		1 - Description: HSS operating state was changed to: HSM.
		"
		::= 20

	hssOpStateChangedToHSC TRAP-TYPE
		ENTERPRISE winlink1000
		VARIABLES   { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { normal }
		--&CLEARS   { 120 }
		--&MESG     "$'1"
		DESCRIPTION
		"
		Indicates that the HSS operating state was changed to HSC type.
		Contains a single parameter, which is its description:
		1 - Description: HSS operating state was changed to: HSC_DT/HSC_CT.		
		"
		::= 21
	
	vlanModeActive TRAP-TYPE
		ENTERPRISE winlink1000
		VARIABLES   { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { normal }
		--&MESG     "$'1"
		DESCRIPTION
		" Indicates to non-VLAN PC that after 2 minutes the system will support only VLAN
		tag on management interface. Contains a single parameter, which is its description:
		1 - Description: VLAN Mode is active. Non-VLAN traffic will be blocked in 2 minutes.
		"
		::= 22
	
	spectrumAnalysis TRAP-TYPE
		ENTERPRISE winlink1000
		VARIABLES   { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { normal }
		--&MESG     "$'1"
		DESCRIPTION
		"
		Indicates that the ODU is in Spectrum Analysis mode.
		Contains a single parameter, which is its description:
		1 - Description: Spectrum analysis in progress.
		"
		::= 23
		
	hbsHsuDeregisteredOffline TRAP-TYPE
		ENTERPRISE winlink1000
		VARIABLES   { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { normal }
		--&MESG     "$'1"
		DESCRIPTION
		"
		Indicates that a HSU was deregistered offline (out of link)
		"
		::= 24
	
	hbsHsuDeregisteredSuccessfully TRAP-TYPE
		ENTERPRISE winlink1000
		VARIABLES   { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { normal }
		--&MESG     "$'1"
		DESCRIPTION
		"
		Indicates that a HSU was deregistered successfully
		"
		::= 25
		
	hbsHsuRegisteredSuccessfully TRAP-TYPE
		ENTERPRISE winlink1000
		VARIABLES   { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { normal }
		--&MESG     "$'1"
		DESCRIPTION
		"
		Indicates that a HSU was registered successfully
		"
		::= 26
		
	hbsHsuRegistrationFailed TRAP-TYPE
		ENTERPRISE winlink1000
		VARIABLES   { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { normal }
		--&MESG     "$'1"
		DESCRIPTION
		"
		Indicates that registration has failed
		"
		::= 27
		
	hbsHsuViolatedState TRAP-TYPE
		ENTERPRISE winlink1000
		VARIABLES   { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { normal }
		--&MESG     "$'1"
		DESCRIPTION
		"
		Indicates (on the HBS side) that a HSU is is violated state
		"
		::= 28
		
	hsuViolatedState TRAP-TYPE
		ENTERPRISE winlink1000
		VARIABLES   { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { normal }
		--&MESG     "$'1"
		DESCRIPTION
		"
		Indicates (on the HSU side) that the HSU is is violated state
		"
		::= 29

	hbsUnregisteredSynchronizedHsu TRAP-TYPE
		ENTERPRISE winlink1000
		VARIABLES   { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { normal }
		--&MESG     "$'1"
		DESCRIPTION
		"
		Indicates an unregistered HSU has been synchronized.
		"
		::= 30
		
	hbsUnregisteredUnsynchronizedHsu TRAP-TYPE
		ENTERPRISE winlink1000
		VARIABLES   { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { normal }
		--&MESG     "$'1"
		DESCRIPTION
		"
		Indicates an unregistered HSU lost synchronization.
		"
		::= 31
		
	cableQuality TRAP-TYPE
		ENTERPRISE winlink1000
		VARIABLES   { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { normal }
		--&MESG     "$'1"
		DESCRIPTION
		"
		1Gbps rate is not supported due to bad line quality.
		"
		::= 32
		
	httpAuthentication TRAP-TYPE
		ENTERPRISE winlink1000
		VARIABLES   { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { normal }
		--&MESG     "$'1"
		DESCRIPTION
		"
		HTTP Authentication Failure.
		"
		::= 33
		
	telnetAuthentication TRAP-TYPE
		ENTERPRISE winlink1000
		VARIABLES   { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { normal }
		--&MESG     "$'1"
		DESCRIPTION
		"
		Telnet Authentication Failure.
		"
		::= 34

	tdmServiceAlarm TRAP-TYPE
		ENTERPRISE winlink1000
		VARIABLES { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { major }
		--&MESG "$'1"
		DESCRIPTION
		"
		Indicates that TDM Service is in alarm state.
		Contains a single parameter, which is its description:
		1 - Description: TDM Service - Alarm.
		"
		::= 100

	ethServiceClosed TRAP-TYPE
		ENTERPRISE winlink1000
		VARIABLES { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { major }
		--&MESG "$'1"
		DESCRIPTION
		"
		Indicates that Ethernet Service is closed.
		Contains a single parameter, which is its description:
		1 - Description: Ethernet Service is closed.
		"
		::= 101

	ethServiceNotPermitted TRAP-TYPE
		ENTERPRISE winlink1000
		VARIABLES { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { major }
		--&MESG "$'1"
		DESCRIPTION
		"
		Indicates that Ethernet Service is not permitted.
		Contains a single parameter, which is its description:
		1 - Description: A valid IDU could not be detected at %s. Please check your configuration.
		%s - Is the Local Site name or Remote Site name or both sides of the Link.
		"
		::= 102

	encryptionAlarm TRAP-TYPE
		ENTERPRISE winlink1000
		VARIABLES { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { major }
		--&MESG "$'1"
		DESCRIPTION
		"
		Indicates an encryption key mismatch.
		Contains a single parameter, which is its description:
		1 - Description: Encryption Status - Failed. No Services are available.
		"
		::= 103

	changeLinkPasswordAlarm TRAP-TYPE
		ENTERPRISE winlink1000
		VARIABLES { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { major }
		--&MESG "$'1"
		DESCRIPTION
		"
		Indicates that a failure has occurred while attempting to change the Link Password.
		Contains a single parameter, which is its description:
		1 - Description: Failed to change the Link Password at/on: %s.
		%s - Is the Local Site name or Remote Site name or both sides of the Link.
		"
		::= 104

	externalAlarmInPort1Alarm TRAP-TYPE
		ENTERPRISE winlink1000
		VARIABLES { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { major }
		--&MESG "$'1"
		DESCRIPTION
		"
		The trap is sent every time an alarm occurs in the External Alarm Input of port #1.
		Contains a single parameter, which is its description:
		1 - Description: External Alarm 1 - <User Text> - Alarm.
		"
		::= 105

	externalAlarmInPort2Alarm TRAP-TYPE
		ENTERPRISE winlink1000
		VARIABLES { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { major }
		--&MESG "$'1"
		DESCRIPTION
		"
		The trap is sent every time an alarm occurs in the External Alarm Input of port #2.
		Contains a single parameter, which is its description:
		1 - Description: External Alarm 2 - <User Text> - Alarm.
		"
		::= 106

	bitFailedAlarm TRAP-TYPE
		ENTERPRISE winlink1000
		VARIABLES { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { critical }
		--&MESG "$'1"
		DESCRIPTION
		"
		The trap is sent if there is no way to recover from the situation.		
		Contains two parameters:
		1 - Description: ODU power up built in test failed. Error code is: %n
		2 - %n number
		"
		::= 107

	wrongConfigurationLoadedAlarm TRAP-TYPE
		ENTERPRISE winlink1000
		VARIABLES { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { major }
		--&MESG "$'1"
		DESCRIPTION
		"
		The trap is sent if there is a way to recover from the situation.		
		Contains two parameters:
		1 - Description: Wrong configuration loaded. Error code is: %n
		2 - %n number
		"
		::= 108

	lanPort1DisconnectedAlarm TRAP-TYPE
		ENTERPRISE winlink1000
		VARIABLES { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { major }
		--&MESG "$'1"
		DESCRIPTION
		"
		Indicates the LAN port 1 status changed to disconnected.		
		Contains a single parameter, which is its description:
		1 - Description: LAN port 1 status changed to disconnected.
		"
		::= 109

	lanPort2DisconnectedAlarm TRAP-TYPE
		ENTERPRISE winlink1000
		VARIABLES { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { major }
		--&MESG "$'1"
		DESCRIPTION
		"
		Indicates the LAN port 2 status changed to disconnected.		
		Contains a single parameter, which is its description:
		1 - Description: LAN port 2 status changed to disconnected.
		"
		::= 110

	mngPortDisconnectedAlarm TRAP-TYPE
		ENTERPRISE winlink1000
		VARIABLES { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { major }
		--&MESG "$'1"
		DESCRIPTION
		"
		Indicates the LAN1 port status changed to disconnected.		
		Contains a single parameter, which is its description:
		1 - Description: LAN1 port status changed to disconnected.
		"
		::= 111

	externalAlarmInPort3Alarm TRAP-TYPE
		ENTERPRISE winlink1000
		VARIABLES { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { major }
		--&MESG "$'1"
		DESCRIPTION
		"
		The trap is sent every time an alarm occurs in the External Alarm Input of port #3.
		Contains a single parameter, which is its description:
		1 - Description: External Alarm 3 - <User Text> - Alarm.
		"
		::= 112

	externalAlarmInPort4Alarm TRAP-TYPE
		ENTERPRISE winlink1000
		VARIABLES { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { major }
		--&MESG "$'1"
		DESCRIPTION
		"
		The trap is sent every time an alarm occurs in the External Alarm Input of port #4.
		Contains a single parameter, which is its description:
		1 - Description: External Alarm 4 - <User Text> - Alarm.
		"
		::= 113

	swVersionsMismatchFullCompatibilityAlarm TRAP-TYPE
		ENTERPRISE winlink1000
		VARIABLES { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { warning }
		--&MESG "$'1"
		DESCRIPTION
		"
		The trap is sent if SW versions mismatch with full link functionality.
		Contains a single parameter, which is its description:
		1 - Description: Software versions mismatch - full link functionality
		"
		::= 114

	swVersionsMismatchRestrictedCompatibilityAlarm TRAP-TYPE
		ENTERPRISE winlink1000
		VARIABLES { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { minor }
		--&MESG "$'1"
		DESCRIPTION
		"
		The trap is sent if SW versions mismatch with restricted link functionality.
		Contains a single parameter, which is its description:
		1 - Description: Software versions mismatch - restricted link functionality
		"
		::= 115

	swVersionsMismatchSoftwareUpgradeRequired TRAP-TYPE
		ENTERPRISE winlink1000
		VARIABLES { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { major }
		--&MESG "$'1"
		DESCRIPTION
		"
		The trap is sent if SW versions mismatch and SW upgrade is required.
		Contains a single parameter, which is its description:
		1 - Description: Software versions mismatch - Software upgrade required
		"
		::= 116

	swVersionsIncompatible TRAP-TYPE
		ENTERPRISE winlink1000
		VARIABLES { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { critical }
		--&MESG "$'1"
		DESCRIPTION
		"
		The trap is sent if SW versions are incompatible.
		Contains a single parameter, which is its description:
		1 - Description: SW Versions incompatible
		"
		::= 117

	hssMultipleSourcesDetectedAlarm TRAP-TYPE
		ENTERPRISE winlink1000
		VARIABLES { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { major }
		--&MESG "$'1"
		DESCRIPTION
		"
		Indicates that multiple sync pulse sources were detected.
		Contains a single parameter, which is its description:
		1 - Description: HSS multiple sync sources were detected.
		"
		::= 118

	hssSyncToProperSourceStoppedAlarm TRAP-TYPE
		ENTERPRISE winlink1000
		VARIABLES { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { major }
		--&MESG "$'1"
		DESCRIPTION
		"
		Indicates that synchronization to a proper sync pulse source was stopped.
		Contains a single parameter, which is its description:
		1 - Description: HSS sync pulse - Down. The reason is: %s.
		%s - Is the reason for the sync down.
		"
		::= 119

	hssSyncPulseDetectedAlarm TRAP-TYPE
		ENTERPRISE winlink1000
		VARIABLES   { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { major }
		--&MESG     "$'1"
		DESCRIPTION
		"
		Indicates that HSS additional sync pulse was detected.
		Contains a single parameter, which is its description:
		1 - Description: HSS additional sync pulse was detected.		
		"
		::= 120

	tdmBackupAlarm TRAP-TYPE
		ENTERPRISE winlink1000
		VARIABLES   { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { major }
		--&MESG     "$'1"
		DESCRIPTION
		"
		Indicates that the TDM backup link was activated.
		Contains a single parameter, which is its description:
		1 - Description: TDM backup alarm - backup link was activated.
		"
		::= 121
		
	linkLockUnauthorizedRemoteODU TRAP-TYPE
		ENTERPRISE winlink1000
		VARIABLES   { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { major }
		--&MESG     "$'1"
		DESCRIPTION
		"
		Indicates that the remote ODU is unauthorized. 
		Contains a single parameter, which is its description:
		1 - Description: Unauthorized remote ODU connection rejected.
		"
		::= 122
		
	linkLockUnauthorizedODU TRAP-TYPE
		ENTERPRISE winlink1000
		VARIABLES   { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { major }
		--&MESG     "$'1"
		DESCRIPTION
		"
		Indicates that the ODU is unauthorized. 
		Contains a single parameter, which is its description:
		1 - Description: Unauthorized ODU connection rejected.
		"
		::= 123
		
	hotStandbyAlarm TRAP-TYPE
		ENTERPRISE winlink1000
		VARIABLES   { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { major }
		--&MESG     "$'1"
		DESCRIPTION
		"
		Indicates that the hot standby secondary link was activated.
		Contains a single parameter, which is its description:
		1 - Description: Secondary Link Is Active.
		"
		::= 124

	sfpInsertion TRAP-TYPE
		ENTERPRISE winlink1000
		VARIABLES   { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { normal }
		--&MESG     "$'1"
		DESCRIPTION
		"
		Indicates that a device was inserted to SFP Port
		"
		::= 126

	sfpPort1DisconnectedAlarm TRAP-TYPE
		ENTERPRISE winlink1000
		VARIABLES { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { major }
		--&MESG "$'1"
		DESCRIPTION
		"
		Indicates the SFP port 1 status changed to disconnected.		
		Contains a single parameter which is its description:
		1 - Description: SFP port 1 status changed to disconnected.
		"
		::= 127
		
	ringRplStateActiveAlarm TRAP-TYPE
		ENTERPRISE winlink1000
		VARIABLES   { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { major }
		--&MESG     "$'1"
		DESCRIPTION
		"
		RPL state changed to Active.
		"
		::= 128
			

	desiredRatioCanNotBeAppliedAlarm TRAP-TYPE
		ENTERPRISE winlink1000
		VARIABLES { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { minor }
		--&MESG "$'1"
		DESCRIPTION
		"
		Indicates Desired UL/DL RAtio Can Not Be Applied.
		"
		::= 129
		
	cbwMismatch TRAP-TYPE
		ENTERPRISE winlink1000
		VARIABLES { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { major }
		--&MESG "$'1"
		DESCRIPTION
		"
		Indicates that a Channel Bandwidth mismatch was detected.		
		Contains two parameters:
		1 - Description: Channel Bandwidth Mismatch: one side is %n0 MHz and the other is %n1 MHz.
		%n0 is the local Channel Bandwidth value in MHz.
		%n1 is the remoet Channel Bandwidth value in MHz."
		::= 130

	gpsNotSynchronized TRAP-TYPE
		ENTERPRISE winlink1000
		VARIABLES   { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { major }
		--&MESG     "$'1"
		DESCRIPTION
		"
		Indicates that the GPS is not synchronized with satellites.
		Pulses are self generated.
		"
		::= 131
		
	pdTooHighDueCbwLimitations TRAP-TYPE
		ENTERPRISE winlink1000
		VARIABLES   { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { major }
		--&MESG     "$'1"
		DESCRIPTION
		"
		Indicates that link cannot be established because 
		link range is too large for channel bandwidth.
		"
		::= 132
		
	hbsEncryptionAlarm TRAP-TYPE
		ENTERPRISE winlink1000
		VARIABLES { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { major }
		--&MESG "$'1"
		DESCRIPTION
		"
		Indicates an encryption key mismatch.
		Contains a single parameter, which is its description, including the HSU's name
		"
		::= 133
		
	hbsEhServiceClosedToHsu TRAP-TYPE
		ENTERPRISE winlink1000
		VARIABLES { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { major }
		--&MESG "$'1"
		DESCRIPTION
		"
		Indicates an encryption key mismatch.
		Contains a single parameter, which is its description, including the HSU's name
		"
		::= 134

	hbsUnsynchronizedHsuAlarm TRAP-TYPE
		ENTERPRISE winlink1000
		VARIABLES { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { critical }
		--&MESG "$'1"
		DESCRIPTION
		"
		Indicates a registered HSU lost synchronization.
		"
		::= 135
		
	hbsInactiveHbsAlarm TRAP-TYPE
		ENTERPRISE winlink1000
		VARIABLES { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { major }
		--&MESG "$'1"
		DESCRIPTION
		"
		Indicates HBS is InActive.
		"
		::= 136
		
	incompatibleHsu TRAP-TYPE
		ENTERPRISE winlink1000
		VARIABLES { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { critical }
		--&MESG "$'1"
		DESCRIPTION
		"
		Indicates that the HSU is not compatible to HBS.
		Contains a single parameter, which is its description:
		1 - Description: Incompatible ODUs.
		"
		::= 137
		
	hsuUnsupportedBeacon TRAP-TYPE
		ENTERPRISE winlink1000
		VARIABLES { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { warning }
		--&MESG "$'1"
		DESCRIPTION
		"
		Indicates an unsupported beacon has arrived at HSU
		"
		::= 138
		
	lanPortDisconnectedAlarm TRAP-TYPE
		ENTERPRISE winlink1000
		VARIABLES { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { major }
		--&MESG "$'1"
		DESCRIPTION
		"
		Indicates the LAN port status changed to disconnected.		
		Contains a single parameter, which is its description:
		1 - Description: LAN port status changed to disconnected.
		"
		::= 139
		
	poePortDisconnectedAlarm TRAP-TYPE
		ENTERPRISE winlink1000
		VARIABLES { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { major }
		--&MESG "$'1"
		DESCRIPTION
		"
		Indicates the LAN2 port status changed to disconnected.		
		Contains a single parameter, which is its description:
		1 - Description: LAN2 port status changed to disconnected.
		"
		::= 140
		
	poePowerConsumptionAlarm TRAP-TYPE
		ENTERPRISE winlink1000
		VARIABLES { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { major }
		--&MESG "$'1"
		DESCRIPTION
		"
		Indicates the POE Power Consumption is above allowed maximum.		
		Contains a single parameter, which is its description:
		1 - Description: POE consumption above allowed maximum. port closed.
		"
		::= 141
		
	hobupFaultyStateAlarm TRAP-TYPE
		ENTERPRISE winlink1000
		VARIABLES { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { major }
		--&MESG "$'1"
		DESCRIPTION
		"
		This Alarm will indicate that the Hot Backup module is in faulty state.
		1 - Description: Hot Backup fault detected: %s unit.
		%s - Primary Or Secondary Unit
		"
		::= 149

	gpsOverCurrentAlarm TRAP-TYPE
		ENTERPRISE winlink1000
		VARIABLES { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { major }
		--&MESG "$'1"
		DESCRIPTION
		"
		Indicates the GPS Antenna current consumption is above allowed maximum.		
		Contains a single parameter, which is its description:
		1 - Description: GPS Antenna current consumption above allowed maximum. GPS closed.
		"
		::= 150
		
	gpsCommunicationFailiureAlarm TRAP-TYPE
		ENTERPRISE winlink1000
		VARIABLES { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { major }
		--&MESG "$'1"
		DESCRIPTION
		"
		Indicates the GPS data isn't received.		
		Contains a single parameter, which is its description:
		1 - Description: GPS Communication failiure.
		"
		::= 151
	
	temperatureThresholdAlarm TRAP-TYPE
		ENTERPRISE winlink1000
		VARIABLES { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { major }
		--&MESG "$'1"
		DESCRIPTION
		"
		Indicates the board temperature is above allowed maximum.		
		Contains a single parameter, which is its description:
		1 - Description: GPS Antenna current consumption above allowed maximum. GPS closed.
		"
		::= 152
		
	localRouterDiscoveryStatus TRAP-TYPE
		ENTERPRISE winlink1000
		VARIABLES { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { major }
		--&MESG "$'1"
		DESCRIPTION
		"
		This Alarm will indicate that we have no connection with local train router.
		1 - Description: MacLearningUpdate detected disconnection with local train router %s
		%s - local train IP
		"
		::= 153
	
	trackRouterDiscoveryStatus TRAP-TYPE
		ENTERPRISE winlink1000
		VARIABLES { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { major }
		--&MESG "$'1"
		DESCRIPTION
		"
		This Alarm will indicate that we have no connection with Track side router.
		1 - Description: MacLearningUpdate detected disconnection with Track side router %s
		%s - Default gateway IP
		"
		::= 154
		
	lastUserSnmpAccessOverHourAgo TRAP-TYPE
		ENTERPRISE winlink1000
		VARIABLES { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { normal }
		--&MESG "$'1"
		DESCRIPTION
		"
		This trap will indicate that the last access of the accessing user was more than an hour ago.
		1 - Description: User %s performed SNMP access after more than an hour.
		%s - user name
		"
		::= 155
		
	btsTargetUnreachable TRAP-TYPE
		ENTERPRISE winlink1000
		VARIABLES { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { major }
		--&MESG "$'1"
		DESCRIPTION
		"
		This Alarm will indicate that we have no connection with Bts desired target.
		1 - Description: TNC detected disconnection with the BTS target %s
		%s - Default gateway IP
		"
		::= 156
		
	tdmServiceClear TRAP-TYPE
		ENTERPRISE winlink1000
		VARIABLES   { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { normal }
		--&CLEARS   { 100 }
		--&MESG     "$'1"
		DESCRIPTION
		"
		Indicates that TDM Service fault is cleared.
		Contains a single parameter, which is its description:
		1 - Description: TDM Service - Normal.
		"
		::= 200

	ethServiceOpened TRAP-TYPE
		ENTERPRISE winlink1000
		VARIABLES   { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { normal }
		--&CLEARS   { 101 }
		--&MESG     "$'1"
		DESCRIPTION
		"
		Indicates that Ethernet Service has been opened.
		Contains a single parameter, which is its description:
		1 - Description: Ethernet Service has been opened.
		"
		::= 201

	encryptionClear TRAP-TYPE
		ENTERPRISE winlink1000
		VARIABLES   { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { normal }
		--&CLEARS   { 103 }
		--&MESG     "$'1"
		DESCRIPTION
		"
		Indicates that encryption is OK.
		Contains a single parameter, which is its description:
		1 - Description: Encryption Status - Normal.
		"
		::= 203

	changeLinkPasswordClear TRAP-TYPE
		ENTERPRISE winlink1000
		VARIABLES   { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { normal }
		--&CLEARS   { 104 }
		--&MESG     "$'1"
		DESCRIPTION
		"
		Indicates that the Link Password was changed successfully.
		Contains a single parameter, which is its description:
		1 - Description: Link Password has been changed at/on: %s.
		%s - Is the Local Site name or Remote Site name or both sides of the Link.
		"
		::= 204

	externalAlarmInPort1Clear TRAP-TYPE
		ENTERPRISE winlink1000
		VARIABLES   { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { normal }
		--&CLEARS   { 105 }
		--&MESG     "$'1"
		DESCRIPTION
		"
		This Trap is sent every time an External Alarm Input fault of port # 1 is cleared.
		Contains a single parameter, which is its description:
		1 - Description: External Alarm 1 - <User Text> - Alarm Cleared.
		"
		::= 205	

	externalAlarmInPort2Clear TRAP-TYPE
		ENTERPRISE winlink1000
		VARIABLES   { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { normal }
		--&CLEARS   { 106 }
		--&MESG     "$'1"
		DESCRIPTION
		"
		This Trap is sent every time an External Alarm Input fault of port # 2 is cleared.
		Contains a single parameter, which is its description:
		1 - Description: External Alarm 2 - <User Text> - Alarm Cleared.
		"
		::= 206
		
	lanPort1Clear TRAP-TYPE
		ENTERPRISE winlink1000
		VARIABLES   { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { normal }
		--&CLEARS   { 109 }
		--&MESG     "$'1"
		DESCRIPTION
		"
		Indicates the LAN port 1 status changed to connected.
		Contains two parameters:
		1 - Description: LAN port 1 status changed to connected - %s
		2 - %s Is the Eth. mode (speed & duplex)
		"
		::= 209
		
	lanPort2Clear TRAP-TYPE
		ENTERPRISE winlink1000
		VARIABLES   { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { normal }
		--&CLEARS   { 110 }
		--&MESG     "$'1"
		DESCRIPTION
		"
		Indicates the LAN port 2 status changed to connected.
		Contains two parameters:
		1 - Description: LAN port 2 status changed to connected - %s.
		2 - %s Is the Eth. mode (speed & duplex).
		"
		::= 210
		
	mngPortClear TRAP-TYPE
		ENTERPRISE winlink1000
		VARIABLES   { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { normal }
		--&CLEARS   { 111 }
		--&MESG     "$'1"
		DESCRIPTION
		"
		Indicates the LAN1 port status changed to connected.
		Contains two parameters:
		1 - Description: LAN1 port status changed to connected - %s
		2 - %s Is the Eth. mode (speed & duplex)
		"
		::= 211

	externalAlarmInPort3Clear TRAP-TYPE
		ENTERPRISE winlink1000
		VARIABLES   { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { normal }
		--&CLEARS   { 112 }
		--&MESG     "$'1"
		DESCRIPTION
		"
		This Trap is sent every time an External Alarm Input fault of port # 3 is cleared.
		Contains a single parameter, which is its description:
		1 - Description: External Alarm 3 - <User Text> - Alarm Cleared.
		"
		::= 212	

	externalAlarmInPort4Clear TRAP-TYPE
		ENTERPRISE winlink1000
		VARIABLES   { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { normal }
		--&CLEARS   { 113 }
		--&MESG     "$'1"
		DESCRIPTION
		"
		This Trap is sent every time an External Alarm Input fault of port # 4 is cleared.
		Contains a single parameter, which is its description:
		1 - Description: External Alarm 4 - <User Text> - Alarm Cleared.
		"
		::= 213
	
	swVersionsMatchFullCompatibilityClear TRAP-TYPE
		ENTERPRISE winlink1000
		VARIABLES   { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { normal }
		--&CLEARS   { 114 }
		--&MESG     "$'1"
		DESCRIPTION
		"
		The trap is sent if SW versions match.
		Contains a single parameter, which is its description:
		1 - Description: Software Versions compatible
		"
		::= 214

	swVersionsMatchRestrictedCompatibilityClear TRAP-TYPE
		ENTERPRISE winlink1000
		VARIABLES   { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { normal }
		--&CLEARS   { 115 }
		--&MESG     "$'1"
		DESCRIPTION
		"
		The trap is sent if SW versions match and link functionality is not restricted.
		Contains a single parameter, which is its description:
		1 - Description: Software Versions compatible
		"
		::= 215

	swVersionsMatchSoftwareUpgradeRequiredClear TRAP-TYPE
		ENTERPRISE winlink1000
		VARIABLES   { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { normal }
		--&CLEARS   { 116 }
		--&MESG     "$'1"
		DESCRIPTION
		"
		The trap is sent if SW versions match and SW upgrade is successful.
		Contains a single parameter, which is its description:
		1 - Description: Software Versions compatible
		"
		::= 216

	swVersionsCompatibleClear TRAP-TYPE
		ENTERPRISE winlink1000
		VARIABLES   { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { normal }
		--&CLEARS   { 117 }
		--&MESG     "$'1"
		DESCRIPTION
		"
		The trap is sent if SW versions compatible
		Contains a single parameter, which is its description:
		1 - Description: Software Versions compatible
		"
		::= 217

	hssMultipleSourcesDisappearedClear TRAP-TYPE
		ENTERPRISE winlink1000
		VARIABLES   { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { normal }
		--&CLEARS   { 118 }
		--&MESG     "$'1"
		DESCRIPTION
		"
		Indicates that multiple sync pulse sources disappeared.
		Contains a single parameter, which is its description:
		1 - Description: HSS multiple sync pulse sources disappeared.
		"
		::= 218

	hssSyncToProperSourceAchievedClear TRAP-TYPE
		ENTERPRISE winlink1000
		VARIABLES   { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { normal }
		--&CLEARS   { 119 }
		--&MESG     "$'1"
		DESCRIPTION
		"
		Indicates that synchronization to a proper Sync source was achieved.
		Contains a single parameter, which is its description:
		1 - Description: HSS sync pulse - Up.
		"
		::= 219

	hssSyncPulseDisappearedClear TRAP-TYPE
		ENTERPRISE winlink1000
		VARIABLES   { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { normal }
		--&CLEARS   { 120 }
		--&MESG     "$'1"
		DESCRIPTION
		"
		Indicates that HSS additional sync pulse disappeared.
		Contains a single parameter, which is its description:
		1 - Description: HSS additional sync pulse was disappeared.		
		"
		::= 220

	tdmBackupClear TRAP-TYPE
		ENTERPRISE winlink1000
		VARIABLES   { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { normal }
		--&CLEARS   { 121 }
		--&MESG     "$'1"
		DESCRIPTION
		"
		Indicates that the TDM main link was activated.
		Contains a single parameter, which is its description:
		1 - Description: TDM main link was activated.
		"
		::= 221
		
	linkLockAuthorizedRemoteODU TRAP-TYPE
		ENTERPRISE winlink1000
		VARIABLES   { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { normal }
		--&CLEARS   { 122 }
		--&MESG     "$'1"
		DESCRIPTION
		"
		Indicates that the remote ODU is authorized.
		Contains a single parameter, which is its description:
		1 - Description: Authorized remote ODU connection accepted.
		"
		::= 222

	linkLockAuthorizedODU TRAP-TYPE
		ENTERPRISE winlink1000
		VARIABLES   { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { normal }
		--&CLEARS   { 123 }
		--&MESG     "$'1"
		DESCRIPTION
		"
		Indicates that the ODU is authorized.
		Contains a single parameter, which is its description:
		1 - Description: Authorized ODU connection permitted.
		"
		::= 223		

	linkAuthenticationDisabled TRAP-TYPE
		ENTERPRISE winlink1000
		VARIABLES   { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { normal }
		--&CLEARS   { 122 }
		--&MESG     "$'1"
		DESCRIPTION
		"
		Indicates that the Link Lock is disabled.
		Contains a single parameter, which is its description:
		1 - Description: Link Authentication has been disabled.
		"
		::= 224	

	hotStandbyClear TRAP-TYPE
		ENTERPRISE winlink1000
		VARIABLES   { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { normal }
		--&CLEARS   { 124 }
		--&MESG     "$'1"
		DESCRIPTION
		"
		Indicates that the Primary Link Was Activated.
		Contains a single parameter, which is its description:
		1 - Description: Primary Link Is Active.
		"
		::= 225
		
	sfpExtraction TRAP-TYPE
		ENTERPRISE winlink1000
		VARIABLES   { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { normal }
		--&MESG     "$'1"
		DESCRIPTION
		"
		Indicates that a device was extracted from SFP Port
		"
		::= 226

	sfpPort1Clear TRAP-TYPE
		ENTERPRISE winlink1000
		VARIABLES   { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { normal }
		--&CLEARS   { 127 }
		--&MESG     "$'1"
		DESCRIPTION
		"
		Indicates the SFP port 1 status changed to connected.
		Contains two parameters:
		1 - Description: SFP port 1 status changed to connected - %s
		2 - %s Is the Eth. mode (speed & duplex)
		"
		::= 227

	compatibleIdus TRAP-TYPE
		ENTERPRISE winlink1000
		VARIABLES   { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { normal }
		--&CLEARS   { 10 }
		--&MESG     "$'1"
		DESCRIPTION
		"
		Indicates that the ODU has identified compatible Idus on both sides of the link.
		"
		::= 228	

	desiredRatioCanNotBeAppliedClear TRAP-TYPE
		ENTERPRISE winlink1000
		VARIABLES   { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { normal }
		--&CLEARS   { 129 }
		--&MESG     "$'1"
		DESCRIPTION
		"
		Indicates Current UL/DL Ratio Is Equal To Desired Ratio.
		"
		::= 229
		
	cbwMatch TRAP-TYPE
		ENTERPRISE winlink1000
		VARIABLES   { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { normal }
		--&CLEARS   { 130 }
		--&MESG     "$'1"
		DESCRIPTION
		"
		Indicates that a Channel Bandwidth match was detected.
		Contains a single parameter, which is its description:
		1 - Channel Bandwidth value in MHz.
		"
		::= 230
		
	switchCbwAndChannel TRAP-TYPE
		ENTERPRISE winlink1000
		VARIABLES   { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { normal }
		--&MESG     "$'1"
		DESCRIPTION
		"
		Indicates that the system is switching Channel Bandwidth and channel frequency.
		Contains two parameters:
		1 - Switching to Channel Bandwith %n0 MHz and to channel %n1 GHz.
		"
		::= 231			
		
	ringRplStateIdle TRAP-TYPE
		ENTERPRISE winlink1000
		VARIABLES   { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { normal }
		--&CLEARS   { 128 }
		--&MESG     "$'1"
		DESCRIPTION
		"
		RPL state changed to Idle.
		"
		::= 232
		
	ringEthServiceStatus TRAP-TYPE
		ENTERPRISE winlink1000
		VARIABLES   { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { normal }		
		--&MESG     "$'1"
		DESCRIPTION
		"
		Indicates Ethernet service's state - blocked \ unblocked.
		Contains a single parameter:
		1 - Description: Ethernet's state (blocked \ unblocked)
		"
		::= 233
		
	ringFirstRpmReceived TRAP-TYPE
		ENTERPRISE winlink1000
		VARIABLES   { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { normal }		
		--&MESG     "$'1"
		DESCRIPTION
		"
		Ring application: in non-RPL link indicates first from a specific RPL was received.
		Contains a single parameter:
		1 - Description: RPM's VLAN ID
		"
		::= 234
		
	ringEthernetSrviceUnblockedTO TRAP-TYPE
		ENTERPRISE winlink1000
		VARIABLES   { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { normal }		
		--&MESG     "$'1"
		DESCRIPTION
		"
		Ring application: in non-RPL link Ethernet service is unblocked due to RPM timeout.		
		"
		::= 235
		
	gpsSynchronized TRAP-TYPE
		ENTERPRISE winlink1000
		VARIABLES   { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { normal }
		--&CLEARS   { 131 }
		--&MESG     "$'1"
		DESCRIPTION
		"
		Indicates that the GPS is synchronized with satellites.
		"
		::= 236

	hbsEncryptionClear TRAP-TYPE
		ENTERPRISE winlink1000
		VARIABLES   { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { normal }
		--&CLEARS   { 133 }
		--&MESG     "$'1"
		DESCRIPTION
		"
		Indicates that encryption is OK.
		Contains a single parameter, which is its description, including the HSU's name
		"
		::= 237
		
	hbsEhServiceOpenedToHsu TRAP-TYPE
		ENTERPRISE winlink1000
		VARIABLES   { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { normal }
		--&CLEARS   { 134 }
		--&MESG     "$'1"
		DESCRIPTION
		"
		Indicates that encryption is OK.
		Contains a single parameter, which is its description, including the HSU's name
		"
		::= 238

	hbsSynchronizedHsuAlarm TRAP-TYPE
		ENTERPRISE winlink1000
		VARIABLES   { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { normal }
		--&CLEARS   { 135 }
		--&MESG     "$'1"
		DESCRIPTION
		"
		Indicates a registered HSU is synchronized.
		"
		::= 239
		
	hbsActiveHbs TRAP-TYPE
		ENTERPRISE winlink1000
		VARIABLES   { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { normal }
		--&CLEARS   { 136 }
		--&MESG     "$'1"
		DESCRIPTION
		"
		Indicates when HBS has been activated.
		"
		::= 240
		
	switchCBW TRAP-TYPE
		ENTERPRISE winlink1000
		VARIABLES   { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { normal }
		--&MESG     "$'1"
		DESCRIPTION
		"
		Switching Channel Bandwidth.
		"
		::= 241		

	changeRatio TRAP-TYPE
		ENTERPRISE winlink1000
		VARIABLES   { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { normal }
		--&MESG     "$'1"
		DESCRIPTION
		"
		HBS Tx ratio has changed.
		"
		::= 242			

	lanPortClear TRAP-TYPE
		ENTERPRISE winlink1000
		VARIABLES   { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { normal }
		--&CLEARS   { 139 }
		--&MESG     "$'1"
		DESCRIPTION
		"
		Indicates the LAN port status changed to connected.
		Contains two parameters:
		1 - Description: LAN port status changed to connected - %s
		2 - %s Is the Eth. mode (speed & duplex)
		"
		::= 243

	poePortClear TRAP-TYPE
		ENTERPRISE winlink1000
		VARIABLES   { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { normal }
		--&CLEARS   { 140 }
		--&MESG     "$'1"
		DESCRIPTION
		"
		Indicates the LAN2 port status changed to connected.
		Contains two parameters:
		1 - Description: LAN2 port status changed to connected - %s
		2 - %s Is the Eth. mode (speed & duplex)
		"
		::= 244	
		
	poePowerConsumptionClear TRAP-TYPE
		ENTERPRISE winlink1000
		VARIABLES   { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { normal }
		--&CLEARS   { 141 }
		--&MESG     "$'1"
		DESCRIPTION
		"
		Indicates the POE power consumption is valid.
		Contains two parameters:
		1 - Description: POE consumption within limits. port is opened.
		2 - %s Is the Eth. mode (speed & duplex)
		"
		::= 245

	incompatibleHbsHsu TRAP-TYPE
		ENTERPRISE winlink1000
		VARIABLES   { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { normal }
		--&MESG     "$'1"
		DESCRIPTION
		"
		Incompatible HBS/HSU software versions - no service.
		"
		::= 246

	mobilityLinkOff TRAP-TYPE
		ENTERPRISE winlink1000
		VARIABLES   { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { normal }
		--&MESG     "$'1"
		DESCRIPTION
		"
		Mobility - Link cannot be established due to:
		1 - The HBS does not support Mobility
		2 - Lack of resources in the HBS for HSU level
		"
		::= 247

	enterLocalConnection TRAP-TYPE
		ENTERPRISE winlink1000
		VARIABLES   { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { normal }
		--&MESG     "$'1"
		DESCRIPTION
		"
		Entering Local Connection (Broadcast) Mode.
		"
		::= 248	
	
	hobupActiveStateFaultyClear TRAP-TYPE
		ENTERPRISE winlink1000
		VARIABLES   { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { normal }
		--&CLEARS   { 149 }
		--&MESG     "$'1"
		DESCRIPTION
		"
		this clear alarm will indicate that the Hot Backup unit is in active state.
		Contains a single parameter, which is its description:
		1 - Description: Hot Backup %s unit activated.
		%s - Primary Or Secondary Unit
		"	
		::= 249	
		
	hobupStandbyState TRAP-TYPE
		ENTERPRISE winlink1000
		VARIABLES   { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { normal }
		--&MESG     "$'1"
		DESCRIPTION
		"
		This info fault will indicate that the Hot backup module has entered standby/peer_detection state
		Contains a single parameter, which is its description:
		1 - Description: Hot Backup in Standby state: %s unit.
		%s - Primary Or Secondary Unit
		"	
		::= 250		

	gpsOverCurrentClear TRAP-TYPE
		ENTERPRISE winlink1000
		VARIABLES   { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { normal }
		--&CLEARS   { 150 }
		--&MESG     "$'1"
		DESCRIPTION
		"
		Indicates the GPS Antenna current consumption is valid.
		"
		::= 251
		
	temperatureThresholdClear TRAP-TYPE
		ENTERPRISE winlink1000
		VARIABLES   { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { normal }
		--&CLEARS   { 152 }
		--&MESG     "$'1"
		DESCRIPTION
		"
		Indicates the board temperature is valid.
		"
		::= 252		
		
	localRouterDiscoverySucceed TRAP-TYPE
		ENTERPRISE winlink1000
		VARIABLES   { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { normal }
		--&CLEARS   { 153 }
		--&MESG     "$'1"
		DESCRIPTION
		"
		Indicated the we succeeded to discover train router in ip %s MAC address %s
		%s Train IP
		%s Train MAC Address
		"
		::= 253	
	
	trackRouterDiscoverySucceed TRAP-TYPE
		ENTERPRISE winlink1000
		VARIABLES   { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { normal }
		--&CLEARS   { 154 }
		--&MESG     "$'1"
		DESCRIPTION
		"
		Indicated the we succeeded to discover track router in ip %s MAC address %s
		%s Train IP
		%s Train MAC Address
		"
		::= 254	
		
	qosVersion2StrictMismatch TRAP-TYPE
		ENTERPRISE winlink1000
		VARIABLES   { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { normal }
		--&MESG     "$'1"
		DESCRIPTION
		"
		CPE  doesn't support strict QOS configuration.
		"	
		::= 255
		
	qosVersion2TtlMismatch TRAP-TYPE
		ENTERPRISE winlink1000
		VARIABLES   { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { normal }
		--&MESG     "$'1"
		DESCRIPTION
		"
		CPE doesn't support TTL configuration.
		"	
		::= 256
		
	btsTargetIsReachable TRAP-TYPE
		ENTERPRISE winlink1000
		VARIABLES   { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { normal }
		--&CLEARS   { 156 }
		--&MESG     "$'1"
		DESCRIPTION
		"
		Indicated the we succeeded to establish connection with the Bts desired target (%s)
		%s Target IP
		"
		::= 257
		
	tcNotSupportedByHSU TRAP-TYPE
		ENTERPRISE winlink1000
		VARIABLES   { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { normal }
		--&MESG     "$'1"
		DESCRIPTION
		"
		CPE doesn't support TC functionality.
		"	
		::= 258
		
	syncEPortHOStateChange TRAP-TYPE
		ENTERPRISE winlink1000
		VARIABLES   { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { normal }
		--&MESG     "$'1"
		DESCRIPTION
		"
		Enter/leave HO state of SyncE port.
		"	
		::= 259
		
	syncEPortFailureStateChange TRAP-TYPE
		ENTERPRISE winlink1000
		VARIABLES   { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { normal }
		--&MESG     "$'1"
		DESCRIPTION
		"
		Enter/leave Failure state of SyncE port.
		"	
		::= 260
		
	btsCpeUpdateServiceFailed TRAP-TYPE
		ENTERPRISE winlink1000
		VARIABLES   { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { normal }
		--&MESG     "$'1"
		DESCRIPTION
		"
		Update service Failed
		"	
		::= 261
		
	btsCpeUpdateServiceSucceed TRAP-TYPE
		ENTERPRISE winlink1000
		VARIABLES   { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { normal }
		--&MESG     "$'1"
		DESCRIPTION
		"
		Update service Succeed
		"	
		::= 262
	radiusServerNoREsponse TRAP-TYPE
		ENTERPRISE winlink1000
		VARIABLES   { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { normal }
		--&MESG     "$'1"
		DESCRIPTION
		"
		No response from radius server
		"	
		::= 263	
	noRadiusServerRespond TRAP-TYPE
		ENTERPRISE winlink1000
		VARIABLES   { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { major }
		--&MESG     "$'1"
		DESCRIPTION
		"
		Alarm indicates that no Radius server is connected
		"	
		::= 264	
	radiusServerRespondedSuccessfully TRAP-TYPE
		ENTERPRISE winlink1000
		VARIABLES   { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { normal }
		--&CLEARS   { 264 }
		--&MESG     "$'1"
		DESCRIPTION
		"
		indicates that Radius server responded seccessfully.
		"	
		::= 265	

	bsaAlignmentStarted TRAP-TYPE
		ENTERPRISE winlink1000
		VARIABLES   { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { normal }
		--&MESG     "$'1"
		DESCRIPTION
		"
		Indicate the beginning of Alignment Process
		"
		::= 266
		
	bsaAlignmentFinished TRAP-TYPE
		ENTERPRISE winlink1000
		VARIABLES   { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { normal }
		--&MESG     "$'1"
		DESCRIPTION
		"
		Indicate the completion of Alignment Process
		"
		::= 267
		
	bsaAlignmentTriggered TRAP-TYPE
		ENTERPRISE winlink1000
		VARIABLES   { winlink1000GeneralTrapDescription, winlink1000OduAgnCurrAlarmSeverity, winlink1000OduAgnCurrAlarmIfIndex,
		winlink1000OduAgnCurrAlarmUnit, winlink1000OduAgnCurrAlarmTimeT, winlink1000OduAgnCurrAlarmId }
		--&ACTIONS  { normal }
		--&MESG     "$'1"
		DESCRIPTION
		"
		Indicate the triggering of Alignment Process due to exceeding thresholds
		"
		::= 268

	-- ###########################################################
	--                 Products Section
	-- ###########################################################


	radwinProducts			OBJECT IDENTIFIER ::= { radwin 20 }
	winlink1000Family		OBJECT IDENTIFIER ::= { radwinProducts 2 } 
	radwin2000Family		OBJECT IDENTIFIER ::= { radwinProducts 3 }
	gpsSynchronizerFamily	OBJECT IDENTIFIER ::= { radwinProducts 4 }
	radwin5000HBSFamily		OBJECT IDENTIFIER ::= { radwinProducts 5 }
	radwin5000HSUFamily		OBJECT IDENTIFIER ::= { radwinProducts 6 }
	radwin6000Family		OBJECT IDENTIFIER ::= { radwinProducts 10 }
	radwinWiFiAPFamily		OBJECT IDENTIFIER ::= { radwinProducts 20 }


	--
	-- the following identifiers are assigned to ODU Products
	--        

	odu	       					OBJECT IDENTIFIER ::= { winlink1000Family 1 }

	oduIntegratedAntenna        OBJECT IDENTIFIER ::= { odu 1 }
	oduExternalAntenna          OBJECT IDENTIFIER ::= { odu 2 }

	--
	-- Suffix 3,4,5,6,7,8,9,10,11,12,13,14,15,16 in the products section
	-- are reserved for backward compatibility.
	--

	odu2000    					OBJECT IDENTIFIER ::= { radwin2000Family 1 }

	odu2KIntegratedAntenna        OBJECT IDENTIFIER ::= { odu2000 1 }
	odu2KExternalAntenna          OBJECT IDENTIFIER ::= { odu2000 2 }

	oduGSU						OBJECT IDENTIFIER ::= { gpsSynchronizerFamily 1 }
	
	oduGSUExternalAntenna		OBJECT IDENTIFIER ::= { oduGSU 2 }

	hssSyncUnits				OBJECT IDENTIFIER ::= { gpsSynchronizerFamily 2 }
	
	hssISU						OBJECT IDENTIFIER ::= { hssSyncUnits 1 }
	hssGSU						OBJECT IDENTIFIER ::= { hssSyncUnits 2 }

	oduHBS    					OBJECT IDENTIFIER ::= { radwin5000HBSFamily 1 }

	oduHBSIntegratedAntenna		OBJECT IDENTIFIER ::= { oduHBS 1 }
	oduHBSExternalAntenna		OBJECT IDENTIFIER ::= { oduHBS 2 }
	
	oduHSU    					OBJECT IDENTIFIER ::= { radwin5000HSUFamily 1 }

	oduHSUIntegratedAntenna		OBJECT IDENTIFIER ::= { oduHSU 1 }
	oduHSUExternalAntenna		OBJECT IDENTIFIER ::= { oduHSU 2 }	

	odu6000    					OBJECT IDENTIFIER ::= { radwin6000Family 1 }

	odu6K						OBJECT IDENTIFIER ::= { odu6000 1 }
	
	gateway6000    				OBJECT IDENTIFIER ::= { radwin6000Family 2 }

	gateway6K						OBJECT IDENTIFIER ::= { gateway6000 1 }
	
	odu600    					OBJECT IDENTIFIER ::= { radwinWiFiAPFamily 1 }

	oduWiFiAP					OBJECT IDENTIFIER ::= { odu600 1 }
	
	END
