TACACS-CLIENT-MIB DEFINITIONS ::= BEGIN

IMPORTS
       MODULE-IDENTITY, OBJECT-TYPE, OBJECT-IDENTITY,
       Counter32, Integer32, Gauge32,
       IpAddress, TimeTicks, mib-2      FROM SNMPv2-SMI
       SnmpAdminString                  FROM SNMP-FRAMEWORK-MIB
       MODULE-COMPLIANCE, OBJECT-GROUP  FROM SNMPv2-CONF
       cadAuthentication  		FROM CADANT-PRODUCTS-MIB;

tacacsClientMIB MODULE-IDENTITY
       LAST-UPDATED "200310160000Z" -- 16 Oct 2003
       ORGANIZATION "Arris International Inc."
       CONTACT-INFO
              " Customer Support

		Postal: Arris International Inc.
        	4343 Commerce Court
        	Lisle, IL 60532
		
		Phone:  +1 630 281 3000
		Email:  support@cadant.com"
       DESCRIPTION
             "The MIB module for entities implementing the client
              side of the TACACS+ protocol."
       REVISION "200303140000Z"    -- 14 Mar 2003
       DESCRIPTION "Initial version"
       REVISION "200310160000Z"  
       DESCRIPTION "In tacacsServerEntry table, replaced round trip time 
		with server unreachables count"
       ::= { cadAuthentication 10 }

tacacsClientMIBObjects OBJECT IDENTIFIER ::= { tacacsClientMIB 1 }
tacacsClient OBJECT IDENTIFIER ::= { tacacsClientMIBObjects 1 }

tacacsClientInvalidServerAddresses OBJECT-TYPE
      SYNTAX Counter32
      MAX-ACCESS read-only
      STATUS current
      DESCRIPTION
            "The number of TACACS+ response packets
             received from unknown addresses."
      ::= { tacacsClient 1 }

tacacsClientIdentifier OBJECT-TYPE
      SYNTAX SnmpAdminString
      MAX-ACCESS read-only
      STATUS current
      DESCRIPTION
             "The NAS-Identifier of the TACACS+ client.
              This is not necessarily the same as sysName in MIB II."
      ::= { tacacsClient 2 }

tacacsServerTable OBJECT-TYPE
      SYNTAX     SEQUENCE OF TacacsServerEntry
      MAX-ACCESS not-accessible
      STATUS     current
      DESCRIPTION
            "The (conceptual) table listing the TACACS+ 
             servers with which the client shares a secret."
      ::= { tacacsClient 3 }

tacacsServerEntry OBJECT-TYPE
      SYNTAX     TacacsServerEntry
      MAX-ACCESS not-accessible
      STATUS     current
      DESCRIPTION
            "An entry (conceptual row) representing a TACACS+
             server with which the client shares
             a secret."
      INDEX      { tacacsServerIndex }
      ::= { tacacsServerTable 1 }

TacacsServerEntry ::= SEQUENCE {
      tacacsServerIndex                           Integer32,
      tacacsServerAddress                         IpAddress,
      tacacsClientServerUnreachables              Counter32,
      tacacsClientAuthLoginRequests               Counter32,
      tacacsClientAuthEnableRequests              Counter32,
      tacacsClientAuthPassResponses               Counter32,
      tacacsClientAuthFailResponses               Counter32,
      tacacsClientAuthGetDataResponses            Counter32,
      tacacsClientAuthGetUserResponses            Counter32,
      tacacsClientAuthGetPassResponses            Counter32,
      tacacsClientAuthRestartResponses            Counter32,
      tacacsClientAuthErrorResponses              Counter32,
      tacacsClientAuthFollowResponses             Counter32,
      tacacsClientAuthorRequests                  Counter32,
      tacacsClientAuthorPassAddResponses          Counter32,
      tacacsClientAuthorPassReplResponses         Counter32,
      tacacsClientAuthorFailResponses             Counter32,
      tacacsClientAuthorErrorResponses            Counter32,
      tacacsClientAuthorFollowResponses           Counter32,
      tacacsClientAccStartRequests                Counter32,
      tacacsClientAccStopRequests                 Counter32,
      tacacsClientAccSuccessResponses             Counter32,
      tacacsClientAccErrorResponses               Counter32,
      tacacsClientAccFollowResponses		  Counter32,
      tacacsClientMalformedPackets		  Counter32,
      tacacsClientInvalidMessageTypes		  Counter32,
      tacacsClientInvalidSequenceNumbers          Counter32,
      tacacsClientInvalidSessionIds               Counter32
}

tacacsServerIndex OBJECT-TYPE
      SYNTAX     Integer32 (1..2147483647)
      MAX-ACCESS not-accessible
      STATUS     current
      DESCRIPTION
             "A number uniquely identifying each TACACS+
             server with which this client
             communicates."
      ::= { tacacsServerEntry 1 }

tacacsServerAddress OBJECT-TYPE
      SYNTAX     IpAddress
      MAX-ACCESS read-only
      STATUS     current
      DESCRIPTION
            "The IP address of the TACACS+ server
             referred to in this table entry."
      ::= { tacacsServerEntry 2 }

tacacsClientServerUnreachables OBJECT-TYPE
      SYNTAX Counter32
      MAX-ACCESS read-only
      STATUS current
      DESCRIPTION
            "The number of TACACS+ packets that were dropped because
             the TACACS+ server was unreachable."
      ::= { tacacsServerEntry 3 }

tacacsClientAuthLoginRequests OBJECT-TYPE
      SYNTAX Counter32
      MAX-ACCESS read-only
      STATUS current
      DESCRIPTION
            "The number of TACACS+ authentication Login-Request packets sent
             to this server."
      ::= { tacacsServerEntry 4 }

tacacsClientAuthEnableRequests OBJECT-TYPE
      SYNTAX Counter32
      MAX-ACCESS read-only
      STATUS current
      DESCRIPTION
            "The number of TACACS+ authentication Enable-Request packets sent
             to this server."
      ::= { tacacsServerEntry 5 }

tacacsClientAuthPassResponses OBJECT-TYPE
      SYNTAX Counter32
      MAX-ACCESS read-only
      STATUS current
      DESCRIPTION
            "The number of TACACS+ authentication Pass-Response packets
             received from this server."
      ::= { tacacsServerEntry 6 }

tacacsClientAuthFailResponses OBJECT-TYPE
      SYNTAX Counter32
      MAX-ACCESS read-only
      STATUS current
      DESCRIPTION
            "The number of TACACS+ authentication Fail-Response packets
             received from this server."
      ::= { tacacsServerEntry 7 }

tacacsClientAuthGetDataResponses OBJECT-TYPE
      SYNTAX Counter32
      MAX-ACCESS read-only
      STATUS current
      DESCRIPTION
            "The number of TACACS+ authentication Get-Data-Response packets
             received from this server."
      ::= { tacacsServerEntry 8 }

tacacsClientAuthGetUserResponses OBJECT-TYPE
      SYNTAX Counter32
      MAX-ACCESS read-only
      STATUS current
      DESCRIPTION
            "The number of TACACS+ authentication Get-User-Response packets
             received from this server."
      ::= { tacacsServerEntry 9 }

tacacsClientAuthGetPassResponses OBJECT-TYPE
      SYNTAX Counter32
      MAX-ACCESS read-only
      STATUS current
      DESCRIPTION
            "The number of TACACS+ authentication Get-Pass-Response packets
             received from this server."
      ::= { tacacsServerEntry 10 }

tacacsClientAuthRestartResponses OBJECT-TYPE
      SYNTAX Counter32
      MAX-ACCESS read-only
      STATUS current
      DESCRIPTION
            "The number of TACACS+ authentication Restart-Response packets
             received from this server."
      ::= { tacacsServerEntry 11 }

tacacsClientAuthErrorResponses OBJECT-TYPE
      SYNTAX Counter32
      MAX-ACCESS read-only
      STATUS current
      DESCRIPTION
            "The number of TACACS+ authentication Error-Response packets
             received from this server."
      ::= { tacacsServerEntry 12 }

tacacsClientAuthFollowResponses OBJECT-TYPE
      SYNTAX Counter32
      MAX-ACCESS read-only
      STATUS current
      DESCRIPTION
            "The number of TACACS+ authentication Follow-Response packets
             received from this server."
      ::= { tacacsServerEntry 13 }

tacacsClientAuthorRequests OBJECT-TYPE
      SYNTAX Counter32
      MAX-ACCESS read-only
      STATUS current
      DESCRIPTION
            "The number of TACACS+ authorization Request packets
             sent to this server."
      ::= { tacacsServerEntry 14 }

tacacsClientAuthorPassAddResponses OBJECT-TYPE
      SYNTAX Counter32
      MAX-ACCESS read-only
      STATUS current
      DESCRIPTION
            "The number of TACACS+ authorization Pass-Add-Response packets
             received from this server."
      ::= { tacacsServerEntry 15 }

tacacsClientAuthorPassReplResponses OBJECT-TYPE
      SYNTAX Counter32
      MAX-ACCESS read-only
      STATUS current
      DESCRIPTION
            "The number of TACACS+ authorization Pass-Repl-Response packets
             received from this server."
      ::= { tacacsServerEntry 16 }

tacacsClientAuthorFailResponses OBJECT-TYPE
      SYNTAX Counter32
      MAX-ACCESS read-only
      STATUS current
      DESCRIPTION
            "The number of TACACS+ authorization Fail-Response packets
             received from this server."
      ::= { tacacsServerEntry 17 }

tacacsClientAuthorErrorResponses OBJECT-TYPE
      SYNTAX Counter32
      MAX-ACCESS read-only
      STATUS current
      DESCRIPTION
            "The number of TACACS+ authorization Error-Response packets
             received from this server."
      ::= { tacacsServerEntry 18 }

tacacsClientAuthorFollowResponses OBJECT-TYPE
      SYNTAX Counter32
      MAX-ACCESS read-only
      STATUS current
      DESCRIPTION
            "The number of TACACS+ authorization Follow-Response packets
             received from this server."
      ::= { tacacsServerEntry 19 }

tacacsClientAccStartRequests OBJECT-TYPE
      SYNTAX Counter32
      MAX-ACCESS read-only
      STATUS current
      DESCRIPTION
            "The number of TACACS+ accounting Start-Request packets
             sent to this server."
      ::= { tacacsServerEntry 20 }

tacacsClientAccStopRequests OBJECT-TYPE
      SYNTAX Counter32
      MAX-ACCESS read-only
      STATUS current
      DESCRIPTION
            "The number of TACACS+ accounting Stop-Request packets
             sent to this server."
      ::= { tacacsServerEntry 21 }

tacacsClientAccSuccessResponses OBJECT-TYPE
      SYNTAX Counter32
      MAX-ACCESS read-only
      STATUS current
      DESCRIPTION
            "The number of TACACS+ accounting Success-Response packets
             received from this server."
      ::= { tacacsServerEntry 22 }

tacacsClientAccErrorResponses OBJECT-TYPE
      SYNTAX Counter32
      MAX-ACCESS read-only
      STATUS current
      DESCRIPTION
            "The number of TACACS+ accounting Error-Response packets
             received from this server."
      ::= { tacacsServerEntry 23 }

tacacsClientAccFollowResponses OBJECT-TYPE
      SYNTAX Counter32
      MAX-ACCESS read-only
      STATUS current
      DESCRIPTION
            "The number of TACACS+ accounting Follow-Response packets
             received from this server."
      ::= { tacacsServerEntry 24 }

tacacsClientMalformedPackets OBJECT-TYPE
      SYNTAX Counter32
      MAX-ACCESS read-only
      STATUS current
      DESCRIPTION
            "The number of TACACS+ malformed packets
             received from this server."
      ::= { tacacsServerEntry 25 }

tacacsClientInvalidMessageTypes OBJECT-TYPE
      SYNTAX Counter32
      MAX-ACCESS read-only
      STATUS current
      DESCRIPTION
            "The number of TACACS+ packets with unknown message type
             received from this server."
      ::= { tacacsServerEntry 26 }

tacacsClientInvalidSequenceNumbers OBJECT-TYPE
      SYNTAX Counter32
      MAX-ACCESS read-only
      STATUS current
      DESCRIPTION
            "The number of TACACS+ packets with invalid sequence numbers
             received from this server."
      ::= { tacacsServerEntry 27 }

tacacsClientInvalidSessionIds OBJECT-TYPE
      SYNTAX Counter32
      MAX-ACCESS read-only
      STATUS current
      DESCRIPTION
            "The number of TACACS+ packets with invalid session ids
             received from this server."
      ::= { tacacsServerEntry 28 }

-- conformance information

tacacsClientMIBConformance
             OBJECT IDENTIFIER ::= { tacacsClientMIB 2 }
tacacsClientMIBCompliances
             OBJECT IDENTIFIER ::= { tacacsClientMIBConformance 1 }
tacacsClientMIBGroups
             OBJECT IDENTIFIER ::= { tacacsClientMIBConformance 2 }


-- compliance statements

tacacsClientMIBCompliance MODULE-COMPLIANCE
     STATUS  current
     DESCRIPTION
           "The compliance statement for clients
            implementing the TACACS+ Client MIB."
     MODULE  -- this module
            MANDATORY-GROUPS { tacacsClientMIBGroup }

     ::= { tacacsClientMIBCompliances 1 }


-- units of conformance

tacacsClientMIBGroup OBJECT-GROUP
     OBJECTS { 	tacacsClientIdentifier,
               	tacacsClientInvalidServerAddresses,
               	tacacsServerAddress,
      		tacacsClientServerUnreachables,
      		tacacsClientAuthLoginRequests,
      		tacacsClientAuthEnableRequests,
      		tacacsClientAuthPassResponses,
      		tacacsClientAuthFailResponses,
      		tacacsClientAuthGetDataResponses,
      		tacacsClientAuthGetUserResponses,
      		tacacsClientAuthGetPassResponses,
      		tacacsClientAuthRestartResponses,
      		tacacsClientAuthErrorResponses,
      		tacacsClientAuthFollowResponses,
      		tacacsClientAuthorRequests,
      		tacacsClientAuthorPassAddResponses,
      		tacacsClientAuthorPassReplResponses,
      		tacacsClientAuthorFailResponses,
      		tacacsClientAuthorErrorResponses,
      		tacacsClientAuthorFollowResponses,
      		tacacsClientAccStartRequests,
      		tacacsClientAccStopRequests,
      		tacacsClientAccSuccessResponses,
      		tacacsClientAccErrorResponses,
      		tacacsClientAccFollowResponses,
      		tacacsClientMalformedPackets,
      		tacacsClientInvalidMessageTypes,
      		tacacsClientInvalidSequenceNumbers 
            }
     STATUS  current
     DESCRIPTION
           "The basic collection of objects providing management of
            TACACS+ Clients."
     ::= { tacacsClientMIBGroups 1 }

END
