Nortel-MsCarrier-MscPassport-AtmTrunksMIB
DEFINITIONS ::= BEGIN



IMPORTS

      OBJECT-TYPE
   FROM RFC-1212

      mscPassportMIBs
   FROM Nortel-MsCarrier-MscPassport-UsefulDefinitionsMIB

      DisplayString,
      StorageType,
      RowStatus,
      Gauge32,
      Unsigned32
   FROM Nortel-MsCarrier-MscPassport-StandardTextualConventionsMIB

      NonReplicated,
      FixedPoint1,
      Link
   FROM Nortel-MsCarrier-MscPassport-TextualConventionsMIB

      mscTrk,
      mscTrkIndex
   FROM Nortel-MsCarrier-MscPassport-TrunksMIB;




-- LAST-UPDATED   "9909010000Z"
-- ORGANIZATION   "Nortel Networks"
-- CONTACT-INFO   "
--         Nortel Carrier Data Network Management
--         
--         Postal:       P.O. Box 3511, Station C 
--                       Ottawa, Ontario 
--                       Canada  K1Y 4H7
--         
--         via the WEB:  http://www.nortelnetworks.com  
--                       select 'Contact Us' from the menu
--          
--         via phone:    1-800-4NORTEL"
-- DESCRIPTION
--    "The module describing the Nortel MsCarrier MscPassport
--     AtmTrunks Enterprise MIB."

atmTrunksMIB OBJECT IDENTIFIER ::= { mscPassportMIBs 59 }










-- Trunk/n AtmAccess
-- The AtmAccess component provides a Layer 2 protocol that adds no 
-- overhead to data on the ATM link that it accesses.

mscTrkAtm OBJECT IDENTIFIER ::= { mscTrk 3 }



mscTrkAtmRowStatusTable OBJECT-TYPE
   SYNTAX     SEQUENCE OF MscTrkAtmRowStatusEntry
   ACCESS     not-accessible
   STATUS     mandatory
   DESCRIPTION
     "This entry controls the addition and deletion of 
      mscTrkAtm components."
::= { mscTrkAtm 1 }

mscTrkAtmRowStatusEntry OBJECT-TYPE
   SYNTAX     MscTrkAtmRowStatusEntry
   ACCESS     not-accessible
   STATUS     mandatory
   DESCRIPTION
     "A single entry in the table represents a single 
      mscTrkAtm component."
   INDEX {
      mscTrkIndex,
      mscTrkAtmIndex }
::= { mscTrkAtmRowStatusTable 1 }

MscTrkAtmRowStatusEntry ::= SEQUENCE {
   mscTrkAtmRowStatus
      RowStatus,
   mscTrkAtmComponentName
      DisplayString,
   mscTrkAtmStorageType
      StorageType,
   mscTrkAtmIndex
      NonReplicated }

mscTrkAtmRowStatus OBJECT-TYPE
   SYNTAX     RowStatus 
   ACCESS     read-write
   STATUS     mandatory
   DESCRIPTION
     "This variable is used as the basis for SNMP naming of
      mscTrkAtm components.
      These components can be added and deleted."
::= { mscTrkAtmRowStatusEntry 1 }

mscTrkAtmComponentName OBJECT-TYPE
   SYNTAX     DisplayString 
   ACCESS     read-only
   STATUS     mandatory
   DESCRIPTION
     "This variable provides the component's string name for
      use with the ASCII Console Interface"
::= { mscTrkAtmRowStatusEntry 2 }

mscTrkAtmStorageType OBJECT-TYPE
   SYNTAX     StorageType 
   ACCESS     read-only
   STATUS     mandatory
   DESCRIPTION
     "This variable represents the storage type value for the
      mscTrkAtm tables."
::= { mscTrkAtmRowStatusEntry 4 }

mscTrkAtmIndex OBJECT-TYPE
   SYNTAX     NonReplicated 
   ACCESS     not-accessible
   STATUS     mandatory
   DESCRIPTION
     "This variable represents the index for the mscTrkAtm tables."
::= { mscTrkAtmRowStatusEntry 10 }

mscTrkAtmProvTable OBJECT-TYPE
   SYNTAX     SEQUENCE OF MscTrkAtmProvEntry
   ACCESS     not-accessible
   STATUS     mandatory
   DESCRIPTION
     "This group of provisionable attributes contains the parameters used 
      by AtmAccess for monitoring link quality."
::= { mscTrkAtm 10 }

mscTrkAtmProvEntry OBJECT-TYPE
   SYNTAX     MscTrkAtmProvEntry
   ACCESS     not-accessible
   STATUS     mandatory
   DESCRIPTION
     "An entry in the mscTrkAtmProvTable."
   INDEX {
      mscTrkIndex,
      mscTrkAtmIndex }
::= { mscTrkAtmProvTable 1 }

MscTrkAtmProvEntry ::= SEQUENCE {
   mscTrkAtmMaximumErroredInterval
      Unsigned32,
   mscTrkAtmReceiveErrorSensitivity
      Unsigned32,
   mscTrkAtmAtmAccMaximumErroredInterval
      FixedPoint1 }

mscTrkAtmMaximumErroredInterval OBJECT-TYPE
   SYNTAX     Unsigned32 (0 | 1..15)
   ACCESS     read-write
   STATUS     obsolete
   DESCRIPTION
     "This attribute specifies the interval time over which the error 
      threshold (as specified by receiveErrorSensitivity) must be 
      continuously exceeded before the Unacknowledged, Utp, 
      AtmAccess or FrAccess component can be degraded. Once the error 
      interval count exceeds the provisioned value, the Unacknowledged, 
      Utp, AtmAccess or FrAccess component will issue an alarm 
      indicating that link quality has degraded, and it will also disable its 
      parent component. The exception to this is a value of zero, the 
      default, which indicates that the mechanism is completely disabled."
   DEFVAL     { 0 }
::= { mscTrkAtmProvEntry 1 }

mscTrkAtmReceiveErrorSensitivity OBJECT-TYPE
   SYNTAX     Unsigned32 (0 | 1..10)
   ACCESS     read-write
   STATUS     mandatory
   DESCRIPTION
     "This attribute specifies the allowable error rate beyond which the 
      AtmAccess component can be degraded if the error rate persists for 
      a duration longer than the maximumErrorInterval. The threshold is 
      expressed as a percentage. It is the ratio of the number of errored 
      cells in the last interval over the number of cells received in the last 
      interval. For AAL5, the number of errored cells is converted from 
      rxFrameDiscard of AtmIf Vcc using the assumption that three ATM 
      cells are used to carry a 128 byte AAL5 frame. The number of 
      received cells is specified by rxCell of AtmIf Vcc. 
      
      The configurable values are:
      0 = the mechanism is completely disabled
      1 = 1/(2**1)
      2 = 1/(2**2)
      3 = 1/(2**3)
      :
      10 = 1/(2**10)"
   DEFVAL     { 3 }
::= { mscTrkAtmProvEntry 2 }

mscTrkAtmAtmAccMaximumErroredInterval OBJECT-TYPE
   SYNTAX     FixedPoint1 (0 | 5 | 10 | 15 | 20 | 25 | 30 | 35 | 40 | 45 | 50 | 60 | 70 | 80 | 90 | 100 | 110 | 120 | 130 | 140 | 150)
   ACCESS     read-write
   STATUS     mandatory
   DESCRIPTION
     "This attribute specifies the interval time over which the error 
      threshold (as specified by receiveErrorSensitivity) must be 
      continuously exceeded before the AtmAccess component can be 
      degraded. Once the error interval count exceeds the provisioned 
      value, the AtmAccess component issues an alarm indicating that link 
      quality has degraded, and it disables its parent component. The 
      exception to this is a value of zero, the default, which indicates that 
      the mechanism is completely disabled."
   DEFVAL     { 0 }
::= { mscTrkAtmProvEntry 3 }

mscTrkAtmInterfaceTable OBJECT-TYPE
   SYNTAX     SEQUENCE OF MscTrkAtmInterfaceEntry
   ACCESS     not-accessible
   STATUS     mandatory
   DESCRIPTION
     "This group of attributes provides the parameters used by the 
      AtmAccess component for specifying access to an ATM interface."
::= { mscTrkAtm 11 }

mscTrkAtmInterfaceEntry OBJECT-TYPE
   SYNTAX     MscTrkAtmInterfaceEntry
   ACCESS     not-accessible
   STATUS     mandatory
   DESCRIPTION
     "An entry in the mscTrkAtmInterfaceTable."
   INDEX {
      mscTrkIndex,
      mscTrkAtmIndex }
::= { mscTrkAtmInterfaceTable 1 }

MscTrkAtmInterfaceEntry ::= SEQUENCE {
   mscTrkAtmAtmConnection
      Link,
   mscTrkAtmBwElastic
      INTEGER,
   mscTrkAtmVccReportingBw
      INTEGER }

mscTrkAtmAtmConnection OBJECT-TYPE
   SYNTAX     Link 
   ACCESS     read-write
   STATUS     mandatory
   DESCRIPTION
     "This attribute specifies the component name of the ATM Layer 2 
      AAL5 interface that the AtmAccess component will use."
::= { mscTrkAtmInterfaceEntry 1 }

mscTrkAtmBwElastic OBJECT-TYPE
   SYNTAX     INTEGER  {
                 no(0),
                 yes(1) }
   ACCESS     read-write
   STATUS     mandatory
   DESCRIPTION
     "This attribute specifies how changes in the bandwidth of the 
      atmConnection are handled by the ATM software. If its value is no, 
      the atmConnection will be released by the ATM software if it is 
      incapable of providing the bandwidth specified by the peak cell rate 
      (PCR) defined in txTrafficDescParm of AtmIf Vcc Vcd. If the value 
      is yes, the atmConnection is not released in this situation, but its 
      bandwidth may be reduced. Also, if this value is yes, the Dynamic 
      Speed Reporting mechanism must be enabled, by provisioning at 
      least one value in the speedReportingThresholds attribute of the 
      parent Trunk component."
   DEFVAL     { no }
::= { mscTrkAtmInterfaceEntry 2 }

mscTrkAtmVccReportingBw OBJECT-TYPE
   SYNTAX     INTEGER  {
                 pcr(0),
                 acr(1) }
   ACCESS     read-write
   STATUS     mandatory
   DESCRIPTION
     "This attribute specifies how the bandwidth of the VCC is reported to 
      the parent Trunk component. If its value is pcr and attribute 
      bwElastic of AtmAccess has a value of no, the peak cell rate (PCR) 
      of the VCC, defined in txTrafficDescParm of AtmIf Vcc Vcd, is 
      reported. If its value is pcr and attribute bwElastic of AtmAccess has 
      a value of yes, the minimum of the PCR, defined in 
      txTrafficDescParm of AtmIf Vcc Vcd, and the current cell rate 
      (CCR) of the VCC is reported. If its value is acr, the best 
      measurement of the actual cell rate (ACR) of the VCC is reported, 
      which is the minimum of the PCR, the CCR and the actual shaping 
      rate (ASR). The value of the reported bandwidth of the VCC is 
      indicated by the measuredSpeedToIf attribute of the parent Trunk 
      component."
   DEFVAL     { pcr }
::= { mscTrkAtmInterfaceEntry 3 }

mscTrkAtmStateTable OBJECT-TYPE
   SYNTAX     SEQUENCE OF MscTrkAtmStateEntry
   ACCESS     not-accessible
   STATUS     mandatory
   DESCRIPTION
     "This group contains the three OSI State attributes and the six OSI 
      Status attributes. The descriptions generically indicate what each 
      attribute implies about the component. Note that not all the values 
      and state combinations described here are supported by every 
      component which uses this group. For component-specific 
      information and the valid state combinations, refer to NTP 241-
      7001-150, Passport Operations and Maintenance Guide."
::= { mscTrkAtm 12 }

mscTrkAtmStateEntry OBJECT-TYPE
   SYNTAX     MscTrkAtmStateEntry
   ACCESS     not-accessible
   STATUS     mandatory
   DESCRIPTION
     "An entry in the mscTrkAtmStateTable."
   INDEX {
      mscTrkIndex,
      mscTrkAtmIndex }
::= { mscTrkAtmStateTable 1 }

MscTrkAtmStateEntry ::= SEQUENCE {
   mscTrkAtmAdminState
      INTEGER,
   mscTrkAtmOperationalState
      INTEGER,
   mscTrkAtmUsageState
      INTEGER,
   mscTrkAtmAvailabilityStatus
      OCTET STRING,
   mscTrkAtmProceduralStatus
      OCTET STRING,
   mscTrkAtmControlStatus
      OCTET STRING,
   mscTrkAtmAlarmStatus
      OCTET STRING,
   mscTrkAtmStandbyStatus
      INTEGER,
   mscTrkAtmUnknownStatus
      INTEGER }

mscTrkAtmAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component.
      
      The OSI Status attributes, if supported by the component, may 
      provide more details, qualifying the state of the component."
   DEFVAL     { unlocked }
::= { mscTrkAtmStateEntry 1 }

mscTrkAtmOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle.
      
      The OSI Status attributes, if supported by the component, may 
      provide more details, qualifying the state of the component."
   DEFVAL     { disabled }
::= { mscTrkAtmStateEntry 2 }

mscTrkAtmUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time.
      
      The OSI Status attributes, if supported by the component, may 
      provide more details, qualifying the state of the component."
   DEFVAL     { idle }
::= { mscTrkAtmStateEntry 3 }

mscTrkAtmAvailabilityStatus OBJECT-TYPE
   SYNTAX     OCTET STRING (SIZE (2))
   ACCESS     read-only
   STATUS     mandatory
   DESCRIPTION
     "If supported by the component, this attribute indicates the OSI 
      Availability status of the component. Note that, even though it is 
      defined as a multi-valued set, at most one value is shown to the user.
      
      When no values are in the set, this indicates that either the attribute 
      is not supported or that none of the status conditions described 
      below are present.
      
      The value inTest indicates that the resource is undergoing a test 
      procedure. If adminState is locked or shuttingDown, the normal 
      users are precluded from using the resource and controlStatus is 
      reservedForTest. Tests that do not exclude additional users can be 
      present in any operational or administrative state but the 
      reservedForTest condition should not be present.
      
      The value failed indicates that the component has an internal fault 
      that prevents it from operating. The operationalState is disabled.
      
      The value dependency indicates that the component cannot operate 
      because some other resource on which it depends is unavailable. 
      The operationalState is disabled.
      
      The value powerOff indicates the resource requires power to be 
      applied and it is not powered on. The operationalState is disabled.
      
      The value offLine indicates the resource requires a routine 
      operation (either manual, automatic, or both) to be performed to 
      place it on-line and make it available for use. The operationalState 
      is disabled.
      
      The value offDuty indicates the resource is inactive in accordance 
      with a predetermined time schedule. In the absence of other 
      disabling conditions, the operationalState is enabled or disabled.
      
      The value degraded indicates the service provided by the 
      component is degraded in some way, such as in speed or operating 
      capacity. However, the resource remains available for service. The 
      operationalState is enabled.
      
      The value notInstalled indicates the resource is not present. The 
      operationalState is disabled.
      
      The value logFull is not used.

      Description of bits:
      inTest(0)
      failed(1)
      powerOff(2)
      offLine(3)
      offDuty(4)
      dependency(5)
      degraded(6)
      notInstalled(7)
      logFull(8)"
::= { mscTrkAtmStateEntry 4 }

mscTrkAtmProceduralStatus OBJECT-TYPE
   SYNTAX     OCTET STRING (SIZE (1))
   ACCESS     read-only
   STATUS     mandatory
   DESCRIPTION
     "If supported by the component, this attribute indicates the OSI 
      Procedural status of the component. Note that, even though it is 
      defined as a multi-valued set, at most one value is shown to the user.
      
      When no values are in the set, this indicates that either the attribute 
      is not supported or that none of the status conditions described 
      below are present.
      
      The value initializationRequired indicates (for a resource which 
      doesn't initialize autonomously) that initialization is required before 
      it can perform its normal functions, and this procedure has not been 
      initiated. The operationalState is disabled.
      
      The value notInitialized indicates (for a resource which does 
      initialize autonomously) that initialization is required before it can 
      perform its normal functions, and this procedure has not been 
      initiated. The operationalState may be enabled or disabled.
      
      The value initializing indicates that initialization has been initiated 
      but is not yet complete. The operationalState may be enabled or 
      disabled.
      
      The value reporting indicates the resource has completed some 
      processing operation and is notifying the results. The 
      operationalState is enabled.
      
      The value terminating indicates the component is in a termination 
      phase. If the resource doesn't reinitialize autonomously, 
      operationalState is disabled; otherwise it is enabled or disabled.

      Description of bits:
      initializationRequired(0)
      notInitialized(1)
      initializing(2)
      reporting(3)
      terminating(4)"
::= { mscTrkAtmStateEntry 5 }

mscTrkAtmControlStatus OBJECT-TYPE
   SYNTAX     OCTET STRING (SIZE (1))
   ACCESS     read-only
   STATUS     mandatory
   DESCRIPTION
     "If supported by the component, this attribute indicates the OSI 
      Control status of the component. Note that, even though it is defined 
      as a multi-valued set, at most one value is shown to the user.
      
      When no values are in the set, this indicates that either the attribute 
      is not supported or that none of the status conditions described 
      below are present.
      
      The value subjectToTest indicates the resource is available but tests 
      may be conducted simultaneously at unpredictable times, which 
      may cause it to exhibit unusual characteristics.
      
      The value partOfServicesLocked indicates that part of the service is 
      restricted from users of a resource. The adminState is unlocked.
      
      The value reservedForTest indicates that the component is 
      administratively unavailable because it is undergoing a test 
      procedure. The adminState is locked.
      
      The value suspended indicates that the service has been 
      administratively suspended.

      Description of bits:
      subjectToTest(0)
      partOfServicesLocked(1)
      reservedForTest(2)
      suspended(3)"
::= { mscTrkAtmStateEntry 6 }

mscTrkAtmAlarmStatus OBJECT-TYPE
   SYNTAX     OCTET STRING (SIZE (1))
   ACCESS     read-only
   STATUS     mandatory
   DESCRIPTION
     "If supported by the component, this attribute indicates the OSI 
      Alarm status of the component. Note that, even though it is defined 
      as a multi-valued set, at most one value is shown to the user.
      
      When no values are in the set, this indicates that either the attribute 
      is not supported or that none of the status conditions described 
      below are present.
      
      The value underRepair indicates the component is currently being 
      repaired. The operationalState is enabled or disabled.
      
      The value critical indicates one or more critical alarms are 
      outstanding against the component. Other, less severe, alarms may 
      also be outstanding. The operationalState is enabled or disabled.
      
      The value major indicates one or more major alarms are 
      outstanding against the component. Other, less severe, alarms may 
      also be outstanding. The operationalState is enabled or disabled.
      
      The value minor indicates one or more minor alarms are 
      outstanding against the component. Other, less severe, alarms may 
      also be outstanding. The operationalState is enabled or disabled.
      
      The value alarmOutstanding generically indicates that an alarm of 
      some severity is outstanding against the component.

      Description of bits:
      underRepair(0)
      critical(1)
      major(2)
      minor(3)
      alarmOutstanding(4)"
::= { mscTrkAtmStateEntry 7 }

mscTrkAtmStandbyStatus OBJECT-TYPE
   SYNTAX     INTEGER  {
                 hotStandby(0),
                 coldStandby(1),
                 providingService(2),
                 notSet(15) }
   ACCESS     read-only
   STATUS     mandatory
   DESCRIPTION
     "If supported by the component, this attribute indicates the OSI 
      Standby status of the component.
      
      The value notSet indicates that either the attribute is not supported 
      or that none of the status conditions described below are present. 
      Note that this is a non-standard value, used because the original 
      specification indicated this attribute was set-valued and thus, did not 
      provide a value to indicate that none of the other three are 
      applicable.
      
      The value hotStandby indicates that the resource is not providing 
      service but will be immediately able to take over the role of the 
      resource to be backed up, without initialization activity, and 
      containing the same information as the resource to be backed up.
      
      The value coldStandby indicates the resource is a backup for 
      another resource but will not be immediately able to take over the 
      role of the backed up resource and will require some initialization 
      activity.
      
      The value providingService indicates that this component, as a 
      backup resource, is currently backing up another resource."
   DEFVAL     { notSet }
::= { mscTrkAtmStateEntry 8 }

mscTrkAtmUnknownStatus OBJECT-TYPE
   SYNTAX     INTEGER  {
                 false(0),
                 true(1) }
   ACCESS     read-only
   STATUS     mandatory
   DESCRIPTION
     "This attribute indicates the OSI Unknown status of the component.
      
      The value false indicates that all of the other OSI State and Status 
      attribute values can be considered accurate.
      
      The value true indicates that the actual state of the component is not 
      known for sure."
   DEFVAL     { false }
::= { mscTrkAtmStateEntry 9 }

mscTrkAtmUtilTable OBJECT-TYPE
   SYNTAX     SEQUENCE OF MscTrkAtmUtilEntry
   ACCESS     not-accessible
   STATUS     mandatory
   DESCRIPTION
     "This group contains all of the provisioning data required to set the 
      ATM VCC utilization alarm thresholds. The ATM VCC utilization 
      is indicated by the lastCalculatedVccUtilization attribute.
      All thresholds are percentages which can take on any value in the 
      range of 0% through 200%. The value 200% is used to disable an 
      individual threshold. For values other than 200%, the minor alarm 
      threshold must be less than the other thresholds and the major alarm 
      threshold must be less than the critical alarm threshold."
::= { mscTrkAtm 14 }

mscTrkAtmUtilEntry OBJECT-TYPE
   SYNTAX     MscTrkAtmUtilEntry
   ACCESS     not-accessible
   STATUS     mandatory
   DESCRIPTION
     "An entry in the mscTrkAtmUtilTable."
   INDEX {
      mscTrkIndex,
      mscTrkAtmIndex }
::= { mscTrkAtmUtilTable 1 }

MscTrkAtmUtilEntry ::= SEQUENCE {
   mscTrkAtmMinorVccUtilAlarmThreshold
      Unsigned32,
   mscTrkAtmMajorVccUtilAlarmThreshold
      Unsigned32,
   mscTrkAtmCriticalVccUtilAlarmThreshold
      Unsigned32,
   mscTrkAtmVccUtilAlarmStatus
      INTEGER }

mscTrkAtmMinorVccUtilAlarmThreshold OBJECT-TYPE
   SYNTAX     Unsigned32 (0..200)
   ACCESS     read-write
   STATUS     mandatory
   DESCRIPTION
     "This attribute specifies the threshold value at which a minor alarm 
      will be issued based on a sustained average ATM VCC utilization as 
      indicated by the lastCalculatedVccUtilization attribute. The Set 
      alarm is issued after 3 minutes of utilization greater than the 
      threshold. The corresponding Clear alarm is issued after a 
      subsequent 3 minutes of utilization less than or equal to the 
      threshold.
      The value 200% is used to disable this threshold. For values other 
      than 200%, the minor alarm threshold must be less than the other 
      thresholds."
   DEFVAL     { 75 }
::= { mscTrkAtmUtilEntry 1 }

mscTrkAtmMajorVccUtilAlarmThreshold OBJECT-TYPE
   SYNTAX     Unsigned32 (0..200)
   ACCESS     read-write
   STATUS     mandatory
   DESCRIPTION
     "This attribute specifies the threshold value at which a major alarm 
      will be issued based on a sustained average ATM VCC utilization as 
      indicated by the lastCalculatedVccUtilization attribute. The Set 
      alarm is issued after 3 minutes of utilization greater than the 
      threshold. The corresponding Clear alarm is issued after a 
      subsequent 3 minutes of utilization less than or equal to the 
      threshold.
      The value 200% is used to disable this threshold. For values other 
      than 200%, the major alarm threshold must be greater than the 
      minor threshold and less than the critical threshold."
   DEFVAL     { 85 }
::= { mscTrkAtmUtilEntry 2 }

mscTrkAtmCriticalVccUtilAlarmThreshold OBJECT-TYPE
   SYNTAX     Unsigned32 (0..200)
   ACCESS     read-write
   STATUS     mandatory
   DESCRIPTION
     "This attribute specifies the threshold value at which a critical alarm 
      will be issued based on a sustained average ATM VCC utilization as 
      indicated by the lastCalculatedVccUtilization attribute. The Set 
      alarm is issued after 3 minutes of utilization greater than the 
      threshold. The corresponding Clear alarm is issued after a 
      subsequent 3 minutes of utilization less than or equal to the 
      threshold.
      The value 200% is used to disable this threshold. For values other 
      than 200%, the critical alarm threshold must be greater than the 
      other thresholds."
   DEFVAL     { 95 }
::= { mscTrkAtmUtilEntry 3 }

mscTrkAtmVccUtilAlarmStatus OBJECT-TYPE
   SYNTAX     INTEGER  {
                 disabled(0),
                 enabled(1) }
   ACCESS     read-write
   STATUS     mandatory
   DESCRIPTION
     "This attribute provides control of the generation of ATM VCC 
      utilization alarms. If the value is disabled, none of the alarms is 
      generated (this is equivalent to setting all of the thresholds to 
      200%). If the value is enabled, the individual thresholds are 
      handled."
   DEFVAL     { disabled }
::= { mscTrkAtmUtilEntry 4 }

mscTrkAtmStatsTable OBJECT-TYPE
   SYNTAX     SEQUENCE OF MscTrkAtmStatsEntry
   ACCESS     not-accessible
   STATUS     mandatory
   DESCRIPTION
     "This group of attributes contains statistics collected by the 
      AtmAccess component."
::= { mscTrkAtm 15 }

mscTrkAtmStatsEntry OBJECT-TYPE
   SYNTAX     MscTrkAtmStatsEntry
   ACCESS     not-accessible
   STATUS     mandatory
   DESCRIPTION
     "An entry in the mscTrkAtmStatsTable."
   INDEX {
      mscTrkIndex,
      mscTrkAtmIndex }
::= { mscTrkAtmStatsTable 1 }

MscTrkAtmStatsEntry ::= SEQUENCE {
   mscTrkAtmLastCalculatedVccUtilization
      Gauge32,
   mscTrkAtmLastCalculatedTxVccUtilization
      Gauge32 }

mscTrkAtmLastCalculatedVccUtilization OBJECT-TYPE
   SYNTAX     Gauge32 (0..200)
   ACCESS     read-only
   STATUS     mandatory
   DESCRIPTION
     "This attribute indicates the last calculated receive utilization of the 
      ATM VCC. It is calculated every 30 seconds based on comparing 
      the number of cells received by the AtmIf Vcc with the estimated 
      available bandwidth on the AtmIf Vcc."
   DEFVAL     { 0 }
::= { mscTrkAtmStatsEntry 1 }

mscTrkAtmLastCalculatedTxVccUtilization OBJECT-TYPE
   SYNTAX     Gauge32 (0..200)
   ACCESS     read-only
   STATUS     mandatory
   DESCRIPTION
     "This attribute indicates the last calculated transmit utilization of the 
      ATM VCC. It is calculated every 30 seconds based on comparing 
      the number of cells transmitted by the AtmIf Vcc with the estimated 
      available bandwidth on the AtmIf Vcc."
   DEFVAL     { 0 }
::= { mscTrkAtmStatsEntry 2 }




-- 
-- Version and Compliance statements
-- 



-- Object-Group Statement:
-- A list of all current accessible leaf objects.

-- OBJECTS { mscTrkAtmAdminState,
--           mscTrkAtmVccReportingBw,
--           mscTrkAtmComponentName,
--           mscTrkAtmStandbyStatus,
--           mscTrkAtmBwElastic,
--           mscTrkAtmLastCalculatedVccUtilization,
--           mscTrkAtmMajorVccUtilAlarmThreshold,
--           mscTrkAtmAtmConnection,
--           mscTrkAtmStorageType,
--           mscTrkAtmRowStatus,
--           mscTrkAtmAvailabilityStatus,
--           mscTrkAtmVccUtilAlarmStatus,
--           mscTrkAtmLastCalculatedTxVccUtilization,
--           mscTrkAtmProceduralStatus,
--           mscTrkAtmUnknownStatus,
--           mscTrkAtmAtmAccMaximumErroredInterval,
--           mscTrkAtmMinorVccUtilAlarmThreshold,
--           mscTrkAtmReceiveErrorSensitivity,
--           mscTrkAtmCriticalVccUtilAlarmThreshold,
--           mscTrkAtmAlarmStatus,
--           mscTrkAtmUsageState,
--           mscTrkAtmOperationalState,
--           mscTrkAtmControlStatus }
-- STATUS  mandatory
-- DESCRIPTION
--   "A list of all current accessible leaf objects."

atmTrunksGroup OBJECT IDENTIFIER ::= { atmTrunksMIB 1 }
atmTrunksGroupCA OBJECT IDENTIFIER ::= { atmTrunksGroup 1 }
atmTrunksGroupCA02 OBJECT IDENTIFIER ::= { atmTrunksGroupCA 3 }
atmTrunksGroupCA02A OBJECT IDENTIFIER ::= { atmTrunksGroupCA02 2 }



-- Agent-Capabilities Statement:

-- PRODUCT-RELEASE "MscPassport Release 1.2 AtmTrunks."
-- STATUS          mandatory
-- DESCRIPTION     "Carrier Passport AtmTrunks MIB: MIB Version CA02A,
--                  Software Version CA02S9C."
-- SUPPORTS        Nortel-MsCarrier-MscPassport-AtmTrunksMIB
--    INCLUDES     { atmTrunksGroupCA02A }

atmTrunksCapabilities OBJECT IDENTIFIER ::= { atmTrunksMIB 3 }
atmTrunksCapabilitiesCA OBJECT IDENTIFIER ::= { atmTrunksCapabilities 1 }
atmTrunksCapabilitiesCA02 OBJECT IDENTIFIER ::= { atmTrunksCapabilitiesCA 3 }
atmTrunksCapabilitiesCA02A OBJECT IDENTIFIER ::= { atmTrunksCapabilitiesCA02 2 }





END
