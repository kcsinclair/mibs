Nortel-MsCarrier-MscPassport-DisdnTS014MIB
DEFINITIONS ::= BEGIN



IMPORTS

      OBJECT-TYPE
   FROM RFC-1212

      mscPassportMIBs
   FROM Nortel-MsCarrier-MscPassport-UsefulDefinitionsMIB

      DisplayString,
      StorageType,
      RowStatus,
      Unsigned32
   FROM Nortel-MsCarrier-MscPassport-StandardTextualConventionsMIB

      NonReplicated,
      Link
   FROM Nortel-MsCarrier-MscPassport-TextualConventionsMIB

      mscDataSigChanIndex,
      mscDataSigChan
   FROM Nortel-MsCarrier-MscPassport-DataIsdnMIB;




-- LAST-UPDATED   "9909010000Z"
-- ORGANIZATION   "Nortel Networks"
-- CONTACT-INFO   "
--         Nortel Carrier Data Network Management
--         
--         Postal:       P.O. Box 3511, Station C 
--                       Ottawa, Ontario 
--                       Canada  K1Y 4H7
--         
--         via the WEB:  http://www.nortelnetworks.com  
--                       select 'Contact Us' from the menu
--          
--         via phone:    1-800-4NORTEL"
-- DESCRIPTION
--    "The module describing the Nortel MsCarrier MscPassport
--     DisdnTS014 Enterprise MIB."

disdnTS014MIB OBJECT IDENTIFIER ::= { mscPassportMIBs 114 }










-- DataSigChan/n TS014
-- The TS014 component defines the operational characteristics of the 
-- signalling channel's connection to the external equipment.

mscDataSigChanTS014 OBJECT IDENTIFIER ::= { mscDataSigChan 9 }



mscDataSigChanTS014RowStatusTable OBJECT-TYPE
   SYNTAX     SEQUENCE OF MscDataSigChanTS014RowStatusEntry
   ACCESS     not-accessible
   STATUS     mandatory
   DESCRIPTION
     "This entry controls the addition and deletion of 
      mscDataSigChanTS014 components."
::= { mscDataSigChanTS014 1 }

mscDataSigChanTS014RowStatusEntry OBJECT-TYPE
   SYNTAX     MscDataSigChanTS014RowStatusEntry
   ACCESS     not-accessible
   STATUS     mandatory
   DESCRIPTION
     "A single entry in the table represents a single 
      mscDataSigChanTS014 component."
   INDEX {
      mscDataSigChanIndex,
      mscDataSigChanTS014Index }
::= { mscDataSigChanTS014RowStatusTable 1 }

MscDataSigChanTS014RowStatusEntry ::= SEQUENCE {
   mscDataSigChanTS014RowStatus
      RowStatus,
   mscDataSigChanTS014ComponentName
      DisplayString,
   mscDataSigChanTS014StorageType
      StorageType,
   mscDataSigChanTS014Index
      NonReplicated }

mscDataSigChanTS014RowStatus OBJECT-TYPE
   SYNTAX     RowStatus 
   ACCESS     read-write
   STATUS     mandatory
   DESCRIPTION
     "This variable is used as the basis for SNMP naming of
      mscDataSigChanTS014 components.
      These components can be added and deleted."
::= { mscDataSigChanTS014RowStatusEntry 1 }

mscDataSigChanTS014ComponentName OBJECT-TYPE
   SYNTAX     DisplayString 
   ACCESS     read-only
   STATUS     mandatory
   DESCRIPTION
     "This variable provides the component's string name for
      use with the ASCII Console Interface"
::= { mscDataSigChanTS014RowStatusEntry 2 }

mscDataSigChanTS014StorageType OBJECT-TYPE
   SYNTAX     StorageType 
   ACCESS     read-only
   STATUS     mandatory
   DESCRIPTION
     "This variable represents the storage type value for the
      mscDataSigChanTS014 tables."
::= { mscDataSigChanTS014RowStatusEntry 4 }

mscDataSigChanTS014Index OBJECT-TYPE
   SYNTAX     NonReplicated 
   ACCESS     not-accessible
   STATUS     mandatory
   DESCRIPTION
     "This variable represents the index for the mscDataSigChanTS014 tables."
::= { mscDataSigChanTS014RowStatusEntry 10 }

mscDataSigChanTS014L2Table OBJECT-TYPE
   SYNTAX     SEQUENCE OF MscDataSigChanTS014L2Entry
   ACCESS     not-accessible
   STATUS     mandatory
   DESCRIPTION
     "This group represents the provisionable Layer 2 attributes of the 
      Q931 CCITT protocol."
::= { mscDataSigChanTS014 11 }

mscDataSigChanTS014L2Entry OBJECT-TYPE
   SYNTAX     MscDataSigChanTS014L2Entry
   ACCESS     not-accessible
   STATUS     mandatory
   DESCRIPTION
     "An entry in the mscDataSigChanTS014L2Table."
   INDEX {
      mscDataSigChanIndex,
      mscDataSigChanTS014Index }
::= { mscDataSigChanTS014L2Table 1 }

MscDataSigChanTS014L2Entry ::= SEQUENCE {
   mscDataSigChanTS014T23
      Unsigned32,
   mscDataSigChanTS014T200
      Unsigned32,
   mscDataSigChanTS014N200
      Unsigned32,
   mscDataSigChanTS014T203
      Unsigned32,
   mscDataSigChanTS014N201
      Unsigned32,
   mscDataSigChanTS014CircuitSwitchedK
      Unsigned32 }

mscDataSigChanTS014T23 OBJECT-TYPE
   SYNTAX     Unsigned32 (1..15)
   ACCESS     read-write
   STATUS     mandatory
   DESCRIPTION
     "This attribute specifies the layer2 enable request timer."
   DEFVAL     { 10 }
::= { mscDataSigChanTS014L2Entry 1 }

mscDataSigChanTS014T200 OBJECT-TYPE
   SYNTAX     Unsigned32 (1..20)
   ACCESS     read-write
   STATUS     mandatory
   DESCRIPTION
     "This attribute specifies the maximum time between a layer 2 frame 
      and its acknowledgement"
   DEFVAL     { 2 }
::= { mscDataSigChanTS014L2Entry 2 }

mscDataSigChanTS014N200 OBJECT-TYPE
   SYNTAX     Unsigned32 (1..8)
   ACCESS     read-write
   STATUS     mandatory
   DESCRIPTION
     "This attribute specifies the maximum number of re-transmissions of 
      a layer2 frame."
   DEFVAL     { 3 }
::= { mscDataSigChanTS014L2Entry 3 }

mscDataSigChanTS014T203 OBJECT-TYPE
   SYNTAX     Unsigned32 (2..40)
   ACCESS     read-write
   STATUS     mandatory
   DESCRIPTION
     "This attribute specifies the maximum time that a no layer 2 traffic 
      situation can last. Expiry triggers a check on whether the far end is 
      a live."
   DEFVAL     { 10 }
::= { mscDataSigChanTS014L2Entry 4 }

mscDataSigChanTS014N201 OBJECT-TYPE
   SYNTAX     Unsigned32 (4..260)
   ACCESS     read-write
   STATUS     mandatory
   DESCRIPTION
     "This attribute specifies the maximum number of octets in an 
      information field."
   DEFVAL     { 260 }
::= { mscDataSigChanTS014L2Entry 5 }

mscDataSigChanTS014CircuitSwitchedK OBJECT-TYPE
   SYNTAX     Unsigned32 (1..632)
   ACCESS     read-write
   STATUS     mandatory
   DESCRIPTION
     "This attribute specifies the maximum number of frames for B 
      channel use."
   DEFVAL     { 7 }
::= { mscDataSigChanTS014L2Entry 6 }

mscDataSigChanTS014ProvTable OBJECT-TYPE
   SYNTAX     SEQUENCE OF MscDataSigChanTS014ProvEntry
   ACCESS     not-accessible
   STATUS     mandatory
   DESCRIPTION
     "This group defines the general options of the d-channel signalling 
      link."
::= { mscDataSigChanTS014 13 }

mscDataSigChanTS014ProvEntry OBJECT-TYPE
   SYNTAX     MscDataSigChanTS014ProvEntry
   ACCESS     not-accessible
   STATUS     mandatory
   DESCRIPTION
     "An entry in the mscDataSigChanTS014ProvTable."
   INDEX {
      mscDataSigChanIndex,
      mscDataSigChanTS014Index }
::= { mscDataSigChanTS014ProvTable 1 }

MscDataSigChanTS014ProvEntry ::= SEQUENCE {
   mscDataSigChanTS014Side
      INTEGER }

mscDataSigChanTS014Side OBJECT-TYPE
   SYNTAX     INTEGER  {
                 network(1),
                 user(2) }
   ACCESS     read-write
   STATUS     mandatory
   DESCRIPTION
     "This attribute specifies whether the layer 2 HDLC interface is the 
      network or user side of the connection."
   DEFVAL     { user }
::= { mscDataSigChanTS014ProvEntry 1 }

mscDataSigChanTS014OperTable OBJECT-TYPE
   SYNTAX     SEQUENCE OF MscDataSigChanTS014OperEntry
   ACCESS     not-accessible
   STATUS     mandatory
   DESCRIPTION
     "This group provides the operational attributes for the signalling 
      protocol."
::= { mscDataSigChanTS014 15 }

mscDataSigChanTS014OperEntry OBJECT-TYPE
   SYNTAX     MscDataSigChanTS014OperEntry
   ACCESS     not-accessible
   STATUS     mandatory
   DESCRIPTION
     "An entry in the mscDataSigChanTS014OperTable."
   INDEX {
      mscDataSigChanIndex,
      mscDataSigChanTS014Index }
::= { mscDataSigChanTS014OperTable 1 }

MscDataSigChanTS014OperEntry ::= SEQUENCE {
   mscDataSigChanTS014ActiveChannels
      Unsigned32,
   mscDataSigChanTS014PeakActiveChannels
      Unsigned32,
   mscDataSigChanTS014DChanStatus
      INTEGER }

mscDataSigChanTS014ActiveChannels OBJECT-TYPE
   SYNTAX     Unsigned32 (0..128)
   ACCESS     read-only
   STATUS     mandatory
   DESCRIPTION
     "This attribute indicates the number of currently active channels. 
      This includes data and voice channels."
   DEFVAL     { 0 }
::= { mscDataSigChanTS014OperEntry 1 }

mscDataSigChanTS014PeakActiveChannels OBJECT-TYPE
   SYNTAX     Unsigned32 (0..128)
   ACCESS     read-only
   STATUS     mandatory
   DESCRIPTION
     "This attribute indicates the maximum number of channels that have 
      been active on this signalling channel during the last polling period."
   DEFVAL     { 0 }
::= { mscDataSigChanTS014OperEntry 4 }

mscDataSigChanTS014DChanStatus OBJECT-TYPE
   SYNTAX     INTEGER  {
                 outOfService(0),
                 establishing(1),
                 established(2),
                 enabling(3),
                 inService(4),
                 restarting(5) }
   ACCESS     read-only
   STATUS     mandatory
   DESCRIPTION
     "This attribute indicates the state of the D-channel. 
      outOfService means that there is no layer 2 or layer 3 connectivity 
      to the PBX.
      establishing means that the signalling channel is attempting to stage 
      the layer 2.
      established means that the layer 2 is enabled. If the signalling 
      channel stays in the established state, then it is waiting for a restart 
      from the PBX.
      enabling means that the resources for processing calls are being 
      initialized. If the signalling channel stays in the enabling state then 
      it is waiting for a restart acknowledgement from the PBX. 
      inService means that the resources for processing calls are 
      available. 
      restarting means that the resources for call processing are being rei-
      initialized."
::= { mscDataSigChanTS014OperEntry 7 }

mscDataSigChanTS014ToolsTable OBJECT-TYPE
   SYNTAX     SEQUENCE OF MscDataSigChanTS014ToolsEntry
   ACCESS     not-accessible
   STATUS     mandatory
   DESCRIPTION
     "This group contains a series of operational attributes which turn on 
      and off several kinds of tracing."
::= { mscDataSigChanTS014 16 }

mscDataSigChanTS014ToolsEntry OBJECT-TYPE
   SYNTAX     MscDataSigChanTS014ToolsEntry
   ACCESS     not-accessible
   STATUS     mandatory
   DESCRIPTION
     "An entry in the mscDataSigChanTS014ToolsTable."
   INDEX {
      mscDataSigChanIndex,
      mscDataSigChanTS014Index }
::= { mscDataSigChanTS014ToolsTable 1 }

MscDataSigChanTS014ToolsEntry ::= SEQUENCE {
   mscDataSigChanTS014Tracing
      OCTET STRING }

mscDataSigChanTS014Tracing OBJECT-TYPE
   SYNTAX     OCTET STRING (SIZE (1))
   ACCESS     read-write
   STATUS     mandatory
   DESCRIPTION
     "This attribute defines which types of tracing are active for this 
      signalling channel.  The tracing messages are sent to the debug 
      stream. To see the messages the agentQueue attribute in Col/debug 
      must be greater than 0 and a Telnet NMIS session must list the 
      debug stream in in its data streams (ex. set nmis telnet session/1 
      dataStreams debug). Different types of tracing can be enabled 
      simultaneously. 
      Note that tracing consumes additional CPU resources and will slow 
      down call processing on a heavily loaded card.  If there is message 
      block exhaustion tracing will be suspended for a period and then 
      automatically reenabled.  An alarm is generated on tracing 
      suspension and resumption.  This mechanism protects the function 
      processor against excessive numbers of tracing messages.
      
      Types of tracing include: 
      protocolErrors - get details of any protocol errors which are 
      occuring. Protocol errors are also reported in summary form as 
      alarms. 
      q931Summary - Summary of the Q.931 messages on the signalling 
      link, including certain call details (calling number, called number, 
      release codes). 
      q931Hex - Q.931 messages displayed in hex format.  Useful to 
      determine protocol compliance in case of errors reported on local or 
      remote ends.
      q931Symbolic - Q.931 messages parsed to give maximum detail.  
      Useful for understanding content of messages flowing on the link.
      portHex - Messages in hex format being sent and received on the 
      link.

      Description of bits:
      protocolErrors(0)
      q931Summary(1)
      q931Hex(2)
      q931Symbolic(3)
      portHex(4)"
::= { mscDataSigChanTS014ToolsEntry 1 }


-- 
-- DataSigChan/n ts014 Framer
-- 
-- The Framer component controls link layer framing for application 
-- components sending and receiving data on a link interface. It is also 
-- through Framer, that an application component is associated with a 
-- specific hardware link interface.
-- 
-- The Framer component provides provisionable attributes related to 
-- datapath aspects of the hardware interface (such as crc and frame 
-- length). The Framer component also provides a provisionable 
-- attribute which binds the application component to a specific 
-- hardware component.
-- 
-- The Framer component contains operational attributes for link 
-- interface datapath statistics (such as frame counts and aborts).
-- 

mscDataSigChanTS014Framer OBJECT IDENTIFIER ::= { mscDataSigChanTS014 2 }



mscDataSigChanTS014FramerRowStatusTable OBJECT-TYPE
   SYNTAX     SEQUENCE OF MscDataSigChanTS014FramerRowStatusEntry
   ACCESS     not-accessible
   STATUS     mandatory
   DESCRIPTION
     "This entry controls the addition and deletion of 
      mscDataSigChanTS014Framer components."
::= { mscDataSigChanTS014Framer 1 }

mscDataSigChanTS014FramerRowStatusEntry OBJECT-TYPE
   SYNTAX     MscDataSigChanTS014FramerRowStatusEntry
   ACCESS     not-accessible
   STATUS     mandatory
   DESCRIPTION
     "A single entry in the table represents a single 
      mscDataSigChanTS014Framer component."
   INDEX {
      mscDataSigChanIndex,
      mscDataSigChanTS014Index,
      mscDataSigChanTS014FramerIndex }
::= { mscDataSigChanTS014FramerRowStatusTable 1 }

MscDataSigChanTS014FramerRowStatusEntry ::= SEQUENCE {
   mscDataSigChanTS014FramerRowStatus
      RowStatus,
   mscDataSigChanTS014FramerComponentName
      DisplayString,
   mscDataSigChanTS014FramerStorageType
      StorageType,
   mscDataSigChanTS014FramerIndex
      NonReplicated }

mscDataSigChanTS014FramerRowStatus OBJECT-TYPE
   SYNTAX     RowStatus 
   ACCESS     read-only
   STATUS     mandatory
   DESCRIPTION
     "This variable is used as the basis for SNMP naming of
      mscDataSigChanTS014Framer components.
      These components cannot be added nor deleted."
::= { mscDataSigChanTS014FramerRowStatusEntry 1 }

mscDataSigChanTS014FramerComponentName OBJECT-TYPE
   SYNTAX     DisplayString 
   ACCESS     read-only
   STATUS     mandatory
   DESCRIPTION
     "This variable provides the component's string name for
      use with the ASCII Console Interface"
::= { mscDataSigChanTS014FramerRowStatusEntry 2 }

mscDataSigChanTS014FramerStorageType OBJECT-TYPE
   SYNTAX     StorageType 
   ACCESS     read-only
   STATUS     mandatory
   DESCRIPTION
     "This variable represents the storage type value for the
      mscDataSigChanTS014Framer tables."
::= { mscDataSigChanTS014FramerRowStatusEntry 4 }

mscDataSigChanTS014FramerIndex OBJECT-TYPE
   SYNTAX     NonReplicated 
   ACCESS     not-accessible
   STATUS     mandatory
   DESCRIPTION
     "This variable represents the index for the mscDataSigChanTS014Framer tables."
::= { mscDataSigChanTS014FramerRowStatusEntry 10 }

mscDataSigChanTS014FramerProvTable OBJECT-TYPE
   SYNTAX     SEQUENCE OF MscDataSigChanTS014FramerProvEntry
   ACCESS     not-accessible
   STATUS     mandatory
   DESCRIPTION
     "This group contains the base provisioning data for the Framer 
      component. Application or hardware interface specific provisioning 
      data is contained in other provisionable Framer groups."
::= { mscDataSigChanTS014Framer 10 }

mscDataSigChanTS014FramerProvEntry OBJECT-TYPE
   SYNTAX     MscDataSigChanTS014FramerProvEntry
   ACCESS     not-accessible
   STATUS     mandatory
   DESCRIPTION
     "An entry in the mscDataSigChanTS014FramerProvTable."
   INDEX {
      mscDataSigChanIndex,
      mscDataSigChanTS014Index,
      mscDataSigChanTS014FramerIndex }
::= { mscDataSigChanTS014FramerProvTable 1 }

MscDataSigChanTS014FramerProvEntry ::= SEQUENCE {
   mscDataSigChanTS014FramerInterfaceName
      Link }

mscDataSigChanTS014FramerInterfaceName OBJECT-TYPE
   SYNTAX     Link 
   ACCESS     read-write
   STATUS     mandatory
   DESCRIPTION
     "This attribute contains a hardware component name.
      
      The attribute associates the application with a specific link. This 
      defines the module processor on which Framer's parent component 
      (as well as Framer itself) will run."
::= { mscDataSigChanTS014FramerProvEntry 1 }

mscDataSigChanTS014FramerStateTable OBJECT-TYPE
   SYNTAX     SEQUENCE OF MscDataSigChanTS014FramerStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscDataSigChanTS014Framer 12 }

mscDataSigChanTS014FramerStateEntry OBJECT-TYPE
   SYNTAX     MscDataSigChanTS014FramerStateEntry
   ACCESS     not-accessible
   STATUS     mandatory
   DESCRIPTION
     "An entry in the mscDataSigChanTS014FramerStateTable."
   INDEX {
      mscDataSigChanIndex,
      mscDataSigChanTS014Index,
      mscDataSigChanTS014FramerIndex }
::= { mscDataSigChanTS014FramerStateTable 1 }

MscDataSigChanTS014FramerStateEntry ::= SEQUENCE {
   mscDataSigChanTS014FramerAdminState
      INTEGER,
   mscDataSigChanTS014FramerOperationalState
      INTEGER,
   mscDataSigChanTS014FramerUsageState
      INTEGER }

mscDataSigChanTS014FramerAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscDataSigChanTS014FramerStateEntry 1 }

mscDataSigChanTS014FramerOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscDataSigChanTS014FramerStateEntry 2 }

mscDataSigChanTS014FramerUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscDataSigChanTS014FramerStateEntry 3 }

mscDataSigChanTS014FramerStatsTable OBJECT-TYPE
   SYNTAX     SEQUENCE OF MscDataSigChanTS014FramerStatsEntry
   ACCESS     not-accessible
   STATUS     mandatory
   DESCRIPTION
     "This group contains the operational statistics data for a Framer 
      component."
::= { mscDataSigChanTS014Framer 13 }

mscDataSigChanTS014FramerStatsEntry OBJECT-TYPE
   SYNTAX     MscDataSigChanTS014FramerStatsEntry
   ACCESS     not-accessible
   STATUS     mandatory
   DESCRIPTION
     "An entry in the mscDataSigChanTS014FramerStatsTable."
   INDEX {
      mscDataSigChanIndex,
      mscDataSigChanTS014Index,
      mscDataSigChanTS014FramerIndex }
::= { mscDataSigChanTS014FramerStatsTable 1 }

MscDataSigChanTS014FramerStatsEntry ::= SEQUENCE {
   mscDataSigChanTS014FramerFrmToIf
      Unsigned32,
   mscDataSigChanTS014FramerFrmFromIf
      Unsigned32,
   mscDataSigChanTS014FramerOctetFromIf
      Unsigned32,
   mscDataSigChanTS014FramerAborts
      Unsigned32,
   mscDataSigChanTS014FramerCrcErrors
      Unsigned32,
   mscDataSigChanTS014FramerLrcErrors
      Unsigned32,
   mscDataSigChanTS014FramerNonOctetErrors
      Unsigned32,
   mscDataSigChanTS014FramerOverruns
      Unsigned32,
   mscDataSigChanTS014FramerUnderruns
      Unsigned32,
   mscDataSigChanTS014FramerLargeFrmErrors
      Unsigned32 }

mscDataSigChanTS014FramerFrmToIf OBJECT-TYPE
   SYNTAX     Unsigned32 (0..4294967295)
   ACCESS     read-only
   STATUS     mandatory
   DESCRIPTION
     "This attribute counts the number of frames transmitted to the link 
      interface by Framer.
      This count wraps to zero after reaching its maximum value."
   DEFVAL     { 0 }
::= { mscDataSigChanTS014FramerStatsEntry 1 }

mscDataSigChanTS014FramerFrmFromIf OBJECT-TYPE
   SYNTAX     Unsigned32 (0..4294967295)
   ACCESS     read-only
   STATUS     mandatory
   DESCRIPTION
     "This attribute counts the number of frames received from the link 
      interface by Framer.
      This count wraps to zero after reaching its maximum value."
   DEFVAL     { 0 }
::= { mscDataSigChanTS014FramerStatsEntry 2 }

mscDataSigChanTS014FramerOctetFromIf OBJECT-TYPE
   SYNTAX     Unsigned32 (0..4294967295)
   ACCESS     read-only
   STATUS     mandatory
   DESCRIPTION
     "The number of bytes received from the link interface by Framer."
   DEFVAL     { 0 }
::= { mscDataSigChanTS014FramerStatsEntry 3 }

mscDataSigChanTS014FramerAborts OBJECT-TYPE
   SYNTAX     Unsigned32 (0..4294967295)
   ACCESS     read-only
   STATUS     mandatory
   DESCRIPTION
     "This attribute counts the total number of aborts received.
      This count wraps to zero after reaching its maximum value."
   DEFVAL     { 0 }
::= { mscDataSigChanTS014FramerStatsEntry 4 }

mscDataSigChanTS014FramerCrcErrors OBJECT-TYPE
   SYNTAX     Unsigned32 (0..4294967295)
   ACCESS     read-only
   STATUS     mandatory
   DESCRIPTION
     "This attribute counts the total number of frames with CRC errors.
      This count wraps to zero after reaching its maximum value."
   DEFVAL     { 0 }
::= { mscDataSigChanTS014FramerStatsEntry 5 }

mscDataSigChanTS014FramerLrcErrors OBJECT-TYPE
   SYNTAX     Unsigned32 (0..4294967295)
   ACCESS     read-only
   STATUS     mandatory
   DESCRIPTION
     "This attribute counts the total number of frames with LRC errors.
      This count wraps to zero after reaching its maximum value."
   DEFVAL     { 0 }
::= { mscDataSigChanTS014FramerStatsEntry 6 }

mscDataSigChanTS014FramerNonOctetErrors OBJECT-TYPE
   SYNTAX     Unsigned32 (0..4294967295)
   ACCESS     read-only
   STATUS     mandatory
   DESCRIPTION
     "This attribute counts the total number of frames that were non octet 
      aligned.
      This count wraps to zero after reaching its maximum value."
   DEFVAL     { 0 }
::= { mscDataSigChanTS014FramerStatsEntry 7 }

mscDataSigChanTS014FramerOverruns OBJECT-TYPE
   SYNTAX     Unsigned32 (0..4294967295)
   ACCESS     read-only
   STATUS     mandatory
   DESCRIPTION
     "This attribute counts the total number of frames received from the 
      link for which overruns occurred.
      This count wraps to zero after reaching its maximum value."
   DEFVAL     { 0 }
::= { mscDataSigChanTS014FramerStatsEntry 8 }

mscDataSigChanTS014FramerUnderruns OBJECT-TYPE
   SYNTAX     Unsigned32 (0..4294967295)
   ACCESS     read-only
   STATUS     mandatory
   DESCRIPTION
     "This attribute counts the total number of frames transmitted to the 
      link for which underruns occurred.
      This count wraps to zero after reaching its maximum value."
   DEFVAL     { 0 }
::= { mscDataSigChanTS014FramerStatsEntry 9 }

mscDataSigChanTS014FramerLargeFrmErrors OBJECT-TYPE
   SYNTAX     Unsigned32 (0..4294967295)
   ACCESS     read-only
   STATUS     mandatory
   DESCRIPTION
     "This attribute counts the total number of frames received which 
      were too large. The frame was longer than 500 bytes.
      This count wraps to zero after reaching its maximum value."
   DEFVAL     { 0 }
::= { mscDataSigChanTS014FramerStatsEntry 10 }




-- 
-- Version and Compliance statements
-- 



-- Object-Group Statement:
-- A list of all current accessible leaf objects.

-- OBJECTS { mscDataSigChanTS014FramerLargeFrmErrors,
--           mscDataSigChanTS014PeakActiveChannels,
--           mscDataSigChanTS014FramerRowStatus,
--           mscDataSigChanTS014ActiveChannels,
--           mscDataSigChanTS014RowStatus,
--           mscDataSigChanTS014N201,
--           mscDataSigChanTS014Tracing,
--           mscDataSigChanTS014FramerNonOctetErrors,
--           mscDataSigChanTS014FramerStorageType,
--           mscDataSigChanTS014FramerUsageState,
--           mscDataSigChanTS014FramerComponentName,
--           mscDataSigChanTS014N200,
--           mscDataSigChanTS014FramerFrmFromIf,
--           mscDataSigChanTS014FramerInterfaceName,
--           mscDataSigChanTS014ComponentName,
--           mscDataSigChanTS014T23,
--           mscDataSigChanTS014FramerUnderruns,
--           mscDataSigChanTS014Side,
--           mscDataSigChanTS014FramerCrcErrors,
--           mscDataSigChanTS014StorageType,
--           mscDataSigChanTS014FramerOperationalState,
--           mscDataSigChanTS014T200,
--           mscDataSigChanTS014FramerOctetFromIf,
--           mscDataSigChanTS014T203,
--           mscDataSigChanTS014FramerFrmToIf,
--           mscDataSigChanTS014DChanStatus,
--           mscDataSigChanTS014FramerAdminState,
--           mscDataSigChanTS014CircuitSwitchedK,
--           mscDataSigChanTS014FramerAborts,
--           mscDataSigChanTS014FramerLrcErrors,
--           mscDataSigChanTS014FramerOverruns }
-- STATUS  mandatory
-- DESCRIPTION
--   "A list of all current accessible leaf objects."

disdnTS014Group OBJECT IDENTIFIER ::= { disdnTS014MIB 1 }
disdnTS014GroupCA OBJECT IDENTIFIER ::= { disdnTS014Group 1 }
disdnTS014GroupCA02 OBJECT IDENTIFIER ::= { disdnTS014GroupCA 3 }
disdnTS014GroupCA02A OBJECT IDENTIFIER ::= { disdnTS014GroupCA02 2 }



-- Agent-Capabilities Statement:

-- PRODUCT-RELEASE "MscPassport Release 1.2 DisdnTS014."
-- STATUS          mandatory
-- DESCRIPTION     "Carrier Passport DisdnTS014 MIB: MIB Version CA02A,
--                  Software Version CA02S9C."
-- SUPPORTS        Nortel-MsCarrier-MscPassport-DisdnTS014MIB
--    INCLUDES     { disdnTS014GroupCA02A }

disdnTS014Capabilities OBJECT IDENTIFIER ::= { disdnTS014MIB 3 }
disdnTS014CapabilitiesCA OBJECT IDENTIFIER ::= { disdnTS014Capabilities 1 }
disdnTS014CapabilitiesCA02 OBJECT IDENTIFIER ::= { disdnTS014CapabilitiesCA 3 }
disdnTS014CapabilitiesCA02A OBJECT IDENTIFIER ::= { disdnTS014CapabilitiesCA02 2 }





END
