-- ************************************************************ 
-- *                   
-- *                   
-- *                   
-- *  Project:         
-- *                   
-- *  System:          
-- *                   
-- *  Process:         
-- *                   
-- *  $Author: Cipriani $
-- *          Alcatel Italia
-- *                            
-- *  $Clearcase File: alarm.my $
-- *                
-- *  $Revision: /main/R500_branch/4 $
-- *          
-- *  $Date: 2003/11/24 14:30:00 $
-- *
-- *  Description: 
-- *
-- ************************************************************
--
-- ******************************************************
-- *                  COPYRIGHT NOTICE                  *
-- *                                                    *
-- *                    CONFIDENTIAL                    * 
-- *                                                    *
-- *    All rights reserved. Alcatel Italia.            *
-- *    This computer program is protected under        *
-- *    Copyright. Recipient is to retain the program   *
-- *    in confidence and is not permitted to copy,     *
-- *    use, distribute, modify or translate this       *
-- *    program without authorisation                   *
-- *                                                    * 
-- ******************************************************

GENOSALARMNOTIFICATION-MIB  DEFINITIONS ::= BEGIN

IMPORTS
        MODULE-IDENTITY, OBJECT-TYPE,  NOTIFICATION-TYPE, enterprises,
	Counter32
                FROM SNMPv2-SMI
	TruthValue, DisplayString
                FROM SNMPv2-TC;

alcatel  OBJECT IDENTIFIER 
        ::= { enterprises 637 }

nmu  OBJECT IDENTIFIER 
        ::= { alcatel 65 }

genos  OBJECT IDENTIFIER 
        ::= { nmu 1 }

alarmHandoff  MODULE-IDENTITY
	      LAST-UPDATED "9807030000Z"
	      ORGANIZATION "Alcatel GENOS Development"
	      CONTACT-INFO ""
	      DESCRIPTION
		"The MIB module for GENOS alarm handoff"
        ::= { genos 1 }

alarmHandoffObjects OBJECT IDENTIFIER ::= { alarmHandoff 1 }

unsolicitedEventsEnabled        OBJECT-TYPE
        SYNTAX TruthValue
        MAX-ACCESS  read-write
        STATUS  current
        DESCRIPTION     "Status indicating if unsolicited alarm
                                traps are to be generated"
        ::= { alarmHandoffObjects 1 }

alarmTable      OBJECT-TYPE
        SYNTAX  SEQUENCE OF AlarmEntry
        MAX-ACCESS not-accessible
        STATUS  current
        DESCRIPTION     "The list of currently raised alarms"
        ::= { alarmHandoffObjects 2 }


alarmEntry      OBJECT-TYPE
        SYNTAX  AlarmEntry
        MAX-ACCESS  not-accessible
        STATUS  current
        DESCRIPTION     "Each entry contains 1 alarm description"
        INDEX   { currentAlarmId }
        ::= { alarmTable 1 }

AlarmEntry ::=
        SEQUENCE {
                currentAlarmId AlarmId,
                friendlyName
                        DisplayString,
                eventTime
                        DisplayString,
                eventType
                        DisplayString,
                probableCause
                        DisplayString,
                perceivedSeverity
                        DisplayString,
		additionalText
			DisplayString,
		specificProblems
			DisplayString,
		acknowledgementStatus
			DisplayString,
	        reserveStatus	
			DisplayString,
		additionalInformation
			DisplayString,
                neLocationName
                        DisplayString,
		managedobjectInstance
		        DisplayString,
		acknowledgementUserName 
		DisplayString,      
		asIdentity
			DisplayString	
        }

currentAlarmId  OBJECT-TYPE
        SYNTAX  AlarmId
        MAX-ACCESS  read-only
        STATUS  current
        DESCRIPTION "A unique identifier for an alarm"
        ::= { alarmEntry 1 }

AlarmId ::= Counter32 (1..4294967295)

friendlyName    OBJECT-TYPE
        SYNTAX  DisplayString
        MAX-ACCESS  read-only
        STATUS  current
        DESCRIPTION     "The source of the alarm in a human
                                readable form"
        ::= { alarmEntry 2 }

eventTime       OBJECT-TYPE
        SYNTAX  DisplayString
        MAX-ACCESS  read-only
        STATUS  current
        DESCRIPTION     "The time the alarm event occurred"
        ::= { alarmEntry 3 }

eventType       OBJECT-TYPE
        SYNTAX  DisplayString
        MAX-ACCESS  read-only
        STATUS  current
        DESCRIPTION     "A conversion of the X721 notification types
                                to a human readable form"
        ::= { alarmEntry 4 }

probableCause   OBJECT-TYPE
        SYNTAX  DisplayString
        MAX-ACCESS  read-only
        STATUS  current
        DESCRIPTION     "A conversion of the local and global OIDs to a
                                human readable form"
        ::= { alarmEntry 5 }

perceivedSeverity       OBJECT-TYPE
        SYNTAX      DisplayString
        MAX-ACCESS  read-only
        STATUS  current
        DESCRIPTION     "The perceived Severity of the of the alarm
			        it will be one of:
                                   indeterminate
                                   critical
                                   major
                                   minor
                                   warning
                                   cleared"
        ::= { alarmEntry 6 }

additionalText       OBJECT-TYPE
        SYNTAX      DisplayString
        MAX-ACCESS  read-only
        STATUS      current
        DESCRIPTION     "Additional text for the alarm"
        ::= { alarmEntry 7 }

specificProblems     OBJECT-TYPE
        SYNTAX      DisplayString
        MAX-ACCESS  read-only
        STATUS      current
        DESCRIPTION     "Specific Problems of the alarm"
        ::= { alarmEntry 8 }

acknowledgementStatus  OBJECT-TYPE
        SYNTAX      DisplayString
        MAX-ACCESS  read-only
        STATUS      current
        DESCRIPTION     "The Acknowledgement Status of the alarm"
        ::= { alarmEntry 9 }

reserveStatus  OBJECT-TYPE
        SYNTAX      DisplayString
        MAX-ACCESS  read-only
        STATUS      current
        DESCRIPTION     "The Reserve Status of the alarm"
        ::= { alarmEntry 10 }

additionalInformation  OBJECT-TYPE
        SYNTAX      DisplayString
        MAX-ACCESS  read-only
        STATUS      current
        DESCRIPTION     "The Additional Information of the alarm"
        ::= { alarmEntry 11 }

neLocationName  OBJECT-TYPE
        SYNTAX      DisplayString
        MAX-ACCESS  read-only
        STATUS      current
        DESCRIPTION     "The NE Location Name of the alarm"
        ::= { alarmEntry 12 }

managedobjectInstance  OBJECT-TYPE
        SYNTAX      DisplayString
        MAX-ACCESS  read-only
        STATUS      current
        DESCRIPTION     "The managed object Instance of the alarm"
        ::= { alarmEntry 13 }

acknowledgementUserName  OBJECT-TYPE
        SYNTAX      DisplayString
        MAX-ACCESS  read-only
        STATUS      current
        DESCRIPTION     "acknowledgement User Name"
        ::= { alarmEntry 14 }

asIdentity    OBJECT-TYPE
        SYNTAX  DisplayString
        MAX-ACCESS  read-only
        STATUS  current
        DESCRIPTION     "The identity of the AS"
        ::= { alarmEntry 15 }

alarmHandoffTraps OBJECT IDENTIFIER ::= { alarmHandoff 2 }

alarmRaise NOTIFICATION-TYPE
	   OBJECTS { currentAlarmId,
		     friendlyName,
		     eventTime,
		     eventType,
		     probableCause,
		     perceivedSeverity,
		     additionalText,
		     specificProblems,
		     acknowledgementStatus,
		     reserveStatus,
		     additionalInformation,
		     neLocationName,
		     managedobjectInstance,
		     acknowledgementUserName,
		     asIdentity
		     }
	   STATUS current
	   DESCRIPTION "Notification that an alarm is currently active"
	   ::= { alarmHandoffTraps 1 }

alarmClear NOTIFICATION-TYPE
	   OBJECTS { currentAlarmId,
		     eventTime,
		     friendlyName,
		     probableCause,
		     asIdentity}
	   STATUS current
	   DESCRIPTION "Notification that an alarm has been cleared"
	   ::= { alarmHandoffTraps 2 }

alarmAck   NOTIFICATION-TYPE
           OBJECTS { listAlarmIds,
                     operatorName,
		     asIdentity }
           STATUS current
           DESCRIPTION "Notification that an alarm has been acknowledged"
           ::= { alarmHandoffTraps 3 }

alarmPurge   NOTIFICATION-TYPE
           OBJECTS { purgelistAlarmIds,
	   	     asIdentity
                     }
           STATUS current
           DESCRIPTION "Notification that an alarm has been purged"
           ::= { alarmHandoffTraps 4 } 
 
alarmReserve   NOTIFICATION-TYPE
           OBJECTS { reservelistAlarmIds,
                     reserveoperatorName,
		     asIdentity }
           STATUS current
           DESCRIPTION "Notification that an alarm has been reserved"
           ::= { alarmHandoffTraps 5 }

alarmUnreserve   NOTIFICATION-TYPE
           OBJECTS { unreservelistAlarmIds,
                     unreserveoperatorName,
		     asIdentity }
           STATUS current
           DESCRIPTION "Notification that an alarm has been unreserved"
           ::= { alarmHandoffTraps 6 }

asConnectionStatus   NOTIFICATION-TYPE
           OBJECTS { asconnectionstatus,
                     asId }
           STATUS current
           DESCRIPTION "Notification that an AS status is changed"
           ::= { alarmHandoffTraps 7 }
           
-- add the following unack for AS P10
alarmUnAck   NOTIFICATION-TYPE
           OBJECTS { unacklistAlarmIds,
                     unackoperatorName,
		     asIdentity }
           STATUS current
           DESCRIPTION "Notification that an alarm has been unacknowledged"
           ::= { alarmHandoffTraps 8 }
-- end add the unack for AS P10                     
alarmHandoffAck OBJECT IDENTIFIER ::= { alarmHandoff 3 }
           
listAlarmIds        OBJECT-TYPE
        SYNTAX DisplayString
        MAX-ACCESS  read-write
        STATUS  current
        DESCRIPTION     "The list of Alarms which are acknowledged  
                              by the Operator "
        ::= { alarmHandoffAck 1 }

operatorName        OBJECT-TYPE
        SYNTAX DisplayString
        MAX-ACCESS  read-write
        STATUS  current
        DESCRIPTION     "The name of the Operator that performed the 
                             acknowledgement "
        ::= { alarmHandoffAck 2 }

ackasIdentityFilter        OBJECT-TYPE
        SYNTAX DisplayString
        MAX-ACCESS  read-write
        STATUS  current
        DESCRIPTION     "Dinamic Filter for AS Identity "  
        ::= { alarmHandoffAck 3  }   

alarmHandoffFilter OBJECT IDENTIFIER ::= { alarmHandoff 4 }
	   
friendlyNameFilter        OBJECT-TYPE
        SYNTAX DisplayString
        MAX-ACCESS  read-write
        STATUS  current
        DESCRIPTION     "Dinamic Filter for Friendly name "  
        ::= { alarmHandoffFilter 1 }
	
eventTimeFilter        OBJECT-TYPE
        SYNTAX DisplayString
        MAX-ACCESS  read-write
        STATUS  current
        DESCRIPTION     "Dinamic Filter for event Time"  
        ::= { alarmHandoffFilter 2 }
	
eventTypeFilter        OBJECT-TYPE
        SYNTAX DisplayString
        MAX-ACCESS  read-write
        STATUS  current
        DESCRIPTION     "Dinamic Filter for event Type"  
        ::= { alarmHandoffFilter 3 }
	
probableCauseFilter        OBJECT-TYPE
        SYNTAX DisplayString
        MAX-ACCESS  read-write
        STATUS  current
        DESCRIPTION     "Dinamic Filter for probable Cause"  
        ::= { alarmHandoffFilter 4 }

perceivedSeverityFilter        OBJECT-TYPE
        SYNTAX DisplayString
        MAX-ACCESS  read-write
        STATUS  current
        DESCRIPTION     "Dinamic Filter for  perceived Severity"  
        ::= { alarmHandoffFilter 5 }

specificProblemsFilter        OBJECT-TYPE
        SYNTAX DisplayString
        MAX-ACCESS  read-write
        STATUS  current
        DESCRIPTION     "Dinamic Filter for specific Problems"  
        ::= { alarmHandoffFilter 6 }

nelocationNameFilter        OBJECT-TYPE
        SYNTAX DisplayString
        MAX-ACCESS  read-write
        STATUS  current
        DESCRIPTION     "Dinamic Filter for nelocation name "  
        ::= { alarmHandoffFilter 7 }

additionalInformationFilter        OBJECT-TYPE
        SYNTAX DisplayString
        MAX-ACCESS  read-write
        STATUS  current
        DESCRIPTION     "Dinamic Filter for additional Information "  
        ::= { alarmHandoffFilter 8 }

managedobjectInstanceFilter        OBJECT-TYPE
        SYNTAX DisplayString
        MAX-ACCESS  read-write
        STATUS  current
        DESCRIPTION     "Dinamic Filter for managed object Instance "  
        ::= { alarmHandoffFilter 9 }

asIdentityFilter        OBJECT-TYPE
        SYNTAX DisplayString
        MAX-ACCESS  read-write
        STATUS  current
        DESCRIPTION     "Dinamic Filter for AS Identity "  
        ::= { alarmHandoffFilter 10 }     

alarmHandoffPurge OBJECT IDENTIFIER ::= { alarmHandoff 5 }
           
purgelistAlarmIds        OBJECT-TYPE
        SYNTAX DisplayString
        MAX-ACCESS  read-write
        STATUS  current
        DESCRIPTION     "The list of Alarms which are purged  
                              by the Operator "
        ::= { alarmHandoffPurge 1 }

purgeoperatorName        OBJECT-TYPE
        SYNTAX DisplayString
        MAX-ACCESS  read-write
        STATUS  current
        DESCRIPTION     "The name of the Operator that performed the 
                             purge "
        ::= { alarmHandoffPurge 2 }

purgeasIdentityFilter        OBJECT-TYPE
        SYNTAX DisplayString
        MAX-ACCESS  read-write
        STATUS  current
        DESCRIPTION     "Dinamic Filter for AS Identity "  
        ::= { alarmHandoffPurge 3 }     


alarmHandoffReserve OBJECT IDENTIFIER ::= { alarmHandoff 6 }
           
reservelistAlarmIds        OBJECT-TYPE
        SYNTAX DisplayString
        MAX-ACCESS  read-write
        STATUS  current
        DESCRIPTION     "The list of Alarms which are reserved 
                              by the Operator "
        ::= { alarmHandoffReserve 1 }

reserveoperatorName        OBJECT-TYPE
        SYNTAX DisplayString
        MAX-ACCESS  read-write
        STATUS  current
        DESCRIPTION     "The name of the Operator that performed the 
                             reserved "
        ::= { alarmHandoffReserve 2 }

reserveasIdentityFilter        OBJECT-TYPE
        SYNTAX DisplayString
        MAX-ACCESS  read-write
        STATUS  current
        DESCRIPTION     "Dinamic Filter for AS Identity "  
        ::= { alarmHandoffReserve 3  }     
 
alarmHandoffUnreserve OBJECT IDENTIFIER ::= { alarmHandoff 7 }
           
unreservelistAlarmIds        OBJECT-TYPE
        SYNTAX DisplayString
        MAX-ACCESS  read-write
        STATUS  current
        DESCRIPTION     "The list of Alarms which are unreserved 
                              by the Operator "
        ::= { alarmHandoffUnreserve 1 }

unreserveoperatorName        OBJECT-TYPE
        SYNTAX DisplayString
        MAX-ACCESS  read-write
        STATUS  current
        DESCRIPTION     "The name of the Operator that performed the 
                             unreserved "
        ::= { alarmHandoffUnreserve 2 } 

unreserveasIdentityFilter        OBJECT-TYPE
        SYNTAX DisplayString
        MAX-ACCESS  read-write
        STATUS  current
        DESCRIPTION     "Dinamic Filter for AS Identity "  
        ::= { alarmHandoffUnreserve 3  }   

alarmHandoffasConnectionStatus OBJECT IDENTIFIER ::= { alarmHandoff 8 }
           
asconnectionstatus          OBJECT-TYPE
        SYNTAX DisplayString
        MAX-ACCESS  read-only
        STATUS  current
        DESCRIPTION     "The status of the AS "
        ::= { alarmHandoffasConnectionStatus 1 }
	
asId          OBJECT-TYPE
        SYNTAX DisplayString
        MAX-ACCESS  read-only
        STATUS  current
        DESCRIPTION     "The identity of the AS "
        ::= { alarmHandoffasConnectionStatus 2 }	

-- add the alarmHandoffUnAck for AS P10
alarmHandoffUnAck OBJECT IDENTIFIER ::= { alarmHandoff 9 }
           
unacklistAlarmIds        OBJECT-TYPE
        SYNTAX DisplayString
        MAX-ACCESS  read-write
        STATUS  current
        DESCRIPTION     "The list of Alarms which are unacknowledged  
                              by the Operator "
        ::= { alarmHandoffUnAck 1 }

unackoperatorName        OBJECT-TYPE
        SYNTAX DisplayString
        MAX-ACCESS  read-write
        STATUS  current
        DESCRIPTION     "The name of the Operator that performed the 
                             unacknowledgement "
        ::= { alarmHandoffUnAck 2 }

unackasIdentityFilter        OBJECT-TYPE
        SYNTAX DisplayString
        MAX-ACCESS  read-write
        STATUS  current
        DESCRIPTION     "Dinamic Filter for AS Identity "  
        ::= { alarmHandoffUnAck 3  }   
-- end add the alarmHandoffUnack for AS P10	
END
