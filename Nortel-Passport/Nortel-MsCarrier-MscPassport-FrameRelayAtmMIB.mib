Nortel-MsCarrier-MscPassport-FrameRelayAtmMIB
DEFINITIONS ::= BEGIN



IMPORTS

      OBJECT-TYPE
   FROM RFC-1212

      mscPassportMIBs,
      mscComponents
   FROM Nortel-MsCarrier-MscPassport-UsefulDefinitionsMIB

      Counter32,
      RowPointer,
      DisplayString,
      StorageType,
      RowStatus,
      InterfaceIndex,
      Gauge32,
      Integer32,
      Unsigned32
   FROM Nortel-MsCarrier-MscPassport-StandardTextualConventionsMIB

      AsciiString,
      NonReplicated,
      HexString,
      EnterpriseDateAndTime,
      PassportCounter64,
      Link,
      IntegerSequence,
      Unsigned64
   FROM Nortel-MsCarrier-MscPassport-TextualConventionsMIB;




-- LAST-UPDATED   "9909010000Z"
-- ORGANIZATION   "Nortel Networks"
-- CONTACT-INFO   "
--         Nortel Carrier Data Network Management
--         
--         Postal:       P.O. Box 3511, Station C 
--                       Ottawa, Ontario 
--                       Canada  K1Y 4H7
--         
--         via the WEB:  http://www.nortelnetworks.com  
--                       select 'Contact Us' from the menu
--          
--         via phone:    1-800-4NORTEL"
-- DESCRIPTION
--    "The module describing the Nortel MsCarrier MscPassport
--     FrameRelayAtm Enterprise MIB."

frameRelayAtmMIB OBJECT IDENTIFIER ::= { mscPassportMIBs 51 }










-- FrameRelayAtmInterface/n
-- This component defines an instance of the Frame Relay to ATM 
-- interworking interface. It manages the set of Frame Relay DLCI 
-- connections that are interworked with ATM connections. The 
-- component instance value is a unique positive integer within a 
-- module. Framer is created whenever the FrAtm is added. Users who 
-- need VirtualFramer should delete the Framer first, then add the 
-- VirtualFramer.

mscFrAtm OBJECT IDENTIFIER ::= { mscComponents 72 }



mscFrAtmRowStatusTable OBJECT-TYPE
   SYNTAX     SEQUENCE OF MscFrAtmRowStatusEntry
   ACCESS     not-accessible
   STATUS     mandatory
   DESCRIPTION
     "This entry controls the addition and deletion of 
      mscFrAtm components."
::= { mscFrAtm 1 }

mscFrAtmRowStatusEntry OBJECT-TYPE
   SYNTAX     MscFrAtmRowStatusEntry
   ACCESS     not-accessible
   STATUS     mandatory
   DESCRIPTION
     "A single entry in the table represents a single 
      mscFrAtm component."
   INDEX {
      mscFrAtmIndex }
::= { mscFrAtmRowStatusTable 1 }

MscFrAtmRowStatusEntry ::= SEQUENCE {
   mscFrAtmRowStatus
      RowStatus,
   mscFrAtmComponentName
      DisplayString,
   mscFrAtmStorageType
      StorageType,
   mscFrAtmIndex
      Integer32 }

mscFrAtmRowStatus OBJECT-TYPE
   SYNTAX     RowStatus 
   ACCESS     read-write
   STATUS     mandatory
   DESCRIPTION
     "This variable is used as the basis for SNMP naming of
      mscFrAtm components.
      These components can be added and deleted."
::= { mscFrAtmRowStatusEntry 1 }

mscFrAtmComponentName OBJECT-TYPE
   SYNTAX     DisplayString 
   ACCESS     read-only
   STATUS     mandatory
   DESCRIPTION
     "This variable provides the component's string name for
      use with the ASCII Console Interface"
::= { mscFrAtmRowStatusEntry 2 }

mscFrAtmStorageType OBJECT-TYPE
   SYNTAX     StorageType 
   ACCESS     read-only
   STATUS     mandatory
   DESCRIPTION
     "This variable represents the storage type value for the
      mscFrAtm tables."
::= { mscFrAtmRowStatusEntry 4 }

mscFrAtmIndex OBJECT-TYPE
   SYNTAX     Integer32 (1..65535)
   ACCESS     not-accessible
   STATUS     mandatory
   DESCRIPTION
     "This variable represents the index for the mscFrAtm tables."
::= { mscFrAtmRowStatusEntry 10 }

mscFrAtmCidDataTable OBJECT-TYPE
   SYNTAX     SEQUENCE OF MscFrAtmCidDataEntry
   ACCESS     not-accessible
   STATUS     mandatory
   DESCRIPTION
     "This group contains the attribute for a component's Customer 
      Identifier (CID). Refer to the attribute description for a detailed 
      explanation of CIDs."
::= { mscFrAtm 10 }

mscFrAtmCidDataEntry OBJECT-TYPE
   SYNTAX     MscFrAtmCidDataEntry
   ACCESS     not-accessible
   STATUS     mandatory
   DESCRIPTION
     "An entry in the mscFrAtmCidDataTable."
   INDEX {
      mscFrAtmIndex }
::= { mscFrAtmCidDataTable 1 }

MscFrAtmCidDataEntry ::= SEQUENCE {
   mscFrAtmCustomerIdentifier
      Unsigned32 }

mscFrAtmCustomerIdentifier OBJECT-TYPE
   SYNTAX     Unsigned32 (0 | 1..8191)
   ACCESS     read-write
   STATUS     mandatory
   DESCRIPTION
     "This attribute holds the Customer Identifier (CID).
      
      Every component has a CID. If a component has a cid attribute, the 
      component's CID is the provisioned value of that attribute; 
      otherwise the component inherits the CID of its parent. The top-
      level component has a CID of 0.
      
      Every operator session also has a CID, which is the CID 
      provisioned for the operator's user ID. An operator will see only the 
      stream data for components having a matching CID. Also, the 
      operator will be allowed to issue commands for only those 
      components which have a matching CID.
      
      An operator CID of 0 is used to identify the Network Manager 
      (referred to as 'NetMan' in DPN). This CID matches the CID of 
      any component. Values 1 to 8191 inclusive (equivalent to 'basic 
      CIDs' in DPN) may be assigned to specific customers."
   DEFVAL     { 0 }
::= { mscFrAtmCidDataEntry 1 }

mscFrAtmStateTable OBJECT-TYPE
   SYNTAX     SEQUENCE OF MscFrAtmStateEntry
   ACCESS     not-accessible
   STATUS     mandatory
   DESCRIPTION
     "This group contains the three OSI State attributes and the six OSI 
      Status attributes. The descriptions generically indicate what each 
      attribute implies about the component. Note that not all the values 
      and state combinations described here are supported by every 
      component which uses this group. For component-specific 
      information and the valid state combinations, refer to NTP 241-
      7001-150, Passport Operations and Maintenance Guide."
::= { mscFrAtm 11 }

mscFrAtmStateEntry OBJECT-TYPE
   SYNTAX     MscFrAtmStateEntry
   ACCESS     not-accessible
   STATUS     mandatory
   DESCRIPTION
     "An entry in the mscFrAtmStateTable."
   INDEX {
      mscFrAtmIndex }
::= { mscFrAtmStateTable 1 }

MscFrAtmStateEntry ::= SEQUENCE {
   mscFrAtmAdminState
      INTEGER,
   mscFrAtmOperationalState
      INTEGER,
   mscFrAtmUsageState
      INTEGER,
   mscFrAtmAvailabilityStatus
      OCTET STRING,
   mscFrAtmProceduralStatus
      OCTET STRING,
   mscFrAtmControlStatus
      OCTET STRING,
   mscFrAtmAlarmStatus
      OCTET STRING,
   mscFrAtmStandbyStatus
      INTEGER,
   mscFrAtmUnknownStatus
      INTEGER }

mscFrAtmAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component.
      
      The OSI Status attributes, if supported by the component, may 
      provide more details, qualifying the state of the component."
   DEFVAL     { unlocked }
::= { mscFrAtmStateEntry 1 }

mscFrAtmOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle.
      
      The OSI Status attributes, if supported by the component, may 
      provide more details, qualifying the state of the component."
   DEFVAL     { disabled }
::= { mscFrAtmStateEntry 2 }

mscFrAtmUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time.
      
      The OSI Status attributes, if supported by the component, may 
      provide more details, qualifying the state of the component."
   DEFVAL     { idle }
::= { mscFrAtmStateEntry 3 }

mscFrAtmAvailabilityStatus OBJECT-TYPE
   SYNTAX     OCTET STRING (SIZE (2))
   ACCESS     read-only
   STATUS     mandatory
   DESCRIPTION
     "If supported by the component, this attribute indicates the OSI 
      Availability status of the component. Note that, even though it is 
      defined as a multi-valued set, at most one value is shown to the user.
      
      When no values are in the set, this indicates that either the attribute 
      is not supported or that none of the status conditions described 
      below are present.
      
      The value inTest indicates that the resource is undergoing a test 
      procedure. If adminState is locked or shuttingDown, the normal 
      users are precluded from using the resource and controlStatus is 
      reservedForTest. Tests that do not exclude additional users can be 
      present in any operational or administrative state but the 
      reservedForTest condition should not be present.
      
      The value failed indicates that the component has an internal fault 
      that prevents it from operating. The operationalState is disabled.
      
      The value dependency indicates that the component cannot operate 
      because some other resource on which it depends is unavailable. 
      The operationalState is disabled.
      
      The value powerOff indicates the resource requires power to be 
      applied and it is not powered on. The operationalState is disabled.
      
      The value offLine indicates the resource requires a routine 
      operation (either manual, automatic, or both) to be performed to 
      place it on-line and make it available for use. The operationalState 
      is disabled.
      
      The value offDuty indicates the resource is inactive in accordance 
      with a predetermined time schedule. In the absence of other 
      disabling conditions, the operationalState is enabled or disabled.
      
      The value degraded indicates the service provided by the 
      component is degraded in some way, such as in speed or operating 
      capacity. However, the resource remains available for service. The 
      operationalState is enabled.
      
      The value notInstalled indicates the resource is not present. The 
      operationalState is disabled.
      
      The value logFull is not used.

      Description of bits:
      inTest(0)
      failed(1)
      powerOff(2)
      offLine(3)
      offDuty(4)
      dependency(5)
      degraded(6)
      notInstalled(7)
      logFull(8)"
::= { mscFrAtmStateEntry 4 }

mscFrAtmProceduralStatus OBJECT-TYPE
   SYNTAX     OCTET STRING (SIZE (1))
   ACCESS     read-only
   STATUS     mandatory
   DESCRIPTION
     "If supported by the component, this attribute indicates the OSI 
      Procedural status of the component. Note that, even though it is 
      defined as a multi-valued set, at most one value is shown to the user.
      
      When no values are in the set, this indicates that either the attribute 
      is not supported or that none of the status conditions described 
      below are present.
      
      The value initializationRequired indicates (for a resource which 
      doesn't initialize autonomously) that initialization is required before 
      it can perform its normal functions, and this procedure has not been 
      initiated. The operationalState is disabled.
      
      The value notInitialized indicates (for a resource which does 
      initialize autonomously) that initialization is required before it can 
      perform its normal functions, and this procedure has not been 
      initiated. The operationalState may be enabled or disabled.
      
      The value initializing indicates that initialization has been initiated 
      but is not yet complete. The operationalState may be enabled or 
      disabled.
      
      The value reporting indicates the resource has completed some 
      processing operation and is notifying the results. The 
      operationalState is enabled.
      
      The value terminating indicates the component is in a termination 
      phase. If the resource doesn't reinitialize autonomously, 
      operationalState is disabled; otherwise it is enabled or disabled.

      Description of bits:
      initializationRequired(0)
      notInitialized(1)
      initializing(2)
      reporting(3)
      terminating(4)"
::= { mscFrAtmStateEntry 5 }

mscFrAtmControlStatus OBJECT-TYPE
   SYNTAX     OCTET STRING (SIZE (1))
   ACCESS     read-only
   STATUS     mandatory
   DESCRIPTION
     "If supported by the component, this attribute indicates the OSI 
      Control status of the component. Note that, even though it is defined 
      as a multi-valued set, at most one value is shown to the user.
      
      When no values are in the set, this indicates that either the attribute 
      is not supported or that none of the status conditions described 
      below are present.
      
      The value subjectToTest indicates the resource is available but tests 
      may be conducted simultaneously at unpredictable times, which 
      may cause it to exhibit unusual characteristics.
      
      The value partOfServicesLocked indicates that part of the service is 
      restricted from users of a resource. The adminState is unlocked.
      
      The value reservedForTest indicates that the component is 
      administratively unavailable because it is undergoing a test 
      procedure. The adminState is locked.
      
      The value suspended indicates that the service has been 
      administratively suspended.

      Description of bits:
      subjectToTest(0)
      partOfServicesLocked(1)
      reservedForTest(2)
      suspended(3)"
::= { mscFrAtmStateEntry 6 }

mscFrAtmAlarmStatus OBJECT-TYPE
   SYNTAX     OCTET STRING (SIZE (1))
   ACCESS     read-only
   STATUS     mandatory
   DESCRIPTION
     "If supported by the component, this attribute indicates the OSI 
      Alarm status of the component. Note that, even though it is defined 
      as a multi-valued set, at most one value is shown to the user.
      
      When no values are in the set, this indicates that either the attribute 
      is not supported or that none of the status conditions described 
      below are present.
      
      The value underRepair indicates the component is currently being 
      repaired. The operationalState is enabled or disabled.
      
      The value critical indicates one or more critical alarms are 
      outstanding against the component. Other, less severe, alarms may 
      also be outstanding. The operationalState is enabled or disabled.
      
      The value major indicates one or more major alarms are 
      outstanding against the component. Other, less severe, alarms may 
      also be outstanding. The operationalState is enabled or disabled.
      
      The value minor indicates one or more minor alarms are 
      outstanding against the component. Other, less severe, alarms may 
      also be outstanding. The operationalState is enabled or disabled.
      
      The value alarmOutstanding generically indicates that an alarm of 
      some severity is outstanding against the component.

      Description of bits:
      underRepair(0)
      critical(1)
      major(2)
      minor(3)
      alarmOutstanding(4)"
::= { mscFrAtmStateEntry 7 }

mscFrAtmStandbyStatus OBJECT-TYPE
   SYNTAX     INTEGER  {
                 hotStandby(0),
                 coldStandby(1),
                 providingService(2),
                 notSet(15) }
   ACCESS     read-only
   STATUS     mandatory
   DESCRIPTION
     "If supported by the component, this attribute indicates the OSI 
      Standby status of the component.
      
      The value notSet indicates that either the attribute is not supported 
      or that none of the status conditions described below are present. 
      Note that this is a non-standard value, used because the original 
      specification indicated this attribute was set-valued and thus, did not 
      provide a value to indicate that none of the other three are 
      applicable.
      
      The value hotStandby indicates that the resource is not providing 
      service but will be immediately able to take over the role of the 
      resource to be backed up, without initialization activity, and 
      containing the same information as the resource to be backed up.
      
      The value coldStandby indicates the resource is a backup for 
      another resource but will not be immediately able to take over the 
      role of the backed up resource and will require some initialization 
      activity.
      
      The value providingService indicates that this component, as a 
      backup resource, is currently backing up another resource."
   DEFVAL     { notSet }
::= { mscFrAtmStateEntry 8 }

mscFrAtmUnknownStatus OBJECT-TYPE
   SYNTAX     INTEGER  {
                 false(0),
                 true(1) }
   ACCESS     read-only
   STATUS     mandatory
   DESCRIPTION
     "This attribute indicates the OSI Unknown status of the component.
      
      The value false indicates that all of the other OSI State and Status 
      attribute values can be considered accurate.
      
      The value true indicates that the actual state of the component is not 
      known for sure."
   DEFVAL     { false }
::= { mscFrAtmStateEntry 9 }

mscFrAtmStatsTable OBJECT-TYPE
   SYNTAX     SEQUENCE OF MscFrAtmStatsEntry
   ACCESS     not-accessible
   STATUS     mandatory
   DESCRIPTION
     "FrUni/n Statistics
      This group contains the statistics about the operational behavior of 
      the service at the interface level."
::= { mscFrAtm 12 }

mscFrAtmStatsEntry OBJECT-TYPE
   SYNTAX     MscFrAtmStatsEntry
   ACCESS     not-accessible
   STATUS     mandatory
   DESCRIPTION
     "An entry in the mscFrAtmStatsTable."
   INDEX {
      mscFrAtmIndex }
::= { mscFrAtmStatsTable 1 }

MscFrAtmStatsEntry ::= SEQUENCE {
   mscFrAtmLastUnknownDlci
      Unsigned32,
   mscFrAtmUnknownDlciFramesFromIf
      Counter32,
   mscFrAtmInvalidHeaderFramesFromIf
      Counter32 }

mscFrAtmLastUnknownDlci OBJECT-TYPE
   SYNTAX     Unsigned32 (0..1023)
   ACCESS     read-only
   STATUS     mandatory
   DESCRIPTION
     "This attribute identifies the most recent DLCI which user frames 
      were received on for which a DLCI has not been provisioned on the 
      port."
   DEFVAL     { 0 }
::= { mscFrAtmStatsEntry 1 }

mscFrAtmUnknownDlciFramesFromIf OBJECT-TYPE
   SYNTAX     Counter32 
   ACCESS     read-only
   STATUS     mandatory
   DESCRIPTION
     "This attribute contains a count of the number of frames received 
      from the interface with an unknown DLCI (DLCI which is not 
      provisioned). When the maximum is reached the count wraps to 
      zero."
::= { mscFrAtmStatsEntry 2 }

mscFrAtmInvalidHeaderFramesFromIf OBJECT-TYPE
   SYNTAX     Counter32 
   ACCESS     read-only
   STATUS     mandatory
   DESCRIPTION
     "This attribute counts the number of frames received from the 
      interface with an invalid header format. When the maximum is 
      reached the count wraps to zero."
::= { mscFrAtmStatsEntry 3 }

mscFrAtmIfEntryTable OBJECT-TYPE
   SYNTAX     SEQUENCE OF MscFrAtmIfEntryEntry
   ACCESS     not-accessible
   STATUS     mandatory
   DESCRIPTION
     "This group contains the provisionable attributes for the ifEntry."
::= { mscFrAtm 13 }

mscFrAtmIfEntryEntry OBJECT-TYPE
   SYNTAX     MscFrAtmIfEntryEntry
   ACCESS     not-accessible
   STATUS     mandatory
   DESCRIPTION
     "An entry in the mscFrAtmIfEntryTable."
   INDEX {
      mscFrAtmIndex }
::= { mscFrAtmIfEntryTable 1 }

MscFrAtmIfEntryEntry ::= SEQUENCE {
   mscFrAtmIfAdminStatus
      INTEGER,
   mscFrAtmIfIndex
      InterfaceIndex }

mscFrAtmIfAdminStatus OBJECT-TYPE
   SYNTAX     INTEGER  {
                 up(1),
                 down(2),
                 testing(3) }
   ACCESS     read-write
   STATUS     mandatory
   DESCRIPTION
     "The desired state of the interface. The up state indicates the 
      interface is operational. The down state indicates the interface is not 
      operational. The testing state indicates that no operational packets 
      can be passed."
   DEFVAL     { up }
::= { mscFrAtmIfEntryEntry 1 }

mscFrAtmIfIndex OBJECT-TYPE
   SYNTAX     InterfaceIndex (1..65535)
   ACCESS     read-only
   STATUS     mandatory
   DESCRIPTION
     "This is the index for the IfEntry. Its value is automatically initialized 
      during the provisioning process."
::= { mscFrAtmIfEntryEntry 2 }

mscFrAtmOperStatusTable OBJECT-TYPE
   SYNTAX     SEQUENCE OF MscFrAtmOperStatusEntry
   ACCESS     not-accessible
   STATUS     mandatory
   DESCRIPTION
     "This group includes the Operational Status attribute. This attribute 
      defines the current operational state of this component."
::= { mscFrAtm 14 }

mscFrAtmOperStatusEntry OBJECT-TYPE
   SYNTAX     MscFrAtmOperStatusEntry
   ACCESS     not-accessible
   STATUS     mandatory
   DESCRIPTION
     "An entry in the mscFrAtmOperStatusTable."
   INDEX {
      mscFrAtmIndex }
::= { mscFrAtmOperStatusTable 1 }

MscFrAtmOperStatusEntry ::= SEQUENCE {
   mscFrAtmSnmpOperStatus
      INTEGER }

mscFrAtmSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { mscFrAtmOperStatusEntry 1 }

mscFrAtmEmissionPriorityQsTable OBJECT-TYPE
   SYNTAX     SEQUENCE OF MscFrAtmEmissionPriorityQsEntry
   ACCESS     not-accessible
   STATUS     mandatory
   DESCRIPTION
     "This group contains the provisionable attribute to specifie the 
      number of Frame Relay egress emission priority queues to be used 
      on that Frame Relay Interface"
::= { mscFrAtm 15 }

mscFrAtmEmissionPriorityQsEntry OBJECT-TYPE
   SYNTAX     MscFrAtmEmissionPriorityQsEntry
   ACCESS     not-accessible
   STATUS     mandatory
   DESCRIPTION
     "An entry in the mscFrAtmEmissionPriorityQsTable."
   INDEX {
      mscFrAtmIndex }
::= { mscFrAtmEmissionPriorityQsTable 1 }

MscFrAtmEmissionPriorityQsEntry ::= SEQUENCE {
   mscFrAtmNumberOfEmissionQs
      Unsigned32 }

mscFrAtmNumberOfEmissionQs OBJECT-TYPE
   SYNTAX     Unsigned32 (2 | 4)
   ACCESS     read-write
   STATUS     mandatory
   DESCRIPTION
     "This attribute specifies the number of egress emission priority 
      queues that will be used for that Frame Relay interface. The 
      possible values of this attribute are 2 or 4:
      For V.35, V.11, HSSI, E1, DS1, E3, DS3 or 8pDS1 the possible 
      values are: 2 (in which case they are hardware queues), or 4 (in 
      which case they are software queues).
      For DS1C, E1C or DS3C the possible values are 2, 4 (in all cases 
      they are software queues)."
   DEFVAL     { 2 }
::= { mscFrAtmEmissionPriorityQsEntry 1 }

mscFrAtmFrmToIfByQueueTable OBJECT-TYPE
   SYNTAX     SEQUENCE OF MscFrAtmFrmToIfByQueueEntry
   ACCESS     not-accessible
   STATUS     mandatory
   DESCRIPTION
     "This attribute counts the total number of frames transmitted to the 
      interface per egress emission priority queue since the component 
      has been activated. There is potientially a maximum of 4 emission 
      priority queues. The number of available egress queues varies 
      according to the value of the provisionable attribute 
      numberOfEmissionQs. Egress queue 0 has the lowest priority, while 
      egress queue 3 has the highest priority. The queue values
      are only indicated when the numberOfEmissionQs is set to 4 
      queues."
::= { mscFrAtm 341 }

mscFrAtmFrmToIfByQueueEntry OBJECT-TYPE
   SYNTAX     MscFrAtmFrmToIfByQueueEntry
   ACCESS     not-accessible
   STATUS     mandatory
   DESCRIPTION
     "An entry in the mscFrAtmFrmToIfByQueueTable."
   INDEX {
      mscFrAtmIndex,
      mscFrAtmFrmToIfByQueueIndex }
::= { mscFrAtmFrmToIfByQueueTable 1 }

MscFrAtmFrmToIfByQueueEntry ::= SEQUENCE {
   mscFrAtmFrmToIfByQueueIndex
      Integer32,
   mscFrAtmFrmToIfByQueueValue
      Unsigned32 }

mscFrAtmFrmToIfByQueueIndex OBJECT-TYPE
   SYNTAX     Integer32 (0..3)
   ACCESS     not-accessible
   STATUS     mandatory
   DESCRIPTION
     "This variable represents the index for the mscFrAtmFrmToIfByQueueTable."
::= { mscFrAtmFrmToIfByQueueEntry 1 }

mscFrAtmFrmToIfByQueueValue OBJECT-TYPE
   SYNTAX     Unsigned32 (0..4294967295)
   ACCESS     read-only
   STATUS     mandatory
   DESCRIPTION
     "This variable represents an individual value for the
      mscFrAtmFrmToIfByQueueTable."
::= { mscFrAtmFrmToIfByQueueEntry 2 }

mscFrAtmOctetToIfByQueueTable OBJECT-TYPE
   SYNTAX     SEQUENCE OF MscFrAtmOctetToIfByQueueEntry
   ACCESS     not-accessible
   STATUS     mandatory
   DESCRIPTION
     "This attribute counts the total number of octets transmitted from the 
      service to the interface per emission priority queue since the 
      component has been activated. There is potientially a maximum of 
      4 emission priority queues. The number of available egress queues 
      varies according to the value of the provisionable attribute 
      numberOfEmissionQs. Egress queue 0 has the lowest priority, while 
      egress queue 3 has the highest priority."
::= { mscFrAtm 342 }

mscFrAtmOctetToIfByQueueEntry OBJECT-TYPE
   SYNTAX     MscFrAtmOctetToIfByQueueEntry
   ACCESS     not-accessible
   STATUS     mandatory
   DESCRIPTION
     "An entry in the mscFrAtmOctetToIfByQueueTable."
   INDEX {
      mscFrAtmIndex,
      mscFrAtmOctetToIfByQueueIndex }
::= { mscFrAtmOctetToIfByQueueTable 1 }

MscFrAtmOctetToIfByQueueEntry ::= SEQUENCE {
   mscFrAtmOctetToIfByQueueIndex
      Integer32,
   mscFrAtmOctetToIfByQueueValue
      Unsigned32 }

mscFrAtmOctetToIfByQueueIndex OBJECT-TYPE
   SYNTAX     Integer32 (0..3)
   ACCESS     not-accessible
   STATUS     mandatory
   DESCRIPTION
     "This variable represents the index for the mscFrAtmOctetToIfByQueueTable."
::= { mscFrAtmOctetToIfByQueueEntry 1 }

mscFrAtmOctetToIfByQueueValue OBJECT-TYPE
   SYNTAX     Unsigned32 (0..4294967295)
   ACCESS     read-only
   STATUS     mandatory
   DESCRIPTION
     "This variable represents an individual value for the
      mscFrAtmOctetToIfByQueueTable."
::= { mscFrAtmOctetToIfByQueueEntry 2 }


-- FrUni/n Framer
-- FrNni/n Framer
-- FrAtm/n Framer
-- This component controls link layer framing for application 
-- components sending and receiving data on a link interface. It is also 
-- through Framer, that an application component is associated with a 
-- specific hardware link interface.
-- 
-- The Framer component provides provisionable attributes related to 
-- datapath aspects of the hardware interface (such as crc and frame 
-- length) rather than interface specific attributes (such as modem 
-- leads and clocking) which are associated with specific hardware 
-- components (such as V35/n or DS1/n). The Framer component also 
-- provides a provisionable attribute which binds the application 
-- component to a specific hardware component.
-- 
-- The Framer component contains operational attributes for link 
-- interface datapath statistics (such as frame counts and aborts).
-- 

mscFrAtmFramer OBJECT IDENTIFIER ::= { mscFrAtm 2 }



mscFrAtmFramerRowStatusTable OBJECT-TYPE
   SYNTAX     SEQUENCE OF MscFrAtmFramerRowStatusEntry
   ACCESS     not-accessible
   STATUS     mandatory
   DESCRIPTION
     "This entry controls the addition and deletion of 
      mscFrAtmFramer components."
::= { mscFrAtmFramer 1 }

mscFrAtmFramerRowStatusEntry OBJECT-TYPE
   SYNTAX     MscFrAtmFramerRowStatusEntry
   ACCESS     not-accessible
   STATUS     mandatory
   DESCRIPTION
     "A single entry in the table represents a single 
      mscFrAtmFramer component."
   INDEX {
      mscFrAtmIndex,
      mscFrAtmFramerIndex }
::= { mscFrAtmFramerRowStatusTable 1 }

MscFrAtmFramerRowStatusEntry ::= SEQUENCE {
   mscFrAtmFramerRowStatus
      RowStatus,
   mscFrAtmFramerComponentName
      DisplayString,
   mscFrAtmFramerStorageType
      StorageType,
   mscFrAtmFramerIndex
      NonReplicated }

mscFrAtmFramerRowStatus OBJECT-TYPE
   SYNTAX     RowStatus 
   ACCESS     read-write
   STATUS     mandatory
   DESCRIPTION
     "This variable is used as the basis for SNMP naming of
      mscFrAtmFramer components.
      These components can be added and deleted."
::= { mscFrAtmFramerRowStatusEntry 1 }

mscFrAtmFramerComponentName OBJECT-TYPE
   SYNTAX     DisplayString 
   ACCESS     read-only
   STATUS     mandatory
   DESCRIPTION
     "This variable provides the component's string name for
      use with the ASCII Console Interface"
::= { mscFrAtmFramerRowStatusEntry 2 }

mscFrAtmFramerStorageType OBJECT-TYPE
   SYNTAX     StorageType 
   ACCESS     read-only
   STATUS     mandatory
   DESCRIPTION
     "This variable represents the storage type value for the
      mscFrAtmFramer tables."
::= { mscFrAtmFramerRowStatusEntry 4 }

mscFrAtmFramerIndex OBJECT-TYPE
   SYNTAX     NonReplicated 
   ACCESS     not-accessible
   STATUS     mandatory
   DESCRIPTION
     "This variable represents the index for the mscFrAtmFramer tables."
::= { mscFrAtmFramerRowStatusEntry 10 }

mscFrAtmFramerProvTable OBJECT-TYPE
   SYNTAX     SEQUENCE OF MscFrAtmFramerProvEntry
   ACCESS     not-accessible
   STATUS     mandatory
   DESCRIPTION
     "This group contains the base provisioning data for the Framer 
      component. Application or hardware interface specific provisioning 
      data is contained in other provisionable Framer groups."
::= { mscFrAtmFramer 10 }

mscFrAtmFramerProvEntry OBJECT-TYPE
   SYNTAX     MscFrAtmFramerProvEntry
   ACCESS     not-accessible
   STATUS     mandatory
   DESCRIPTION
     "An entry in the mscFrAtmFramerProvTable."
   INDEX {
      mscFrAtmIndex,
      mscFrAtmFramerIndex }
::= { mscFrAtmFramerProvTable 1 }

MscFrAtmFramerProvEntry ::= SEQUENCE {
   mscFrAtmFramerInterfaceName
      Link }

mscFrAtmFramerInterfaceName OBJECT-TYPE
   SYNTAX     Link 
   ACCESS     read-write
   STATUS     mandatory
   DESCRIPTION
     "This attribute contains a hardware component name.
      
      The attribute associates the application with a specific link. This 
      defines the module processor on which Framer's parent component 
      (as well as Framer itself) will run."
::= { mscFrAtmFramerProvEntry 1 }

mscFrAtmFramerLinkTable OBJECT-TYPE
   SYNTAX     SEQUENCE OF MscFrAtmFramerLinkEntry
   ACCESS     not-accessible
   STATUS     mandatory
   DESCRIPTION
     "This group contains attributes defining the framing of data on the 
      link interface."
::= { mscFrAtmFramer 11 }

mscFrAtmFramerLinkEntry OBJECT-TYPE
   SYNTAX     MscFrAtmFramerLinkEntry
   ACCESS     not-accessible
   STATUS     mandatory
   DESCRIPTION
     "An entry in the mscFrAtmFramerLinkTable."
   INDEX {
      mscFrAtmIndex,
      mscFrAtmFramerIndex }
::= { mscFrAtmFramerLinkTable 1 }

MscFrAtmFramerLinkEntry ::= SEQUENCE {
   mscFrAtmFramerDataInversion
      INTEGER,
   mscFrAtmFramerFrameCrcType
      INTEGER,
   mscFrAtmFramerFlagsBetweenFrames
      Unsigned32 }

mscFrAtmFramerDataInversion OBJECT-TYPE
   SYNTAX     INTEGER  {
                 off(0),
                 on(16) }
   ACCESS     read-write
   STATUS     mandatory
   DESCRIPTION
     "This attribute determines whether data bits are to be inverted (1 to 0 
      and 0 to 1) before transmission of frames to the interface. If the 
      value of this attribute is On, the incoming data bits will also be 
      inverted when frames are received from the link before being 
      processed.
      
      This option is typically used in hdlc framing mode when inversion 
      is used to guarantee 1's density.
      
      Note that aborts (in hdlc and interrupting modes) are corrupted 
      when data is inverted.
      
      This attribute may only take its default value for non-MSA cards."
   DEFVAL     { off }
::= { mscFrAtmFramerLinkEntry 2 }

mscFrAtmFramerFrameCrcType OBJECT-TYPE
   SYNTAX     INTEGER  {
                 crc16(0),
                 crc32(1),
                 noCrc(2) }
   ACCESS     read-write
   STATUS     mandatory
   DESCRIPTION
     "This attribute defines the type of CRC used. 
      
      The CRC value calculated is appended to the end of the frames 
      transmitted to the link. The CRC value is removed from the end of 
      frames received from the link and checked for correctness.
      NoCrc means that CRC is not used.
      
      This attribute may take only its default value for non-MSA cards."
   DEFVAL     { crc16 }
::= { mscFrAtmFramerLinkEntry 3 }

mscFrAtmFramerFlagsBetweenFrames OBJECT-TYPE
   SYNTAX     Unsigned32 (1..16)
   ACCESS     read-write
   STATUS     mandatory
   DESCRIPTION
     "This attribute defines the number of flags that are inserted between 
      frames sent to the link interface."
   DEFVAL     { 1 }
::= { mscFrAtmFramerLinkEntry 4 }

mscFrAtmFramerStateTable OBJECT-TYPE
   SYNTAX     SEQUENCE OF MscFrAtmFramerStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscFrAtmFramer 12 }

mscFrAtmFramerStateEntry OBJECT-TYPE
   SYNTAX     MscFrAtmFramerStateEntry
   ACCESS     not-accessible
   STATUS     mandatory
   DESCRIPTION
     "An entry in the mscFrAtmFramerStateTable."
   INDEX {
      mscFrAtmIndex,
      mscFrAtmFramerIndex }
::= { mscFrAtmFramerStateTable 1 }

MscFrAtmFramerStateEntry ::= SEQUENCE {
   mscFrAtmFramerAdminState
      INTEGER,
   mscFrAtmFramerOperationalState
      INTEGER,
   mscFrAtmFramerUsageState
      INTEGER }

mscFrAtmFramerAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscFrAtmFramerStateEntry 1 }

mscFrAtmFramerOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscFrAtmFramerStateEntry 2 }

mscFrAtmFramerUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscFrAtmFramerStateEntry 3 }

mscFrAtmFramerStatsTable OBJECT-TYPE
   SYNTAX     SEQUENCE OF MscFrAtmFramerStatsEntry
   ACCESS     not-accessible
   STATUS     mandatory
   DESCRIPTION
     "This group contains the operational statistics data for a Framer 
      component."
::= { mscFrAtmFramer 13 }

mscFrAtmFramerStatsEntry OBJECT-TYPE
   SYNTAX     MscFrAtmFramerStatsEntry
   ACCESS     not-accessible
   STATUS     mandatory
   DESCRIPTION
     "An entry in the mscFrAtmFramerStatsTable."
   INDEX {
      mscFrAtmIndex,
      mscFrAtmFramerIndex }
::= { mscFrAtmFramerStatsTable 1 }

MscFrAtmFramerStatsEntry ::= SEQUENCE {
   mscFrAtmFramerFrmToIf
      Counter32,
   mscFrAtmFramerFrmFromIf
      Counter32,
   mscFrAtmFramerOctetFromIf
      Counter32,
   mscFrAtmFramerAborts
      Counter32,
   mscFrAtmFramerCrcErrors
      Counter32,
   mscFrAtmFramerLrcErrors
      Counter32,
   mscFrAtmFramerNonOctetErrors
      Counter32,
   mscFrAtmFramerOverruns
      Counter32,
   mscFrAtmFramerUnderruns
      Counter32,
   mscFrAtmFramerLargeFrmErrors
      Counter32,
   mscFrAtmFramerFrmModeErrors
      Counter32,
   mscFrAtmFramerFrmToIf64
      PassportCounter64,
   mscFrAtmFramerFrmFromIf64
      PassportCounter64,
   mscFrAtmFramerOctetFromIf64
      PassportCounter64 }

mscFrAtmFramerFrmToIf OBJECT-TYPE
   SYNTAX     Counter32 
   ACCESS     read-only
   STATUS     obsolete
   DESCRIPTION
     "The number of frames transmitted to the link interface by Framer.
      
      Note: This does not include the number of frames transmitted 
      directly to the hardware queue, thus bypassing the Framer 
      component."
::= { mscFrAtmFramerStatsEntry 1 }

mscFrAtmFramerFrmFromIf OBJECT-TYPE
   SYNTAX     Counter32 
   ACCESS     read-only
   STATUS     obsolete
   DESCRIPTION
     "The number of frames received from the link interface by Framer."
::= { mscFrAtmFramerStatsEntry 2 }

mscFrAtmFramerOctetFromIf OBJECT-TYPE
   SYNTAX     Counter32 
   ACCESS     read-only
   STATUS     obsolete
   DESCRIPTION
     "The number of bytes received from the link interface by Framer."
::= { mscFrAtmFramerStatsEntry 3 }

mscFrAtmFramerAborts OBJECT-TYPE
   SYNTAX     Counter32 
   ACCESS     read-only
   STATUS     mandatory
   DESCRIPTION
     "This attribute is the total number of aborts received."
::= { mscFrAtmFramerStatsEntry 4 }

mscFrAtmFramerCrcErrors OBJECT-TYPE
   SYNTAX     Counter32 
   ACCESS     read-only
   STATUS     mandatory
   DESCRIPTION
     "This attribute is the total number of frames with CRC errors, 
      occurring in the receive direction from the link."
::= { mscFrAtmFramerStatsEntry 5 }

mscFrAtmFramerLrcErrors OBJECT-TYPE
   SYNTAX     Counter32 
   ACCESS     read-only
   STATUS     mandatory
   DESCRIPTION
     "This attribute is the total number of frames with LRC errors, 
      occurring in the Tx link prior to transmission onto the link."
::= { mscFrAtmFramerStatsEntry 6 }

mscFrAtmFramerNonOctetErrors OBJECT-TYPE
   SYNTAX     Counter32 
   ACCESS     read-only
   STATUS     mandatory
   DESCRIPTION
     "This attribute is the total number of frames that were non octet 
      aligned."
::= { mscFrAtmFramerStatsEntry 7 }

mscFrAtmFramerOverruns OBJECT-TYPE
   SYNTAX     Counter32 
   ACCESS     read-only
   STATUS     mandatory
   DESCRIPTION
     "This attribute is the total number of frames received from the link 
      for which overruns occurred."
::= { mscFrAtmFramerStatsEntry 8 }

mscFrAtmFramerUnderruns OBJECT-TYPE
   SYNTAX     Counter32 
   ACCESS     read-only
   STATUS     mandatory
   DESCRIPTION
     "This attribute is the total number of frames transmitted to the link 
      for which underruns occurred."
::= { mscFrAtmFramerStatsEntry 9 }

mscFrAtmFramerLargeFrmErrors OBJECT-TYPE
   SYNTAX     Counter32 
   ACCESS     read-only
   STATUS     mandatory
   DESCRIPTION
     "This attribute is the total number of frames received which were too 
      large. The frame execeeded the maximumFrameLengthLimit 
      provisioned attribute or it contained more than the 255 block 
      hardware limit."
::= { mscFrAtmFramerStatsEntry 10 }

mscFrAtmFramerFrmModeErrors OBJECT-TYPE
   SYNTAX     Counter32 
   ACCESS     read-only
   STATUS     mandatory
   DESCRIPTION
     "This attribute is the total number of frames detected with framing 
      mode errors. A framingModeError is flagged when frames are 
      inconsistent with the specified framingType, that is when 
      interrupting frames are used while running in hdlc mode."
::= { mscFrAtmFramerStatsEntry 11 }

mscFrAtmFramerFrmToIf64 OBJECT-TYPE
   SYNTAX     PassportCounter64 
   ACCESS     read-only
   STATUS     mandatory
   DESCRIPTION
     "The number of frames transmitted to the link interface by Framer.
      
      Note: This does not include the number of frames transmitted 
      directly to the hardware queue, thus bypassing the Framer 
      component."
::= { mscFrAtmFramerStatsEntry 14 }

mscFrAtmFramerFrmFromIf64 OBJECT-TYPE
   SYNTAX     PassportCounter64 
   ACCESS     read-only
   STATUS     mandatory
   DESCRIPTION
     "The number of frames received from the link interface by Framer."
::= { mscFrAtmFramerStatsEntry 15 }

mscFrAtmFramerOctetFromIf64 OBJECT-TYPE
   SYNTAX     PassportCounter64 
   ACCESS     read-only
   STATUS     mandatory
   DESCRIPTION
     "The number of bytes received from the link interface by Framer."
::= { mscFrAtmFramerStatsEntry 16 }

mscFrAtmFramerUtilTable OBJECT-TYPE
   SYNTAX     SEQUENCE OF MscFrAtmFramerUtilEntry
   ACCESS     not-accessible
   STATUS     mandatory
   DESCRIPTION
     "This group contains the link utilizaiton operational data for a 
      Framer component."
::= { mscFrAtmFramer 14 }

mscFrAtmFramerUtilEntry OBJECT-TYPE
   SYNTAX     MscFrAtmFramerUtilEntry
   ACCESS     not-accessible
   STATUS     mandatory
   DESCRIPTION
     "An entry in the mscFrAtmFramerUtilTable."
   INDEX {
      mscFrAtmIndex,
      mscFrAtmFramerIndex }
::= { mscFrAtmFramerUtilTable 1 }

MscFrAtmFramerUtilEntry ::= SEQUENCE {
   mscFrAtmFramerNormPrioLinkUtilToIf
      Gauge32,
   mscFrAtmFramerNormPrioLinkUtilFromIf
      Gauge32 }

mscFrAtmFramerNormPrioLinkUtilToIf OBJECT-TYPE
   SYNTAX     Gauge32 (0..100)
   ACCESS     read-only
   STATUS     mandatory
   DESCRIPTION
     "This attribute is the utilization of the normal and high priority data 
      traffic (interruptable traffic) sent to the link as a percentage of the 
      available bandwidth on the link. Note that this indluces traffic with 
      Transfer Priorities (TP) of 0, 6 and 9 and/or Emission Priority of 2 
      and 3. The utilization is the average for the last minute."
   DEFVAL     { 0 }
::= { mscFrAtmFramerUtilEntry 1 }

mscFrAtmFramerNormPrioLinkUtilFromIf OBJECT-TYPE
   SYNTAX     Gauge32 (0..100)
   ACCESS     read-only
   STATUS     mandatory
   DESCRIPTION
     "This attribute is the utilization of the normal and high priority data 
      traffic (interruptable traffic) received from the link as a percentage 
      of the available bandwidth on the link. Note that this includes traffic 
      with Transfer Priorities (TP) of 0, 6 and 9 and/or Emission Priority 
      of 2 and 3. The utilization is the average for the last minute."
   DEFVAL     { 0 }
::= { mscFrAtmFramerUtilEntry 3 }


-- FrUni/n LocalManagementInterface
-- FrNni/n LocalManagementInterface
-- FrAtm/n LocalManagementInterface
-- This component defines the parameters for implementing the Local 
-- Management Interface protocol.

mscFrAtmLmi OBJECT IDENTIFIER ::= { mscFrAtm 3 }



mscFrAtmLmiRowStatusTable OBJECT-TYPE
   SYNTAX     SEQUENCE OF MscFrAtmLmiRowStatusEntry
   ACCESS     not-accessible
   STATUS     mandatory
   DESCRIPTION
     "This entry controls the addition and deletion of 
      mscFrAtmLmi components."
::= { mscFrAtmLmi 1 }

mscFrAtmLmiRowStatusEntry OBJECT-TYPE
   SYNTAX     MscFrAtmLmiRowStatusEntry
   ACCESS     not-accessible
   STATUS     mandatory
   DESCRIPTION
     "A single entry in the table represents a single 
      mscFrAtmLmi component."
   INDEX {
      mscFrAtmIndex,
      mscFrAtmLmiIndex }
::= { mscFrAtmLmiRowStatusTable 1 }

MscFrAtmLmiRowStatusEntry ::= SEQUENCE {
   mscFrAtmLmiRowStatus
      RowStatus,
   mscFrAtmLmiComponentName
      DisplayString,
   mscFrAtmLmiStorageType
      StorageType,
   mscFrAtmLmiIndex
      NonReplicated }

mscFrAtmLmiRowStatus OBJECT-TYPE
   SYNTAX     RowStatus 
   ACCESS     read-only
   STATUS     mandatory
   DESCRIPTION
     "This variable is used as the basis for SNMP naming of
      mscFrAtmLmi components.
      These components cannot be added nor deleted."
::= { mscFrAtmLmiRowStatusEntry 1 }

mscFrAtmLmiComponentName OBJECT-TYPE
   SYNTAX     DisplayString 
   ACCESS     read-only
   STATUS     mandatory
   DESCRIPTION
     "This variable provides the component's string name for
      use with the ASCII Console Interface"
::= { mscFrAtmLmiRowStatusEntry 2 }

mscFrAtmLmiStorageType OBJECT-TYPE
   SYNTAX     StorageType 
   ACCESS     read-only
   STATUS     mandatory
   DESCRIPTION
     "This variable represents the storage type value for the
      mscFrAtmLmi tables."
::= { mscFrAtmLmiRowStatusEntry 4 }

mscFrAtmLmiIndex OBJECT-TYPE
   SYNTAX     NonReplicated 
   ACCESS     not-accessible
   STATUS     mandatory
   DESCRIPTION
     "This variable represents the index for the mscFrAtmLmi tables."
::= { mscFrAtmLmiRowStatusEntry 10 }

mscFrAtmLmiParmsTable OBJECT-TYPE
   SYNTAX     SEQUENCE OF MscFrAtmLmiParmsEntry
   ACCESS     not-accessible
   STATUS     mandatory
   DESCRIPTION
     "This group contains the provisionable attributes of the LMI 
      component."
::= { mscFrAtmLmi 10 }

mscFrAtmLmiParmsEntry OBJECT-TYPE
   SYNTAX     MscFrAtmLmiParmsEntry
   ACCESS     not-accessible
   STATUS     mandatory
   DESCRIPTION
     "An entry in the mscFrAtmLmiParmsTable."
   INDEX {
      mscFrAtmIndex,
      mscFrAtmLmiIndex }
::= { mscFrAtmLmiParmsTable 1 }

MscFrAtmLmiParmsEntry ::= SEQUENCE {
   mscFrAtmLmiProcedures
      INTEGER,
   mscFrAtmLmiAsyncStatusReport
      INTEGER,
   mscFrAtmLmiErrorEventThreshold
      Unsigned32,
   mscFrAtmLmiEventCount
      Unsigned32,
   mscFrAtmLmiCheckPointTimer
      Unsigned32,
   mscFrAtmLmiMessageCountTimer
      Unsigned32,
   mscFrAtmLmiIgnoreActiveBit
      INTEGER,
   mscFrAtmLmiSide
      INTEGER,
   mscFrAtmLmiPvcConfigParmsInFsr
      INTEGER }

mscFrAtmLmiProcedures OBJECT-TYPE
   SYNTAX     INTEGER  {
                 none(0),
                 vendorForum(1),
                 ansi(2),
                 itu(3),
                 autoConfigure(4) }
   ACCESS     read-write
   STATUS     mandatory
   DESCRIPTION
     "This attribute selects the procedures to be used for the Local 
      Management Interface. The following procedures are supported:
      
      none: no Local Management Interface procedures are running on 
      this interface. This accommodates Frame Relay user equipment that 
      has not implemented any LMI procedures. The remaining attributes 
      of this group are ignored.
      
      vendorForum: Local Management Interface procedures from the 
      Vendor Forum specification are supported on this interface. DLCI 
      1023 is used for the LMI protocol. This value cannot be used if the 
      side attribute is both.
      
      ansi: Local Management Interface procedures from the ANSI 
      specification are supported. DLCI 0 is used for the LMI protocol.
      
      itu: Local Management Interface procedures from the ITU-T 
      specification are supported. DLCI 0 is used for the LMI protocol. 
      Was previously ccitt.
      
      autoConfigure: The interface determines automatically which 
      Local Management Interface procedures to use. This value cannot 
      be used if the side attribute is user.
      
      The procedures currently in use can be seen in the operational 
      attribute opProcedures."
   DEFVAL     { autoConfigure }
::= { mscFrAtmLmiParmsEntry 1 }

mscFrAtmLmiAsyncStatusReport OBJECT-TYPE
   SYNTAX     INTEGER  {
                 off(0),
                 on(1) }
   ACCESS     read-write
   STATUS     mandatory
   DESCRIPTION
     "This attribute selects the use of asynchronous PVC status report 
      procedures as specified in ANSI, CCITT, and Vendor Forum. 
      
      This attribute can be set to on or off. If procedures is set to none, 
      this attribute is ignored."
   DEFVAL     { off }
::= { mscFrAtmLmiParmsEntry 2 }

mscFrAtmLmiErrorEventThreshold OBJECT-TYPE
   SYNTAX     Unsigned32 (1..10)
   ACCESS     read-write
   STATUS     mandatory
   DESCRIPTION
     "An event is defined as follows: (1) receipt of a STATUS ENQUIRY 
      message; or (2) expiration of timer T392. An error event is (1) 
      nonreceipt of STATUS ENQUIRY in T392 seconds; (2) invalid 
      contents of a LMI message; (3) invalid receive sequence number. 
      This attribute specifies the number of error events which, if they 
      occur within eventCount events, cause a protocol error condition. 
      The condition is cleared after eventCount sequential correct events 
      occur. This attribute corresponds to the nN2 parameter described in 
      the Vendor Forum Specification. 
      
      It must be less than or equal to eventCount."
   DEFVAL     { 3 }
::= { mscFrAtmLmiParmsEntry 3 }

mscFrAtmLmiEventCount OBJECT-TYPE
   SYNTAX     Unsigned32 (1..10)
   ACCESS     read-write
   STATUS     mandatory
   DESCRIPTION
     "This attribute specifies the number of contiguous events within 
      which no more than eventErrorThreshold error events are allowed. 
      This attribute corresponds to the nN3 parameter described in the 
      Vendor Forum Specification. 
      
      It must be greater than or equal to errorEventThreshold."
   DEFVAL     { 4 }
::= { mscFrAtmLmiParmsEntry 4 }

mscFrAtmLmiCheckPointTimer OBJECT-TYPE
   SYNTAX     Unsigned32 (5 | 10 | 15 | 20 | 25 | 30)
   ACCESS     read-write
   STATUS     mandatory
   DESCRIPTION
     "This attribute selects the time (in seconds) within which a STATUS 
      ENQUIRY message is expected. This attribute corresponds to the 
      nT2 parameter described in the Vendor Forum Specification.
      
      It must be less than messageCountTimer."
   DEFVAL     { 15 }
::= { mscFrAtmLmiParmsEntry 5 }

mscFrAtmLmiMessageCountTimer OBJECT-TYPE
   SYNTAX     Unsigned32 (5 | 10 | 15 | 20 | 25 | 30)
   ACCESS     read-write
   STATUS     mandatory
   DESCRIPTION
     "This attribute selects the time (in seconds) within which at most five 
      (this is a fixed value and corresponds to maximum message count in 
      VendorForum) STATUS ENQUIRY messages are expected. This 
      attribute applies only when the lmiProcedures is set to 
      vendorForum.
      
      messageCountTimer must always be greater than checkPointTimer."
   DEFVAL     { 20 }
::= { mscFrAtmLmiParmsEntry 6 }

mscFrAtmLmiIgnoreActiveBit OBJECT-TYPE
   SYNTAX     INTEGER  {
                 no(0),
                 yes(1) }
   ACCESS     read-write
   STATUS     mandatory
   DESCRIPTION
     "This attribute specifies whether the Frame Relay LMI Active Bit 
      (A-bit) has a bearing on the transfer of user data across this Frame 
      Relay interface for both directions of traffic flow.
      
      When this attribute is set to yes, the A-bit status of a user DLCI 
      connection does not affect data transfer.
      
      When this attribute is set to no, data received from the local 
      interface will be discarded if an A-bit =0 condition exists towards 
      the local user. Data being sent to the local interface is discarded if 
      an A-bit = 0 condition exists towards the subnet."
   DEFVAL     { no }
::= { mscFrAtmLmiParmsEntry 7 }

mscFrAtmLmiSide OBJECT-TYPE
   SYNTAX     INTEGER  {
                 network(0),
                 user(1),
                 both(2) }
   ACCESS     read-write
   STATUS     mandatory
   DESCRIPTION
     "This attribute can be set to user, network, or both. 
      
      When this attribute is set to user, USP LMI procedures are running. 
      When this attribute is set to network, NSP LMI procedures are 
      running. When this attribute is set to both, USPNSP LMI 
      procedures are running.
      When the value is both, the procedures attribute must not be set to 
      vendorForum. 
      Setting the value to user when the procedures attribute is set to 
      autoConfigure is disallowed semantically."
   DEFVAL     { network }
::= { mscFrAtmLmiParmsEntry 8 }

mscFrAtmLmiPvcConfigParmsInFsr OBJECT-TYPE
   SYNTAX     INTEGER  {
                 no(0),
                 yes(1) }
   ACCESS     read-write
   STATUS     mandatory
   DESCRIPTION
     "When this attribute is set to yes, additional Q.933 information 
      elements are included in the LMI Full Status message to facilitate 
      CPE PVC parameter configuring.
      
      When set to yes, the Check Prov command fails if the Lmi side is 
      not set to network.
      
      When set to yes, Check Prov fails if the number of DLCIs on the 
      FrUni is greater than 300.
      
      If the service is not a FrUni this attribute is ignored."
   DEFVAL     { no }
::= { mscFrAtmLmiParmsEntry 9 }

mscFrAtmLmiStateTable OBJECT-TYPE
   SYNTAX     SEQUENCE OF MscFrAtmLmiStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscFrAtmLmi 11 }

mscFrAtmLmiStateEntry OBJECT-TYPE
   SYNTAX     MscFrAtmLmiStateEntry
   ACCESS     not-accessible
   STATUS     mandatory
   DESCRIPTION
     "An entry in the mscFrAtmLmiStateTable."
   INDEX {
      mscFrAtmIndex,
      mscFrAtmLmiIndex }
::= { mscFrAtmLmiStateTable 1 }

MscFrAtmLmiStateEntry ::= SEQUENCE {
   mscFrAtmLmiAdminState
      INTEGER,
   mscFrAtmLmiOperationalState
      INTEGER,
   mscFrAtmLmiUsageState
      INTEGER }

mscFrAtmLmiAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscFrAtmLmiStateEntry 1 }

mscFrAtmLmiOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscFrAtmLmiStateEntry 2 }

mscFrAtmLmiUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscFrAtmLmiStateEntry 3 }

mscFrAtmLmiPsiTable OBJECT-TYPE
   SYNTAX     SEQUENCE OF MscFrAtmLmiPsiEntry
   ACCESS     not-accessible
   STATUS     mandatory
   DESCRIPTION
     "This group provides the protocol status of the Local Management 
      Interface."
::= { mscFrAtmLmi 12 }

mscFrAtmLmiPsiEntry OBJECT-TYPE
   SYNTAX     MscFrAtmLmiPsiEntry
   ACCESS     not-accessible
   STATUS     mandatory
   DESCRIPTION
     "An entry in the mscFrAtmLmiPsiTable."
   INDEX {
      mscFrAtmIndex,
      mscFrAtmLmiIndex }
::= { mscFrAtmLmiPsiTable 1 }

MscFrAtmLmiPsiEntry ::= SEQUENCE {
   mscFrAtmLmiProtocolStatus
      INTEGER,
   mscFrAtmLmiOpProcedures
      INTEGER }

mscFrAtmLmiProtocolStatus OBJECT-TYPE
   SYNTAX     INTEGER  {
                 errorCondition(0),
                 normalCondition(1),
                 configuring(2) }
   ACCESS     read-only
   STATUS     mandatory
   DESCRIPTION
     "This attribute indicates whether the LMI is in an error condition or 
      whether the LMI procedures are behaving normally. When 
      operating with no LMI protocol, this attribute is always set to 
      normalCondition. When operating with LMI procedures, this 
      attribute is set to errorCondition after n392 of the last n393 events 
      are in error. The consequence of an errorCondition is that all 
      DLCIs on this interface will become inactive in both directions. The 
      errorCondition is cleared and a normalCondition is indicated when 
      a sufficient number of events have occurred without error. In ANSI, 
      this occurs when n393 consecutive good events take place.
      
      If the procedures attribute is set to autoConfigure, this attribute is 
      set to configuring while adaptive LMI determines which LMI 
      procedures are running on the link. A single LMI error event during 
      auto configuration causes the attribute value to change to 
      errorCondition. If during configuring no LMI message is received, 
      an LMI errorCondition is raised after n392 x t392 seconds."
::= { mscFrAtmLmiPsiEntry 1 }

mscFrAtmLmiOpProcedures OBJECT-TYPE
   SYNTAX     INTEGER  {
                 none(0),
                 vendorForum(1),
                 ansi(2),
                 itu(3),
                 unknown(4) }
   ACCESS     read-only
   STATUS     mandatory
   DESCRIPTION
     "The opProcedures attribute indicates the procedures being used for 
      the Local Management Interface. This attribute should be ignored if 
      protocolStatus is not normalCondition. The following procedures 
      are supported:
      
      none: Local Management Interface procedures are not running on 
      this interface. This accommodates Frame Relay user equipment that 
      has not implemented any LMI procedures.
      
      vendorForum: Local Management Interface procedures from the 
      Vendor Forum specification are running on this interface. DLCI 
      1023 is used for the LMI protocol.
      
      ansi: Local Management Interface procedures from the ANSI 
      specification are running. DLCI 0 is used for the LMI protocol.
      
      itu: Local Management Interface procedures from the ITU-T 
      specification are running. DLCI 0 is used for the LMI protocol. Was 
      previously ccitt.
      
      unknown: Local Management Interface procedures have yet to be 
      determined by Adaptive LMI."
::= { mscFrAtmLmiPsiEntry 2 }

mscFrAtmLmiStatsTable OBJECT-TYPE
   SYNTAX     SEQUENCE OF MscFrAtmLmiStatsEntry
   ACCESS     not-accessible
   STATUS     mandatory
   DESCRIPTION
     "This group contains the operational statistics for the Frame Relay 
      Local Management Interface."
::= { mscFrAtmLmi 13 }

mscFrAtmLmiStatsEntry OBJECT-TYPE
   SYNTAX     MscFrAtmLmiStatsEntry
   ACCESS     not-accessible
   STATUS     mandatory
   DESCRIPTION
     "An entry in the mscFrAtmLmiStatsTable."
   INDEX {
      mscFrAtmIndex,
      mscFrAtmLmiIndex }
::= { mscFrAtmLmiStatsTable 1 }

MscFrAtmLmiStatsEntry ::= SEQUENCE {
   mscFrAtmLmiKeepAliveStatusToIf
      Counter32,
   mscFrAtmLmiFullStatusToIf
      Counter32,
   mscFrAtmLmiKeepAliveStatusEnqFromIf
      Counter32,
   mscFrAtmLmiFullStatusEnqFromIf
      Counter32,
   mscFrAtmLmiNetworkSideEventHistory
      AsciiString,
   mscFrAtmLmiProtocolErrors
      Counter32,
   mscFrAtmLmiUnexpectedIes
      Counter32,
   mscFrAtmLmiSequenceErrors
      Counter32,
   mscFrAtmLmiUnexpectedReports
      Counter32,
   mscFrAtmLmiPollingVerifTimeouts
      Counter32,
   mscFrAtmLmiKeepAliveEnqToIf
      Counter32,
   mscFrAtmLmiFullStatusEnqToIf
      Counter32,
   mscFrAtmLmiUserSideEventHistory
      AsciiString,
   mscFrAtmLmiStatusSequenceErrors
      Counter32,
   mscFrAtmLmiNoStatusReportCount
      Counter32 }

mscFrAtmLmiKeepAliveStatusToIf OBJECT-TYPE
   SYNTAX     Counter32 
   ACCESS     read-only
   STATUS     mandatory
   DESCRIPTION
     "This attribute counts the number of Local Management Interface 
      keep alive status messages sent to the external user device in 
      response to a status enquiry for keep alive status. When the 
      maximum count is exceeded it wraps to zero."
::= { mscFrAtmLmiStatsEntry 1 }

mscFrAtmLmiFullStatusToIf OBJECT-TYPE
   SYNTAX     Counter32 
   ACCESS     read-only
   STATUS     mandatory
   DESCRIPTION
     "This attribute counts the number of Local Management Interface 
      full status messages sent to the external user device in response to a 
      status enquiry for keep alive or full status. When the maximum 
      count is reached it wraps to zero."
::= { mscFrAtmLmiStatsEntry 2 }

mscFrAtmLmiKeepAliveStatusEnqFromIf OBJECT-TYPE
   SYNTAX     Counter32 
   ACCESS     read-only
   STATUS     mandatory
   DESCRIPTION
     "This attribute counts the number of Local Management Interface 
      valid keep alive status enquiry messages received from the external 
      user device. When the maximum count is reached it wraps to zero."
::= { mscFrAtmLmiStatsEntry 3 }

mscFrAtmLmiFullStatusEnqFromIf OBJECT-TYPE
   SYNTAX     Counter32 
   ACCESS     read-only
   STATUS     mandatory
   DESCRIPTION
     "This attribute counts the number of Local Management Interface 
      valid full status enquiry messages received from the external user 
      device. When the maximum count is reached it wraps to zero."
::= { mscFrAtmLmiStatsEntry 4 }

mscFrAtmLmiNetworkSideEventHistory OBJECT-TYPE
   SYNTAX     AsciiString (SIZE (1..10))
   ACCESS     read-only
   STATUS     mandatory
   DESCRIPTION
     "This attribute displays the Local Management Interface network 
      side procedure event history in order of occurrence. An event is 
      represented by a single symbol. A '+' symbol indicates a good 
      event. An 'X' symbol indicates a protocol error event. The leftmost 
      event is the most recent to occur. The provisioned eventCount (nN3/
      N393) dictates the maximum number of events displayed. A good 
      event is triggered by receipt of a valid status enquiry message. An 
      error event is one of three possibilities, either a nT2/T392 timer 
      expiry, receipt of a status enquiry message with bad sequence 
      numbers, or when lmiProcedures is provisioned to vendorForum 
      and we receive more than nN4 status enquiry messages within the 
      provisioned messageCountTimer (nT3)."
::= { mscFrAtmLmiStatsEntry 5 }

mscFrAtmLmiProtocolErrors OBJECT-TYPE
   SYNTAX     Counter32 
   ACCESS     read-only
   STATUS     mandatory
   DESCRIPTION
     "This attribute counts the number of Local Management Interface 
      protocol errors. It is the sum of the sequence (sequenceErrors), 
      timeout (pollingVerifTimeouts) and too many status enquiry 
      messages received within the messageCountTimer (nT3) errors. The 
      too many status enquiries error only applies when lmiProcedures is 
      set to vendorForum. When the maximum count is exceeded it 
      wraps to zero."
::= { mscFrAtmLmiStatsEntry 6 }

mscFrAtmLmiUnexpectedIes OBJECT-TYPE
   SYNTAX     Counter32 
   ACCESS     read-only
   STATUS     mandatory
   DESCRIPTION
     "This attribute counts the number of Local Management Interface 
      frames received with an Information Element identifier that is 
      unknown or unexpected. An unexpected Information Element is not 
      a protocol error. When the maximum count is reached, this counter 
      wraps to zero."
::= { mscFrAtmLmiStatsEntry 7 }

mscFrAtmLmiSequenceErrors OBJECT-TYPE
   SYNTAX     Counter32 
   ACCESS     read-only
   STATUS     mandatory
   DESCRIPTION
     "This attribute counts the number of Local Management Interface 
      Status Enquiry message sequence errors. A sequence error is receipt 
      of a Status Enquiry message with a receive sequence number not 
      equal to the last send sequence number. When the maximum count 
      is reached the counter wraps to zero."
::= { mscFrAtmLmiStatsEntry 8 }

mscFrAtmLmiUnexpectedReports OBJECT-TYPE
   SYNTAX     Counter32 
   ACCESS     read-only
   STATUS     mandatory
   DESCRIPTION
     "This attribute counts the number of Local Management Interface 
      frames received with an unknown or unexpected report type. An 
      unexpected report type is not a protocol error. When the maximum 
      count is reached the counter wraps to zero."
::= { mscFrAtmLmiStatsEntry 9 }

mscFrAtmLmiPollingVerifTimeouts OBJECT-TYPE
   SYNTAX     Counter32 
   ACCESS     read-only
   STATUS     mandatory
   DESCRIPTION
     "This attribute counts the number of checkPointTImer (t392) timer 
      expiries occurring on the Local Management Interface. When the 
      maximum count is reached the counter wraps to zero."
::= { mscFrAtmLmiStatsEntry 10 }

mscFrAtmLmiKeepAliveEnqToIf OBJECT-TYPE
   SYNTAX     Counter32 
   ACCESS     read-only
   STATUS     mandatory
   DESCRIPTION
     "This attribute counts the number of Local Management Interface 
      keep alive enquiry status messages sent to the external user device 
      for keep alive status. When the maximum count is reached it wraps 
      to zero."
::= { mscFrAtmLmiStatsEntry 11 }

mscFrAtmLmiFullStatusEnqToIf OBJECT-TYPE
   SYNTAX     Counter32 
   ACCESS     read-only
   STATUS     mandatory
   DESCRIPTION
     "This attribute counts the number of Local Management Interface 
      full status messages sent to the external user device in response to a 
      status enquiry for keep alive or full status. When the maximum 
      count is reached it wraps to zero."
::= { mscFrAtmLmiStatsEntry 12 }

mscFrAtmLmiUserSideEventHistory OBJECT-TYPE
   SYNTAX     AsciiString (SIZE (1..10))
   ACCESS     read-only
   STATUS     mandatory
   DESCRIPTION
     "This attribute displays the Local Management Interface user side 
      procedure event history in order of occurrence. An event is 
      represented by a single symbol. A '+' symbol indicates a good 
      event. An 'X' symbol indicates a protocol error event. The left most 
      event is the most recent to occur. The provisioned eventCount (nN3/
      N393) dictates the maximum number of events displayed. A good 
      event is triggered by receipt of a valid status message. An error 
      event is either a nT1/T391 timer expiry or receipt of a status 
      message with bad sequence numbers."
::= { mscFrAtmLmiStatsEntry 13 }

mscFrAtmLmiStatusSequenceErrors OBJECT-TYPE
   SYNTAX     Counter32 
   ACCESS     read-only
   STATUS     mandatory
   DESCRIPTION
     "This attribute counts the number of Local Management Interface 
      Status message sequence errors. A sequence error is receipt of a 
      Status message with a receive sequence number not equal to the last 
      send sequence number. When the maximum count is reached the 
      counter wraps to zero."
::= { mscFrAtmLmiStatsEntry 14 }

mscFrAtmLmiNoStatusReportCount OBJECT-TYPE
   SYNTAX     Counter32 
   ACCESS     read-only
   STATUS     mandatory
   DESCRIPTION
     "This attribute counts the number of times when no status report or 
      an invalid status report comes from the external network. This 
      attribute is incremented in two cases: 
      i) after a status enquiry is sent out and T391 timer expires without 
      having a status report received.
      ii) an invalid status report is received.
      
      When the maximum count is reached it wraps to zero."
::= { mscFrAtmLmiStatsEntry 15 }

mscFrAtmLmiUspParmsTable OBJECT-TYPE
   SYNTAX     SEQUENCE OF MscFrAtmLmiUspParmsEntry
   ACCESS     not-accessible
   STATUS     mandatory
   DESCRIPTION
     "This group contains the provisionable attributes of the Local 
      Management Interface user side procedure."
::= { mscFrAtmLmi 14 }

mscFrAtmLmiUspParmsEntry OBJECT-TYPE
   SYNTAX     MscFrAtmLmiUspParmsEntry
   ACCESS     not-accessible
   STATUS     mandatory
   DESCRIPTION
     "An entry in the mscFrAtmLmiUspParmsTable."
   INDEX {
      mscFrAtmIndex,
      mscFrAtmLmiIndex }
::= { mscFrAtmLmiUspParmsTable 1 }

MscFrAtmLmiUspParmsEntry ::= SEQUENCE {
   mscFrAtmLmiFullStatusPollingCycles
      Unsigned32,
   mscFrAtmLmiLinkVerificationTimer
      Unsigned32 }

mscFrAtmLmiFullStatusPollingCycles OBJECT-TYPE
   SYNTAX     Unsigned32 (1..255)
   ACCESS     read-write
   STATUS     mandatory
   DESCRIPTION
     "This attribute specifies how frequently the Frame Relay UNI service 
      should initiate a Status Enquiry for a full PVC status report. A 
      polling cycle is a Status Enquiry and Status Report exchange. 
      
      This attribute is used only if the side attribute is either user or both."
   DEFVAL     { 6 }
::= { mscFrAtmLmiUspParmsEntry 1 }

mscFrAtmLmiLinkVerificationTimer OBJECT-TYPE
   SYNTAX     Unsigned32 (5 | 10 | 15 | 20 | 25 | 30)
   ACCESS     read-write
   STATUS     mandatory
   DESCRIPTION
     "This attribute specifies how frequently the Frame Relay UNI service 
      should initiate a Status Enquiry for link integrity verification. It 
      must be less than checkPointTimer (t392).
      
      When the Lmi side is network, this attribute is ignored."
   DEFVAL     { 10 }
::= { mscFrAtmLmiUspParmsEntry 2 }


-- FrAtm/n DataLinkConnectionIdentifier/n
-- This component represents a data link connection. The instance 
-- value defines the DLCI value for this connection. For example, 
-- Dlci/30 defines a logical connection with a DLCI of 30. 
-- 
-- The Dlci component is a subcomponent of FrAtm, and is 
-- responsible for the Frame Relay U-plane (User-plane) protocol for 
-- the specified data link connection.

mscFrAtmDlci OBJECT IDENTIFIER ::= { mscFrAtm 4 }



mscFrAtmDlciRowStatusTable OBJECT-TYPE
   SYNTAX     SEQUENCE OF MscFrAtmDlciRowStatusEntry
   ACCESS     not-accessible
   STATUS     mandatory
   DESCRIPTION
     "This entry controls the addition and deletion of 
      mscFrAtmDlci components."
::= { mscFrAtmDlci 1 }

mscFrAtmDlciRowStatusEntry OBJECT-TYPE
   SYNTAX     MscFrAtmDlciRowStatusEntry
   ACCESS     not-accessible
   STATUS     mandatory
   DESCRIPTION
     "A single entry in the table represents a single 
      mscFrAtmDlci component."
   INDEX {
      mscFrAtmIndex,
      mscFrAtmDlciIndex }
::= { mscFrAtmDlciRowStatusTable 1 }

MscFrAtmDlciRowStatusEntry ::= SEQUENCE {
   mscFrAtmDlciRowStatus
      RowStatus,
   mscFrAtmDlciComponentName
      DisplayString,
   mscFrAtmDlciStorageType
      StorageType,
   mscFrAtmDlciIndex
      Integer32 }

mscFrAtmDlciRowStatus OBJECT-TYPE
   SYNTAX     RowStatus 
   ACCESS     read-write
   STATUS     mandatory
   DESCRIPTION
     "This variable is used as the basis for SNMP naming of
      mscFrAtmDlci components.
      These components can be added and deleted."
::= { mscFrAtmDlciRowStatusEntry 1 }

mscFrAtmDlciComponentName OBJECT-TYPE
   SYNTAX     DisplayString 
   ACCESS     read-only
   STATUS     mandatory
   DESCRIPTION
     "This variable provides the component's string name for
      use with the ASCII Console Interface"
::= { mscFrAtmDlciRowStatusEntry 2 }

mscFrAtmDlciStorageType OBJECT-TYPE
   SYNTAX     StorageType 
   ACCESS     read-only
   STATUS     mandatory
   DESCRIPTION
     "This variable represents the storage type value for the
      mscFrAtmDlci tables."
::= { mscFrAtmDlciRowStatusEntry 4 }

mscFrAtmDlciIndex OBJECT-TYPE
   SYNTAX     Integer32 (16..1007)
   ACCESS     not-accessible
   STATUS     mandatory
   DESCRIPTION
     "This variable represents the index for the mscFrAtmDlci tables."
::= { mscFrAtmDlciRowStatusEntry 10 }

mscFrAtmDlciStateTable OBJECT-TYPE
   SYNTAX     SEQUENCE OF MscFrAtmDlciStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscFrAtmDlci 10 }

mscFrAtmDlciStateEntry OBJECT-TYPE
   SYNTAX     MscFrAtmDlciStateEntry
   ACCESS     not-accessible
   STATUS     mandatory
   DESCRIPTION
     "An entry in the mscFrAtmDlciStateTable."
   INDEX {
      mscFrAtmIndex,
      mscFrAtmDlciIndex }
::= { mscFrAtmDlciStateTable 1 }

MscFrAtmDlciStateEntry ::= SEQUENCE {
   mscFrAtmDlciAdminState
      INTEGER,
   mscFrAtmDlciOperationalState
      INTEGER,
   mscFrAtmDlciUsageState
      INTEGER }

mscFrAtmDlciAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscFrAtmDlciStateEntry 1 }

mscFrAtmDlciOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscFrAtmDlciStateEntry 2 }

mscFrAtmDlciUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscFrAtmDlciStateEntry 3 }

mscFrAtmDlciABitTable OBJECT-TYPE
   SYNTAX     SEQUENCE OF MscFrAtmDlciABitEntry
   ACCESS     not-accessible
   STATUS     mandatory
   DESCRIPTION
     "This group contains the A-Bit status information for this Data Link 
      Connection Identifier."
::= { mscFrAtmDlci 11 }

mscFrAtmDlciABitEntry OBJECT-TYPE
   SYNTAX     MscFrAtmDlciABitEntry
   ACCESS     not-accessible
   STATUS     mandatory
   DESCRIPTION
     "An entry in the mscFrAtmDlciABitTable."
   INDEX {
      mscFrAtmIndex,
      mscFrAtmDlciIndex }
::= { mscFrAtmDlciABitTable 1 }

MscFrAtmDlciABitEntry ::= SEQUENCE {
   mscFrAtmDlciABitStatusToIf
      INTEGER,
   mscFrAtmDlciABitReasonToIf
      INTEGER,
   mscFrAtmDlciABitStatusFromIf
      INTEGER,
   mscFrAtmDlciABitReasonFromIf
      INTEGER }

mscFrAtmDlciABitStatusToIf OBJECT-TYPE
   SYNTAX     INTEGER  {
                 inactive(0),
                 active(1),
                 notApplicable(2) }
   ACCESS     read-only
   STATUS     mandatory
   DESCRIPTION
     "This attribute contains the most recent A-bit status sent to the 
      interface. The A-bit status is part of the LMI protocol, and indicates 
      the remote end's willingness to accept data from the local interface. 
      When an inactive setting is sent out, the Frame Relay service will 
      discard any data offered from the local interface. When an active 
      setting is sent out, the Frame Relay service tries to process all data 
      offered from the local interface."
::= { mscFrAtmDlciABitEntry 1 }

mscFrAtmDlciABitReasonToIf OBJECT-TYPE
   SYNTAX     INTEGER  {
                 notApplicable(0),
                 remoteUserSignaled(1),
                 localLmiError(2),
                 remoteLmiError(3),
                 localLinkDown(4),
                 remoteLinkDown(5),
                 pvcDown(6) }
   ACCESS     read-only
   STATUS     mandatory
   DESCRIPTION
     "This attribute provides the reason (if any) for an inactive status to be 
      sent to the interface. This reason is notApplicable for an active 
      status."
::= { mscFrAtmDlciABitEntry 2 }

mscFrAtmDlciABitStatusFromIf OBJECT-TYPE
   SYNTAX     INTEGER  {
                 inactive(0),
                 active(1),
                 notApplicable(2) }
   ACCESS     read-only
   STATUS     mandatory
   DESCRIPTION
     "This attribute indicates the most recent A-Bit status received from 
      the interface."
::= { mscFrAtmDlciABitEntry 3 }

mscFrAtmDlciABitReasonFromIf OBJECT-TYPE
   SYNTAX     INTEGER  {
                 notApplicable(0),
                 remoteUserSignaled(1),
                 localLmiError(2),
                 localLinkDown(4),
                 pvcDown(6),
                 missingFromLmiReport(7) }
   ACCESS     read-only
   STATUS     mandatory
   DESCRIPTION
     "This attribute provides the reason (if any) for an inactive status to be 
      sent to the subnet.
      The value is notApplicable when the aBitStatusFromIf attribute is 
      active.
      The value is remoteUserSignaled if the remote interface originating 
      the A-Bit status detects that the virtual circuit is down at the remote 
      network through the LMI protocol. The remote interface must be 
      running network site LMI protocol for this A-Bit status reason to be 
      sent.
      The value is localLmiError if the LMI protocol is down at this 
      interface.
      The value is localLinkDown if the physical link is disabled at this 
      interface.
      The value is pvcDown if no A-Bit status has been sent to this 
      interface from the local network.
      The value is missingFromLmiReport if the remote interface did not 
      provide a reason along with the inactive A-Bit status.
      DESCRIPTION"
::= { mscFrAtmDlciABitEntry 4 }

mscFrAtmDlciSpOpTable OBJECT-TYPE
   SYNTAX     SEQUENCE OF MscFrAtmDlciSpOpEntry
   ACCESS     not-accessible
   STATUS     mandatory
   DESCRIPTION
     "This group contains service parameters for the Dlci component."
::= { mscFrAtmDlci 12 }

mscFrAtmDlciSpOpEntry OBJECT-TYPE
   SYNTAX     MscFrAtmDlciSpOpEntry
   ACCESS     not-accessible
   STATUS     mandatory
   DESCRIPTION
     "An entry in the mscFrAtmDlciSpOpTable."
   INDEX {
      mscFrAtmIndex,
      mscFrAtmDlciIndex }
::= { mscFrAtmDlciSpOpTable 1 }

MscFrAtmDlciSpOpEntry ::= SEQUENCE {
   mscFrAtmDlciMaximumFrameSize
      Unsigned32,
   mscFrAtmDlciRateEnforcement
      INTEGER,
   mscFrAtmDlciCommittedInformationRate
      Unsigned32,
   mscFrAtmDlciCommittedBurstSize
      Unsigned32,
   mscFrAtmDlciExcessBurstSize
      Unsigned32,
   mscFrAtmDlciMeasurementInterval
      Unsigned32,
   mscFrAtmDlciEmissionPriorityToIf
      INTEGER,
   mscFrAtmDlciDlciType
      INTEGER,
   mscFrAtmDlciTroubled
      INTEGER,
   mscFrAtmDlciTroubledReason
      INTEGER }

mscFrAtmDlciMaximumFrameSize OBJECT-TYPE
   SYNTAX     Unsigned32 (1..8187)
   ACCESS     read-only
   STATUS     mandatory
   DESCRIPTION
     "This attribute indicates the maximum number of octets which can 
      be included in the information field. This definition does not include 
      the FrameRelay header and CRC octets. This attribute corresponds 
      to the dN1 parameter described in the Vendor Forum Specification."
::= { mscFrAtmDlciSpOpEntry 1 }

mscFrAtmDlciRateEnforcement OBJECT-TYPE
   SYNTAX     INTEGER  {
                 off(0),
                 on(1) }
   ACCESS     read-only
   STATUS     mandatory
   DESCRIPTION
     "This attribute indicates whether rate enforcement is in effect for this 
      user Data Link Connection on this FrAtm interface. 
      
      When rate enforcement is on, Committed Information Rate (CIR) 
      and DE=1 traffic will be measured and enforced.
      
      When rate enforcement is off, all frames from the user will be 
      accepted and no modifications to the frame with respect to the DE 
      bit will be made."
::= { mscFrAtmDlciSpOpEntry 2 }

mscFrAtmDlciCommittedInformationRate OBJECT-TYPE
   SYNTAX     Unsigned32 (0..50000000)
   ACCESS     read-only
   STATUS     mandatory
   DESCRIPTION
     "This attribute indicates the committed information rate (CIR) in bits 
      per second (bit/s) and represents the rate at which the network 
      agrees to transfer information under normal conditions when 
      rateEnforcement is on. This rate is measured over a measurement 
      interval (t).
      
      This attribute is not applicable when rateEnforcement is off."
::= { mscFrAtmDlciSpOpEntry 3 }

mscFrAtmDlciCommittedBurstSize OBJECT-TYPE
   SYNTAX     Unsigned32 (0..50000000)
   ACCESS     read-only
   STATUS     mandatory
   DESCRIPTION
     "This attribute indicates the committed burst size (Bc) in bits and 
      represents the amount of data that a network agrees to transfer 
      under normal conditions over a measurement interval (t) when 
      rateEnforcement is on. Data marked with DE=1 is not accounted for 
      in committed burst size.
      
      This attribute is not applicable when rateEnforcement is off."
::= { mscFrAtmDlciSpOpEntry 4 }

mscFrAtmDlciExcessBurstSize OBJECT-TYPE
   SYNTAX     Unsigned32 (0..50000000)
   ACCESS     read-only
   STATUS     mandatory
   DESCRIPTION
     "This attribute indicates the excess burst size (Be) in bits and 
      represents the amount of uncommitted data that the network 
      attempts to deliver over measurement interval (t) when 
      rateEnforcement is on. Data marked DE=1 by the user or by the 
      network is accounted for here.
      
      This attribute is not applicable ignored when rateEnforcement is 
      off."
::= { mscFrAtmDlciSpOpEntry 5 }

mscFrAtmDlciMeasurementInterval OBJECT-TYPE
   SYNTAX     Unsigned32 (0..4294967295)
   ACCESS     read-only
   STATUS     mandatory
   DESCRIPTION
     "This attribute indicates the time interval over which rates and burst 
      sizes are measured.
      
      This attribute is not applicable when rateEnforcement is off."
::= { mscFrAtmDlciSpOpEntry 6 }

mscFrAtmDlciEmissionPriorityToIf OBJECT-TYPE
   SYNTAX     INTEGER (0 | 1 | 2 | 3)
   ACCESS     read-only
   STATUS     mandatory
   DESCRIPTION
     "This attribute indicates the emission priority of frames sent to the 
      interface.
      
      If the value of FrAtm/n numberOfEmissionQs is 2, set the value of 
      this attribute to either 0 or 1; if the value of FrAtm/n 
      numberOfEmissionQs is 4, set the value of this attribute to one of 0, 
      1, 2, 3."
::= { mscFrAtmDlciSpOpEntry 7 }

mscFrAtmDlciDlciType OBJECT-TYPE
   SYNTAX     INTEGER  {
                 serviceInterworking(0),
                 networkInterworking(1) }
   ACCESS     read-only
   STATUS     mandatory
   DESCRIPTION
     "This attribute indicates the type of DLCI.
      A value of serviceInterworking indicates that a FrAtm/n Dlci/n Siwf 
      component is present.
      A value of networkInterworking indicates that a FrAtm/n Dlci/n 
      Niwf component is present."
::= { mscFrAtmDlciSpOpEntry 8 }

mscFrAtmDlciTroubled OBJECT-TYPE
   SYNTAX     INTEGER  {
                 no(0),
                 yes(1) }
   ACCESS     read-only
   STATUS     mandatory
   DESCRIPTION
     "This attribute indicates whether or not the connection is in a 
      troubled state. Connections may become troubled for the following 
      reasons; if CAC failed to admit the call, or if one of the attributes 
      aBitStatusToIf, aBitStatusFromIf goes inactive; otherwise it is set to 
      no."
   DEFVAL     { no }
::= { mscFrAtmDlciSpOpEntry 9 }

mscFrAtmDlciTroubledReason OBJECT-TYPE
   SYNTAX     INTEGER  {
                 notApplicable(0),
                 notAdmitted(1) }
   ACCESS     read-only
   STATUS     mandatory
   DESCRIPTION
     "This attribute provides the reason (if any) for a troubled connection. 
      
      A value of notApplicable indicates no current failures; either 
      Connection Admission Control (CAC) is off, or call was admitted.
      
      A value of notAdmitted indicates the CAC algorithm fails to admit 
      this connection. Check if there is a sufficient bandwidth allocation."
   DEFVAL     { notApplicable }
::= { mscFrAtmDlciSpOpEntry 10 }

mscFrAtmDlciStatsTable OBJECT-TYPE
   SYNTAX     SEQUENCE OF MscFrAtmDlciStatsEntry
   ACCESS     not-accessible
   STATUS     mandatory
   DESCRIPTION
     "This group contains the operational statistics for the Frame Relay 
      Data Link Connection Identifier."
::= { mscFrAtmDlci 13 }

mscFrAtmDlciStatsEntry OBJECT-TYPE
   SYNTAX     MscFrAtmDlciStatsEntry
   ACCESS     not-accessible
   STATUS     mandatory
   DESCRIPTION
     "An entry in the mscFrAtmDlciStatsTable."
   INDEX {
      mscFrAtmIndex,
      mscFrAtmDlciIndex }
::= { mscFrAtmDlciStatsTable 1 }

MscFrAtmDlciStatsEntry ::= SEQUENCE {
   mscFrAtmDlciFrmToIf
      Counter32,
   mscFrAtmDlciFecnFrmToIf
      Counter32,
   mscFrAtmDlciBecnFrmToIf
      Counter32,
   mscFrAtmDlciDeFrmToIf
      Counter32,
   mscFrAtmDlciDiscCongestedToIf
      Counter32,
   mscFrAtmDlciDiscDeCongestedToIf
      Counter32,
   mscFrAtmDlciFrmFromIf
      Counter32,
   mscFrAtmDlciFecnFrmFromIf
      Counter32,
   mscFrAtmDlciBecnFrmFromIf
      Counter32,
   mscFrAtmDlciEfciFrmFromNetwork
      Counter32,
   mscFrAtmDlciDeFrmFromIf
      Counter32,
   mscFrAtmDlciExcessFrmFromIf
      Counter32,
   mscFrAtmDlciDiscExcessFromIf
      Counter32,
   mscFrAtmDlciDiscFrameAbit
      Counter32,
   mscFrAtmDlciDiscCongestedFromIf
      Counter32,
   mscFrAtmDlciDiscDeCongestedFromIf
      Counter32,
   mscFrAtmDlciErrorShortFrmFromIf
      Counter32,
   mscFrAtmDlciErrorLongFrmFromIf
      Counter32,
   mscFrAtmDlciBecnFrmSetByService
      Counter32,
   mscFrAtmDlciBytesToIf
      Counter32,
   mscFrAtmDlciDeBytesToIf
      Counter32,
   mscFrAtmDlciDiscCongestedToIfBytes
      Counter32,
   mscFrAtmDlciDiscDeCongestedToIfBytes
      Counter32,
   mscFrAtmDlciBytesFromIf
      Counter32,
   mscFrAtmDlciDeBytesFromIf
      Counter32,
   mscFrAtmDlciExcessBytesFromIf
      Counter32,
   mscFrAtmDlciDiscExcessFromIfBytes
      Counter32,
   mscFrAtmDlciDiscByteAbit
      Counter32,
   mscFrAtmDlciDiscCongestedFromIfBytes
      Counter32,
   mscFrAtmDlciDiscDeCongestedFromIfBytes
      Counter32,
   mscFrAtmDlciErrorShortBytesFromIf
      Counter32,
   mscFrAtmDlciErrorLongBytesFromIf
      Counter32 }

mscFrAtmDlciFrmToIf OBJECT-TYPE
   SYNTAX     Counter32 
   ACCESS     read-only
   STATUS     mandatory
   DESCRIPTION
     "This attribute counts the number of frames sent to the interface. 
      When the maximum count is reached, the count wraps to zero."
::= { mscFrAtmDlciStatsEntry 1 }

mscFrAtmDlciFecnFrmToIf OBJECT-TYPE
   SYNTAX     Counter32 
   ACCESS     read-only
   STATUS     mandatory
   DESCRIPTION
     "This attribute counts the number of frames sent to the interface with 
      the Forward Explicit Congestion Notification (FECN) bit set. When 
      the maximum count is reached, the count wraps to zero."
::= { mscFrAtmDlciStatsEntry 2 }

mscFrAtmDlciBecnFrmToIf OBJECT-TYPE
   SYNTAX     Counter32 
   ACCESS     read-only
   STATUS     mandatory
   DESCRIPTION
     "This attribute counts the number of frames sent to the interface with 
      the Backward Explicit Congestion Notification (BECN) bit set. 
      When the maximum count is reached, the count wraps to zero."
::= { mscFrAtmDlciStatsEntry 3 }

mscFrAtmDlciDeFrmToIf OBJECT-TYPE
   SYNTAX     Counter32 
   ACCESS     read-only
   STATUS     mandatory
   DESCRIPTION
     "This attribute counts the number of frames sent to the interface with 
      the Discard Eligibility (DE) bit set. When the maximum count is 
      reached, the count wraps to zero."
::= { mscFrAtmDlciStatsEntry 4 }

mscFrAtmDlciDiscCongestedToIf OBJECT-TYPE
   SYNTAX     Counter32 
   ACCESS     read-only
   STATUS     mandatory
   DESCRIPTION
     "This attribute counts the number of frame discards at the Frame 
      Relay service due to local congestion in the direction toward the 
      interface. When the maximum count is reached, the count wraps to 
      zero."
::= { mscFrAtmDlciStatsEntry 5 }

mscFrAtmDlciDiscDeCongestedToIf OBJECT-TYPE
   SYNTAX     Counter32 
   ACCESS     read-only
   STATUS     mandatory
   DESCRIPTION
     "This attribute counts the number of discarded frames, with the 
      Discard Eligibility (DE) bit set, at the Frame Relay service, due to 
      local congestion in the direction toward the interface. When the 
      maximum count is reached, the count wraps to zero."
::= { mscFrAtmDlciStatsEntry 6 }

mscFrAtmDlciFrmFromIf OBJECT-TYPE
   SYNTAX     Counter32 
   ACCESS     read-only
   STATUS     mandatory
   DESCRIPTION
     "This attribute counts the number of frames received from the 
      interface. Frames that are discarded due to error or excess are not 
      counted. When the maximum count is reached, the count wraps to 
      zero."
::= { mscFrAtmDlciStatsEntry 7 }

mscFrAtmDlciFecnFrmFromIf OBJECT-TYPE
   SYNTAX     Counter32 
   ACCESS     read-only
   STATUS     mandatory
   DESCRIPTION
     "This attribute counts the number of frames received from the 
      interface with the Forward Explicit Congestion Notification (FECN) 
      bit set. When the maximum count is reached, the count wraps to 
      zero."
::= { mscFrAtmDlciStatsEntry 8 }

mscFrAtmDlciBecnFrmFromIf OBJECT-TYPE
   SYNTAX     Counter32 
   ACCESS     read-only
   STATUS     mandatory
   DESCRIPTION
     "This attribute counts the number of frames received from the 
      interface with the Backward Explicit Congestion Notification 
      (BECN) bit set. When the maximum count is reached, the count 
      wraps to zero."
::= { mscFrAtmDlciStatsEntry 9 }

mscFrAtmDlciEfciFrmFromNetwork OBJECT-TYPE
   SYNTAX     Counter32 
   ACCESS     read-only
   STATUS     mandatory
   DESCRIPTION
     "This attribute counts the number of frames received from the 
      interworking function with the Explicit Forward Congestion 
      Indication (EFCI) bit set. When the maximum count is reached, the 
      count wraps to zero."
::= { mscFrAtmDlciStatsEntry 10 }

mscFrAtmDlciDeFrmFromIf OBJECT-TYPE
   SYNTAX     Counter32 
   ACCESS     read-only
   STATUS     mandatory
   DESCRIPTION
     "This attribute counts the number of frames received from the 
      interface with the Discard Eligibility (DE) bit set. When the 
      maximum count is reached, the count wraps to zero."
::= { mscFrAtmDlciStatsEntry 11 }

mscFrAtmDlciExcessFrmFromIf OBJECT-TYPE
   SYNTAX     Counter32 
   ACCESS     read-only
   STATUS     mandatory
   DESCRIPTION
     "This attribute counts the number of frames received from the 
      interface with the Discard Eligibility (DE) bit clear, but 
      subsequently set by the network due to rate enforcement. When the 
      maximum count is reached, the count wraps to zero."
::= { mscFrAtmDlciStatsEntry 12 }

mscFrAtmDlciDiscExcessFromIf OBJECT-TYPE
   SYNTAX     Counter32 
   ACCESS     read-only
   STATUS     mandatory
   DESCRIPTION
     "This attribute counts the number of frames which were discarded 
      due to rate enforcement. When the maximum count is reached, the 
      count wraps to zero."
::= { mscFrAtmDlciStatsEntry 13 }

mscFrAtmDlciDiscFrameAbit OBJECT-TYPE
   SYNTAX     Counter32 
   ACCESS     read-only
   STATUS     mandatory
   DESCRIPTION
     "This attribute counts the number of frame discards at the Frame 
      Relay Service, due to an inactive PVC status, in the direction 
      toward the interworking function. When the maximum count is 
      reached, the count wraps to zero."
::= { mscFrAtmDlciStatsEntry 14 }

mscFrAtmDlciDiscCongestedFromIf OBJECT-TYPE
   SYNTAX     Counter32 
   ACCESS     read-only
   STATUS     mandatory
   DESCRIPTION
     "This attribute counts the number of frame discards at the Frame 
      Relay service due to local congestion in the direction toward the 
      interworking function. When the maximum count is reached, the 
      count wraps to zero."
::= { mscFrAtmDlciStatsEntry 15 }

mscFrAtmDlciDiscDeCongestedFromIf OBJECT-TYPE
   SYNTAX     Counter32 
   ACCESS     read-only
   STATUS     mandatory
   DESCRIPTION
     "This attribute counts the number of discarded frames, with the 
      Discard Eligibility (DE) bit set due to local congestion in the 
      direction toward the interworking function. When the maximum 
      count is reached, the count wraps to zero."
::= { mscFrAtmDlciStatsEntry 16 }

mscFrAtmDlciErrorShortFrmFromIf OBJECT-TYPE
   SYNTAX     Counter32 
   ACCESS     read-only
   STATUS     mandatory
   DESCRIPTION
     "This attribute counts the number of frames received with 0 octets in 
      the information field. When the maximum count is reached, the 
      count wraps to zero."
::= { mscFrAtmDlciStatsEntry 17 }

mscFrAtmDlciErrorLongFrmFromIf OBJECT-TYPE
   SYNTAX     Counter32 
   ACCESS     read-only
   STATUS     mandatory
   DESCRIPTION
     "This attribute counts the number of frames received with number of 
      octets in the information field greater than the subscribed 
      maximum. When the maximum count is reached, the count wraps to 
      zero. The hardware ignores frame lengths greater than the hardware 
      receive buffer, and therfore does not includes them in this count."
::= { mscFrAtmDlciStatsEntry 18 }

mscFrAtmDlciBecnFrmSetByService OBJECT-TYPE
   SYNTAX     Counter32 
   ACCESS     read-only
   STATUS     mandatory
   DESCRIPTION
     "This attribute counts the number of frames with BECN set by the 
      Frame Relay service. It is incremented when the Frame Relay 
      service sets BECN on a frame upon detecting local congestion. This 
      count is incremented regardless of whether the frame already bears 
      a set BECN bit since its use is to determine the place of congestion. 
      When the maximum count is reached, the count wraps to zero."
::= { mscFrAtmDlciStatsEntry 19 }

mscFrAtmDlciBytesToIf OBJECT-TYPE
   SYNTAX     Counter32 
   ACCESS     read-only
   STATUS     mandatory
   DESCRIPTION
     "This attribute counts the number of bytes sent out the interface. 
      When the maximum count is reached, the count wraps to zero."
::= { mscFrAtmDlciStatsEntry 20 }

mscFrAtmDlciDeBytesToIf OBJECT-TYPE
   SYNTAX     Counter32 
   ACCESS     read-only
   STATUS     mandatory
   DESCRIPTION
     "This attribute counts the number of bytes sent to the interface with 
      the Discard Eligibility (DE) bit set. When the maximum count is 
      reached, the count wraps to zero."
::= { mscFrAtmDlciStatsEntry 21 }

mscFrAtmDlciDiscCongestedToIfBytes OBJECT-TYPE
   SYNTAX     Counter32 
   ACCESS     read-only
   STATUS     mandatory
   DESCRIPTION
     "This attribute counts the number of byte discards at the Frame 
      Relay service due to local congestion in the direction toward the 
      link. When the maximum count is reached, the count wraps to zero."
::= { mscFrAtmDlciStatsEntry 22 }

mscFrAtmDlciDiscDeCongestedToIfBytes OBJECT-TYPE
   SYNTAX     Counter32 
   ACCESS     read-only
   STATUS     mandatory
   DESCRIPTION
     "This attribute counts the number of discard eligible (DE=1) byte 
      discards at the Frame Relay service due to local congestion in the 
      direction toward the link. When the maximum count is reached, the 
      count wraps to zero."
::= { mscFrAtmDlciStatsEntry 23 }

mscFrAtmDlciBytesFromIf OBJECT-TYPE
   SYNTAX     Counter32 
   ACCESS     read-only
   STATUS     mandatory
   DESCRIPTION
     "This attribute counts the number of bytes received from the 
      interface. Bytes that are discarded due to error or excess are not 
      counted. When the maximum count is reached, the count wraps to 
      zero."
::= { mscFrAtmDlciStatsEntry 24 }

mscFrAtmDlciDeBytesFromIf OBJECT-TYPE
   SYNTAX     Counter32 
   ACCESS     read-only
   STATUS     mandatory
   DESCRIPTION
     "This attribute counts the number of bytes received from the 
      interface with the Discard Eligibility (DE) bit set. When the 
      maximum count is reached, the count wraps to zero."
::= { mscFrAtmDlciStatsEntry 25 }

mscFrAtmDlciExcessBytesFromIf OBJECT-TYPE
   SYNTAX     Counter32 
   ACCESS     read-only
   STATUS     mandatory
   DESCRIPTION
     "This attribute counts the number of bytes received from the 
      interface with the Discard Eligibility (DE) bit clear, but 
      subsequently set by the network due to rate enforcement. When the 
      maximum count is reached, the count wraps to zero."
::= { mscFrAtmDlciStatsEntry 26 }

mscFrAtmDlciDiscExcessFromIfBytes OBJECT-TYPE
   SYNTAX     Counter32 
   ACCESS     read-only
   STATUS     mandatory
   DESCRIPTION
     "This attribute counts the number of bytes which were discarded due 
      to rate enforcement. When the maximum count is reached, the 
      count wraps to zero."
::= { mscFrAtmDlciStatsEntry 27 }

mscFrAtmDlciDiscByteAbit OBJECT-TYPE
   SYNTAX     Counter32 
   ACCESS     read-only
   STATUS     mandatory
   DESCRIPTION
     "This attribute counts the bytes number of which were discarded due 
      to the A-bit being turned off. When the maximum count is reached, 
      the count wraps to zero."
::= { mscFrAtmDlciStatsEntry 28 }

mscFrAtmDlciDiscCongestedFromIfBytes OBJECT-TYPE
   SYNTAX     Counter32 
   ACCESS     read-only
   STATUS     mandatory
   DESCRIPTION
     "This attribute counts the number of byte discards at the Frame 
      Relay service due to local congestion in the direction toward the 
      interworking function. When the maximum count is reached, the 
      count wraps to zero."
::= { mscFrAtmDlciStatsEntry 29 }

mscFrAtmDlciDiscDeCongestedFromIfBytes OBJECT-TYPE
   SYNTAX     Counter32 
   ACCESS     read-only
   STATUS     mandatory
   DESCRIPTION
     "This attribute counts the number of discard eligible (DE=1) byte 
      discards at the Frame Relay service due to local congestion in the 
      direction toward the interworking function. When the maximum 
      count is reached, the count wraps to zero."
::= { mscFrAtmDlciStatsEntry 30 }

mscFrAtmDlciErrorShortBytesFromIf OBJECT-TYPE
   SYNTAX     Counter32 
   ACCESS     read-only
   STATUS     mandatory
   DESCRIPTION
     "This attribute counts the number of bytes received with 0 octets in 
      the information field. When the maximum count is reached, the 
      count wraps to zero."
::= { mscFrAtmDlciStatsEntry 31 }

mscFrAtmDlciErrorLongBytesFromIf OBJECT-TYPE
   SYNTAX     Counter32 
   ACCESS     read-only
   STATUS     mandatory
   DESCRIPTION
     "This attribute counts the number of bytes received when the number 
      of octets in the information field is greater than the subscribed 
      maximum. The hardware ignores bytes lengths greater than the 
      hardware receive buffer and therefore does not include them in this 
      count.
      
      When the maximum count is reached, the count wraps to zero."
::= { mscFrAtmDlciStatsEntry 32 }

mscFrAtmDlciCalldTable OBJECT-TYPE
   SYNTAX     SEQUENCE OF MscFrAtmDlciCalldEntry
   ACCESS     not-accessible
   STATUS     mandatory
   DESCRIPTION
     "This group contains the operational values for the FrAtm Dlci call 
      data. If the accountingEnabled attribute is no, then this group 
      except for accountingEnabled is not displayed."
::= { mscFrAtmDlci 14 }

mscFrAtmDlciCalldEntry OBJECT-TYPE
   SYNTAX     MscFrAtmDlciCalldEntry
   ACCESS     not-accessible
   STATUS     mandatory
   DESCRIPTION
     "An entry in the mscFrAtmDlciCalldTable."
   INDEX {
      mscFrAtmIndex,
      mscFrAtmDlciIndex }
::= { mscFrAtmDlciCalldTable 1 }

MscFrAtmDlciCalldEntry ::= SEQUENCE {
   mscFrAtmDlciAccountingEnabled
      INTEGER,
   mscFrAtmDlciAccountingEnd
      INTEGER,
   mscFrAtmDlciCorrelationTag
      HexString }

mscFrAtmDlciAccountingEnabled OBJECT-TYPE
   SYNTAX     INTEGER  {
                 no(0),
                 yes(1) }
   ACCESS     read-only
   STATUS     mandatory
   DESCRIPTION
     "This attribute indicates whether accounting is enabled. To enable 
      accounting, the FrAtm Ca accountCollection attribute must be non-
      empty and FrAtm Dlci Sp accounting attribute must be on."
::= { mscFrAtmDlciCalldEntry 1 }

mscFrAtmDlciAccountingEnd OBJECT-TYPE
   SYNTAX     INTEGER  {
                 callingEnd(0),
                 calledEnd(1) }
   ACCESS     read-only
   STATUS     mandatory
   DESCRIPTION
     "This attribute indicates whether this DLCI represents the called or 
      calling end of the connection. If the accountingEnabled attribute is 
      no, then this attribute is not displayed."
::= { mscFrAtmDlciCalldEntry 2 }

mscFrAtmDlciCorrelationTag OBJECT-TYPE
   SYNTAX     HexString (SIZE (0..28))
   ACCESS     read-only
   STATUS     mandatory
   DESCRIPTION
     "This attribute indicates the unique string which identifies this 
      connection. The value of this operational attribute can be 
      provisioned in the correlationTag attribute of either the Siwf Npvc, 
      Siwf Spvc, or Niwf Spvc subcomponents. For the Siwf Spvc and Niwf 
      Spvc cases, when the provisionable correlationTag is an empty 
      string, then this attribute receives the value of a system- generated 
      correlationTag. Downstream processing uses this attribute to 
      correlate accounting records issued at different nodes in the 
      network. If the accountingEnabled attribute is no, then this attribute 
      is not displayed."
   DEFVAL     { ''H }  -- ""
::= { mscFrAtmDlciCalldEntry 3 }

mscFrAtmDlciIntTable OBJECT-TYPE
   SYNTAX     SEQUENCE OF MscFrAtmDlciIntEntry
   ACCESS     not-accessible
   STATUS     mandatory
   DESCRIPTION
     "This group contains the operational statistics for the FrAtm Dlci 
      interval data."
::= { mscFrAtmDlci 15 }

mscFrAtmDlciIntEntry OBJECT-TYPE
   SYNTAX     MscFrAtmDlciIntEntry
   ACCESS     not-accessible
   STATUS     mandatory
   DESCRIPTION
     "An entry in the mscFrAtmDlciIntTable."
   INDEX {
      mscFrAtmIndex,
      mscFrAtmDlciIndex }
::= { mscFrAtmDlciIntTable 1 }

MscFrAtmDlciIntEntry ::= SEQUENCE {
   mscFrAtmDlciStartTime
      EnterpriseDateAndTime,
   mscFrAtmDlciTotalIngressBytes
      Unsigned64,
   mscFrAtmDlciTotalEgressBytes
      Unsigned64,
   mscFrAtmDlciEirIngressBytes
      Unsigned64,
   mscFrAtmDlciEirEgressBytes
      Unsigned64,
   mscFrAtmDlciDiscardedBytes
      Unsigned64,
   mscFrAtmDlciTotalIngressFrames
      Unsigned32,
   mscFrAtmDlciTotalEgressFrames
      Unsigned32,
   mscFrAtmDlciEirIngressFrames
      Unsigned32,
   mscFrAtmDlciEirEgressFrames
      Unsigned32,
   mscFrAtmDlciDiscardedFrames
      Unsigned32,
   mscFrAtmDlciElapsedDifference
      Unsigned32 }

mscFrAtmDlciStartTime OBJECT-TYPE
   SYNTAX     EnterpriseDateAndTime (SIZE (0 | 19))
   ACCESS     read-only
   STATUS     mandatory
   DESCRIPTION
     "This attribute indicates the start time of this interval. A new interval 
      is started each time an accounting record is generated and call at a 
      setup. If the accountingEnabled attribute is no, then this attribute is 
      not displayed."
::= { mscFrAtmDlciIntEntry 1 }

mscFrAtmDlciTotalIngressBytes OBJECT-TYPE
   SYNTAX     Unsigned64 (SIZE (8))
   ACCESS     read-only
   STATUS     mandatory
   DESCRIPTION
     "This attribute counts the total payload bytes in received from the 
      link since the start of the interval. To calculate total valid payload 
      bytes received from link, subtract discardedBytes from this 
      attribute. The start of the interval is captured in the startTime 
      attribute. The count is reset to zero when an accounting record is 
      generated or at call setup. If the accountingEnabled attribute is no, 
      then this attribute is not displayed."
::= { mscFrAtmDlciIntEntry 2 }

mscFrAtmDlciTotalEgressBytes OBJECT-TYPE
   SYNTAX     Unsigned64 (SIZE (8))
   ACCESS     read-only
   STATUS     mandatory
   DESCRIPTION
     "This attribute counts the total payload bytes sent to the link since 
      the start of the interval. The start of the interval is captured in the 
      startTime attribute. The count is reset to zero when an accounting 
      record is generated or at call setup. If the accountingEnabled 
      attribute is no, then this attribute is not displayed."
::= { mscFrAtmDlciIntEntry 3 }

mscFrAtmDlciEirIngressBytes OBJECT-TYPE
   SYNTAX     Unsigned64 (SIZE (8))
   ACCESS     read-only
   STATUS     mandatory
   DESCRIPTION
     "This attribute counts the total valid payload bytes in frames with the 
      Discard Eligibility (DE) bit set to 1 received from the link since the 
      start of the interval. Subtract this attribute and discardedBytes from 
      totalIngressBytes to calculate total valid payload bytes in frames 
      received from the link, with the DE bit set to 0. The start of the 
      interval is captured in the startTime attribute. The count is reset to 
      zero when an accounting record is generated or at call setup. If the 
      accountingEnabled attribute is no, then this attribute is not 
      displayed."
::= { mscFrAtmDlciIntEntry 4 }

mscFrAtmDlciEirEgressBytes OBJECT-TYPE
   SYNTAX     Unsigned64 (SIZE (8))
   ACCESS     read-only
   STATUS     mandatory
   DESCRIPTION
     "This attribute counts the total valid payload bytes in frames with the 
      Discard Eligibility (DE) bit set sent to the link since the start of the 
      interval. Subtract the value of this attribute from totalEgressBytes to 
      calculate total valid payload bytes in frames, with DE set to 0, sent 
      to the link. The start of the interval is captured in the startTime 
      attribute. The count is reset to zero when an accounting record is 
      generated or at call setup. If the accountingEnabled attribute is no, 
      then this attribute is not displayed."
::= { mscFrAtmDlciIntEntry 5 }

mscFrAtmDlciDiscardedBytes OBJECT-TYPE
   SYNTAX     Unsigned64 (SIZE (8))
   ACCESS     read-only
   STATUS     mandatory
   DESCRIPTION
     "This attribute counts the total payload bytes in invalid frames 
      received from the link and discarded at the DLCI since the start of 
      the interval. This count is a sum of octets in frames discarded due 
      to: frames too long or too short; A-Bit off; or to rate enforcement. 
      The start of the interval is captured in the startTime attribute. The 
      count is reset to zero when an accounting record is generated or at 
      call setup. If the accountingEnabled attribute is no, then this 
      attribute is not displayed."
::= { mscFrAtmDlciIntEntry 6 }

mscFrAtmDlciTotalIngressFrames OBJECT-TYPE
   SYNTAX     Unsigned32 (0..4294967295)
   ACCESS     read-only
   STATUS     mandatory
   DESCRIPTION
     "This attribute counts the total number of frames received from the 
      link since the start of the interval. To calculate the total valid 
      number of frames received from the link, subtract discardedFrames 
      from this attribute. The start of the interval is captured in the 
      startTime attribute. The count is reset to zero when an accounting 
      record is generated or at call setup. If the accountingEnabled 
      attribute is no, then this attribute is not displayed."
   DEFVAL     { 0 }
::= { mscFrAtmDlciIntEntry 7 }

mscFrAtmDlciTotalEgressFrames OBJECT-TYPE
   SYNTAX     Unsigned32 (0..4294967295)
   ACCESS     read-only
   STATUS     mandatory
   DESCRIPTION
     "This attribute counts the total number of frames sent to the link 
      since the start of the interval. The start of the interval is captured in 
      the startTime attribute. The count is reset to zero when an 
      accounting record is generated or at call setup. If the 
      accountingEnabled attribute is no, then this attribute is not 
      displayed."
   DEFVAL     { 0 }
::= { mscFrAtmDlciIntEntry 8 }

mscFrAtmDlciEirIngressFrames OBJECT-TYPE
   SYNTAX     Unsigned32 (0..4294967295)
   ACCESS     read-only
   STATUS     mandatory
   DESCRIPTION
     "This attribute counts the number of valid frames with the Discard 
      Eligibility (DE) bit set to 1 received from the link since the start of 
      the interval. Subtract this attribute and discardedFrames from 
      totalIngressFrames to calculate total valid frames received from the 
      link, with the DE bit set to 0. The start of the interval is captured in 
      the startTime attribute. The count is reset to zero when an 
      accounting record is generated or at call setup. If the 
      accountingEnabled attribute is no, then this attribute is not 
      displayed."
   DEFVAL     { 0 }
::= { mscFrAtmDlciIntEntry 9 }

mscFrAtmDlciEirEgressFrames OBJECT-TYPE
   SYNTAX     Unsigned32 (0..4294967295)
   ACCESS     read-only
   STATUS     mandatory
   DESCRIPTION
     "This attribute counts the number of frames with the Discard 
      Eligibility (DE) bit set sent to the link since the start of the interval. 
      Subtract the value of this attribute from totalEgressFrames to 
      calculate total frames, with DE set to 0, sent to the link.The start of 
      the interval is captured in the startTime attribute. The count is reset 
      to zero when an accounting record is generated call setup. If the 
      accountingEnabled attribute is no, then this attribute is not 
      displayed."
   DEFVAL     { 0 }
::= { mscFrAtmDlciIntEntry 10 }

mscFrAtmDlciDiscardedFrames OBJECT-TYPE
   SYNTAX     Unsigned32 (0..4294967295)
   ACCESS     read-only
   STATUS     mandatory
   DESCRIPTION
     "This attribute counts the number of invalid frames received from the 
      link and discarded at the DLCI. The count is reset to zero when an 
      accounting record is generated or at call setup. The count is a sum 
      of frames discarded due to: frames too long or too short; A-Bit is 
      off; or rate enforcement. If the accountingEnabled attribute is no, 
      then this attribute is not displayed."
   DEFVAL     { 0 }
::= { mscFrAtmDlciIntEntry 11 }

mscFrAtmDlciElapsedDifference OBJECT-TYPE
   SYNTAX     Unsigned32 (0..4294967295)
   ACCESS     read-only
   STATUS     mandatory
   DESCRIPTION
     "This attribute indicates the elapsed time representing the of this 
      interval data. It is the elapsed time in 0.1 second increments since 
      the start of the interval. If the accountingEnabled attribute is no, 
      then this attribute is not displayed."
   DEFVAL     { 0 }
::= { mscFrAtmDlciIntEntry 12 }


-- FrAtm/n Dlci/n ServiceParameters
-- This component is a subcomponent of Dlci. It contains the 
-- provisionable attributes for the parent Dlci component.

mscFrAtmDlciSp OBJECT IDENTIFIER ::= { mscFrAtmDlci 2 }



mscFrAtmDlciSpRowStatusTable OBJECT-TYPE
   SYNTAX     SEQUENCE OF MscFrAtmDlciSpRowStatusEntry
   ACCESS     not-accessible
   STATUS     mandatory
   DESCRIPTION
     "This entry controls the addition and deletion of 
      mscFrAtmDlciSp components."
::= { mscFrAtmDlciSp 1 }

mscFrAtmDlciSpRowStatusEntry OBJECT-TYPE
   SYNTAX     MscFrAtmDlciSpRowStatusEntry
   ACCESS     not-accessible
   STATUS     mandatory
   DESCRIPTION
     "A single entry in the table represents a single 
      mscFrAtmDlciSp component."
   INDEX {
      mscFrAtmIndex,
      mscFrAtmDlciIndex,
      mscFrAtmDlciSpIndex }
::= { mscFrAtmDlciSpRowStatusTable 1 }

MscFrAtmDlciSpRowStatusEntry ::= SEQUENCE {
   mscFrAtmDlciSpRowStatus
      RowStatus,
   mscFrAtmDlciSpComponentName
      DisplayString,
   mscFrAtmDlciSpStorageType
      StorageType,
   mscFrAtmDlciSpIndex
      NonReplicated }

mscFrAtmDlciSpRowStatus OBJECT-TYPE
   SYNTAX     RowStatus 
   ACCESS     read-only
   STATUS     mandatory
   DESCRIPTION
     "This variable is used as the basis for SNMP naming of
      mscFrAtmDlciSp components.
      These components cannot be added nor deleted."
::= { mscFrAtmDlciSpRowStatusEntry 1 }

mscFrAtmDlciSpComponentName OBJECT-TYPE
   SYNTAX     DisplayString 
   ACCESS     read-only
   STATUS     mandatory
   DESCRIPTION
     "This variable provides the component's string name for
      use with the ASCII Console Interface"
::= { mscFrAtmDlciSpRowStatusEntry 2 }

mscFrAtmDlciSpStorageType OBJECT-TYPE
   SYNTAX     StorageType 
   ACCESS     read-only
   STATUS     mandatory
   DESCRIPTION
     "This variable represents the storage type value for the
      mscFrAtmDlciSp tables."
::= { mscFrAtmDlciSpRowStatusEntry 4 }

mscFrAtmDlciSpIndex OBJECT-TYPE
   SYNTAX     NonReplicated 
   ACCESS     not-accessible
   STATUS     mandatory
   DESCRIPTION
     "This variable represents the index for the mscFrAtmDlciSp tables."
::= { mscFrAtmDlciSpRowStatusEntry 10 }

mscFrAtmDlciSpProvTable OBJECT-TYPE
   SYNTAX     SEQUENCE OF MscFrAtmDlciSpProvEntry
   ACCESS     not-accessible
   STATUS     mandatory
   DESCRIPTION
     "This group contains the provisionable attributes for the Data Link 
      Connection Identifier. These attributes reflect the service parameters 
      specific to this instance of DLCI. The congestion control attributes 
      in this group are defined in T1.606 Addendum 1."
::= { mscFrAtmDlciSp 10 }

mscFrAtmDlciSpProvEntry OBJECT-TYPE
   SYNTAX     MscFrAtmDlciSpProvEntry
   ACCESS     not-accessible
   STATUS     mandatory
   DESCRIPTION
     "An entry in the mscFrAtmDlciSpProvTable."
   INDEX {
      mscFrAtmIndex,
      mscFrAtmDlciIndex,
      mscFrAtmDlciSpIndex }
::= { mscFrAtmDlciSpProvTable 1 }

MscFrAtmDlciSpProvEntry ::= SEQUENCE {
   mscFrAtmDlciSpMaximumFrameSize
      Unsigned32,
   mscFrAtmDlciSpRateEnforcement
      INTEGER,
   mscFrAtmDlciSpCommittedInformationRate
      Unsigned32,
   mscFrAtmDlciSpCommittedBurstSize
      Unsigned32,
   mscFrAtmDlciSpExcessBurstSize
      Unsigned32,
   mscFrAtmDlciSpMeasurementInterval
      Unsigned32,
   mscFrAtmDlciSpEmissionPriorityToIf
      INTEGER,
   mscFrAtmDlciSpEmissionPrioToIf
      INTEGER,
   mscFrAtmDlciSpAccounting
      INTEGER }

mscFrAtmDlciSpMaximumFrameSize OBJECT-TYPE
   SYNTAX     Unsigned32 (1..8187)
   ACCESS     read-write
   STATUS     mandatory
   DESCRIPTION
     "This attribute specifies the maximum number of octets which may 
      be included in the information field. The Frame Relay header and 
      CRC octets are not included in this definition. This attribute 
      corresponds to the dN1 parameter described in the Vendor Forum 
      Specification."
   DEFVAL     { 2100 }
::= { mscFrAtmDlciSpProvEntry 1 }

mscFrAtmDlciSpRateEnforcement OBJECT-TYPE
   SYNTAX     INTEGER  {
                 off(0),
                 on(1) }
   ACCESS     read-write
   STATUS     mandatory
   DESCRIPTION
     "This attribute specifies whether rate enforcement is in effect for this 
      user data link connection. 
      
      When rateEnforcement is on, the CIR and De=1 traffic will be 
      measured and enforced. 
      
      When rateEnforcement is off, all frames from the user are accepted 
      and no modifications to the frame with respect to the De bit will be 
      made."
   DEFVAL     { on }
::= { mscFrAtmDlciSpProvEntry 2 }

mscFrAtmDlciSpCommittedInformationRate OBJECT-TYPE
   SYNTAX     Unsigned32 (0..50000000)
   ACCESS     read-write
   STATUS     mandatory
   DESCRIPTION
     "This attribute specifies the committed information rate (CIR). It 
      represents the rate at which the network agrees to transfer 
      information under normal conditions when rate enforcement is in 
      effect.
      
      When rate enforcement is not in effect, this attribute is ignored.
      
      Determination of the actual CIR is based on 
      committedInformationRate, committedBurstSize and a measurement 
      interval. The measurement interval is determined internally when 
      committedInformationRate has a non-zero value. Otherwise, it is 
      based on measurementInterval which must be explicitly 
      provisioned.
      
      Note: The committedBurstSize must have a value of 0 when rate 
      enforcement is in effect and committedInformationRate has a value 
      of 0."
   DEFVAL     { 64000 }
::= { mscFrAtmDlciSpProvEntry 3 }

mscFrAtmDlciSpCommittedBurstSize OBJECT-TYPE
   SYNTAX     Unsigned32 (0..50000000)
   ACCESS     read-write
   STATUS     mandatory
   DESCRIPTION
     "This attribute specifies the committed burst size (Bc). It represents 
      the amount of data that a network agrees to transfer under normal 
      conditions over a measurement interval when rate enforcement is in 
      effect. Data marked DE=1 is not accounted for in the committed 
      burst size.
      
      When rate enforcement is not in effect, this attribute is ignored. 
      
      Note: The committedInformationRate must have a value of 0 when 
      rate enforcement is in effect and committedBurstSize has a value of 
      0."
   DEFVAL     { 64000 }
::= { mscFrAtmDlciSpProvEntry 4 }

mscFrAtmDlciSpExcessBurstSize OBJECT-TYPE
   SYNTAX     Unsigned32 (0..50000000)
   ACCESS     read-write
   STATUS     mandatory
   DESCRIPTION
     "This attribute specifies the excess burst size (Be). It represents the 
      amount of uncommitted data that the network will attempt to deliver 
      over a measurement interval when rate enforcement is in effect. 
      Data marked DE=1 by the user or by the network is accounted for 
      here.
      
      committedInformationRate, committedBurstSize, and 
      excessBurstSize cannot all be zero when rate enforcement is in 
      effect."
   DEFVAL     { 0 }
::= { mscFrAtmDlciSpProvEntry 5 }

mscFrAtmDlciSpMeasurementInterval OBJECT-TYPE
   SYNTAX     Unsigned32 (0..25500)
   ACCESS     read-write
   STATUS     mandatory
   DESCRIPTION
     "This attribute specifies the time interval over which rates and burst 
      sizes are measured when rate enforcement is in effect.
      
      When rate enforcement is in effect and both 
      committedInformationRate and committedBurstSize have values of 
      zero, this attribute must have a non-zero value.
      
      When rate enforcement is not in effect or when 
      committedInformationRate and committedBurstSize have non-zero 
      values, this attribute is ignored.
      
      When committedInformationRate and committedBurstSize have 
      non-zero values, the time interval is internally calculated. In this 
      situation, measurementInterval is ignored, and it does not represent 
      the time interval."
   DEFVAL     { 0 }
::= { mscFrAtmDlciSpProvEntry 6 }

mscFrAtmDlciSpEmissionPriorityToIf OBJECT-TYPE
   SYNTAX     INTEGER  {
                 low(0),
                 high(3) }
   ACCESS     read-write
   STATUS     obsolete
   DESCRIPTION
     "This attribute specifies the emission priority of frames sent to the 
      interface.
      
      The high priority frames in the high priority frame queue will be 
      served before the low priority frames in the low priority queue.
      
      This attribute is obsoleted. During migration, its value will be 
      transferred to emissionPriToIf."
   DEFVAL     { low }
::= { mscFrAtmDlciSpProvEntry 7 }

mscFrAtmDlciSpEmissionPrioToIf OBJECT-TYPE
   SYNTAX     INTEGER (0 | 1 | 2 | 3)
   ACCESS     read-write
   STATUS     obsolete
   DESCRIPTION
     "This attribute specifies the emission priority of frames sent to the 
      interface.
      
      Frames in a higher priority queue will be sent before frames in a 
      lower priority queue.
      
      The value of this attribute must be greater than or equal to 0, and 
      less than the value of the provisionable attribute 
      numberOfEmissionQs."
   DEFVAL     { 0 }
::= { mscFrAtmDlciSpProvEntry 8 }

mscFrAtmDlciSpAccounting OBJECT-TYPE
   SYNTAX     INTEGER  {
                 off(0),
                 on(1) }
   ACCESS     read-write
   STATUS     mandatory
   DESCRIPTION
     "This attribute allows the operator to control accounting for this 
      DLCI. To enable accounting data collection and record generation, 
      the value of this attribute must be on and at least one of the 
      accountCollection reasons in the FrAtm Ca component must be set."
   DEFVAL     { off }
::= { mscFrAtmDlciSpProvEntry 9 }


-- FrAtm/n Dlci/n ServiceInterworkingFunction
-- The Siwf component provides the service interworking function 
-- capability between a Frame Relay data link connection and an ATM 
-- connection.

mscFrAtmDlciSiwf OBJECT IDENTIFIER ::= { mscFrAtmDlci 3 }



mscFrAtmDlciSiwfRowStatusTable OBJECT-TYPE
   SYNTAX     SEQUENCE OF MscFrAtmDlciSiwfRowStatusEntry
   ACCESS     not-accessible
   STATUS     mandatory
   DESCRIPTION
     "This entry controls the addition and deletion of 
      mscFrAtmDlciSiwf components."
::= { mscFrAtmDlciSiwf 1 }

mscFrAtmDlciSiwfRowStatusEntry OBJECT-TYPE
   SYNTAX     MscFrAtmDlciSiwfRowStatusEntry
   ACCESS     not-accessible
   STATUS     mandatory
   DESCRIPTION
     "A single entry in the table represents a single 
      mscFrAtmDlciSiwf component."
   INDEX {
      mscFrAtmIndex,
      mscFrAtmDlciIndex,
      mscFrAtmDlciSiwfIndex }
::= { mscFrAtmDlciSiwfRowStatusTable 1 }

MscFrAtmDlciSiwfRowStatusEntry ::= SEQUENCE {
   mscFrAtmDlciSiwfRowStatus
      RowStatus,
   mscFrAtmDlciSiwfComponentName
      DisplayString,
   mscFrAtmDlciSiwfStorageType
      StorageType,
   mscFrAtmDlciSiwfIndex
      NonReplicated }

mscFrAtmDlciSiwfRowStatus OBJECT-TYPE
   SYNTAX     RowStatus 
   ACCESS     read-write
   STATUS     mandatory
   DESCRIPTION
     "This variable is used as the basis for SNMP naming of
      mscFrAtmDlciSiwf components.
      These components can be added and deleted."
::= { mscFrAtmDlciSiwfRowStatusEntry 1 }

mscFrAtmDlciSiwfComponentName OBJECT-TYPE
   SYNTAX     DisplayString 
   ACCESS     read-only
   STATUS     mandatory
   DESCRIPTION
     "This variable provides the component's string name for
      use with the ASCII Console Interface"
::= { mscFrAtmDlciSiwfRowStatusEntry 2 }

mscFrAtmDlciSiwfStorageType OBJECT-TYPE
   SYNTAX     StorageType 
   ACCESS     read-only
   STATUS     mandatory
   DESCRIPTION
     "This variable represents the storage type value for the
      mscFrAtmDlciSiwf tables."
::= { mscFrAtmDlciSiwfRowStatusEntry 4 }

mscFrAtmDlciSiwfIndex OBJECT-TYPE
   SYNTAX     NonReplicated 
   ACCESS     not-accessible
   STATUS     mandatory
   DESCRIPTION
     "This variable represents the index for the mscFrAtmDlciSiwf tables."
::= { mscFrAtmDlciSiwfRowStatusEntry 10 }

mscFrAtmDlciSiwfConnOpTable OBJECT-TYPE
   SYNTAX     SEQUENCE OF MscFrAtmDlciSiwfConnOpEntry
   ACCESS     not-accessible
   STATUS     mandatory
   DESCRIPTION
     "This group contains operational attributes for the ATM connection."
::= { mscFrAtmDlciSiwf 11 }

mscFrAtmDlciSiwfConnOpEntry OBJECT-TYPE
   SYNTAX     MscFrAtmDlciSiwfConnOpEntry
   ACCESS     not-accessible
   STATUS     mandatory
   DESCRIPTION
     "An entry in the mscFrAtmDlciSiwfConnOpTable."
   INDEX {
      mscFrAtmIndex,
      mscFrAtmDlciIndex,
      mscFrAtmDlciSiwfIndex }
::= { mscFrAtmDlciSiwfConnOpTable 1 }

MscFrAtmDlciSiwfConnOpEntry ::= SEQUENCE {
   mscFrAtmDlciSiwfDiscardPriority
      INTEGER,
   mscFrAtmDlciSiwfAtmServiceCategory
      INTEGER,
   mscFrAtmDlciSiwfTrafficParmConvPolicy
      INTEGER,
   mscFrAtmDlciSiwfAvgFrameSize
      INTEGER,
   mscFrAtmDlciSiwfRemoteAddress
      AsciiString,
   mscFrAtmDlciSiwfRemoteConnectionIdentifier
      IntegerSequence }

mscFrAtmDlciSiwfDiscardPriority OBJECT-TYPE
   SYNTAX     INTEGER  {
                 dp1(1),
                 dp2(2),
                 dp3(3) }
   ACCESS     read-only
   STATUS     mandatory
   DESCRIPTION
     "This attribute indicates the discard priority of frames sent to and 
      received from the ATM connection.
      
      When discardPriority is dp3 the frames belonging to this 
      connection will be discarded first when the FrAtm/n Dlci/n Siwf and 
      the ATM End-Point experience congestion.
      
      When discardPriority is dp2 the frames belonging to this 
      connection will be discarded after all the dp3 priority frames are 
      discarded when the FrAtm/n Dlci/n Siwf and the ATM End-Point 
      experience congestion.
      
      When discardPriority is dp1 the frames belonging to this 
      connection will be discarded after all the dp2 and dp3 priority 
      frames are discarded when the FrAtm/n Dlci/n Siwf and the ATM 
      End-Point experience congestion."
::= { mscFrAtmDlciSiwfConnOpEntry 2 }

mscFrAtmDlciSiwfAtmServiceCategory OBJECT-TYPE
   SYNTAX     INTEGER  {
                 ubr(0),
                 cbr(1),
                 rtVbr(2),
                 nrtVbr(3),
                 notApplicable(5) }
   ACCESS     read-only
   STATUS     mandatory
   DESCRIPTION
     "This attribute indicates the ATM service category that is used for 
      this connection. This attribute is only displayed for SPVCs."
::= { mscFrAtmDlciSiwfConnOpEntry 4 }

mscFrAtmDlciSiwfTrafficParmConvPolicy OBJECT-TYPE
   SYNTAX     INTEGER  {
                 n3(3),
                 n4(4),
                 n5(5),
                 n6(6),
                 notApplicable(7) }
   ACCESS     read-only
   STATUS     mandatory
   DESCRIPTION
     "This attribute indicates the traffic parameter conversion policy that 
      is being used for this connection. 
      
      For Npvcs, this attribute is not displayed.
      
      Policy 3 characterizes the traffic in the following way:
      - ATM traffic descriptor type 6 is selected
      - ATM service category rtVbr and nrtVbr supported only
      - PCR0+1 is based on AR
      - SCR0+1 is based on CIR and EIR
      - MBS0+1 is based on Bc, Be, CIR, EIR and AR
      - Takes into account that the instantaneous rate of the frame relay 
      stream can be above CIR and up to the AR.
      
      Policy 4 characterizes the traffic in the following way:
      - ATM traffic descriptor type 7 or 8 is selected. Type 7 is chosen 
      when non-conforming cells are to be discarded and type 8 when 
      non-conforming cells are tagged by UPC traffic policer.
      - PCR0+1 is based on AR
      - SCR0 is based on CIR
      - MBS0 is based on Bc, CIR, and AR
      - There is no direct characterization of EIR. The allowed EIR can be 
      derived using the difference between the AR and CIR.
      
      Policy 5 characterizes the traffic in the following way:
      - ATM traffic descriptor type 7 or 8 is selected. Type 7 is chosen 
      when non-conforming cells are to be discarded and type 8 when 
      non-conforming cells are tagged by UPC traffic policer
      - ATM service category rtVbr and nrtVbr supported only
      - PCR0+1 is based on CIR and EIR
      - SCR0 is based on the CIR
      - MBS0 is based on the CIR
      - The maximum PCR is no longer based on the AR but rather on the 
      CIR and EIR or CIR.
      
      Policy 6 characterizes the traffic in the following way:
      - ATM traffic descriptor type 3 is selected
      - ATM service category ubr, cbr, rtVbr and nrtVbr supported only
      - PCR0+1 is based only on CIR.
      DESCRIPTION"
::= { mscFrAtmDlciSiwfConnOpEntry 5 }

mscFrAtmDlciSiwfAvgFrameSize OBJECT-TYPE
   SYNTAX     INTEGER (0..8187)
   ACCESS     read-only
   STATUS     mandatory
   DESCRIPTION
     "This attribute indicates the average frame size that is used for this 
      connection as part of the traffic parameter conversion policy.
      Average frame size is not applicable for Npvcs, and therefore it is 
      not displayed."
::= { mscFrAtmDlciSiwfConnOpEntry 6 }

mscFrAtmDlciSiwfRemoteAddress OBJECT-TYPE
   SYNTAX     AsciiString (SIZE (1..44))
   ACCESS     read-only
   STATUS     mandatory
   DESCRIPTION
     "This attribute indicates the remote address (native E.164, native 
      X.121 or NSAP) for this connection. This attribute is only displayed 
      for SPVCs."
::= { mscFrAtmDlciSiwfConnOpEntry 8 }

mscFrAtmDlciSiwfRemoteConnectionIdentifier OBJECT-TYPE
   SYNTAX     IntegerSequence (SIZE (3..9))
   ACCESS     read-only
   STATUS     mandatory
   DESCRIPTION
     "This attribute indicates the remote connection identifier. This 
      identifier is either a remote Atm Vpi.Vci logical channel number or a 
      remote Frame Relay Dlci logical channel number. The remote Atm 
      Vpi.Vci logical channel number is displayed as 'Vpi.Vci'. and the 
      remote Frame Relay Dlci logical channel number is displayed as 
      '0.remoteDlci'.
      For NPVCs, this attribute is not displayed."
::= { mscFrAtmDlciSiwfConnOpEntry 9 }

mscFrAtmDlciSiwfSdOpTable OBJECT-TYPE
   SYNTAX     SEQUENCE OF MscFrAtmDlciSiwfSdOpEntry
   ACCESS     not-accessible
   STATUS     mandatory
   DESCRIPTION
     "This group contains operational information for a Siwf component."
::= { mscFrAtmDlciSiwf 12 }

mscFrAtmDlciSiwfSdOpEntry OBJECT-TYPE
   SYNTAX     MscFrAtmDlciSiwfSdOpEntry
   ACCESS     not-accessible
   STATUS     mandatory
   DESCRIPTION
     "An entry in the mscFrAtmDlciSiwfSdOpTable."
   INDEX {
      mscFrAtmIndex,
      mscFrAtmDlciIndex,
      mscFrAtmDlciSiwfIndex }
::= { mscFrAtmDlciSiwfSdOpTable 1 }

MscFrAtmDlciSiwfSdOpEntry ::= SEQUENCE {
   mscFrAtmDlciSiwfMode
      INTEGER,
   mscFrAtmDlciSiwfDeToClpMapping
      INTEGER,
   mscFrAtmDlciSiwfClpToDeMapping
      INTEGER,
   mscFrAtmDlciSiwfFecnToEfciMapping
      INTEGER,
   mscFrAtmDlciSiwfCrToUuMapping
      INTEGER,
   mscFrAtmDlciSiwfTransferPriority
      INTEGER,
   mscFrAtmDlciSiwfAssignedBandwidthPool
      INTEGER }

mscFrAtmDlciSiwfMode OBJECT-TYPE
   SYNTAX     INTEGER  {
                 translationMode(0),
                 transparentMode(1),
                 speTranslationMode(2) }
   ACCESS     read-only
   STATUS     mandatory
   DESCRIPTION
     "This attribute indicates the mode of interoperability between the 
      Frame Relay and ATM connections regarding upper layer protocol 
      encapsulations.
      
      A value of translationMode indicates that the interworking function 
      performs translation between RFC 1490 and RFC 1483 
      encapsulated headers, including routed protocol translation, bridged 
      protocol translation, and connection oriented protocol translation 
      (except for RFC 1490 connection oriented protocol without RFC 
      1490 header, which is done in speTranslationMode).
      
      A value of transparentMode indicates that the interworking 
      function forwards data without altering the upper layer user 
      protocol encapsulation. Transparent mode is selected when the 
      upper layer user protocol encapsulation methods are compatible 
      between terminal equipments.
      
      A value of speTranslationMode indicates that the interworking 
      function performs single protocol translation between RFC 1490 
      with no header and RFC 1483 encapsulated packets."
::= { mscFrAtmDlciSiwfSdOpEntry 1 }

mscFrAtmDlciSiwfDeToClpMapping OBJECT-TYPE
   SYNTAX     INTEGER  {
                 always0(0),
                 always1(1),
                 preserve(2) }
   ACCESS     read-only
   STATUS     mandatory
   DESCRIPTION
     "This attribute indicates the type of DE to CLP mapping that is 
      performed in the Frame Relay to ATM direction.
      
      A value of preserve indicates that the DE field in a Q.922 core 
      frame is copied to the ATM CLP field of every cell containing the 
      information of that frame.
      
      A value of always0 indicates that the CLP field of every generated 
      ATM cell is always 0.
      
      A value of always1 indicates that the CLP field of every generated 
      ATM cell is always1."
::= { mscFrAtmDlciSiwfSdOpEntry 2 }

mscFrAtmDlciSiwfClpToDeMapping OBJECT-TYPE
   SYNTAX     INTEGER  {
                 always0(0),
                 always1(1),
                 preserve(2) }
   ACCESS     read-only
   STATUS     mandatory
   DESCRIPTION
     "This attribute indicates the type of CLP to DE mapping that is 
      performed in the ATM to Frame Relay direction.
      
      A value of preserve indicates that the DE field of the Q.922 Core 
      frame is set when one or more ATM cells belonging to an AAL5 
      frame have their CLP field set.
      
      A value of always0 indicates that the DE field of the Q.922 Core 
      frame is always set to 0.
      
      A value of always1 indicates that the DE field of the Q.922 Core 
      frame is always set to 1."
::= { mscFrAtmDlciSiwfSdOpEntry 3 }

mscFrAtmDlciSiwfFecnToEfciMapping OBJECT-TYPE
   SYNTAX     INTEGER  {
                 always0(0),
                 preserve(2) }
   ACCESS     read-only
   STATUS     mandatory
   DESCRIPTION
     "This attribute indicates the type of FECN to EFCI mapping that is 
      performed in the Frame Relay to ATM direction.
      
      A value of preserve indicates that the FECN field in a Q.922 Core 
      frame is copied directly to the ATM EFCI field of every cell.
      
      A value of always0 indicates that the EFCI field in every ATM cell 
      generated is set to 0."
::= { mscFrAtmDlciSiwfSdOpEntry 4 }

mscFrAtmDlciSiwfCrToUuMapping OBJECT-TYPE
   SYNTAX     INTEGER  {
                 always0(0),
                 preserve(2) }
   ACCESS     read-only
   STATUS     obsolete
   DESCRIPTION
     "This attribute indicates the type of CR to UU mapping that is 
      performed in the Frame Relay to ATM direction.
      
      A value of preserve indicates that the CR field in the Q.922 Core 
      frame is mapped directly to the ATM UU field of every cell 
      generated by the AAL5 segmentation process.
      
      A value of always0 indicates that the UU field in every ATM cell 
      generated is set to 0."
   DEFVAL     { preserve }
::= { mscFrAtmDlciSiwfSdOpEntry 5 }

mscFrAtmDlciSiwfTransferPriority OBJECT-TYPE
   SYNTAX     INTEGER  {
                 n0(0),
                 n1(1),
                 n2(2),
                 n3(3),
                 n4(4),
                 n5(5),
                 n6(6),
                 n7(7),
                 n8(8),
                 n9(9),
                 n10(10),
                 n11(11),
                 n12(12),
                 n13(13),
                 n14(14),
                 n15(15),
                 notApplicable(253) }
   ACCESS     read-only
   STATUS     mandatory
   DESCRIPTION
     "This attribute indicates the transfer priority used to establish the 
      connection. 
      For Npvcs, the value is notApplicable."
::= { mscFrAtmDlciSiwfSdOpEntry 6 }

mscFrAtmDlciSiwfAssignedBandwidthPool OBJECT-TYPE
   SYNTAX     INTEGER  {
                 n0(0),
                 n1(1),
                 n2(2),
                 n3(3),
                 n4(4),
                 n5(5),
                 n6(6),
                 n7(7),
                 n8(8),
                 n9(9),
                 n10(10),
                 n11(11),
                 n12(12),
                 n13(13),
                 n14(14),
                 n15(15) }
   ACCESS     read-only
   STATUS     mandatory
   DESCRIPTION
     "This attribute specifies the bandwidth pool that this Dlci uses."
::= { mscFrAtmDlciSiwfSdOpEntry 7 }

mscFrAtmDlciSiwfSiwfSpvcOpTable OBJECT-TYPE
   SYNTAX     SEQUENCE OF MscFrAtmDlciSiwfSiwfSpvcOpEntry
   ACCESS     not-accessible
   STATUS     mandatory
   DESCRIPTION
     "This group contains operational attributes for the FrAtm Dlci Siwf 
      Spvc connection."
::= { mscFrAtmDlciSiwf 13 }

mscFrAtmDlciSiwfSiwfSpvcOpEntry OBJECT-TYPE
   SYNTAX     MscFrAtmDlciSiwfSiwfSpvcOpEntry
   ACCESS     not-accessible
   STATUS     mandatory
   DESCRIPTION
     "An entry in the mscFrAtmDlciSiwfSiwfSpvcOpTable."
   INDEX {
      mscFrAtmIndex,
      mscFrAtmDlciIndex,
      mscFrAtmDlciSiwfIndex }
::= { mscFrAtmDlciSiwfSiwfSpvcOpTable 1 }

MscFrAtmDlciSiwfSiwfSpvcOpEntry ::= SEQUENCE {
   mscFrAtmDlciSiwfPeakCellRate0
      Unsigned32,
   mscFrAtmDlciSiwfPeakCellRate01
      Unsigned32,
   mscFrAtmDlciSiwfSustainedCellRate0
      Unsigned32,
   mscFrAtmDlciSiwfSustainedCellRate01
      Unsigned32,
   mscFrAtmDlciSiwfMaximumBurstSize0
      Unsigned32,
   mscFrAtmDlciSiwfMaximumBurstSize01
      Unsigned32,
   mscFrAtmDlciSiwfEquivalentBitRate
      Unsigned32,
   mscFrAtmDlciSiwfType
      INTEGER,
   mscFrAtmDlciSiwfVccClearCause
      Unsigned32,
   mscFrAtmDlciSiwfVccCauseDiag
      HexString }

mscFrAtmDlciSiwfPeakCellRate0 OBJECT-TYPE
   SYNTAX     Unsigned32 (0..4294967295)
   ACCESS     read-only
   STATUS     mandatory
   DESCRIPTION
     "This attribute indicates the Peak Cell Rate (PCR) of the ATM VCC 
      to which this interworking function is linked for all cells (with 
      CLP=0 and CLP=1).
      
      The pcr0 is derived from the remote end traffic parameters using the 
      conversion policy of the transferPriorityMapping.
      
      For NPVCs, this attribute is not displayed."
::= { mscFrAtmDlciSiwfSiwfSpvcOpEntry 1 }

mscFrAtmDlciSiwfPeakCellRate01 OBJECT-TYPE
   SYNTAX     Unsigned32 (0..4294967295)
   ACCESS     read-only
   STATUS     mandatory
   DESCRIPTION
     "This attribute indicates the Peak Cell Rate (PCR) of the ATM VCC 
      to which this interworking function is linked for all cells (with 
      CLP=0 and CLP=1).
      
      The pcr01 is derived from the remote end traffic parameters using 
      the conversion policy of the transferPriorityMapping.
      
      For NPVCs, this attribute is not displayed."
::= { mscFrAtmDlciSiwfSiwfSpvcOpEntry 2 }

mscFrAtmDlciSiwfSustainedCellRate0 OBJECT-TYPE
   SYNTAX     Unsigned32 (0..4294967295)
   ACCESS     read-only
   STATUS     mandatory
   DESCRIPTION
     "This attribute indicates the Sustained Cell Rate (SCR) of the ATM 
      VCC to which this interworking function is linked for high priority 
      cells (with CLP=0).
      
      The scr0 is derived from the remote end traffic parameters using the 
      conversion policy of the transferPriorityMapping.
      
      For NPVCs, this attribute is not displayed."
::= { mscFrAtmDlciSiwfSiwfSpvcOpEntry 3 }

mscFrAtmDlciSiwfSustainedCellRate01 OBJECT-TYPE
   SYNTAX     Unsigned32 (0..4294967295)
   ACCESS     read-only
   STATUS     mandatory
   DESCRIPTION
     "This attribute indicates the Sustained Cell Rate (SCR) of the ATM 
      VCC that to which this interworking function is linked for all cells 
      (with CLP=0 and CLP=1).
      
      The scr01 is derived from the remote end traffic parameters using 
      the conversion policy of the transferPriorityMapping.
      
      For NPVCs, this attribute is not displayed."
::= { mscFrAtmDlciSiwfSiwfSpvcOpEntry 4 }

mscFrAtmDlciSiwfMaximumBurstSize0 OBJECT-TYPE
   SYNTAX     Unsigned32 (0..4294967295)
   ACCESS     read-only
   STATUS     mandatory
   DESCRIPTION
     "This attribute indicates the Maximum Burst Size (MBS) of the 
      ATM VCC to which this interworking function is linked for high 
      priority cells (with CLP=0).
      
      The mbs0 is derived from the remote end traffic parameters using 
      the conversion policy of the transferPriorityMapping.
      
      For NPVCs, this attribute is not displayed."
::= { mscFrAtmDlciSiwfSiwfSpvcOpEntry 5 }

mscFrAtmDlciSiwfMaximumBurstSize01 OBJECT-TYPE
   SYNTAX     Unsigned32 (0..4294967295)
   ACCESS     read-only
   STATUS     mandatory
   DESCRIPTION
     "This attribute indicates the Maximum Burst Size (MBS) of the 
      ATM VCC to which this interworking function is linked for all cells 
      (with CLP=0 and CLP=1).
      
      The mbs01 is derived from the remote end traffic parameters using 
      the conversion policy of the transferPriorityMapping.
      
      For NPVCs, this attribute is not displayed."
::= { mscFrAtmDlciSiwfSiwfSpvcOpEntry 6 }

mscFrAtmDlciSiwfEquivalentBitRate OBJECT-TYPE
   SYNTAX     Unsigned32 (0..4294967295)
   ACCESS     read-only
   STATUS     mandatory
   DESCRIPTION
     "This attribute indicates the access reserved bandwidth for this FR-
      ATM connection when CAC is on. If a connection is subcribed to 
      CIR only or CIR plus EIR service, the EBR reserved is CIR. If a 
      connection is subcribed to EIR only service, the EBR reserved is 0."
::= { mscFrAtmDlciSiwfSiwfSpvcOpEntry 7 }

mscFrAtmDlciSiwfType OBJECT-TYPE
   SYNTAX     INTEGER  {
                 master(0),
                 slave(1),
                 notApplicable(2) }
   ACCESS     read-only
   STATUS     mandatory
   DESCRIPTION
     "This attribute indicates if the component provisioned is a calling or 
      called end. If the value is master, the Dlci Siwf Spvc component is 
      provisioned as a calling end and is responsible for originating the 
      call to set up the ATM VCC. If the value is slave, this Dlci Siwf 
      component is provisioned as a called end and is responsible for 
      terminating call setup requests from the remote end. This attribute is 
      not displayed for NPVCs."
::= { mscFrAtmDlciSiwfSiwfSpvcOpEntry 9 }

mscFrAtmDlciSiwfVccClearCause OBJECT-TYPE
   SYNTAX     Unsigned32 (0..255)
   ACCESS     read-only
   STATUS     mandatory
   DESCRIPTION
     "This attribute indicates the last received clear cause message from 
      the network. This attribute is not displayed for NPVCs.
      
      Please refer to ATM User-Network Interface Specification for 
      possible clear causes."
::= { mscFrAtmDlciSiwfSiwfSpvcOpEntry 10 }

mscFrAtmDlciSiwfVccCauseDiag OBJECT-TYPE
   SYNTAX     HexString (SIZE (1..8))
   ACCESS     read-only
   STATUS     mandatory
   DESCRIPTION
     "This attribute indicates the diagnostic value of the last release 
      message received from the network. This attribute is not displayed 
      for NPVCs.
      
      Please refer to ATM User-Network Interface Specification for 
      possible diagnostic values."
::= { mscFrAtmDlciSiwfSiwfSpvcOpEntry 15 }

mscFrAtmDlciSiwfStatsTable OBJECT-TYPE
   SYNTAX     SEQUENCE OF MscFrAtmDlciSiwfStatsEntry
   ACCESS     not-accessible
   STATUS     mandatory
   DESCRIPTION
     "This group contains statistics for the Siwf component."
::= { mscFrAtmDlciSiwf 14 }

mscFrAtmDlciSiwfStatsEntry OBJECT-TYPE
   SYNTAX     MscFrAtmDlciSiwfStatsEntry
   ACCESS     not-accessible
   STATUS     mandatory
   DESCRIPTION
     "An entry in the mscFrAtmDlciSiwfStatsTable."
   INDEX {
      mscFrAtmIndex,
      mscFrAtmDlciIndex,
      mscFrAtmDlciSiwfIndex }
::= { mscFrAtmDlciSiwfStatsTable 1 }

MscFrAtmDlciSiwfStatsEntry ::= SEQUENCE {
   mscFrAtmDlciSiwfUnknown1490Frames
      Counter32,
   mscFrAtmDlciSiwfInvalid1490Frames
      Counter32,
   mscFrAtmDlciSiwfLastUnknown1490ProtocolHeader
      HexString,
   mscFrAtmDlciSiwfUnknown1483Frames
      Counter32,
   mscFrAtmDlciSiwfInvalid1483Frames
      Counter32,
   mscFrAtmDlciSiwfLastUnknown1483ProtocolHeader
      HexString }

mscFrAtmDlciSiwfUnknown1490Frames OBJECT-TYPE
   SYNTAX     Counter32 
   ACCESS     read-only
   STATUS     mandatory
   DESCRIPTION
     "This attribute counts the number of frames received from the 
      interface that have a frame header that is not recognized by the RFC 
      1490. 
      
      When the maximum count is reached, it wraps to zero."
::= { mscFrAtmDlciSiwfStatsEntry 1 }

mscFrAtmDlciSiwfInvalid1490Frames OBJECT-TYPE
   SYNTAX     Counter32 
   ACCESS     read-only
   STATUS     mandatory
   DESCRIPTION
     "This attribute counts the number of frames received from the 
      interface that have an invalid frame header. An invalid frame header 
      occurs when the frame has less than the expected number of bytes. 
      
      When the maximum count is reached, the count wraps to zero."
::= { mscFrAtmDlciSiwfStatsEntry 2 }

mscFrAtmDlciSiwfLastUnknown1490ProtocolHeader OBJECT-TYPE
   SYNTAX     HexString (SIZE (1..8))
   ACCESS     read-only
   STATUS     mandatory
   DESCRIPTION
     "This attribute contains the most recent unrecognized protocol 
      header that was received from the interface. 
      
      All the RFC 1490 protocols described in sections 5.3.1.1 through 
      5.3.1.3 of FRF.8 are supported, except ARP is not supported."
::= { mscFrAtmDlciSiwfStatsEntry 3 }

mscFrAtmDlciSiwfUnknown1483Frames OBJECT-TYPE
   SYNTAX     Counter32 
   ACCESS     read-only
   STATUS     mandatory
   DESCRIPTION
     "This attribute counts the number of frames received from the ATM 
      connection that have a frame header that is not recognized by the 
      RFC 1483. 
      
      When the maximum count is reached, it wraps to zero."
::= { mscFrAtmDlciSiwfStatsEntry 4 }

mscFrAtmDlciSiwfInvalid1483Frames OBJECT-TYPE
   SYNTAX     Counter32 
   ACCESS     read-only
   STATUS     mandatory
   DESCRIPTION
     "This attribute counts the number of frames received from the ATM 
      connection that have an invalid frame header. An invalid frame 
      header occurs when the frame has less than the expected number of 
      bytes. 
      
      When the maximum count is reached, it wraps to zero."
::= { mscFrAtmDlciSiwfStatsEntry 5 }

mscFrAtmDlciSiwfLastUnknown1483ProtocolHeader OBJECT-TYPE
   SYNTAX     HexString (SIZE (1..8))
   ACCESS     read-only
   STATUS     mandatory
   DESCRIPTION
     "This attribute identifies the most recent unrecognized protocol 
      header that was received from the ATM connection.
      
      All the RFC 1483 protocols described in sections 5.3.1.1 through 
      5.3.1.3 of FRF.8 are supported except ARP."
::= { mscFrAtmDlciSiwfStatsEntry 6 }


-- FrAtm/n Dlci/n Siwf ServiceDescriptor
-- The Sd component contains provisioning information for its parent 
-- Siwf component. It is a required component when Npvc is 
-- provisioned. In the case of Spvc, if this component is not 
-- provisioned, the connection will use the provisioning information 
-- from the FrAtm Ca component.

mscFrAtmDlciSiwfSd OBJECT IDENTIFIER ::= { mscFrAtmDlciSiwf 2 }



mscFrAtmDlciSiwfSdRowStatusTable OBJECT-TYPE
   SYNTAX     SEQUENCE OF MscFrAtmDlciSiwfSdRowStatusEntry
   ACCESS     not-accessible
   STATUS     mandatory
   DESCRIPTION
     "This entry controls the addition and deletion of 
      mscFrAtmDlciSiwfSd components."
::= { mscFrAtmDlciSiwfSd 1 }

mscFrAtmDlciSiwfSdRowStatusEntry OBJECT-TYPE
   SYNTAX     MscFrAtmDlciSiwfSdRowStatusEntry
   ACCESS     not-accessible
   STATUS     mandatory
   DESCRIPTION
     "A single entry in the table represents a single 
      mscFrAtmDlciSiwfSd component."
   INDEX {
      mscFrAtmIndex,
      mscFrAtmDlciIndex,
      mscFrAtmDlciSiwfIndex,
      mscFrAtmDlciSiwfSdIndex }
::= { mscFrAtmDlciSiwfSdRowStatusTable 1 }

MscFrAtmDlciSiwfSdRowStatusEntry ::= SEQUENCE {
   mscFrAtmDlciSiwfSdRowStatus
      RowStatus,
   mscFrAtmDlciSiwfSdComponentName
      DisplayString,
   mscFrAtmDlciSiwfSdStorageType
      StorageType,
   mscFrAtmDlciSiwfSdIndex
      NonReplicated }

mscFrAtmDlciSiwfSdRowStatus OBJECT-TYPE
   SYNTAX     RowStatus 
   ACCESS     read-write
   STATUS     mandatory
   DESCRIPTION
     "This variable is used as the basis for SNMP naming of
      mscFrAtmDlciSiwfSd components.
      These components can be added and deleted."
::= { mscFrAtmDlciSiwfSdRowStatusEntry 1 }

mscFrAtmDlciSiwfSdComponentName OBJECT-TYPE
   SYNTAX     DisplayString 
   ACCESS     read-only
   STATUS     mandatory
   DESCRIPTION
     "This variable provides the component's string name for
      use with the ASCII Console Interface"
::= { mscFrAtmDlciSiwfSdRowStatusEntry 2 }

mscFrAtmDlciSiwfSdStorageType OBJECT-TYPE
   SYNTAX     StorageType 
   ACCESS     read-only
   STATUS     mandatory
   DESCRIPTION
     "This variable represents the storage type value for the
      mscFrAtmDlciSiwfSd tables."
::= { mscFrAtmDlciSiwfSdRowStatusEntry 4 }

mscFrAtmDlciSiwfSdIndex OBJECT-TYPE
   SYNTAX     NonReplicated 
   ACCESS     not-accessible
   STATUS     mandatory
   DESCRIPTION
     "This variable represents the index for the mscFrAtmDlciSiwfSd tables."
::= { mscFrAtmDlciSiwfSdRowStatusEntry 10 }

mscFrAtmDlciSiwfSdProvTable OBJECT-TYPE
   SYNTAX     SEQUENCE OF MscFrAtmDlciSiwfSdProvEntry
   ACCESS     not-accessible
   STATUS     mandatory
   DESCRIPTION
     "This group contains provisionable attributes for the parent Siwf 
      component."
::= { mscFrAtmDlciSiwfSd 10 }

mscFrAtmDlciSiwfSdProvEntry OBJECT-TYPE
   SYNTAX     MscFrAtmDlciSiwfSdProvEntry
   ACCESS     not-accessible
   STATUS     mandatory
   DESCRIPTION
     "An entry in the mscFrAtmDlciSiwfSdProvTable."
   INDEX {
      mscFrAtmIndex,
      mscFrAtmDlciIndex,
      mscFrAtmDlciSiwfIndex,
      mscFrAtmDlciSiwfSdIndex }
::= { mscFrAtmDlciSiwfSdProvTable 1 }

MscFrAtmDlciSiwfSdProvEntry ::= SEQUENCE {
   mscFrAtmDlciSiwfSdMode
      INTEGER,
   mscFrAtmDlciSiwfSdDeToClpMapping
      INTEGER,
   mscFrAtmDlciSiwfSdClpToDeMapping
      INTEGER,
   mscFrAtmDlciSiwfSdFecnToEfciMapping
      INTEGER,
   mscFrAtmDlciSiwfSdCrToUuMapping
      INTEGER }

mscFrAtmDlciSiwfSdMode OBJECT-TYPE
   SYNTAX     INTEGER  {
                 translationMode(0),
                 transparentMode(1),
                 speTranslationMode(2),
                 sameAsInterface(255) }
   ACCESS     read-write
   STATUS     mandatory
   DESCRIPTION
     "This attribute specifies the mode of interoperability between the 
      Frame Relay and ATM connections regarding upper layer protocol 
      encapsulations.
      
      When translationMode is selected, the interworking function 
      performs translations between RFC 1490 and RFC 1483 
      encapsulated headers, including routed protocol translation, bridged 
      protocol translation, and connection oriented protocol translation 
      (except for RFC 1490 connection oriented protocol without RFC 
      1490 header, which is done in speTranslationMode). 
      
      A value of transparentMode indicates that the interworking 
      function forwards data without altering the upper layer user 
      protocol encapsulation. Transparent mode is selected when the 
      upper layer user protocol encapsulation methods are compatible 
      between terminal equipments.
      
      A value of speTranslationMode indicates that the interworking 
      function performs single protocol translation between RFC 1490 
      with no header and RFC 1483 encapsulated packets.
      
      The default value is sameAsInterface, which means as defined in 
      FrAtm/n Ca sdMode."
   DEFVAL     { sameAsInterface }
::= { mscFrAtmDlciSiwfSdProvEntry 1 }

mscFrAtmDlciSiwfSdDeToClpMapping OBJECT-TYPE
   SYNTAX     INTEGER  {
                 always0(0),
                 always1(1),
                 preserve(2),
                 sameAsInterface(255) }
   ACCESS     read-write
   STATUS     mandatory
   DESCRIPTION
     "This attribute specifies the DE to CLP mapping that is performed in 
      the Frame Relay to ATM direction.
      
      When preserve is selected, the DE field in the Q.922 core frame is 
      mapped to the ATM CLP field of every cell generated by the 
      segmentation process of the AAL5 PDU containing the information 
      of that frame.
      
      When always0 is selected, the CLP field of every ATM cell 
      generated by the segmentation process of the AAL5 PDU 
      containing the information of that frame is always set to 0.
      
      When always1 is selected, the CLP field of every ATM cell 
      generated by the segmentation process of the AAL5 PDU 
      containing the information of that frame is always set to 1."
   DEFVAL     { sameAsInterface }
::= { mscFrAtmDlciSiwfSdProvEntry 2 }

mscFrAtmDlciSiwfSdClpToDeMapping OBJECT-TYPE
   SYNTAX     INTEGER  {
                 always0(0),
                 always1(1),
                 preserve(2),
                 sameAsInterface(255) }
   ACCESS     read-write
   STATUS     mandatory
   DESCRIPTION
     "This attribute specifies the type of CLP to DE mapping that is 
      performed in the ATM to Frame Relay to direction.
      
      When preserve is selected, the DE field of the Q.922 Core frame is 
      set when one or more ATM cells belonging to an AAL5 frame have 
      their CLP field set.
      
      When always0 is selected, the DE field of the Q.922 Core frame is 
      always set to 0.
      
      When always1 is selected, the DE field of the Q.922 Core frame is 
      always set to 1."
   DEFVAL     { sameAsInterface }
::= { mscFrAtmDlciSiwfSdProvEntry 3 }

mscFrAtmDlciSiwfSdFecnToEfciMapping OBJECT-TYPE
   SYNTAX     INTEGER  {
                 always0(0),
                 preserve(2),
                 sameAsInterface(255) }
   ACCESS     read-write
   STATUS     mandatory
   DESCRIPTION
     "This attribute specifies the type of FECN to EFCI mapping that is 
      performed in the Frame Relay to ATM direction.
      
      When preserve is selected, the FECN field in the Q.922 Core frame 
      is mapped directly to the ATM EFCI field of every cell generated by 
      the AAL5 segmentation process.
      
      When always0 is selected, the EFCI field in every ATM cell 
      generated is set to 0."
   DEFVAL     { sameAsInterface }
::= { mscFrAtmDlciSiwfSdProvEntry 4 }

mscFrAtmDlciSiwfSdCrToUuMapping OBJECT-TYPE
   SYNTAX     INTEGER  {
                 always0(0),
                 preserve(2),
                 sameAsInterface(255) }
   ACCESS     read-write
   STATUS     obsolete
   DESCRIPTION
     "This attribute indicates the type of CR to UU mapping that is 
      performed in the Frame Relay to ATM direction.
      
      A value of preserve indicates that the CR field in the Q.922 Core 
      frame is mapped directly to the ATM UU field of every cell 
      generated by the AAL5 segmentation process.
      
      A value of always0 indicates that the UU field in every ATM cell 
      generated is set to 0."
   DEFVAL     { sameAsInterface }
::= { mscFrAtmDlciSiwfSdProvEntry 5 }


-- FrAtm/n Dlci/n Siwf NailedUpPvc
-- This component associates an interworking function with an ATM 
-- connection.

mscFrAtmDlciSiwfNPvc OBJECT IDENTIFIER ::= { mscFrAtmDlciSiwf 3 }



mscFrAtmDlciSiwfNPvcRowStatusTable OBJECT-TYPE
   SYNTAX     SEQUENCE OF MscFrAtmDlciSiwfNPvcRowStatusEntry
   ACCESS     not-accessible
   STATUS     mandatory
   DESCRIPTION
     "This entry controls the addition and deletion of 
      mscFrAtmDlciSiwfNPvc components."
::= { mscFrAtmDlciSiwfNPvc 1 }

mscFrAtmDlciSiwfNPvcRowStatusEntry OBJECT-TYPE
   SYNTAX     MscFrAtmDlciSiwfNPvcRowStatusEntry
   ACCESS     not-accessible
   STATUS     mandatory
   DESCRIPTION
     "A single entry in the table represents a single 
      mscFrAtmDlciSiwfNPvc component."
   INDEX {
      mscFrAtmIndex,
      mscFrAtmDlciIndex,
      mscFrAtmDlciSiwfIndex,
      mscFrAtmDlciSiwfNPvcIndex }
::= { mscFrAtmDlciSiwfNPvcRowStatusTable 1 }

MscFrAtmDlciSiwfNPvcRowStatusEntry ::= SEQUENCE {
   mscFrAtmDlciSiwfNPvcRowStatus
      RowStatus,
   mscFrAtmDlciSiwfNPvcComponentName
      DisplayString,
   mscFrAtmDlciSiwfNPvcStorageType
      StorageType,
   mscFrAtmDlciSiwfNPvcIndex
      NonReplicated }

mscFrAtmDlciSiwfNPvcRowStatus OBJECT-TYPE
   SYNTAX     RowStatus 
   ACCESS     read-write
   STATUS     mandatory
   DESCRIPTION
     "This variable is used as the basis for SNMP naming of
      mscFrAtmDlciSiwfNPvc components.
      These components can be added and deleted."
::= { mscFrAtmDlciSiwfNPvcRowStatusEntry 1 }

mscFrAtmDlciSiwfNPvcComponentName OBJECT-TYPE
   SYNTAX     DisplayString 
   ACCESS     read-only
   STATUS     mandatory
   DESCRIPTION
     "This variable provides the component's string name for
      use with the ASCII Console Interface"
::= { mscFrAtmDlciSiwfNPvcRowStatusEntry 2 }

mscFrAtmDlciSiwfNPvcStorageType OBJECT-TYPE
   SYNTAX     StorageType 
   ACCESS     read-only
   STATUS     mandatory
   DESCRIPTION
     "This variable represents the storage type value for the
      mscFrAtmDlciSiwfNPvc tables."
::= { mscFrAtmDlciSiwfNPvcRowStatusEntry 4 }

mscFrAtmDlciSiwfNPvcIndex OBJECT-TYPE
   SYNTAX     NonReplicated 
   ACCESS     not-accessible
   STATUS     mandatory
   DESCRIPTION
     "This variable represents the index for the mscFrAtmDlciSiwfNPvc tables."
::= { mscFrAtmDlciSiwfNPvcRowStatusEntry 10 }

mscFrAtmDlciSiwfNPvcProvTable OBJECT-TYPE
   SYNTAX     SEQUENCE OF MscFrAtmDlciSiwfNPvcProvEntry
   ACCESS     not-accessible
   STATUS     mandatory
   DESCRIPTION
     "This group contains provisionable attributes for the NPvc 
      component."
::= { mscFrAtmDlciSiwfNPvc 10 }

mscFrAtmDlciSiwfNPvcProvEntry OBJECT-TYPE
   SYNTAX     MscFrAtmDlciSiwfNPvcProvEntry
   ACCESS     not-accessible
   STATUS     mandatory
   DESCRIPTION
     "An entry in the mscFrAtmDlciSiwfNPvcProvTable."
   INDEX {
      mscFrAtmIndex,
      mscFrAtmDlciIndex,
      mscFrAtmDlciSiwfIndex,
      mscFrAtmDlciSiwfNPvcIndex }
::= { mscFrAtmDlciSiwfNPvcProvTable 1 }

MscFrAtmDlciSiwfNPvcProvEntry ::= SEQUENCE {
   mscFrAtmDlciSiwfNPvcAtmConnection
      Link,
   mscFrAtmDlciSiwfNPvcCorrelationTag
      HexString }

mscFrAtmDlciSiwfNPvcAtmConnection OBJECT-TYPE
   SYNTAX     Link 
   ACCESS     read-write
   STATUS     mandatory
   DESCRIPTION
     "This attribute specifies the ATM connection to which the 
      interworking function is linked.
      
      The ATM connection must be linked to an ATM end-point. For 
      example AtmIf/m Vcc/m Nep."
::= { mscFrAtmDlciSiwfNPvcProvEntry 1 }

mscFrAtmDlciSiwfNPvcCorrelationTag OBJECT-TYPE
   SYNTAX     HexString (SIZE (0..28))
   ACCESS     read-write
   STATUS     mandatory
   DESCRIPTION
     "This attribute specifies a unique string, set by the operator, which 
      identifies the call for accounting purposes. Downstream processing 
      uses this attribute to correlate accounting records issued at different 
      nodes in the network. Normally, this value is provisioned with the 
      same value at each end of the connection. If the value of 
      accountingEnabled is no, this attribute has no effect. This attribute 
      is also visible in the FrAtm Dlci component when accounting is 
      enabled."
   DEFVAL     { ''H }  -- ""
::= { mscFrAtmDlciSiwfNPvcProvEntry 3 }

mscFrAtmDlciSiwfNPvcSiwfNpvcOpTable OBJECT-TYPE
   SYNTAX     SEQUENCE OF MscFrAtmDlciSiwfNPvcSiwfNpvcOpEntry
   ACCESS     not-accessible
   STATUS     mandatory
   DESCRIPTION
     "This group contains the operational attributes for the FrAtm Dlci 
      Siwf Npvc connection."
::= { mscFrAtmDlciSiwfNPvc 11 }

mscFrAtmDlciSiwfNPvcSiwfNpvcOpEntry OBJECT-TYPE
   SYNTAX     MscFrAtmDlciSiwfNPvcSiwfNpvcOpEntry
   ACCESS     not-accessible
   STATUS     mandatory
   DESCRIPTION
     "An entry in the mscFrAtmDlciSiwfNPvcSiwfNpvcOpTable."
   INDEX {
      mscFrAtmIndex,
      mscFrAtmDlciIndex,
      mscFrAtmDlciSiwfIndex,
      mscFrAtmDlciSiwfNPvcIndex }
::= { mscFrAtmDlciSiwfNPvcSiwfNpvcOpTable 1 }

MscFrAtmDlciSiwfNPvcSiwfNpvcOpEntry ::= SEQUENCE {
   mscFrAtmDlciSiwfNPvcConnectionToAtm
      RowPointer }

mscFrAtmDlciSiwfNPvcConnectionToAtm OBJECT-TYPE
   SYNTAX     RowPointer 
   ACCESS     read-only
   STATUS     mandatory
   DESCRIPTION
     "This attribute indicates the ATM connection to which the 
      interworking function is linked."
::= { mscFrAtmDlciSiwfNPvcSiwfNpvcOpEntry 1 }


-- FrAtm/n Dlci/n Siwf SoftPvc 
-- The Spvc component specifies the remote end for a soft PVC.

mscFrAtmDlciSiwfSPvc OBJECT IDENTIFIER ::= { mscFrAtmDlciSiwf 4 }



mscFrAtmDlciSiwfSPvcRowStatusTable OBJECT-TYPE
   SYNTAX     SEQUENCE OF MscFrAtmDlciSiwfSPvcRowStatusEntry
   ACCESS     not-accessible
   STATUS     mandatory
   DESCRIPTION
     "This entry controls the addition and deletion of 
      mscFrAtmDlciSiwfSPvc components."
::= { mscFrAtmDlciSiwfSPvc 1 }

mscFrAtmDlciSiwfSPvcRowStatusEntry OBJECT-TYPE
   SYNTAX     MscFrAtmDlciSiwfSPvcRowStatusEntry
   ACCESS     not-accessible
   STATUS     mandatory
   DESCRIPTION
     "A single entry in the table represents a single 
      mscFrAtmDlciSiwfSPvc component."
   INDEX {
      mscFrAtmIndex,
      mscFrAtmDlciIndex,
      mscFrAtmDlciSiwfIndex,
      mscFrAtmDlciSiwfSPvcIndex }
::= { mscFrAtmDlciSiwfSPvcRowStatusTable 1 }

MscFrAtmDlciSiwfSPvcRowStatusEntry ::= SEQUENCE {
   mscFrAtmDlciSiwfSPvcRowStatus
      RowStatus,
   mscFrAtmDlciSiwfSPvcComponentName
      DisplayString,
   mscFrAtmDlciSiwfSPvcStorageType
      StorageType,
   mscFrAtmDlciSiwfSPvcIndex
      NonReplicated }

mscFrAtmDlciSiwfSPvcRowStatus OBJECT-TYPE
   SYNTAX     RowStatus 
   ACCESS     read-write
   STATUS     mandatory
   DESCRIPTION
     "This variable is used as the basis for SNMP naming of
      mscFrAtmDlciSiwfSPvc components.
      These components can be added and deleted."
::= { mscFrAtmDlciSiwfSPvcRowStatusEntry 1 }

mscFrAtmDlciSiwfSPvcComponentName OBJECT-TYPE
   SYNTAX     DisplayString 
   ACCESS     read-only
   STATUS     mandatory
   DESCRIPTION
     "This variable provides the component's string name for
      use with the ASCII Console Interface"
::= { mscFrAtmDlciSiwfSPvcRowStatusEntry 2 }

mscFrAtmDlciSiwfSPvcStorageType OBJECT-TYPE
   SYNTAX     StorageType 
   ACCESS     read-only
   STATUS     mandatory
   DESCRIPTION
     "This variable represents the storage type value for the
      mscFrAtmDlciSiwfSPvc tables."
::= { mscFrAtmDlciSiwfSPvcRowStatusEntry 4 }

mscFrAtmDlciSiwfSPvcIndex OBJECT-TYPE
   SYNTAX     NonReplicated 
   ACCESS     not-accessible
   STATUS     mandatory
   DESCRIPTION
     "This variable represents the index for the mscFrAtmDlciSiwfSPvc tables."
::= { mscFrAtmDlciSiwfSPvcRowStatusEntry 10 }

mscFrAtmDlciSiwfSPvcProvTable OBJECT-TYPE
   SYNTAX     SEQUENCE OF MscFrAtmDlciSiwfSPvcProvEntry
   ACCESS     not-accessible
   STATUS     mandatory
   DESCRIPTION
     "This group contains provisionable attributes for the soft PVC 
      component."
::= { mscFrAtmDlciSiwfSPvc 10 }

mscFrAtmDlciSiwfSPvcProvEntry OBJECT-TYPE
   SYNTAX     MscFrAtmDlciSiwfSPvcProvEntry
   ACCESS     not-accessible
   STATUS     mandatory
   DESCRIPTION
     "An entry in the mscFrAtmDlciSiwfSPvcProvTable."
   INDEX {
      mscFrAtmIndex,
      mscFrAtmDlciIndex,
      mscFrAtmDlciSiwfIndex,
      mscFrAtmDlciSiwfSPvcIndex }
::= { mscFrAtmDlciSiwfSPvcProvTable 1 }

MscFrAtmDlciSiwfSPvcProvEntry ::= SEQUENCE {
   mscFrAtmDlciSiwfSPvcRemoteAddress
      AsciiString,
   mscFrAtmDlciSiwfSPvcRemoteConnectionIdentifier
      IntegerSequence,
   mscFrAtmDlciSiwfSPvcCorrelationTag
      HexString }

mscFrAtmDlciSiwfSPvcRemoteAddress OBJECT-TYPE
   SYNTAX     AsciiString (SIZE (1..44))
   ACCESS     read-write
   STATUS     mandatory
   DESCRIPTION
     "This attribute specifies the remote address of the SPVC. 
      
      It is represented as a prefix NPI string and a sequence of up to 15 
      digits to specify either a native (E.164 or X.121) address format or 
      Atm End System Address(AESA) in ISO NSAP format.
      
      For example:
      native E.164 = 'e.upto15digits'
      native X.121 = 'x.upto14digits'
      NSAP address = '40 hexadecimal digits'"
::= { mscFrAtmDlciSiwfSPvcProvEntry 2 }

mscFrAtmDlciSiwfSPvcRemoteConnectionIdentifier OBJECT-TYPE
   SYNTAX     IntegerSequence (SIZE (3..9))
   ACCESS     read-write
   STATUS     mandatory
   DESCRIPTION
     "This attribute specifies the remote connection identifier. The 
      identifier is either a remote Atm Vpi.Vci logical channel number 
      assignment or a remote Frame Relay Dlci logical channel number 
      assignment. The remote Atm Vpi.Vci logical channel number is 
      input as 'Vpi.Vci' and the remote Frame Relay Dlci logical channel 
      number is input as '0.remoteDlci'."
::= { mscFrAtmDlciSiwfSPvcProvEntry 3 }

mscFrAtmDlciSiwfSPvcCorrelationTag OBJECT-TYPE
   SYNTAX     HexString (SIZE (0..28))
   ACCESS     read-write
   STATUS     mandatory
   DESCRIPTION
     "This attribute specifies the unique string, set by the operator, which 
      identifies the call for accounting purposes. Downstream processing 
      uses this attribute to correlate accounting records issued at different 
      nodes in the network. If the value of accountingEnabled is no, this 
      attribute has no effect. This attribute is also visible in the FrAtm 
      Dlci component when accounting is enabled. When this attribute is 
      an empty string, the operational correlationTag attribute in the 
      FrAtm Dlci component receives the value of a system-generated 
      correlationTag."
   DEFVAL     { ''H }  -- ""
::= { mscFrAtmDlciSiwfSPvcProvEntry 4 }


-- FrAtm/n Dlci/n Siwf QualityOfService
-- The QoS component provides quality of service overrides for its 
-- parent Siwf component.

mscFrAtmDlciSiwfQoS OBJECT IDENTIFIER ::= { mscFrAtmDlciSiwf 5 }



mscFrAtmDlciSiwfQoSRowStatusTable OBJECT-TYPE
   SYNTAX     SEQUENCE OF MscFrAtmDlciSiwfQoSRowStatusEntry
   ACCESS     not-accessible
   STATUS     mandatory
   DESCRIPTION
     "This entry controls the addition and deletion of 
      mscFrAtmDlciSiwfQoS components."
::= { mscFrAtmDlciSiwfQoS 1 }

mscFrAtmDlciSiwfQoSRowStatusEntry OBJECT-TYPE
   SYNTAX     MscFrAtmDlciSiwfQoSRowStatusEntry
   ACCESS     not-accessible
   STATUS     mandatory
   DESCRIPTION
     "A single entry in the table represents a single 
      mscFrAtmDlciSiwfQoS component."
   INDEX {
      mscFrAtmIndex,
      mscFrAtmDlciIndex,
      mscFrAtmDlciSiwfIndex,
      mscFrAtmDlciSiwfQoSIndex }
::= { mscFrAtmDlciSiwfQoSRowStatusTable 1 }

MscFrAtmDlciSiwfQoSRowStatusEntry ::= SEQUENCE {
   mscFrAtmDlciSiwfQoSRowStatus
      RowStatus,
   mscFrAtmDlciSiwfQoSComponentName
      DisplayString,
   mscFrAtmDlciSiwfQoSStorageType
      StorageType,
   mscFrAtmDlciSiwfQoSIndex
      NonReplicated }

mscFrAtmDlciSiwfQoSRowStatus OBJECT-TYPE
   SYNTAX     RowStatus 
   ACCESS     read-write
   STATUS     mandatory
   DESCRIPTION
     "This variable is used as the basis for SNMP naming of
      mscFrAtmDlciSiwfQoS components.
      These components can be added and deleted."
::= { mscFrAtmDlciSiwfQoSRowStatusEntry 1 }

mscFrAtmDlciSiwfQoSComponentName OBJECT-TYPE
   SYNTAX     DisplayString 
   ACCESS     read-only
   STATUS     mandatory
   DESCRIPTION
     "This variable provides the component's string name for
      use with the ASCII Console Interface"
::= { mscFrAtmDlciSiwfQoSRowStatusEntry 2 }

mscFrAtmDlciSiwfQoSStorageType OBJECT-TYPE
   SYNTAX     StorageType 
   ACCESS     read-only
   STATUS     mandatory
   DESCRIPTION
     "This variable represents the storage type value for the
      mscFrAtmDlciSiwfQoS tables."
::= { mscFrAtmDlciSiwfQoSRowStatusEntry 4 }

mscFrAtmDlciSiwfQoSIndex OBJECT-TYPE
   SYNTAX     NonReplicated 
   ACCESS     not-accessible
   STATUS     mandatory
   DESCRIPTION
     "This variable represents the index for the mscFrAtmDlciSiwfQoS tables."
::= { mscFrAtmDlciSiwfQoSRowStatusEntry 10 }

mscFrAtmDlciSiwfQoSProvTable OBJECT-TYPE
   SYNTAX     SEQUENCE OF MscFrAtmDlciSiwfQoSProvEntry
   ACCESS     not-accessible
   STATUS     mandatory
   DESCRIPTION
     "This group contains the provisionable quality of service attributes 
      for the Qos component."
::= { mscFrAtmDlciSiwfQoS 10 }

mscFrAtmDlciSiwfQoSProvEntry OBJECT-TYPE
   SYNTAX     MscFrAtmDlciSiwfQoSProvEntry
   ACCESS     not-accessible
   STATUS     mandatory
   DESCRIPTION
     "An entry in the mscFrAtmDlciSiwfQoSProvTable."
   INDEX {
      mscFrAtmIndex,
      mscFrAtmDlciIndex,
      mscFrAtmDlciSiwfIndex,
      mscFrAtmDlciSiwfQoSIndex }
::= { mscFrAtmDlciSiwfQoSProvTable 1 }

MscFrAtmDlciSiwfQoSProvEntry ::= SEQUENCE {
   mscFrAtmDlciSiwfQoSEmissionPriorityToIf
      INTEGER,
   mscFrAtmDlciSiwfQoSTransferPriority
      INTEGER }

mscFrAtmDlciSiwfQoSEmissionPriorityToIf OBJECT-TYPE
   SYNTAX     INTEGER  {
                 n0(0),
                 n1(1),
                 n2(2),
                 n3(3),
                 deriveFromTp(254),
                 sameAsInterface(255) }
   ACCESS     read-write
   STATUS     mandatory
   DESCRIPTION
     "This attribute specifies the emission priority of frames sent to the 
      FrAtm interface. Frames in a higher priority queue, represented by a 
      numerically higher number, will be sent before frames in a lower 
      priority queue.
      The value of this attribute is interpreted according to the value of 
      the provisionable attribute numberOfEmissionQs under the parent 
      FrAtm component. If the numberOfEmissionQs attribute is set to 2, 
      emissionPriorityToIf value of 0 maps to emission priority queue 0 
      representing a lower priority queue, and emissionPriorityToIf values 
      of 1, 2, and 3 are mapped to emission priority queue 1 representing 
      the highest priority queue. If the numberOfEmissionQs is set to 4, 
      the emissionPriorityToIf values are directly assigned to the 
      emission priority queues.
      A value of deriveFromTp specifies that the emission priority is to 
      be extracted from the Mod Frs AtmNet Tpm/n component using the 
      transferPriority attribute.
      A value of sameAsInterface specifies that the emission priority is to 
      be extracted from the FrAtm Ca component using the 
      niwfEmissionPriorityToIf attribute."
   DEFVAL     { sameAsInterface }
::= { mscFrAtmDlciSiwfQoSProvEntry 1 }

mscFrAtmDlciSiwfQoSTransferPriority OBJECT-TYPE
   SYNTAX     INTEGER  {
                 n0(0),
                 n1(1),
                 n2(2),
                 n3(3),
                 n4(4),
                 n5(5),
                 n6(6),
                 n7(7),
                 n8(8),
                 n9(9),
                 n10(10),
                 n11(11),
                 n12(12),
                 n13(13),
                 n14(14),
                 n15(15),
                 sameAsInterface(255) }
   ACCESS     read-write
   STATUS     mandatory
   DESCRIPTION
     "This attribute specifies the transfer priority of frames sent to the 
      ATM connection using this particular Dlci.
      In the Frame Relay to ATM direction, the tp selects the ATM 
      service category of the connection.
      In the ATM to Frame Relay direction, the tp selects the FrAtm 
      emission priority queue.
      A value of sameAsInterface specifies that the emission priority 
      extracts from the FrAtm Ca component using the 
      siwfTransferPriority attribute.
      DESCRIPTION"
   DEFVAL     { sameAsInterface }
::= { mscFrAtmDlciSiwfQoSProvEntry 2 }


-- An AtmConnection component is created for each ATM connection 
-- established by an application. It shows where the data traffic for this 
-- connection is directed.

mscFrAtmDlciSiwfAtmCon OBJECT IDENTIFIER ::= { mscFrAtmDlciSiwf 6 }



mscFrAtmDlciSiwfAtmConRowStatusTable OBJECT-TYPE
   SYNTAX     SEQUENCE OF MscFrAtmDlciSiwfAtmConRowStatusEntry
   ACCESS     not-accessible
   STATUS     mandatory
   DESCRIPTION
     "This entry controls the addition and deletion of 
      mscFrAtmDlciSiwfAtmCon components."
::= { mscFrAtmDlciSiwfAtmCon 1 }

mscFrAtmDlciSiwfAtmConRowStatusEntry OBJECT-TYPE
   SYNTAX     MscFrAtmDlciSiwfAtmConRowStatusEntry
   ACCESS     not-accessible
   STATUS     mandatory
   DESCRIPTION
     "A single entry in the table represents a single 
      mscFrAtmDlciSiwfAtmCon component."
   INDEX {
      mscFrAtmIndex,
      mscFrAtmDlciIndex,
      mscFrAtmDlciSiwfIndex,
      mscFrAtmDlciSiwfAtmConIndex }
::= { mscFrAtmDlciSiwfAtmConRowStatusTable 1 }

MscFrAtmDlciSiwfAtmConRowStatusEntry ::= SEQUENCE {
   mscFrAtmDlciSiwfAtmConRowStatus
      RowStatus,
   mscFrAtmDlciSiwfAtmConComponentName
      DisplayString,
   mscFrAtmDlciSiwfAtmConStorageType
      StorageType,
   mscFrAtmDlciSiwfAtmConIndex
      NonReplicated }

mscFrAtmDlciSiwfAtmConRowStatus OBJECT-TYPE
   SYNTAX     RowStatus 
   ACCESS     read-only
   STATUS     mandatory
   DESCRIPTION
     "This variable is used as the basis for SNMP naming of
      mscFrAtmDlciSiwfAtmCon components.
      These components cannot be added nor deleted."
::= { mscFrAtmDlciSiwfAtmConRowStatusEntry 1 }

mscFrAtmDlciSiwfAtmConComponentName OBJECT-TYPE
   SYNTAX     DisplayString 
   ACCESS     read-only
   STATUS     mandatory
   DESCRIPTION
     "This variable provides the component's string name for
      use with the ASCII Console Interface"
::= { mscFrAtmDlciSiwfAtmConRowStatusEntry 2 }

mscFrAtmDlciSiwfAtmConStorageType OBJECT-TYPE
   SYNTAX     StorageType 
   ACCESS     read-only
   STATUS     mandatory
   DESCRIPTION
     "This variable represents the storage type value for the
      mscFrAtmDlciSiwfAtmCon tables."
::= { mscFrAtmDlciSiwfAtmConRowStatusEntry 4 }

mscFrAtmDlciSiwfAtmConIndex OBJECT-TYPE
   SYNTAX     NonReplicated 
   ACCESS     not-accessible
   STATUS     mandatory
   DESCRIPTION
     "This variable represents the index for the mscFrAtmDlciSiwfAtmCon tables."
::= { mscFrAtmDlciSiwfAtmConRowStatusEntry 10 }

mscFrAtmDlciSiwfAtmConOperTable OBJECT-TYPE
   SYNTAX     SEQUENCE OF MscFrAtmDlciSiwfAtmConOperEntry
   ACCESS     not-accessible
   STATUS     mandatory
   DESCRIPTION
     "This attribute group contains the operational attributes for the 
      NapAtmConnection component."
::= { mscFrAtmDlciSiwfAtmCon 10 }

mscFrAtmDlciSiwfAtmConOperEntry OBJECT-TYPE
   SYNTAX     MscFrAtmDlciSiwfAtmConOperEntry
   ACCESS     not-accessible
   STATUS     mandatory
   DESCRIPTION
     "An entry in the mscFrAtmDlciSiwfAtmConOperTable."
   INDEX {
      mscFrAtmIndex,
      mscFrAtmDlciIndex,
      mscFrAtmDlciSiwfIndex,
      mscFrAtmDlciSiwfAtmConIndex }
::= { mscFrAtmDlciSiwfAtmConOperTable 1 }

MscFrAtmDlciSiwfAtmConOperEntry ::= SEQUENCE {
   mscFrAtmDlciSiwfAtmConNextHop
      RowPointer }

mscFrAtmDlciSiwfAtmConNextHop OBJECT-TYPE
   SYNTAX     RowPointer 
   ACCESS     read-only
   STATUS     mandatory
   DESCRIPTION
     "This attribute shows the component name of the AtmIf Vcc Ep or 
      AtmCon component to which this switched connection is 
      established."
::= { mscFrAtmDlciSiwfAtmConOperEntry 1 }


-- FrAtm/n Dlci/n NetworkInterworkingFunction
-- The Niwf component provides the network interworking function 
-- capability between a Frame Relay data link connection and a FRF.5 
-- ATM end point.

mscFrAtmDlciNiwf OBJECT IDENTIFIER ::= { mscFrAtmDlci 4 }



mscFrAtmDlciNiwfRowStatusTable OBJECT-TYPE
   SYNTAX     SEQUENCE OF MscFrAtmDlciNiwfRowStatusEntry
   ACCESS     not-accessible
   STATUS     mandatory
   DESCRIPTION
     "This entry controls the addition and deletion of 
      mscFrAtmDlciNiwf components."
::= { mscFrAtmDlciNiwf 1 }

mscFrAtmDlciNiwfRowStatusEntry OBJECT-TYPE
   SYNTAX     MscFrAtmDlciNiwfRowStatusEntry
   ACCESS     not-accessible
   STATUS     mandatory
   DESCRIPTION
     "A single entry in the table represents a single 
      mscFrAtmDlciNiwf component."
   INDEX {
      mscFrAtmIndex,
      mscFrAtmDlciIndex,
      mscFrAtmDlciNiwfIndex }
::= { mscFrAtmDlciNiwfRowStatusTable 1 }

MscFrAtmDlciNiwfRowStatusEntry ::= SEQUENCE {
   mscFrAtmDlciNiwfRowStatus
      RowStatus,
   mscFrAtmDlciNiwfComponentName
      DisplayString,
   mscFrAtmDlciNiwfStorageType
      StorageType,
   mscFrAtmDlciNiwfIndex
      NonReplicated }

mscFrAtmDlciNiwfRowStatus OBJECT-TYPE
   SYNTAX     RowStatus 
   ACCESS     read-write
   STATUS     mandatory
   DESCRIPTION
     "This variable is used as the basis for SNMP naming of
      mscFrAtmDlciNiwf components.
      These components can be added and deleted."
::= { mscFrAtmDlciNiwfRowStatusEntry 1 }

mscFrAtmDlciNiwfComponentName OBJECT-TYPE
   SYNTAX     DisplayString 
   ACCESS     read-only
   STATUS     mandatory
   DESCRIPTION
     "This variable provides the component's string name for
      use with the ASCII Console Interface"
::= { mscFrAtmDlciNiwfRowStatusEntry 2 }

mscFrAtmDlciNiwfStorageType OBJECT-TYPE
   SYNTAX     StorageType 
   ACCESS     read-only
   STATUS     mandatory
   DESCRIPTION
     "This variable represents the storage type value for the
      mscFrAtmDlciNiwf tables."
::= { mscFrAtmDlciNiwfRowStatusEntry 4 }

mscFrAtmDlciNiwfIndex OBJECT-TYPE
   SYNTAX     NonReplicated 
   ACCESS     not-accessible
   STATUS     mandatory
   DESCRIPTION
     "This variable represents the index for the mscFrAtmDlciNiwf tables."
::= { mscFrAtmDlciNiwfRowStatusEntry 10 }

mscFrAtmDlciNiwfOperTable OBJECT-TYPE
   SYNTAX     SEQUENCE OF MscFrAtmDlciNiwfOperEntry
   ACCESS     not-accessible
   STATUS     mandatory
   DESCRIPTION
     "This group contains operational networking description information 
      for a Niwf component."
::= { mscFrAtmDlciNiwf 10 }

mscFrAtmDlciNiwfOperEntry OBJECT-TYPE
   SYNTAX     MscFrAtmDlciNiwfOperEntry
   ACCESS     not-accessible
   STATUS     mandatory
   DESCRIPTION
     "An entry in the mscFrAtmDlciNiwfOperTable."
   INDEX {
      mscFrAtmIndex,
      mscFrAtmDlciIndex,
      mscFrAtmDlciNiwfIndex }
::= { mscFrAtmDlciNiwfOperTable 1 }

MscFrAtmDlciNiwfOperEntry ::= SEQUENCE {
   mscFrAtmDlciNiwfDeToClpMapping
      INTEGER,
   mscFrAtmDlciNiwfClpToDeMapping
      INTEGER,
   mscFrAtmDlciNiwfTransferPriority
      Unsigned32,
   mscFrAtmDlciNiwfAtmServiceCategory
      INTEGER,
   mscFrAtmDlciNiwfTrafficParmConvPolicy
      INTEGER,
   mscFrAtmDlciNiwfAvgFrameSize
      INTEGER,
   mscFrAtmDlciNiwfEquivalentBitRate
      Unsigned32,
   mscFrAtmDlciNiwfAtmDlci
      AsciiString,
   mscFrAtmDlciNiwfAssignedBandwidthPool
      INTEGER }

mscFrAtmDlciNiwfDeToClpMapping OBJECT-TYPE
   SYNTAX     INTEGER  {
                 always0(0),
                 always1(1),
                 preserve(2) }
   ACCESS     read-only
   STATUS     mandatory
   DESCRIPTION
     "This attribute indicates the type of DE to CLP mapping that is 
      performed in the Frame Relay to ATM direction.
      A value of preserve indicates that the DE field in the Q.922 core 
      frame copies to the CLP field of every ATM cell containing the 
      frame.
      A value of always0 indicates that the CLP field of every ATM cell is 
      always set to 0.
      A value of always1 indicates that the CLP field of every ATM cell is 
      always set to 1."
::= { mscFrAtmDlciNiwfOperEntry 1 }

mscFrAtmDlciNiwfClpToDeMapping OBJECT-TYPE
   SYNTAX     INTEGER  {
                 preserve(2),
                 transparent(3) }
   ACCESS     read-only
   STATUS     mandatory
   DESCRIPTION
     "This attribute indicates the type of CLP to DE mapping that is 
      performed in the ATM to Frame Relay direction.
      A value of preserve indicates that the DE field of the Q.922 core 
      frame is set when one or more ATM cells belonging to the frame 
      has its CLP field set, or when the DE field of the FR-SSCS PDU is 
      set.
      A value of transparent indicates that the DE field of the Q.922 core 
      frame copies directly from the DE field of the FR-SSCS PDU."
::= { mscFrAtmDlciNiwfOperEntry 2 }

mscFrAtmDlciNiwfTransferPriority OBJECT-TYPE
   SYNTAX     Unsigned32 (0..15)
   ACCESS     read-only
   STATUS     mandatory
   DESCRIPTION
     "This attribute indicates the transfer priority in use for a specific 
      connection. This is the transfer priority that the local Frame Relay 
      network uses for this connection to an ATM network.
      In the Frame Relay to ATM direction, the tp selects the FRF.5 End 
      Point which multiplexes the frames.
      In the ATM to Frame Relay direction, the tp selects the default 
      FrAtm emission priority queue to be used by this Dlci."
::= { mscFrAtmDlciNiwfOperEntry 3 }

mscFrAtmDlciNiwfAtmServiceCategory OBJECT-TYPE
   SYNTAX     INTEGER  {
                 ubr(0),
                 cbr(1),
                 rtVbr(2),
                 nrtVbr(3),
                 scNotAvailable(255) }
   ACCESS     read-only
   STATUS     mandatory
   DESCRIPTION
     "This attribute indicates the ATM service category that was mapped 
      for this connection.
      A value of scNotAvailable indicates that atmServiceCategory is not 
      yet available for this connection."
::= { mscFrAtmDlciNiwfOperEntry 4 }

mscFrAtmDlciNiwfTrafficParmConvPolicy OBJECT-TYPE
   SYNTAX     INTEGER  {
                 policyNotAvailable(0),
                 n3(3),
                 n4(4),
                 n5(5),
                 n6(6) }
   ACCESS     read-only
   STATUS     mandatory
   DESCRIPTION
     "This attribute indicates the traffic parameter conversion policy that 
      is used for this connection.
      
      Policy 3 characterizes the traffic in the following way:
      - ATM traffic descriptor type 6 is selected.
      - PCR(0+1) is based on the ATM link rate.
      - SCR(0+1) is based on the CIR and EIR.
      - MB(0+1) is based on Bc, Be, CIR, EIR and AR.
      - Takes into account that the instantaneous rate of the frame relay 
      stream can be above CIR and up to the AR.
      
      Policy 4 characterizes the traffic in the following way:
      - ATM traffic descriptor type 7 or 8 is selected. Type 7 is chosen 
      when non-conforming cells are to be discarded and type 8 when 
      non-conforming cells are tagged by UPC traffic policer.
      - PCR(0+1) is based on AR.
      - SCR(0) is based on the CIR.
      - MBS(0) is based on Bc, CIR, and AR.
      - There is no direct characterization of EIR. The allowed EIR can be 
      derived using the difference between the AR and CIR.
      
      Policy 5 characterizes the traffic in the following way:
      - ATM traffic descriptor type 7 or 8 is selected. Type 7 is chosen 
      when non-conforming cells are to be discarded and type 8 when 
      non-conforming cells are tagged by UPC traffic policer.
      - PCR(0+1) is based on the CIR and EIR.
      - SCR(0) is based on the CIR.
      - MBS(0) is based on the CIR.
      - The maximum PCR is no longer based on the AR but rather on the 
      CIR and EIR.
      
      Policy 6 characterizes the traffic in the following way:
      - ATM traffic descriptor type 3 is selected.
      - PCR(0+1) is based only on the CIR
      policyNotAvailable indicates that the trafficParmConvPolicy is not 
      yet available for this connection."
::= { mscFrAtmDlciNiwfOperEntry 5 }

mscFrAtmDlciNiwfAvgFrameSize OBJECT-TYPE
   SYNTAX     INTEGER (0..8187)
   ACCESS     read-only
   STATUS     mandatory
   DESCRIPTION
     "This attribute indicates the average frame size that was used for this 
      connection as part of the traffic parameter conversion policy.
      A value of zero indicates that the avgFrameSize is not yet available 
      for this connection."
::= { mscFrAtmDlciNiwfOperEntry 6 }

mscFrAtmDlciNiwfEquivalentBitRate OBJECT-TYPE
   SYNTAX     Unsigned32 (0..4294967295)
   ACCESS     read-only
   STATUS     mandatory
   DESCRIPTION
     "This attribute indicates the access reserved bandwidth for this FR-
      ATM connection when CAC is on. If a connection is subcribed to 
      CIR only or CIR plus EIR service, the EBR reserved is CIR. If a 
      connection is subcribed to EIR only service, the EBR reserved is 0."
::= { mscFrAtmDlciNiwfOperEntry 7 }

mscFrAtmDlciNiwfAtmDlci OBJECT-TYPE
   SYNTAX     AsciiString (SIZE (0..40))
   ACCESS     read-only
   STATUS     mandatory
   DESCRIPTION
     "This attribute displays the DLCI logical channel used inside the 
      ATM VCC.
      A null value indicates that the atmDlci is not yet available for this 
      connection."
::= { mscFrAtmDlciNiwfOperEntry 8 }

mscFrAtmDlciNiwfAssignedBandwidthPool OBJECT-TYPE
   SYNTAX     INTEGER  {
                 n0(0),
                 n1(1),
                 n2(2),
                 n3(3),
                 n4(4),
                 n5(5),
                 n6(6),
                 n7(7),
                 n8(8),
                 n9(9),
                 n10(10),
                 n11(11),
                 n12(12),
                 n13(13),
                 n14(14),
                 n15(15) }
   ACCESS     read-only
   STATUS     mandatory
   DESCRIPTION
     "This attribute specifies the bandwidth pool which is used by this 
      Dlci."
::= { mscFrAtmDlciNiwfOperEntry 9 }


-- FrAtm/n Dlci/n Niwf SoftPermanentVirtualCircuit
-- The Spvc component represents the remote end of a soft PVC.

mscFrAtmDlciNiwfSpvc OBJECT IDENTIFIER ::= { mscFrAtmDlciNiwf 2 }



mscFrAtmDlciNiwfSpvcRowStatusTable OBJECT-TYPE
   SYNTAX     SEQUENCE OF MscFrAtmDlciNiwfSpvcRowStatusEntry
   ACCESS     not-accessible
   STATUS     mandatory
   DESCRIPTION
     "This entry controls the addition and deletion of 
      mscFrAtmDlciNiwfSpvc components."
::= { mscFrAtmDlciNiwfSpvc 1 }

mscFrAtmDlciNiwfSpvcRowStatusEntry OBJECT-TYPE
   SYNTAX     MscFrAtmDlciNiwfSpvcRowStatusEntry
   ACCESS     not-accessible
   STATUS     mandatory
   DESCRIPTION
     "A single entry in the table represents a single 
      mscFrAtmDlciNiwfSpvc component."
   INDEX {
      mscFrAtmIndex,
      mscFrAtmDlciIndex,
      mscFrAtmDlciNiwfIndex,
      mscFrAtmDlciNiwfSpvcIndex }
::= { mscFrAtmDlciNiwfSpvcRowStatusTable 1 }

MscFrAtmDlciNiwfSpvcRowStatusEntry ::= SEQUENCE {
   mscFrAtmDlciNiwfSpvcRowStatus
      RowStatus,
   mscFrAtmDlciNiwfSpvcComponentName
      DisplayString,
   mscFrAtmDlciNiwfSpvcStorageType
      StorageType,
   mscFrAtmDlciNiwfSpvcIndex
      NonReplicated }

mscFrAtmDlciNiwfSpvcRowStatus OBJECT-TYPE
   SYNTAX     RowStatus 
   ACCESS     read-only
   STATUS     mandatory
   DESCRIPTION
     "This variable is used as the basis for SNMP naming of
      mscFrAtmDlciNiwfSpvc components.
      These components cannot be added nor deleted."
::= { mscFrAtmDlciNiwfSpvcRowStatusEntry 1 }

mscFrAtmDlciNiwfSpvcComponentName OBJECT-TYPE
   SYNTAX     DisplayString 
   ACCESS     read-only
   STATUS     mandatory
   DESCRIPTION
     "This variable provides the component's string name for
      use with the ASCII Console Interface"
::= { mscFrAtmDlciNiwfSpvcRowStatusEntry 2 }

mscFrAtmDlciNiwfSpvcStorageType OBJECT-TYPE
   SYNTAX     StorageType 
   ACCESS     read-only
   STATUS     mandatory
   DESCRIPTION
     "This variable represents the storage type value for the
      mscFrAtmDlciNiwfSpvc tables."
::= { mscFrAtmDlciNiwfSpvcRowStatusEntry 4 }

mscFrAtmDlciNiwfSpvcIndex OBJECT-TYPE
   SYNTAX     NonReplicated 
   ACCESS     not-accessible
   STATUS     mandatory
   DESCRIPTION
     "This variable represents the index for the mscFrAtmDlciNiwfSpvc tables."
::= { mscFrAtmDlciNiwfSpvcRowStatusEntry 10 }

mscFrAtmDlciNiwfSpvcProvTable OBJECT-TYPE
   SYNTAX     SEQUENCE OF MscFrAtmDlciNiwfSpvcProvEntry
   ACCESS     not-accessible
   STATUS     mandatory
   DESCRIPTION
     "This group contains the provisionable attributes for the soft PVC 
      component."
::= { mscFrAtmDlciNiwfSpvc 10 }

mscFrAtmDlciNiwfSpvcProvEntry OBJECT-TYPE
   SYNTAX     MscFrAtmDlciNiwfSpvcProvEntry
   ACCESS     not-accessible
   STATUS     mandatory
   DESCRIPTION
     "An entry in the mscFrAtmDlciNiwfSpvcProvTable."
   INDEX {
      mscFrAtmIndex,
      mscFrAtmDlciIndex,
      mscFrAtmDlciNiwfIndex,
      mscFrAtmDlciNiwfSpvcIndex }
::= { mscFrAtmDlciNiwfSpvcProvTable 1 }

MscFrAtmDlciNiwfSpvcProvEntry ::= SEQUENCE {
   mscFrAtmDlciNiwfSpvcRemoteAddress
      AsciiString,
   mscFrAtmDlciNiwfSpvcRemoteDlci
      INTEGER,
   mscFrAtmDlciNiwfSpvcCorrelationTag
      HexString }

mscFrAtmDlciNiwfSpvcRemoteAddress OBJECT-TYPE
   SYNTAX     AsciiString (SIZE (3..17))
   ACCESS     read-write
   STATUS     mandatory
   DESCRIPTION
     "This attribute specifies the remote address of the SPVC.
      It is represented as a prefix NPI string and a sequence of up to 15 
      digits to specify either a native E.164 or native X.121 address 
      format. For example, native E.164 = 'e.upto15digits'."
::= { mscFrAtmDlciNiwfSpvcProvEntry 1 }

mscFrAtmDlciNiwfSpvcRemoteDlci OBJECT-TYPE
   SYNTAX     INTEGER (16..1007 | 1022)
   ACCESS     read-write
   STATUS     mandatory
   DESCRIPTION
     "This attribute specifies the remote connection identifier. This 
      identifier is the DLCI logical channel number assignment used 
      inside the ATM pipe."
   DEFVAL     { 1022 }
::= { mscFrAtmDlciNiwfSpvcProvEntry 2 }

mscFrAtmDlciNiwfSpvcCorrelationTag OBJECT-TYPE
   SYNTAX     HexString (SIZE (0..28))
   ACCESS     read-write
   STATUS     mandatory
   DESCRIPTION
     "This attribute specifies aunique string, set by the operator, which 
      identifies the call for accounting purposes. Downstream processing 
      uses this attribute to correlate accounting records issued at different 
      nodes in the network. Normally, the attribute is provisioned with the 
      same value at both ends of the connection. If the value of 
      accountingEnabled is no, this attribute has no effect. This attribute 
      is also visible in the FrAtm Dlci component when accounting is 
      enabled. When this attribute is an empty string, the operational 
      correlationTag attribute in the FrAtm Dlci component receives the 
      value of a system-generated correlationTag."
   DEFVAL     { ''H }  -- ""
::= { mscFrAtmDlciNiwfSpvcProvEntry 3 }


-- FrAtm/n Dlci/n Niwf NetworkingDescriptor
-- The Nd component provides networking descriptor overrides for its 
-- parent Niwf component.

mscFrAtmDlciNiwfNd OBJECT IDENTIFIER ::= { mscFrAtmDlciNiwf 3 }



mscFrAtmDlciNiwfNdRowStatusTable OBJECT-TYPE
   SYNTAX     SEQUENCE OF MscFrAtmDlciNiwfNdRowStatusEntry
   ACCESS     not-accessible
   STATUS     mandatory
   DESCRIPTION
     "This entry controls the addition and deletion of 
      mscFrAtmDlciNiwfNd components."
::= { mscFrAtmDlciNiwfNd 1 }

mscFrAtmDlciNiwfNdRowStatusEntry OBJECT-TYPE
   SYNTAX     MscFrAtmDlciNiwfNdRowStatusEntry
   ACCESS     not-accessible
   STATUS     mandatory
   DESCRIPTION
     "A single entry in the table represents a single 
      mscFrAtmDlciNiwfNd component."
   INDEX {
      mscFrAtmIndex,
      mscFrAtmDlciIndex,
      mscFrAtmDlciNiwfIndex,
      mscFrAtmDlciNiwfNdIndex }
::= { mscFrAtmDlciNiwfNdRowStatusTable 1 }

MscFrAtmDlciNiwfNdRowStatusEntry ::= SEQUENCE {
   mscFrAtmDlciNiwfNdRowStatus
      RowStatus,
   mscFrAtmDlciNiwfNdComponentName
      DisplayString,
   mscFrAtmDlciNiwfNdStorageType
      StorageType,
   mscFrAtmDlciNiwfNdIndex
      NonReplicated }

mscFrAtmDlciNiwfNdRowStatus OBJECT-TYPE
   SYNTAX     RowStatus 
   ACCESS     read-write
   STATUS     mandatory
   DESCRIPTION
     "This variable is used as the basis for SNMP naming of
      mscFrAtmDlciNiwfNd components.
      These components can be added and deleted."
::= { mscFrAtmDlciNiwfNdRowStatusEntry 1 }

mscFrAtmDlciNiwfNdComponentName OBJECT-TYPE
   SYNTAX     DisplayString 
   ACCESS     read-only
   STATUS     mandatory
   DESCRIPTION
     "This variable provides the component's string name for
      use with the ASCII Console Interface"
::= { mscFrAtmDlciNiwfNdRowStatusEntry 2 }

mscFrAtmDlciNiwfNdStorageType OBJECT-TYPE
   SYNTAX     StorageType 
   ACCESS     read-only
   STATUS     mandatory
   DESCRIPTION
     "This variable represents the storage type value for the
      mscFrAtmDlciNiwfNd tables."
::= { mscFrAtmDlciNiwfNdRowStatusEntry 4 }

mscFrAtmDlciNiwfNdIndex OBJECT-TYPE
   SYNTAX     NonReplicated 
   ACCESS     not-accessible
   STATUS     mandatory
   DESCRIPTION
     "This variable represents the index for the mscFrAtmDlciNiwfNd tables."
::= { mscFrAtmDlciNiwfNdRowStatusEntry 10 }

mscFrAtmDlciNiwfNdProvTable OBJECT-TYPE
   SYNTAX     SEQUENCE OF MscFrAtmDlciNiwfNdProvEntry
   ACCESS     not-accessible
   STATUS     mandatory
   DESCRIPTION
     "This group contains provisionable attributes for the parent Niwf 
      component."
::= { mscFrAtmDlciNiwfNd 10 }

mscFrAtmDlciNiwfNdProvEntry OBJECT-TYPE
   SYNTAX     MscFrAtmDlciNiwfNdProvEntry
   ACCESS     not-accessible
   STATUS     mandatory
   DESCRIPTION
     "An entry in the mscFrAtmDlciNiwfNdProvTable."
   INDEX {
      mscFrAtmIndex,
      mscFrAtmDlciIndex,
      mscFrAtmDlciNiwfIndex,
      mscFrAtmDlciNiwfNdIndex }
::= { mscFrAtmDlciNiwfNdProvTable 1 }

MscFrAtmDlciNiwfNdProvEntry ::= SEQUENCE {
   mscFrAtmDlciNiwfNdDeToClpMapping
      INTEGER,
   mscFrAtmDlciNiwfNdClpToDeMapping
      INTEGER,
   mscFrAtmDlciNiwfNdTransferPriority
      INTEGER }

mscFrAtmDlciNiwfNdDeToClpMapping OBJECT-TYPE
   SYNTAX     INTEGER  {
                 always0(0),
                 always1(1),
                 preserve(2),
                 sameAsInterface(255) }
   ACCESS     read-write
   STATUS     mandatory
   DESCRIPTION
     "This attribute specifies the type of DE to CLP mapping performs in 
      the Frame Relay to ATM direction.
      When preserve is selected, the DE field in the Q.922 core frame 
      copies to the CLP field of every ATM cell containing the frame.
      When always0 is selected, the CLP field of every ATM cell is 
      always set to 0.
      When always1 is selected, the CLP field of every ATM cell is 
      always set to 1."
   DEFVAL     { sameAsInterface }
::= { mscFrAtmDlciNiwfNdProvEntry 1 }

mscFrAtmDlciNiwfNdClpToDeMapping OBJECT-TYPE
   SYNTAX     INTEGER  {
                 preserve(2),
                 transparent(3),
                 sameAsInterface(255) }
   ACCESS     read-write
   STATUS     mandatory
   DESCRIPTION
     "This attribute specifies the type of CLP to DE mapping performs in 
      the ATM to Frame Relay direction.
      When preserve is selected, the DE field of the Q.922 core frame is 
      set when one or more ATM cells belonging the frame has its CLP 
      field set, or when the DE field of the FR-SSCS PDU is set.
      When transparent is selected, the DE field of the Q.922 core frame 
      copies directly from the DE field of the FR-SSCS PDU."
   DEFVAL     { sameAsInterface }
::= { mscFrAtmDlciNiwfNdProvEntry 2 }

mscFrAtmDlciNiwfNdTransferPriority OBJECT-TYPE
   SYNTAX     INTEGER  {
                 n0(0),
                 n1(1),
                 n2(2),
                 n3(3),
                 n4(4),
                 n5(5),
                 n6(6),
                 n7(7),
                 n8(8),
                 n9(9),
                 n10(10),
                 n11(11),
                 n12(12),
                 n13(13),
                 n14(14),
                 n15(15),
                 sameAsInterface(255) }
   ACCESS     read-write
   STATUS     obsolete
   DESCRIPTION
     "This attribute specifies the transfer priority of frames sent to and 
      received from the ATM connection.
      In the Frame Relay to ATM direction, the tp selects the FRF.5 End 
      Point which multiplexes the frames.
      In the ATM to Frame Relay direction, the tp is applied to frames on 
      a per-DLCI basis.
      This attribute is obsoleted. During migration, its value will be 
      transfered to the QualityOfService transferPriority."
   DEFVAL     { sameAsInterface }
::= { mscFrAtmDlciNiwfNdProvEntry 3 }


-- FrAtm/n Dlci/n Niwf QualityOfService
-- The QoS component provides quality of service overrides for its 
-- parent Niwf component.

mscFrAtmDlciNiwfQoS OBJECT IDENTIFIER ::= { mscFrAtmDlciNiwf 4 }



mscFrAtmDlciNiwfQoSRowStatusTable OBJECT-TYPE
   SYNTAX     SEQUENCE OF MscFrAtmDlciNiwfQoSRowStatusEntry
   ACCESS     not-accessible
   STATUS     mandatory
   DESCRIPTION
     "This entry controls the addition and deletion of 
      mscFrAtmDlciNiwfQoS components."
::= { mscFrAtmDlciNiwfQoS 1 }

mscFrAtmDlciNiwfQoSRowStatusEntry OBJECT-TYPE
   SYNTAX     MscFrAtmDlciNiwfQoSRowStatusEntry
   ACCESS     not-accessible
   STATUS     mandatory
   DESCRIPTION
     "A single entry in the table represents a single 
      mscFrAtmDlciNiwfQoS component."
   INDEX {
      mscFrAtmIndex,
      mscFrAtmDlciIndex,
      mscFrAtmDlciNiwfIndex,
      mscFrAtmDlciNiwfQoSIndex }
::= { mscFrAtmDlciNiwfQoSRowStatusTable 1 }

MscFrAtmDlciNiwfQoSRowStatusEntry ::= SEQUENCE {
   mscFrAtmDlciNiwfQoSRowStatus
      RowStatus,
   mscFrAtmDlciNiwfQoSComponentName
      DisplayString,
   mscFrAtmDlciNiwfQoSStorageType
      StorageType,
   mscFrAtmDlciNiwfQoSIndex
      NonReplicated }

mscFrAtmDlciNiwfQoSRowStatus OBJECT-TYPE
   SYNTAX     RowStatus 
   ACCESS     read-write
   STATUS     mandatory
   DESCRIPTION
     "This variable is used as the basis for SNMP naming of
      mscFrAtmDlciNiwfQoS components.
      These components can be added and deleted."
::= { mscFrAtmDlciNiwfQoSRowStatusEntry 1 }

mscFrAtmDlciNiwfQoSComponentName OBJECT-TYPE
   SYNTAX     DisplayString 
   ACCESS     read-only
   STATUS     mandatory
   DESCRIPTION
     "This variable provides the component's string name for
      use with the ASCII Console Interface"
::= { mscFrAtmDlciNiwfQoSRowStatusEntry 2 }

mscFrAtmDlciNiwfQoSStorageType OBJECT-TYPE
   SYNTAX     StorageType 
   ACCESS     read-only
   STATUS     mandatory
   DESCRIPTION
     "This variable represents the storage type value for the
      mscFrAtmDlciNiwfQoS tables."
::= { mscFrAtmDlciNiwfQoSRowStatusEntry 4 }

mscFrAtmDlciNiwfQoSIndex OBJECT-TYPE
   SYNTAX     NonReplicated 
   ACCESS     not-accessible
   STATUS     mandatory
   DESCRIPTION
     "This variable represents the index for the mscFrAtmDlciNiwfQoS tables."
::= { mscFrAtmDlciNiwfQoSRowStatusEntry 10 }

mscFrAtmDlciNiwfQoSProvTable OBJECT-TYPE
   SYNTAX     SEQUENCE OF MscFrAtmDlciNiwfQoSProvEntry
   ACCESS     not-accessible
   STATUS     mandatory
   DESCRIPTION
     "This group contains the provisionable quality of service attributes 
      for the Qos component."
::= { mscFrAtmDlciNiwfQoS 10 }

mscFrAtmDlciNiwfQoSProvEntry OBJECT-TYPE
   SYNTAX     MscFrAtmDlciNiwfQoSProvEntry
   ACCESS     not-accessible
   STATUS     mandatory
   DESCRIPTION
     "An entry in the mscFrAtmDlciNiwfQoSProvTable."
   INDEX {
      mscFrAtmIndex,
      mscFrAtmDlciIndex,
      mscFrAtmDlciNiwfIndex,
      mscFrAtmDlciNiwfQoSIndex }
::= { mscFrAtmDlciNiwfQoSProvTable 1 }

MscFrAtmDlciNiwfQoSProvEntry ::= SEQUENCE {
   mscFrAtmDlciNiwfQoSEmissionPriorityToIf
      INTEGER,
   mscFrAtmDlciNiwfQoSTransferPriority
      INTEGER }

mscFrAtmDlciNiwfQoSEmissionPriorityToIf OBJECT-TYPE
   SYNTAX     INTEGER  {
                 n0(0),
                 n1(1),
                 n2(2),
                 n3(3),
                 deriveFromTp(254),
                 sameAsInterface(255) }
   ACCESS     read-write
   STATUS     mandatory
   DESCRIPTION
     "This attribute specifies the emission priority of frames sent to the 
      FrAtm interface. Frames in a higher priority queue, depicted by a 
      numerically higher number, are sent before frames in a lower 
      priority queue.
      The value of this attribute is interpreted according to the value of 
      the provisionable attribute numberOfEmissionQs under the parent 
      FrAtm component. If the numberOfEmissionQs attribute is set to 2, 
      emissionPriorityToIf value of 0 maps to emission priority queue 0 
      representing a lower priority queue, and emissionPriorityToIf values 
      of 1, 2, and 3 map to emission priority queue 1 representing the 
      highest priority queue. If the numberOfEmissionQs is set to 4, the 
      emissionPriorityToIf values are directly assigned to the emission 
      priority queues.
      A value of deriveFromTp specifies that the emission priority is to 
      be extracted from the Mod Frs AtmNet Tpm/n component using the 
      transferPriority attribute.
      A value of sameAsInterface specifies that the emission priority is 
      extracts from the FrAtm Ca component using the 
      niwfEmissionPriorityToIf attribute."
   DEFVAL     { sameAsInterface }
::= { mscFrAtmDlciNiwfQoSProvEntry 1 }

mscFrAtmDlciNiwfQoSTransferPriority OBJECT-TYPE
   SYNTAX     INTEGER  {
                 n0(0),
                 n1(1),
                 n2(2),
                 n3(3),
                 n4(4),
                 n5(5),
                 n6(6),
                 n7(7),
                 n8(8),
                 n9(9),
                 n10(10),
                 n11(11),
                 n12(12),
                 n13(13),
                 n14(14),
                 n15(15),
                 sameAsInterface(255) }
   ACCESS     read-write
   STATUS     mandatory
   DESCRIPTION
     "This attribute specifies the transfer priority of frames sent to the 
      ATM connection.
      In the Frame Relay to ATM direction, the tp selects the FRF.5 End 
      Point which multiplexes the frames.
      In the ATM to Frame Relay direction, the tp selects the default 
      FrAtm emission priority queue to be used by this DLCI.
      A value of sameAsInterface specifies that the emission priority is to 
      be extracted from the FrAtm Ca component using the 
      niwfTransferPriority attribute.
      DESCRIPTION"
   DEFVAL     { sameAsInterface }
::= { mscFrAtmDlciNiwfQoSProvEntry 2 }


-- FrAtm/n Dlci/n EgressServiceParameters
-- This component contains the provisionable attributes of the egress 
-- direction for the parent Dlci component.

mscFrAtmDlciEgSp OBJECT IDENTIFIER ::= { mscFrAtmDlci 5 }



mscFrAtmDlciEgSpRowStatusTable OBJECT-TYPE
   SYNTAX     SEQUENCE OF MscFrAtmDlciEgSpRowStatusEntry
   ACCESS     not-accessible
   STATUS     mandatory
   DESCRIPTION
     "This entry controls the addition and deletion of 
      mscFrAtmDlciEgSp components."
::= { mscFrAtmDlciEgSp 1 }

mscFrAtmDlciEgSpRowStatusEntry OBJECT-TYPE
   SYNTAX     MscFrAtmDlciEgSpRowStatusEntry
   ACCESS     not-accessible
   STATUS     mandatory
   DESCRIPTION
     "A single entry in the table represents a single 
      mscFrAtmDlciEgSp component."
   INDEX {
      mscFrAtmIndex,
      mscFrAtmDlciIndex,
      mscFrAtmDlciEgSpIndex }
::= { mscFrAtmDlciEgSpRowStatusTable 1 }

MscFrAtmDlciEgSpRowStatusEntry ::= SEQUENCE {
   mscFrAtmDlciEgSpRowStatus
      RowStatus,
   mscFrAtmDlciEgSpComponentName
      DisplayString,
   mscFrAtmDlciEgSpStorageType
      StorageType,
   mscFrAtmDlciEgSpIndex
      NonReplicated }

mscFrAtmDlciEgSpRowStatus OBJECT-TYPE
   SYNTAX     RowStatus 
   ACCESS     read-write
   STATUS     mandatory
   DESCRIPTION
     "This variable is used as the basis for SNMP naming of
      mscFrAtmDlciEgSp components.
      These components can be added and deleted."
::= { mscFrAtmDlciEgSpRowStatusEntry 1 }

mscFrAtmDlciEgSpComponentName OBJECT-TYPE
   SYNTAX     DisplayString 
   ACCESS     read-only
   STATUS     mandatory
   DESCRIPTION
     "This variable provides the component's string name for
      use with the ASCII Console Interface"
::= { mscFrAtmDlciEgSpRowStatusEntry 2 }

mscFrAtmDlciEgSpStorageType OBJECT-TYPE
   SYNTAX     StorageType 
   ACCESS     read-only
   STATUS     mandatory
   DESCRIPTION
     "This variable represents the storage type value for the
      mscFrAtmDlciEgSp tables."
::= { mscFrAtmDlciEgSpRowStatusEntry 4 }

mscFrAtmDlciEgSpIndex OBJECT-TYPE
   SYNTAX     NonReplicated 
   ACCESS     not-accessible
   STATUS     mandatory
   DESCRIPTION
     "This variable represents the index for the mscFrAtmDlciEgSp tables."
::= { mscFrAtmDlciEgSpRowStatusEntry 10 }

mscFrAtmDlciEgSpProvTable OBJECT-TYPE
   SYNTAX     SEQUENCE OF MscFrAtmDlciEgSpProvEntry
   ACCESS     not-accessible
   STATUS     mandatory
   DESCRIPTION
     "This group contains the provisionable attributes of the egress 
      direction for the Data Link Connection Identifier. These attributes 
      reflect the service parameters for the egress direction specific to this 
      instance of Dlci."
::= { mscFrAtmDlciEgSp 10 }

mscFrAtmDlciEgSpProvEntry OBJECT-TYPE
   SYNTAX     MscFrAtmDlciEgSpProvEntry
   ACCESS     not-accessible
   STATUS     mandatory
   DESCRIPTION
     "An entry in the mscFrAtmDlciEgSpProvTable."
   INDEX {
      mscFrAtmIndex,
      mscFrAtmDlciIndex,
      mscFrAtmDlciEgSpIndex }
::= { mscFrAtmDlciEgSpProvTable 1 }

MscFrAtmDlciEgSpProvEntry ::= SEQUENCE {
   mscFrAtmDlciEgSpCommittedInformationRate
      Unsigned32,
   mscFrAtmDlciEgSpCommittedBurstSize
      Unsigned32,
   mscFrAtmDlciEgSpExcessBurstSize
      Unsigned32,
   mscFrAtmDlciEgSpMeasurementInterval
      Unsigned32 }

mscFrAtmDlciEgSpCommittedInformationRate OBJECT-TYPE
   SYNTAX     Unsigned32 (0..50000000)
   ACCESS     read-write
   STATUS     mandatory
   DESCRIPTION
     "This attribute specifies the committed information rate (CIR) for the 
      egress direction. It is used for bandwidth reservation for the purpose 
      of performing a Call Admission Control (CAC) function towards 
      the egress link.
      
      This attribute is not used to perform rate enforcement towards the 
      egress link."
   DEFVAL     { 64000 }
::= { mscFrAtmDlciEgSpProvEntry 1 }

mscFrAtmDlciEgSpCommittedBurstSize OBJECT-TYPE
   SYNTAX     Unsigned32 (0..50000000)
   ACCESS     read-write
   STATUS     mandatory
   DESCRIPTION
     "This attribute specifies the committed burst size (Bc) for the egress 
      direction. It is used for bandwidth reservation for the purpose of 
      performing a Call Admission Control (CAC) function towards the 
      egress link.
      
      This attribute is not used to perform rate enforcement towards the 
      egress link."
   DEFVAL     { 64000 }
::= { mscFrAtmDlciEgSpProvEntry 2 }

mscFrAtmDlciEgSpExcessBurstSize OBJECT-TYPE
   SYNTAX     Unsigned32 (0..50000000)
   ACCESS     read-write
   STATUS     mandatory
   DESCRIPTION
     "This attribute specifies the excess burst size (Be) for the egress 
      direction. It is used for bandwidth reservation for the purpose of 
      performing a Call Admission Control (CAC) function towards the 
      egress link.
      
      This attribute is not used to perform rate enforcement towards the 
      egress link."
   DEFVAL     { 0 }
::= { mscFrAtmDlciEgSpProvEntry 3 }

mscFrAtmDlciEgSpMeasurementInterval OBJECT-TYPE
   SYNTAX     Unsigned32 (0..25500)
   ACCESS     read-write
   STATUS     mandatory
   DESCRIPTION
     "This attribute specifies the time interval for the egress direction. It is 
      used for bandwidth reservation for the purpose of performing a Call 
      Admission Control (CAC) function towards the egress link.
      
      This attribute is not used to perform rate enforcement towards the 
      egress link."
   DEFVAL     { 0 }
::= { mscFrAtmDlciEgSpProvEntry 4 }


-- FrUni/n VirtualFramer
-- FrDte/n VirtualFramer
-- The VirtualFramer component binds two services together to 
-- provide data transfer between them. It is mutually exclusive from 
-- Framer component. 

mscFrAtmVFramer OBJECT IDENTIFIER ::= { mscFrAtm 5 }



mscFrAtmVFramerRowStatusTable OBJECT-TYPE
   SYNTAX     SEQUENCE OF MscFrAtmVFramerRowStatusEntry
   ACCESS     not-accessible
   STATUS     mandatory
   DESCRIPTION
     "This entry controls the addition and deletion of 
      mscFrAtmVFramer components."
::= { mscFrAtmVFramer 1 }

mscFrAtmVFramerRowStatusEntry OBJECT-TYPE
   SYNTAX     MscFrAtmVFramerRowStatusEntry
   ACCESS     not-accessible
   STATUS     mandatory
   DESCRIPTION
     "A single entry in the table represents a single 
      mscFrAtmVFramer component."
   INDEX {
      mscFrAtmIndex,
      mscFrAtmVFramerIndex }
::= { mscFrAtmVFramerRowStatusTable 1 }

MscFrAtmVFramerRowStatusEntry ::= SEQUENCE {
   mscFrAtmVFramerRowStatus
      RowStatus,
   mscFrAtmVFramerComponentName
      DisplayString,
   mscFrAtmVFramerStorageType
      StorageType,
   mscFrAtmVFramerIndex
      NonReplicated }

mscFrAtmVFramerRowStatus OBJECT-TYPE
   SYNTAX     RowStatus 
   ACCESS     read-write
   STATUS     mandatory
   DESCRIPTION
     "This variable is used as the basis for SNMP naming of
      mscFrAtmVFramer components.
      These components can be added and deleted."
::= { mscFrAtmVFramerRowStatusEntry 1 }

mscFrAtmVFramerComponentName OBJECT-TYPE
   SYNTAX     DisplayString 
   ACCESS     read-only
   STATUS     mandatory
   DESCRIPTION
     "This variable provides the component's string name for
      use with the ASCII Console Interface"
::= { mscFrAtmVFramerRowStatusEntry 2 }

mscFrAtmVFramerStorageType OBJECT-TYPE
   SYNTAX     StorageType 
   ACCESS     read-only
   STATUS     mandatory
   DESCRIPTION
     "This variable represents the storage type value for the
      mscFrAtmVFramer tables."
::= { mscFrAtmVFramerRowStatusEntry 4 }

mscFrAtmVFramerIndex OBJECT-TYPE
   SYNTAX     NonReplicated 
   ACCESS     not-accessible
   STATUS     mandatory
   DESCRIPTION
     "This variable represents the index for the mscFrAtmVFramer tables."
::= { mscFrAtmVFramerRowStatusEntry 10 }

mscFrAtmVFramerProvTable OBJECT-TYPE
   SYNTAX     SEQUENCE OF MscFrAtmVFramerProvEntry
   ACCESS     not-accessible
   STATUS     mandatory
   DESCRIPTION
     "This group contains provisionable attributes for the VirtualFramer 
      component."
::= { mscFrAtmVFramer 10 }

mscFrAtmVFramerProvEntry OBJECT-TYPE
   SYNTAX     MscFrAtmVFramerProvEntry
   ACCESS     not-accessible
   STATUS     mandatory
   DESCRIPTION
     "An entry in the mscFrAtmVFramerProvTable."
   INDEX {
      mscFrAtmIndex,
      mscFrAtmVFramerIndex }
::= { mscFrAtmVFramerProvTable 1 }

MscFrAtmVFramerProvEntry ::= SEQUENCE {
   mscFrAtmVFramerOtherVirtualFramer
      Link,
   mscFrAtmVFramerLogicalProcessor
      Link }

mscFrAtmVFramerOtherVirtualFramer OBJECT-TYPE
   SYNTAX     Link 
   ACCESS     read-write
   STATUS     mandatory
   DESCRIPTION
     "This attribute specifies the other VirtualFramer to which the service 
      is linked, for example, FrUni/n VirtualFramer, FrDte/n 
      VirtualFramer."
::= { mscFrAtmVFramerProvEntry 1 }

mscFrAtmVFramerLogicalProcessor OBJECT-TYPE
   SYNTAX     Link 
   ACCESS     read-write
   STATUS     mandatory
   DESCRIPTION
     "This attribute specifies the logical processor on which the service 
      component will reside."
::= { mscFrAtmVFramerProvEntry 2 }

mscFrAtmVFramerStateTable OBJECT-TYPE
   SYNTAX     SEQUENCE OF MscFrAtmVFramerStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscFrAtmVFramer 11 }

mscFrAtmVFramerStateEntry OBJECT-TYPE
   SYNTAX     MscFrAtmVFramerStateEntry
   ACCESS     not-accessible
   STATUS     mandatory
   DESCRIPTION
     "An entry in the mscFrAtmVFramerStateTable."
   INDEX {
      mscFrAtmIndex,
      mscFrAtmVFramerIndex }
::= { mscFrAtmVFramerStateTable 1 }

MscFrAtmVFramerStateEntry ::= SEQUENCE {
   mscFrAtmVFramerAdminState
      INTEGER,
   mscFrAtmVFramerOperationalState
      INTEGER,
   mscFrAtmVFramerUsageState
      INTEGER }

mscFrAtmVFramerAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscFrAtmVFramerStateEntry 1 }

mscFrAtmVFramerOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscFrAtmVFramerStateEntry 2 }

mscFrAtmVFramerUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscFrAtmVFramerStateEntry 3 }

mscFrAtmVFramerStatsTable OBJECT-TYPE
   SYNTAX     SEQUENCE OF MscFrAtmVFramerStatsEntry
   ACCESS     not-accessible
   STATUS     mandatory
   DESCRIPTION
     "This group contains the operational statistics data for a 
      VirtualFramer component."
::= { mscFrAtmVFramer 12 }

mscFrAtmVFramerStatsEntry OBJECT-TYPE
   SYNTAX     MscFrAtmVFramerStatsEntry
   ACCESS     not-accessible
   STATUS     mandatory
   DESCRIPTION
     "An entry in the mscFrAtmVFramerStatsTable."
   INDEX {
      mscFrAtmIndex,
      mscFrAtmVFramerIndex }
::= { mscFrAtmVFramerStatsTable 1 }

MscFrAtmVFramerStatsEntry ::= SEQUENCE {
   mscFrAtmVFramerFrmToOtherVFramer
      PassportCounter64,
   mscFrAtmVFramerFrmFromOtherVFramer
      PassportCounter64,
   mscFrAtmVFramerOctetFromOtherVFramer
      PassportCounter64 }

mscFrAtmVFramerFrmToOtherVFramer OBJECT-TYPE
   SYNTAX     PassportCounter64 
   ACCESS     read-only
   STATUS     mandatory
   DESCRIPTION
     "This attribute counts the frames transmitted to the 
      otherVirtualFramer."
::= { mscFrAtmVFramerStatsEntry 2 }

mscFrAtmVFramerFrmFromOtherVFramer OBJECT-TYPE
   SYNTAX     PassportCounter64 
   ACCESS     read-only
   STATUS     mandatory
   DESCRIPTION
     "This attribute counts the frames received from the 
      otherVirtualFramer."
::= { mscFrAtmVFramerStatsEntry 3 }

mscFrAtmVFramerOctetFromOtherVFramer OBJECT-TYPE
   SYNTAX     PassportCounter64 
   ACCESS     read-only
   STATUS     mandatory
   DESCRIPTION
     "This attribute counts the octets received from the 
      otherVirtualFramer."
::= { mscFrAtmVFramerStatsEntry 5 }


-- FrAtm/n Address
-- The Addr component contains the address for a FrAtm interface that 
-- supports native E.164 or X.121.

mscFrAtmAddr OBJECT IDENTIFIER ::= { mscFrAtm 6 }



mscFrAtmAddrRowStatusTable OBJECT-TYPE
   SYNTAX     SEQUENCE OF MscFrAtmAddrRowStatusEntry
   ACCESS     not-accessible
   STATUS     mandatory
   DESCRIPTION
     "This entry controls the addition and deletion of 
      mscFrAtmAddr components."
::= { mscFrAtmAddr 1 }

mscFrAtmAddrRowStatusEntry OBJECT-TYPE
   SYNTAX     MscFrAtmAddrRowStatusEntry
   ACCESS     not-accessible
   STATUS     mandatory
   DESCRIPTION
     "A single entry in the table represents a single 
      mscFrAtmAddr component."
   INDEX {
      mscFrAtmIndex,
      mscFrAtmAddrIndex }
::= { mscFrAtmAddrRowStatusTable 1 }

MscFrAtmAddrRowStatusEntry ::= SEQUENCE {
   mscFrAtmAddrRowStatus
      RowStatus,
   mscFrAtmAddrComponentName
      DisplayString,
   mscFrAtmAddrStorageType
      StorageType,
   mscFrAtmAddrIndex
      NonReplicated }

mscFrAtmAddrRowStatus OBJECT-TYPE
   SYNTAX     RowStatus 
   ACCESS     read-write
   STATUS     mandatory
   DESCRIPTION
     "This variable is used as the basis for SNMP naming of
      mscFrAtmAddr components.
      These components can be added and deleted."
::= { mscFrAtmAddrRowStatusEntry 1 }

mscFrAtmAddrComponentName OBJECT-TYPE
   SYNTAX     DisplayString 
   ACCESS     read-only
   STATUS     mandatory
   DESCRIPTION
     "This variable provides the component's string name for
      use with the ASCII Console Interface"
::= { mscFrAtmAddrRowStatusEntry 2 }

mscFrAtmAddrStorageType OBJECT-TYPE
   SYNTAX     StorageType 
   ACCESS     read-only
   STATUS     mandatory
   DESCRIPTION
     "This variable represents the storage type value for the
      mscFrAtmAddr tables."
::= { mscFrAtmAddrRowStatusEntry 4 }

mscFrAtmAddrIndex OBJECT-TYPE
   SYNTAX     NonReplicated 
   ACCESS     not-accessible
   STATUS     mandatory
   DESCRIPTION
     "This variable represents the index for the mscFrAtmAddr tables."
::= { mscFrAtmAddrRowStatusEntry 10 }

mscFrAtmAddrProvTable OBJECT-TYPE
   SYNTAX     SEQUENCE OF MscFrAtmAddrProvEntry
   ACCESS     not-accessible
   STATUS     mandatory
   DESCRIPTION
     "This group specifies the address of the FrAtm Interface."
::= { mscFrAtmAddr 10 }

mscFrAtmAddrProvEntry OBJECT-TYPE
   SYNTAX     MscFrAtmAddrProvEntry
   ACCESS     not-accessible
   STATUS     mandatory
   DESCRIPTION
     "An entry in the mscFrAtmAddrProvTable."
   INDEX {
      mscFrAtmIndex,
      mscFrAtmAddrIndex }
::= { mscFrAtmAddrProvTable 1 }

MscFrAtmAddrProvEntry ::= SEQUENCE {
   mscFrAtmAddrAddress
      AsciiString }

mscFrAtmAddrAddress OBJECT-TYPE
   SYNTAX     AsciiString (SIZE (1..44))
   ACCESS     read-write
   STATUS     mandatory
   DESCRIPTION
     "This attribute contains digits which form the unique identifier of the 
      customer. It is the equivalent of the telephone number in the 
      telephone network (either native E.164 or X.121 address formats, or 
      Atm End System Address(AESA) in ISO NSAP format.). 
      
      For example, E.164 prefix 'e.613722', X.121 prefix 'x.302', NSAP 
      '45000441812460730F000000000020480D200100'."
::= { mscFrAtmAddrProvEntry 2 }

mscFrAtmAddrAddrOpTable OBJECT-TYPE
   SYNTAX     SEQUENCE OF MscFrAtmAddrAddrOpEntry
   ACCESS     not-accessible
   STATUS     mandatory
   DESCRIPTION
     "This group display the address of the FrAtm Interface."
::= { mscFrAtmAddr 11 }

mscFrAtmAddrAddrOpEntry OBJECT-TYPE
   SYNTAX     MscFrAtmAddrAddrOpEntry
   ACCESS     not-accessible
   STATUS     mandatory
   DESCRIPTION
     "An entry in the mscFrAtmAddrAddrOpTable."
   INDEX {
      mscFrAtmIndex,
      mscFrAtmAddrIndex }
::= { mscFrAtmAddrAddrOpTable 1 }

MscFrAtmAddrAddrOpEntry ::= SEQUENCE {
   mscFrAtmAddrMyAddress
      AsciiString }

mscFrAtmAddrMyAddress OBJECT-TYPE
   SYNTAX     AsciiString (SIZE (40))
   ACCESS     read-only
   STATUS     mandatory
   DESCRIPTION
     "This attribute displays the parent FRATM component's address in 
      the ISO NSAP format."
::= { mscFrAtmAddrAddrOpEntry 1 }


-- FrAtm/n ConnectionAdministrator
-- The Ca component allows common subscription options applicable 
-- to interworking with ATM  networking to be specified by the 
-- network operator on a FrAtm interface. The values defined under 
-- the Ca component interface defaults are  used for the majority of 
-- the connections. For exception cases, the interface defaults specified 
-- in the Ca component can be overridden on a per connection basis by 
-- provisioning FrAtm Dlci Siwf Qos or FrAtm Dlci Niwf Qos 
-- components.

mscFrAtmCa OBJECT IDENTIFIER ::= { mscFrAtm 7 }



mscFrAtmCaRowStatusTable OBJECT-TYPE
   SYNTAX     SEQUENCE OF MscFrAtmCaRowStatusEntry
   ACCESS     not-accessible
   STATUS     mandatory
   DESCRIPTION
     "This entry controls the addition and deletion of 
      mscFrAtmCa components."
::= { mscFrAtmCa 1 }

mscFrAtmCaRowStatusEntry OBJECT-TYPE
   SYNTAX     MscFrAtmCaRowStatusEntry
   ACCESS     not-accessible
   STATUS     mandatory
   DESCRIPTION
     "A single entry in the table represents a single 
      mscFrAtmCa component."
   INDEX {
      mscFrAtmIndex,
      mscFrAtmCaIndex }
::= { mscFrAtmCaRowStatusTable 1 }

MscFrAtmCaRowStatusEntry ::= SEQUENCE {
   mscFrAtmCaRowStatus
      RowStatus,
   mscFrAtmCaComponentName
      DisplayString,
   mscFrAtmCaStorageType
      StorageType,
   mscFrAtmCaIndex
      NonReplicated }

mscFrAtmCaRowStatus OBJECT-TYPE
   SYNTAX     RowStatus 
   ACCESS     read-only
   STATUS     mandatory
   DESCRIPTION
     "This variable is used as the basis for SNMP naming of
      mscFrAtmCa components.
      These components cannot be added nor deleted."
::= { mscFrAtmCaRowStatusEntry 1 }

mscFrAtmCaComponentName OBJECT-TYPE
   SYNTAX     DisplayString 
   ACCESS     read-only
   STATUS     mandatory
   DESCRIPTION
     "This variable provides the component's string name for
      use with the ASCII Console Interface"
::= { mscFrAtmCaRowStatusEntry 2 }

mscFrAtmCaStorageType OBJECT-TYPE
   SYNTAX     StorageType 
   ACCESS     read-only
   STATUS     mandatory
   DESCRIPTION
     "This variable represents the storage type value for the
      mscFrAtmCa tables."
::= { mscFrAtmCaRowStatusEntry 4 }

mscFrAtmCaIndex OBJECT-TYPE
   SYNTAX     NonReplicated 
   ACCESS     not-accessible
   STATUS     mandatory
   DESCRIPTION
     "This variable represents the index for the mscFrAtmCa tables."
::= { mscFrAtmCaRowStatusEntry 10 }

mscFrAtmCaProvTable OBJECT-TYPE
   SYNTAX     SEQUENCE OF MscFrAtmCaProvEntry
   ACCESS     not-accessible
   STATUS     mandatory
   DESCRIPTION
     "This attribute group contains the common provisionable attributes 
      of the Ca component."
::= { mscFrAtmCa 10 }

mscFrAtmCaProvEntry OBJECT-TYPE
   SYNTAX     MscFrAtmCaProvEntry
   ACCESS     not-accessible
   STATUS     mandatory
   DESCRIPTION
     "An entry in the mscFrAtmCaProvTable."
   INDEX {
      mscFrAtmIndex,
      mscFrAtmCaIndex }
::= { mscFrAtmCaProvTable 1 }

MscFrAtmCaProvEntry ::= SEQUENCE {
   mscFrAtmCaCallAdmissionControl
      INTEGER,
   mscFrAtmCaOverrideLinkRate
      Unsigned32 }

mscFrAtmCaCallAdmissionControl OBJECT-TYPE
   SYNTAX     INTEGER  {
                 off(0),
                 on(1) }
   ACCESS     read-write
   STATUS     mandatory
   DESCRIPTION
     "This attribute specifies the control to turn on Call Admission 
      Control (CAC).  The default value for CAC is off."
   DEFVAL     { off }
::= { mscFrAtmCaProvEntry 1 }

mscFrAtmCaOverrideLinkRate OBJECT-TYPE
   SYNTAX     Unsigned32 (0..520000000)
   ACCESS     read-write
   STATUS     mandatory
   DESCRIPTION
     "This attribute allows the link rate to be overridden for this interface.  
      This allows the user to specify a value other than the actual physical 
      link rate computed when a Framer component is provisioned.  In 
      the absence of a Framer component, or when a VirtualFramer 
      component is provisioned, this value needs to be explictly set to 
      provide an equivalent link rate.
      
      This attribute provides control on the amount of bandwidth 
      available for performing CAC. This attribute also provides the 
      requested amount of bandwidth that is negotiated across an  ATM 
      network for traffic conversion polices 3 and 4, since these policies 
      are a function of the access rate."
   DEFVAL     { 0 }
::= { mscFrAtmCaProvEntry 2 }

mscFrAtmCaSdTable OBJECT-TYPE
   SYNTAX     SEQUENCE OF MscFrAtmCaSdEntry
   ACCESS     not-accessible
   STATUS     mandatory
   DESCRIPTION
     "This group contains provisionable service interworking attributes 
      for the FrAtm component. The attributes defined in this group 
      provide the defaults for all the connections on the FrAtm interface."
::= { mscFrAtmCa 11 }

mscFrAtmCaSdEntry OBJECT-TYPE
   SYNTAX     MscFrAtmCaSdEntry
   ACCESS     not-accessible
   STATUS     mandatory
   DESCRIPTION
     "An entry in the mscFrAtmCaSdTable."
   INDEX {
      mscFrAtmIndex,
      mscFrAtmCaIndex }
::= { mscFrAtmCaSdTable 1 }

MscFrAtmCaSdEntry ::= SEQUENCE {
   mscFrAtmCaSdMode
      INTEGER,
   mscFrAtmCaSdDeToClpMapping
      INTEGER,
   mscFrAtmCaSdClpToDeMapping
      INTEGER,
   mscFrAtmCaSdFecnToEfciMapping
      INTEGER,
   mscFrAtmCaSdCrToUuMapping
      INTEGER }

mscFrAtmCaSdMode OBJECT-TYPE
   SYNTAX     INTEGER  {
                 translationMode(0),
                 transparentMode(1),
                 speTranslationMode(2) }
   ACCESS     read-write
   STATUS     mandatory
   DESCRIPTION
     "This attribute specifies the mode of interoperability between the 
      Frame Relay and ATM connections regarding upper layer protocol 
      encapsulations. This is used as the default for all the connections on 
      the interface.
      
      When translationMode is selected, the interworking function 
      performs translations between RFC1490 and RFC1483 
      encapsulated headers.  This includes routed protocol translation, 
      bridged protocol translation, and connection oriented protocol 
      translation (except for RFC 1490 connection oriented protocol 
      without RFC 1490 header, which is done in speTranslationMode). 
      
      A value of transparentMode indicates that the interworking 
      function is forwarding data without altering the upper layer user 
      protocol encapsulation. Use transparent mode when the upper layer 
      user protocol encapsulation methods are compatible between 
      terminal equipments.
      
      A value of speTranslationMode indicates that the interworking 
      function performs single protocol translation between RFC1490 
      with no header and RFC1483 encapsulated packets."
   DEFVAL     { translationMode }
::= { mscFrAtmCaSdEntry 1 }

mscFrAtmCaSdDeToClpMapping OBJECT-TYPE
   SYNTAX     INTEGER  {
                 always0(0),
                 always1(1),
                 preserve(2) }
   ACCESS     read-write
   STATUS     mandatory
   DESCRIPTION
     "This attribute specifies the DE to CLP mapping that is performed in 
      the Frame Relay to ATM direction. This is used as the default for all 
      the connections on the interface.
      
      When preserve is selected, the DE field in a Q.922 core frame 
      copies to the ATM CLP field of every cell containing the 
      information of that frame.
      
      When always0 is selected, the CLP field of every generated ATM 
      cell is always 0.
      
      When always1 is selected, the CLP field of every generated ATM 
      cell is always 1."
   DEFVAL     { preserve }
::= { mscFrAtmCaSdEntry 2 }

mscFrAtmCaSdClpToDeMapping OBJECT-TYPE
   SYNTAX     INTEGER  {
                 always0(0),
                 always1(1),
                 preserve(2) }
   ACCESS     read-write
   STATUS     mandatory
   DESCRIPTION
     "This attribute specifies the type of CLP to DE mapping that is 
      performed in the ATM to Frame Relay direction.
      
      When preserve is selected, the DE field of the Q.922 core frame is 
      set when one or more ATM cells belonging to an AAL5 frame has 
      its CLP field set.
      
      When always0 is selected, the DE field of the Q.922 core frame is 
      always set to 0.
      
      When always1 is selected, the DE field of the Q.922 core frame is 
      always set to 1."
   DEFVAL     { preserve }
::= { mscFrAtmCaSdEntry 3 }

mscFrAtmCaSdFecnToEfciMapping OBJECT-TYPE
   SYNTAX     INTEGER  {
                 always0(0),
                 preserve(2) }
   ACCESS     read-write
   STATUS     mandatory
   DESCRIPTION
     "This attribute specifies the type of FECN to EFCI mapping that is 
      performed in the Frame Relay to ATM direction.
      
      When preserve is selected, the FECN field in the Q.922 Core frame 
      maps directly to the ATM EFCI field of every cell generated by the 
      AAL5 segmentation process.
      
      When always0 is selected, the EFCI field in every ATM cell 
      generated is set to 0."
   DEFVAL     { preserve }
::= { mscFrAtmCaSdEntry 4 }

mscFrAtmCaSdCrToUuMapping OBJECT-TYPE
   SYNTAX     INTEGER  {
                 always0(0),
                 preserve(2) }
   ACCESS     read-write
   STATUS     obsolete
   DESCRIPTION
     "This attribute indicates the type of CR to UU mapping that is 
      performed in the Frame Relay to ATM direction.
      
      A value of preserve indicates that the CR field in the Q.922 Core 
      frame maps directly to the ATM UU field of every cell generated by 
      the AAL5 segmentation process.
      
      A value of always0 indicates that the UU field in every ATM cell 
      generated is set to 0."
   DEFVAL     { preserve }
::= { mscFrAtmCaSdEntry 5 }

mscFrAtmCaNdTable OBJECT-TYPE
   SYNTAX     SEQUENCE OF MscFrAtmCaNdEntry
   ACCESS     not-accessible
   STATUS     mandatory
   DESCRIPTION
     "This group contains the default provisionable networking attributes 
      for the FrAtm component."
::= { mscFrAtmCa 12 }

mscFrAtmCaNdEntry OBJECT-TYPE
   SYNTAX     MscFrAtmCaNdEntry
   ACCESS     not-accessible
   STATUS     mandatory
   DESCRIPTION
     "An entry in the mscFrAtmCaNdTable."
   INDEX {
      mscFrAtmIndex,
      mscFrAtmCaIndex }
::= { mscFrAtmCaNdTable 1 }

MscFrAtmCaNdEntry ::= SEQUENCE {
   mscFrAtmCaNdDeToClpMapping
      INTEGER,
   mscFrAtmCaNdClpToDeMapping
      INTEGER }

mscFrAtmCaNdDeToClpMapping OBJECT-TYPE
   SYNTAX     INTEGER  {
                 always0(0),
                 always1(1),
                 preserve(2) }
   ACCESS     read-write
   STATUS     mandatory
   DESCRIPTION
     "This attribute specifies the type of DE to CLP mapping to be 
      performed in the Frame Relay to ATM direction.
      When preserve is selected, the DE field in the Q.922 core frame  
      copies to the CLP field of every ATM cell containing the frame.
      When always0 is selected, the CLP field of every ATM cell is 
      always set to 0.
      When always1 is selected, the CLP field of every ATM cell is 
      always set to 1."
   DEFVAL     { preserve }
::= { mscFrAtmCaNdEntry 1 }

mscFrAtmCaNdClpToDeMapping OBJECT-TYPE
   SYNTAX     INTEGER  {
                 preserve(2),
                 transparent(3) }
   ACCESS     read-write
   STATUS     mandatory
   DESCRIPTION
     "This attribute specifies the type of CLP to DE mapping to be 
      performed in the ATM to Frame Relay direction.
      When preserve is selected, the DE field of the Q.922 core frame is 
      set when one or more ATM cells belonging to the frame has its CLP 
      field set, or when the DE field of the FR-SSCS PDU is set.
      When transparent is selected, the DE field of the Q.922 core frame 
      copies directly from the DE field of the FR-SSCS PDU."
   DEFVAL     { preserve }
::= { mscFrAtmCaNdEntry 2 }

mscFrAtmCaIfQoSTable OBJECT-TYPE
   SYNTAX     SEQUENCE OF MscFrAtmCaIfQoSEntry
   ACCESS     not-accessible
   STATUS     mandatory
   DESCRIPTION
     "This attribute group contains the provisionable quality of service 
      attributes for the parent FrAtm interface."
::= { mscFrAtmCa 13 }

mscFrAtmCaIfQoSEntry OBJECT-TYPE
   SYNTAX     MscFrAtmCaIfQoSEntry
   ACCESS     not-accessible
   STATUS     mandatory
   DESCRIPTION
     "An entry in the mscFrAtmCaIfQoSTable."
   INDEX {
      mscFrAtmIndex,
      mscFrAtmCaIndex }
::= { mscFrAtmCaIfQoSTable 1 }

MscFrAtmCaIfQoSEntry ::= SEQUENCE {
   mscFrAtmCaSiwfEmissionPriorityToIf
      INTEGER,
   mscFrAtmCaSiwfTransferPriority
      INTEGER,
   mscFrAtmCaNiwfEmissionPriorityToIf
      INTEGER,
   mscFrAtmCaNiwfTransferPriority
      INTEGER }

mscFrAtmCaSiwfEmissionPriorityToIf OBJECT-TYPE
   SYNTAX     INTEGER  {
                 n0(0),
                 n1(1),
                 n2(2),
                 n3(3),
                 deriveFromTp(254) }
   ACCESS     read-write
   STATUS     mandatory
   DESCRIPTION
     "This attribute specifies the emission priority of frames sent to this 
      FrAtm interface from its service interworking functions. Frames in 
      a higher priority queue, designated by a numerically higher number, 
      are sent before frames in a lower priority queue.
      The value of this attribute is interpreted according to the value of 
      the provisionable attribute numberOfEmissionQs under the parent 
      FrAtm component. If the numberOfEmissionQs attribute is set to 2, 
      siwfEmissionPriorityToIf value of 0  maps to emission priority 
      queue 0 representing a lower priority queue, and 
      siwfEmissionPriorityToIf values of 1, 2 or 3  map to emission 
      priority queue 1 representing the highest priority queue. If the 
      numberOfEmissionQs is set to 4, the siwfEmissionPriorityToIf 
      values directly map to the emission priority queues.
      A value of deriveFromTp specifies that the emission priority is 
      extracted from the Mod Frs AtmNet Tpm/n component using the 
      siwfTransferPriority attribute.
      The siwfEmissionPriorityToIf can also be overridden on a per 
      connection basis by setting the emissionPriorityToIf attribute in the 
      FrAtm Dlci Siwf Qos component."
   DEFVAL     { n0 }
::= { mscFrAtmCaIfQoSEntry 1 }

mscFrAtmCaSiwfTransferPriority OBJECT-TYPE
   SYNTAX     INTEGER (0..15)
   ACCESS     read-write
   STATUS     mandatory
   DESCRIPTION
     "This attribute specifies the transfer priority of frames sent to and 
      received from the ATM connection, through the service 
      interworking functions of this interface.
      In the Frame Relay to ATM direction, the stp selects the ATM 
      service category of the connection.
      In the ATM to Frame Relay direction, the stp selects the FrAtm 
      emission priority queue.
      The siwfTransferPriority can also be overridden on a per 
      connection basis by setting the transferPriority atribute in the 
      FrAtm Dlci Siwf Qos component."
   DEFVAL     { 0 }
::= { mscFrAtmCaIfQoSEntry 2 }

mscFrAtmCaNiwfEmissionPriorityToIf OBJECT-TYPE
   SYNTAX     INTEGER  {
                 n0(0),
                 n1(1),
                 n2(2),
                 n3(3),
                 deriveFromTp(254) }
   ACCESS     read-write
   STATUS     mandatory
   DESCRIPTION
     "This attribute specifies the emission priority of frames sent to this 
      FrAtm interface from its network interworking functions. Frames in 
      a higher priority queue are sent before frames in a lower priority 
      queue.
      The value of this attribute is interpreted according to the value of 
      the provisionable attribute numberOfEmissionQs under the parent 
      FrAtm component. If the numberOfEmissionQs attribute is set to 2, 
      niwfEmissionPriorityToIf value of 0 maps to emission priority 
      queue 0 representing a lower priority queue, and 
      niwfEmissionPriorityToIf values of 1, 2 or 3  map to emission 
      priority queue 1 representing the highest priority queue. If the 
      numberOfEmissionQs is set to 4, the emissionPrioToIf values  
      directly assign to the emission priority queues.
      A value of deriveFromTp specifies that the emission priority is 
      extracted from the Mod Frs AtmNet Tpm/n component using the 
      niwfTransferPriority attribute.
      The niwfEmissionPriorityToIf can also be overridden on a per 
      connection basis by setting the emissionPriorityToIf atribute in the 
      FrAtm Dlci Niwf Qos component."
   DEFVAL     { deriveFromTp }
::= { mscFrAtmCaIfQoSEntry 3 }

mscFrAtmCaNiwfTransferPriority OBJECT-TYPE
   SYNTAX     INTEGER (0..15)
   ACCESS     read-write
   STATUS     mandatory
   DESCRIPTION
     "This attribute specifies the transfer priority of frames sent to and 
      received from the ATM connection, through the network 
      interworking functions of this interface.
      In the Frame Relay to ATM direction, the ntp selects the 
      Frf5EndPoint which multiplexes the frames.
      In the ATM to Frame Relay direction, the ntp selects the default 
      FrAtm emission priority queue.
      The niwfTransferPriority can also be overridden on a per 
      connection basis by setting the transferPriority atribute in the 
      FrAtm Dlci Niwf Qos component."
   DEFVAL     { 0 }
::= { mscFrAtmCaIfQoSEntry 4 }

mscFrAtmCaOpTable OBJECT-TYPE
   SYNTAX     SEQUENCE OF MscFrAtmCaOpEntry
   ACCESS     not-accessible
   STATUS     mandatory
   DESCRIPTION
     "This attribute group contains the operational status of the Ca 
      component."
::= { mscFrAtmCa 14 }

mscFrAtmCaOpEntry OBJECT-TYPE
   SYNTAX     MscFrAtmCaOpEntry
   ACCESS     not-accessible
   STATUS     mandatory
   DESCRIPTION
     "An entry in the mscFrAtmCaOpTable."
   INDEX {
      mscFrAtmIndex,
      mscFrAtmCaIndex }
::= { mscFrAtmCaOpTable 1 }

MscFrAtmCaOpEntry ::= SEQUENCE {
   mscFrAtmCaLinkRate
      Unsigned32,
   mscFrAtmCaNailedUpPvcs
      Gauge32,
   mscFrAtmCaTroubledDlcis
      Gauge32,
   mscFrAtmCaSoftPvcs
      Gauge32 }

mscFrAtmCaLinkRate OBJECT-TYPE
   SYNTAX     Unsigned32 (0..520000000)
   ACCESS     read-only
   STATUS     mandatory
   DESCRIPTION
     "This attribute indicates the link rate.
      
      If the provisionable attribute, overrideLinkRate, under the Ca 
      component is 0, then the link rate reported is the actual link rate of 
      the port or channel.  Otherwise, the link rate reported is the 
      overrideLinkRate provisioned under the Ca component."
::= { mscFrAtmCaOpEntry 1 }

mscFrAtmCaNailedUpPvcs OBJECT-TYPE
   SYNTAX     Gauge32 (0..5000)
   ACCESS     read-only
   STATUS     mandatory
   DESCRIPTION
     "This attribute indicates the number of nailed-Up PVCs currently 
      provisioned on this interface."
::= { mscFrAtmCaOpEntry 3 }

mscFrAtmCaTroubledDlcis OBJECT-TYPE
   SYNTAX     Gauge32 (0..5000)
   ACCESS     read-only
   STATUS     mandatory
   DESCRIPTION
     "This attribute indicates the total number of DLCIs that are disabled 
      and are experiencing problems.  This counter  increments as a  
      result of the following problem scenarios:
      Abit down, PVC down,  local CAC failure, or call setup failure due 
      to network problem."
::= { mscFrAtmCaOpEntry 5 }

mscFrAtmCaSoftPvcs OBJECT-TYPE
   SYNTAX     Gauge32 (0..5000)
   ACCESS     read-only
   STATUS     mandatory
   DESCRIPTION
     "This attribute indicates the number of soft PVCs currently 
      provisioned on this interface."
::= { mscFrAtmCaOpEntry 6 }

mscFrAtmCaAccountingOptionsTable OBJECT-TYPE
   SYNTAX     SEQUENCE OF MscFrAtmCaAccountingOptionsEntry
   ACCESS     not-accessible
   STATUS     mandatory
   DESCRIPTION
     "This group contains the common provisioned attributes for 
      accounting on a FrAtm."
::= { mscFrAtmCa 15 }

mscFrAtmCaAccountingOptionsEntry OBJECT-TYPE
   SYNTAX     MscFrAtmCaAccountingOptionsEntry
   ACCESS     not-accessible
   STATUS     mandatory
   DESCRIPTION
     "An entry in the mscFrAtmCaAccountingOptionsTable."
   INDEX {
      mscFrAtmIndex,
      mscFrAtmCaIndex }
::= { mscFrAtmCaAccountingOptionsTable 1 }

MscFrAtmCaAccountingOptionsEntry ::= SEQUENCE {
   mscFrAtmCaAccountClass
      Unsigned32,
   mscFrAtmCaAccountCollection
      OCTET STRING,
   mscFrAtmCaServiceExchange
      Unsigned32 }

mscFrAtmCaAccountClass OBJECT-TYPE
   SYNTAX     Unsigned32 (0..255)
   ACCESS     read-write
   STATUS     mandatory
   DESCRIPTION
     "This attribute specifies the accounting class, which is reserved for 
      network operations usage.  Its value is an arbitrary number. The 
      accounting records the value of this attribute."
   DEFVAL     { 0 }
::= { mscFrAtmCaAccountingOptionsEntry 1 }

mscFrAtmCaAccountCollection OBJECT-TYPE
   SYNTAX     OCTET STRING (SIZE (1))
   ACCESS     read-write
   STATUS     mandatory
   DESCRIPTION
     "This attribute controls accounting data collection at the interface 
      level.  It contains the following values:  bill, test, study, audit, force  
      which are used to specify the reason(s) for which accounting 
      records are collected. If the bill, test, study and audit options are 
      selected in the accountCollection field, accounting records are 
      collected for bill, test, study, or audit purposes.  If the force option 
      is selected in the accountCollection field, accounting records are 
      collected regardless of whether other reasons are provisioned.  If no 
      reason is provisioned for this attribute, then accounting data 
      collection does not occur.

      Description of bits:
      bill(0)
      test(1)
      study(2)
      audit(3)
      force(4)"
   DEFVAL     { '80'H }
::= { mscFrAtmCaAccountingOptionsEntry 2 }

mscFrAtmCaServiceExchange OBJECT-TYPE
   SYNTAX     Unsigned32 (0..255)
   ACCESS     read-write
   STATUS     mandatory
   DESCRIPTION
     "This attribute is an arbitrary number, which is reserved for network 
      operations usage.  It is recorded in the accounting record."
   DEFVAL     { 0 }
::= { mscFrAtmCaAccountingOptionsEntry 3 }

mscFrAtmCaBwPoolTable OBJECT-TYPE
   SYNTAX     SEQUENCE OF MscFrAtmCaBwPoolEntry
   ACCESS     not-accessible
   STATUS     mandatory
   DESCRIPTION
     "Port capacity is partitioned into 16 pools (pool 0 through pool 15). 
      This attribute specifies the percentage of port capacity that is 
      allowed for each pool. The percentage for each pool ranges from 
      0% to 1000%. It allows for under or over subscription of the port. 
      Under subscription occurs when the sum of the percentage assigned 
      to the 16 pools is less than 100%. Over subscription occurs when 
      the sum of the percentage for the 16 pools exceeds 100%.  The sum 
      of the percentage assigned to the 16 pools cannot exceed 1000%.
      
      The default is full sharing of port capacity without pre-set partitions 
      between transfer priorities."
::= { mscFrAtmCa 365 }

mscFrAtmCaBwPoolEntry OBJECT-TYPE
   SYNTAX     MscFrAtmCaBwPoolEntry
   ACCESS     not-accessible
   STATUS     mandatory
   DESCRIPTION
     "An entry in the mscFrAtmCaBwPoolTable."
   INDEX {
      mscFrAtmIndex,
      mscFrAtmCaIndex,
      mscFrAtmCaBwPoolIndex }
::= { mscFrAtmCaBwPoolTable 1 }

MscFrAtmCaBwPoolEntry ::= SEQUENCE {
   mscFrAtmCaBwPoolIndex
      Integer32,
   mscFrAtmCaBwPoolValue
      Unsigned32 }

mscFrAtmCaBwPoolIndex OBJECT-TYPE
   SYNTAX     Integer32 (0..15)
   ACCESS     not-accessible
   STATUS     mandatory
   DESCRIPTION
     "This variable represents the mscFrAtmCaBwPoolTable
      specific index for the mscFrAtmCaBwPoolTable."
::= { mscFrAtmCaBwPoolEntry 1 }

mscFrAtmCaBwPoolValue OBJECT-TYPE
   SYNTAX     Unsigned32 (0..1000)
   ACCESS     read-write
   STATUS     mandatory
   DESCRIPTION
     "This variable represents an individual value for the
      mscFrAtmCaBwPoolTable."
::= { mscFrAtmCaBwPoolEntry 2 }

mscFrAtmCaPoolProvBwTable OBJECT-TYPE
   SYNTAX     SEQUENCE OF MscFrAtmCaPoolProvBwEntry
   ACCESS     not-accessible
   STATUS     mandatory
   DESCRIPTION
     "This attribute indicates the total bandwidth requested for 
      provisioned connections from each bandwidth pool.  Total 
      bandwidth for a given pool can be oversubcribed or undersubcribed."
::= { mscFrAtmCa 366 }

mscFrAtmCaPoolProvBwEntry OBJECT-TYPE
   SYNTAX     MscFrAtmCaPoolProvBwEntry
   ACCESS     not-accessible
   STATUS     mandatory
   DESCRIPTION
     "An entry in the mscFrAtmCaPoolProvBwTable."
   INDEX {
      mscFrAtmIndex,
      mscFrAtmCaIndex,
      mscFrAtmCaPoolProvBwIndex }
::= { mscFrAtmCaPoolProvBwTable 1 }

MscFrAtmCaPoolProvBwEntry ::= SEQUENCE {
   mscFrAtmCaPoolProvBwIndex
      Integer32,
   mscFrAtmCaPoolProvBwValue
      Gauge32 }

mscFrAtmCaPoolProvBwIndex OBJECT-TYPE
   SYNTAX     Integer32 (0..15)
   ACCESS     not-accessible
   STATUS     mandatory
   DESCRIPTION
     "This variable represents the mscFrAtmCaPoolProvBwTable
      specific index for the mscFrAtmCaPoolProvBwTable."
::= { mscFrAtmCaPoolProvBwEntry 1 }

mscFrAtmCaPoolProvBwValue OBJECT-TYPE
   SYNTAX     Gauge32 (0..520000000)
   ACCESS     read-only
   STATUS     mandatory
   DESCRIPTION
     "This variable represents an individual value for the
      mscFrAtmCaPoolProvBwTable."
::= { mscFrAtmCaPoolProvBwEntry 2 }

mscFrAtmCaPoolAvailBwTable OBJECT-TYPE
   SYNTAX     SEQUENCE OF MscFrAtmCaPoolAvailBwEntry
   ACCESS     not-accessible
   STATUS     mandatory
   DESCRIPTION
     "This attribute indicates the total available bandwidth from the 
      bandwidth pool."
::= { mscFrAtmCa 367 }

mscFrAtmCaPoolAvailBwEntry OBJECT-TYPE
   SYNTAX     MscFrAtmCaPoolAvailBwEntry
   ACCESS     not-accessible
   STATUS     mandatory
   DESCRIPTION
     "An entry in the mscFrAtmCaPoolAvailBwTable."
   INDEX {
      mscFrAtmIndex,
      mscFrAtmCaIndex,
      mscFrAtmCaPoolAvailBwIndex }
::= { mscFrAtmCaPoolAvailBwTable 1 }

MscFrAtmCaPoolAvailBwEntry ::= SEQUENCE {
   mscFrAtmCaPoolAvailBwIndex
      Integer32,
   mscFrAtmCaPoolAvailBwValue
      Gauge32 }

mscFrAtmCaPoolAvailBwIndex OBJECT-TYPE
   SYNTAX     Integer32 (0..15)
   ACCESS     not-accessible
   STATUS     mandatory
   DESCRIPTION
     "This variable represents the mscFrAtmCaPoolAvailBwTable
      specific index for the mscFrAtmCaPoolAvailBwTable."
::= { mscFrAtmCaPoolAvailBwEntry 1 }

mscFrAtmCaPoolAvailBwValue OBJECT-TYPE
   SYNTAX     Gauge32 (0..52000000)
   ACCESS     read-only
   STATUS     mandatory
   DESCRIPTION
     "This variable represents an individual value for the
      mscFrAtmCaPoolAvailBwTable."
::= { mscFrAtmCaPoolAvailBwEntry 2 }

mscFrAtmCaPoolAdmitBwTable OBJECT-TYPE
   SYNTAX     SEQUENCE OF MscFrAtmCaPoolAdmitBwEntry
   ACCESS     not-accessible
   STATUS     mandatory
   DESCRIPTION
     "This attribute indicates the total admitted bandwidth from each 
      bandwidth pool. Each value is the sum of the equivalent bit rates of 
      the admitted connections."
::= { mscFrAtmCa 380 }

mscFrAtmCaPoolAdmitBwEntry OBJECT-TYPE
   SYNTAX     MscFrAtmCaPoolAdmitBwEntry
   ACCESS     not-accessible
   STATUS     mandatory
   DESCRIPTION
     "An entry in the mscFrAtmCaPoolAdmitBwTable."
   INDEX {
      mscFrAtmIndex,
      mscFrAtmCaIndex,
      mscFrAtmCaPoolAdmitBwIndex }
::= { mscFrAtmCaPoolAdmitBwTable 1 }

MscFrAtmCaPoolAdmitBwEntry ::= SEQUENCE {
   mscFrAtmCaPoolAdmitBwIndex
      Integer32,
   mscFrAtmCaPoolAdmitBwValue
      Gauge32 }

mscFrAtmCaPoolAdmitBwIndex OBJECT-TYPE
   SYNTAX     Integer32 (0..15)
   ACCESS     not-accessible
   STATUS     mandatory
   DESCRIPTION
     "This variable represents the mscFrAtmCaPoolAdmitBwTable
      specific index for the mscFrAtmCaPoolAdmitBwTable."
::= { mscFrAtmCaPoolAdmitBwEntry 1 }

mscFrAtmCaPoolAdmitBwValue OBJECT-TYPE
   SYNTAX     Gauge32 (0..520000000)
   ACCESS     read-only
   STATUS     mandatory
   DESCRIPTION
     "This variable represents an individual value for the
      mscFrAtmCaPoolAdmitBwTable."
::= { mscFrAtmCaPoolAdmitBwEntry 2 }


-- FrAtm/n Ca TransferPriorityMapping/n
-- The Tpm component defines the corresponding traffic management 
-- subscription options on a FrAtm interface corresponding to a 
-- particular transfer priority.  This component is needed only if there 
-- is a requirement to override the Mod Frs AtmNet Tpm component 
-- defaults.

mscFrAtmCaTpm OBJECT IDENTIFIER ::= { mscFrAtmCa 2 }



mscFrAtmCaTpmRowStatusTable OBJECT-TYPE
   SYNTAX     SEQUENCE OF MscFrAtmCaTpmRowStatusEntry
   ACCESS     not-accessible
   STATUS     mandatory
   DESCRIPTION
     "This entry controls the addition and deletion of 
      mscFrAtmCaTpm components."
::= { mscFrAtmCaTpm 1 }

mscFrAtmCaTpmRowStatusEntry OBJECT-TYPE
   SYNTAX     MscFrAtmCaTpmRowStatusEntry
   ACCESS     not-accessible
   STATUS     mandatory
   DESCRIPTION
     "A single entry in the table represents a single 
      mscFrAtmCaTpm component."
   INDEX {
      mscFrAtmIndex,
      mscFrAtmCaIndex,
      mscFrAtmCaTpmIndex }
::= { mscFrAtmCaTpmRowStatusTable 1 }

MscFrAtmCaTpmRowStatusEntry ::= SEQUENCE {
   mscFrAtmCaTpmRowStatus
      RowStatus,
   mscFrAtmCaTpmComponentName
      DisplayString,
   mscFrAtmCaTpmStorageType
      StorageType,
   mscFrAtmCaTpmIndex
      Integer32 }

mscFrAtmCaTpmRowStatus OBJECT-TYPE
   SYNTAX     RowStatus 
   ACCESS     read-write
   STATUS     mandatory
   DESCRIPTION
     "This variable is used as the basis for SNMP naming of
      mscFrAtmCaTpm components.
      These components can be added and deleted."
::= { mscFrAtmCaTpmRowStatusEntry 1 }

mscFrAtmCaTpmComponentName OBJECT-TYPE
   SYNTAX     DisplayString 
   ACCESS     read-only
   STATUS     mandatory
   DESCRIPTION
     "This variable provides the component's string name for
      use with the ASCII Console Interface"
::= { mscFrAtmCaTpmRowStatusEntry 2 }

mscFrAtmCaTpmStorageType OBJECT-TYPE
   SYNTAX     StorageType 
   ACCESS     read-only
   STATUS     mandatory
   DESCRIPTION
     "This variable represents the storage type value for the
      mscFrAtmCaTpm tables."
::= { mscFrAtmCaTpmRowStatusEntry 4 }

mscFrAtmCaTpmIndex OBJECT-TYPE
   SYNTAX     Integer32 (0..15)
   ACCESS     not-accessible
   STATUS     mandatory
   DESCRIPTION
     "This variable represents the index for the mscFrAtmCaTpm tables."
::= { mscFrAtmCaTpmRowStatusEntry 10 }

mscFrAtmCaTpmProvTable OBJECT-TYPE
   SYNTAX     SEQUENCE OF MscFrAtmCaTpmProvEntry
   ACCESS     not-accessible
   STATUS     mandatory
   DESCRIPTION
     "This attribute group contains the provisionable attributes of the Tpm 
      component at this interface."
::= { mscFrAtmCaTpm 10 }

mscFrAtmCaTpmProvEntry OBJECT-TYPE
   SYNTAX     MscFrAtmCaTpmProvEntry
   ACCESS     not-accessible
   STATUS     mandatory
   DESCRIPTION
     "An entry in the mscFrAtmCaTpmProvTable."
   INDEX {
      mscFrAtmIndex,
      mscFrAtmCaIndex,
      mscFrAtmCaTpmIndex }
::= { mscFrAtmCaTpmProvTable 1 }

MscFrAtmCaTpmProvEntry ::= SEQUENCE {
   mscFrAtmCaTpmAssignedBandwidthPool
      INTEGER,
   mscFrAtmCaTpmTrafficParmConvPolicy
      INTEGER,
   mscFrAtmCaTpmAverageFrameSize
      INTEGER }

mscFrAtmCaTpmAssignedBandwidthPool OBJECT-TYPE
   SYNTAX     INTEGER  {
                 n0(0),
                 n1(1),
                 n2(2),
                 n3(3),
                 n4(4),
                 n5(5),
                 n6(6),
                 n7(7),
                 n8(8),
                 n9(9),
                 n10(10),
                 n11(11),
                 n12(12),
                 n13(13),
                 n14(14),
                 n15(15),
                 samePoolAsModule(255) }
   ACCESS     read-write
   STATUS     mandatory
   DESCRIPTION
     "This attribute specifies the bandwidth pool that supports this 
      transfer priority at this interface."
   DEFVAL     { samePoolAsModule }
::= { mscFrAtmCaTpmProvEntry 1 }

mscFrAtmCaTpmTrafficParmConvPolicy OBJECT-TYPE
   SYNTAX     INTEGER  {
                 sameAsModule(0),
                 policy3(3),
                 policy4(4),
                 policy5(5),
                 policy6(6) }
   ACCESS     read-write
   STATUS     mandatory
   DESCRIPTION
     "This attribute specifies the traffic parameter conversion policy to use 
      for a specific transfer priority for specifying equivalent bandwidth 
      rate at the FrAtm interface. 
      
      Policy 3 characterizes the traffic in the following way:
      - ATM traffic descriptor type 6 is selected
      - ATM service category rtVbr and nrtVbr supported only
      - PCR0+1 is based on AR
      - SCR0+1 is based on CIR and EIR
      - MBS0+1 is based on Bc, Be, CIR, EIR and AR
      - Takes into account that the instantaneous rate of the Frame Relay 
      stream can be above CIR and up to the AR.
      
      Policy 4 characterizes the traffic in the following way:
      - ATM traffic descriptor type 7 or 8 is selected. Type 7 is chosen 
      when non-conforming cells are to be discarded and type 8 when 
      non-conforming cells are tagged by the UPC traffic policer.
      - PCR0+1 is based on AR
      - ATM service category rtVbr and nrtVbr supported only
      - SCR0 is based on CIR
      - MBS0 is based on Bc, CIR, and AR
      - There is no direct characterization of EIR. The allowed EIR can be 
      derived using the difference between the AR and CIR.
      
      Policy 5 characterizes the traffic in the following way:
      - ATM traffic descriptor type 7 or 8 is selected. Type 7 is chosen 
      when non-conforming cells are to be discarded and type 8 when 
      non-conforming cells are tagged by the UPC traffic policer.
      - ATM service category rtVbr and nrtVbr supported only
      - PCR0+1 is based on CIR for descriptor type 7
      - PCR0+1 is based on CIR and EIR for descriptor type 8
      - SCR0 is based on CIR
      - MBS0 is based on Bc, CIR, and AR
      - The maximum PCR is no longer based on the AR but rather on the 
      CIR and EIR or CIR
      
      Policy 6 characterizes the traffic in the following way:
      - ATM traffic descriptor type 3 is selected
      - ATM service category ubr, cbr, rtVbr and nrtVbr supported only
      - PCR0+1 is based only on CIR.
      
      The default value sameAsModule implies the 
      trafficParmConversionPolicy of Mod Frs AtmNet Tpm/n is as 
      defined as Mod Frs AtmNet Tpm/n."
   DEFVAL     { sameAsModule }
::= { mscFrAtmCaTpmProvEntry 2 }

mscFrAtmCaTpmAverageFrameSize OBJECT-TYPE
   SYNTAX     INTEGER (0..8187)
   ACCESS     read-write
   STATUS     mandatory
   DESCRIPTION
     "This attribute specifies the average frame size at the FrAtm interface 
      for connections using this transfer priority.  If a value of 0 is 
      specified, the average frame size defined in Mod Frs AtmNet Tpm/n 
      avgFrameSize attribute is used."
   DEFVAL     { 0 }
::= { mscFrAtmCaTpmProvEntry 3 }




-- 
-- Version and Compliance statements
-- 



-- Object-Group Statement:
-- A list of all current accessible leaf objects.

-- OBJECTS { mscFrAtmFramerAborts,
--           mscFrAtmDlciABitStatusToIf,
--           mscFrAtmDlciEmissionPriorityToIf,
--           mscFrAtmDlciBytesToIf,
--           mscFrAtmDlciEgSpCommittedInformationRate,
--           mscFrAtmDlciSiwfComponentName,
--           mscFrAtmCaPoolAvailBwValue,
--           mscFrAtmVFramerFrmToOtherVFramer,
--           mscFrAtmLmiUsageState,
--           mscFrAtmDlciEgSpStorageType,
--           mscFrAtmDlciNiwfTransferPriority,
--           mscFrAtmAlarmStatus,
--           mscFrAtmDlciABitReasonToIf,
--           mscFrAtmCaPoolProvBwValue,
--           mscFrAtmDlciNiwfClpToDeMapping,
--           mscFrAtmDlciDiscFrameAbit,
--           mscFrAtmDlciEgSpComponentName,
--           mscFrAtmDlciTotalIngressFrames,
--           mscFrAtmDlciDeBytesToIf,
--           mscFrAtmDlciSiwfSdStorageType,
--           mscFrAtmDlciDiscCongestedToIf,
--           mscFrAtmDlciAccountingEnabled,
--           mscFrAtmDlciDeFrmToIf,
--           mscFrAtmLmiOperationalState,
--           mscFrAtmDlciNiwfQoSEmissionPriorityToIf,
--           mscFrAtmDlciDiscDeCongestedFromIfBytes,
--           mscFrAtmDlciDiscByteAbit,
--           mscFrAtmDlciTotalIngressBytes,
--           mscFrAtmDlciSiwfRemoteAddress,
--           mscFrAtmLmiMessageCountTimer,
--           mscFrAtmDlciSiwfQoSComponentName,
--           mscFrAtmDlciSiwfSdDeToClpMapping,
--           mscFrAtmDlciSpMeasurementInterval,
--           mscFrAtmCaBwPoolValue,
--           mscFrAtmDlciSiwfNPvcStorageType,
--           mscFrAtmLmiNoStatusReportCount,
--           mscFrAtmVFramerComponentName,
--           mscFrAtmDlciEgSpCommittedBurstSize,
--           mscFrAtmCaCallAdmissionControl,
--           mscFrAtmFramerOverruns,
--           mscFrAtmDlciTotalEgressBytes,
--           mscFrAtmDlciEirIngressFrames,
--           mscFrAtmCaSoftPvcs,
--           mscFrAtmNumberOfEmissionQs,
--           mscFrAtmDlciSiwfMaximumBurstSize0,
--           mscFrAtmDlciFrmToIf,
--           mscFrAtmLmiSequenceErrors,
--           mscFrAtmVFramerAdminState,
--           mscFrAtmCaSiwfEmissionPriorityToIf,
--           mscFrAtmDlciMeasurementInterval,
--           mscFrAtmDlciSiwfUnknown1490Frames,
--           mscFrAtmDlciEfciFrmFromNetwork,
--           mscFrAtmVFramerOctetFromOtherVFramer,
--           mscFrAtmDlciNiwfSpvcRemoteAddress,
--           mscFrAtmDlciDiscCongestedFromIfBytes,
--           mscFrAtmComponentName,
--           mscFrAtmDlciEirIngressBytes,
--           mscFrAtmDlciEirEgressFrames,
--           mscFrAtmCaSdDeToClpMapping,
--           mscFrAtmDlciNiwfQoSComponentName,
--           mscFrAtmLmiStatusSequenceErrors,
--           mscFrAtmDlciEgSpExcessBurstSize,
--           mscFrAtmCaAccountCollection,
--           mscFrAtmDlciSiwfMaximumBurstSize01,
--           mscFrAtmDlciNiwfAvgFrameSize,
--           mscFrAtmDlciSiwfLastUnknown1483ProtocolHeader,
--           mscFrAtmDlciSiwfVccClearCause,
--           mscFrAtmDlciSiwfSdFecnToEfciMapping,
--           mscFrAtmDlciSiwfInvalid1490Frames,
--           mscFrAtmDlciEirEgressBytes,
--           mscFrAtmDlciSiwfRowStatus,
--           mscFrAtmDlciSpStorageType,
--           mscFrAtmDlciFecnFrmFromIf,
--           mscFrAtmDlciSpAccounting,
--           mscFrAtmFramerFrmFromIf64,
--           mscFrAtmDlciNiwfSpvcRemoteDlci,
--           mscFrAtmDlciSiwfQoSRowStatus,
--           mscFrAtmLmiEventCount,
--           mscFrAtmDlciSiwfPeakCellRate0,
--           mscFrAtmDlciSiwfVccCauseDiag,
--           mscFrAtmDlciSiwfUnknown1483Frames,
--           mscFrAtmLmiCheckPointTimer,
--           mscFrAtmDlciSiwfSPvcRemoteConnectionIdentifier,
--           mscFrAtmLmiUserSideEventHistory,
--           mscFrAtmLmiKeepAliveStatusToIf,
--           mscFrAtmDlciStorageType,
--           mscFrAtmSnmpOperStatus,
--           mscFrAtmDlciSiwfAtmConNextHop,
--           mscFrAtmDlciSiwfLastUnknown1490ProtocolHeader,
--           mscFrAtmLmiSide,
--           mscFrAtmLmiFullStatusPollingCycles,
--           mscFrAtmDlciNiwfSpvcStorageType,
--           mscFrAtmDlciErrorShortBytesFromIf,
--           mscFrAtmDlciSiwfSPvcComponentName,
--           mscFrAtmFramerStorageType,
--           mscFrAtmDlciNiwfNdDeToClpMapping,
--           mscFrAtmDlciAccountingEnd,
--           mscFrAtmDlciNiwfComponentName,
--           mscFrAtmDlciABitReasonFromIf,
--           mscFrAtmDlciCommittedBurstSize,
--           mscFrAtmFramerCrcErrors,
--           mscFrAtmLmiKeepAliveEnqToIf,
--           mscFrAtmDlciSpRateEnforcement,
--           mscFrAtmDlciAdminState,
--           mscFrAtmDlciSiwfAtmConComponentName,
--           mscFrAtmCaTpmComponentName,
--           mscFrAtmFramerAdminState,
--           mscFrAtmLmiLinkVerificationTimer,
--           mscFrAtmLmiAsyncStatusReport,
--           mscFrAtmControlStatus,
--           mscFrAtmFramerLargeFrmErrors,
--           mscFrAtmDlciSiwfNPvcAtmConnection,
--           mscFrAtmFrmToIfByQueueValue,
--           mscFrAtmDlciRateEnforcement,
--           mscFrAtmDlciSiwfSPvcRemoteAddress,
--           mscFrAtmCaNdDeToClpMapping,
--           mscFrAtmDlciTroubledReason,
--           mscFrAtmVFramerStorageType,
--           mscFrAtmRowStatus,
--           mscFrAtmDlciNiwfDeToClpMapping,
--           mscFrAtmDlciSpExcessBurstSize,
--           mscFrAtmLmiProtocolErrors,
--           mscFrAtmDlciNiwfQoSRowStatus,
--           mscFrAtmFramerNonOctetErrors,
--           mscFrAtmDlciNiwfAtmDlci,
--           mscFrAtmDlciBecnFrmFromIf,
--           mscFrAtmDlciNiwfAssignedBandwidthPool,
--           mscFrAtmCaNiwfEmissionPriorityToIf,
--           mscFrAtmDlciTroubled,
--           mscFrAtmDlciNiwfRowStatus,
--           mscFrAtmUsageState,
--           mscFrAtmDlciSiwfSdComponentName,
--           mscFrAtmDlciSiwfTrafficParmConvPolicy,
--           mscFrAtmCaTroubledDlcis,
--           mscFrAtmLmiStorageType,
--           mscFrAtmLmiKeepAliveStatusEnqFromIf,
--           mscFrAtmDlciDiscExcessFromIf,
--           mscFrAtmDlciExcessBurstSize,
--           mscFrAtmDlciSiwfType,
--           mscFrAtmDlciSiwfSustainedCellRate0,
--           mscFrAtmLmiFullStatusToIf,
--           mscFrAtmDlciElapsedDifference,
--           mscFrAtmCaSdClpToDeMapping,
--           mscFrAtmOperationalState,
--           mscFrAtmCaSiwfTransferPriority,
--           mscFrAtmDlciDiscDeCongestedToIfBytes,
--           mscFrAtmDlciDiscCongestedFromIf,
--           mscFrAtmLmiAdminState,
--           mscFrAtmDlciSiwfNPvcComponentName,
--           mscFrAtmLmiProtocolStatus,
--           mscFrAtmCaStorageType,
--           mscFrAtmDlciSiwfSPvcRowStatus,
--           mscFrAtmDlciNiwfAtmServiceCategory,
--           mscFrAtmDlciSiwfNPvcConnectionToAtm,
--           mscFrAtmCaTpmAverageFrameSize,
--           mscFrAtmDlciDlciType,
--           mscFrAtmAvailabilityStatus,
--           mscFrAtmFramerOctetFromIf64,
--           mscFrAtmDlciSiwfAtmConRowStatus,
--           mscFrAtmCaServiceExchange,
--           mscFrAtmDlciSiwfDeToClpMapping,
--           mscFrAtmCaTpmRowStatus,
--           mscFrAtmLmiNetworkSideEventHistory,
--           mscFrAtmDlciSiwfSPvcCorrelationTag,
--           mscFrAtmFramerDataInversion,
--           mscFrAtmVFramerOtherVirtualFramer,
--           mscFrAtmDlciSiwfEquivalentBitRate,
--           mscFrAtmCaPoolAdmitBwValue,
--           mscFrAtmFramerFlagsBetweenFrames,
--           mscFrAtmDlciSpCommittedInformationRate,
--           mscFrAtmLmiPvcConfigParmsInFsr,
--           mscFrAtmDlciSiwfClpToDeMapping,
--           mscFrAtmDlciNiwfNdClpToDeMapping,
--           mscFrAtmAddrComponentName,
--           mscFrAtmAddrMyAddress,
--           mscFrAtmDlciNiwfNdComponentName,
--           mscFrAtmDlciSiwfQoSEmissionPriorityToIf,
--           mscFrAtmDlciSpComponentName,
--           mscFrAtmDlciDiscardedFrames,
--           mscFrAtmFramerFrameCrcType,
--           mscFrAtmDlciDiscDeCongestedFromIf,
--           mscFrAtmCaTpmTrafficParmConvPolicy,
--           mscFrAtmLmiFullStatusEnqFromIf,
--           mscFrAtmDlciNiwfTrafficParmConvPolicy,
--           mscFrAtmDlciSiwfInvalid1483Frames,
--           mscFrAtmDlciFecnFrmToIf,
--           mscFrAtmDlciCommittedInformationRate,
--           mscFrAtmFramerFrmToIf64,
--           mscFrAtmDlciSiwfPeakCellRate01,
--           mscFrAtmDlciSiwfSdRowStatus,
--           mscFrAtmCaTpmAssignedBandwidthPool,
--           mscFrAtmCaSdMode,
--           mscFrAtmLmiIgnoreActiveBit,
--           mscFrAtmDlciDiscardedBytes,
--           mscFrAtmDlciComponentName,
--           mscFrAtmProceduralStatus,
--           mscFrAtmCaNiwfTransferPriority,
--           mscFrAtmDlciSiwfQoSStorageType,
--           mscFrAtmOctetToIfByQueueValue,
--           mscFrAtmInvalidHeaderFramesFromIf,
--           mscFrAtmCaSdFecnToEfciMapping,
--           mscFrAtmLmiUnexpectedReports,
--           mscFrAtmDlciSiwfStorageType,
--           mscFrAtmFramerComponentName,
--           mscFrAtmDlciNiwfSpvcCorrelationTag,
--           mscFrAtmDlciDiscCongestedToIfBytes,
--           mscFrAtmDlciDeBytesFromIf,
--           mscFrAtmDlciSiwfFecnToEfciMapping,
--           mscFrAtmDlciSpMaximumFrameSize,
--           mscFrAtmDlciSiwfNPvcRowStatus,
--           mscFrAtmDlciDeFrmFromIf,
--           mscFrAtmDlciNiwfSpvcComponentName,
--           mscFrAtmVFramerUsageState,
--           mscFrAtmLmiUnexpectedIes,
--           mscFrAtmDlciStartTime,
--           mscFrAtmDlciExcessBytesFromIf,
--           mscFrAtmFramerNormPrioLinkUtilToIf,
--           mscFrAtmDlciMaximumFrameSize,
--           mscFrAtmDlciSiwfNPvcCorrelationTag,
--           mscFrAtmDlciExcessFrmFromIf,
--           mscFrAtmDlciNiwfEquivalentBitRate,
--           mscFrAtmCaOverrideLinkRate,
--           mscFrAtmCaLinkRate,
--           mscFrAtmLmiPollingVerifTimeouts,
--           mscFrAtmVFramerOperationalState,
--           mscFrAtmDlciTotalEgressFrames,
--           mscFrAtmDlciBytesFromIf,
--           mscFrAtmDlciBecnFrmToIf,
--           mscFrAtmDlciNiwfNdRowStatus,
--           mscFrAtmDlciFrmFromIf,
--           mscFrAtmDlciABitStatusFromIf,
--           mscFrAtmCaComponentName,
--           mscFrAtmDlciSiwfDiscardPriority,
--           mscFrAtmLmiComponentName,
--           mscFrAtmLmiErrorEventThreshold,
--           mscFrAtmLastUnknownDlci,
--           mscFrAtmDlciSiwfQoSTransferPriority,
--           mscFrAtmUnknownStatus,
--           mscFrAtmStandbyStatus,
--           mscFrAtmLmiProcedures,
--           mscFrAtmFramerUnderruns,
--           mscFrAtmDlciSiwfSustainedCellRate01,
--           mscFrAtmStorageType,
--           mscFrAtmDlciSiwfTransferPriority,
--           mscFrAtmAddrAddress,
--           mscFrAtmAddrStorageType,
--           mscFrAtmDlciNiwfQoSStorageType,
--           mscFrAtmDlciNiwfSpvcRowStatus,
--           mscFrAtmDlciNiwfNdStorageType,
--           mscFrAtmDlciRowStatus,
--           mscFrAtmDlciNiwfStorageType,
--           mscFrAtmCaNailedUpPvcs,
--           mscFrAtmDlciErrorLongBytesFromIf,
--           mscFrAtmAdminState,
--           mscFrAtmIfIndex,
--           mscFrAtmFramerRowStatus,
--           mscFrAtmDlciErrorLongFrmFromIf,
--           mscFrAtmDlciEgSpRowStatus,
--           mscFrAtmDlciUsageState,
--           mscFrAtmAddrRowStatus,
--           mscFrAtmIfAdminStatus,
--           mscFrAtmVFramerFrmFromOtherVFramer,
--           mscFrAtmDlciSiwfAtmServiceCategory,
--           mscFrAtmCustomerIdentifier,
--           mscFrAtmDlciCorrelationTag,
--           mscFrAtmDlciErrorShortFrmFromIf,
--           mscFrAtmVFramerLogicalProcessor,
--           mscFrAtmFramerUsageState,
--           mscFrAtmCaAccountClass,
--           mscFrAtmLmiOpProcedures,
--           mscFrAtmFramerNormPrioLinkUtilFromIf,
--           mscFrAtmDlciSiwfSdMode,
--           mscFrAtmDlciEgSpMeasurementInterval,
--           mscFrAtmDlciOperationalState,
--           mscFrAtmDlciSpCommittedBurstSize,
--           mscFrAtmDlciSpRowStatus,
--           mscFrAtmFramerInterfaceName,
--           mscFrAtmDlciDiscExcessFromIfBytes,
--           mscFrAtmCaNdClpToDeMapping,
--           mscFrAtmDlciSiwfSdClpToDeMapping,
--           mscFrAtmDlciSiwfSPvcStorageType,
--           mscFrAtmUnknownDlciFramesFromIf,
--           mscFrAtmFramerOperationalState,
--           mscFrAtmVFramerRowStatus,
--           mscFrAtmFramerFrmModeErrors,
--           mscFrAtmDlciSiwfAtmConStorageType,
--           mscFrAtmCaRowStatus,
--           mscFrAtmDlciSiwfAssignedBandwidthPool,
--           mscFrAtmCaTpmStorageType,
--           mscFrAtmDlciBecnFrmSetByService,
--           mscFrAtmDlciDiscDeCongestedToIf,
--           mscFrAtmFramerLrcErrors,
--           mscFrAtmDlciSiwfMode,
--           mscFrAtmDlciNiwfQoSTransferPriority,
--           mscFrAtmLmiFullStatusEnqToIf,
--           mscFrAtmDlciSiwfRemoteConnectionIdentifier,
--           mscFrAtmDlciSiwfAvgFrameSize,
--           mscFrAtmLmiRowStatus }
-- STATUS  mandatory
-- DESCRIPTION
--   "A list of all current accessible leaf objects."

frameRelayAtmGroup OBJECT IDENTIFIER ::= { frameRelayAtmMIB 1 }
frameRelayAtmGroupCA OBJECT IDENTIFIER ::= { frameRelayAtmGroup 1 }
frameRelayAtmGroupCA02 OBJECT IDENTIFIER ::= { frameRelayAtmGroupCA 3 }
frameRelayAtmGroupCA02A OBJECT IDENTIFIER ::= { frameRelayAtmGroupCA02 2 }



-- Agent-Capabilities Statement:

-- PRODUCT-RELEASE "MscPassport Release 1.2 FrameRelayAtm."
-- STATUS          mandatory
-- DESCRIPTION     "Carrier Passport FrameRelayAtm MIB: MIB Version CA02A,
--                  Software Version CA02S9C."
-- SUPPORTS        Nortel-MsCarrier-MscPassport-FrameRelayAtmMIB
--    INCLUDES     { frameRelayAtmGroupCA02A }

frameRelayAtmCapabilities OBJECT IDENTIFIER ::= { frameRelayAtmMIB 3 }
frameRelayAtmCapabilitiesCA OBJECT IDENTIFIER ::= { frameRelayAtmCapabilities 1 }
frameRelayAtmCapabilitiesCA02 OBJECT IDENTIFIER ::= { frameRelayAtmCapabilitiesCA 3 }
frameRelayAtmCapabilitiesCA02A OBJECT IDENTIFIER ::= { frameRelayAtmCapabilitiesCA02 2 }





END
