Nortel-MsCarrier-MscPassport-CallRedirectionMIB
DEFINITIONS ::= BEGIN



IMPORTS

      OBJECT-TYPE
   FROM RFC-1212

      mscPassportMIBs,
      mscComponents
   FROM Nortel-MsCarrier-MscPassport-UsefulDefinitionsMIB

      Counter32,
      DisplayString,
      StorageType,
      RowStatus,
      Integer32,
      Unsigned32
   FROM Nortel-MsCarrier-MscPassport-StandardTextualConventionsMIB

      AsciiString,
      NonReplicated,
      Link,
      AsciiStringIndex
   FROM Nortel-MsCarrier-MscPassport-TextualConventionsMIB;




-- LAST-UPDATED   "9909010000Z"
-- ORGANIZATION   "Nortel Networks"
-- CONTACT-INFO   "
--         Nortel Carrier Data Network Management
--         
--         Postal:       P.O. Box 3511, Station C 
--                       Ottawa, Ontario 
--                       Canada  K1Y 4H7
--         
--         via the WEB:  http://www.nortelnetworks.com  
--                       select 'Contact Us' from the menu
--          
--         via phone:    1-800-4NORTEL"
-- DESCRIPTION
--    "The module describing the Nortel MsCarrier MscPassport
--     CallRedirection Enterprise MIB."

callRedirectionMIB OBJECT IDENTIFIER ::= { mscPassportMIBs 132 }










-- CallRedirectionServer
-- The CallRedirectionServer component provides a set of alternate 
-- destinations for an original address. The alternate destination could 
-- be DPRS routing information (that is, RID/MID) or up to seven 
-- addresses.

mscCrs OBJECT IDENTIFIER ::= { mscComponents 132 }



mscCrsRowStatusTable OBJECT-TYPE
   SYNTAX     SEQUENCE OF MscCrsRowStatusEntry
   ACCESS     not-accessible
   STATUS     mandatory
   DESCRIPTION
     "This entry controls the addition and deletion of 
      mscCrs components."
::= { mscCrs 1 }

mscCrsRowStatusEntry OBJECT-TYPE
   SYNTAX     MscCrsRowStatusEntry
   ACCESS     not-accessible
   STATUS     mandatory
   DESCRIPTION
     "A single entry in the table represents a single 
      mscCrs component."
   INDEX {
      mscCrsIndex }
::= { mscCrsRowStatusTable 1 }

MscCrsRowStatusEntry ::= SEQUENCE {
   mscCrsRowStatus
      RowStatus,
   mscCrsComponentName
      DisplayString,
   mscCrsStorageType
      StorageType,
   mscCrsIndex
      NonReplicated }

mscCrsRowStatus OBJECT-TYPE
   SYNTAX     RowStatus 
   ACCESS     read-write
   STATUS     mandatory
   DESCRIPTION
     "This variable is used as the basis for SNMP naming of
      mscCrs components.
      These components can be added and deleted."
::= { mscCrsRowStatusEntry 1 }

mscCrsComponentName OBJECT-TYPE
   SYNTAX     DisplayString 
   ACCESS     read-only
   STATUS     mandatory
   DESCRIPTION
     "This variable provides the component's string name for
      use with the ASCII Console Interface"
::= { mscCrsRowStatusEntry 2 }

mscCrsStorageType OBJECT-TYPE
   SYNTAX     StorageType 
   ACCESS     read-only
   STATUS     mandatory
   DESCRIPTION
     "This variable represents the storage type value for the
      mscCrs tables."
::= { mscCrsRowStatusEntry 4 }

mscCrsIndex OBJECT-TYPE
   SYNTAX     NonReplicated 
   ACCESS     not-accessible
   STATUS     mandatory
   DESCRIPTION
     "This variable represents the index for the mscCrs tables."
::= { mscCrsRowStatusEntry 10 }

mscCrsProvTable OBJECT-TYPE
   SYNTAX     SEQUENCE OF MscCrsProvEntry
   ACCESS     not-accessible
   STATUS     mandatory
   DESCRIPTION
     "The Provisioned group contains provisionable attributes of the 
      CallRedirectionServer component."
::= { mscCrs 10 }

mscCrsProvEntry OBJECT-TYPE
   SYNTAX     MscCrsProvEntry
   ACCESS     not-accessible
   STATUS     mandatory
   DESCRIPTION
     "An entry in the mscCrsProvTable."
   INDEX {
      mscCrsIndex }
::= { mscCrsProvTable 1 }

MscCrsProvEntry ::= SEQUENCE {
   mscCrsLogicalProcessor
      Link }

mscCrsLogicalProcessor OBJECT-TYPE
   SYNTAX     Link 
   ACCESS     read-write
   STATUS     mandatory
   DESCRIPTION
     "This attribute specifies the logical processor on which the call 
      redirection server process is to run."
::= { mscCrsProvEntry 2 }

mscCrsStateTable OBJECT-TYPE
   SYNTAX     SEQUENCE OF MscCrsStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscCrs 11 }

mscCrsStateEntry OBJECT-TYPE
   SYNTAX     MscCrsStateEntry
   ACCESS     not-accessible
   STATUS     mandatory
   DESCRIPTION
     "An entry in the mscCrsStateTable."
   INDEX {
      mscCrsIndex }
::= { mscCrsStateTable 1 }

MscCrsStateEntry ::= SEQUENCE {
   mscCrsAdminState
      INTEGER,
   mscCrsOperationalState
      INTEGER,
   mscCrsUsageState
      INTEGER }

mscCrsAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscCrsStateEntry 1 }

mscCrsOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscCrsStateEntry 2 }

mscCrsUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscCrsStateEntry 3 }

mscCrsStatTable OBJECT-TYPE
   SYNTAX     SEQUENCE OF MscCrsStatEntry
   ACCESS     not-accessible
   STATUS     mandatory
   DESCRIPTION
     "The Statistics operational group defines the statistics associated 
      with the CallRedirectionServer component."
::= { mscCrs 12 }

mscCrsStatEntry OBJECT-TYPE
   SYNTAX     MscCrsStatEntry
   ACCESS     not-accessible
   STATUS     mandatory
   DESCRIPTION
     "An entry in the mscCrsStatTable."
   INDEX {
      mscCrsIndex }
::= { mscCrsStatTable 1 }

MscCrsStatEntry ::= SEQUENCE {
   mscCrsTotalAddresses
      Unsigned32,
   mscCrsRequestsReceived
      Counter32,
   mscCrsPrimaryMatches
      Counter32,
   mscCrsSecAddressListExhausted
      Counter32,
   mscCrsMaxAddrLenExceeded
      Counter32,
   mscCrsSecRidMidUnsuccessful
      Counter32,
   mscCrsSecAddrUnsuccessful
      Counter32,
   mscCrsRidRedirected
      Counter32,
   mscCrsRidMidRedirected
      Counter32,
   mscCrsAddressRedirected
      Counter32,
   mscCrsAltRidUnsuccessful
      Counter32 }

mscCrsTotalAddresses OBJECT-TYPE
   SYNTAX     Unsigned32 (0..4294967295)
   ACCESS     read-only
   STATUS     mandatory
   DESCRIPTION
     "The totalAddresses attribute indicates the number of 
      PrimaryAddress components associated with the 
      CallRedirectionServer component."
   DEFVAL     { 0 }
::= { mscCrsStatEntry 2 }

mscCrsRequestsReceived OBJECT-TYPE
   SYNTAX     Counter32 
   ACCESS     read-only
   STATUS     mandatory
   DESCRIPTION
     "The requestsReceived attribute counts the number of redirection 
      requests received by the CallRedirectionServer component. This 
      counter wraps to 0 when it exceeds its maximum value."
::= { mscCrsStatEntry 3 }

mscCrsPrimaryMatches OBJECT-TYPE
   SYNTAX     Counter32 
   ACCESS     read-only
   STATUS     mandatory
   DESCRIPTION
     "The primaryMatches attribute counts the Call Redirection Server 
      attempts to find a matching PrimaryAddress where the lookup 
      attempt was successful. This counter wraps to 0 when it exceeds its 
      maximum value."
::= { mscCrsStatEntry 4 }

mscCrsSecAddressListExhausted OBJECT-TYPE
   SYNTAX     Counter32 
   ACCESS     read-only
   STATUS     mandatory
   DESCRIPTION
     "The secAddressListExhausted attribute counts the Call Redirection 
      Server attempts to find a SecondaryAddress component given a 
      PrimaryAddress component where the lookup attempt resulted in 
      the exhaustion of the secondary redirection list. This counter wraps 
      to 0 when it exceeds its maximum value."
::= { mscCrsStatEntry 5 }

mscCrsMaxAddrLenExceeded OBJECT-TYPE
   SYNTAX     Counter32 
   ACCESS     read-only
   STATUS     mandatory
   DESCRIPTION
     "The maxAddrLenExceeded attribute counts how often the 
      concatenation of the secondary address and the suffix digits from 
      the original called address have exceeded the maximum of 15 
      digits.
      The suffix digits can be determined by removing the primary 
      address digits from the front of the original called address.
      If appending the suffix digits to a secondary address causes the 
      resulting address to exceed 15 digits, this secondary member is 
      skipped and the next secondary member is tried."
::= { mscCrsStatEntry 6 }

mscCrsSecRidMidUnsuccessful OBJECT-TYPE
   SYNTAX     Counter32 
   ACCESS     read-only
   STATUS     mandatory
   DESCRIPTION
     "The secRidMidUnsuccessful attribute counts the number of RID/
      MID redirections resulting in the destination address not being 
      reached. This situation could occur when the destination address 
      does not exist on the specified module or the specified module could 
      not be reached."
::= { mscCrsStatEntry 7 }

mscCrsSecAddrUnsuccessful OBJECT-TYPE
   SYNTAX     Counter32 
   ACCESS     read-only
   STATUS     mandatory
   DESCRIPTION
     "The secAddrUnsuccessful attribute counts the number of Address 
      redirections resulting in the destination user not being reached. This 
      situation could occur when the destination user line is disabled, the 
      destination address does not exist on the specified module, or the 
      specified module could not be reached."
::= { mscCrsStatEntry 8 }

mscCrsRidRedirected OBJECT-TYPE
   SYNTAX     Counter32 
   ACCESS     read-only
   STATUS     mandatory
   DESCRIPTION
     "The ridRedirected attribute counts requests received by the Call 
      Redirection Server resulting in the request being redirected to 
      another RID specified by the AlternateRid component. This counter 
      wraps to 0 when it exceeds its maximum value."
::= { mscCrsStatEntry 9 }

mscCrsRidMidRedirected OBJECT-TYPE
   SYNTAX     Counter32 
   ACCESS     read-only
   STATUS     mandatory
   DESCRIPTION
     "The ridMidRedirected attribute counts requests received by the Call 
      Redirection Server resulting in the request being redirected to 
      another RID/MID specified by the SecondaryRidMid component. 
      This counter wraps to 0 when it exceeds its maximum value."
::= { mscCrsStatEntry 10 }

mscCrsAddressRedirected OBJECT-TYPE
   SYNTAX     Counter32 
   ACCESS     read-only
   STATUS     mandatory
   DESCRIPTION
     "The addressRedirected attribute counts requests received by the 
      Call Redirection Server resulting in the request being redirected to 
      another Address specified by the SecondaryAddress component. 
      This counter wraps to 0 when it exceeds its maximum value."
::= { mscCrsStatEntry 11 }

mscCrsAltRidUnsuccessful OBJECT-TYPE
   SYNTAX     Counter32 
   ACCESS     read-only
   STATUS     mandatory
   DESCRIPTION
     "The altRidUnsuccessful attribute counts the number of RID 
      redirections resulting in the destination address not being reached. 
      This situation could occur when the alternate RID cannot be 
      reached, the module hosting the destination address is isolated, or 
      the port associated with the secondary address is unavailable at the 
      alternate RID."
::= { mscCrsStatEntry 12 }


-- Crs PrimaryAddress/<address>
-- The PrimaryAddress component defines a primary address for 
-- which a list of alternate destinations are specified. This primary 
-- address has either a secondary RID/MID destination or up to seven 
-- secondary addresses associated with it.
-- A primary address matches the original destination address if, 
-- beginning with the most significant digit, all digits are identical and 
-- the primary address is less than or equal to the original destination 
-- address in length. The "best match" is the longest such primary 
-- address.
-- The PrimaryAddress component instance value takes the form:
-- x.<X.121 address> or e.<E.164 address>

mscCrsPAddr OBJECT IDENTIFIER ::= { mscCrs 2 }



mscCrsPAddrRowStatusTable OBJECT-TYPE
   SYNTAX     SEQUENCE OF MscCrsPAddrRowStatusEntry
   ACCESS     not-accessible
   STATUS     mandatory
   DESCRIPTION
     "This entry controls the addition and deletion of 
      mscCrsPAddr components."
::= { mscCrsPAddr 1 }

mscCrsPAddrRowStatusEntry OBJECT-TYPE
   SYNTAX     MscCrsPAddrRowStatusEntry
   ACCESS     not-accessible
   STATUS     mandatory
   DESCRIPTION
     "A single entry in the table represents a single 
      mscCrsPAddr component."
   INDEX {
      mscCrsIndex,
      mscCrsPAddrIndex }
::= { mscCrsPAddrRowStatusTable 1 }

MscCrsPAddrRowStatusEntry ::= SEQUENCE {
   mscCrsPAddrRowStatus
      RowStatus,
   mscCrsPAddrComponentName
      DisplayString,
   mscCrsPAddrStorageType
      StorageType,
   mscCrsPAddrIndex
      AsciiStringIndex }

mscCrsPAddrRowStatus OBJECT-TYPE
   SYNTAX     RowStatus 
   ACCESS     read-write
   STATUS     mandatory
   DESCRIPTION
     "This variable is used as the basis for SNMP naming of
      mscCrsPAddr components.
      These components can be added and deleted."
::= { mscCrsPAddrRowStatusEntry 1 }

mscCrsPAddrComponentName OBJECT-TYPE
   SYNTAX     DisplayString 
   ACCESS     read-only
   STATUS     mandatory
   DESCRIPTION
     "This variable provides the component's string name for
      use with the ASCII Console Interface"
::= { mscCrsPAddrRowStatusEntry 2 }

mscCrsPAddrStorageType OBJECT-TYPE
   SYNTAX     StorageType 
   ACCESS     read-only
   STATUS     mandatory
   DESCRIPTION
     "This variable represents the storage type value for the
      mscCrsPAddr tables."
::= { mscCrsPAddrRowStatusEntry 4 }

mscCrsPAddrIndex OBJECT-TYPE
   SYNTAX     AsciiStringIndex (SIZE (1..17))
   ACCESS     not-accessible
   STATUS     mandatory
   DESCRIPTION
     "This variable represents the index for the mscCrsPAddr tables."
::= { mscCrsPAddrRowStatusEntry 10 }


-- Crs Paddr/<address> SecondaryRidMid
-- The SecondaryRidMid component identifies an alternate destination 
-- module on which the primary address is also supported. RID/MID 
-- redirection allows the call redirection server to effectively override 
-- the original destination identified by the call routing system and 
-- forward the call to a different module.

mscCrsPAddrSRidMid OBJECT IDENTIFIER ::= { mscCrsPAddr 2 }



mscCrsPAddrSRidMidRowStatusTable OBJECT-TYPE
   SYNTAX     SEQUENCE OF MscCrsPAddrSRidMidRowStatusEntry
   ACCESS     not-accessible
   STATUS     mandatory
   DESCRIPTION
     "This entry controls the addition and deletion of 
      mscCrsPAddrSRidMid components."
::= { mscCrsPAddrSRidMid 1 }

mscCrsPAddrSRidMidRowStatusEntry OBJECT-TYPE
   SYNTAX     MscCrsPAddrSRidMidRowStatusEntry
   ACCESS     not-accessible
   STATUS     mandatory
   DESCRIPTION
     "A single entry in the table represents a single 
      mscCrsPAddrSRidMid component."
   INDEX {
      mscCrsIndex,
      mscCrsPAddrIndex,
      mscCrsPAddrSRidMidIndex }
::= { mscCrsPAddrSRidMidRowStatusTable 1 }

MscCrsPAddrSRidMidRowStatusEntry ::= SEQUENCE {
   mscCrsPAddrSRidMidRowStatus
      RowStatus,
   mscCrsPAddrSRidMidComponentName
      DisplayString,
   mscCrsPAddrSRidMidStorageType
      StorageType,
   mscCrsPAddrSRidMidIndex
      NonReplicated }

mscCrsPAddrSRidMidRowStatus OBJECT-TYPE
   SYNTAX     RowStatus 
   ACCESS     read-write
   STATUS     mandatory
   DESCRIPTION
     "This variable is used as the basis for SNMP naming of
      mscCrsPAddrSRidMid components.
      These components can be added and deleted."
::= { mscCrsPAddrSRidMidRowStatusEntry 1 }

mscCrsPAddrSRidMidComponentName OBJECT-TYPE
   SYNTAX     DisplayString 
   ACCESS     read-only
   STATUS     mandatory
   DESCRIPTION
     "This variable provides the component's string name for
      use with the ASCII Console Interface"
::= { mscCrsPAddrSRidMidRowStatusEntry 2 }

mscCrsPAddrSRidMidStorageType OBJECT-TYPE
   SYNTAX     StorageType 
   ACCESS     read-only
   STATUS     mandatory
   DESCRIPTION
     "This variable represents the storage type value for the
      mscCrsPAddrSRidMid tables."
::= { mscCrsPAddrSRidMidRowStatusEntry 4 }

mscCrsPAddrSRidMidIndex OBJECT-TYPE
   SYNTAX     NonReplicated 
   ACCESS     not-accessible
   STATUS     mandatory
   DESCRIPTION
     "This variable represents the index for the mscCrsPAddrSRidMid tables."
::= { mscCrsPAddrSRidMidRowStatusEntry 10 }

mscCrsPAddrSRidMidRidMidProvTable OBJECT-TYPE
   SYNTAX     SEQUENCE OF MscCrsPAddrSRidMidRidMidProvEntry
   ACCESS     not-accessible
   STATUS     mandatory
   DESCRIPTION
     "The SecRidMidProv group defines the secondary RID/MID pair 
      associated with a specific primary address."
::= { mscCrsPAddrSRidMid 10 }

mscCrsPAddrSRidMidRidMidProvEntry OBJECT-TYPE
   SYNTAX     MscCrsPAddrSRidMidRidMidProvEntry
   ACCESS     not-accessible
   STATUS     mandatory
   DESCRIPTION
     "An entry in the mscCrsPAddrSRidMidRidMidProvTable."
   INDEX {
      mscCrsIndex,
      mscCrsPAddrIndex,
      mscCrsPAddrSRidMidIndex }
::= { mscCrsPAddrSRidMidRidMidProvTable 1 }

MscCrsPAddrSRidMidRidMidProvEntry ::= SEQUENCE {
   mscCrsPAddrSRidMidRoutingId
      Unsigned32,
   mscCrsPAddrSRidMidModuleId
      Unsigned32 }

mscCrsPAddrSRidMidRoutingId OBJECT-TYPE
   SYNTAX     Unsigned32 (1..126)
   ACCESS     read-write
   STATUS     mandatory
   DESCRIPTION
     "This attribute specifies a group of one or more interconnected nodes 
      (called a subnet) to which the primary address is redirected."
::= { mscCrsPAddrSRidMidRidMidProvEntry 2 }

mscCrsPAddrSRidMidModuleId OBJECT-TYPE
   SYNTAX     Unsigned32 (1..1909)
   ACCESS     read-write
   STATUS     mandatory
   DESCRIPTION
     "This attribute specifies a Passport node to which the primary 
      address is redirected."
::= { mscCrsPAddrSRidMidRidMidProvEntry 3 }


-- Crs Paddr/<address> SecondaryAddress/n
-- The SecondaryAddress component identifies an alternate destination 
-- address. Address redirection allows the call redirection server to 
-- effectively override the original destination address and forward the 
-- call to a different destination within the Passport network. 

mscCrsPAddrSAddr OBJECT IDENTIFIER ::= { mscCrsPAddr 3 }



mscCrsPAddrSAddrRowStatusTable OBJECT-TYPE
   SYNTAX     SEQUENCE OF MscCrsPAddrSAddrRowStatusEntry
   ACCESS     not-accessible
   STATUS     mandatory
   DESCRIPTION
     "This entry controls the addition and deletion of 
      mscCrsPAddrSAddr components."
::= { mscCrsPAddrSAddr 1 }

mscCrsPAddrSAddrRowStatusEntry OBJECT-TYPE
   SYNTAX     MscCrsPAddrSAddrRowStatusEntry
   ACCESS     not-accessible
   STATUS     mandatory
   DESCRIPTION
     "A single entry in the table represents a single 
      mscCrsPAddrSAddr component."
   INDEX {
      mscCrsIndex,
      mscCrsPAddrIndex,
      mscCrsPAddrSAddrIndex }
::= { mscCrsPAddrSAddrRowStatusTable 1 }

MscCrsPAddrSAddrRowStatusEntry ::= SEQUENCE {
   mscCrsPAddrSAddrRowStatus
      RowStatus,
   mscCrsPAddrSAddrComponentName
      DisplayString,
   mscCrsPAddrSAddrStorageType
      StorageType,
   mscCrsPAddrSAddrIndex
      Integer32 }

mscCrsPAddrSAddrRowStatus OBJECT-TYPE
   SYNTAX     RowStatus 
   ACCESS     read-write
   STATUS     mandatory
   DESCRIPTION
     "This variable is used as the basis for SNMP naming of
      mscCrsPAddrSAddr components.
      These components can be added and deleted."
::= { mscCrsPAddrSAddrRowStatusEntry 1 }

mscCrsPAddrSAddrComponentName OBJECT-TYPE
   SYNTAX     DisplayString 
   ACCESS     read-only
   STATUS     mandatory
   DESCRIPTION
     "This variable provides the component's string name for
      use with the ASCII Console Interface"
::= { mscCrsPAddrSAddrRowStatusEntry 2 }

mscCrsPAddrSAddrStorageType OBJECT-TYPE
   SYNTAX     StorageType 
   ACCESS     read-only
   STATUS     mandatory
   DESCRIPTION
     "This variable represents the storage type value for the
      mscCrsPAddrSAddr tables."
::= { mscCrsPAddrSAddrRowStatusEntry 4 }

mscCrsPAddrSAddrIndex OBJECT-TYPE
   SYNTAX     Integer32 (1..7)
   ACCESS     not-accessible
   STATUS     mandatory
   DESCRIPTION
     "This variable represents the index for the mscCrsPAddrSAddr tables."
::= { mscCrsPAddrSAddrRowStatusEntry 10 }

mscCrsPAddrSAddrSecAddrProvTable OBJECT-TYPE
   SYNTAX     SEQUENCE OF MscCrsPAddrSAddrSecAddrProvEntry
   ACCESS     not-accessible
   STATUS     mandatory
   DESCRIPTION
     "The SecAddrProv group defines one of the secondary addresses 
      associated with a specific primary address."
::= { mscCrsPAddrSAddr 10 }

mscCrsPAddrSAddrSecAddrProvEntry OBJECT-TYPE
   SYNTAX     MscCrsPAddrSAddrSecAddrProvEntry
   ACCESS     not-accessible
   STATUS     mandatory
   DESCRIPTION
     "An entry in the mscCrsPAddrSAddrSecAddrProvTable."
   INDEX {
      mscCrsIndex,
      mscCrsPAddrIndex,
      mscCrsPAddrSAddrIndex }
::= { mscCrsPAddrSAddrSecAddrProvTable 1 }

MscCrsPAddrSAddrSecAddrProvEntry ::= SEQUENCE {
   mscCrsPAddrSAddrAddress
      AsciiString }

mscCrsPAddrSAddrAddress OBJECT-TYPE
   SYNTAX     AsciiString (SIZE (1..17))
   ACCESS     read-write
   STATUS     mandatory
   DESCRIPTION
     "This attribute specifies a secondary address to which the primary 
      address is redirected. 
      The address attribute includes the Numbering Plan Indicator (NPI) 
      and the digits which form a unique identifier of the customer 
      interface. The address may belong to the X.121 or E.164 addressing 
      plan. Address digits are selected and assigned by network operators. 
      The address attribute takes the form:
      x.<X.121 address> or e.<E.164 address>"
::= { mscCrsPAddrSAddrSecAddrProvEntry 3 }


-- Crs AlternateRid
-- The AlternateRid component defines the routing identifier value that 
-- is used as the alternate DPRS routing information when routing to 
-- the RID specified by the Call Router (CR) is unsuccessful. This 
-- component should only be provisioned as a temporary 
-- measure.When activated the RID redirection feature as significant 
-- impact on the normal redirection operation, since RID redirection is 
-- always attempted first.
-- One of the possible application of this feature being RID splitting, 
-- the AlternateRid component should be deleted as soon as all module 
-- have been migrated from their original RID and the Call Router 
-- (CR) throughout the network have been updated with the new RID 
-- information. 

mscCrsAltRid OBJECT IDENTIFIER ::= { mscCrs 3 }



mscCrsAltRidRowStatusTable OBJECT-TYPE
   SYNTAX     SEQUENCE OF MscCrsAltRidRowStatusEntry
   ACCESS     not-accessible
   STATUS     mandatory
   DESCRIPTION
     "This entry controls the addition and deletion of 
      mscCrsAltRid components."
::= { mscCrsAltRid 1 }

mscCrsAltRidRowStatusEntry OBJECT-TYPE
   SYNTAX     MscCrsAltRidRowStatusEntry
   ACCESS     not-accessible
   STATUS     mandatory
   DESCRIPTION
     "A single entry in the table represents a single 
      mscCrsAltRid component."
   INDEX {
      mscCrsIndex,
      mscCrsAltRidIndex }
::= { mscCrsAltRidRowStatusTable 1 }

MscCrsAltRidRowStatusEntry ::= SEQUENCE {
   mscCrsAltRidRowStatus
      RowStatus,
   mscCrsAltRidComponentName
      DisplayString,
   mscCrsAltRidStorageType
      StorageType,
   mscCrsAltRidIndex
      NonReplicated }

mscCrsAltRidRowStatus OBJECT-TYPE
   SYNTAX     RowStatus 
   ACCESS     read-write
   STATUS     mandatory
   DESCRIPTION
     "This variable is used as the basis for SNMP naming of
      mscCrsAltRid components.
      These components can be added and deleted."
::= { mscCrsAltRidRowStatusEntry 1 }

mscCrsAltRidComponentName OBJECT-TYPE
   SYNTAX     DisplayString 
   ACCESS     read-only
   STATUS     mandatory
   DESCRIPTION
     "This variable provides the component's string name for
      use with the ASCII Console Interface"
::= { mscCrsAltRidRowStatusEntry 2 }

mscCrsAltRidStorageType OBJECT-TYPE
   SYNTAX     StorageType 
   ACCESS     read-only
   STATUS     mandatory
   DESCRIPTION
     "This variable represents the storage type value for the
      mscCrsAltRid tables."
::= { mscCrsAltRidRowStatusEntry 4 }

mscCrsAltRidIndex OBJECT-TYPE
   SYNTAX     NonReplicated 
   ACCESS     not-accessible
   STATUS     mandatory
   DESCRIPTION
     "This variable represents the index for the mscCrsAltRid tables."
::= { mscCrsAltRidRowStatusEntry 10 }

mscCrsAltRidAltRidProvTable OBJECT-TYPE
   SYNTAX     SEQUENCE OF MscCrsAltRidAltRidProvEntry
   ACCESS     not-accessible
   STATUS     mandatory
   DESCRIPTION
     "The AltRidProv group defines the alternate RID associated with the 
      Crs component."
::= { mscCrsAltRid 10 }

mscCrsAltRidAltRidProvEntry OBJECT-TYPE
   SYNTAX     MscCrsAltRidAltRidProvEntry
   ACCESS     not-accessible
   STATUS     mandatory
   DESCRIPTION
     "An entry in the mscCrsAltRidAltRidProvTable."
   INDEX {
      mscCrsIndex,
      mscCrsAltRidIndex }
::= { mscCrsAltRidAltRidProvTable 1 }

MscCrsAltRidAltRidProvEntry ::= SEQUENCE {
   mscCrsAltRidRoutingId
      Unsigned32 }

mscCrsAltRidRoutingId OBJECT-TYPE
   SYNTAX     Unsigned32 (1..126)
   ACCESS     read-write
   STATUS     mandatory
   DESCRIPTION
     "This attribute specifies a group of one or more interconnected nodes 
      (called a subnet) to which the request is redirected."
::= { mscCrsAltRidAltRidProvEntry 2 }




-- 
-- Version and Compliance statements
-- 



-- Object-Group Statement:
-- A list of all current accessible leaf objects.

-- OBJECTS { mscCrsPAddrSAddrRowStatus,
--           mscCrsStorageType,
--           mscCrsOperationalState,
--           mscCrsPAddrSRidMidComponentName,
--           mscCrsAltRidStorageType,
--           mscCrsPAddrSRidMidRowStatus,
--           mscCrsPAddrStorageType,
--           mscCrsLogicalProcessor,
--           mscCrsAltRidRowStatus,
--           mscCrsAdminState,
--           mscCrsSecAddrUnsuccessful,
--           mscCrsAltRidComponentName,
--           mscCrsAltRidUnsuccessful,
--           mscCrsSecAddressListExhausted,
--           mscCrsPAddrSAddrComponentName,
--           mscCrsPAddrComponentName,
--           mscCrsSecRidMidUnsuccessful,
--           mscCrsRowStatus,
--           mscCrsComponentName,
--           mscCrsPAddrSAddrStorageType,
--           mscCrsRidRedirected,
--           mscCrsPAddrSAddrAddress,
--           mscCrsPrimaryMatches,
--           mscCrsPAddrSRidMidStorageType,
--           mscCrsTotalAddresses,
--           mscCrsPAddrRowStatus,
--           mscCrsPAddrSRidMidRoutingId,
--           mscCrsAltRidRoutingId,
--           mscCrsUsageState,
--           mscCrsPAddrSRidMidModuleId,
--           mscCrsRidMidRedirected,
--           mscCrsRequestsReceived,
--           mscCrsMaxAddrLenExceeded,
--           mscCrsAddressRedirected }
-- STATUS  mandatory
-- DESCRIPTION
--   "A list of all current accessible leaf objects."

callRedirectionGroup OBJECT IDENTIFIER ::= { callRedirectionMIB 1 }
callRedirectionGroupCA OBJECT IDENTIFIER ::= { callRedirectionGroup 1 }
callRedirectionGroupCA02 OBJECT IDENTIFIER ::= { callRedirectionGroupCA 3 }
callRedirectionGroupCA02A OBJECT IDENTIFIER ::= { callRedirectionGroupCA02 2 }



-- Agent-Capabilities Statement:

-- PRODUCT-RELEASE "MscPassport Release 1.2 CallRedirection."
-- STATUS          mandatory
-- DESCRIPTION     "Carrier Passport CallRedirection MIB: MIB Version CA02A,
--                  Software Version CA02S9C."
-- SUPPORTS        Nortel-MsCarrier-MscPassport-CallRedirectionMIB
--    INCLUDES     { callRedirectionGroupCA02A }

callRedirectionCapabilities OBJECT IDENTIFIER ::= { callRedirectionMIB 3 }
callRedirectionCapabilitiesCA OBJECT IDENTIFIER ::= { callRedirectionCapabilities 1 }
callRedirectionCapabilitiesCA02 OBJECT IDENTIFIER ::= { callRedirectionCapabilitiesCA 3 }
callRedirectionCapabilitiesCA02A OBJECT IDENTIFIER ::= { callRedirectionCapabilitiesCA02 2 }





END
