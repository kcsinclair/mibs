Nortel-MsCarrier-MscPassport-BgpMIB
DEFINITIONS ::= BEGIN



IMPORTS

      OBJECT-TYPE
   FROM RFC-1212

      IpAddress
   FROM RFC1155-SMI

      mscPassportMIBs
   FROM Nortel-MsCarrier-MscPassport-UsefulDefinitionsMIB

      Counter32,
      DisplayString,
      StorageType,
      RowStatus,
      Gauge32,
      Integer32,
      Unsigned32
   FROM Nortel-MsCarrier-MscPassport-StandardTextualConventionsMIB

      AsciiString,
      Hex,
      NonReplicated,
      HexString,
      IntegerSequence
   FROM Nortel-MsCarrier-MscPassport-TextualConventionsMIB

      mscVrIpIndex,
      mscVrIp
   FROM Nortel-MsCarrier-MscPassport-IpMIB

      mscVrIndex
   FROM Nortel-MsCarrier-MscPassport-VirtualRouterMIB;




-- LAST-UPDATED   "9909010000Z"
-- ORGANIZATION   "Nortel Networks"
-- CONTACT-INFO   "
--         Nortel Carrier Data Network Management
--         
--         Postal:       P.O. Box 3511, Station C 
--                       Ottawa, Ontario 
--                       Canada  K1Y 4H7
--         
--         via the WEB:  http://www.nortelnetworks.com  
--                       select 'Contact Us' from the menu
--          
--         via phone:    1-800-4NORTEL"
-- DESCRIPTION
--    "The module describing the Nortel MsCarrier MscPassport
--     Bgp Enterprise MIB."

bgpMIB OBJECT IDENTIFIER ::= { mscPassportMIBs 141 }










-- Vr/<string> Ip BorderGatewayProtocol
-- This component is used to run the Border Gateway Protocol for IP.

mscVrIpBgp OBJECT IDENTIFIER ::= { mscVrIp 21 }



mscVrIpBgpRowStatusTable OBJECT-TYPE
   SYNTAX     SEQUENCE OF MscVrIpBgpRowStatusEntry
   ACCESS     not-accessible
   STATUS     mandatory
   DESCRIPTION
     "This entry controls the addition and deletion of 
      mscVrIpBgp components."
::= { mscVrIpBgp 1 }

mscVrIpBgpRowStatusEntry OBJECT-TYPE
   SYNTAX     MscVrIpBgpRowStatusEntry
   ACCESS     not-accessible
   STATUS     mandatory
   DESCRIPTION
     "A single entry in the table represents a single 
      mscVrIpBgp component."
   INDEX {
      mscVrIndex,
      mscVrIpIndex,
      mscVrIpBgpIndex }
::= { mscVrIpBgpRowStatusTable 1 }

MscVrIpBgpRowStatusEntry ::= SEQUENCE {
   mscVrIpBgpRowStatus
      RowStatus,
   mscVrIpBgpComponentName
      DisplayString,
   mscVrIpBgpStorageType
      StorageType,
   mscVrIpBgpIndex
      NonReplicated }

mscVrIpBgpRowStatus OBJECT-TYPE
   SYNTAX     RowStatus 
   ACCESS     read-write
   STATUS     mandatory
   DESCRIPTION
     "This variable is used as the basis for SNMP naming of
      mscVrIpBgp components.
      These components can be added and deleted."
::= { mscVrIpBgpRowStatusEntry 1 }

mscVrIpBgpComponentName OBJECT-TYPE
   SYNTAX     DisplayString 
   ACCESS     read-only
   STATUS     mandatory
   DESCRIPTION
     "This variable provides the component's string name for
      use with the ASCII Console Interface"
::= { mscVrIpBgpRowStatusEntry 2 }

mscVrIpBgpStorageType OBJECT-TYPE
   SYNTAX     StorageType 
   ACCESS     read-only
   STATUS     mandatory
   DESCRIPTION
     "This variable represents the storage type value for the
      mscVrIpBgp tables."
::= { mscVrIpBgpRowStatusEntry 4 }

mscVrIpBgpIndex OBJECT-TYPE
   SYNTAX     NonReplicated 
   ACCESS     not-accessible
   STATUS     mandatory
   DESCRIPTION
     "This variable represents the index for the mscVrIpBgp tables."
::= { mscVrIpBgpRowStatusEntry 10 }

mscVrIpBgpProvTable OBJECT-TYPE
   SYNTAX     SEQUENCE OF MscVrIpBgpProvEntry
   ACCESS     not-accessible
   STATUS     mandatory
   DESCRIPTION
     "This group contains the provisionable attributes for the Bgp 
      component."
::= { mscVrIpBgp 100 }

mscVrIpBgpProvEntry OBJECT-TYPE
   SYNTAX     MscVrIpBgpProvEntry
   ACCESS     not-accessible
   STATUS     mandatory
   DESCRIPTION
     "An entry in the mscVrIpBgpProvTable."
   INDEX {
      mscVrIndex,
      mscVrIpIndex,
      mscVrIpBgpIndex }
::= { mscVrIpBgpProvTable 1 }

MscVrIpBgpProvEntry ::= SEQUENCE {
   mscVrIpBgpBgpIdentifier
      IpAddress,
   mscVrIpBgpLocalAs
      Unsigned32,
   mscVrIpBgpDefaultLocalPreference
      Unsigned32,
   mscVrIpBgpDefaultMultiExitDisc
      Unsigned32,
   mscVrIpBgpRouteThrottleLimit
      Unsigned32,
   mscVrIpBgpRouteThrottleInter
      Unsigned32,
   mscVrIpBgpRouteReflector
      INTEGER,
   mscVrIpBgpRouteReflectorCluster
      IpAddress,
   mscVrIpBgpRedistributeIgpToIbgp
      INTEGER }

mscVrIpBgpBgpIdentifier OBJECT-TYPE
   SYNTAX     IpAddress 
   ACCESS     read-write
   STATUS     mandatory
   DESCRIPTION
     "This attribute specifies the Bgp Identifier of this Bgp component 
      instance. It is picked from the IP address space, and should follow 
      the same rule as choosing an unique IP address for IpPort."
::= { mscVrIpBgpProvEntry 1 }

mscVrIpBgpLocalAs OBJECT-TYPE
   SYNTAX     Unsigned32 (0..65535)
   ACCESS     read-write
   STATUS     mandatory
   DESCRIPTION
     "This attribute specifies the autonomous system identifier 
      for this Bgp component instance."
::= { mscVrIpBgpProvEntry 2 }

mscVrIpBgpDefaultLocalPreference OBJECT-TYPE
   SYNTAX     Unsigned32 (0..4294967295)
   ACCESS     read-write
   STATUS     mandatory
   DESCRIPTION
     "This attribute specifies this Bgp component instance's default 
      degree of preference for routes. It can be overridden by the 
      localPreference provisioned in ImportPolicy. A higher value 
      indicates a more preferred route."
   DEFVAL     { 144 }
::= { mscVrIpBgpProvEntry 3 }

mscVrIpBgpDefaultMultiExitDisc OBJECT-TYPE
   SYNTAX     Unsigned32 (0..4294967295)
   ACCESS     read-write
   STATUS     mandatory
   DESCRIPTION
     "This attribute specifies this Bgp component instance's default metric 
      to discriminate between multiple exit points to the same adjacent 
      autonomous system. It can be overridden by the 
      sendMultiExitDiscToEbgp provisioned in ExportPolicy. A lower 
      value indicates a more preferred route."
   DEFVAL     { 4294967294 }
::= { mscVrIpBgpProvEntry 4 }

mscVrIpBgpRouteThrottleLimit OBJECT-TYPE
   SYNTAX     Unsigned32 (1..1000)
   ACCESS     read-write
   STATUS     mandatory
   DESCRIPTION
     "This attribute specifies the maximum number of routes in the IP 
      forwarding table this Bgp component instance will process at one 
      time to decide if a route in the IP forwarding table should be 
      exported to a peer. This limit is used for the throttling and is made 
      configurable because the throttling requirements will be different 
      under different network configurations. The default value is 250."
   DEFVAL     { 250 }
::= { mscVrIpBgpProvEntry 5 }

mscVrIpBgpRouteThrottleInter OBJECT-TYPE
   SYNTAX     Unsigned32 (1..30)
   ACCESS     read-write
   STATUS     mandatory
   DESCRIPTION
     "This attribute specifies the interval in seconds, between the 
      processing of the routes in the IP forwarding table to decide if a 
      route in the IP forwarding table should be exported to a peer. This 
      interval is used for the throttling and is made configurable because 
      the throttling requirements will be different under different network 
      configurations. The default value is 5 seconds."
   DEFVAL     { 5 }
::= { mscVrIpBgpProvEntry 6 }

mscVrIpBgpRouteReflector OBJECT-TYPE
   SYNTAX     INTEGER  {
                 true(1),
                 false(2) }
   ACCESS     read-write
   STATUS     mandatory
   DESCRIPTION
     "This attribute specifies whether this Bgp instance is a Route 
      Reflector. If the value of this attribute is true, Bgp redistributes 
      routes it learns from an IBGP speaker to other IBGP speakers in the 
      AS. The rule of redistribution depends on the peer type: 1) When a 
      route is learned from a non-client peer, it is redistributed to all the 
      client peers within the cluster. 2) When a route is learned from a 
      client peer, it is redistributed to all the non-client peers and also to 
      the client peers. If the value of this attribute is false, Bgp does not 
      redistribute routes it learns from one IBGP speaker to other IBGP 
      speakers in the AS."
   DEFVAL     { false }
::= { mscVrIpBgpProvEntry 7 }

mscVrIpBgpRouteReflectorCluster OBJECT-TYPE
   SYNTAX     IpAddress 
   ACCESS     read-write
   STATUS     mandatory
   DESCRIPTION
     "This attribute identifies the cluster consisting of the Route Reflector 
      and its peer clients. When routeReflector of Bgp is true, value of 
      0.0.0.0 or 255.255.255.255 is invalid; the default value of this 
      attribute is same as bgpIdentifier. For redundancy, a cluster may 
      have more than one Route Reflector; in this case, the value of this 
      attribute of all the Route Reflectors in the same cluster should be 
      same. The value of this attribute is ignored when routeReflector of 
      Bgp is false"
::= { mscVrIpBgpProvEntry 8 }

mscVrIpBgpRedistributeIgpToIbgp OBJECT-TYPE
   SYNTAX     INTEGER  {
                 true(1),
                 false(2) }
   ACCESS     read-write
   STATUS     mandatory
   DESCRIPTION
     "This attribute specifies whether this Bgp instance allows exporting 
      of IGP routes to internal Bgp peers. IGP routes include the routes 
      learned from OSPF, RIP, local routes and static routes. If the value 
      of this attribute is true, and if ExportPolicy is specified to distribute, 
      then Bgp allows IGP route to be distributed to internal Bgp peers. If 
      the value of this attribute is false, Bgp does not allow IGP routes to 
      be distributed to internal Bgp peer, even if ExportPolicy is specified 
      to distribute. This attribute is set to true if and only this Bgp is part 
      of the Carrier Manage Service, otherwise, a routing loop may result."
   DEFVAL     { false }
::= { mscVrIpBgpProvEntry 9 }

mscVrIpBgpOperTable OBJECT-TYPE
   SYNTAX     SEQUENCE OF MscVrIpBgpOperEntry
   ACCESS     not-accessible
   STATUS     mandatory
   DESCRIPTION
     "This group contains the operational attributes for the Bgp 
      component."
::= { mscVrIpBgp 101 }

mscVrIpBgpOperEntry OBJECT-TYPE
   SYNTAX     MscVrIpBgpOperEntry
   ACCESS     not-accessible
   STATUS     mandatory
   DESCRIPTION
     "An entry in the mscVrIpBgpOperTable."
   INDEX {
      mscVrIndex,
      mscVrIpIndex,
      mscVrIpBgpIndex }
::= { mscVrIpBgpOperTable 1 }

MscVrIpBgpOperEntry ::= SEQUENCE {
   mscVrIpBgpTableVersion
      Counter32,
   mscVrIpBgpInMsgs
      Counter32,
   mscVrIpBgpInErrors
      Counter32,
   mscVrIpBgpInErrorMsgs
      Counter32,
   mscVrIpBgpOutMsgs
      Counter32,
   mscVrIpBgpOutDiscards
      Counter32,
   mscVrIpBgpOutErrorMsgs
      Counter32,
   mscVrIpBgpIndbSize
      Counter32 }

mscVrIpBgpTableVersion OBJECT-TYPE
   SYNTAX     Counter32 
   ACCESS     read-only
   STATUS     mandatory
   DESCRIPTION
     "This attribute indicates the version of the BGP routing table. It is 
      incremented every time the BGP routing table changes. This 
      counter will wrap to zero once the value exceeds the maximum 
      value."
::= { mscVrIpBgpOperEntry 2 }

mscVrIpBgpInMsgs OBJECT-TYPE
   SYNTAX     Counter32 
   ACCESS     read-only
   STATUS     mandatory
   DESCRIPTION
     "This attribute counts the total number of BGP messages received 
      without error. This counter will wrap to zero once the value exceeds 
      the maximum value."
::= { mscVrIpBgpOperEntry 3 }

mscVrIpBgpInErrors OBJECT-TYPE
   SYNTAX     Counter32 
   ACCESS     read-only
   STATUS     mandatory
   DESCRIPTION
     "This attribute counts the total number of BGP messages received 
      from all peers that proved to be in error. This counter will wrap to 
      zero once the value exceeds the maximum value."
::= { mscVrIpBgpOperEntry 4 }

mscVrIpBgpInErrorMsgs OBJECT-TYPE
   SYNTAX     Counter32 
   ACCESS     read-only
   STATUS     mandatory
   DESCRIPTION
     "This attribute counts the total number of BGP NOTIFICATION 
      messages from all the peers. This counter will wrap to zero once the 
      value exceeds the maximum value."
::= { mscVrIpBgpOperEntry 5 }

mscVrIpBgpOutMsgs OBJECT-TYPE
   SYNTAX     Counter32 
   ACCESS     read-only
   STATUS     mandatory
   DESCRIPTION
     "This attribute counts the total number of BGP messages sent to 
      peers. This counter will wrap to zero once the value exceeds the 
      maximum value."
::= { mscVrIpBgpOperEntry 6 }

mscVrIpBgpOutDiscards OBJECT-TYPE
   SYNTAX     Counter32 
   ACCESS     read-only
   STATUS     mandatory
   DESCRIPTION
     "This attribute counts the number of BGP messages that were locally 
      generated but were not sent out due to resource limitations within a 
      Bgp instance. This counter will wrap to zero once the value exceeds 
      the maximum value."
::= { mscVrIpBgpOperEntry 7 }

mscVrIpBgpOutErrorMsgs OBJECT-TYPE
   SYNTAX     Counter32 
   ACCESS     read-only
   STATUS     mandatory
   DESCRIPTION
     "This attribute counts the BGP NOTIFICATION messages sent to 
      the peers. This counter will wrap to zero once the value exceeds the 
      maximum value."
::= { mscVrIpBgpOperEntry 8 }

mscVrIpBgpIndbSize OBJECT-TYPE
   SYNTAX     Counter32 
   ACCESS     read-only
   STATUS     mandatory
   DESCRIPTION
     "This attribute indicates the number of Bgp indb entries under this 
      Bgp component instance."
::= { mscVrIpBgpOperEntry 9 }

mscVrIpBgpStateTable OBJECT-TYPE
   SYNTAX     SEQUENCE OF MscVrIpBgpStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscVrIpBgp 102 }

mscVrIpBgpStateEntry OBJECT-TYPE
   SYNTAX     MscVrIpBgpStateEntry
   ACCESS     not-accessible
   STATUS     mandatory
   DESCRIPTION
     "An entry in the mscVrIpBgpStateTable."
   INDEX {
      mscVrIndex,
      mscVrIpIndex,
      mscVrIpBgpIndex }
::= { mscVrIpBgpStateTable 1 }

MscVrIpBgpStateEntry ::= SEQUENCE {
   mscVrIpBgpAdminState
      INTEGER,
   mscVrIpBgpOperationalState
      INTEGER,
   mscVrIpBgpUsageState
      INTEGER }

mscVrIpBgpAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscVrIpBgpStateEntry 1 }

mscVrIpBgpOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscVrIpBgpStateEntry 2 }

mscVrIpBgpUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscVrIpBgpStateEntry 3 }

mscVrIpBgpAdminControlTable OBJECT-TYPE
   SYNTAX     SEQUENCE OF MscVrIpBgpAdminControlEntry
   ACCESS     not-accessible
   STATUS     mandatory
   DESCRIPTION
     "This group includes the Administrative Control attribute. This 
      attribute defines the current administrative state of this component."
::= { mscVrIpBgp 103 }

mscVrIpBgpAdminControlEntry OBJECT-TYPE
   SYNTAX     MscVrIpBgpAdminControlEntry
   ACCESS     not-accessible
   STATUS     mandatory
   DESCRIPTION
     "An entry in the mscVrIpBgpAdminControlTable."
   INDEX {
      mscVrIndex,
      mscVrIpIndex,
      mscVrIpBgpIndex }
::= { mscVrIpBgpAdminControlTable 1 }

MscVrIpBgpAdminControlEntry ::= SEQUENCE {
   mscVrIpBgpSnmpAdminStatus
      INTEGER }

mscVrIpBgpSnmpAdminStatus OBJECT-TYPE
   SYNTAX     INTEGER  {
                 up(1),
                 down(2),
                 testing(3) }
   ACCESS     read-write
   STATUS     mandatory
   DESCRIPTION
     "The desired state of the interface. The up state indicates the 
      interface is operational and packet forwarding is allowed. The down 
      state indicates the interface is not operational and packet forwarding 
      is unavailable. The testing state indicates that no operational 
      packets can be passed."
   DEFVAL     { up }
::= { mscVrIpBgpAdminControlEntry 1 }

mscVrIpBgpOperStatusTable OBJECT-TYPE
   SYNTAX     SEQUENCE OF MscVrIpBgpOperStatusEntry
   ACCESS     not-accessible
   STATUS     mandatory
   DESCRIPTION
     "This group includes the Operational Status attribute. This attribute 
      defines the current operational state of this component."
::= { mscVrIpBgp 106 }

mscVrIpBgpOperStatusEntry OBJECT-TYPE
   SYNTAX     MscVrIpBgpOperStatusEntry
   ACCESS     not-accessible
   STATUS     mandatory
   DESCRIPTION
     "An entry in the mscVrIpBgpOperStatusTable."
   INDEX {
      mscVrIndex,
      mscVrIpIndex,
      mscVrIpBgpIndex }
::= { mscVrIpBgpOperStatusTable 1 }

MscVrIpBgpOperStatusEntry ::= SEQUENCE {
   mscVrIpBgpSnmpOperStatus
      INTEGER }

mscVrIpBgpSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { mscVrIpBgpOperStatusEntry 1 }


-- Vr/<string> Ip Bgp Peer/<Ip Address>
-- This component identifies the properties of a Bgp peer.
-- The index value of this entry identifies the IP address of that peer. 
-- This component is required for BGP to set up a peer session with 
-- the peer with the IP address identified in the index value.

mscVrIpBgpPeer OBJECT IDENTIFIER ::= { mscVrIpBgp 2 }



mscVrIpBgpPeerRowStatusTable OBJECT-TYPE
   SYNTAX     SEQUENCE OF MscVrIpBgpPeerRowStatusEntry
   ACCESS     not-accessible
   STATUS     mandatory
   DESCRIPTION
     "This entry controls the addition and deletion of 
      mscVrIpBgpPeer components."
::= { mscVrIpBgpPeer 1 }

mscVrIpBgpPeerRowStatusEntry OBJECT-TYPE
   SYNTAX     MscVrIpBgpPeerRowStatusEntry
   ACCESS     not-accessible
   STATUS     mandatory
   DESCRIPTION
     "A single entry in the table represents a single 
      mscVrIpBgpPeer component."
   INDEX {
      mscVrIndex,
      mscVrIpIndex,
      mscVrIpBgpIndex,
      mscVrIpBgpPeerPeerAddressIndex }
::= { mscVrIpBgpPeerRowStatusTable 1 }

MscVrIpBgpPeerRowStatusEntry ::= SEQUENCE {
   mscVrIpBgpPeerRowStatus
      RowStatus,
   mscVrIpBgpPeerComponentName
      DisplayString,
   mscVrIpBgpPeerStorageType
      StorageType,
   mscVrIpBgpPeerPeerAddressIndex
      IpAddress }

mscVrIpBgpPeerRowStatus OBJECT-TYPE
   SYNTAX     RowStatus 
   ACCESS     read-write
   STATUS     mandatory
   DESCRIPTION
     "This variable is used as the basis for SNMP naming of
      mscVrIpBgpPeer components.
      These components can be added and deleted."
::= { mscVrIpBgpPeerRowStatusEntry 1 }

mscVrIpBgpPeerComponentName OBJECT-TYPE
   SYNTAX     DisplayString 
   ACCESS     read-only
   STATUS     mandatory
   DESCRIPTION
     "This variable provides the component's string name for
      use with the ASCII Console Interface"
::= { mscVrIpBgpPeerRowStatusEntry 2 }

mscVrIpBgpPeerStorageType OBJECT-TYPE
   SYNTAX     StorageType 
   ACCESS     read-only
   STATUS     mandatory
   DESCRIPTION
     "This variable represents the storage type value for the
      mscVrIpBgpPeer tables."
::= { mscVrIpBgpPeerRowStatusEntry 4 }

mscVrIpBgpPeerPeerAddressIndex OBJECT-TYPE
   SYNTAX     IpAddress 
   ACCESS     not-accessible
   STATUS     mandatory
   DESCRIPTION
     "This variable represents the index for the mscVrIpBgpPeer tables."
::= { mscVrIpBgpPeerRowStatusEntry 10 }

mscVrIpBgpPeerProvTable OBJECT-TYPE
   SYNTAX     SEQUENCE OF MscVrIpBgpPeerProvEntry
   ACCESS     not-accessible
   STATUS     mandatory
   DESCRIPTION
     "This group contains the provisionable attributes for this 
      BGP Peer component"
::= { mscVrIpBgpPeer 10 }

mscVrIpBgpPeerProvEntry OBJECT-TYPE
   SYNTAX     MscVrIpBgpPeerProvEntry
   ACCESS     not-accessible
   STATUS     mandatory
   DESCRIPTION
     "An entry in the mscVrIpBgpPeerProvTable."
   INDEX {
      mscVrIndex,
      mscVrIpIndex,
      mscVrIpBgpIndex,
      mscVrIpBgpPeerPeerAddressIndex }
::= { mscVrIpBgpPeerProvTable 1 }

MscVrIpBgpPeerProvEntry ::= SEQUENCE {
   mscVrIpBgpPeerPeerAs
      Unsigned32,
   mscVrIpBgpPeerLocalAddressConfigured
      IpAddress,
   mscVrIpBgpPeerKeepAliveConfigured
      Unsigned32,
   mscVrIpBgpPeerHoldTimeConfigured
      Unsigned32,
   mscVrIpBgpPeerConnectRetryTime
      Unsigned32,
   mscVrIpBgpPeerMinAsOrigTime
      Unsigned32,
   mscVrIpBgpPeerMinRouteAdvTime
      Unsigned32,
   mscVrIpBgpPeerDefaultInAggMed
      Unsigned32,
   mscVrIpBgpPeerIsRouteReflectorClient
      INTEGER,
   mscVrIpBgpPeerRemovePrivateAs
      INTEGER }

mscVrIpBgpPeerPeerAs OBJECT-TYPE
   SYNTAX     Unsigned32 (0..65535)
   ACCESS     read-write
   STATUS     mandatory
   DESCRIPTION
     "This attribute specifies the autonomous system identifier of this 
      BGP Peer component. It will be used to verify the autonomous 
      system identifier learned from the peer through the OPEN message. 
      The peer connection will be rejected and a NOTIFICATION 
      message will be sent to the peer if these two numbers don't match."
   DEFVAL     { 0 }
::= { mscVrIpBgpPeerProvEntry 1 }

mscVrIpBgpPeerLocalAddressConfigured OBJECT-TYPE
   SYNTAX     IpAddress 
   ACCESS     read-write
   STATUS     mandatory
   DESCRIPTION
     "This attribute specifies the local IP address configured for this Bgp 
      Peer connection. If this attribute is 0.0.0.0, TCP will choose a local 
      IP interface based on the remote IP address of this peer connection 
      and the IP forwarding table. The value chosen is stored in the 
      localAddressUsed attribute under the same Peer component."
   DEFVAL     { '00000000'H }  -- "0.0.0.0"
::= { mscVrIpBgpPeerProvEntry 2 }

mscVrIpBgpPeerKeepAliveConfigured OBJECT-TYPE
   SYNTAX     Unsigned32 (0..21845)
   ACCESS     read-write
   STATUS     mandatory
   DESCRIPTION
     "This attribute specifies the configured interval in seconds, between 
      BGP KEEPALIVE message retransmissions. It is used to establish 
      the ratio between keepalive interval and hold time. If this attribute is 
      zero, then the holdTimeConfigured attribute should also be zero, 
      which means that periodic KEEPALIVE messages will not be sent."
   DEFVAL     { 30 }
::= { mscVrIpBgpPeerProvEntry 3 }

mscVrIpBgpPeerHoldTimeConfigured OBJECT-TYPE
   SYNTAX     Unsigned32 (0 | 3..65535)
   ACCESS     read-write
   STATUS     mandatory
   DESCRIPTION
     "This attribute specifies the maximum time in seconds, that may 
      elapse without receiving a KEEPALIVE or UPDATE message 
      before the connection is considered down. The hold time must be 
      either zero or at least three seconds. If this attribute is zero, then the 
      keepAliveConfigured attribute should also be zero, which means 
      that periodic KEEPALIVE messages will not be sent."
   DEFVAL     { 90 }
::= { mscVrIpBgpPeerProvEntry 4 }

mscVrIpBgpPeerConnectRetryTime OBJECT-TYPE
   SYNTAX     Unsigned32 (1..65535)
   ACCESS     read-write
   STATUS     mandatory
   DESCRIPTION
     "This attribute specifies the time interval in seconds for the 
      ConnectRetry timer. It is the minimum amount of time that must 
      elapse between successive TCP connection retries for establishing 
      BGP peer connection."
   DEFVAL     { 120 }
::= { mscVrIpBgpPeerProvEntry 5 }

mscVrIpBgpPeerMinAsOrigTime OBJECT-TYPE
   SYNTAX     Unsigned32 (1..65535)
   ACCESS     read-write
   STATUS     mandatory
   DESCRIPTION
     "This attribute specifies the time interval in seconds for the 
      MinAsOriginationInterval timer. It is the minimum amount of time 
      that must elapse between updates that advertise a change to a route 
      within the local autonomous system to neighboring autonomous 
      systems."
   DEFVAL     { 15 }
::= { mscVrIpBgpPeerProvEntry 6 }

mscVrIpBgpPeerMinRouteAdvTime OBJECT-TYPE
   SYNTAX     Unsigned32 (1..65535)
   ACCESS     read-write
   STATUS     mandatory
   DESCRIPTION
     "This attribute specifies the time interval in seconds for the 
      MinRouteAdvertisementInterval timer. Feasible routes received 
      from peers in other autonomous systems may only be re-advertised 
      to peers in other autonomous systems at a rate no greater than 
      MinRouteAdvertisementInterval."
   DEFVAL     { 30 }
::= { mscVrIpBgpPeerProvEntry 7 }

mscVrIpBgpPeerDefaultInAggMed OBJECT-TYPE
   SYNTAX     Unsigned32 (0..4294967295)
   ACCESS     read-write
   STATUS     mandatory
   DESCRIPTION
     "This attribute specifies this Bgp Peer component instance's metric 
      for generating a dynamic default route whenever this external bgp 
      peer got established. It is used to prioritize between the dynamic 
      default routes generated by Passport Bgp speakers. If this attribute 
      is not set, Bgp will not generate a dynamic default route. If this 
      attribute is set, Bgp will automatically generate a dynamic default 
      route when the connection established."
   DEFVAL     { 4294967295 }
::= { mscVrIpBgpPeerProvEntry 8 }

mscVrIpBgpPeerIsRouteReflectorClient OBJECT-TYPE
   SYNTAX     INTEGER  {
                 true(1),
                 false(2) }
   ACCESS     read-write
   STATUS     mandatory
   DESCRIPTION
     "This attribute specifies whether the peer is a client peer or non-
      client peer of this Bgp instance. The attribute is only meaningful if 
      attribute routeReflector of Bgp is true."
   DEFVAL     { false }
::= { mscVrIpBgpPeerProvEntry 9 }

mscVrIpBgpPeerRemovePrivateAs OBJECT-TYPE
   SYNTAX     INTEGER  {
                 enabled(1),
                 disabled(2) }
   ACCESS     read-write
   STATUS     mandatory
   DESCRIPTION
     "This attribute specifies the treatment of the AS_PATH path attribute 
      in routes sent to the peer. If this attribute is enabled, then BGP will 
      remove private AS numbers from the AS_PATH. This attribute is 
      meaningful only for external peers."
   DEFVAL     { disabled }
::= { mscVrIpBgpPeerProvEntry 10 }

mscVrIpBgpPeerStateTable OBJECT-TYPE
   SYNTAX     SEQUENCE OF MscVrIpBgpPeerStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscVrIpBgpPeer 11 }

mscVrIpBgpPeerStateEntry OBJECT-TYPE
   SYNTAX     MscVrIpBgpPeerStateEntry
   ACCESS     not-accessible
   STATUS     mandatory
   DESCRIPTION
     "An entry in the mscVrIpBgpPeerStateTable."
   INDEX {
      mscVrIndex,
      mscVrIpIndex,
      mscVrIpBgpIndex,
      mscVrIpBgpPeerPeerAddressIndex }
::= { mscVrIpBgpPeerStateTable 1 }

MscVrIpBgpPeerStateEntry ::= SEQUENCE {
   mscVrIpBgpPeerAdminState
      INTEGER,
   mscVrIpBgpPeerOperationalState
      INTEGER,
   mscVrIpBgpPeerUsageState
      INTEGER }

mscVrIpBgpPeerAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscVrIpBgpPeerStateEntry 1 }

mscVrIpBgpPeerOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscVrIpBgpPeerStateEntry 2 }

mscVrIpBgpPeerUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscVrIpBgpPeerStateEntry 3 }

mscVrIpBgpPeerOperTable OBJECT-TYPE
   SYNTAX     SEQUENCE OF MscVrIpBgpPeerOperEntry
   ACCESS     not-accessible
   STATUS     mandatory
   DESCRIPTION
     "This group contains the operational attributes for the Peer 
      component."
::= { mscVrIpBgpPeer 12 }

mscVrIpBgpPeerOperEntry OBJECT-TYPE
   SYNTAX     MscVrIpBgpPeerOperEntry
   ACCESS     not-accessible
   STATUS     mandatory
   DESCRIPTION
     "An entry in the mscVrIpBgpPeerOperTable."
   INDEX {
      mscVrIndex,
      mscVrIpIndex,
      mscVrIpBgpIndex,
      mscVrIpBgpPeerPeerAddressIndex }
::= { mscVrIpBgpPeerOperTable 1 }

MscVrIpBgpPeerOperEntry ::= SEQUENCE {
   mscVrIpBgpPeerConnectionState
      INTEGER,
   mscVrIpBgpPeerBgpIdentifier
      IpAddress,
   mscVrIpBgpPeerVersionNegotiated
      Unsigned32,
   mscVrIpBgpPeerHoldTimeNegotiated
      Unsigned32,
   mscVrIpBgpPeerKeepAliveNegotiated
      Unsigned32,
   mscVrIpBgpPeerLocalAddressUsed
      IpAddress,
   mscVrIpBgpPeerLocalPort
      Unsigned32,
   mscVrIpBgpPeerRemotePort
      Unsigned32,
   mscVrIpBgpPeerLastError
      HexString,
   mscVrIpBgpPeerConnectionEstablishedTime
      Gauge32,
   mscVrIpBgpPeerConnectionEstablishedTransitions
      Counter32,
   mscVrIpBgpPeerInUpdateElapsedTime
      Gauge32,
   mscVrIpBgpPeerInMsgs
      Counter32,
   mscVrIpBgpPeerInUpdates
      Counter32,
   mscVrIpBgpPeerInErrors
      Counter32,
   mscVrIpBgpPeerInErrorMsgs
      Counter32,
   mscVrIpBgpPeerOutMsgs
      Counter32,
   mscVrIpBgpPeerOutUpdates
      Counter32,
   mscVrIpBgpPeerOutDiscards
      Counter32,
   mscVrIpBgpPeerOutErrorMsgs
      Counter32,
   mscVrIpBgpPeerInRoutes
      Counter32 }

mscVrIpBgpPeerConnectionState OBJECT-TYPE
   SYNTAX     INTEGER  {
                 idle(1),
                 connect(2),
                 active(3),
                 openSent(4),
                 openConfirm(5),
                 established(6) }
   ACCESS     read-only
   STATUS     mandatory
   DESCRIPTION
     "This attribute indicates the current state of this BGP peer 
      connection. The meaning of each state is as follows:
      idle - it is the initial state of the BGP peer connection. Error events 
      will also cause BGP peer connection to transit to the idle state.
      connect - BGP has initiated a TCP connection request to this peer, 
      and waiting for reply from that peer.
      active - BGP is not initiating a TCP connection request to this peer, 
      because TCP connection failed and is waiting for connection retry 
      time-out.
      openSent - a TCP connection to this peer has been established, but 
      the OPEN message has not been successfully exchanged.
      openConfirm - OPEN message has been successfully exchanged 
      with this peer, but the first KEEPALIVE message has not been 
      received from that peer.
      established - the first KEEPALIVE message has been received 
      from this peer, which means this BGP peer connection has been 
      established.
      See RFC 1771 for a detailed description of BGP state transitions."
   DEFVAL     { idle }
::= { mscVrIpBgpPeerOperEntry 3 }

mscVrIpBgpPeerBgpIdentifier OBJECT-TYPE
   SYNTAX     IpAddress 
   ACCESS     read-only
   STATUS     mandatory
   DESCRIPTION
     "This attribute indicates the BGP Identifier of this Bgp Peer 
      component. It is learned from the peer through the OPEN message."
::= { mscVrIpBgpPeerOperEntry 4 }

mscVrIpBgpPeerVersionNegotiated OBJECT-TYPE
   SYNTAX     Unsigned32 (0..4)
   ACCESS     read-only
   STATUS     mandatory
   DESCRIPTION
     "This attribute indicates the BGP version number negotiated with 
      this peer through the OPEN message. Currently, only BGP version 
      4 is supported. BGP will reject the peer connection if our peer 
      proposes a BGP version other than 4."
::= { mscVrIpBgpPeerOperEntry 5 }

mscVrIpBgpPeerHoldTimeNegotiated OBJECT-TYPE
   SYNTAX     Unsigned32 (0 | 3..65535)
   ACCESS     read-only
   STATUS     mandatory
   DESCRIPTION
     "This attribute indicates the maximum time in seconds, that may 
      elapse without receiving a KEEPALIVE or UPDATE message 
      before the connection is considered down. This is the negotiated 
      value with peer through the OPEN message. The hold time must be 
      either zero or at least three seconds. If the negotiated hold time is 
      zero, then periodic KEEPALIVE messages are not expected from 
      the peer."
::= { mscVrIpBgpPeerOperEntry 6 }

mscVrIpBgpPeerKeepAliveNegotiated OBJECT-TYPE
   SYNTAX     Unsigned32 (0..21845)
   ACCESS     read-only
   STATUS     mandatory
   DESCRIPTION
     "This attribute indicates the interval in seconds, between BGP 
      KEEPALIVE message retransmissions. This keepalive interval will 
      have the same ratio to the hold time negotiated with the peer as that 
      of the locally configured keepalive and hold time. This attribute will 
      be zero if the holdTimeNegotiated attribute is zero, which means 
      periodic KEEPALIVE messages will not be sent."
::= { mscVrIpBgpPeerOperEntry 7 }

mscVrIpBgpPeerLocalAddressUsed OBJECT-TYPE
   SYNTAX     IpAddress 
   ACCESS     read-only
   STATUS     mandatory
   DESCRIPTION
     "This attribute indicates the local IP address used for this BGP peer 
      connection. If the localAddressConfigured attribute is non-zero, its 
      value will be used. Otherwise, the local address will be assigned by 
      TCP based on the remote IP address of this peer connection and the 
      IP forwarding table."
::= { mscVrIpBgpPeerOperEntry 8 }

mscVrIpBgpPeerLocalPort OBJECT-TYPE
   SYNTAX     Unsigned32 (0..65535)
   ACCESS     read-only
   STATUS     mandatory
   DESCRIPTION
     "This attribute indicates the local TCP port for the connection 
      between the BGP peers."
::= { mscVrIpBgpPeerOperEntry 9 }

mscVrIpBgpPeerRemotePort OBJECT-TYPE
   SYNTAX     Unsigned32 (0..65535)
   ACCESS     read-only
   STATUS     mandatory
   DESCRIPTION
     "This attribute indicates the remote TCP port for the connection 
      between the BGP peers."
::= { mscVrIpBgpPeerOperEntry 10 }

mscVrIpBgpPeerLastError OBJECT-TYPE
   SYNTAX     HexString (SIZE (2))
   ACCESS     read-only
   STATUS     mandatory
   DESCRIPTION
     "This attribute indicates the last error code and subcode seen by this 
      Bgp component instance on this peer connection. The first byte of 
      this two byte OCTET STRING contains the error code, and the 
      second byte contains the subcode. A value of zero means that no 
      error has occurred. Check RFC 1771 for mappings of error codes 
      and error subcodes."
::= { mscVrIpBgpPeerOperEntry 11 }

mscVrIpBgpPeerConnectionEstablishedTime OBJECT-TYPE
   SYNTAX     Gauge32 (0..4294967295)
   ACCESS     read-only
   STATUS     mandatory
   DESCRIPTION
     "This attribute indicates how long since this Peer component's last 
      transition to or from the established state. It is set to zero when the 
      Peer component is activated.
      DESCRIPTION"
   DEFVAL     { 0 }
::= { mscVrIpBgpPeerOperEntry 12 }

mscVrIpBgpPeerConnectionEstablishedTransitions OBJECT-TYPE
   SYNTAX     Counter32 
   ACCESS     read-only
   STATUS     mandatory
   DESCRIPTION
     "This attribute counts the total number of times the BGP connection 
      state transitioned into the established state."
::= { mscVrIpBgpPeerOperEntry 13 }

mscVrIpBgpPeerInUpdateElapsedTime OBJECT-TYPE
   SYNTAX     Gauge32 (0..4294967295)
   ACCESS     read-only
   STATUS     mandatory
   DESCRIPTION
     "This attribute indicates the elapsed time in seconds since the last 
      BGP UPDATE message was received from the peer. Each time 
      inUpdates attribute is incremented, the value of this attribute is set 
      to zero."
::= { mscVrIpBgpPeerOperEntry 14 }

mscVrIpBgpPeerInMsgs OBJECT-TYPE
   SYNTAX     Counter32 
   ACCESS     read-only
   STATUS     mandatory
   DESCRIPTION
     "This attribute counts the number of BGP messages received without 
      error from the BGP peer. This counter will wrap to zero once the 
      value exceeds the maximum value."
::= { mscVrIpBgpPeerOperEntry 15 }

mscVrIpBgpPeerInUpdates OBJECT-TYPE
   SYNTAX     Counter32 
   ACCESS     read-only
   STATUS     mandatory
   DESCRIPTION
     "This attribute counts the number of BGP UPDATE messages 
      received on this peer connection. This counter will wrap to zero 
      once the value exceeds the maximum value."
::= { mscVrIpBgpPeerOperEntry 16 }

mscVrIpBgpPeerInErrors OBJECT-TYPE
   SYNTAX     Counter32 
   ACCESS     read-only
   STATUS     mandatory
   DESCRIPTION
     "This attribute counts the number of messages received from this 
      BGP peer that proved to be in error. This counter will wrap to zero 
      once the value exceeds the maximum value."
::= { mscVrIpBgpPeerOperEntry 17 }

mscVrIpBgpPeerInErrorMsgs OBJECT-TYPE
   SYNTAX     Counter32 
   ACCESS     read-only
   STATUS     mandatory
   DESCRIPTION
     "This attribute counts the number of BGP NOTIFICATION 
      messages received from this BGP peer. This counter will wrap to 
      zero once the value exceeds the maximum value."
::= { mscVrIpBgpPeerOperEntry 18 }

mscVrIpBgpPeerOutMsgs OBJECT-TYPE
   SYNTAX     Counter32 
   ACCESS     read-only
   STATUS     mandatory
   DESCRIPTION
     "This attribute counts the number of locally generated BGP 
      messages sent to this BGP peer. It does not include discarded 
      messages. This counter will wrap to zero once the value exceeds the 
      maximum value."
::= { mscVrIpBgpPeerOperEntry 19 }

mscVrIpBgpPeerOutUpdates OBJECT-TYPE
   SYNTAX     Counter32 
   ACCESS     read-only
   STATUS     mandatory
   DESCRIPTION
     "This attribute counts the number of BGP UPDATE messages sent to 
      this peer. This counter will wrap to zero once the value exceeds the 
      maximum value."
::= { mscVrIpBgpPeerOperEntry 20 }

mscVrIpBgpPeerOutDiscards OBJECT-TYPE
   SYNTAX     Counter32 
   ACCESS     read-only
   STATUS     mandatory
   DESCRIPTION
     "This attribute counts the number of locally generated BGP 
      messages not sent to this BGP peer due to resource limitations 
      within a BGP entity. This counter will wrap to zero once the value 
      exceeds the maximum value."
::= { mscVrIpBgpPeerOperEntry 21 }

mscVrIpBgpPeerOutErrorMsgs OBJECT-TYPE
   SYNTAX     Counter32 
   ACCESS     read-only
   STATUS     mandatory
   DESCRIPTION
     "This attribute counts the number of BGP NOTIFICATION 
      messages sent to this BGP peer. This counter will wrap to zero once 
      the value exceeds the maximum value."
::= { mscVrIpBgpPeerOperEntry 22 }

mscVrIpBgpPeerInRoutes OBJECT-TYPE
   SYNTAX     Counter32 
   ACCESS     read-only
   STATUS     mandatory
   DESCRIPTION
     "This attribute indicates the number of routes received from this 
      BGP peer."
::= { mscVrIpBgpPeerOperEntry 23 }


-- Vr/<string> Ip Bgp Import/n
-- Each instance of this component describes a BGP import policy. A 
-- BGP import policy is used to decide if certain routing information 
-- learned from its peer is to be ignored or used. 
-- If no import policy is provisioned, BGP will accept all routes 
-- received from its IBGP peers, but will not use any routing 
-- information received from its EBGP peers. 
-- If multiple import policies are provisioned, the one with the most 
-- specific match will apply.
-- The keys are matched in the following order from the least specified 
-- to the most specified:
-- Network,
-- peerAs, 
-- peerIpAddress,
-- originAs, 
-- originProtocol,
-- matchAsPath,
-- matchCommunity.
-- Example1: 
-- There are 2 import policies defined:
-- vr/0 ip bgp import/1, originProtocol = any, originAs = 20, 
-- usageFlag = use
-- vr/0 ip bgp import/2, originProtocol = igp, usageFlag = ignore 
-- If a BGP NLRI contains a route originally learned from an igp with 
-- origin AS 20, it will be used.
-- Example2: 
-- There are 2 import policies defined:
-- vr/0 ip bgp import/1, originProtocol = any, matchAsPath = "1 2 3",, 
-- usageFlag = ignore
-- vr/0 ip bgp import/2, originProtocol = any, usageFlag = use
-- If a BGP NLRI contains a route originally learned from an igp with 
-- the AsPath "1 2 3 4", it will be ignored.
-- DESCRIPTION	

mscVrIpBgpImport OBJECT IDENTIFIER ::= { mscVrIpBgp 3 }



mscVrIpBgpImportRowStatusTable OBJECT-TYPE
   SYNTAX     SEQUENCE OF MscVrIpBgpImportRowStatusEntry
   ACCESS     not-accessible
   STATUS     mandatory
   DESCRIPTION
     "This entry controls the addition and deletion of 
      mscVrIpBgpImport components."
::= { mscVrIpBgpImport 1 }

mscVrIpBgpImportRowStatusEntry OBJECT-TYPE
   SYNTAX     MscVrIpBgpImportRowStatusEntry
   ACCESS     not-accessible
   STATUS     mandatory
   DESCRIPTION
     "A single entry in the table represents a single 
      mscVrIpBgpImport component."
   INDEX {
      mscVrIndex,
      mscVrIpIndex,
      mscVrIpBgpIndex,
      mscVrIpBgpImportIndex }
::= { mscVrIpBgpImportRowStatusTable 1 }

MscVrIpBgpImportRowStatusEntry ::= SEQUENCE {
   mscVrIpBgpImportRowStatus
      RowStatus,
   mscVrIpBgpImportComponentName
      DisplayString,
   mscVrIpBgpImportStorageType
      StorageType,
   mscVrIpBgpImportIndex
      Integer32 }

mscVrIpBgpImportRowStatus OBJECT-TYPE
   SYNTAX     RowStatus 
   ACCESS     read-write
   STATUS     mandatory
   DESCRIPTION
     "This variable is used as the basis for SNMP naming of
      mscVrIpBgpImport components.
      These components can be added and deleted."
::= { mscVrIpBgpImportRowStatusEntry 1 }

mscVrIpBgpImportComponentName OBJECT-TYPE
   SYNTAX     DisplayString 
   ACCESS     read-only
   STATUS     mandatory
   DESCRIPTION
     "This variable provides the component's string name for
      use with the ASCII Console Interface"
::= { mscVrIpBgpImportRowStatusEntry 2 }

mscVrIpBgpImportStorageType OBJECT-TYPE
   SYNTAX     StorageType 
   ACCESS     read-only
   STATUS     mandatory
   DESCRIPTION
     "This variable represents the storage type value for the
      mscVrIpBgpImport tables."
::= { mscVrIpBgpImportRowStatusEntry 4 }

mscVrIpBgpImportIndex OBJECT-TYPE
   SYNTAX     Integer32 (0..65535)
   ACCESS     not-accessible
   STATUS     mandatory
   DESCRIPTION
     "This variable represents the index for the mscVrIpBgpImport tables."
::= { mscVrIpBgpImportRowStatusEntry 10 }

mscVrIpBgpImportProvTable OBJECT-TYPE
   SYNTAX     SEQUENCE OF MscVrIpBgpImportProvEntry
   ACCESS     not-accessible
   STATUS     mandatory
   DESCRIPTION
     "This group contains all the provisionable attributes for the Import 
      component."
::= { mscVrIpBgpImport 10 }

mscVrIpBgpImportProvEntry OBJECT-TYPE
   SYNTAX     MscVrIpBgpImportProvEntry
   ACCESS     not-accessible
   STATUS     mandatory
   DESCRIPTION
     "An entry in the mscVrIpBgpImportProvTable."
   INDEX {
      mscVrIndex,
      mscVrIpIndex,
      mscVrIpBgpIndex,
      mscVrIpBgpImportIndex }
::= { mscVrIpBgpImportProvTable 1 }

MscVrIpBgpImportProvEntry ::= SEQUENCE {
   mscVrIpBgpImportPeerAs
      Unsigned32,
   mscVrIpBgpImportPeerIpAddress
      IpAddress,
   mscVrIpBgpImportOriginAs
      Unsigned32,
   mscVrIpBgpImportOriginProtocol
      INTEGER,
   mscVrIpBgpImportUsageFlag
      INTEGER,
   mscVrIpBgpImportLocalPreference
      Unsigned32,
   mscVrIpBgpImportPreferredOver
      INTEGER,
   mscVrIpBgpImportAsPathExpression
      AsciiString,
   mscVrIpBgpImportCommunityExpression
      AsciiString,
   mscVrIpBgpImportExpressPreference
      Unsigned32,
   mscVrIpBgpImportAppendCommunity
      Unsigned32 }

mscVrIpBgpImportPeerAs OBJECT-TYPE
   SYNTAX     Unsigned32 (0..65535)
   ACCESS     read-write
   STATUS     mandatory
   DESCRIPTION
     "This key attribute specifies the autonomous system number of the 
      peer from which the routes are learned. A value of 0 for this 
      attribute means that peer AS number will match any AS number."
   DEFVAL     { 0 }
::= { mscVrIpBgpImportProvEntry 1 }

mscVrIpBgpImportPeerIpAddress OBJECT-TYPE
   SYNTAX     IpAddress 
   ACCESS     read-write
   STATUS     mandatory
   DESCRIPTION
     "This key attribute specifies the IP address of the peer from which 
      the routes are learned. A value of 0.0.0.0 for this attribute means 
      that peer IP address will match any IP address."
   DEFVAL     { '00000000'H }  -- "0.0.0.0"
::= { mscVrIpBgpImportProvEntry 2 }

mscVrIpBgpImportOriginAs OBJECT-TYPE
   SYNTAX     Unsigned32 (0..65535)
   ACCESS     read-write
   STATUS     mandatory
   DESCRIPTION
     "This key attribute specifies the autonomous system number where 
      the routes were originated. A value of 0 for this attribute means 
      origin AS number will match any AS number."
   DEFVAL     { 0 }
::= { mscVrIpBgpImportProvEntry 3 }

mscVrIpBgpImportOriginProtocol OBJECT-TYPE
   SYNTAX     INTEGER  {
                 any(0),
                 igp(1),
                 egp(2),
                 incomplete(3) }
   ACCESS     read-write
   STATUS     mandatory
   DESCRIPTION
     "This key attribute specifies the protocols that originated the routes. 
      A value of incomplete for this attribute means this information is 
      not available."
   DEFVAL     { any }
::= { mscVrIpBgpImportProvEntry 4 }

mscVrIpBgpImportUsageFlag OBJECT-TYPE
   SYNTAX     INTEGER  {
                 use(1),
                 ignore(2) }
   ACCESS     read-write
   STATUS     mandatory
   DESCRIPTION
     "This attribute specifies whether BGP will use or ignore information 
      in received update if it meets criteria specified by the key attributes 
      of this component."
   DEFVAL     { use }
::= { mscVrIpBgpImportProvEntry 5 }

mscVrIpBgpImportLocalPreference OBJECT-TYPE
   SYNTAX     Unsigned32 (0..4294967295)
   ACCESS     read-write
   STATUS     mandatory
   DESCRIPTION
     "This attribute specifies this Bgp component instance's degree of 
      preference for those routes that match the criteria of this import 
      policy. A higher value indicates a more preferred route. A value of 0 
      for this attribute means that the default local preference value 
      provisioned under the Bgp component should be used."
   DEFVAL     { 0 }
::= { mscVrIpBgpImportProvEntry 6 }

mscVrIpBgpImportPreferredOver OBJECT-TYPE
   SYNTAX     INTEGER  {
                 overIntOspf(6),
                 underIntOspf(70) }
   ACCESS     read-write
   STATUS     mandatory
   DESCRIPTION
     "This attribute indicates the preference of the external BGP route 
      with the OSPF internal route. overIntOspf means that the external 
      BGP route is chosen over OSPF internal route, while underIntOspf 
      means that the OSPF internal route is chosen over the external BGP 
      route. The default preference is set to underIntOspf."
   DEFVAL     { underIntOspf }
::= { mscVrIpBgpImportProvEntry 7 }

mscVrIpBgpImportAsPathExpression OBJECT-TYPE
   SYNTAX     AsciiString (SIZE (0..255))
   ACCESS     read-write
   STATUS     mandatory
   DESCRIPTION
     "This key attribute allows the user to enter a regular expression to 
      match the import AS Path Attribute of the received update message. 
      Note: the AS Path Attribute lists the ASs in reverse traversal order. 
      The syntax of the regular expression is a subset of the RFC 2280. 
      The basic syntax of a regular expression is a list of AS number 
      separated by a space which making up a AS path.
      The following characters has the special meaning:
      '.' 					- Matches any AS number.
      '^n' 		- Matches the first AS item (n) in the AS Path Attribute,
      or in order words, matches the last AS (n) traversed in
      the AS path.
      'n$' 		- Matches the last AS item (n) in the AS Path Attribute,
      or in order words, matches the first AS (n) traversed in
      the AS path.
      '[n1 ... n2]' 		- Matches any AS number that appeared in the set n1 ...
      n2.	
      'n1 - n2' 		- Matches any AS number between the range of n1 and
      n2.
      '()' 		- is supported to change the order of evaluation.
      'n*' 		- Matches 0 or more occurrences of n, where n can be a
      set, 	 range or AS number.
      'n+' 		- Matches 1 or more occurrences of n, where n can be a
      set, range or AS number.
      'n?' 		- Matches 0 or 1 occurrences of n, where n can be a AS
      set, range or number.
      The following logical operators are evaluated in decending order:
      'NOT' 		- Given a regular expression x, NOT x matches the AS
      number 	pattern that is not matched by x. 
      'AND'		- Given two regular expressions x and y, x AND y
      matches the intersection of the AS path that are
      matched by x and those are matched by y.
      'OR' 		- Given two regular expressions x and y, x OR y
      matches the union of the AS path that are matched by x
      and those are matched by y.
      For example: The AS path '5 4 3 2 1', where 1 is the origin AS, 
      would be match by any one of the following regular expressions:
      1$,
      ^5,
      4 3,
      5 3 - 4*,
      5 [4 3 2] not10 2 1,
      not (6 7 8 9 10) and 5 4 .* 1
      Empty regular expression implies a match on all AS path."
::= { mscVrIpBgpImportProvEntry 8 }

mscVrIpBgpImportCommunityExpression OBJECT-TYPE
   SYNTAX     AsciiString (SIZE (0..255))
   ACCESS     read-write
   STATUS     mandatory
   DESCRIPTION
     "This key attribute allows the user to enter a regular expression to 
      match the import Community Attribute of the received update 
      message. The syntax of the regular expression is a subset of the 
      RFC 2280. 
      The basic syntax of a regular expression is a list of Community 
      number seperated by a space which making up a Community 
      attribute.
      The following characters has the special meaning:
      '[n1 ... n2]' 		- Matches any Community number that appeared in the
      set n1 ...							n2.	
      'n1 - n2' 		- Matches any Community number between the range of
      n1 and 							n2.
      '()' 		- is supported to change the order of evaluation.
      'n*' 		- Matches 0 or more occurrences of n, where n can be a
      set, 	 range or Community number.
      'n+' 		- Matches 1 or more occurrences of n, where n can be a
      set, range or Community number.
      'n?' 		- Matches 0 or 1 occurrences of n, where n can be a
      set, range or number.
      The following logical operators are evaluated in decending order:
      'NOT' 		- Given a regular expression x, NOT x matches the
      Community 			attribute that is not matched by x. 
      'AND'		- Given two regular expressions x and y, x AND y
      matches the intersection of the Community attribute that
      are matched by x and those are matched by y.
      'OR' 		- Given two regular expressions x and y, x OR y
      matches the union of the Community attribute that are
      matched by x and those are matched by y.
      For example: The Community path '1 2 3 4 5' would be match by 
      any one of the following regular expression:
      1,
      5,
      4 3,
      2 3 - 4*,
      1 [3 4 2]+,
      not (6 7 8 9 10) and 1 2 
      Empty regular expression implies a match on all Community path."
::= { mscVrIpBgpImportProvEntry 9 }

mscVrIpBgpImportExpressPreference OBJECT-TYPE
   SYNTAX     Unsigned32 (0..255)
   ACCESS     read-write
   STATUS     mandatory
   DESCRIPTION
     "This attribute specifies the relative preference of the policy which 
      use the keys expressAsPath and expressCommunity. This attribute is 
      ignored if attributes expressAsPath and expressCommunity are both 
      empty. This attribute is used to break the tie when two import 
      policies' expression attributes match a specific AS Path or 
      Community. A higher value indicates a more preferred policy."
   DEFVAL     { 128 }
::= { mscVrIpBgpImportProvEntry 10 }

mscVrIpBgpImportAppendCommunity OBJECT-TYPE
   SYNTAX     Unsigned32 (0..4294967295)
   ACCESS     read-write
   STATUS     mandatory
   DESCRIPTION
     "This attribute indicates which community number this Import policy 
      will send along with the Path Attribute. Refer to RFC 1997 for the 
      detailed description of how this attribute may be used to pass 
      additional information to BGP peers. If the value is set to 0, no 
      community is appended to the Community attribute."
   DEFVAL     { 0 }
::= { mscVrIpBgpImportProvEntry 11 }


-- Vr/<string> Ip Bgp Import/n Network/n
-- This is an optional subcomponent of Import component and 
-- identifies destination networks that this BGP import policy applies 
-- to. This component is used as a key for the import policy. If no 
-- network list is provisioned, the import policy applies to all 
-- networks.

mscVrIpBgpImportNet OBJECT IDENTIFIER ::= { mscVrIpBgpImport 2 }



mscVrIpBgpImportNetRowStatusTable OBJECT-TYPE
   SYNTAX     SEQUENCE OF MscVrIpBgpImportNetRowStatusEntry
   ACCESS     not-accessible
   STATUS     mandatory
   DESCRIPTION
     "This entry controls the addition and deletion of 
      mscVrIpBgpImportNet components."
::= { mscVrIpBgpImportNet 1 }

mscVrIpBgpImportNetRowStatusEntry OBJECT-TYPE
   SYNTAX     MscVrIpBgpImportNetRowStatusEntry
   ACCESS     not-accessible
   STATUS     mandatory
   DESCRIPTION
     "A single entry in the table represents a single 
      mscVrIpBgpImportNet component."
   INDEX {
      mscVrIndex,
      mscVrIpIndex,
      mscVrIpBgpIndex,
      mscVrIpBgpImportIndex,
      mscVrIpBgpImportNetIndex }
::= { mscVrIpBgpImportNetRowStatusTable 1 }

MscVrIpBgpImportNetRowStatusEntry ::= SEQUENCE {
   mscVrIpBgpImportNetRowStatus
      RowStatus,
   mscVrIpBgpImportNetComponentName
      DisplayString,
   mscVrIpBgpImportNetStorageType
      StorageType,
   mscVrIpBgpImportNetIndex
      Integer32 }

mscVrIpBgpImportNetRowStatus OBJECT-TYPE
   SYNTAX     RowStatus 
   ACCESS     read-write
   STATUS     mandatory
   DESCRIPTION
     "This variable is used as the basis for SNMP naming of
      mscVrIpBgpImportNet components.
      These components can be added and deleted."
::= { mscVrIpBgpImportNetRowStatusEntry 1 }

mscVrIpBgpImportNetComponentName OBJECT-TYPE
   SYNTAX     DisplayString 
   ACCESS     read-only
   STATUS     mandatory
   DESCRIPTION
     "This variable provides the component's string name for
      use with the ASCII Console Interface"
::= { mscVrIpBgpImportNetRowStatusEntry 2 }

mscVrIpBgpImportNetStorageType OBJECT-TYPE
   SYNTAX     StorageType 
   ACCESS     read-only
   STATUS     mandatory
   DESCRIPTION
     "This variable represents the storage type value for the
      mscVrIpBgpImportNet tables."
::= { mscVrIpBgpImportNetRowStatusEntry 4 }

mscVrIpBgpImportNetIndex OBJECT-TYPE
   SYNTAX     Integer32 (0..65535)
   ACCESS     not-accessible
   STATUS     mandatory
   DESCRIPTION
     "This variable represents the index for the mscVrIpBgpImportNet tables."
::= { mscVrIpBgpImportNetRowStatusEntry 10 }

mscVrIpBgpImportNetProvTable OBJECT-TYPE
   SYNTAX     SEQUENCE OF MscVrIpBgpImportNetProvEntry
   ACCESS     not-accessible
   STATUS     mandatory
   DESCRIPTION
     "This group contains the set of provisionable attributes for the 
      Network component."
::= { mscVrIpBgpImportNet 10 }

mscVrIpBgpImportNetProvEntry OBJECT-TYPE
   SYNTAX     MscVrIpBgpImportNetProvEntry
   ACCESS     not-accessible
   STATUS     mandatory
   DESCRIPTION
     "An entry in the mscVrIpBgpImportNetProvTable."
   INDEX {
      mscVrIndex,
      mscVrIpIndex,
      mscVrIpBgpIndex,
      mscVrIpBgpImportIndex,
      mscVrIpBgpImportNetIndex }
::= { mscVrIpBgpImportNetProvTable 1 }

MscVrIpBgpImportNetProvEntry ::= SEQUENCE {
   mscVrIpBgpImportNetPrefix
      IpAddress,
   mscVrIpBgpImportNetLength
      Unsigned32 }

mscVrIpBgpImportNetPrefix OBJECT-TYPE
   SYNTAX     IpAddress 
   ACCESS     read-write
   STATUS     mandatory
   DESCRIPTION
     "This attribute specifies the network prefix whose length is 
      determined by the length attribute under the same Network 
      component."
::= { mscVrIpBgpImportNetProvEntry 1 }

mscVrIpBgpImportNetLength OBJECT-TYPE
   SYNTAX     Unsigned32 (1..32)
   ACCESS     read-write
   STATUS     mandatory
   DESCRIPTION
     "This attribute specifies the length of the network prefix."
::= { mscVrIpBgpImportNetProvEntry 2 }


-- Vr/<string> Ip Bgp Export/n
-- Each instance of this component describes a BGP export policy. A 
-- BGP export policy is used to decide if certain routing information 
-- should be blocked or advertised to its peers.
-- If no export policy is provisioned, BGP will advertise all external 
-- BGP learned routes to its internal peers, but not advertise any 
-- routing information to its external peers.
-- If multiple export policies are provisioned, the one with the most 
-- specific match will apply.
-- The keys are matched in the following order from the least specified 
-- to the most specified:
-- peerAs,
-- peerIpAddress, 
-- protocol, 
-- ripInterface (if applicable), 
-- egpAs, bgpAs, ripNeighbour, or ospfTag (whichever is applicable),
-- Network,
-- matchAsPath,
-- matchCommunity.
-- Example1: 
-- There are 2 export policies defined:
-- vr/0 ip bgp export/1, protocol = all, advertiseStatus = send
-- vr/0 ip bgp export/2, protocol = rip, advertiseStatus = block 
-- BGP will generate BGP updates for all routes except the routes 
-- learned from RIP.
-- Example2: 
-- There are 2 export policies defined:
-- vr/0 ip bgp export/1, protocol = all, matchCommunity = 303, 
-- advertiseStatus = send
-- vr/0 ip bgp export/2, protocol = all, advertiseStatus = block 
-- BGP will generate BGP updates for all routes that belongs to 
-- Community 303.
-- DESCRIPTION	

mscVrIpBgpExport OBJECT IDENTIFIER ::= { mscVrIpBgp 4 }



mscVrIpBgpExportRowStatusTable OBJECT-TYPE
   SYNTAX     SEQUENCE OF MscVrIpBgpExportRowStatusEntry
   ACCESS     not-accessible
   STATUS     mandatory
   DESCRIPTION
     "This entry controls the addition and deletion of 
      mscVrIpBgpExport components."
::= { mscVrIpBgpExport 1 }

mscVrIpBgpExportRowStatusEntry OBJECT-TYPE
   SYNTAX     MscVrIpBgpExportRowStatusEntry
   ACCESS     not-accessible
   STATUS     mandatory
   DESCRIPTION
     "A single entry in the table represents a single 
      mscVrIpBgpExport component."
   INDEX {
      mscVrIndex,
      mscVrIpIndex,
      mscVrIpBgpIndex,
      mscVrIpBgpExportIndex }
::= { mscVrIpBgpExportRowStatusTable 1 }

MscVrIpBgpExportRowStatusEntry ::= SEQUENCE {
   mscVrIpBgpExportRowStatus
      RowStatus,
   mscVrIpBgpExportComponentName
      DisplayString,
   mscVrIpBgpExportStorageType
      StorageType,
   mscVrIpBgpExportIndex
      Integer32 }

mscVrIpBgpExportRowStatus OBJECT-TYPE
   SYNTAX     RowStatus 
   ACCESS     read-write
   STATUS     mandatory
   DESCRIPTION
     "This variable is used as the basis for SNMP naming of
      mscVrIpBgpExport components.
      These components can be added and deleted."
::= { mscVrIpBgpExportRowStatusEntry 1 }

mscVrIpBgpExportComponentName OBJECT-TYPE
   SYNTAX     DisplayString 
   ACCESS     read-only
   STATUS     mandatory
   DESCRIPTION
     "This variable provides the component's string name for
      use with the ASCII Console Interface"
::= { mscVrIpBgpExportRowStatusEntry 2 }

mscVrIpBgpExportStorageType OBJECT-TYPE
   SYNTAX     StorageType 
   ACCESS     read-only
   STATUS     mandatory
   DESCRIPTION
     "This variable represents the storage type value for the
      mscVrIpBgpExport tables."
::= { mscVrIpBgpExportRowStatusEntry 4 }

mscVrIpBgpExportIndex OBJECT-TYPE
   SYNTAX     Integer32 (0..65535)
   ACCESS     not-accessible
   STATUS     mandatory
   DESCRIPTION
     "This variable represents the index for the mscVrIpBgpExport tables."
::= { mscVrIpBgpExportRowStatusEntry 10 }

mscVrIpBgpExportProvTable OBJECT-TYPE
   SYNTAX     SEQUENCE OF MscVrIpBgpExportProvEntry
   ACCESS     not-accessible
   STATUS     mandatory
   DESCRIPTION
     "This group contains all the provisioned attributes for the Export 
      component."
::= { mscVrIpBgpExport 10 }

mscVrIpBgpExportProvEntry OBJECT-TYPE
   SYNTAX     MscVrIpBgpExportProvEntry
   ACCESS     not-accessible
   STATUS     mandatory
   DESCRIPTION
     "An entry in the mscVrIpBgpExportProvTable."
   INDEX {
      mscVrIndex,
      mscVrIpIndex,
      mscVrIpBgpIndex,
      mscVrIpBgpExportIndex }
::= { mscVrIpBgpExportProvTable 1 }

MscVrIpBgpExportProvEntry ::= SEQUENCE {
   mscVrIpBgpExportPeerAs
      Unsigned32,
   mscVrIpBgpExportPeerIpAddress
      IpAddress,
   mscVrIpBgpExportProtocol
      INTEGER,
   mscVrIpBgpExportEgpAsId
      Unsigned32,
   mscVrIpBgpExportBgpAsId
      Unsigned32,
   mscVrIpBgpExportOspfTag
      Hex,
   mscVrIpBgpExportRipInterface
      IpAddress,
   mscVrIpBgpExportRipNeighbor
      IpAddress,
   mscVrIpBgpExportAdvertiseStatus
      INTEGER,
   mscVrIpBgpExportMultiExitDisc
      Unsigned32,
   mscVrIpBgpExportSendMultiExitDiscToEbgp
      INTEGER,
   mscVrIpBgpExportAsPathExpression
      AsciiString,
   mscVrIpBgpExportCommunityExpression
      AsciiString,
   mscVrIpBgpExportExpressPreference
      Unsigned32,
   mscVrIpBgpExportSendCommunity
      Unsigned32,
   mscVrIpBgpExportInsertDummyAs
      IntegerSequence }

mscVrIpBgpExportPeerAs OBJECT-TYPE
   SYNTAX     Unsigned32 (0..65535)
   ACCESS     read-write
   STATUS     mandatory
   DESCRIPTION
     "This key attribute specifies the autonomous system number of the 
      peer where the routes are advertised to. A value of 0 for this 
      attribute means this export policy applies to all peer ASes."
   DEFVAL     { 0 }
::= { mscVrIpBgpExportProvEntry 1 }

mscVrIpBgpExportPeerIpAddress OBJECT-TYPE
   SYNTAX     IpAddress 
   ACCESS     read-write
   STATUS     mandatory
   DESCRIPTION
     "This key attribute specifies the IP address of the peer where the 
      routes are advertised to. A value of 0.0.0.0 for this attribute means 
      this export policy applies to all peers."
   DEFVAL     { '00000000'H }  -- "0.0.0.0"
::= { mscVrIpBgpExportProvEntry 2 }

mscVrIpBgpExportProtocol OBJECT-TYPE
   SYNTAX     INTEGER  {
                 all(1),
                 egp(2),
                 rip(3),
                 ospfInternal(4),
                 ospfExternal(5),
                 staticLocal(6),
                 staticRemote(7),
                 bgpInternal(8),
                 bgpExternal(9) }
   ACCESS     read-write
   STATUS     mandatory
   DESCRIPTION
     "This key attribute specifies which protocol the export policy applies 
      to. If it is set to all, that means this export policy will apply all 
      routes in the IP routing table.
      Example: 
      vr/1 ip ospf export/1 with
      advertise Status = block
      protocol = bgpExternal
      bgpAsId = 3
      peerAs = 5
      This policy specifies that all routes learned from EBGP Peers that 
      are originated from AS 3 should not be advertised to AS 5."
   DEFVAL     { all }
::= { mscVrIpBgpExportProvEntry 3 }

mscVrIpBgpExportEgpAsId OBJECT-TYPE
   SYNTAX     Unsigned32 (0..65535)
   ACCESS     read-write
   STATUS     mandatory
   DESCRIPTION
     "This key attribute specifies the EGP autonomous system number 
      that this export policy will apply to.
      When this value is non-zero, the protocol attribute must be set to 
      egp."
   DEFVAL     { 0 }
::= { mscVrIpBgpExportProvEntry 4 }

mscVrIpBgpExportBgpAsId OBJECT-TYPE
   SYNTAX     Unsigned32 (0..65535)
   ACCESS     read-write
   STATUS     mandatory
   DESCRIPTION
     "This key attribute specifies the BGP autonomous system number 
      that this export policy will apply to.
      When this value is non-zero, the protocol attribute must be set to 
      either bgpInternal or bgpExternal."
   DEFVAL     { 0 }
::= { mscVrIpBgpExportProvEntry 5 }

mscVrIpBgpExportOspfTag OBJECT-TYPE
   SYNTAX     Hex (0..4294967295)
   ACCESS     read-write
   STATUS     mandatory
   DESCRIPTION
     "This key attribute specifies the OSPF tag when the protocol 
      attribute is set to either ospfInternal or ospfExternal. The default 
      tag value 4294967295 (FFFFFFFF in hex) indicates that the tag not 
      specified."
   DEFVAL     { 4294967295 }
::= { mscVrIpBgpExportProvEntry 6 }

mscVrIpBgpExportRipInterface OBJECT-TYPE
   SYNTAX     IpAddress 
   ACCESS     read-write
   STATUS     mandatory
   DESCRIPTION
     "This key attribute specifies the local RIP interface where the routes 
      are learned from.
      The ripInterface attribute when non-zero should be equal to one of 
      the IP addresses provisioned as a logicalIf component under IpPort. 
      Otherwise, this policy will be ignored.
      The value of the protocol attribute must be set to rip if a value for 
      the ripInterface attribute is non-zero."
   DEFVAL     { '00000000'H }  -- "0.0.0.0"
::= { mscVrIpBgpExportProvEntry 7 }

mscVrIpBgpExportRipNeighbor OBJECT-TYPE
   SYNTAX     IpAddress 
   ACCESS     read-write
   STATUS     mandatory
   DESCRIPTION
     "This key attribute specifies the RIP neighbor where the routes were 
      learned from.
      The value of the protocol attribute must be set to rip
      if a value for the ripNeighbor attribute is non-zero."
   DEFVAL     { '00000000'H }  -- "0.0.0.0"
::= { mscVrIpBgpExportProvEntry 8 }

mscVrIpBgpExportAdvertiseStatus OBJECT-TYPE
   SYNTAX     INTEGER  {
                 send(1),
                 block(2) }
   ACCESS     read-write
   STATUS     mandatory
   DESCRIPTION
     "This attribute specifies whether data will be exported if it meets 
      criteria specified by the other key attributes of this component."
   DEFVAL     { send }
::= { mscVrIpBgpExportProvEntry 9 }

mscVrIpBgpExportMultiExitDisc OBJECT-TYPE
   SYNTAX     Unsigned32 (0..4294967295)
   ACCESS     read-write
   STATUS     mandatory
   DESCRIPTION
     "This attribute specifies this Bgp component instance's metric to 
      discriminate between multiple exit points to an adjacent 
      autonomous system if the route meets the criteria specified by the 
      key attributes of this component. A lower value indicates a more 
      preferred route. A value of 0 for this attribute means the default 
      MED value provisioned under the Bgp component should be used."
   DEFVAL     { 0 }
::= { mscVrIpBgpExportProvEntry 10 }

mscVrIpBgpExportSendMultiExitDiscToEbgp OBJECT-TYPE
   SYNTAX     INTEGER  {
                 false(1),
                 true(2) }
   ACCESS     read-write
   STATUS     mandatory
   DESCRIPTION
     "This attribute specifies whether the Multi Exit Discriminator(MED) 
      attribute should be included in an update message sent to an EBGP 
      peer."
   DEFVAL     { false }
::= { mscVrIpBgpExportProvEntry 11 }

mscVrIpBgpExportAsPathExpression OBJECT-TYPE
   SYNTAX     AsciiString (SIZE (0..255))
   ACCESS     read-write
   STATUS     mandatory
   DESCRIPTION
     "This key attribute allows the user to enter a regular expression to 
      match the import AS Path Attribute of the export update message. 
      Note: the AS Path Attribute lists the ASs in reverse traversal order. 
      The syntax of the regular expression is a subset of the RFC 2280. 
      The basic syntax of a regular expression is a list of AS number 
      separated by a space which making up a AS path.
      The following characters has the special meaning:
      '.' 					- Matches any AS number.
      '^n' 		- Matches the first AS item (n) in the AS Path Attribute,
      or in order words, matches the last AS (n) traversed in
      the AS path.
      'n$' 		- Matches the last AS item (n) in the AS Path Attribute,
      or in order words, matches the first AS (n) traversed in
      the AS path.
      '[n1 ... n2]' 		- Matches any AS number that appeared in the set n1 ...
      n2.	
      'n1 - n2' 		- Matches any AS number between the range of n1 and
      n2.
      '()' 		- is supported to change the order of evaluation.
      'n*' 		- Matches 0 or more occurrences of n, where n can be a
      set, 	 range or AS number.
      'n+' 		- Matches 1 or more occurrences of n, where n can be a
      set, range or AS number.
      'n?' 		- Matches 0 or 1 occurrences of n, where n can be a
      set, range or number.
      The following logical operators are evaluated in decending order:
      'NOT' 		- Given a regular expression x, NOT x matches the AS
      number 	pattern that is not matched by x. 
      'AND'		- Given two regular expressions x and y, x AND y
      matches the intersection of the AS path that are
      matched by x and those are matched by y.
      'OR' 		- Given two regular expressions x and y, x OR y
      matches the union of the AS path that are matched by x
      and those are matched by y.
      For example: The AS path '5 4 3 2 1', where 1 is the origin AS, 
      would be match by any one of the following regular expressions:
      1$,
      ^5,
      4 3,
      5 3 - 4*,
      5 [4 3 2] not10 2 1,
      not (6 7 8 9 10) and 5 4 .* 1
      Empty regular expression implies a match on all AS path."
::= { mscVrIpBgpExportProvEntry 12 }

mscVrIpBgpExportCommunityExpression OBJECT-TYPE
   SYNTAX     AsciiString (SIZE (0..255))
   ACCESS     read-write
   STATUS     mandatory
   DESCRIPTION
     "This key attribute allows the user to enter a regular expression to 
      match the import Community Attribute of the received update 
      message. The syntax of the regular expression is a subset of the 
      RFC 2280. 
      The basic syntax of a regular expression is a list of Community 
      number seperated by a space which making up a Community 
      attribute.
      The following characters has the special meaning:
      '[n1 ... n2]' 		- Matches any Community number that appeared in the
      set n1 ...							n2.	
      'n1 - n2' 		- Matches any Community number between the range of
      n1 and 							n2.
      '()' 		- is supported to change the order of evaluation.
      'n*' 		- Matches 0 or more occurrences of n, where n can be a
      set, 	 range or Community number.
      'n+' 		- Matches 1 or more occurrences of n, where n can be a
      set, range or Community number.
      'n?' 		- Matches 0 or 1 occurrences of n, where n can be a
      set, range or number.
      The following logical operators are evaluated in decending order:
      'NOT' 		- Given a regular expression x, NOT x matches the
      Community 			attribute that is not matched by x. 
      'AND'		- Given two regular expressions x and y, x AND y
      matches the intersection of the Community attribute that
      are matched by x and those are matched by y.
      'OR' 		- Given two regular expressions x and y, x OR y
      matches the union of the Community attribute that are
      matched by x and those are matched by y.
      For example: The Community path '1 2 3 4 5' would be match by 
      any one of the following regular expression:
      1,
      5,
      4 3,
      2 3 - 4*,
      1 [3 4 2]+,
      not (6 7 8 9 10) and 1 2 
      Empty regular expression implies a match on all Community path."
::= { mscVrIpBgpExportProvEntry 13 }

mscVrIpBgpExportExpressPreference OBJECT-TYPE
   SYNTAX     Unsigned32 (0..255)
   ACCESS     read-write
   STATUS     mandatory
   DESCRIPTION
     "This attribute specifies the relative preference of the policy which 
      use the keys expressAsPath and expressCommunity. This attribute is 
      ignored if attributes expressAsPath and expressCommunity are both 
      empty. This attribute is used to break the tie when two export 
      policies' expression attributes match a specific AS Path or 
      Community. A higher value indicates a more preferred policy."
   DEFVAL     { 128 }
::= { mscVrIpBgpExportProvEntry 14 }

mscVrIpBgpExportSendCommunity OBJECT-TYPE
   SYNTAX     Unsigned32 (0..4294967295)
   ACCESS     read-write
   STATUS     mandatory
   DESCRIPTION
     "This attribute indicates which community number this Export policy 
      will send along with the Path Attribute. Refer to RFC 1997 for the 
      detailed description of how this attribute may be used to pass 
      additional information to BGP peers. If the value is set to 0, no 
      community is added to the Community attribute."
   DEFVAL     { 0 }
::= { mscVrIpBgpExportProvEntry 15 }

mscVrIpBgpExportInsertDummyAs OBJECT-TYPE
   SYNTAX     IntegerSequence 
   ACCESS     read-write
   STATUS     mandatory
   DESCRIPTION
     "This attribute specifies the AS number(s) to be inserted into the AS 
      Path Attribute. The value is a seuence of AS number seperated by 
      period(.). For example, if the value is 20.20.30, the AS numbers 20, 
      20 and 30 would be inserted at the end of the AS Path Attribute just 
      before the local AS number."
::= { mscVrIpBgpExportProvEntry 200 }


-- Vr/<string> Ip Bgp Export/n Network/n
-- This is an optional subcomponent of the Export component and 
-- identifies a destination network that this BGP export policy will 
-- apply to. This component is used as a key for the export policy. If 
-- no network list is provisioned, the import policy applies to all 
-- networks.

mscVrIpBgpExportNet OBJECT IDENTIFIER ::= { mscVrIpBgpExport 2 }



mscVrIpBgpExportNetRowStatusTable OBJECT-TYPE
   SYNTAX     SEQUENCE OF MscVrIpBgpExportNetRowStatusEntry
   ACCESS     not-accessible
   STATUS     mandatory
   DESCRIPTION
     "This entry controls the addition and deletion of 
      mscVrIpBgpExportNet components."
::= { mscVrIpBgpExportNet 1 }

mscVrIpBgpExportNetRowStatusEntry OBJECT-TYPE
   SYNTAX     MscVrIpBgpExportNetRowStatusEntry
   ACCESS     not-accessible
   STATUS     mandatory
   DESCRIPTION
     "A single entry in the table represents a single 
      mscVrIpBgpExportNet component."
   INDEX {
      mscVrIndex,
      mscVrIpIndex,
      mscVrIpBgpIndex,
      mscVrIpBgpExportIndex,
      mscVrIpBgpExportNetIndex }
::= { mscVrIpBgpExportNetRowStatusTable 1 }

MscVrIpBgpExportNetRowStatusEntry ::= SEQUENCE {
   mscVrIpBgpExportNetRowStatus
      RowStatus,
   mscVrIpBgpExportNetComponentName
      DisplayString,
   mscVrIpBgpExportNetStorageType
      StorageType,
   mscVrIpBgpExportNetIndex
      Integer32 }

mscVrIpBgpExportNetRowStatus OBJECT-TYPE
   SYNTAX     RowStatus 
   ACCESS     read-write
   STATUS     mandatory
   DESCRIPTION
     "This variable is used as the basis for SNMP naming of
      mscVrIpBgpExportNet components.
      These components can be added and deleted."
::= { mscVrIpBgpExportNetRowStatusEntry 1 }

mscVrIpBgpExportNetComponentName OBJECT-TYPE
   SYNTAX     DisplayString 
   ACCESS     read-only
   STATUS     mandatory
   DESCRIPTION
     "This variable provides the component's string name for
      use with the ASCII Console Interface"
::= { mscVrIpBgpExportNetRowStatusEntry 2 }

mscVrIpBgpExportNetStorageType OBJECT-TYPE
   SYNTAX     StorageType 
   ACCESS     read-only
   STATUS     mandatory
   DESCRIPTION
     "This variable represents the storage type value for the
      mscVrIpBgpExportNet tables."
::= { mscVrIpBgpExportNetRowStatusEntry 4 }

mscVrIpBgpExportNetIndex OBJECT-TYPE
   SYNTAX     Integer32 (0..65535)
   ACCESS     not-accessible
   STATUS     mandatory
   DESCRIPTION
     "This variable represents the index for the mscVrIpBgpExportNet tables."
::= { mscVrIpBgpExportNetRowStatusEntry 10 }

mscVrIpBgpExportNetProvTable OBJECT-TYPE
   SYNTAX     SEQUENCE OF MscVrIpBgpExportNetProvEntry
   ACCESS     not-accessible
   STATUS     mandatory
   DESCRIPTION
     "This group contains the set of provisionable attributes for the 
      Network component."
::= { mscVrIpBgpExportNet 10 }

mscVrIpBgpExportNetProvEntry OBJECT-TYPE
   SYNTAX     MscVrIpBgpExportNetProvEntry
   ACCESS     not-accessible
   STATUS     mandatory
   DESCRIPTION
     "An entry in the mscVrIpBgpExportNetProvTable."
   INDEX {
      mscVrIndex,
      mscVrIpIndex,
      mscVrIpBgpIndex,
      mscVrIpBgpExportIndex,
      mscVrIpBgpExportNetIndex }
::= { mscVrIpBgpExportNetProvTable 1 }

MscVrIpBgpExportNetProvEntry ::= SEQUENCE {
   mscVrIpBgpExportNetPrefix
      IpAddress,
   mscVrIpBgpExportNetLength
      Unsigned32 }

mscVrIpBgpExportNetPrefix OBJECT-TYPE
   SYNTAX     IpAddress 
   ACCESS     read-write
   STATUS     mandatory
   DESCRIPTION
     "This attribute specifies the network prefix whose length is 
      determined by the length attribute under the same Network 
      component."
::= { mscVrIpBgpExportNetProvEntry 1 }

mscVrIpBgpExportNetLength OBJECT-TYPE
   SYNTAX     Unsigned32 (1..32)
   ACCESS     read-write
   STATUS     mandatory
   DESCRIPTION
     "This attribute specifies the length of the network prefix."
::= { mscVrIpBgpExportNetProvEntry 2 }


-- Vr/<string> Ip Bgp As/n
-- This component associates attributes to an autonomous system.

mscVrIpBgpAs OBJECT IDENTIFIER ::= { mscVrIpBgp 5 }



mscVrIpBgpAsRowStatusTable OBJECT-TYPE
   SYNTAX     SEQUENCE OF MscVrIpBgpAsRowStatusEntry
   ACCESS     not-accessible
   STATUS     mandatory
   DESCRIPTION
     "This entry controls the addition and deletion of 
      mscVrIpBgpAs components."
::= { mscVrIpBgpAs 1 }

mscVrIpBgpAsRowStatusEntry OBJECT-TYPE
   SYNTAX     MscVrIpBgpAsRowStatusEntry
   ACCESS     not-accessible
   STATUS     mandatory
   DESCRIPTION
     "A single entry in the table represents a single 
      mscVrIpBgpAs component."
   INDEX {
      mscVrIndex,
      mscVrIpIndex,
      mscVrIpBgpIndex,
      mscVrIpBgpAsIndex }
::= { mscVrIpBgpAsRowStatusTable 1 }

MscVrIpBgpAsRowStatusEntry ::= SEQUENCE {
   mscVrIpBgpAsRowStatus
      RowStatus,
   mscVrIpBgpAsComponentName
      DisplayString,
   mscVrIpBgpAsStorageType
      StorageType,
   mscVrIpBgpAsIndex
      Integer32 }

mscVrIpBgpAsRowStatus OBJECT-TYPE
   SYNTAX     RowStatus 
   ACCESS     read-write
   STATUS     mandatory
   DESCRIPTION
     "This variable is used as the basis for SNMP naming of
      mscVrIpBgpAs components.
      These components can be added and deleted."
::= { mscVrIpBgpAsRowStatusEntry 1 }

mscVrIpBgpAsComponentName OBJECT-TYPE
   SYNTAX     DisplayString 
   ACCESS     read-only
   STATUS     mandatory
   DESCRIPTION
     "This variable provides the component's string name for
      use with the ASCII Console Interface"
::= { mscVrIpBgpAsRowStatusEntry 2 }

mscVrIpBgpAsStorageType OBJECT-TYPE
   SYNTAX     StorageType 
   ACCESS     read-only
   STATUS     mandatory
   DESCRIPTION
     "This variable represents the storage type value for the
      mscVrIpBgpAs tables."
::= { mscVrIpBgpAsRowStatusEntry 4 }

mscVrIpBgpAsIndex OBJECT-TYPE
   SYNTAX     Integer32 (0..65535)
   ACCESS     not-accessible
   STATUS     mandatory
   DESCRIPTION
     "This variable represents the index for the mscVrIpBgpAs tables."
::= { mscVrIpBgpAsRowStatusEntry 10 }

mscVrIpBgpAsProvTable OBJECT-TYPE
   SYNTAX     SEQUENCE OF MscVrIpBgpAsProvEntry
   ACCESS     not-accessible
   STATUS     mandatory
   DESCRIPTION
     "This group contains the attributes associated to each autonomous 
      system for this Bgp component instance."
::= { mscVrIpBgpAs 10 }

mscVrIpBgpAsProvEntry OBJECT-TYPE
   SYNTAX     MscVrIpBgpAsProvEntry
   ACCESS     not-accessible
   STATUS     mandatory
   DESCRIPTION
     "An entry in the mscVrIpBgpAsProvTable."
   INDEX {
      mscVrIndex,
      mscVrIpIndex,
      mscVrIpBgpIndex,
      mscVrIpBgpAsIndex }
::= { mscVrIpBgpAsProvTable 1 }

MscVrIpBgpAsProvEntry ::= SEQUENCE {
   mscVrIpBgpAsWeight
      Unsigned32 }

mscVrIpBgpAsWeight OBJECT-TYPE
   SYNTAX     Unsigned32 (0..255)
   ACCESS     read-write
   STATUS     mandatory
   DESCRIPTION
     "This attribute specifies the weight for an autonomous system. It 
      allows users to prefer some ASes over others. It is used in route 
      selection. Lowest weight is preferred. Setting the weight of an AS 
      to 255 will make any route that traverses through that AS 
      unpreferred."
   DEFVAL     { 128 }
::= { mscVrIpBgpAsProvEntry 1 }


-- Vr/<string> Ip Bgp AggregatePolicy/<Ip Address>,<Decimal>
-- This component is used to perform aggregation of BGP routes for 
-- exporting. Aggregation is the process of combining the 
-- characteristics of several different routes in such a way that a single 
-- route can be advertised. Aggregation reduces the amount of 
-- information that a BGP speaker must store and exchange with other 
-- BGP speakers. Refer to RFC1771 for the set of rules regarding 
-- which routes can be aggregated. 
-- A network subcomponent is automatically added with the same 
-- network range as the aggregation policy key and its action is set to 
-- aggregate. So by default all subnets under the aggregation key 
-- range will be aggregated.
-- Examples:
-- Example #1: aggregate all the networks covered by A.0.0.0/8
-- add vr/0 ip bgp aggregate/A.0.0.0,8
-- (Note: the following subcomponent vr/0 ip bgp aggregate/A.0.0.0,8 
-- network/0 prefix A.0.0.0, length 8, action aggregate will be 
-- automatically added)
-- 
-- Example #2: aggregate A.B.0.0/16 and A.C.0.0/16 as A.0.0.0/8 and 
-- advertise other networks
-- add vr/0 ip bgp aggregate/A.0.0.0,8
-- set vr/0 ip bgp aggregate/A.0.0.0,8 network/0 prefix A.B.0.0, length 
-- 16, action aggregate
-- (Note: this set command will overwrite the default network 
-- subcomponent
-- vr/0 ip bgp aggregate/A.0.0.0,8 network/0 prefix A.0.0.0, length 8, 
-- action aggregate)
-- add vr/0 ip bgp aggregate/A.0.0.0,8 network/1
-- set vr/0 ip bgp aggregate/A.0.0.0,8 network/1 prefix A.C.0.0, length 
-- 16, action aggregate
-- 
-- Example #3: aggregate A.B.0.0/16 and A.C.0.0/16 as A.0.0.0/8 and 
-- advertise other networks; also advertise A.B.C.0/24
-- add vr/0 ip bgp aggregate/A.0.0.0,8
-- set vr/0 ip bgp aggregate/A.0.0.0,8 networkl/0 prefix A.B.0.0, 
-- length 16, action aggregate
-- add vr/0 ip bgp aggregate/A.0.0.0,8 network/1
-- set vr/0 ip bgp aggregate/A.0.0.0,8 network/1 prefix A.C.0.0, length 
-- 16, action aggregate
-- add vr/0 ip bgp aggregate/A.0.0.0,8 network/2
-- set vr/0 ip bgp aggregate/A.0.0.0,8 network/2 prefix A.B.C.0, 
-- length 24, action advertise
-- 
-- Example #4: aggregate all networks under A.0.0.0/8, meanwhile 
-- advertise A.B.0.0/16
-- add vr/0 ip bgp aggregate/A.0.0.0,8
-- add vr/0 ip bgp aggregate/A.0.0.0,8 network/1
-- set vr/0 ip bgp aggregate/A.0.0.0,8 network/1 prefix A.B.0.0, length 
-- 16, action advertise

mscVrIpBgpAggregate OBJECT IDENTIFIER ::= { mscVrIpBgp 6 }



mscVrIpBgpAggregateRowStatusTable OBJECT-TYPE
   SYNTAX     SEQUENCE OF MscVrIpBgpAggregateRowStatusEntry
   ACCESS     not-accessible
   STATUS     mandatory
   DESCRIPTION
     "This entry controls the addition and deletion of 
      mscVrIpBgpAggregate components."
::= { mscVrIpBgpAggregate 1 }

mscVrIpBgpAggregateRowStatusEntry OBJECT-TYPE
   SYNTAX     MscVrIpBgpAggregateRowStatusEntry
   ACCESS     not-accessible
   STATUS     mandatory
   DESCRIPTION
     "A single entry in the table represents a single 
      mscVrIpBgpAggregate component."
   INDEX {
      mscVrIndex,
      mscVrIpIndex,
      mscVrIpBgpIndex,
      mscVrIpBgpAggregatePrefixIndex,
      mscVrIpBgpAggregateLengthIndex }
::= { mscVrIpBgpAggregateRowStatusTable 1 }

MscVrIpBgpAggregateRowStatusEntry ::= SEQUENCE {
   mscVrIpBgpAggregateRowStatus
      RowStatus,
   mscVrIpBgpAggregateComponentName
      DisplayString,
   mscVrIpBgpAggregateStorageType
      StorageType,
   mscVrIpBgpAggregatePrefixIndex
      IpAddress,
   mscVrIpBgpAggregateLengthIndex
      Integer32 }

mscVrIpBgpAggregateRowStatus OBJECT-TYPE
   SYNTAX     RowStatus 
   ACCESS     read-write
   STATUS     mandatory
   DESCRIPTION
     "This variable is used as the basis for SNMP naming of
      mscVrIpBgpAggregate components.
      These components can be added and deleted."
::= { mscVrIpBgpAggregateRowStatusEntry 1 }

mscVrIpBgpAggregateComponentName OBJECT-TYPE
   SYNTAX     DisplayString 
   ACCESS     read-only
   STATUS     mandatory
   DESCRIPTION
     "This variable provides the component's string name for
      use with the ASCII Console Interface"
::= { mscVrIpBgpAggregateRowStatusEntry 2 }

mscVrIpBgpAggregateStorageType OBJECT-TYPE
   SYNTAX     StorageType 
   ACCESS     read-only
   STATUS     mandatory
   DESCRIPTION
     "This variable represents the storage type value for the
      mscVrIpBgpAggregate tables."
::= { mscVrIpBgpAggregateRowStatusEntry 4 }

mscVrIpBgpAggregatePrefixIndex OBJECT-TYPE
   SYNTAX     IpAddress 
   ACCESS     not-accessible
   STATUS     mandatory
   DESCRIPTION
     "This variable represents an index for the mscVrIpBgpAggregate tables."
::= { mscVrIpBgpAggregateRowStatusEntry 10 }

mscVrIpBgpAggregateLengthIndex OBJECT-TYPE
   SYNTAX     Integer32 (0..32)
   ACCESS     not-accessible
   STATUS     mandatory
   DESCRIPTION
     "This variable represents an index for the mscVrIpBgpAggregate tables."
::= { mscVrIpBgpAggregateRowStatusEntry 11 }


-- Vr/<string> Ip Bgp AggregatePolicy/ Network/n
-- This is an optional subcomponent of Aggregate component and 
-- identifies a set of more specific routes that this BGP will aggregate 
-- or advertise together with the aggregated route.

mscVrIpBgpAggregateNet OBJECT IDENTIFIER ::= { mscVrIpBgpAggregate 2 }



mscVrIpBgpAggregateNetRowStatusTable OBJECT-TYPE
   SYNTAX     SEQUENCE OF MscVrIpBgpAggregateNetRowStatusEntry
   ACCESS     not-accessible
   STATUS     mandatory
   DESCRIPTION
     "This entry controls the addition and deletion of 
      mscVrIpBgpAggregateNet components."
::= { mscVrIpBgpAggregateNet 1 }

mscVrIpBgpAggregateNetRowStatusEntry OBJECT-TYPE
   SYNTAX     MscVrIpBgpAggregateNetRowStatusEntry
   ACCESS     not-accessible
   STATUS     mandatory
   DESCRIPTION
     "A single entry in the table represents a single 
      mscVrIpBgpAggregateNet component."
   INDEX {
      mscVrIndex,
      mscVrIpIndex,
      mscVrIpBgpIndex,
      mscVrIpBgpAggregatePrefixIndex,
      mscVrIpBgpAggregateLengthIndex,
      mscVrIpBgpAggregateNetIndex }
::= { mscVrIpBgpAggregateNetRowStatusTable 1 }

MscVrIpBgpAggregateNetRowStatusEntry ::= SEQUENCE {
   mscVrIpBgpAggregateNetRowStatus
      RowStatus,
   mscVrIpBgpAggregateNetComponentName
      DisplayString,
   mscVrIpBgpAggregateNetStorageType
      StorageType,
   mscVrIpBgpAggregateNetIndex
      Integer32 }

mscVrIpBgpAggregateNetRowStatus OBJECT-TYPE
   SYNTAX     RowStatus 
   ACCESS     read-write
   STATUS     mandatory
   DESCRIPTION
     "This variable is used as the basis for SNMP naming of
      mscVrIpBgpAggregateNet components.
      These components can be added and deleted."
::= { mscVrIpBgpAggregateNetRowStatusEntry 1 }

mscVrIpBgpAggregateNetComponentName OBJECT-TYPE
   SYNTAX     DisplayString 
   ACCESS     read-only
   STATUS     mandatory
   DESCRIPTION
     "This variable provides the component's string name for
      use with the ASCII Console Interface"
::= { mscVrIpBgpAggregateNetRowStatusEntry 2 }

mscVrIpBgpAggregateNetStorageType OBJECT-TYPE
   SYNTAX     StorageType 
   ACCESS     read-only
   STATUS     mandatory
   DESCRIPTION
     "This variable represents the storage type value for the
      mscVrIpBgpAggregateNet tables."
::= { mscVrIpBgpAggregateNetRowStatusEntry 4 }

mscVrIpBgpAggregateNetIndex OBJECT-TYPE
   SYNTAX     Integer32 (0..65535)
   ACCESS     not-accessible
   STATUS     mandatory
   DESCRIPTION
     "This variable represents the index for the mscVrIpBgpAggregateNet tables."
::= { mscVrIpBgpAggregateNetRowStatusEntry 10 }

mscVrIpBgpAggregateNetProvTable OBJECT-TYPE
   SYNTAX     SEQUENCE OF MscVrIpBgpAggregateNetProvEntry
   ACCESS     not-accessible
   STATUS     mandatory
   DESCRIPTION
     "This group contains the set of provisionable attributes for the 
      Network component."
::= { mscVrIpBgpAggregateNet 10 }

mscVrIpBgpAggregateNetProvEntry OBJECT-TYPE
   SYNTAX     MscVrIpBgpAggregateNetProvEntry
   ACCESS     not-accessible
   STATUS     mandatory
   DESCRIPTION
     "An entry in the mscVrIpBgpAggregateNetProvTable."
   INDEX {
      mscVrIndex,
      mscVrIpIndex,
      mscVrIpBgpIndex,
      mscVrIpBgpAggregatePrefixIndex,
      mscVrIpBgpAggregateLengthIndex,
      mscVrIpBgpAggregateNetIndex }
::= { mscVrIpBgpAggregateNetProvTable 1 }

MscVrIpBgpAggregateNetProvEntry ::= SEQUENCE {
   mscVrIpBgpAggregateNetPrefix
      IpAddress,
   mscVrIpBgpAggregateNetLength
      Unsigned32,
   mscVrIpBgpAggregateNetProtocol
      INTEGER,
   mscVrIpBgpAggregateNetEgpAsId
      Unsigned32,
   mscVrIpBgpAggregateNetBgpAsId
      Unsigned32,
   mscVrIpBgpAggregateNetOspfTag
      Hex,
   mscVrIpBgpAggregateNetRipInterface
      IpAddress,
   mscVrIpBgpAggregateNetAction
      INTEGER }

mscVrIpBgpAggregateNetPrefix OBJECT-TYPE
   SYNTAX     IpAddress 
   ACCESS     read-write
   STATUS     mandatory
   DESCRIPTION
     "This attribute specifies the network prefix whose length is 
      determined by the length attribute under the same Network 
      component."
   DEFVAL     { '00000000'H }  -- "0.0.0.0"
::= { mscVrIpBgpAggregateNetProvEntry 1 }

mscVrIpBgpAggregateNetLength OBJECT-TYPE
   SYNTAX     Unsigned32 (0..32)
   ACCESS     read-write
   STATUS     mandatory
   DESCRIPTION
     "This attribute specifies the length of the network prefix."
   DEFVAL     { 0 }
::= { mscVrIpBgpAggregateNetProvEntry 2 }

mscVrIpBgpAggregateNetProtocol OBJECT-TYPE
   SYNTAX     INTEGER  {
                 all(1),
                 egp(2),
                 rip(3),
                 ospfInternal(4),
                 ospfExternal(5),
                 staticLocal(6),
                 staticRemote(7),
                 bgpInternal(8),
                 bgpExternal(9) }
   ACCESS     read-write
   STATUS     mandatory
   DESCRIPTION
     "This attribute specifies the IP protocols to which this route should 
      belong."
   DEFVAL     { all }
::= { mscVrIpBgpAggregateNetProvEntry 3 }

mscVrIpBgpAggregateNetEgpAsId OBJECT-TYPE
   SYNTAX     Unsigned32 (0..65535)
   ACCESS     read-write
   STATUS     mandatory
   DESCRIPTION
     "This attribute specifies an EGP autonomous system number. 
      
      When this value is non-zero, the protocol attribute must be set to 
      either egp or to all. And this more specific route will be advertised 
      together with the aggregated route only if it is learned through egp 
      and this attribute matches the EGP autonomous system number 
      where the network is learned from.
      The default value 0 indicates that the EGP autonomous system 
      number is not specified."
   DEFVAL     { 0 }
::= { mscVrIpBgpAggregateNetProvEntry 4 }

mscVrIpBgpAggregateNetBgpAsId OBJECT-TYPE
   SYNTAX     Unsigned32 (0..65535)
   ACCESS     read-write
   STATUS     mandatory
   DESCRIPTION
     "This attribute specifies the BGP autonomous system number.
      
      When this value is non-zero, the protocol attribute must be set to 
      either bgp or to all. And this more specific route will be advertised 
      together with the aggregated route only if it is learned through BGP 
      and this attribute matches the BGP autonomous system number 
      where the network is learned from.
      The default value 0 indicates that the BGP autonomous system 
      number is not specified."
   DEFVAL     { 0 }
::= { mscVrIpBgpAggregateNetProvEntry 5 }

mscVrIpBgpAggregateNetOspfTag OBJECT-TYPE
   SYNTAX     Hex (0..4294967295)
   ACCESS     read-write
   STATUS     mandatory
   DESCRIPTION
     "This attribute specifies the OSPF tag.
      
      When this attribute is set to a value other than the default value 
      FFFFFFFF in hex, the protocol attribute must be set to either ospf 
      or to all. And this more specific route will be advertised together 
      with the aggregated route only if its OSPF tag matches this 
      value. 
      The default tag value 4294967295 (FFFFFFFF in hex) indicates that 
      the tag is not specified."
   DEFVAL     { 4294967295 }
::= { mscVrIpBgpAggregateNetProvEntry 6 }

mscVrIpBgpAggregateNetRipInterface OBJECT-TYPE
   SYNTAX     IpAddress 
   ACCESS     read-write
   STATUS     mandatory
   DESCRIPTION
     "This attribute specifies a local RIP interface which should be equal 
      to one of the IP addresses provisioned as a logicalIf component 
      under IpPort.
      
      When this value is non-zero, the value of the protocol attribute must 
      be either set to rip or to all. And this more specific route will be 
      advertised together with the aggregated route only if it is learned 
      through RIP and this RIP interface.
      The default value 0.0.0.0 indicates that the RIP interface is not 
      specified."
   DEFVAL     { '00000000'H }  -- "0.0.0.0"
::= { mscVrIpBgpAggregateNetProvEntry 7 }

mscVrIpBgpAggregateNetAction OBJECT-TYPE
   SYNTAX     INTEGER  {
                 aggregate(1),
                 advertise(2) }
   ACCESS     read-write
   STATUS     mandatory
   DESCRIPTION
     "This attribute specifies whether this network should be aggregated 
      or advertised out."
   DEFVAL     { aggregate }
::= { mscVrIpBgpAggregateNetProvEntry 8 }

-- 
-- *** THIS SUBTREE CURRENTLY NOT IMPLEMENTED ***
-- 

-- Vr/<string> Ip Bgp IndbEntry/<Ip Address>,<Decimal>,<Ip 
-- Address>
-- This component describes a BGP route received from one of its 
-- peers.

mscVrIpBgpIndb OBJECT IDENTIFIER ::= { mscVrIpBgp 7 }



mscVrIpBgpIndbRowStatusTable OBJECT-TYPE
   SYNTAX     SEQUENCE OF MscVrIpBgpIndbRowStatusEntry
   ACCESS     not-accessible
   STATUS     mandatory
   DESCRIPTION
     "*** THIS TABLE CURRENTLY NOT IMPLEMENTED ***

      This entry controls the addition and deletion of 
      mscVrIpBgpIndb components."
::= { mscVrIpBgpIndb 1 }

mscVrIpBgpIndbRowStatusEntry OBJECT-TYPE
   SYNTAX     MscVrIpBgpIndbRowStatusEntry
   ACCESS     not-accessible
   STATUS     mandatory
   DESCRIPTION
     "A single entry in the table represents a single 
      mscVrIpBgpIndb component."
   INDEX {
      mscVrIndex,
      mscVrIpIndex,
      mscVrIpBgpIndex,
      mscVrIpBgpIndbPrefixIndex,
      mscVrIpBgpIndbLengthIndex,
      mscVrIpBgpIndbPeerIndex }
::= { mscVrIpBgpIndbRowStatusTable 1 }

MscVrIpBgpIndbRowStatusEntry ::= SEQUENCE {
   mscVrIpBgpIndbRowStatus
      RowStatus,
   mscVrIpBgpIndbComponentName
      DisplayString,
   mscVrIpBgpIndbStorageType
      StorageType,
   mscVrIpBgpIndbPrefixIndex
      IpAddress,
   mscVrIpBgpIndbLengthIndex
      Integer32,
   mscVrIpBgpIndbPeerIndex
      IpAddress }

mscVrIpBgpIndbRowStatus OBJECT-TYPE
   SYNTAX     RowStatus 
   ACCESS     read-only
   STATUS     mandatory
   DESCRIPTION
     "This variable is used as the basis for SNMP naming of
      mscVrIpBgpIndb components.
      These components cannot be added nor deleted."
::= { mscVrIpBgpIndbRowStatusEntry 1 }

mscVrIpBgpIndbComponentName OBJECT-TYPE
   SYNTAX     DisplayString 
   ACCESS     read-only
   STATUS     mandatory
   DESCRIPTION
     "This variable provides the component's string name for
      use with the ASCII Console Interface"
::= { mscVrIpBgpIndbRowStatusEntry 2 }

mscVrIpBgpIndbStorageType OBJECT-TYPE
   SYNTAX     StorageType 
   ACCESS     read-only
   STATUS     mandatory
   DESCRIPTION
     "This variable represents the storage type value for the
      mscVrIpBgpIndb tables."
::= { mscVrIpBgpIndbRowStatusEntry 4 }

mscVrIpBgpIndbPrefixIndex OBJECT-TYPE
   SYNTAX     IpAddress 
   ACCESS     not-accessible
   STATUS     mandatory
   DESCRIPTION
     "This variable represents an index for the mscVrIpBgpIndb tables."
::= { mscVrIpBgpIndbRowStatusEntry 10 }

mscVrIpBgpIndbLengthIndex OBJECT-TYPE
   SYNTAX     Integer32 (0..32)
   ACCESS     not-accessible
   STATUS     mandatory
   DESCRIPTION
     "This variable represents an index for the mscVrIpBgpIndb tables."
::= { mscVrIpBgpIndbRowStatusEntry 11 }

mscVrIpBgpIndbPeerIndex OBJECT-TYPE
   SYNTAX     IpAddress 
   ACCESS     not-accessible
   STATUS     mandatory
   DESCRIPTION
     "This variable represents an index for the mscVrIpBgpIndb tables."
::= { mscVrIpBgpIndbRowStatusEntry 12 }

mscVrIpBgpIndbOperTable OBJECT-TYPE
   SYNTAX     SEQUENCE OF MscVrIpBgpIndbOperEntry
   ACCESS     not-accessible
   STATUS     mandatory
   DESCRIPTION
     "*** THIS TABLE CURRENTLY NOT IMPLEMENTED ***

      This group contains all the operational attributes of the IndbEntry 
      component."
::= { mscVrIpBgpIndb 10 }

mscVrIpBgpIndbOperEntry OBJECT-TYPE
   SYNTAX     MscVrIpBgpIndbOperEntry
   ACCESS     not-accessible
   STATUS     mandatory
   DESCRIPTION
     "An entry in the mscVrIpBgpIndbOperTable."
   INDEX {
      mscVrIndex,
      mscVrIpIndex,
      mscVrIpBgpIndex,
      mscVrIpBgpIndbPrefixIndex,
      mscVrIpBgpIndbLengthIndex,
      mscVrIpBgpIndbPeerIndex }
::= { mscVrIpBgpIndbOperTable 1 }

MscVrIpBgpIndbOperEntry ::= SEQUENCE {
   mscVrIpBgpIndbOrigin
      INTEGER,
   mscVrIpBgpIndbInLocaldb
      INTEGER,
   mscVrIpBgpIndbNextHop
      IpAddress,
   mscVrIpBgpIndbLocalPreference
      Unsigned32,
   mscVrIpBgpIndbCalcLocalPref
      Unsigned32,
   mscVrIpBgpIndbMultiExitDiscriminator
      Unsigned32,
   mscVrIpBgpIndbAtomicAggregate
      INTEGER,
   mscVrIpBgpIndbAggregatorAs
      Unsigned32,
   mscVrIpBgpIndbAggregatorAddr
      IpAddress,
   mscVrIpBgpIndbAsPath
      AsciiString,
   mscVrIpBgpIndbUnknownAttributes
      AsciiString,
   mscVrIpBgpIndbCommunityPath
      AsciiString,
   mscVrIpBgpIndbAsOriginatorId
      IpAddress }

mscVrIpBgpIndbOrigin OBJECT-TYPE
   SYNTAX     INTEGER  {
                 igp(1),
                 egp(2),
                 incomplete(3) }
   ACCESS     read-only
   STATUS     mandatory
   DESCRIPTION
     "This attribute indicates the ultimate origin of the path information. 
      A value of incomplete means this information is not available."
::= { mscVrIpBgpIndbOperEntry 4 }

mscVrIpBgpIndbInLocaldb OBJECT-TYPE
   SYNTAX     INTEGER  {
                 false(1),
                 true(2) }
   ACCESS     read-only
   STATUS     mandatory
   DESCRIPTION
     "This attribute indicates whether or not this route was chosen as the 
      best BGP4 route."
::= { mscVrIpBgpIndbOperEntry 5 }

mscVrIpBgpIndbNextHop OBJECT-TYPE
   SYNTAX     IpAddress 
   ACCESS     read-only
   STATUS     mandatory
   DESCRIPTION
     "This attribute indicates the IP address of the border router that 
      should be used as the next hop for the destination network."
::= { mscVrIpBgpIndbOperEntry 6 }

mscVrIpBgpIndbLocalPreference OBJECT-TYPE
   SYNTAX     Unsigned32 (0..4294967295)
   ACCESS     read-only
   STATUS     mandatory
   DESCRIPTION
     "This attribute indicates our IBGP peer's degree of preference for an 
      advertised route. A higher value indicates a more preferred route."
::= { mscVrIpBgpIndbOperEntry 7 }

mscVrIpBgpIndbCalcLocalPref OBJECT-TYPE
   SYNTAX     Unsigned32 (0..4294967295)
   ACCESS     read-only
   STATUS     mandatory
   DESCRIPTION
     "This attribute indicates our degree of preference for this route. A 
      higher value indicates a more preferred route."
::= { mscVrIpBgpIndbOperEntry 8 }

mscVrIpBgpIndbMultiExitDiscriminator OBJECT-TYPE
   SYNTAX     Unsigned32 (0..4294967295)
   ACCESS     read-only
   STATUS     mandatory
   DESCRIPTION
     "This attribute indicates a metric used to discriminate between 
      multiple exit points to the same adjacent autonomous system. A 
      lower value indicates a more preferred route."
::= { mscVrIpBgpIndbOperEntry 9 }

mscVrIpBgpIndbAtomicAggregate OBJECT-TYPE
   SYNTAX     INTEGER  {
                 lessSpecificRouteNotSelected(1),
                 lessSpecificRouteSelected(2) }
   ACCESS     read-only
   STATUS     mandatory
   DESCRIPTION
     "This attribute indicates whether or not the local system has selected 
      a less specific route without selecting a more specific route."
::= { mscVrIpBgpIndbOperEntry 10 }

mscVrIpBgpIndbAggregatorAs OBJECT-TYPE
   SYNTAX     Unsigned32 (0..65535)
   ACCESS     read-only
   STATUS     mandatory
   DESCRIPTION
     "This attribute indicates the AS number of the last BGP4 speaker 
      that performed route aggregation. A value of zero (0) indicates the 
      absence of this attribute."
::= { mscVrIpBgpIndbOperEntry 11 }

mscVrIpBgpIndbAggregatorAddr OBJECT-TYPE
   SYNTAX     IpAddress 
   ACCESS     read-only
   STATUS     mandatory
   DESCRIPTION
     "This attribute indicates the IP address of the last BGP4 speaker that 
      performed route aggregation. A value of 0.0.0.0 indicates the 
      absence of this attribute."
::= { mscVrIpBgpIndbOperEntry 12 }

mscVrIpBgpIndbAsPath OBJECT-TYPE
   SYNTAX     AsciiString (SIZE (2..255))
   ACCESS     read-only
   STATUS     mandatory
   DESCRIPTION
     "This attribute indicates the sequence of AS path segments. The AS 
      Path Attribute lists the ASs in reverse traversal order."
::= { mscVrIpBgpIndbOperEntry 13 }

mscVrIpBgpIndbUnknownAttributes OBJECT-TYPE
   SYNTAX     AsciiString (SIZE (0..255))
   ACCESS     read-only
   STATUS     mandatory
   DESCRIPTION
     "This attribute indicates all the path attributes not understood by this 
      Bgp component instance."
::= { mscVrIpBgpIndbOperEntry 14 }

mscVrIpBgpIndbCommunityPath OBJECT-TYPE
   SYNTAX     AsciiString (SIZE (0..255))
   ACCESS     read-only
   STATUS     mandatory
   DESCRIPTION
     "This attribute indicates the Community path attribute."
::= { mscVrIpBgpIndbOperEntry 15 }

mscVrIpBgpIndbAsOriginatorId OBJECT-TYPE
   SYNTAX     IpAddress 
   ACCESS     read-only
   STATUS     mandatory
   DESCRIPTION
     "This attribute is associated with the Route Reflector. It indicates the 
      router-id of the originator in the local AS. A value of 0.0.0.0 
      indicates this attribute is not present in the learned IBGP route or if 
      this Bgp instance is not a Route Reflector."
::= { mscVrIpBgpIndbOperEntry 16 }

mscVrIpBgpIndbRrClusterListTable OBJECT-TYPE
   SYNTAX     SEQUENCE OF MscVrIpBgpIndbRrClusterListEntry
   ACCESS     not-accessible
   STATUS     mandatory
   DESCRIPTION
     "*** THIS TABLE CURRENTLY NOT IMPLEMENTED ***

      This attribute indicates a sequence of cluster-ids that the route has 
      traversed. A blank list indicates this attribute is not present in the 
      learned IBGP route or if this Bgp instance is not a Route Reflector."
::= { mscVrIpBgpIndb 798 }

mscVrIpBgpIndbRrClusterListEntry OBJECT-TYPE
   SYNTAX     MscVrIpBgpIndbRrClusterListEntry
   ACCESS     not-accessible
   STATUS     mandatory
   DESCRIPTION
     "An entry in the mscVrIpBgpIndbRrClusterListTable."
   INDEX {
      mscVrIndex,
      mscVrIpIndex,
      mscVrIpBgpIndex,
      mscVrIpBgpIndbPrefixIndex,
      mscVrIpBgpIndbLengthIndex,
      mscVrIpBgpIndbPeerIndex,
      mscVrIpBgpIndbRrClusterListValue }
::= { mscVrIpBgpIndbRrClusterListTable 1 }

MscVrIpBgpIndbRrClusterListEntry ::= SEQUENCE {
   mscVrIpBgpIndbRrClusterListValue
      IpAddress }

mscVrIpBgpIndbRrClusterListValue OBJECT-TYPE
   SYNTAX     IpAddress 
   ACCESS     read-only
   STATUS     mandatory
   DESCRIPTION
     "This variable represents both the value and the index for the
      mscVrIpBgpIndbRrClusterListTable."
::= { mscVrIpBgpIndbRrClusterListEntry 1 }

-- 
-- *** THIS SUBTREE CURRENTLY NOT IMPLEMENTED ***
-- 

-- Vr/<string> Ip Bgp LocaldbEntry/<Ip Address>,<Decimal>,<Ip 
-- Address>
-- This component describes an entry in the BGP local database. This 
-- database contains the routing information that the BGP speaker has 
-- selected by applying its local import policies and decision process 
-- to the routing information stored in IndbEntry.

mscVrIpBgpLocaldb OBJECT IDENTIFIER ::= { mscVrIpBgp 8 }



mscVrIpBgpLocaldbRowStatusTable OBJECT-TYPE
   SYNTAX     SEQUENCE OF MscVrIpBgpLocaldbRowStatusEntry
   ACCESS     not-accessible
   STATUS     mandatory
   DESCRIPTION
     "*** THIS TABLE CURRENTLY NOT IMPLEMENTED ***

      This entry controls the addition and deletion of 
      mscVrIpBgpLocaldb components."
::= { mscVrIpBgpLocaldb 1 }

mscVrIpBgpLocaldbRowStatusEntry OBJECT-TYPE
   SYNTAX     MscVrIpBgpLocaldbRowStatusEntry
   ACCESS     not-accessible
   STATUS     mandatory
   DESCRIPTION
     "A single entry in the table represents a single 
      mscVrIpBgpLocaldb component."
   INDEX {
      mscVrIndex,
      mscVrIpIndex,
      mscVrIpBgpIndex,
      mscVrIpBgpLocaldbPrefixIndex,
      mscVrIpBgpLocaldbLengthIndex,
      mscVrIpBgpLocaldbPeerIndex }
::= { mscVrIpBgpLocaldbRowStatusTable 1 }

MscVrIpBgpLocaldbRowStatusEntry ::= SEQUENCE {
   mscVrIpBgpLocaldbRowStatus
      RowStatus,
   mscVrIpBgpLocaldbComponentName
      DisplayString,
   mscVrIpBgpLocaldbStorageType
      StorageType,
   mscVrIpBgpLocaldbPrefixIndex
      IpAddress,
   mscVrIpBgpLocaldbLengthIndex
      Integer32,
   mscVrIpBgpLocaldbPeerIndex
      IpAddress }

mscVrIpBgpLocaldbRowStatus OBJECT-TYPE
   SYNTAX     RowStatus 
   ACCESS     read-only
   STATUS     mandatory
   DESCRIPTION
     "This variable is used as the basis for SNMP naming of
      mscVrIpBgpLocaldb components.
      These components cannot be added nor deleted."
::= { mscVrIpBgpLocaldbRowStatusEntry 1 }

mscVrIpBgpLocaldbComponentName OBJECT-TYPE
   SYNTAX     DisplayString 
   ACCESS     read-only
   STATUS     mandatory
   DESCRIPTION
     "This variable provides the component's string name for
      use with the ASCII Console Interface"
::= { mscVrIpBgpLocaldbRowStatusEntry 2 }

mscVrIpBgpLocaldbStorageType OBJECT-TYPE
   SYNTAX     StorageType 
   ACCESS     read-only
   STATUS     mandatory
   DESCRIPTION
     "This variable represents the storage type value for the
      mscVrIpBgpLocaldb tables."
::= { mscVrIpBgpLocaldbRowStatusEntry 4 }

mscVrIpBgpLocaldbPrefixIndex OBJECT-TYPE
   SYNTAX     IpAddress 
   ACCESS     not-accessible
   STATUS     mandatory
   DESCRIPTION
     "This variable represents an index for the mscVrIpBgpLocaldb tables."
::= { mscVrIpBgpLocaldbRowStatusEntry 10 }

mscVrIpBgpLocaldbLengthIndex OBJECT-TYPE
   SYNTAX     Integer32 (0..32)
   ACCESS     not-accessible
   STATUS     mandatory
   DESCRIPTION
     "This variable represents an index for the mscVrIpBgpLocaldb tables."
::= { mscVrIpBgpLocaldbRowStatusEntry 11 }

mscVrIpBgpLocaldbPeerIndex OBJECT-TYPE
   SYNTAX     IpAddress 
   ACCESS     not-accessible
   STATUS     mandatory
   DESCRIPTION
     "This variable represents an index for the mscVrIpBgpLocaldb tables."
::= { mscVrIpBgpLocaldbRowStatusEntry 12 }

mscVrIpBgpLocaldbOperTable OBJECT-TYPE
   SYNTAX     SEQUENCE OF MscVrIpBgpLocaldbOperEntry
   ACCESS     not-accessible
   STATUS     mandatory
   DESCRIPTION
     "*** THIS TABLE CURRENTLY NOT IMPLEMENTED ***

      This group contains all the operational attributes of the 
      LocaldbEntry component."
::= { mscVrIpBgpLocaldb 10 }

mscVrIpBgpLocaldbOperEntry OBJECT-TYPE
   SYNTAX     MscVrIpBgpLocaldbOperEntry
   ACCESS     not-accessible
   STATUS     mandatory
   DESCRIPTION
     "An entry in the mscVrIpBgpLocaldbOperTable."
   INDEX {
      mscVrIndex,
      mscVrIpIndex,
      mscVrIpBgpIndex,
      mscVrIpBgpLocaldbPrefixIndex,
      mscVrIpBgpLocaldbLengthIndex,
      mscVrIpBgpLocaldbPeerIndex }
::= { mscVrIpBgpLocaldbOperTable 1 }

MscVrIpBgpLocaldbOperEntry ::= SEQUENCE {
   mscVrIpBgpLocaldbOrigin
      INTEGER,
   mscVrIpBgpLocaldbNextHop
      IpAddress,
   mscVrIpBgpLocaldbLocalPreference
      Unsigned32,
   mscVrIpBgpLocaldbMultiExitDiscriminator
      Unsigned32,
   mscVrIpBgpLocaldbAtomicAggregate
      INTEGER,
   mscVrIpBgpLocaldbAggregatorAs
      Unsigned32,
   mscVrIpBgpLocaldbAggregatorAddr
      IpAddress,
   mscVrIpBgpLocaldbAsPath
      AsciiString,
   mscVrIpBgpLocaldbUnknownAttributes
      AsciiString,
   mscVrIpBgpLocaldbCommunityPath
      AsciiString,
   mscVrIpBgpLocaldbAsOriginatorId
      IpAddress }

mscVrIpBgpLocaldbOrigin OBJECT-TYPE
   SYNTAX     INTEGER  {
                 igp(1),
                 egp(2),
                 incomplete(3) }
   ACCESS     read-only
   STATUS     mandatory
   DESCRIPTION
     "This attribute indicates the ultimate origin of the path information. 
      A value of incomplete means this information is not available."
::= { mscVrIpBgpLocaldbOperEntry 4 }

mscVrIpBgpLocaldbNextHop OBJECT-TYPE
   SYNTAX     IpAddress 
   ACCESS     read-only
   STATUS     mandatory
   DESCRIPTION
     "This attribute indicates the IP address of the border router that 
      should be used as the next hop for the destination network."
::= { mscVrIpBgpLocaldbOperEntry 5 }

mscVrIpBgpLocaldbLocalPreference OBJECT-TYPE
   SYNTAX     Unsigned32 (0..4294967295)
   ACCESS     read-only
   STATUS     mandatory
   DESCRIPTION
     "This attribute indicates our IBGP peer's degree of preference for an 
      advertised route. A higher value indicates a more preferred route."
::= { mscVrIpBgpLocaldbOperEntry 6 }

mscVrIpBgpLocaldbMultiExitDiscriminator OBJECT-TYPE
   SYNTAX     Unsigned32 (0..4294967295)
   ACCESS     read-only
   STATUS     mandatory
   DESCRIPTION
     "This attribute indicates a metric used to discriminate between 
      multiple exit points to the same adjacent autonomous system. A 
      lower value indicates a more preferred route."
::= { mscVrIpBgpLocaldbOperEntry 7 }

mscVrIpBgpLocaldbAtomicAggregate OBJECT-TYPE
   SYNTAX     INTEGER  {
                 lessSpecificRouteNotSelected(1),
                 lessSpecificRouteSelected(2) }
   ACCESS     read-only
   STATUS     mandatory
   DESCRIPTION
     "This attribute indicates whether or not the local system has selected 
      a less specific route without selecting a more specific route."
::= { mscVrIpBgpLocaldbOperEntry 8 }

mscVrIpBgpLocaldbAggregatorAs OBJECT-TYPE
   SYNTAX     Unsigned32 (0..65535)
   ACCESS     read-only
   STATUS     mandatory
   DESCRIPTION
     "This attribute indicates the AS number of the last BGP4 speaker 
      that performed route aggregation. A value of zero (0) indicates the 
      absence of this attribute."
::= { mscVrIpBgpLocaldbOperEntry 9 }

mscVrIpBgpLocaldbAggregatorAddr OBJECT-TYPE
   SYNTAX     IpAddress 
   ACCESS     read-only
   STATUS     mandatory
   DESCRIPTION
     "This attribute indicates the IP address of the last BGP4 speaker that 
      performed route aggregation. A value of 0.0.0.0 indicates the 
      absence of this attribute."
::= { mscVrIpBgpLocaldbOperEntry 10 }

mscVrIpBgpLocaldbAsPath OBJECT-TYPE
   SYNTAX     AsciiString (SIZE (2..255))
   ACCESS     read-only
   STATUS     mandatory
   DESCRIPTION
     "This attribute indicates the sequence of AS path segments. The AS 
      Path Attribute lists the ASs in reverse traversal order."
::= { mscVrIpBgpLocaldbOperEntry 11 }

mscVrIpBgpLocaldbUnknownAttributes OBJECT-TYPE
   SYNTAX     AsciiString (SIZE (0..255))
   ACCESS     read-only
   STATUS     mandatory
   DESCRIPTION
     "This attribute indicates all the path attributes not understood by this 
      Bgp component instance."
::= { mscVrIpBgpLocaldbOperEntry 12 }

mscVrIpBgpLocaldbCommunityPath OBJECT-TYPE
   SYNTAX     AsciiString (SIZE (0..255))
   ACCESS     read-only
   STATUS     mandatory
   DESCRIPTION
     "This attribute indicates the Community path attribute."
::= { mscVrIpBgpLocaldbOperEntry 13 }

mscVrIpBgpLocaldbAsOriginatorId OBJECT-TYPE
   SYNTAX     IpAddress 
   ACCESS     read-only
   STATUS     mandatory
   DESCRIPTION
     "This attribute is associated with the Route Reflector. It indicates the 
      router-id of the originator in the local AS. A value of 0.0.0.0 
      indicates this attribute is not present in the learned IBGP route or if 
      this Bgp instance is not a Route Reflector."
::= { mscVrIpBgpLocaldbOperEntry 14 }

mscVrIpBgpLocaldbRrClusterListTable OBJECT-TYPE
   SYNTAX     SEQUENCE OF MscVrIpBgpLocaldbRrClusterListEntry
   ACCESS     not-accessible
   STATUS     mandatory
   DESCRIPTION
     "*** THIS TABLE CURRENTLY NOT IMPLEMENTED ***

      This attribute indicates a sequence of cluster-ids that the route has 
      traversed. A blank list indicates this attribute is not present in the 
      learned IBGP route or if this Bgp instance is not a Route Reflector."
::= { mscVrIpBgpLocaldb 797 }

mscVrIpBgpLocaldbRrClusterListEntry OBJECT-TYPE
   SYNTAX     MscVrIpBgpLocaldbRrClusterListEntry
   ACCESS     not-accessible
   STATUS     mandatory
   DESCRIPTION
     "An entry in the mscVrIpBgpLocaldbRrClusterListTable."
   INDEX {
      mscVrIndex,
      mscVrIpIndex,
      mscVrIpBgpIndex,
      mscVrIpBgpLocaldbPrefixIndex,
      mscVrIpBgpLocaldbLengthIndex,
      mscVrIpBgpLocaldbPeerIndex,
      mscVrIpBgpLocaldbRrClusterListValue }
::= { mscVrIpBgpLocaldbRrClusterListTable 1 }

MscVrIpBgpLocaldbRrClusterListEntry ::= SEQUENCE {
   mscVrIpBgpLocaldbRrClusterListValue
      IpAddress }

mscVrIpBgpLocaldbRrClusterListValue OBJECT-TYPE
   SYNTAX     IpAddress 
   ACCESS     read-only
   STATUS     mandatory
   DESCRIPTION
     "This variable represents both the value and the index for the
      mscVrIpBgpLocaldbRrClusterListTable."
::= { mscVrIpBgpLocaldbRrClusterListEntry 1 }

-- 
-- *** THIS SUBTREE CURRENTLY NOT IMPLEMENTED ***
-- 

-- Vr/<string> Ip Bgp OutdbEntry/<Ip Address>,<Decimal>,<Ip 
-- Address>
-- This component describes an entry in the BGP output database that 
-- BGP advertises to its peers. The database contents are selected by 
-- applying its local export policies to the routing information stored 
-- in the IP forwarding table.

mscVrIpBgpOutdb OBJECT IDENTIFIER ::= { mscVrIpBgp 9 }



mscVrIpBgpOutdbRowStatusTable OBJECT-TYPE
   SYNTAX     SEQUENCE OF MscVrIpBgpOutdbRowStatusEntry
   ACCESS     not-accessible
   STATUS     mandatory
   DESCRIPTION
     "*** THIS TABLE CURRENTLY NOT IMPLEMENTED ***

      This entry controls the addition and deletion of 
      mscVrIpBgpOutdb components."
::= { mscVrIpBgpOutdb 1 }

mscVrIpBgpOutdbRowStatusEntry OBJECT-TYPE
   SYNTAX     MscVrIpBgpOutdbRowStatusEntry
   ACCESS     not-accessible
   STATUS     mandatory
   DESCRIPTION
     "A single entry in the table represents a single 
      mscVrIpBgpOutdb component."
   INDEX {
      mscVrIndex,
      mscVrIpIndex,
      mscVrIpBgpIndex,
      mscVrIpBgpOutdbPrefixIndex,
      mscVrIpBgpOutdbLengthIndex,
      mscVrIpBgpOutdbPeerIndex }
::= { mscVrIpBgpOutdbRowStatusTable 1 }

MscVrIpBgpOutdbRowStatusEntry ::= SEQUENCE {
   mscVrIpBgpOutdbRowStatus
      RowStatus,
   mscVrIpBgpOutdbComponentName
      DisplayString,
   mscVrIpBgpOutdbStorageType
      StorageType,
   mscVrIpBgpOutdbPrefixIndex
      IpAddress,
   mscVrIpBgpOutdbLengthIndex
      Integer32,
   mscVrIpBgpOutdbPeerIndex
      IpAddress }

mscVrIpBgpOutdbRowStatus OBJECT-TYPE
   SYNTAX     RowStatus 
   ACCESS     read-only
   STATUS     mandatory
   DESCRIPTION
     "This variable is used as the basis for SNMP naming of
      mscVrIpBgpOutdb components.
      These components cannot be added nor deleted."
::= { mscVrIpBgpOutdbRowStatusEntry 1 }

mscVrIpBgpOutdbComponentName OBJECT-TYPE
   SYNTAX     DisplayString 
   ACCESS     read-only
   STATUS     mandatory
   DESCRIPTION
     "This variable provides the component's string name for
      use with the ASCII Console Interface"
::= { mscVrIpBgpOutdbRowStatusEntry 2 }

mscVrIpBgpOutdbStorageType OBJECT-TYPE
   SYNTAX     StorageType 
   ACCESS     read-only
   STATUS     mandatory
   DESCRIPTION
     "This variable represents the storage type value for the
      mscVrIpBgpOutdb tables."
::= { mscVrIpBgpOutdbRowStatusEntry 4 }

mscVrIpBgpOutdbPrefixIndex OBJECT-TYPE
   SYNTAX     IpAddress 
   ACCESS     not-accessible
   STATUS     mandatory
   DESCRIPTION
     "This variable represents an index for the mscVrIpBgpOutdb tables."
::= { mscVrIpBgpOutdbRowStatusEntry 10 }

mscVrIpBgpOutdbLengthIndex OBJECT-TYPE
   SYNTAX     Integer32 (0..32)
   ACCESS     not-accessible
   STATUS     mandatory
   DESCRIPTION
     "This variable represents an index for the mscVrIpBgpOutdb tables."
::= { mscVrIpBgpOutdbRowStatusEntry 11 }

mscVrIpBgpOutdbPeerIndex OBJECT-TYPE
   SYNTAX     IpAddress 
   ACCESS     not-accessible
   STATUS     mandatory
   DESCRIPTION
     "This variable represents an index for the mscVrIpBgpOutdb tables."
::= { mscVrIpBgpOutdbRowStatusEntry 12 }

mscVrIpBgpOutdbOperTable OBJECT-TYPE
   SYNTAX     SEQUENCE OF MscVrIpBgpOutdbOperEntry
   ACCESS     not-accessible
   STATUS     mandatory
   DESCRIPTION
     "*** THIS TABLE CURRENTLY NOT IMPLEMENTED ***

      This group contains all the operational attributes of the OutdbEntry 
      component."
::= { mscVrIpBgpOutdb 10 }

mscVrIpBgpOutdbOperEntry OBJECT-TYPE
   SYNTAX     MscVrIpBgpOutdbOperEntry
   ACCESS     not-accessible
   STATUS     mandatory
   DESCRIPTION
     "An entry in the mscVrIpBgpOutdbOperTable."
   INDEX {
      mscVrIndex,
      mscVrIpIndex,
      mscVrIpBgpIndex,
      mscVrIpBgpOutdbPrefixIndex,
      mscVrIpBgpOutdbLengthIndex,
      mscVrIpBgpOutdbPeerIndex }
::= { mscVrIpBgpOutdbOperTable 1 }

MscVrIpBgpOutdbOperEntry ::= SEQUENCE {
   mscVrIpBgpOutdbOrigin
      INTEGER,
   mscVrIpBgpOutdbNextHop
      IpAddress,
   mscVrIpBgpOutdbLocalPreference
      Unsigned32,
   mscVrIpBgpOutdbMultiExitDiscriminator
      Unsigned32,
   mscVrIpBgpOutdbAtomicAggregate
      INTEGER,
   mscVrIpBgpOutdbAggregatorAs
      Unsigned32,
   mscVrIpBgpOutdbAggregatorAddr
      IpAddress,
   mscVrIpBgpOutdbAsPath
      AsciiString,
   mscVrIpBgpOutdbUnknownAttributes
      AsciiString,
   mscVrIpBgpOutdbCommunityPath
      AsciiString,
   mscVrIpBgpOutdbAsOriginatorId
      IpAddress }

mscVrIpBgpOutdbOrigin OBJECT-TYPE
   SYNTAX     INTEGER  {
                 igp(1),
                 egp(2),
                 incomplete(3) }
   ACCESS     read-only
   STATUS     mandatory
   DESCRIPTION
     "This attribute indicates the ultimate origin of the path information. 
      A value of incomplete means this information is not available."
::= { mscVrIpBgpOutdbOperEntry 4 }

mscVrIpBgpOutdbNextHop OBJECT-TYPE
   SYNTAX     IpAddress 
   ACCESS     read-only
   STATUS     mandatory
   DESCRIPTION
     "This attribute indicates the IP address of the border router that 
      should be used as the next hop for the destination network."
::= { mscVrIpBgpOutdbOperEntry 5 }

mscVrIpBgpOutdbLocalPreference OBJECT-TYPE
   SYNTAX     Unsigned32 (0..4294967295)
   ACCESS     read-only
   STATUS     mandatory
   DESCRIPTION
     "This attribute indicates this Bgp instance's degree of preference for 
      an advertised route. A higher value indicates a more preferred route."
::= { mscVrIpBgpOutdbOperEntry 6 }

mscVrIpBgpOutdbMultiExitDiscriminator OBJECT-TYPE
   SYNTAX     Unsigned32 (0..4294967295)
   ACCESS     read-only
   STATUS     mandatory
   DESCRIPTION
     "This attribute indicates a metric used to discriminate between 
      multiple exit points to the same adjacent autonomous system. A 
      lower value indicates a more preferred route."
::= { mscVrIpBgpOutdbOperEntry 7 }

mscVrIpBgpOutdbAtomicAggregate OBJECT-TYPE
   SYNTAX     INTEGER  {
                 lessSpecificRouteNotSelected(1),
                 lessSpecificRouteSelected(2) }
   ACCESS     read-only
   STATUS     mandatory
   DESCRIPTION
     "This attribute indicates whether or not the local system has selected 
      a less specific route without selecting a more specific route."
::= { mscVrIpBgpOutdbOperEntry 8 }

mscVrIpBgpOutdbAggregatorAs OBJECT-TYPE
   SYNTAX     Unsigned32 (0..65535)
   ACCESS     read-only
   STATUS     mandatory
   DESCRIPTION
     "This attribute indicates the AS number of the last BGP4 speaker 
      that performed route aggregation. A value of zero (0) indicates the 
      absence of this attribute."
::= { mscVrIpBgpOutdbOperEntry 9 }

mscVrIpBgpOutdbAggregatorAddr OBJECT-TYPE
   SYNTAX     IpAddress 
   ACCESS     read-only
   STATUS     mandatory
   DESCRIPTION
     "This attribute indicates the IP address of the last BGP4 speaker that 
      performed route aggregation. A value of 0.0.0.0 indicates the 
      absence of this attribute."
::= { mscVrIpBgpOutdbOperEntry 10 }

mscVrIpBgpOutdbAsPath OBJECT-TYPE
   SYNTAX     AsciiString (SIZE (2..255))
   ACCESS     read-only
   STATUS     mandatory
   DESCRIPTION
     "This attribute indicates the sequence of AS path segments. The AS 
      Path Attribute lists the ASs in reverse traversal order."
::= { mscVrIpBgpOutdbOperEntry 11 }

mscVrIpBgpOutdbUnknownAttributes OBJECT-TYPE
   SYNTAX     AsciiString (SIZE (0..255))
   ACCESS     read-only
   STATUS     mandatory
   DESCRIPTION
     "This attribute indicates all the path attributes not understood by this 
      Bgp component instance."
::= { mscVrIpBgpOutdbOperEntry 12 }

mscVrIpBgpOutdbCommunityPath OBJECT-TYPE
   SYNTAX     AsciiString (SIZE (0..255))
   ACCESS     read-only
   STATUS     mandatory
   DESCRIPTION
     "This attribute indicates the Community path attribute."
::= { mscVrIpBgpOutdbOperEntry 13 }

mscVrIpBgpOutdbAsOriginatorId OBJECT-TYPE
   SYNTAX     IpAddress 
   ACCESS     read-only
   STATUS     mandatory
   DESCRIPTION
     "This attribute is associated with the Route Reflector. It indicates the 
      router-id of the originator of a route in the local AS. When the 
      Route Reflector distributes a learned IBGP route to other IBGP 
      speakers, the value of this attribute in the learned route is used if 
      one is present; othewise, the Route Reflector's router-id is used. A 
      value of 0.0.0.0 indicates this Bgp instance is not a Route Reflector."
::= { mscVrIpBgpOutdbOperEntry 14 }

mscVrIpBgpOutdbRrClusterListTable OBJECT-TYPE
   SYNTAX     SEQUENCE OF MscVrIpBgpOutdbRrClusterListEntry
   ACCESS     not-accessible
   STATUS     mandatory
   DESCRIPTION
     "*** THIS TABLE CURRENTLY NOT IMPLEMENTED ***

      This attribute indicates a sequence of cluster-ids that the route has 
      traversed. When the Route Reflector redistributes a learned IBGP to 
      other IBGP speakers, the cluster id of this Route Reflector is 
      appended to the cluster list of the learned IBGP route. If this Bgp 
      instance is not a Route Reflector, this attribute is blank."
::= { mscVrIpBgpOutdb 799 }

mscVrIpBgpOutdbRrClusterListEntry OBJECT-TYPE
   SYNTAX     MscVrIpBgpOutdbRrClusterListEntry
   ACCESS     not-accessible
   STATUS     mandatory
   DESCRIPTION
     "An entry in the mscVrIpBgpOutdbRrClusterListTable."
   INDEX {
      mscVrIndex,
      mscVrIpIndex,
      mscVrIpBgpIndex,
      mscVrIpBgpOutdbPrefixIndex,
      mscVrIpBgpOutdbLengthIndex,
      mscVrIpBgpOutdbPeerIndex,
      mscVrIpBgpOutdbRrClusterListValue }
::= { mscVrIpBgpOutdbRrClusterListTable 1 }

MscVrIpBgpOutdbRrClusterListEntry ::= SEQUENCE {
   mscVrIpBgpOutdbRrClusterListValue
      IpAddress }

mscVrIpBgpOutdbRrClusterListValue OBJECT-TYPE
   SYNTAX     IpAddress 
   ACCESS     read-only
   STATUS     mandatory
   DESCRIPTION
     "This variable represents both the value and the index for the
      mscVrIpBgpOutdbRrClusterListTable."
::= { mscVrIpBgpOutdbRrClusterListEntry 1 }




-- 
-- Version and Compliance statements
-- 



-- Object-Group Statement:
-- A list of all current accessible leaf objects.

-- OBJECTS { mscVrIpBgpLocaldbAsPath,
--           mscVrIpBgpPeerBgpIdentifier,
--           mscVrIpBgpLocaldbRowStatus,
--           mscVrIpBgpIndbAggregatorAddr,
--           mscVrIpBgpExportNetPrefix,
--           mscVrIpBgpOutdbAggregatorAddr,
--           mscVrIpBgpExportNetLength,
--           mscVrIpBgpOutdbOrigin,
--           mscVrIpBgpLocaldbAsOriginatorId,
--           mscVrIpBgpLocaldbMultiExitDiscriminator,
--           mscVrIpBgpOutdbMultiExitDiscriminator,
--           mscVrIpBgpOperationalState,
--           mscVrIpBgpOutdbNextHop,
--           mscVrIpBgpInMsgs,
--           mscVrIpBgpIndbRrClusterListValue,
--           mscVrIpBgpPeerOutErrorMsgs,
--           mscVrIpBgpImportNetComponentName,
--           mscVrIpBgpAggregateNetRipInterface,
--           mscVrIpBgpOutDiscards,
--           mscVrIpBgpAggregateNetComponentName,
--           mscVrIpBgpPeerInUpdates,
--           mscVrIpBgpExportRowStatus,
--           mscVrIpBgpExportAdvertiseStatus,
--           mscVrIpBgpOutdbComponentName,
--           mscVrIpBgpImportOriginAs,
--           mscVrIpBgpLocaldbAggregatorAddr,
--           mscVrIpBgpImportCommunityExpression,
--           mscVrIpBgpOutdbCommunityPath,
--           mscVrIpBgpIndbUnknownAttributes,
--           mscVrIpBgpOutdbRrClusterListValue,
--           mscVrIpBgpLocaldbRrClusterListValue,
--           mscVrIpBgpImportPeerIpAddress,
--           mscVrIpBgpExportPeerAs,
--           mscVrIpBgpRouteThrottleInter,
--           mscVrIpBgpOutdbAsOriginatorId,
--           mscVrIpBgpPeerVersionNegotiated,
--           mscVrIpBgpExportRipNeighbor,
--           mscVrIpBgpPeerComponentName,
--           mscVrIpBgpIndbOrigin,
--           mscVrIpBgpExportMultiExitDisc,
--           mscVrIpBgpImportComponentName,
--           mscVrIpBgpStorageType,
--           mscVrIpBgpPeerOutMsgs,
--           mscVrIpBgpIndbNextHop,
--           mscVrIpBgpLocaldbComponentName,
--           mscVrIpBgpOutErrorMsgs,
--           mscVrIpBgpExportInsertDummyAs,
--           mscVrIpBgpBgpIdentifier,
--           mscVrIpBgpPeerLocalAddressConfigured,
--           mscVrIpBgpAggregateNetEgpAsId,
--           mscVrIpBgpExportNetComponentName,
--           mscVrIpBgpRouteReflector,
--           mscVrIpBgpAsStorageType,
--           mscVrIpBgpLocalAs,
--           mscVrIpBgpImportExpressPreference,
--           mscVrIpBgpIndbCommunityPath,
--           mscVrIpBgpPeerRemovePrivateAs,
--           mscVrIpBgpIndbComponentName,
--           mscVrIpBgpPeerInErrors,
--           mscVrIpBgpLocaldbAggregatorAs,
--           mscVrIpBgpImportUsageFlag,
--           mscVrIpBgpDefaultLocalPreference,
--           mscVrIpBgpExportSendCommunity,
--           mscVrIpBgpImportNetStorageType,
--           mscVrIpBgpLocaldbCommunityPath,
--           mscVrIpBgpIndbCalcLocalPref,
--           mscVrIpBgpExportPeerIpAddress,
--           mscVrIpBgpAsWeight,
--           mscVrIpBgpOutdbUnknownAttributes,
--           mscVrIpBgpIndbAggregatorAs,
--           mscVrIpBgpIndbMultiExitDiscriminator,
--           mscVrIpBgpImportNetLength,
--           mscVrIpBgpExportCommunityExpression,
--           mscVrIpBgpPeerOperationalState,
--           mscVrIpBgpPeerInMsgs,
--           mscVrIpBgpImportAsPathExpression,
--           mscVrIpBgpSnmpAdminStatus,
--           mscVrIpBgpInErrorMsgs,
--           mscVrIpBgpPeerInRoutes,
--           mscVrIpBgpImportLocalPreference,
--           mscVrIpBgpLocaldbOrigin,
--           mscVrIpBgpExportRipInterface,
--           mscVrIpBgpComponentName,
--           mscVrIpBgpImportNetRowStatus,
--           mscVrIpBgpPeerStorageType,
--           mscVrIpBgpPeerHoldTimeConfigured,
--           mscVrIpBgpLocaldbUnknownAttributes,
--           mscVrIpBgpOutMsgs,
--           mscVrIpBgpLocaldbNextHop,
--           mscVrIpBgpLocaldbLocalPreference,
--           mscVrIpBgpOutdbLocalPreference,
--           mscVrIpBgpImportNetPrefix,
--           mscVrIpBgpOutdbRowStatus,
--           mscVrIpBgpIndbAsPath,
--           mscVrIpBgpRouteThrottleLimit,
--           mscVrIpBgpPeerIsRouteReflectorClient,
--           mscVrIpBgpPeerConnectionState,
--           mscVrIpBgpAggregateNetOspfTag,
--           mscVrIpBgpIndbLocalPreference,
--           mscVrIpBgpIndbSize,
--           mscVrIpBgpPeerAdminState,
--           mscVrIpBgpPeerConnectRetryTime,
--           mscVrIpBgpAggregateNetProtocol,
--           mscVrIpBgpAggregateNetStorageType,
--           mscVrIpBgpAsComponentName,
--           mscVrIpBgpInErrors,
--           mscVrIpBgpImportStorageType,
--           mscVrIpBgpAggregateNetBgpAsId,
--           mscVrIpBgpPeerRowStatus,
--           mscVrIpBgpDefaultMultiExitDisc,
--           mscVrIpBgpImportRowStatus,
--           mscVrIpBgpIndbAtomicAggregate,
--           mscVrIpBgpPeerHoldTimeNegotiated,
--           mscVrIpBgpPeerInUpdateElapsedTime,
--           mscVrIpBgpImportOriginProtocol,
--           mscVrIpBgpExportEgpAsId,
--           mscVrIpBgpPeerMinRouteAdvTime,
--           mscVrIpBgpTableVersion,
--           mscVrIpBgpPeerConnectionEstablishedTime,
--           mscVrIpBgpImportAppendCommunity,
--           mscVrIpBgpPeerRemotePort,
--           mscVrIpBgpPeerUsageState,
--           mscVrIpBgpPeerPeerAs,
--           mscVrIpBgpPeerConnectionEstablishedTransitions,
--           mscVrIpBgpImportPreferredOver,
--           mscVrIpBgpImportPeerAs,
--           mscVrIpBgpUsageState,
--           mscVrIpBgpSnmpOperStatus,
--           mscVrIpBgpIndbRowStatus,
--           mscVrIpBgpAggregateStorageType,
--           mscVrIpBgpPeerDefaultInAggMed,
--           mscVrIpBgpPeerInErrorMsgs,
--           mscVrIpBgpRouteReflectorCluster,
--           mscVrIpBgpAggregateNetPrefix,
--           mscVrIpBgpExportExpressPreference,
--           mscVrIpBgpExportSendMultiExitDiscToEbgp,
--           mscVrIpBgpOutdbAggregatorAs,
--           mscVrIpBgpIndbStorageType,
--           mscVrIpBgpOutdbAtomicAggregate,
--           mscVrIpBgpPeerOutDiscards,
--           mscVrIpBgpRedistributeIgpToIbgp,
--           mscVrIpBgpExportNetStorageType,
--           mscVrIpBgpAggregateComponentName,
--           mscVrIpBgpAdminState,
--           mscVrIpBgpExportComponentName,
--           mscVrIpBgpPeerLastError,
--           mscVrIpBgpAggregateNetLength,
--           mscVrIpBgpAggregateRowStatus,
--           mscVrIpBgpLocaldbStorageType,
--           mscVrIpBgpIndbAsOriginatorId,
--           mscVrIpBgpRowStatus,
--           mscVrIpBgpPeerKeepAliveNegotiated,
--           mscVrIpBgpPeerLocalPort,
--           mscVrIpBgpAsRowStatus,
--           mscVrIpBgpExportBgpAsId,
--           mscVrIpBgpAggregateNetRowStatus,
--           mscVrIpBgpPeerMinAsOrigTime,
--           mscVrIpBgpPeerLocalAddressUsed,
--           mscVrIpBgpExportAsPathExpression,
--           mscVrIpBgpOutdbAsPath,
--           mscVrIpBgpPeerOutUpdates,
--           mscVrIpBgpAggregateNetAction,
--           mscVrIpBgpIndbInLocaldb,
--           mscVrIpBgpExportOspfTag,
--           mscVrIpBgpPeerKeepAliveConfigured,
--           mscVrIpBgpLocaldbAtomicAggregate,
--           mscVrIpBgpExportNetRowStatus,
--           mscVrIpBgpExportProtocol,
--           mscVrIpBgpExportStorageType,
--           mscVrIpBgpOutdbStorageType }
-- STATUS  mandatory
-- DESCRIPTION
--   "A list of all current accessible leaf objects."

bgpGroup OBJECT IDENTIFIER ::= { bgpMIB 1 }
bgpGroupCA OBJECT IDENTIFIER ::= { bgpGroup 1 }
bgpGroupCA02 OBJECT IDENTIFIER ::= { bgpGroupCA 3 }
bgpGroupCA02A OBJECT IDENTIFIER ::= { bgpGroupCA02 2 }



-- Agent-Capabilities Statement:

-- PRODUCT-RELEASE "MscPassport Release 1.2 Bgp."
-- STATUS          mandatory
-- DESCRIPTION     "Carrier Passport Bgp MIB: MIB Version CA02A,
--                  Software Version CA02S9C."
-- SUPPORTS        Nortel-MsCarrier-MscPassport-BgpMIB
--    INCLUDES     { bgpGroupCA02A }

bgpCapabilities OBJECT IDENTIFIER ::= { bgpMIB 3 }
bgpCapabilitiesCA OBJECT IDENTIFIER ::= { bgpCapabilities 1 }
bgpCapabilitiesCA02 OBJECT IDENTIFIER ::= { bgpCapabilitiesCA 3 }
bgpCapabilitiesCA02A OBJECT IDENTIFIER ::= { bgpCapabilitiesCA02 2 }





END
