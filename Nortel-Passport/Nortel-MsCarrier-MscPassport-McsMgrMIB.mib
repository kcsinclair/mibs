Nortel-MsCarrier-MscPassport-McsMgrMIB
DEFINITIONS ::= BEGIN



IMPORTS

      OBJECT-TYPE
   FROM RFC-1212

      mscPassportMIBs,
      mscComponents
   FROM Nortel-MsCarrier-MscPassport-UsefulDefinitionsMIB

      RowPointer,
      DisplayString,
      StorageType,
      RowStatus,
      Unsigned32
   FROM Nortel-MsCarrier-MscPassport-StandardTextualConventionsMIB

      AsciiString,
      NonReplicated,
      Link
   FROM Nortel-MsCarrier-MscPassport-TextualConventionsMIB;




-- LAST-UPDATED   "9909010000Z"
-- ORGANIZATION   "Nortel Networks"
-- CONTACT-INFO   "
--         Nortel Carrier Data Network Management
--         
--         Postal:       P.O. Box 3511, Station C 
--                       Ottawa, Ontario 
--                       Canada  K1Y 4H7
--         
--         via the WEB:  http://www.nortelnetworks.com  
--                       select 'Contact Us' from the menu
--          
--         via phone:    1-800-4NORTEL"
-- DESCRIPTION
--    "The module describing the Nortel MsCarrier MscPassport
--     McsMgr Enterprise MIB."

mcsMgrMIB OBJECT IDENTIFIER ::= { mscPassportMIBs 124 }










-- McsManager
-- There is at most one McsManager per module. The McsManager is 
-- required for FRF5 PVC and DPRS MCS functionality. The 
-- McsManager can run on one of a number of LPs. The LP of the 
-- active McsManager can be determined by looking at the currentLp 
-- operational attribute.

mscMcsMgr OBJECT IDENTIFIER ::= { mscComponents 122 }



mscMcsMgrRowStatusTable OBJECT-TYPE
   SYNTAX     SEQUENCE OF MscMcsMgrRowStatusEntry
   ACCESS     not-accessible
   STATUS     mandatory
   DESCRIPTION
     "This entry controls the addition and deletion of 
      mscMcsMgr components."
::= { mscMcsMgr 1 }

mscMcsMgrRowStatusEntry OBJECT-TYPE
   SYNTAX     MscMcsMgrRowStatusEntry
   ACCESS     not-accessible
   STATUS     mandatory
   DESCRIPTION
     "A single entry in the table represents a single 
      mscMcsMgr component."
   INDEX {
      mscMcsMgrIndex }
::= { mscMcsMgrRowStatusTable 1 }

MscMcsMgrRowStatusEntry ::= SEQUENCE {
   mscMcsMgrRowStatus
      RowStatus,
   mscMcsMgrComponentName
      DisplayString,
   mscMcsMgrStorageType
      StorageType,
   mscMcsMgrIndex
      NonReplicated }

mscMcsMgrRowStatus OBJECT-TYPE
   SYNTAX     RowStatus 
   ACCESS     read-write
   STATUS     mandatory
   DESCRIPTION
     "This variable is used as the basis for SNMP naming of
      mscMcsMgr components.
      These components can be added and deleted."
::= { mscMcsMgrRowStatusEntry 1 }

mscMcsMgrComponentName OBJECT-TYPE
   SYNTAX     DisplayString 
   ACCESS     read-only
   STATUS     mandatory
   DESCRIPTION
     "This variable provides the component's string name for
      use with the ASCII Console Interface"
::= { mscMcsMgrRowStatusEntry 2 }

mscMcsMgrStorageType OBJECT-TYPE
   SYNTAX     StorageType 
   ACCESS     read-only
   STATUS     mandatory
   DESCRIPTION
     "This variable represents the storage type value for the
      mscMcsMgr tables."
::= { mscMcsMgrRowStatusEntry 4 }

mscMcsMgrIndex OBJECT-TYPE
   SYNTAX     NonReplicated 
   ACCESS     not-accessible
   STATUS     mandatory
   DESCRIPTION
     "This variable represents the index for the mscMcsMgr tables."
::= { mscMcsMgrRowStatusEntry 10 }

mscMcsMgrProvTable OBJECT-TYPE
   SYNTAX     SEQUENCE OF MscMcsMgrProvEntry
   ACCESS     not-accessible
   STATUS     mandatory
   DESCRIPTION
     "This group contains the provisionable attributes of the 
      McsManager."
::= { mscMcsMgr 10 }

mscMcsMgrProvEntry OBJECT-TYPE
   SYNTAX     MscMcsMgrProvEntry
   ACCESS     not-accessible
   STATUS     mandatory
   DESCRIPTION
     "An entry in the mscMcsMgrProvTable."
   INDEX {
      mscMcsMgrIndex }
::= { mscMcsMgrProvTable 1 }

MscMcsMgrProvEntry ::= SEQUENCE {
   mscMcsMgrMaxEps
      INTEGER,
   mscMcsMgrEpAlarmThreshold
      INTEGER,
   mscMcsMgrOverrideNsapAddress
      AsciiString,
   mscMcsMgrLogicalProcessor
      Link,
   mscMcsMgrSecurity
      INTEGER }

mscMcsMgrMaxEps OBJECT-TYPE
   SYNTAX     INTEGER (1..16384)
   ACCESS     read-write
   STATUS     mandatory
   DESCRIPTION
     "This attribute specifies the number of end points that will be 
      allowed on the module.This includes end points originating from 
      and terminating on this module. When this limit is reached calls 
      requiring the creation of an end point are rejected. The current 
      number of EPs is indicated by the currentEps attribute."
   DEFVAL     { 512 }
::= { mscMcsMgrProvEntry 1 }

mscMcsMgrEpAlarmThreshold OBJECT-TYPE
   SYNTAX     INTEGER (1..16384)
   ACCESS     read-write
   STATUS     mandatory
   DESCRIPTION
     "This attribute specifies the maximum number of end points that can 
      exist before an alarm is raised. When currentEps exceeds this value 
      an alarm is generated. The alarm is cleared when currentEps falls 
      below this value."
   DEFVAL     { 128 }
::= { mscMcsMgrProvEntry 2 }

mscMcsMgrOverrideNsapAddress OBJECT-TYPE
   SYNTAX     AsciiString (SIZE (0..44))
   ACCESS     read-write
   STATUS     mandatory
   DESCRIPTION
     "This attribute specifies the NSAP address to use as the address of 
      the McsManager. If this attribute is left empty the default 
      McsManager NSAP address is used. The nsapAddress attribute 
      indicates the NSAP address used by the McsManager. 
      The default NSAP address for the McsManager takes the form:
      <26 byte module prefix>0020480d100100"
   DEFVAL     { ''H }  -- ""
::= { mscMcsMgrProvEntry 3 }

mscMcsMgrLogicalProcessor OBJECT-TYPE
   SYNTAX     Link 
   ACCESS     read-write
   STATUS     obsolete
   DESCRIPTION
     "This attribute specifies the LogicalProcessor on which the 
      DataShuntManager will be running."
::= { mscMcsMgrProvEntry 4 }

mscMcsMgrSecurity OBJECT-TYPE
   SYNTAX     INTEGER  {
                 off(0),
                 on(1) }
   ACCESS     read-write
   STATUS     mandatory
   DESCRIPTION
     "This attribute enables or disables security for the McsManager. 
      In the case of DPRS MCS Switched Paths, if security is set to on 
      this node must have a DprsMcsEpGroup with the nsapAddress of 
      the Addr subcomponent set to the same value as the node 
      originating the call setup for the call to be accepted.If this attribute 
      is set to off this node will accept DPRS MCS setup requests from 
      any other node in the network.
      This attribute has no effect on the setup of FRF5 switched paths 
      since an originating and terminating EP are required to establish an 
      FRF5 switched path."
   DEFVAL     { off }
::= { mscMcsMgrProvEntry 5 }

mscMcsMgrStateTable OBJECT-TYPE
   SYNTAX     SEQUENCE OF MscMcsMgrStateEntry
   ACCESS     not-accessible
   STATUS     mandatory
   DESCRIPTION
     "This group contains the three OSI State attributes and the six OSI 
      Status attributes. The descriptions generically indicate what each 
      attribute implies about the component. Note that not all the values 
      and state combinations described here are supported by every 
      component which uses this group. For component-specific 
      information and the valid state combinations, refer to NTP 241-
      7001-150, Passport Operations and Maintenance Guide."
::= { mscMcsMgr 11 }

mscMcsMgrStateEntry OBJECT-TYPE
   SYNTAX     MscMcsMgrStateEntry
   ACCESS     not-accessible
   STATUS     mandatory
   DESCRIPTION
     "An entry in the mscMcsMgrStateTable."
   INDEX {
      mscMcsMgrIndex }
::= { mscMcsMgrStateTable 1 }

MscMcsMgrStateEntry ::= SEQUENCE {
   mscMcsMgrAdminState
      INTEGER,
   mscMcsMgrOperationalState
      INTEGER,
   mscMcsMgrUsageState
      INTEGER,
   mscMcsMgrAvailabilityStatus
      OCTET STRING,
   mscMcsMgrProceduralStatus
      OCTET STRING,
   mscMcsMgrControlStatus
      OCTET STRING,
   mscMcsMgrAlarmStatus
      OCTET STRING,
   mscMcsMgrStandbyStatus
      INTEGER,
   mscMcsMgrUnknownStatus
      INTEGER }

mscMcsMgrAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component.
      
      The OSI Status attributes, if supported by the component, may 
      provide more details, qualifying the state of the component."
   DEFVAL     { unlocked }
::= { mscMcsMgrStateEntry 1 }

mscMcsMgrOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle.
      
      The OSI Status attributes, if supported by the component, may 
      provide more details, qualifying the state of the component."
   DEFVAL     { disabled }
::= { mscMcsMgrStateEntry 2 }

mscMcsMgrUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time.
      
      The OSI Status attributes, if supported by the component, may 
      provide more details, qualifying the state of the component."
   DEFVAL     { idle }
::= { mscMcsMgrStateEntry 3 }

mscMcsMgrAvailabilityStatus OBJECT-TYPE
   SYNTAX     OCTET STRING (SIZE (2))
   ACCESS     read-only
   STATUS     mandatory
   DESCRIPTION
     "If supported by the component, this attribute indicates the OSI 
      Availability status of the component. Note that, even though it is 
      defined as a multi-valued set, at most one value is shown to the user.
      
      When no values are in the set, this indicates that either the attribute 
      is not supported or that none of the status conditions described 
      below are present.
      
      The value inTest indicates that the resource is undergoing a test 
      procedure. If adminState is locked or shuttingDown, the normal 
      users are precluded from using the resource and controlStatus is 
      reservedForTest. Tests that do not exclude additional users can be 
      present in any operational or administrative state but the 
      reservedForTest condition should not be present.
      
      The value failed indicates that the component has an internal fault 
      that prevents it from operating. The operationalState is disabled.
      
      The value dependency indicates that the component cannot operate 
      because some other resource on which it depends is unavailable. 
      The operationalState is disabled.
      
      The value powerOff indicates the resource requires power to be 
      applied and it is not powered on. The operationalState is disabled.
      
      The value offLine indicates the resource requires a routine 
      operation (either manual, automatic, or both) to be performed to 
      place it on-line and make it available for use. The operationalState 
      is disabled.
      
      The value offDuty indicates the resource is inactive in accordance 
      with a predetermined time schedule. In the absence of other 
      disabling conditions, the operationalState is enabled or disabled.
      
      The value degraded indicates the service provided by the 
      component is degraded in some way, such as in speed or operating 
      capacity. However, the resource remains available for service. The 
      operationalState is enabled.
      
      The value notInstalled indicates the resource is not present. The 
      operationalState is disabled.
      
      The value logFull is not used.

      Description of bits:
      inTest(0)
      failed(1)
      powerOff(2)
      offLine(3)
      offDuty(4)
      dependency(5)
      degraded(6)
      notInstalled(7)
      logFull(8)"
::= { mscMcsMgrStateEntry 4 }

mscMcsMgrProceduralStatus OBJECT-TYPE
   SYNTAX     OCTET STRING (SIZE (1))
   ACCESS     read-only
   STATUS     mandatory
   DESCRIPTION
     "If supported by the component, this attribute indicates the OSI 
      Procedural status of the component. Note that, even though it is 
      defined as a multi-valued set, at most one value is shown to the user.
      
      When no values are in the set, this indicates that either the attribute 
      is not supported or that none of the status conditions described 
      below are present.
      
      The value initializationRequired indicates (for a resource which 
      doesn't initialize autonomously) that initialization is required before 
      it can perform its normal functions, and this procedure has not been 
      initiated. The operationalState is disabled.
      
      The value notInitialized indicates (for a resource which does 
      initialize autonomously) that initialization is required before it can 
      perform its normal functions, and this procedure has not been 
      initiated. The operationalState may be enabled or disabled.
      
      The value initializing indicates that initialization has been initiated 
      but is not yet complete. The operationalState may be enabled or 
      disabled.
      
      The value reporting indicates the resource has completed some 
      processing operation and is notifying the results. The 
      operationalState is enabled.
      
      The value terminating indicates the component is in a termination 
      phase. If the resource doesn't reinitialize autonomously, 
      operationalState is disabled; otherwise it is enabled or disabled.

      Description of bits:
      initializationRequired(0)
      notInitialized(1)
      initializing(2)
      reporting(3)
      terminating(4)"
::= { mscMcsMgrStateEntry 5 }

mscMcsMgrControlStatus OBJECT-TYPE
   SYNTAX     OCTET STRING (SIZE (1))
   ACCESS     read-only
   STATUS     mandatory
   DESCRIPTION
     "If supported by the component, this attribute indicates the OSI 
      Control status of the component. Note that, even though it is defined 
      as a multi-valued set, at most one value is shown to the user.
      
      When no values are in the set, this indicates that either the attribute 
      is not supported or that none of the status conditions described 
      below are present.
      
      The value subjectToTest indicates the resource is available but tests 
      may be conducted simultaneously at unpredictable times, which 
      may cause it to exhibit unusual characteristics.
      
      The value partOfServicesLocked indicates that part of the service is 
      restricted from users of a resource. The adminState is unlocked.
      
      The value reservedForTest indicates that the component is 
      administratively unavailable because it is undergoing a test 
      procedure. The adminState is locked.
      
      The value suspended indicates that the service has been 
      administratively suspended.

      Description of bits:
      subjectToTest(0)
      partOfServicesLocked(1)
      reservedForTest(2)
      suspended(3)"
::= { mscMcsMgrStateEntry 6 }

mscMcsMgrAlarmStatus OBJECT-TYPE
   SYNTAX     OCTET STRING (SIZE (1))
   ACCESS     read-only
   STATUS     mandatory
   DESCRIPTION
     "If supported by the component, this attribute indicates the OSI 
      Alarm status of the component. Note that, even though it is defined 
      as a multi-valued set, at most one value is shown to the user.
      
      When no values are in the set, this indicates that either the attribute 
      is not supported or that none of the status conditions described 
      below are present.
      
      The value underRepair indicates the component is currently being 
      repaired. The operationalState is enabled or disabled.
      
      The value critical indicates one or more critical alarms are 
      outstanding against the component. Other, less severe, alarms may 
      also be outstanding. The operationalState is enabled or disabled.
      
      The value major indicates one or more major alarms are 
      outstanding against the component. Other, less severe, alarms may 
      also be outstanding. The operationalState is enabled or disabled.
      
      The value minor indicates one or more minor alarms are 
      outstanding against the component. Other, less severe, alarms may 
      also be outstanding. The operationalState is enabled or disabled.
      
      The value alarmOutstanding generically indicates that an alarm of 
      some severity is outstanding against the component.

      Description of bits:
      underRepair(0)
      critical(1)
      major(2)
      minor(3)
      alarmOutstanding(4)"
::= { mscMcsMgrStateEntry 7 }

mscMcsMgrStandbyStatus OBJECT-TYPE
   SYNTAX     INTEGER  {
                 hotStandby(0),
                 coldStandby(1),
                 providingService(2),
                 notSet(15) }
   ACCESS     read-only
   STATUS     mandatory
   DESCRIPTION
     "If supported by the component, this attribute indicates the OSI 
      Standby status of the component.
      
      The value notSet indicates that either the attribute is not supported 
      or that none of the status conditions described below are present. 
      Note that this is a non-standard value, used because the original 
      specification indicated this attribute was set-valued and thus, did not 
      provide a value to indicate that none of the other three are 
      applicable.
      
      The value hotStandby indicates that the resource is not providing 
      service but will be immediately able to take over the role of the 
      resource to be backed up, without initialization activity, and 
      containing the same information as the resource to be backed up.
      
      The value coldStandby indicates the resource is a backup for 
      another resource but will not be immediately able to take over the 
      role of the backed up resource and will require some initialization 
      activity.
      
      The value providingService indicates that this component, as a 
      backup resource, is currently backing up another resource."
   DEFVAL     { notSet }
::= { mscMcsMgrStateEntry 8 }

mscMcsMgrUnknownStatus OBJECT-TYPE
   SYNTAX     INTEGER  {
                 false(0),
                 true(1) }
   ACCESS     read-only
   STATUS     mandatory
   DESCRIPTION
     "This attribute indicates the OSI Unknown status of the component.
      
      The value false indicates that all of the other OSI State and Status 
      attribute values can be considered accurate.
      
      The value true indicates that the actual state of the component is not 
      known for sure."
   DEFVAL     { false }
::= { mscMcsMgrStateEntry 9 }

mscMcsMgrOperTable OBJECT-TYPE
   SYNTAX     SEQUENCE OF MscMcsMgrOperEntry
   ACCESS     not-accessible
   STATUS     mandatory
   DESCRIPTION
     "This group contains the operational attributes of the McsManager 
      component."
::= { mscMcsMgr 12 }

mscMcsMgrOperEntry OBJECT-TYPE
   SYNTAX     MscMcsMgrOperEntry
   ACCESS     not-accessible
   STATUS     mandatory
   DESCRIPTION
     "An entry in the mscMcsMgrOperTable."
   INDEX {
      mscMcsMgrIndex }
::= { mscMcsMgrOperTable 1 }

MscMcsMgrOperEntry ::= SEQUENCE {
   mscMcsMgrCurrentLp
      RowPointer,
   mscMcsMgrCurrentEps
      Unsigned32,
   mscMcsMgrNsapAddress
      AsciiString }

mscMcsMgrCurrentLp OBJECT-TYPE
   SYNTAX     RowPointer 
   ACCESS     read-only
   STATUS     mandatory
   DESCRIPTION
     "This attribute indicates the current LP on which the McsManager 
      resides. If this attribute is blank then no McsManager is available."
::= { mscMcsMgrOperEntry 1 }

mscMcsMgrCurrentEps OBJECT-TYPE
   SYNTAX     Unsigned32 (0..16384)
   ACCESS     read-only
   STATUS     mandatory
   DESCRIPTION
     "The indicates the number of EPs both originating and terminating 
      on this module."
::= { mscMcsMgrOperEntry 3 }

mscMcsMgrNsapAddress OBJECT-TYPE
   SYNTAX     AsciiString (SIZE (0..44))
   ACCESS     read-only
   STATUS     mandatory
   DESCRIPTION
     "This attribute indicates the NSAP address of the McsManager on 
      this node. The value of this attributed depends on how the 
      overrideNsapAddress attribute is set. All DPRS MCS and FRF5 
      switched paths that are to terminate on this node must specify this 
      NSAP address as their destination."
::= { mscMcsMgrOperEntry 4 }

mscMcsMgrCanLpsTable OBJECT-TYPE
   SYNTAX     SEQUENCE OF MscMcsMgrCanLpsEntry
   ACCESS     not-accessible
   STATUS     mandatory
   DESCRIPTION
     "This attribute indicates the set of LPs capable of running the 
      McsManager. If this attribute is blank then there are no candidate 
      LPs."
::= { mscMcsMgr 418 }

mscMcsMgrCanLpsEntry OBJECT-TYPE
   SYNTAX     MscMcsMgrCanLpsEntry
   ACCESS     not-accessible
   STATUS     mandatory
   DESCRIPTION
     "An entry in the mscMcsMgrCanLpsTable."
   INDEX {
      mscMcsMgrIndex,
      mscMcsMgrCanLpsValue }
::= { mscMcsMgrCanLpsTable 1 }

MscMcsMgrCanLpsEntry ::= SEQUENCE {
   mscMcsMgrCanLpsValue
      RowPointer }

mscMcsMgrCanLpsValue OBJECT-TYPE
   SYNTAX     RowPointer 
   ACCESS     read-only
   STATUS     mandatory
   DESCRIPTION
     "This variable represents both the value and the index for the
      mscMcsMgrCanLpsTable."
::= { mscMcsMgrCanLpsEntry 1 }




-- 
-- Version and Compliance statements
-- 



-- Object-Group Statement:
-- A list of all current accessible leaf objects.

-- OBJECTS { mscMcsMgrComponentName,
--           mscMcsMgrSecurity,
--           mscMcsMgrUnknownStatus,
--           mscMcsMgrStandbyStatus,
--           mscMcsMgrCanLpsValue,
--           mscMcsMgrCurrentLp,
--           mscMcsMgrStorageType,
--           mscMcsMgrRowStatus,
--           mscMcsMgrCurrentEps,
--           mscMcsMgrProceduralStatus,
--           mscMcsMgrOperationalState,
--           mscMcsMgrMaxEps,
--           mscMcsMgrNsapAddress,
--           mscMcsMgrOverrideNsapAddress,
--           mscMcsMgrAvailabilityStatus,
--           mscMcsMgrAlarmStatus,
--           mscMcsMgrUsageState,
--           mscMcsMgrControlStatus,
--           mscMcsMgrAdminState,
--           mscMcsMgrEpAlarmThreshold }
-- STATUS  mandatory
-- DESCRIPTION
--   "A list of all current accessible leaf objects."

mcsMgrGroup OBJECT IDENTIFIER ::= { mcsMgrMIB 1 }
mcsMgrGroupCA OBJECT IDENTIFIER ::= { mcsMgrGroup 1 }
mcsMgrGroupCA02 OBJECT IDENTIFIER ::= { mcsMgrGroupCA 3 }
mcsMgrGroupCA02A OBJECT IDENTIFIER ::= { mcsMgrGroupCA02 2 }



-- Agent-Capabilities Statement:

-- PRODUCT-RELEASE "MscPassport Release 1.2 McsMgr."
-- STATUS          mandatory
-- DESCRIPTION     "Carrier Passport McsMgr MIB: MIB Version CA02A,
--                  Software Version CA02S9C."
-- SUPPORTS        Nortel-MsCarrier-MscPassport-McsMgrMIB
--    INCLUDES     { mcsMgrGroupCA02A }

mcsMgrCapabilities OBJECT IDENTIFIER ::= { mcsMgrMIB 3 }
mcsMgrCapabilitiesCA OBJECT IDENTIFIER ::= { mcsMgrCapabilities 1 }
mcsMgrCapabilitiesCA02 OBJECT IDENTIFIER ::= { mcsMgrCapabilitiesCA 3 }
mcsMgrCapabilitiesCA02A OBJECT IDENTIFIER ::= { mcsMgrCapabilitiesCA02 2 }





END
