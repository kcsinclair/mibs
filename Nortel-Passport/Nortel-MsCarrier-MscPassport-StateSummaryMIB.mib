Nortel-MsCarrier-MscPassport-StateSummaryMIB
DEFINITIONS ::= BEGIN

IMPORTS

      TimeTicks
   FROM RFC1155-SMI

      MODULE-IDENTITY, OBJECT-TYPE, Gauge32
   FROM SNMPv2-SMI

      DisplayString
   FROM SNMPv2-TC

      mscComponents, mscPassportMIBs
   FROM Nortel-MsCarrier-MscPassport-UsefulDefinitionsMIB;

stateSummaryMIB MODULE-IDENTITY
  LAST-UPDATED "9907300000Z"
  ORGANIZATION "Nortel Networks"
  CONTACT-INFO "
         Nortel Carrier Data Network Management

         Postal:      P.O. Box 3511, Station C 
                      Ottawa, Ontario
                      Canada  K1Y 4H7

	 via the WEB: http://www.nortelnetworks.com
                      select 'Contact Us' from the menu

         via phone:   1-800-4NORTEL"

 DESCRIPTION
    "This MIB module specifies the variables used to implement 
     the Nortel MsCarrier MscPassport state summary functionality."
::= { mscPassportMIBs 7 }

--stateSummaryMIB OBJECT IDENTIFIER  ::= { mscPassportMIBs 7 }

mscStateSummary OBJECT IDENTIFIER ::= { mscComponents 5 }

-- the mscTimeOfLastTableChange group

-- STATUS       current
-- DESCRIPTION
--    " This group contains the variables (timestamps) indicating
--      when a change has occurred in one of the state summary tables.
--      There is one timestamp per table."
mscTimeOfLastTableChange   OBJECT IDENTIFIER ::= { mscStateSummary 1 }

mscTimeOfLastStateSummTableChange OBJECT-TYPE
   SYNTAX       TimeTicks
   ACCESS   read-only
   STATUS       current
   DESCRIPTION
        "The value of sysUpTime at the time that an entry in the
	 mscCompClassTable detected a change."
   ::= { mscTimeOfLastTableChange 1 }

mscCompClassTable OBJECT-TYPE
    SYNTAX  SEQUENCE OF CompClassEntry
    ACCESS  not-accessible
    STATUS  current
    DESCRIPTION
            "A list of component classes that have state
	     information summaries."
    ::= { mscStateSummary 2 }

mscCompClassEntry OBJECT-TYPE
    SYNTAX  CompClassEntry
    ACCESS  not-accessible
    STATUS  current
    DESCRIPTION
            "A component class entry."
    INDEX   { mscCompClass }
    ::= { mscCompClassTable 1 }

CompClassEntry ::=
    SEQUENCE {
        mscCompClass
            OBJECT IDENTIFIER,
	mscCompName
	    DisplayString,
        mscTimeOfLastStateStatusChange
            TimeTicks,
	mscNumberDown
	    Gauge32,
	mscNumberTroubled
	    Gauge32
             }

mscCompClass OBJECT-TYPE
    SYNTAX  OBJECT IDENTIFIER
    ACCESS  read-only
    STATUS  current
    DESCRIPTION
            "An object identifier which points to the SNMP Mib Arc for
	     that particular component class. For example, a 
	     replication of 1.3.6.1.4.1.562.36.2.1.12 (iso.org.dod.
	     internet.private.enterprises.nortel.mscCarrier.mscPassport.
             mscComponents.mscLp) corresponds to the Lp  component class."
    ::= { mscCompClassEntry 1 }

mscCompName OBJECT-TYPE
    SYNTAX  DisplayString
    ACCESS  read-only
    STATUS  current
      DESCRIPTION
            "The string representation of the component class object 
             identifier.  For example, 1.3.6.1.4.1.562.36.2.1.12 (iso.org.
             dod.internet.private.enterprises.nortel.mscCarrier.mscPassport.
             mscComponents.mscLp) is represented as the string, LogicalProcessor."
    ::= { mscCompClassEntry 2 }

mscTimeOfLastStateStatusChange OBJECT-TYPE
    SYNTAX  TimeTicks
    ACCESS  read-only
    STATUS  current
      DESCRIPTION
            "The value of sysUpTime when an OsiState or OsiStateStatus
	     change was detected for the component class.  Currently
	     monitored attributes include: AdminState, OperationalState,
	     AvailabilityStatus and AlarmStatus."
    ::= { mscCompClassEntry 3 }

mscNumberDown OBJECT-TYPE
    SYNTAX  Gauge32
    ACCESS  read-only
    STATUS  current
      DESCRIPTION
            "The number of component instances that are down.  A component
             is considered down when its administrative state is locked 
             or its operational state is disabled. "
    ::= { mscCompClassEntry 4 }

mscNumberTroubled OBJECT-TYPE
    SYNTAX  Gauge32
    ACCESS  read-only
    STATUS  current
      DESCRIPTION
            "The number of component instances that are troubled. A component
             is considered troubled when its administrative status is 
             shuttingDown or its alarm status is not empty or its availability
             status is degraded."
    ::= { mscCompClassEntry 5 }

--
-- Version and Compliance statements
--
 
 
-- Object-Group Statement:
 
-- OBJECTS   { mscTimeOfLastStateSummTableChange, mscCompClass,
--             mscCompName, mscTimeOfLastStateStatusChange, 
--             mscNumberDown, mscNumberTroubled }
-- STATUS     current
-- DESCRIPTION
--       "A list of all current accessible leaf objects."
 
stateSummaryGroupCA01A OBJECT IDENTIFIER
::= { stateSummaryMIB
      stateSummaryGroup(1)
      stateSummaryGroupCA(1)
      stateSummaryGroupCA01(2)  2 }
 
 
-- Agent-Capabilities Statement:
 
-- PRODUCT-RELEASE "Passport Carrier Release 1.1 State Summary ."
-- STATUS          current
-- DESCRIPTION
--    "Carrier Passport State Summary MIB: MIB Version CA01A."
-- SUPPORTS        Nortel-MsCarrier-MscPassport-StateSummaryMIB
-- INCLUDES        { stateSummaryGroupCA01A }
 
stateSummaryCapabilitiesCA01A OBJECT IDENTIFIER
::= { stateSummaryMIB
      stateSummaryCapabilities(3)
      stateSummaryCapabilitiesCA(1)
      stateSummaryCapabilitiesCA01(2)  2 }

END
