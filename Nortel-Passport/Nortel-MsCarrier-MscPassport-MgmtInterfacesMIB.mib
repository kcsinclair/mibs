Nortel-MsCarrier-MscPassport-MgmtInterfacesMIB
DEFINITIONS ::= BEGIN



IMPORTS

      OBJECT-TYPE
   FROM RFC-1212

      IpAddress
   FROM RFC1155-SMI

      mscPassportMIBs,
      mscComponents
   FROM Nortel-MsCarrier-MscPassport-UsefulDefinitionsMIB

      RowPointer,
      DisplayString,
      StorageType,
      RowStatus,
      Integer32,
      Unsigned32
   FROM Nortel-MsCarrier-MscPassport-StandardTextualConventionsMIB

      AsciiString,
      NonReplicated,
      AsciiStringIndex
   FROM Nortel-MsCarrier-MscPassport-TextualConventionsMIB;




-- LAST-UPDATED   "9909010000Z"
-- ORGANIZATION   "Nortel Networks"
-- CONTACT-INFO   "
--         Nortel Carrier Data Network Management
--         
--         Postal:       P.O. Box 3511, Station C 
--                       Ottawa, Ontario 
--                       Canada  K1Y 4H7
--         
--         via the WEB:  http://www.nortelnetworks.com  
--                       select 'Contact Us' from the menu
--          
--         via phone:    1-800-4NORTEL"
-- DESCRIPTION
--    "The module describing the Nortel MsCarrier MscPassport
--     MgmtInterfaces Enterprise MIB."

mgmtInterfacesMIB OBJECT IDENTIFIER ::= { mscPassportMIBs 15 }










-- Nmis
-- The Network Management Interface System (NMIS) is the 
-- collection of software Interfaces on Passport provided to administer 
-- the Passport. NMIS offers Telnet (server and client) and FTP 
-- (server) access, a directly-connected Local Operator capability, and 
-- a proprietary FMIP Interface for use by Magellan NMS.
-- The Nmis component is a placeholder component to collect all the 
-- Network Management Interface components below it.

mscNmis OBJECT IDENTIFIER ::= { mscComponents 17 }



mscNmisRowStatusTable OBJECT-TYPE
   SYNTAX     SEQUENCE OF MscNmisRowStatusEntry
   ACCESS     not-accessible
   STATUS     mandatory
   DESCRIPTION
     "This entry controls the addition and deletion of 
      mscNmis components."
::= { mscNmis 1 }

mscNmisRowStatusEntry OBJECT-TYPE
   SYNTAX     MscNmisRowStatusEntry
   ACCESS     not-accessible
   STATUS     mandatory
   DESCRIPTION
     "A single entry in the table represents a single 
      mscNmis component."
   INDEX {
      mscNmisIndex }
::= { mscNmisRowStatusTable 1 }

MscNmisRowStatusEntry ::= SEQUENCE {
   mscNmisRowStatus
      RowStatus,
   mscNmisComponentName
      DisplayString,
   mscNmisStorageType
      StorageType,
   mscNmisIndex
      NonReplicated }

mscNmisRowStatus OBJECT-TYPE
   SYNTAX     RowStatus 
   ACCESS     read-only
   STATUS     mandatory
   DESCRIPTION
     "This variable is used as the basis for SNMP naming of
      mscNmis components.
      These components cannot be added nor deleted."
::= { mscNmisRowStatusEntry 1 }

mscNmisComponentName OBJECT-TYPE
   SYNTAX     DisplayString 
   ACCESS     read-only
   STATUS     mandatory
   DESCRIPTION
     "This variable provides the component's string name for
      use with the ASCII Console Interface"
::= { mscNmisRowStatusEntry 2 }

mscNmisStorageType OBJECT-TYPE
   SYNTAX     StorageType 
   ACCESS     read-only
   STATUS     mandatory
   DESCRIPTION
     "This variable represents the storage type value for the
      mscNmis tables."
::= { mscNmisRowStatusEntry 4 }

mscNmisIndex OBJECT-TYPE
   SYNTAX     NonReplicated 
   ACCESS     not-accessible
   STATUS     mandatory
   DESCRIPTION
     "This variable represents the index for the mscNmis tables."
::= { mscNmisRowStatusEntry 10 }


-- Nmis Local
-- This network management interface is supported on the V.24 DCE 
-- port on the Control Processors. A VT-100 ASCII terminal must be 
-- connected to the V.24 DCE port to log in to the Local Operator 
-- Interface. The Local Operator Interface is otherwise identical to the 
-- Telnet operator interface.

mscNmisLocal OBJECT IDENTIFIER ::= { mscNmis 2 }



mscNmisLocalRowStatusTable OBJECT-TYPE
   SYNTAX     SEQUENCE OF MscNmisLocalRowStatusEntry
   ACCESS     not-accessible
   STATUS     mandatory
   DESCRIPTION
     "This entry controls the addition and deletion of 
      mscNmisLocal components."
::= { mscNmisLocal 1 }

mscNmisLocalRowStatusEntry OBJECT-TYPE
   SYNTAX     MscNmisLocalRowStatusEntry
   ACCESS     not-accessible
   STATUS     mandatory
   DESCRIPTION
     "A single entry in the table represents a single 
      mscNmisLocal component."
   INDEX {
      mscNmisIndex,
      mscNmisLocalIndex }
::= { mscNmisLocalRowStatusTable 1 }

MscNmisLocalRowStatusEntry ::= SEQUENCE {
   mscNmisLocalRowStatus
      RowStatus,
   mscNmisLocalComponentName
      DisplayString,
   mscNmisLocalStorageType
      StorageType,
   mscNmisLocalIndex
      NonReplicated }

mscNmisLocalRowStatus OBJECT-TYPE
   SYNTAX     RowStatus 
   ACCESS     read-only
   STATUS     mandatory
   DESCRIPTION
     "This variable is used as the basis for SNMP naming of
      mscNmisLocal components.
      These components cannot be added nor deleted."
::= { mscNmisLocalRowStatusEntry 1 }

mscNmisLocalComponentName OBJECT-TYPE
   SYNTAX     DisplayString 
   ACCESS     read-only
   STATUS     mandatory
   DESCRIPTION
     "This variable provides the component's string name for
      use with the ASCII Console Interface"
::= { mscNmisLocalRowStatusEntry 2 }

mscNmisLocalStorageType OBJECT-TYPE
   SYNTAX     StorageType 
   ACCESS     read-only
   STATUS     mandatory
   DESCRIPTION
     "This variable represents the storage type value for the
      mscNmisLocal tables."
::= { mscNmisLocalRowStatusEntry 4 }

mscNmisLocalIndex OBJECT-TYPE
   SYNTAX     NonReplicated 
   ACCESS     not-accessible
   STATUS     mandatory
   DESCRIPTION
     "This variable represents the index for the mscNmisLocal tables."
::= { mscNmisLocalRowStatusEntry 10 }

mscNmisLocalStateTable OBJECT-TYPE
   SYNTAX     SEQUENCE OF MscNmisLocalStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscNmisLocal 10 }

mscNmisLocalStateEntry OBJECT-TYPE
   SYNTAX     MscNmisLocalStateEntry
   ACCESS     not-accessible
   STATUS     mandatory
   DESCRIPTION
     "An entry in the mscNmisLocalStateTable."
   INDEX {
      mscNmisIndex,
      mscNmisLocalIndex }
::= { mscNmisLocalStateTable 1 }

MscNmisLocalStateEntry ::= SEQUENCE {
   mscNmisLocalAdminState
      INTEGER,
   mscNmisLocalOperationalState
      INTEGER,
   mscNmisLocalUsageState
      INTEGER }

mscNmisLocalAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscNmisLocalStateEntry 1 }

mscNmisLocalOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscNmisLocalStateEntry 2 }

mscNmisLocalUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscNmisLocalStateEntry 3 }

mscNmisLocalOperTable OBJECT-TYPE
   SYNTAX     SEQUENCE OF MscNmisLocalOperEntry
   ACCESS     not-accessible
   STATUS     mandatory
   DESCRIPTION
     "This group contains the operational attributes for an NMIS 
      manager. This group is common to all NMIS managers."
::= { mscNmisLocal 11 }

mscNmisLocalOperEntry OBJECT-TYPE
   SYNTAX     MscNmisLocalOperEntry
   ACCESS     not-accessible
   STATUS     mandatory
   DESCRIPTION
     "An entry in the mscNmisLocalOperTable."
   INDEX {
      mscNmisIndex,
      mscNmisLocalIndex }
::= { mscNmisLocalOperTable 1 }

MscNmisLocalOperEntry ::= SEQUENCE {
   mscNmisLocalMaxAllowedSessions
      Unsigned32,
   mscNmisLocalActiveSessions
      Unsigned32 }

mscNmisLocalMaxAllowedSessions OBJECT-TYPE
   SYNTAX     Unsigned32 (2..35)
   ACCESS     read-only
   STATUS     mandatory
   DESCRIPTION
     "This attribute indicates the maximum number of simultaneous 
      sessions the manager will allow."
::= { mscNmisLocalOperEntry 1 }

mscNmisLocalActiveSessions OBJECT-TYPE
   SYNTAX     Unsigned32 (0..35)
   ACCESS     read-only
   STATUS     mandatory
   DESCRIPTION
     "This attribute indicates the number of simultaneous sessions 
      currently active under the manager. Note that there may be fewer  
      Session components than what is shown here, since an active 
      session could be in the midst of logging in and may not yet be fully 
      up."
::= { mscNmisLocalOperEntry 2 }


-- Nmis Local Session/n
-- This Session component supports a single local operator logged in 
-- to a V.24 DCE port of a control processor.

mscNmisLocalSession OBJECT IDENTIFIER ::= { mscNmisLocal 2 }



mscNmisLocalSessionRowStatusTable OBJECT-TYPE
   SYNTAX     SEQUENCE OF MscNmisLocalSessionRowStatusEntry
   ACCESS     not-accessible
   STATUS     mandatory
   DESCRIPTION
     "This entry controls the addition and deletion of 
      mscNmisLocalSession components."
::= { mscNmisLocalSession 1 }

mscNmisLocalSessionRowStatusEntry OBJECT-TYPE
   SYNTAX     MscNmisLocalSessionRowStatusEntry
   ACCESS     not-accessible
   STATUS     mandatory
   DESCRIPTION
     "A single entry in the table represents a single 
      mscNmisLocalSession component."
   INDEX {
      mscNmisIndex,
      mscNmisLocalIndex,
      mscNmisLocalSessionIndex }
::= { mscNmisLocalSessionRowStatusTable 1 }

MscNmisLocalSessionRowStatusEntry ::= SEQUENCE {
   mscNmisLocalSessionRowStatus
      RowStatus,
   mscNmisLocalSessionComponentName
      DisplayString,
   mscNmisLocalSessionStorageType
      StorageType,
   mscNmisLocalSessionIndex
      Integer32 }

mscNmisLocalSessionRowStatus OBJECT-TYPE
   SYNTAX     RowStatus 
   ACCESS     read-only
   STATUS     mandatory
   DESCRIPTION
     "This variable is used as the basis for SNMP naming of
      mscNmisLocalSession components.
      These components cannot be added nor deleted."
::= { mscNmisLocalSessionRowStatusEntry 1 }

mscNmisLocalSessionComponentName OBJECT-TYPE
   SYNTAX     DisplayString 
   ACCESS     read-only
   STATUS     mandatory
   DESCRIPTION
     "This variable provides the component's string name for
      use with the ASCII Console Interface"
::= { mscNmisLocalSessionRowStatusEntry 2 }

mscNmisLocalSessionStorageType OBJECT-TYPE
   SYNTAX     StorageType 
   ACCESS     read-only
   STATUS     mandatory
   DESCRIPTION
     "This variable represents the storage type value for the
      mscNmisLocalSession tables."
::= { mscNmisLocalSessionRowStatusEntry 4 }

mscNmisLocalSessionIndex OBJECT-TYPE
   SYNTAX     Integer32 (1..2)
   ACCESS     not-accessible
   STATUS     mandatory
   DESCRIPTION
     "This variable represents the index for the mscNmisLocalSession tables."
::= { mscNmisLocalSessionRowStatusEntry 10 }

mscNmisLocalSessionOperTable OBJECT-TYPE
   SYNTAX     SEQUENCE OF MscNmisLocalSessionOperEntry
   ACCESS     not-accessible
   STATUS     mandatory
   DESCRIPTION
     "This group contains the operational attributes for a Local session."
::= { mscNmisLocalSession 10 }

mscNmisLocalSessionOperEntry OBJECT-TYPE
   SYNTAX     MscNmisLocalSessionOperEntry
   ACCESS     not-accessible
   STATUS     mandatory
   DESCRIPTION
     "An entry in the mscNmisLocalSessionOperTable."
   INDEX {
      mscNmisIndex,
      mscNmisLocalIndex,
      mscNmisLocalSessionIndex }
::= { mscNmisLocalSessionOperTable 1 }

MscNmisLocalSessionOperEntry ::= SEQUENCE {
   mscNmisLocalSessionUserid
      AsciiString,
   mscNmisLocalSessionDataStreams
      OCTET STRING,
   mscNmisLocalSessionHostCard
      RowPointer,
   mscNmisLocalSessionScreenWidth
      Unsigned32 }

mscNmisLocalSessionUserid OBJECT-TYPE
   SYNTAX     AsciiString (SIZE (8))
   ACCESS     read-only
   STATUS     mandatory
   DESCRIPTION
     "This attribute indicates the Userid logged in to the Session."
::= { mscNmisLocalSessionOperEntry 1 }

mscNmisLocalSessionDataStreams OBJECT-TYPE
   SYNTAX     OCTET STRING (SIZE (1))
   ACCESS     read-write
   STATUS     mandatory
   DESCRIPTION
     "This attribute indicates which data streams will be transmitted back 
      to the operator through this session. Only a userid with a command 
      impact of system administration may register for logs.

      Description of bits:
      notused0(0)
      alarm(1)
      log(2)
      debug(3)
      scn(4)"
::= { mscNmisLocalSessionOperEntry 2 }

mscNmisLocalSessionHostCard OBJECT-TYPE
   SYNTAX     RowPointer 
   ACCESS     read-only
   STATUS     mandatory
   DESCRIPTION
     "This attribute holds the component name of the host control 
      processor Card servicing the local operator session."
::= { mscNmisLocalSessionOperEntry 3 }

mscNmisLocalSessionScreenWidth OBJECT-TYPE
   SYNTAX     Unsigned32 (79..2000)
   ACCESS     read-write
   STATUS     mandatory
   DESCRIPTION
     "This attribute indicates the maximum width (in characters) of 
      operator command responses. Beyond this maximum, responses are 
      either truncated or wrapped onto the next line, as appropriate.
      
      Asynchronous responses, such as alarms, are always displayed 
      using a 79 character width."
   DEFVAL     { 79 }
::= { mscNmisLocalSessionOperEntry 4 }


-- Nmis Telnet
-- Passport supports both the Telnet server and client. The Session 
-- subcomponent corresponds to the server connection, while the 
-- Session's Client subcomponent corresponds to the client 
-- connection. The server (that is, the network management interface) 
-- is accessed from a remote computer using the Telnet protocol. The 
-- Telnet operator interface is otherwise identical to the local operator 
-- interface. Each server can set up a single client connection. Note 
-- that Telnet clients are accessible only from a Telnet session, not 
-- from Local, FMIP, or FTP sessions.

mscNmisTelnet OBJECT IDENTIFIER ::= { mscNmis 3 }



mscNmisTelnetRowStatusTable OBJECT-TYPE
   SYNTAX     SEQUENCE OF MscNmisTelnetRowStatusEntry
   ACCESS     not-accessible
   STATUS     mandatory
   DESCRIPTION
     "This entry controls the addition and deletion of 
      mscNmisTelnet components."
::= { mscNmisTelnet 1 }

mscNmisTelnetRowStatusEntry OBJECT-TYPE
   SYNTAX     MscNmisTelnetRowStatusEntry
   ACCESS     not-accessible
   STATUS     mandatory
   DESCRIPTION
     "A single entry in the table represents a single 
      mscNmisTelnet component."
   INDEX {
      mscNmisIndex,
      mscNmisTelnetIndex }
::= { mscNmisTelnetRowStatusTable 1 }

MscNmisTelnetRowStatusEntry ::= SEQUENCE {
   mscNmisTelnetRowStatus
      RowStatus,
   mscNmisTelnetComponentName
      DisplayString,
   mscNmisTelnetStorageType
      StorageType,
   mscNmisTelnetIndex
      NonReplicated }

mscNmisTelnetRowStatus OBJECT-TYPE
   SYNTAX     RowStatus 
   ACCESS     read-only
   STATUS     mandatory
   DESCRIPTION
     "This variable is used as the basis for SNMP naming of
      mscNmisTelnet components.
      These components cannot be added nor deleted."
::= { mscNmisTelnetRowStatusEntry 1 }

mscNmisTelnetComponentName OBJECT-TYPE
   SYNTAX     DisplayString 
   ACCESS     read-only
   STATUS     mandatory
   DESCRIPTION
     "This variable provides the component's string name for
      use with the ASCII Console Interface"
::= { mscNmisTelnetRowStatusEntry 2 }

mscNmisTelnetStorageType OBJECT-TYPE
   SYNTAX     StorageType 
   ACCESS     read-only
   STATUS     mandatory
   DESCRIPTION
     "This variable represents the storage type value for the
      mscNmisTelnet tables."
::= { mscNmisTelnetRowStatusEntry 4 }

mscNmisTelnetIndex OBJECT-TYPE
   SYNTAX     NonReplicated 
   ACCESS     not-accessible
   STATUS     mandatory
   DESCRIPTION
     "This variable represents the index for the mscNmisTelnet tables."
::= { mscNmisTelnetRowStatusEntry 10 }

mscNmisTelnetStateTable OBJECT-TYPE
   SYNTAX     SEQUENCE OF MscNmisTelnetStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscNmisTelnet 10 }

mscNmisTelnetStateEntry OBJECT-TYPE
   SYNTAX     MscNmisTelnetStateEntry
   ACCESS     not-accessible
   STATUS     mandatory
   DESCRIPTION
     "An entry in the mscNmisTelnetStateTable."
   INDEX {
      mscNmisIndex,
      mscNmisTelnetIndex }
::= { mscNmisTelnetStateTable 1 }

MscNmisTelnetStateEntry ::= SEQUENCE {
   mscNmisTelnetAdminState
      INTEGER,
   mscNmisTelnetOperationalState
      INTEGER,
   mscNmisTelnetUsageState
      INTEGER }

mscNmisTelnetAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscNmisTelnetStateEntry 1 }

mscNmisTelnetOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscNmisTelnetStateEntry 2 }

mscNmisTelnetUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscNmisTelnetStateEntry 3 }

mscNmisTelnetOperTable OBJECT-TYPE
   SYNTAX     SEQUENCE OF MscNmisTelnetOperEntry
   ACCESS     not-accessible
   STATUS     mandatory
   DESCRIPTION
     "This group contains the operational attributes for an NMIS 
      manager. This group is common to all NMIS managers."
::= { mscNmisTelnet 11 }

mscNmisTelnetOperEntry OBJECT-TYPE
   SYNTAX     MscNmisTelnetOperEntry
   ACCESS     not-accessible
   STATUS     mandatory
   DESCRIPTION
     "An entry in the mscNmisTelnetOperTable."
   INDEX {
      mscNmisIndex,
      mscNmisTelnetIndex }
::= { mscNmisTelnetOperTable 1 }

MscNmisTelnetOperEntry ::= SEQUENCE {
   mscNmisTelnetMaxAllowedSessions
      Unsigned32,
   mscNmisTelnetActiveSessions
      Unsigned32 }

mscNmisTelnetMaxAllowedSessions OBJECT-TYPE
   SYNTAX     Unsigned32 (2..35)
   ACCESS     read-only
   STATUS     mandatory
   DESCRIPTION
     "This attribute indicates the maximum number of simultaneous 
      sessions the manager will allow."
::= { mscNmisTelnetOperEntry 1 }

mscNmisTelnetActiveSessions OBJECT-TYPE
   SYNTAX     Unsigned32 (0..35)
   ACCESS     read-only
   STATUS     mandatory
   DESCRIPTION
     "This attribute indicates the number of simultaneous sessions 
      currently active under the manager. Note that there may be fewer  
      Session components than what is shown here, since an active 
      session could be in the midst of logging in and may not yet be fully 
      up."
::= { mscNmisTelnetOperEntry 2 }


-- Nmis Telnet Session/n
-- This  component supports a single remote Telnet operator logged in 
-- using the Telnet protocol. Optionally, a single outgoing Telnet client 
-- connection can be established from here.

mscNmisTelnetSession OBJECT IDENTIFIER ::= { mscNmisTelnet 2 }



mscNmisTelnetSessionRowStatusTable OBJECT-TYPE
   SYNTAX     SEQUENCE OF MscNmisTelnetSessionRowStatusEntry
   ACCESS     not-accessible
   STATUS     mandatory
   DESCRIPTION
     "This entry controls the addition and deletion of 
      mscNmisTelnetSession components."
::= { mscNmisTelnetSession 1 }

mscNmisTelnetSessionRowStatusEntry OBJECT-TYPE
   SYNTAX     MscNmisTelnetSessionRowStatusEntry
   ACCESS     not-accessible
   STATUS     mandatory
   DESCRIPTION
     "A single entry in the table represents a single 
      mscNmisTelnetSession component."
   INDEX {
      mscNmisIndex,
      mscNmisTelnetIndex,
      mscNmisTelnetSessionIndex }
::= { mscNmisTelnetSessionRowStatusTable 1 }

MscNmisTelnetSessionRowStatusEntry ::= SEQUENCE {
   mscNmisTelnetSessionRowStatus
      RowStatus,
   mscNmisTelnetSessionComponentName
      DisplayString,
   mscNmisTelnetSessionStorageType
      StorageType,
   mscNmisTelnetSessionIndex
      Integer32 }

mscNmisTelnetSessionRowStatus OBJECT-TYPE
   SYNTAX     RowStatus 
   ACCESS     read-only
   STATUS     mandatory
   DESCRIPTION
     "This variable is used as the basis for SNMP naming of
      mscNmisTelnetSession components.
      These components cannot be added nor deleted."
::= { mscNmisTelnetSessionRowStatusEntry 1 }

mscNmisTelnetSessionComponentName OBJECT-TYPE
   SYNTAX     DisplayString 
   ACCESS     read-only
   STATUS     mandatory
   DESCRIPTION
     "This variable provides the component's string name for
      use with the ASCII Console Interface"
::= { mscNmisTelnetSessionRowStatusEntry 2 }

mscNmisTelnetSessionStorageType OBJECT-TYPE
   SYNTAX     StorageType 
   ACCESS     read-only
   STATUS     mandatory
   DESCRIPTION
     "This variable represents the storage type value for the
      mscNmisTelnetSession tables."
::= { mscNmisTelnetSessionRowStatusEntry 4 }

mscNmisTelnetSessionIndex OBJECT-TYPE
   SYNTAX     Integer32 (1..8)
   ACCESS     not-accessible
   STATUS     mandatory
   DESCRIPTION
     "This variable represents the index for the mscNmisTelnetSession tables."
::= { mscNmisTelnetSessionRowStatusEntry 10 }

mscNmisTelnetSessionOperTable OBJECT-TYPE
   SYNTAX     SEQUENCE OF MscNmisTelnetSessionOperEntry
   ACCESS     not-accessible
   STATUS     mandatory
   DESCRIPTION
     "This group contains the operational attributes for a Telnet session."
::= { mscNmisTelnetSession 10 }

mscNmisTelnetSessionOperEntry OBJECT-TYPE
   SYNTAX     MscNmisTelnetSessionOperEntry
   ACCESS     not-accessible
   STATUS     mandatory
   DESCRIPTION
     "An entry in the mscNmisTelnetSessionOperTable."
   INDEX {
      mscNmisIndex,
      mscNmisTelnetIndex,
      mscNmisTelnetSessionIndex }
::= { mscNmisTelnetSessionOperTable 1 }

MscNmisTelnetSessionOperEntry ::= SEQUENCE {
   mscNmisTelnetSessionUserid
      AsciiString,
   mscNmisTelnetSessionDataStreams
      OCTET STRING,
   mscNmisTelnetSessionRemoteIpAddr
      IpAddress,
   mscNmisTelnetSessionRemoteTcpPort
      Unsigned32,
   mscNmisTelnetSessionScreenWidth
      Unsigned32 }

mscNmisTelnetSessionUserid OBJECT-TYPE
   SYNTAX     AsciiString (SIZE (8))
   ACCESS     read-only
   STATUS     mandatory
   DESCRIPTION
     "This attribute indicates the userid logged in to the session."
::= { mscNmisTelnetSessionOperEntry 1 }

mscNmisTelnetSessionDataStreams OBJECT-TYPE
   SYNTAX     OCTET STRING (SIZE (1))
   ACCESS     read-write
   STATUS     mandatory
   DESCRIPTION
     "This attribute indicates which data streams (alarm, debug, log, scn) 
      will be transmitted back to the operator through this session. Only a 
      userid with a command impact of system administration may 
      register for logs.
      
      When a client connection is up through this interface, all of the 
      values are turned off. This means that this data is discarded when 
      the session has a Telnet client connection set up.
      
      When the client connection terminates, the data which was being 
      received prior to the client being set up is requested again.

      Description of bits:
      notused0(0)
      alarm(1)
      log(2)
      debug(3)
      scn(4)"
::= { mscNmisTelnetSessionOperEntry 2 }

mscNmisTelnetSessionRemoteIpAddr OBJECT-TYPE
   SYNTAX     IpAddress 
   ACCESS     read-only
   STATUS     mandatory
   DESCRIPTION
     "This attribute indicates the IP address of the remote device 
      connected to the session."
::= { mscNmisTelnetSessionOperEntry 3 }

mscNmisTelnetSessionRemoteTcpPort OBJECT-TYPE
   SYNTAX     Unsigned32 (0..65535)
   ACCESS     read-only
   STATUS     mandatory
   DESCRIPTION
     "This attribute indicates the TCP port number of the Telnet client 
      being used on the remote device connected to the session."
::= { mscNmisTelnetSessionOperEntry 4 }

mscNmisTelnetSessionScreenWidth OBJECT-TYPE
   SYNTAX     Unsigned32 (79..2000)
   ACCESS     read-write
   STATUS     mandatory
   DESCRIPTION
     "This attribute indicates the maximum width (in characters) of 
      operator command responses. Beyond this maximum, responses are 
      either truncated or wrapped onto the next line, as appropriate.
      
      Asynchronous responses, such as alarms, are always displayed 
      using a 79 character width."
   DEFVAL     { 79 }
::= { mscNmisTelnetSessionOperEntry 5 }


-- Nmis Telnet Session/n Client
-- This component represents a client connection to a remote node 
-- through this session. The client connection is established by 
-- invoking the Telnet command of a Vr component.

mscNmisTelnetSessionClient OBJECT IDENTIFIER ::= { mscNmisTelnetSession 2 }



mscNmisTelnetSessionClientRowStatusTable OBJECT-TYPE
   SYNTAX     SEQUENCE OF MscNmisTelnetSessionClientRowStatusEntry
   ACCESS     not-accessible
   STATUS     mandatory
   DESCRIPTION
     "This entry controls the addition and deletion of 
      mscNmisTelnetSessionClient components."
::= { mscNmisTelnetSessionClient 1 }

mscNmisTelnetSessionClientRowStatusEntry OBJECT-TYPE
   SYNTAX     MscNmisTelnetSessionClientRowStatusEntry
   ACCESS     not-accessible
   STATUS     mandatory
   DESCRIPTION
     "A single entry in the table represents a single 
      mscNmisTelnetSessionClient component."
   INDEX {
      mscNmisIndex,
      mscNmisTelnetIndex,
      mscNmisTelnetSessionIndex,
      mscNmisTelnetSessionClientIndex }
::= { mscNmisTelnetSessionClientRowStatusTable 1 }

MscNmisTelnetSessionClientRowStatusEntry ::= SEQUENCE {
   mscNmisTelnetSessionClientRowStatus
      RowStatus,
   mscNmisTelnetSessionClientComponentName
      DisplayString,
   mscNmisTelnetSessionClientStorageType
      StorageType,
   mscNmisTelnetSessionClientIndex
      NonReplicated }

mscNmisTelnetSessionClientRowStatus OBJECT-TYPE
   SYNTAX     RowStatus 
   ACCESS     read-only
   STATUS     mandatory
   DESCRIPTION
     "This variable is used as the basis for SNMP naming of
      mscNmisTelnetSessionClient components.
      These components cannot be added nor deleted."
::= { mscNmisTelnetSessionClientRowStatusEntry 1 }

mscNmisTelnetSessionClientComponentName OBJECT-TYPE
   SYNTAX     DisplayString 
   ACCESS     read-only
   STATUS     mandatory
   DESCRIPTION
     "This variable provides the component's string name for
      use with the ASCII Console Interface"
::= { mscNmisTelnetSessionClientRowStatusEntry 2 }

mscNmisTelnetSessionClientStorageType OBJECT-TYPE
   SYNTAX     StorageType 
   ACCESS     read-only
   STATUS     mandatory
   DESCRIPTION
     "This variable represents the storage type value for the
      mscNmisTelnetSessionClient tables."
::= { mscNmisTelnetSessionClientRowStatusEntry 4 }

mscNmisTelnetSessionClientIndex OBJECT-TYPE
   SYNTAX     NonReplicated 
   ACCESS     not-accessible
   STATUS     mandatory
   DESCRIPTION
     "This variable represents the index for the mscNmisTelnetSessionClient tables."
::= { mscNmisTelnetSessionClientRowStatusEntry 10 }

mscNmisTelnetSessionClientOperTable OBJECT-TYPE
   SYNTAX     SEQUENCE OF MscNmisTelnetSessionClientOperEntry
   ACCESS     not-accessible
   STATUS     mandatory
   DESCRIPTION
     "This group contains the operational attributes for a Telnet client."
::= { mscNmisTelnetSessionClient 10 }

mscNmisTelnetSessionClientOperEntry OBJECT-TYPE
   SYNTAX     MscNmisTelnetSessionClientOperEntry
   ACCESS     not-accessible
   STATUS     mandatory
   DESCRIPTION
     "An entry in the mscNmisTelnetSessionClientOperTable."
   INDEX {
      mscNmisIndex,
      mscNmisTelnetIndex,
      mscNmisTelnetSessionIndex,
      mscNmisTelnetSessionClientIndex }
::= { mscNmisTelnetSessionClientOperTable 1 }

MscNmisTelnetSessionClientOperEntry ::= SEQUENCE {
   mscNmisTelnetSessionClientVirtualRouter
      RowPointer,
   mscNmisTelnetSessionClientRemoteIpAddr
      IpAddress,
   mscNmisTelnetSessionClientRemoteTcpPort
      Unsigned32 }

mscNmisTelnetSessionClientVirtualRouter OBJECT-TYPE
   SYNTAX     RowPointer 
   ACCESS     read-only
   STATUS     mandatory
   DESCRIPTION
     "This attribute indicates the VR instance that determines which 
      address space the remoteIpAddr belongs to."
::= { mscNmisTelnetSessionClientOperEntry 1 }

mscNmisTelnetSessionClientRemoteIpAddr OBJECT-TYPE
   SYNTAX     IpAddress 
   ACCESS     read-only
   STATUS     mandatory
   DESCRIPTION
     "This attribute indicates the IP address of the remote side of the 
      client connection."
::= { mscNmisTelnetSessionClientOperEntry 2 }

mscNmisTelnetSessionClientRemoteTcpPort OBJECT-TYPE
   SYNTAX     Unsigned32 (0..65535)
   ACCESS     read-only
   STATUS     mandatory
   DESCRIPTION
     "This attribute indicates the TCP port number of the remote side of 
      the client connection."
::= { mscNmisTelnetSessionClientOperEntry 3 }


-- Nmis Fmip
-- This network management interface is accessed by a Magellan 
-- NMS calling the Passport for management purposes, using the 
-- proprietary FMIP protocol.

mscNmisFmip OBJECT IDENTIFIER ::= { mscNmis 4 }



mscNmisFmipRowStatusTable OBJECT-TYPE
   SYNTAX     SEQUENCE OF MscNmisFmipRowStatusEntry
   ACCESS     not-accessible
   STATUS     mandatory
   DESCRIPTION
     "This entry controls the addition and deletion of 
      mscNmisFmip components."
::= { mscNmisFmip 1 }

mscNmisFmipRowStatusEntry OBJECT-TYPE
   SYNTAX     MscNmisFmipRowStatusEntry
   ACCESS     not-accessible
   STATUS     mandatory
   DESCRIPTION
     "A single entry in the table represents a single 
      mscNmisFmip component."
   INDEX {
      mscNmisIndex,
      mscNmisFmipIndex }
::= { mscNmisFmipRowStatusTable 1 }

MscNmisFmipRowStatusEntry ::= SEQUENCE {
   mscNmisFmipRowStatus
      RowStatus,
   mscNmisFmipComponentName
      DisplayString,
   mscNmisFmipStorageType
      StorageType,
   mscNmisFmipIndex
      NonReplicated }

mscNmisFmipRowStatus OBJECT-TYPE
   SYNTAX     RowStatus 
   ACCESS     read-only
   STATUS     mandatory
   DESCRIPTION
     "This variable is used as the basis for SNMP naming of
      mscNmisFmip components.
      These components cannot be added nor deleted."
::= { mscNmisFmipRowStatusEntry 1 }

mscNmisFmipComponentName OBJECT-TYPE
   SYNTAX     DisplayString 
   ACCESS     read-only
   STATUS     mandatory
   DESCRIPTION
     "This variable provides the component's string name for
      use with the ASCII Console Interface"
::= { mscNmisFmipRowStatusEntry 2 }

mscNmisFmipStorageType OBJECT-TYPE
   SYNTAX     StorageType 
   ACCESS     read-only
   STATUS     mandatory
   DESCRIPTION
     "This variable represents the storage type value for the
      mscNmisFmip tables."
::= { mscNmisFmipRowStatusEntry 4 }

mscNmisFmipIndex OBJECT-TYPE
   SYNTAX     NonReplicated 
   ACCESS     not-accessible
   STATUS     mandatory
   DESCRIPTION
     "This variable represents the index for the mscNmisFmip tables."
::= { mscNmisFmipRowStatusEntry 10 }

mscNmisFmipStateTable OBJECT-TYPE
   SYNTAX     SEQUENCE OF MscNmisFmipStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscNmisFmip 10 }

mscNmisFmipStateEntry OBJECT-TYPE
   SYNTAX     MscNmisFmipStateEntry
   ACCESS     not-accessible
   STATUS     mandatory
   DESCRIPTION
     "An entry in the mscNmisFmipStateTable."
   INDEX {
      mscNmisIndex,
      mscNmisFmipIndex }
::= { mscNmisFmipStateTable 1 }

MscNmisFmipStateEntry ::= SEQUENCE {
   mscNmisFmipAdminState
      INTEGER,
   mscNmisFmipOperationalState
      INTEGER,
   mscNmisFmipUsageState
      INTEGER }

mscNmisFmipAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscNmisFmipStateEntry 1 }

mscNmisFmipOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscNmisFmipStateEntry 2 }

mscNmisFmipUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscNmisFmipStateEntry 3 }

mscNmisFmipOperTable OBJECT-TYPE
   SYNTAX     SEQUENCE OF MscNmisFmipOperEntry
   ACCESS     not-accessible
   STATUS     mandatory
   DESCRIPTION
     "This group contains the operational attributes for an NMIS 
      manager. This group is common to all NMIS managers."
::= { mscNmisFmip 11 }

mscNmisFmipOperEntry OBJECT-TYPE
   SYNTAX     MscNmisFmipOperEntry
   ACCESS     not-accessible
   STATUS     mandatory
   DESCRIPTION
     "An entry in the mscNmisFmipOperTable."
   INDEX {
      mscNmisIndex,
      mscNmisFmipIndex }
::= { mscNmisFmipOperTable 1 }

MscNmisFmipOperEntry ::= SEQUENCE {
   mscNmisFmipMaxAllowedSessions
      Unsigned32,
   mscNmisFmipActiveSessions
      Unsigned32 }

mscNmisFmipMaxAllowedSessions OBJECT-TYPE
   SYNTAX     Unsigned32 (2..35)
   ACCESS     read-only
   STATUS     mandatory
   DESCRIPTION
     "This attribute indicates the maximum number of simultaneous 
      sessions the manager will allow."
::= { mscNmisFmipOperEntry 1 }

mscNmisFmipActiveSessions OBJECT-TYPE
   SYNTAX     Unsigned32 (0..35)
   ACCESS     read-only
   STATUS     mandatory
   DESCRIPTION
     "This attribute indicates the number of simultaneous sessions 
      currently active under the manager. Note that there may be fewer  
      Session components than what is shown here, since an active 
      session could be in the midst of logging in and may not yet be fully 
      up."
::= { mscNmisFmipOperEntry 2 }


-- Nmis Fmip Session/n
-- This Session component supports a single FMIP connection from a 
-- remote Magellan NMS.

mscNmisFmipSession OBJECT IDENTIFIER ::= { mscNmisFmip 2 }



mscNmisFmipSessionRowStatusTable OBJECT-TYPE
   SYNTAX     SEQUENCE OF MscNmisFmipSessionRowStatusEntry
   ACCESS     not-accessible
   STATUS     mandatory
   DESCRIPTION
     "This entry controls the addition and deletion of 
      mscNmisFmipSession components."
::= { mscNmisFmipSession 1 }

mscNmisFmipSessionRowStatusEntry OBJECT-TYPE
   SYNTAX     MscNmisFmipSessionRowStatusEntry
   ACCESS     not-accessible
   STATUS     mandatory
   DESCRIPTION
     "A single entry in the table represents a single 
      mscNmisFmipSession component."
   INDEX {
      mscNmisIndex,
      mscNmisFmipIndex,
      mscNmisFmipSessionIndex }
::= { mscNmisFmipSessionRowStatusTable 1 }

MscNmisFmipSessionRowStatusEntry ::= SEQUENCE {
   mscNmisFmipSessionRowStatus
      RowStatus,
   mscNmisFmipSessionComponentName
      DisplayString,
   mscNmisFmipSessionStorageType
      StorageType,
   mscNmisFmipSessionIndex
      Integer32 }

mscNmisFmipSessionRowStatus OBJECT-TYPE
   SYNTAX     RowStatus 
   ACCESS     read-only
   STATUS     mandatory
   DESCRIPTION
     "This variable is used as the basis for SNMP naming of
      mscNmisFmipSession components.
      These components cannot be added nor deleted."
::= { mscNmisFmipSessionRowStatusEntry 1 }

mscNmisFmipSessionComponentName OBJECT-TYPE
   SYNTAX     DisplayString 
   ACCESS     read-only
   STATUS     mandatory
   DESCRIPTION
     "This variable provides the component's string name for
      use with the ASCII Console Interface"
::= { mscNmisFmipSessionRowStatusEntry 2 }

mscNmisFmipSessionStorageType OBJECT-TYPE
   SYNTAX     StorageType 
   ACCESS     read-only
   STATUS     mandatory
   DESCRIPTION
     "This variable represents the storage type value for the
      mscNmisFmipSession tables."
::= { mscNmisFmipSessionRowStatusEntry 4 }

mscNmisFmipSessionIndex OBJECT-TYPE
   SYNTAX     Integer32 (1..35)
   ACCESS     not-accessible
   STATUS     mandatory
   DESCRIPTION
     "This variable represents the index for the mscNmisFmipSession tables."
::= { mscNmisFmipSessionRowStatusEntry 10 }

mscNmisFmipSessionOperTable OBJECT-TYPE
   SYNTAX     SEQUENCE OF MscNmisFmipSessionOperEntry
   ACCESS     not-accessible
   STATUS     mandatory
   DESCRIPTION
     "This group contains the operational attributes for an FMIP session."
::= { mscNmisFmipSession 10 }

mscNmisFmipSessionOperEntry OBJECT-TYPE
   SYNTAX     MscNmisFmipSessionOperEntry
   ACCESS     not-accessible
   STATUS     mandatory
   DESCRIPTION
     "An entry in the mscNmisFmipSessionOperTable."
   INDEX {
      mscNmisIndex,
      mscNmisFmipIndex,
      mscNmisFmipSessionIndex }
::= { mscNmisFmipSessionOperTable 1 }

MscNmisFmipSessionOperEntry ::= SEQUENCE {
   mscNmisFmipSessionUserid
      AsciiString,
   mscNmisFmipSessionDataStreams
      OCTET STRING,
   mscNmisFmipSessionRemoteIpAddr
      IpAddress,
   mscNmisFmipSessionRemoteTcpPort
      Unsigned32,
   mscNmisFmipSessionScreenWidth
      Unsigned32 }

mscNmisFmipSessionUserid OBJECT-TYPE
   SYNTAX     AsciiString (SIZE (8))
   ACCESS     read-only
   STATUS     mandatory
   DESCRIPTION
     "This attribute indicates the userid logged in to the session."
::= { mscNmisFmipSessionOperEntry 1 }

mscNmisFmipSessionDataStreams OBJECT-TYPE
   SYNTAX     OCTET STRING (SIZE (1))
   ACCESS     read-write
   STATUS     mandatory
   DESCRIPTION
     "This attribute indicates which data streams will be transmitted back 
      to the operator through this session. Only a userid with a command 
      impact of system administration may register for logs.

      Description of bits:
      notused0(0)
      alarm(1)
      log(2)
      debug(3)
      scn(4)"
::= { mscNmisFmipSessionOperEntry 2 }

mscNmisFmipSessionRemoteIpAddr OBJECT-TYPE
   SYNTAX     IpAddress 
   ACCESS     read-only
   STATUS     mandatory
   DESCRIPTION
     "This attribute indicates the IP address of the remote device 
      connected to the session."
::= { mscNmisFmipSessionOperEntry 3 }

mscNmisFmipSessionRemoteTcpPort OBJECT-TYPE
   SYNTAX     Unsigned32 (0..65535)
   ACCESS     read-only
   STATUS     mandatory
   DESCRIPTION
     "This attribute indicates the TCP port number of the FMIP client 
      being used on the remote device connected to the session."
::= { mscNmisFmipSessionOperEntry 4 }

mscNmisFmipSessionScreenWidth OBJECT-TYPE
   SYNTAX     Unsigned32 (79..2000)
   ACCESS     read-write
   STATUS     mandatory
   DESCRIPTION
     "This attribute indicates the maximum width (in characters) of 
      operator command responses. Beyond this maximum, responses are 
      either truncated or wrapped onto the next line, as appropriate.
      
      Asynchronous responses, such as alarms, are always displayed 
      using a 79 character width."
   DEFVAL     { 79 }
::= { mscNmisFmipSessionOperEntry 5 }


-- Nmis Ftp
-- This network management interface is accessed from a remote 
-- computer using the FTP protocol.

mscNmisFtp OBJECT IDENTIFIER ::= { mscNmis 5 }



mscNmisFtpRowStatusTable OBJECT-TYPE
   SYNTAX     SEQUENCE OF MscNmisFtpRowStatusEntry
   ACCESS     not-accessible
   STATUS     mandatory
   DESCRIPTION
     "This entry controls the addition and deletion of 
      mscNmisFtp components."
::= { mscNmisFtp 1 }

mscNmisFtpRowStatusEntry OBJECT-TYPE
   SYNTAX     MscNmisFtpRowStatusEntry
   ACCESS     not-accessible
   STATUS     mandatory
   DESCRIPTION
     "A single entry in the table represents a single 
      mscNmisFtp component."
   INDEX {
      mscNmisIndex,
      mscNmisFtpIndex }
::= { mscNmisFtpRowStatusTable 1 }

MscNmisFtpRowStatusEntry ::= SEQUENCE {
   mscNmisFtpRowStatus
      RowStatus,
   mscNmisFtpComponentName
      DisplayString,
   mscNmisFtpStorageType
      StorageType,
   mscNmisFtpIndex
      NonReplicated }

mscNmisFtpRowStatus OBJECT-TYPE
   SYNTAX     RowStatus 
   ACCESS     read-only
   STATUS     mandatory
   DESCRIPTION
     "This variable is used as the basis for SNMP naming of
      mscNmisFtp components.
      These components cannot be added nor deleted."
::= { mscNmisFtpRowStatusEntry 1 }

mscNmisFtpComponentName OBJECT-TYPE
   SYNTAX     DisplayString 
   ACCESS     read-only
   STATUS     mandatory
   DESCRIPTION
     "This variable provides the component's string name for
      use with the ASCII Console Interface"
::= { mscNmisFtpRowStatusEntry 2 }

mscNmisFtpStorageType OBJECT-TYPE
   SYNTAX     StorageType 
   ACCESS     read-only
   STATUS     mandatory
   DESCRIPTION
     "This variable represents the storage type value for the
      mscNmisFtp tables."
::= { mscNmisFtpRowStatusEntry 4 }

mscNmisFtpIndex OBJECT-TYPE
   SYNTAX     NonReplicated 
   ACCESS     not-accessible
   STATUS     mandatory
   DESCRIPTION
     "This variable represents the index for the mscNmisFtp tables."
::= { mscNmisFtpRowStatusEntry 10 }

mscNmisFtpStateTable OBJECT-TYPE
   SYNTAX     SEQUENCE OF MscNmisFtpStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscNmisFtp 10 }

mscNmisFtpStateEntry OBJECT-TYPE
   SYNTAX     MscNmisFtpStateEntry
   ACCESS     not-accessible
   STATUS     mandatory
   DESCRIPTION
     "An entry in the mscNmisFtpStateTable."
   INDEX {
      mscNmisIndex,
      mscNmisFtpIndex }
::= { mscNmisFtpStateTable 1 }

MscNmisFtpStateEntry ::= SEQUENCE {
   mscNmisFtpAdminState
      INTEGER,
   mscNmisFtpOperationalState
      INTEGER,
   mscNmisFtpUsageState
      INTEGER }

mscNmisFtpAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscNmisFtpStateEntry 1 }

mscNmisFtpOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscNmisFtpStateEntry 2 }

mscNmisFtpUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscNmisFtpStateEntry 3 }

mscNmisFtpOperTable OBJECT-TYPE
   SYNTAX     SEQUENCE OF MscNmisFtpOperEntry
   ACCESS     not-accessible
   STATUS     mandatory
   DESCRIPTION
     "This group contains the operational attributes for an NMIS 
      manager. This group is common to all NMIS managers."
::= { mscNmisFtp 11 }

mscNmisFtpOperEntry OBJECT-TYPE
   SYNTAX     MscNmisFtpOperEntry
   ACCESS     not-accessible
   STATUS     mandatory
   DESCRIPTION
     "An entry in the mscNmisFtpOperTable."
   INDEX {
      mscNmisIndex,
      mscNmisFtpIndex }
::= { mscNmisFtpOperTable 1 }

MscNmisFtpOperEntry ::= SEQUENCE {
   mscNmisFtpMaxAllowedSessions
      Unsigned32,
   mscNmisFtpActiveSessions
      Unsigned32 }

mscNmisFtpMaxAllowedSessions OBJECT-TYPE
   SYNTAX     Unsigned32 (2..35)
   ACCESS     read-only
   STATUS     mandatory
   DESCRIPTION
     "This attribute indicates the maximum number of simultaneous 
      sessions the manager will allow."
::= { mscNmisFtpOperEntry 1 }

mscNmisFtpActiveSessions OBJECT-TYPE
   SYNTAX     Unsigned32 (0..35)
   ACCESS     read-only
   STATUS     mandatory
   DESCRIPTION
     "This attribute indicates the number of simultaneous sessions 
      currently active under the manager. Note that there may be fewer  
      Session components than what is shown here, since an active 
      session could be in the midst of logging in and may not yet be fully 
      up."
::= { mscNmisFtpOperEntry 2 }


-- Nmis Ftp Session/n
-- This component supports a single remote FTP client logged in using 
-- the FTP protocol.

mscNmisFtpSession OBJECT IDENTIFIER ::= { mscNmisFtp 2 }



mscNmisFtpSessionRowStatusTable OBJECT-TYPE
   SYNTAX     SEQUENCE OF MscNmisFtpSessionRowStatusEntry
   ACCESS     not-accessible
   STATUS     mandatory
   DESCRIPTION
     "This entry controls the addition and deletion of 
      mscNmisFtpSession components."
::= { mscNmisFtpSession 1 }

mscNmisFtpSessionRowStatusEntry OBJECT-TYPE
   SYNTAX     MscNmisFtpSessionRowStatusEntry
   ACCESS     not-accessible
   STATUS     mandatory
   DESCRIPTION
     "A single entry in the table represents a single 
      mscNmisFtpSession component."
   INDEX {
      mscNmisIndex,
      mscNmisFtpIndex,
      mscNmisFtpSessionIndex }
::= { mscNmisFtpSessionRowStatusTable 1 }

MscNmisFtpSessionRowStatusEntry ::= SEQUENCE {
   mscNmisFtpSessionRowStatus
      RowStatus,
   mscNmisFtpSessionComponentName
      DisplayString,
   mscNmisFtpSessionStorageType
      StorageType,
   mscNmisFtpSessionIndex
      Integer32 }

mscNmisFtpSessionRowStatus OBJECT-TYPE
   SYNTAX     RowStatus 
   ACCESS     read-only
   STATUS     mandatory
   DESCRIPTION
     "This variable is used as the basis for SNMP naming of
      mscNmisFtpSession components.
      These components cannot be added nor deleted."
::= { mscNmisFtpSessionRowStatusEntry 1 }

mscNmisFtpSessionComponentName OBJECT-TYPE
   SYNTAX     DisplayString 
   ACCESS     read-only
   STATUS     mandatory
   DESCRIPTION
     "This variable provides the component's string name for
      use with the ASCII Console Interface"
::= { mscNmisFtpSessionRowStatusEntry 2 }

mscNmisFtpSessionStorageType OBJECT-TYPE
   SYNTAX     StorageType 
   ACCESS     read-only
   STATUS     mandatory
   DESCRIPTION
     "This variable represents the storage type value for the
      mscNmisFtpSession tables."
::= { mscNmisFtpSessionRowStatusEntry 4 }

mscNmisFtpSessionIndex OBJECT-TYPE
   SYNTAX     Integer32 (1..16)
   ACCESS     not-accessible
   STATUS     mandatory
   DESCRIPTION
     "This variable represents the index for the mscNmisFtpSession tables."
::= { mscNmisFtpSessionRowStatusEntry 10 }

mscNmisFtpSessionOperTable OBJECT-TYPE
   SYNTAX     SEQUENCE OF MscNmisFtpSessionOperEntry
   ACCESS     not-accessible
   STATUS     mandatory
   DESCRIPTION
     "This group contains the operational attributes for an FTP session."
::= { mscNmisFtpSession 10 }

mscNmisFtpSessionOperEntry OBJECT-TYPE
   SYNTAX     MscNmisFtpSessionOperEntry
   ACCESS     not-accessible
   STATUS     mandatory
   DESCRIPTION
     "An entry in the mscNmisFtpSessionOperTable."
   INDEX {
      mscNmisIndex,
      mscNmisFtpIndex,
      mscNmisFtpSessionIndex }
::= { mscNmisFtpSessionOperTable 1 }

MscNmisFtpSessionOperEntry ::= SEQUENCE {
   mscNmisFtpSessionUserid
      AsciiString,
   mscNmisFtpSessionRemoteIpAddr
      IpAddress,
   mscNmisFtpSessionRemoteTcpPort
      Unsigned32 }

mscNmisFtpSessionUserid OBJECT-TYPE
   SYNTAX     AsciiString (SIZE (8))
   ACCESS     read-only
   STATUS     mandatory
   DESCRIPTION
     "This attribute indicates the userid logged in to the session."
::= { mscNmisFtpSessionOperEntry 1 }

mscNmisFtpSessionRemoteIpAddr OBJECT-TYPE
   SYNTAX     IpAddress 
   ACCESS     read-only
   STATUS     mandatory
   DESCRIPTION
     "This attribute indicates the IP address of the remote device 
      connected to the session."
::= { mscNmisFtpSessionOperEntry 2 }

mscNmisFtpSessionRemoteTcpPort OBJECT-TYPE
   SYNTAX     Unsigned32 (0..65535)
   ACCESS     read-only
   STATUS     mandatory
   DESCRIPTION
     "This attribute indicates the TCP port number of the FTP control 
      connection being used on the remote device connected to the 
      session."
::= { mscNmisFtpSessionOperEntry 3 }


-- AccessControl
-- The AccessControl component performs security validation to 
-- restrict access to a Passport module. AccessControl ensures that 
-- only authorized remote devices can log in to the Network 
-- Management Interfaces for management purposes.
-- The AccessControl component is a placeholder to collect all the 
-- Userid and IpAccess components below it.

mscAc OBJECT IDENTIFIER ::= { mscComponents 18 }



mscAcRowStatusTable OBJECT-TYPE
   SYNTAX     SEQUENCE OF MscAcRowStatusEntry
   ACCESS     not-accessible
   STATUS     mandatory
   DESCRIPTION
     "This entry controls the addition and deletion of 
      mscAc components."
::= { mscAc 1 }

mscAcRowStatusEntry OBJECT-TYPE
   SYNTAX     MscAcRowStatusEntry
   ACCESS     not-accessible
   STATUS     mandatory
   DESCRIPTION
     "A single entry in the table represents a single 
      mscAc component."
   INDEX {
      mscAcIndex }
::= { mscAcRowStatusTable 1 }

MscAcRowStatusEntry ::= SEQUENCE {
   mscAcRowStatus
      RowStatus,
   mscAcComponentName
      DisplayString,
   mscAcStorageType
      StorageType,
   mscAcIndex
      NonReplicated }

mscAcRowStatus OBJECT-TYPE
   SYNTAX     RowStatus 
   ACCESS     read-write
   STATUS     mandatory
   DESCRIPTION
     "This variable is used as the basis for SNMP naming of
      mscAc components.
      These components can be added."
::= { mscAcRowStatusEntry 1 }

mscAcComponentName OBJECT-TYPE
   SYNTAX     DisplayString 
   ACCESS     read-only
   STATUS     mandatory
   DESCRIPTION
     "This variable provides the component's string name for
      use with the ASCII Console Interface"
::= { mscAcRowStatusEntry 2 }

mscAcStorageType OBJECT-TYPE
   SYNTAX     StorageType 
   ACCESS     read-only
   STATUS     mandatory
   DESCRIPTION
     "This variable represents the storage type value for the
      mscAc tables."
::= { mscAcRowStatusEntry 4 }

mscAcIndex OBJECT-TYPE
   SYNTAX     NonReplicated 
   ACCESS     not-accessible
   STATUS     mandatory
   DESCRIPTION
     "This variable represents the index for the mscAc tables."
::= { mscAcRowStatusEntry 10 }

mscAcProvTable OBJECT-TYPE
   SYNTAX     SEQUENCE OF MscAcProvEntry
   ACCESS     not-accessible
   STATUS     mandatory
   DESCRIPTION
     "This group contains the provisionable attributes which apply to the 
      overall access of the the node."
::= { mscAc 10 }

mscAcProvEntry OBJECT-TYPE
   SYNTAX     MscAcProvEntry
   ACCESS     not-accessible
   STATUS     mandatory
   DESCRIPTION
     "An entry in the mscAcProvTable."
   INDEX {
      mscAcIndex }
::= { mscAcProvTable 1 }

MscAcProvEntry ::= SEQUENCE {
   mscAcPublicKeyAuth
      OCTET STRING }

mscAcPublicKeyAuth OBJECT-TYPE
   SYNTAX     OCTET STRING (SIZE (1))
   ACCESS     read-write
   STATUS     mandatory
   DESCRIPTION
     "This attribute indicates whether Telnet sessions require a public key 
      exchange in order to log in to the node. FMIP sessions always 
      require a public key exchange for login authentication.

      Description of bits:
      telnet(0)"
::= { mscAcProvEntry 1 }


-- AccessControl Userid/<string>
-- The Userid component holds all provisionable attributes for a 
-- userid. Every Network Management Interface requires a user to 
-- supply a valid userid and password to log in, like most computer 
-- systems.
-- The instance value must be the userid string itself, consisting of 1-8 
-- alphanumeric (letters and numbers) characters. Letters in the userid 
-- string are case-insensitive.

mscAcUserid OBJECT IDENTIFIER ::= { mscAc 2 }



mscAcUseridRowStatusTable OBJECT-TYPE
   SYNTAX     SEQUENCE OF MscAcUseridRowStatusEntry
   ACCESS     not-accessible
   STATUS     mandatory
   DESCRIPTION
     "This entry controls the addition and deletion of 
      mscAcUserid components."
::= { mscAcUserid 1 }

mscAcUseridRowStatusEntry OBJECT-TYPE
   SYNTAX     MscAcUseridRowStatusEntry
   ACCESS     not-accessible
   STATUS     mandatory
   DESCRIPTION
     "A single entry in the table represents a single 
      mscAcUserid component."
   INDEX {
      mscAcIndex,
      mscAcUseridIndex }
::= { mscAcUseridRowStatusTable 1 }

MscAcUseridRowStatusEntry ::= SEQUENCE {
   mscAcUseridRowStatus
      RowStatus,
   mscAcUseridComponentName
      DisplayString,
   mscAcUseridStorageType
      StorageType,
   mscAcUseridIndex
      AsciiStringIndex }

mscAcUseridRowStatus OBJECT-TYPE
   SYNTAX     RowStatus 
   ACCESS     read-write
   STATUS     mandatory
   DESCRIPTION
     "This variable is used as the basis for SNMP naming of
      mscAcUserid components.
      These components can be added and deleted."
::= { mscAcUseridRowStatusEntry 1 }

mscAcUseridComponentName OBJECT-TYPE
   SYNTAX     DisplayString 
   ACCESS     read-only
   STATUS     mandatory
   DESCRIPTION
     "This variable provides the component's string name for
      use with the ASCII Console Interface"
::= { mscAcUseridRowStatusEntry 2 }

mscAcUseridStorageType OBJECT-TYPE
   SYNTAX     StorageType 
   ACCESS     read-only
   STATUS     mandatory
   DESCRIPTION
     "This variable represents the storage type value for the
      mscAcUserid tables."
::= { mscAcUseridRowStatusEntry 4 }

mscAcUseridIndex OBJECT-TYPE
   SYNTAX     AsciiStringIndex (SIZE (1..8))
   ACCESS     not-accessible
   STATUS     mandatory
   DESCRIPTION
     "This variable represents the index for the mscAcUserid tables."
::= { mscAcUseridRowStatusEntry 10 }

mscAcUseridProvTable OBJECT-TYPE
   SYNTAX     SEQUENCE OF MscAcUseridProvEntry
   ACCESS     not-accessible
   STATUS     mandatory
   DESCRIPTION
     "This group contains the provisionable attributes for a userid."
::= { mscAcUserid 10 }

mscAcUseridProvEntry OBJECT-TYPE
   SYNTAX     MscAcUseridProvEntry
   ACCESS     not-accessible
   STATUS     mandatory
   DESCRIPTION
     "An entry in the mscAcUseridProvTable."
   INDEX {
      mscAcIndex,
      mscAcUseridIndex }
::= { mscAcUseridProvTable 1 }

MscAcUseridProvEntry ::= SEQUENCE {
   mscAcUseridPassword
      AsciiString,
   mscAcUseridCustomerIdentifier
      Unsigned32,
   mscAcUseridCommandScope
      INTEGER,
   mscAcUseridCommandImpact
      INTEGER,
   mscAcUseridAllowedAccess
      OCTET STRING,
   mscAcUseridLoginDirectory
      AsciiString,
   mscAcUseridAllowedOutAccess
      OCTET STRING }

mscAcUseridPassword OBJECT-TYPE
   SYNTAX     AsciiString (SIZE (5..8))
   ACCESS     write-only
   STATUS     mandatory
   DESCRIPTION
     "This attribute holds the password for the userid. This is a write-only 
      attribute to provide additional security for passwords. The password 
      string consists of 5-8 characters, which may be any printable ASCII 
      characters. If the password string includes any non-alphanumeric 
      character, such as $ or *, the entire string must be enclosed in 
      double quotes. Letters in the password string are case-sensitive."
::= { mscAcUseridProvEntry 1 }

mscAcUseridCustomerIdentifier OBJECT-TYPE
   SYNTAX     Unsigned32 (0..8191)
   ACCESS     read-write
   STATUS     mandatory
   DESCRIPTION
     "This attribute indicates the Customer Identifier (CID) assigned to 
      the userid. The CID is used in Customer Network Management 
      (CNM). A CNM operator may only send commands to components 
      provisioned with the same CID as the operator. A CNM operator 
      will only receive event data, such as alarms, which is generated by 
      components provisioned with the same CID as the operator. 
      The special CID of 0 is reserved for the network owner, known as 
      the Netman. 
      The Passport CID attribute is compatible with DPN-100 Netman 
      and Basic CIDs."
   DEFVAL     { 0 }
::= { mscAcUseridProvEntry 2 }

mscAcUseridCommandScope OBJECT-TYPE
   SYNTAX     INTEGER  {
                 network(1),
                 device(2),
                 application(3) }
   ACCESS     read-write
   STATUS     mandatory
   DESCRIPTION
     "This attribute indicates the command scope assigned to the userid. 
      The scope determines the importance of the components on which 
      the userid will be allowed to execute commands. Scope has three 
      levels:
      
      1) Network scope implies the userid can manage components that 
      affect the operation of the entire network, such as trunks.
      2) Device scope implies the userid can manage components that 
      affect the operation of the entire Passport module, such as 
      processors or the file system.
      3) Application scope implies the userid can manage components 
      that affect the operation of a single application.
      
      Note that scope is hierarchical: A userid provisioned with network 
      scope can also manage components with a scope of device or 
      application."
   DEFVAL     { application }
::= { mscAcUseridProvEntry 3 }

mscAcUseridCommandImpact OBJECT-TYPE
   SYNTAX     INTEGER  {
                 debug(3),
                 systemAdministration(4),
                 configuration(5),
                 service(6),
                 passive(7) }
   ACCESS     read-write
   STATUS     mandatory
   DESCRIPTION
     "This attribute indicates the command impact assigned to the userid. 
      The impact determines the importance of the commands which the 
      userid will be allowed to execute. Impact has five levels:
      
      1) Debug impact implies the userid can issue all debugging 
      commands. Debug is the highest impact level.
      2) System Administration impact implies the userid can issue 
      provisioning commands on security components. This means the 
      userid can Add, Delete, Display, or Set the Userid and IpAccess 
      subcomponents of AccessControl.
      3) Configuration impact implies the userid can issue provisioning 
      commands to alter the provisioned configuration of the Passport 
      module, such as Start Prov, Add, Delete, and Set.
      4) Service impact implies the userid can issue operational 
      commands which may affect the service of running components, 
      such as Lock and Unlock.
      5) Passive impact implies the userid can only issue query 
      commands which display unrestricted information but otherwise do 
      not affect the operation or configuration of the Passport module. 
      Commands such as List and Display. Passive is the lowest impact 
      level.
      
      Note that impact is hierarchical: A userid provisioned with debug 
      impact can also issue all other commands at lower impact levels."
   DEFVAL     { passive }
::= { mscAcUseridProvEntry 4 }

mscAcUseridAllowedAccess OBJECT-TYPE
   SYNTAX     OCTET STRING (SIZE (1))
   ACCESS     read-write
   STATUS     mandatory
   DESCRIPTION
     "This attribute indicates the set of network management interfaces 
      through which the userid will be allowed incoming access to the 
      Passport. The allowedAccess attribute can be used to restrict a 
      userid to a desired subset of the network management interfaces 
      provided.

      Description of bits:
      local(0)
      telnet(1)
      fmip(2)
      ftp(3)"
   DEFVAL     { '80'H }
::= { mscAcUseridProvEntry 5 }

mscAcUseridLoginDirectory OBJECT-TYPE
   SYNTAX     AsciiString (SIZE (1..128))
   ACCESS     read-write
   STATUS     mandatory
   DESCRIPTION
     "This attribute is the login directory for file system commands or 
      FTP commands. The userid will initially be placed in this directory 
      upon logging in to Telnet, FMIP, Local or FTP.
      The default value of '/' is the root of the /sfs/ shadowed file system."
   DEFVAL     { '2f'H }  -- "/"
::= { mscAcUseridProvEntry 6 }

mscAcUseridAllowedOutAccess OBJECT-TYPE
   SYNTAX     OCTET STRING (SIZE (1))
   ACCESS     read-write
   STATUS     mandatory
   DESCRIPTION
     "This attribute indicates whether or not the userid will be allowed 
      outgoing Telnet access from the Passport.

      Description of bits:
      telnet(0)"
::= { mscAcUseridProvEntry 7 }


-- AccessControl IpAccess/<IP address>
-- This component represents a single "friendly" remote IP address 
-- which is permitted to call into the Telnet, FTP, or FMIP Interfaces 
-- on the Passport. All the friendly IP addresses must be provisioned 
-- as IpAccess components. The IpAccess components, taken together, 
-- form a complete list of all the IP addresses which are allowed 
-- access to the Passport's Network Management Interfaces. This set 
-- of friendly IP addresses excludes all other addresses, restricting 
-- access only to the friendly computers.
-- The instance value is the IP address itself, or an IP subnetwork 
-- address, entered in Internet   nnn.nnn.nnn.nnn   notation. An IP 
-- subnetwork address, in combination with the ipAddressMask 
-- attribute described below, may be provisioned to include an entire 
-- IP subnetwork into the friendly list with a single IpAccess 
-- component.
-- 
-- Note that with the introduction of Telnet client capability, the 
-- IpAccess lists must allow for the fact that Telnet access may now be 
-- from another Passport (or another type of node) in the network, not 
-- just management workstations.

mscAcIpAccess OBJECT IDENTIFIER ::= { mscAc 3 }



mscAcIpAccessRowStatusTable OBJECT-TYPE
   SYNTAX     SEQUENCE OF MscAcIpAccessRowStatusEntry
   ACCESS     not-accessible
   STATUS     mandatory
   DESCRIPTION
     "This entry controls the addition and deletion of 
      mscAcIpAccess components."
::= { mscAcIpAccess 1 }

mscAcIpAccessRowStatusEntry OBJECT-TYPE
   SYNTAX     MscAcIpAccessRowStatusEntry
   ACCESS     not-accessible
   STATUS     mandatory
   DESCRIPTION
     "A single entry in the table represents a single 
      mscAcIpAccess component."
   INDEX {
      mscAcIndex,
      mscAcIpAccessIndex }
::= { mscAcIpAccessRowStatusTable 1 }

MscAcIpAccessRowStatusEntry ::= SEQUENCE {
   mscAcIpAccessRowStatus
      RowStatus,
   mscAcIpAccessComponentName
      DisplayString,
   mscAcIpAccessStorageType
      StorageType,
   mscAcIpAccessIndex
      IpAddress }

mscAcIpAccessRowStatus OBJECT-TYPE
   SYNTAX     RowStatus 
   ACCESS     read-write
   STATUS     mandatory
   DESCRIPTION
     "This variable is used as the basis for SNMP naming of
      mscAcIpAccess components.
      These components can be added and deleted."
::= { mscAcIpAccessRowStatusEntry 1 }

mscAcIpAccessComponentName OBJECT-TYPE
   SYNTAX     DisplayString 
   ACCESS     read-only
   STATUS     mandatory
   DESCRIPTION
     "This variable provides the component's string name for
      use with the ASCII Console Interface"
::= { mscAcIpAccessRowStatusEntry 2 }

mscAcIpAccessStorageType OBJECT-TYPE
   SYNTAX     StorageType 
   ACCESS     read-only
   STATUS     mandatory
   DESCRIPTION
     "This variable represents the storage type value for the
      mscAcIpAccess tables."
::= { mscAcIpAccessRowStatusEntry 4 }

mscAcIpAccessIndex OBJECT-TYPE
   SYNTAX     IpAddress 
   ACCESS     not-accessible
   STATUS     mandatory
   DESCRIPTION
     "This variable represents the index for the mscAcIpAccess tables."
::= { mscAcIpAccessRowStatusEntry 10 }

mscAcIpAccessProvTable OBJECT-TYPE
   SYNTAX     SEQUENCE OF MscAcIpAccessProvEntry
   ACCESS     not-accessible
   STATUS     mandatory
   DESCRIPTION
     "This group contains the provisionable attributes for an IpAccess 
      component."
::= { mscAcIpAccess 10 }

mscAcIpAccessProvEntry OBJECT-TYPE
   SYNTAX     MscAcIpAccessProvEntry
   ACCESS     not-accessible
   STATUS     mandatory
   DESCRIPTION
     "An entry in the mscAcIpAccessProvTable."
   INDEX {
      mscAcIndex,
      mscAcIpAccessIndex }
::= { mscAcIpAccessProvTable 1 }

MscAcIpAccessProvEntry ::= SEQUENCE {
   mscAcIpAccessIpAddressMask
      IpAddress }

mscAcIpAccessIpAddressMask OBJECT-TYPE
   SYNTAX     IpAddress 
   ACCESS     read-write
   STATUS     mandatory
   DESCRIPTION
     "This attribute indicates the bit mask indicating the significant bits 
      which are used in the comparison of an incoming IP address against 
      the 'friendly' IP address in the instance value of the IpAccess 
      component. This bit mask is ANDed to the incoming IP address, 
      and ANDed to the instance value, before the comparison.
      
      An IP subnetwork address, in combination with this bit mask 
      attribute, may be provisioned to include an entire IP subnetwork 
      into the friendly IP address list with a single IpAccess component."
   DEFVAL     { 'ffffffff'H }  -- "255.255.255.255"
::= { mscAcIpAccessProvEntry 1 }




-- 
-- Version and Compliance statements
-- 



-- Object-Group Statement:
-- A list of all current accessible leaf objects.

-- OBJECTS { mscNmisLocalSessionStorageType,
--           mscAcUseridAllowedOutAccess,
--           mscNmisTelnetSessionScreenWidth,
--           mscNmisFmipActiveSessions,
--           mscNmisTelnetSessionComponentName,
--           mscNmisTelnetSessionDataStreams,
--           mscNmisFtpSessionRemoteIpAddr,
--           mscNmisFmipUsageState,
--           mscAcIpAccessComponentName,
--           mscNmisTelnetAdminState,
--           mscNmisFtpActiveSessions,
--           mscNmisFmipComponentName,
--           mscNmisFtpSessionStorageType,
--           mscNmisTelnetSessionClientRemoteIpAddr,
--           mscNmisTelnetRowStatus,
--           mscAcStorageType,
--           mscAcUseridComponentName,
--           mscNmisStorageType,
--           mscNmisTelnetSessionUserid,
--           mscNmisFmipSessionRemoteTcpPort,
--           mscNmisTelnetSessionClientStorageType,
--           mscNmisFmipOperationalState,
--           mscNmisLocalMaxAllowedSessions,
--           mscNmisTelnetActiveSessions,
--           mscAcUseridStorageType,
--           mscAcRowStatus,
--           mscNmisTelnetUsageState,
--           mscNmisTelnetSessionClientRemoteTcpPort,
--           mscNmisFtpOperationalState,
--           mscAcUseridCommandImpact,
--           mscNmisLocalStorageType,
--           mscNmisTelnetSessionStorageType,
--           mscNmisFtpMaxAllowedSessions,
--           mscNmisFtpSessionRowStatus,
--           mscNmisLocalSessionScreenWidth,
--           mscNmisFtpAdminState,
--           mscNmisLocalSessionComponentName,
--           mscNmisLocalSessionDataStreams,
--           mscAcComponentName,
--           mscAcUseridCommandScope,
--           mscNmisRowStatus,
--           mscNmisFtpStorageType,
--           mscNmisTelnetOperationalState,
--           mscNmisTelnetSessionRemoteIpAddr,
--           mscNmisLocalAdminState,
--           mscNmisFmipSessionStorageType,
--           mscAcPublicKeyAuth,
--           mscNmisFtpSessionComponentName,
--           mscNmisLocalRowStatus,
--           mscNmisFmipSessionRowStatus,
--           mscNmisFmipMaxAllowedSessions,
--           mscNmisLocalSessionUserid,
--           mscNmisFmipStorageType,
--           mscAcIpAccessStorageType,
--           mscNmisComponentName,
--           mscNmisTelnetComponentName,
--           mscNmisLocalActiveSessions,
--           mscNmisTelnetSessionClientComponentName,
--           mscNmisTelnetSessionRemoteTcpPort,
--           mscAcUseridPassword,
--           mscNmisLocalUsageState,
--           mscNmisFtpRowStatus,
--           mscAcIpAccessRowStatus,
--           mscNmisFmipSessionScreenWidth,
--           mscAcUseridRowStatus,
--           mscNmisLocalSessionRowStatus,
--           mscNmisLocalComponentName,
--           mscNmisFmipSessionComponentName,
--           mscNmisFmipSessionDataStreams,
--           mscAcUseridCustomerIdentifier,
--           mscAcUseridAllowedAccess,
--           mscNmisTelnetSessionClientRowStatus,
--           mscNmisLocalSessionHostCard,
--           mscNmisTelnetSessionRowStatus,
--           mscNmisTelnetMaxAllowedSessions,
--           mscNmisFmipAdminState,
--           mscNmisFtpUsageState,
--           mscAcIpAccessIpAddressMask,
--           mscNmisLocalOperationalState,
--           mscNmisFmipSessionRemoteIpAddr,
--           mscNmisFtpSessionUserid,
--           mscNmisFtpComponentName,
--           mscNmisTelnetStorageType,
--           mscNmisFmipRowStatus,
--           mscNmisFtpSessionRemoteTcpPort,
--           mscNmisTelnetSessionClientVirtualRouter,
--           mscNmisFmipSessionUserid,
--           mscAcUseridLoginDirectory }
-- STATUS  mandatory
-- DESCRIPTION
--   "A list of all current accessible leaf objects."

mgmtInterfacesGroup OBJECT IDENTIFIER ::= { mgmtInterfacesMIB 1 }
mgmtInterfacesGroupCA OBJECT IDENTIFIER ::= { mgmtInterfacesGroup 1 }
mgmtInterfacesGroupCA02 OBJECT IDENTIFIER ::= { mgmtInterfacesGroupCA 3 }
mgmtInterfacesGroupCA02A OBJECT IDENTIFIER ::= { mgmtInterfacesGroupCA02 2 }



-- Agent-Capabilities Statement:

-- PRODUCT-RELEASE "MscPassport Release 1.2 MgmtInterfaces."
-- STATUS          mandatory
-- DESCRIPTION     "Carrier Passport MgmtInterfaces MIB: MIB Version CA02A,
--                  Software Version CA02S9C."
-- SUPPORTS        Nortel-MsCarrier-MscPassport-MgmtInterfacesMIB
--    INCLUDES     { mgmtInterfacesGroupCA02A }

mgmtInterfacesCapabilities OBJECT IDENTIFIER ::= { mgmtInterfacesMIB 3 }
mgmtInterfacesCapabilitiesCA OBJECT IDENTIFIER ::= { mgmtInterfacesCapabilities 1 }
mgmtInterfacesCapabilitiesCA02 OBJECT IDENTIFIER ::= { mgmtInterfacesCapabilitiesCA 3 }
mgmtInterfacesCapabilitiesCA02A OBJECT IDENTIFIER ::= { mgmtInterfacesCapabilitiesCA02 2 }





END
