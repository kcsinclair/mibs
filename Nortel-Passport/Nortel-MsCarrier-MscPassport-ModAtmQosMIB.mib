Nortel-MsCarrier-MscPassport-ModAtmQosMIB
DEFINITIONS ::= BEGIN



IMPORTS

      OBJECT-TYPE
   FROM RFC-1212

      mscPassportMIBs
   FROM Nortel-MsCarrier-MscPassport-UsefulDefinitionsMIB

      DisplayString,
      StorageType,
      RowStatus,
      Integer32,
      Unsigned32
   FROM Nortel-MsCarrier-MscPassport-StandardTextualConventionsMIB

      NonReplicated
   FROM Nortel-MsCarrier-MscPassport-TextualConventionsMIB

      mscModFrsIndex,
      mscModFrs
   FROM Nortel-MsCarrier-MscPassport-ModCommonMIB

      mscModIndex
   FROM Nortel-MsCarrier-MscPassport-BaseShelfMIB;




-- LAST-UPDATED   "9909010000Z"
-- ORGANIZATION   "Nortel Networks"
-- CONTACT-INFO   "
--         Nortel Carrier Data Network Management
--         
--         Postal:       P.O. Box 3511, Station C 
--                       Ottawa, Ontario 
--                       Canada  K1Y 4H7
--         
--         via the WEB:  http://www.nortelnetworks.com  
--                       select 'Contact Us' from the menu
--          
--         via phone:    1-800-4NORTEL"
-- DESCRIPTION
--    "The module describing the Nortel MsCarrier MscPassport
--     ModAtmQos Enterprise MIB."

modAtmQosMIB OBJECT IDENTIFIER ::= { mscPassportMIBs 75 }










-- Mod Frs AtmNetworking
-- AtmNetworking is used to define a number of general characteristics 
-- for all Frame Relay to ATM interworking on module. All the 
-- modules in the network should have identical AtmNetworking 
-- attributes. If these attributes are not consistent across the network, 
-- then the service may be degraded. 

mscModFrsAtmNet OBJECT IDENTIFIER ::= { mscModFrs 2 }



mscModFrsAtmNetRowStatusTable OBJECT-TYPE
   SYNTAX     SEQUENCE OF MscModFrsAtmNetRowStatusEntry
   ACCESS     not-accessible
   STATUS     mandatory
   DESCRIPTION
     "This entry controls the addition and deletion of 
      mscModFrsAtmNet components."
::= { mscModFrsAtmNet 1 }

mscModFrsAtmNetRowStatusEntry OBJECT-TYPE
   SYNTAX     MscModFrsAtmNetRowStatusEntry
   ACCESS     not-accessible
   STATUS     mandatory
   DESCRIPTION
     "A single entry in the table represents a single 
      mscModFrsAtmNet component."
   INDEX {
      mscModIndex,
      mscModFrsIndex,
      mscModFrsAtmNetIndex }
::= { mscModFrsAtmNetRowStatusTable 1 }

MscModFrsAtmNetRowStatusEntry ::= SEQUENCE {
   mscModFrsAtmNetRowStatus
      RowStatus,
   mscModFrsAtmNetComponentName
      DisplayString,
   mscModFrsAtmNetStorageType
      StorageType,
   mscModFrsAtmNetIndex
      NonReplicated }

mscModFrsAtmNetRowStatus OBJECT-TYPE
   SYNTAX     RowStatus 
   ACCESS     read-only
   STATUS     mandatory
   DESCRIPTION
     "This variable is used as the basis for SNMP naming of
      mscModFrsAtmNet components.
      These components cannot be added nor deleted."
::= { mscModFrsAtmNetRowStatusEntry 1 }

mscModFrsAtmNetComponentName OBJECT-TYPE
   SYNTAX     DisplayString 
   ACCESS     read-only
   STATUS     mandatory
   DESCRIPTION
     "This variable provides the component's string name for
      use with the ASCII Console Interface"
::= { mscModFrsAtmNetRowStatusEntry 2 }

mscModFrsAtmNetStorageType OBJECT-TYPE
   SYNTAX     StorageType 
   ACCESS     read-only
   STATUS     mandatory
   DESCRIPTION
     "This variable represents the storage type value for the
      mscModFrsAtmNet tables."
::= { mscModFrsAtmNetRowStatusEntry 4 }

mscModFrsAtmNetIndex OBJECT-TYPE
   SYNTAX     NonReplicated 
   ACCESS     not-accessible
   STATUS     mandatory
   DESCRIPTION
     "This variable represents the index for the mscModFrsAtmNet tables."
::= { mscModFrsAtmNetRowStatusEntry 10 }

mscModFrsAtmNetProvTable OBJECT-TYPE
   SYNTAX     SEQUENCE OF MscModFrsAtmNetProvEntry
   ACCESS     not-accessible
   STATUS     mandatory
   DESCRIPTION
     "This group contains information related to the Frame Relay to ATM 
      interworking."
::= { mscModFrsAtmNet 10 }

mscModFrsAtmNetProvEntry OBJECT-TYPE
   SYNTAX     MscModFrsAtmNetProvEntry
   ACCESS     not-accessible
   STATUS     mandatory
   DESCRIPTION
     "An entry in the mscModFrsAtmNetProvTable."
   INDEX {
      mscModIndex,
      mscModFrsIndex,
      mscModFrsAtmNetIndex }
::= { mscModFrsAtmNetProvTable 1 }

MscModFrsAtmNetProvEntry ::= SEQUENCE {
   mscModFrsAtmNetRetryTimerPeriod
      Unsigned32 }

mscModFrsAtmNetRetryTimerPeriod OBJECT-TYPE
   SYNTAX     Unsigned32 (30..300)
   ACCESS     read-write
   STATUS     mandatory
   DESCRIPTION
     "This attribute specifies the module wide retry timer interval for 
      failed SPVC calls using Frame Relay to ATM Networking. Changes 
      to this attribute will take effect on subsequent call setups."
   DEFVAL     { 60 }
::= { mscModFrsAtmNetProvEntry 1 }


-- Mod Frs AtmNet TransferPriorityMapping/n
-- This component specifies call setup parameters for Frame Relay to 
-- ATM interworking using transfer priority n. The changed 
-- parameters will take effect on new calls.
-- 
-- Some attributes can be overidden on per interface basis by FrAtm 
-- Ca Tpm component.

mscModFrsAtmNetTpm OBJECT IDENTIFIER ::= { mscModFrsAtmNet 2 }



mscModFrsAtmNetTpmRowStatusTable OBJECT-TYPE
   SYNTAX     SEQUENCE OF MscModFrsAtmNetTpmRowStatusEntry
   ACCESS     not-accessible
   STATUS     mandatory
   DESCRIPTION
     "This entry controls the addition and deletion of 
      mscModFrsAtmNetTpm components."
::= { mscModFrsAtmNetTpm 1 }

mscModFrsAtmNetTpmRowStatusEntry OBJECT-TYPE
   SYNTAX     MscModFrsAtmNetTpmRowStatusEntry
   ACCESS     not-accessible
   STATUS     mandatory
   DESCRIPTION
     "A single entry in the table represents a single 
      mscModFrsAtmNetTpm component."
   INDEX {
      mscModIndex,
      mscModFrsIndex,
      mscModFrsAtmNetIndex,
      mscModFrsAtmNetTpmIndex }
::= { mscModFrsAtmNetTpmRowStatusTable 1 }

MscModFrsAtmNetTpmRowStatusEntry ::= SEQUENCE {
   mscModFrsAtmNetTpmRowStatus
      RowStatus,
   mscModFrsAtmNetTpmComponentName
      DisplayString,
   mscModFrsAtmNetTpmStorageType
      StorageType,
   mscModFrsAtmNetTpmIndex
      Integer32 }

mscModFrsAtmNetTpmRowStatus OBJECT-TYPE
   SYNTAX     RowStatus 
   ACCESS     read-write
   STATUS     mandatory
   DESCRIPTION
     "This variable is used as the basis for SNMP naming of
      mscModFrsAtmNetTpm components.
      These components can be added."
::= { mscModFrsAtmNetTpmRowStatusEntry 1 }

mscModFrsAtmNetTpmComponentName OBJECT-TYPE
   SYNTAX     DisplayString 
   ACCESS     read-only
   STATUS     mandatory
   DESCRIPTION
     "This variable provides the component's string name for
      use with the ASCII Console Interface"
::= { mscModFrsAtmNetTpmRowStatusEntry 2 }

mscModFrsAtmNetTpmStorageType OBJECT-TYPE
   SYNTAX     StorageType 
   ACCESS     read-only
   STATUS     mandatory
   DESCRIPTION
     "This variable represents the storage type value for the
      mscModFrsAtmNetTpm tables."
::= { mscModFrsAtmNetTpmRowStatusEntry 4 }

mscModFrsAtmNetTpmIndex OBJECT-TYPE
   SYNTAX     Integer32 (0..15)
   ACCESS     not-accessible
   STATUS     mandatory
   DESCRIPTION
     "This variable represents the index for the mscModFrsAtmNetTpm tables."
::= { mscModFrsAtmNetTpmRowStatusEntry 10 }

mscModFrsAtmNetTpmProvTable OBJECT-TYPE
   SYNTAX     SEQUENCE OF MscModFrsAtmNetTpmProvEntry
   ACCESS     not-accessible
   STATUS     mandatory
   DESCRIPTION
     "This group specifies the mapping from Frame Relay parameters to 
      ATM parameters for a Frame Relay using the defined transfer 
      priority."
::= { mscModFrsAtmNetTpm 2 }

mscModFrsAtmNetTpmProvEntry OBJECT-TYPE
   SYNTAX     MscModFrsAtmNetTpmProvEntry
   ACCESS     not-accessible
   STATUS     mandatory
   DESCRIPTION
     "An entry in the mscModFrsAtmNetTpmProvTable."
   INDEX {
      mscModIndex,
      mscModFrsIndex,
      mscModFrsAtmNetIndex,
      mscModFrsAtmNetTpmIndex }
::= { mscModFrsAtmNetTpmProvTable 1 }

MscModFrsAtmNetTpmProvEntry ::= SEQUENCE {
   mscModFrsAtmNetTpmEmissionPriority
      Unsigned32,
   mscModFrsAtmNetTpmAtmServiceCategory
      INTEGER,
   mscModFrsAtmNetTpmAvgFrameSize
      Unsigned32,
   mscModFrsAtmNetTpmTrafficParmConversionPolicy
      INTEGER,
   mscModFrsAtmNetTpmAssignedBandwidthPool
      INTEGER }

mscModFrsAtmNetTpmEmissionPriority OBJECT-TYPE
   SYNTAX     Unsigned32 (0..3)
   ACCESS     read-write
   STATUS     mandatory
   DESCRIPTION
     "This attribute specifies the egress emission priority at the FR to 
      ATM interface. A value of 3 specifies the highest priority, whereas a 
      value of 0 specifies the lowest priority."
   DEFVAL     { 0 }
::= { mscModFrsAtmNetTpmProvEntry 1 }

mscModFrsAtmNetTpmAtmServiceCategory OBJECT-TYPE
   SYNTAX     INTEGER  {
                 ubr(0),
                 cbr(1),
                 rtVbr(2),
                 nrtVbr(3) }
   ACCESS     read-write
   STATUS     mandatory
   DESCRIPTION
     "This attribute specifies the ATM class of service value to be used on 
      a transport connection."
   DEFVAL     { nrtVbr }
::= { mscModFrsAtmNetTpmProvEntry 2 }

mscModFrsAtmNetTpmAvgFrameSize OBJECT-TYPE
   SYNTAX     Unsigned32 (1..8187)
   ACCESS     read-write
   STATUS     mandatory
   DESCRIPTION
     "This attribute specifies the average frame size that is used in the 
      traffic parameter conversion policy calculations for this transfer 
      priority to determine the overhead factor for FR to ATM 
      interworking. The overhead factor affects the granularity of the 
      bandwidth requirements. The values should be identical across the 
      network. Otherwise, there may result in bandwidth conversion 
      inconsistencies."
   DEFVAL     { 128 }
::= { mscModFrsAtmNetTpmProvEntry 3 }

mscModFrsAtmNetTpmTrafficParmConversionPolicy OBJECT-TYPE
   SYNTAX     INTEGER  {
                 n3(3),
                 n4(4),
                 n5(5),
                 n6(6) }
   ACCESS     read-write
   STATUS     mandatory
   DESCRIPTION
     "This attribute specifies the traffic parameter conversion policy to use 
      for this transfer priority to specify the equivalent bandwidth rate at 
      the FrAtm interface. 
      
      Policy 3 characterizes the traffic in the following way:
      - ATM traffic descriptor type 6 is selected
      - PCR0+1 is based on the AR
      - SCR0+1 is based on the CIR and EIR
      - MBS0+1 is based on Bc,Be,CIR,EIR and AR
      - Takes into account that the instananeous rate of the frame relay 
      stream can burst above CIR and up tp the AR.
      
      Policy 4 characterizes the traffic in the following way:
      - ATM traffic descriptor type 7 or 8 is selected. Type 7 is chosen 
      when non-conforming cells are to be discarded and type 8 when 
      non-conforming cells are tagged by UPC traffic policer.
      - PCR0+1 is based on the AR
      - SCR0 is based on the CIR
      - MBS0 is based on Bc,CIR and AR
      - There is no direct characterization of EIR. The allowed EIR can be 
      derived using the difference between the AR and CIR.
      
      Policy 5 characterizes the traffic in the following way:
      - ATM traffic descriptor type 7 or 8 is selected . Type 7 is chosen 
      when non-conforming cells are to be discarded and type 8 when 
      non-conforming cells are tagged by UPC traffic policer
      - PCR0+1 is based on CIR and EIR
      - SCR0 is based on the CIR
      - MBS0 is based on the Bc,CIR and AR
      - The maximum PCR is no longer based on AR but based on the 
      CIR and EIR.
      
      Policy 6 characterizes the traffic in the following way:
      - ATM traffic descriptor type 3 is selected
      - PCR0+1 is based only on CIR."
   DEFVAL     { n6 }
::= { mscModFrsAtmNetTpmProvEntry 4 }

mscModFrsAtmNetTpmAssignedBandwidthPool OBJECT-TYPE
   SYNTAX     INTEGER  {
                 n0(0),
                 n1(1),
                 n2(2),
                 n3(3),
                 n4(4),
                 n5(5),
                 n6(6),
                 n7(7),
                 n8(8),
                 n9(9),
                 n10(10),
                 n11(11),
                 n12(12),
                 n13(13),
                 n14(14),
                 n15(15) }
   ACCESS     read-write
   STATUS     mandatory
   DESCRIPTION
     "This attribute specifies the bandwidth pool which is used to support 
      this transfer priority. The bandwidth pool is defined in the frAtm Ca 
      component."
   DEFVAL     { n0 }
::= { mscModFrsAtmNetTpmProvEntry 5 }




-- 
-- Version and Compliance statements
-- 



-- Object-Group Statement:
-- A list of all current accessible leaf objects.

-- OBJECTS { mscModFrsAtmNetTpmAssignedBandwidthPool,
--           mscModFrsAtmNetTpmAtmServiceCategory,
--           mscModFrsAtmNetTpmTrafficParmConversionPolicy,
--           mscModFrsAtmNetTpmComponentName,
--           mscModFrsAtmNetComponentName,
--           mscModFrsAtmNetTpmStorageType,
--           mscModFrsAtmNetTpmRowStatus,
--           mscModFrsAtmNetStorageType,
--           mscModFrsAtmNetRowStatus,
--           mscModFrsAtmNetTpmAvgFrameSize,
--           mscModFrsAtmNetRetryTimerPeriod,
--           mscModFrsAtmNetTpmEmissionPriority }
-- STATUS  mandatory
-- DESCRIPTION
--   "A list of all current accessible leaf objects."

modAtmQosGroup OBJECT IDENTIFIER ::= { modAtmQosMIB 1 }
modAtmQosGroupCA OBJECT IDENTIFIER ::= { modAtmQosGroup 1 }
modAtmQosGroupCA02 OBJECT IDENTIFIER ::= { modAtmQosGroupCA 3 }
modAtmQosGroupCA02A OBJECT IDENTIFIER ::= { modAtmQosGroupCA02 2 }



-- Agent-Capabilities Statement:

-- PRODUCT-RELEASE "MscPassport Release 1.2 ModAtmQos."
-- STATUS          mandatory
-- DESCRIPTION     "Carrier Passport ModAtmQos MIB: MIB Version CA02A,
--                  Software Version CA02S9C."
-- SUPPORTS        Nortel-MsCarrier-MscPassport-ModAtmQosMIB
--    INCLUDES     { modAtmQosGroupCA02A }

modAtmQosCapabilities OBJECT IDENTIFIER ::= { modAtmQosMIB 3 }
modAtmQosCapabilitiesCA OBJECT IDENTIFIER ::= { modAtmQosCapabilities 1 }
modAtmQosCapabilitiesCA02 OBJECT IDENTIFIER ::= { modAtmQosCapabilitiesCA 3 }
modAtmQosCapabilitiesCA02A OBJECT IDENTIFIER ::= { modAtmQosCapabilitiesCA02 2 }





END
