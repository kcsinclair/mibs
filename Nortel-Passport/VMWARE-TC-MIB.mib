-- **********************************************************
-- Copyright 2007 VMware, Inc.  All rights reserved.
-- **********************************************************

VMWARE-TC-MIB DEFINITIONS ::= BEGIN

    IMPORTS
        MODULE-IDENTITY
    FROM SNMPv2-SMI
        TEXTUAL-CONVENTION
    FROM SNMPv2-TC
        vmwSystem
    FROM VMWARE-ROOT-MIB;

    vmwTcMIB MODULE-IDENTITY
    LAST-UPDATED "200909050000Z"
    ORGANIZATION "VMware, Inc"
    CONTACT-INFO
    "VMware, Inc
    3401 Hillview Ave
    Palo Alto, CA 94304
    Tel: 1-877-486-9273 or 650-427-5000
    Fax: 650-427-5001
    Web: http://communities.vmware.com/community/developer/forums/managementapi
    "
DESCRIPTION
    "This MIB module provides common datatypes for use in VMWARE
     enterprise mib modules"
REVISION      "200909050000Z"
DESCRIPTION
    "Added VmwLongDisplayString"
REVISION      "200712270000Z"
DESCRIPTION
    "This is the first revision."
::= { vmwSystem 11 }

VmwSubsystemTypes ::= TEXTUAL-CONVENTION
    STATUS       current
    DESCRIPTION
            "Define the various hardware subsystems."
    SYNTAX   INTEGER { unknown(1), chassis(2), powerSupply(3), fan(4), cpu(5),
                       memory(6), battery(7), temperatureSensor(8),
                       raidController(9), voltage(10)
                     }

VmwCIMAlertTypes ::= TEXTUAL-CONVENTION
    STATUS       current
    DESCRIPTION
            "Primary classifications for alert messages."
    SYNTAX   INTEGER { other(1), communications(2), qos(3), processingError(4),
                       deviceAlert(5), environmentalAlert(6), modelChange(7),
                       securityAlert(8)
                     }

VmwCIMAlertFormat ::= TEXTUAL-CONVENTION
    STATUS       current
    DESCRIPTION
            "Indication of what the Alerting Managed Element property is."
    SYNTAX  INTEGER { unknown(0), other(1), cimObjectPath(2) }

VmwSubsystemStatus ::= TEXTUAL-CONVENTION
    STATUS       current
    DESCRIPTION
            "Define the state of a given subsystem if known."
    SYNTAX  INTEGER { unknown(1), normal(2), marginal(3), critical(4), failed(5) }

VmwCIMSeverity ::= TEXTUAL-CONVENTION
    STATUS       current
    DESCRIPTION
            "Recommendation.ITU|X733.Perceived severity possible values."
    SYNTAX  INTEGER { unknown(0), other(1), information(2), warning(3), minor(4), major(5), critical(6), fatal(7) }

VmwCimName ::= TEXTUAL-CONVENTION
    DISPLAY-HINT "256a"
    STATUS       current
    DESCRIPTION
            "Contains a name of no more than 256 characters."
    SYNTAX  OCTET STRING (SIZE (0..256))

VmwConnectedState ::= TEXTUAL-CONVENTION
    DISPLAY-HINT "7a"
    STATUS       current
    DESCRIPTION
            "Can hold one of the following values: 'true' or 'false' or 'unknown'."
    SYNTAX  OCTET STRING (SIZE (7))

VmwLongDisplayString ::= TEXTUAL-CONVENTION
    DISPLAY-HINT "1a"
    STATUS       current
    DESCRIPTION
            "Represents textual information taken from the NVT ASCII
            character set, as defined in pages 4, 10-11 of RFC 854.

            To summarize RFC 854, the NVT ASCII repertoire specifies:

              - the use of character codes 0-127 (decimal)

              - the graphics characters (32-126) are interpreted as
                US ASCII

              - NUL, LF, CR, BEL, BS, HT, VT and FF have the special
                meanings specified in RFC 854

              - the other 25 codes have no standard interpretation

              - the sequence 'CR LF' means newline

              - the sequence 'CR NUL' means carriage-return

              - an 'LF' not preceded by a 'CR' means moving to the
                same column on the next line.

              - the sequence 'CR x' for any x other than LF or NUL is
                illegal.  (Note that this also means that a string may
                end with either 'CR LF' or 'CR NUL', but not with CR.)

            An object defined using this syntax may be of indefinite
            length, as specified by the protocol, but displays may
            choose to display only the first 4096 characters."
    SYNTAX       OCTET STRING

VmwLongSnmpAdminString ::= TEXTUAL-CONVENTION
    DISPLAY-HINT "4096t"
    STATUS       current
    DESCRIPTION "This TC adapted from SnmpAdminString from SNMP-FRAMEWORK-MIB An
                 octet string containing administrative information, preferably
                 in human-readable form.

                 To facilitate internationalization, this
                 information is represented using the ISO/IEC
                 IS 10646-1 character set, encoded as an octet
                 string using the UTF-8 transformation format
                 described in [RFC2279].

                 Since additional code points are added by
                 amendments to the 10646 standard from time
                 to time, implementations must be prepared to
                 encounter any code point from 0x00000000 to
                 0x7fffffff.  Byte sequences that do not
                 correspond to the valid UTF-8 encoding of a
                 code point or are outside this range are
                 prohibited.

                 The use of control codes should be avoided.

                 When it is necessary to represent a newline,
                 the control code sequence CR LF should be used.

                 The use of leading or trailing white space should
                 be avoided.

                 For code points not directly supported by user
                 interface hardware or software, an alternative
                 means of entry and display, such as hexadecimal,
                 may be provided.

                 For information encoded in 7-bit US-ASCII,
                 the UTF-8 encoding is identical to the
                 US-ASCII encoding.

                 UTF-8 may require multiple bytes to represent a
                 single character / code point; thus the length
                 of this object in octets may be different from
                 the number of characters encoded.  Similarly,
                 size constraints refer to the number of encoded
                 octets, not the number of characters represented
                 by an encoding.

                 Note that when this TC is used for an object that
                 is used or envisioned to be used as an index, then
                 a SIZE restriction MUST be specified so that the
                 number of sub-identifiers for any object instance
                 does not exceed the limit of 128, as defined by
                 [RFC3416].

                 Note that the size of an SnmpAdminString object is
                 measured in octets, not characters."

    SYNTAX       OCTET STRING

END
