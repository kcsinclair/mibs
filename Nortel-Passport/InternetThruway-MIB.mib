InternetThruway-MIB DEFINITIONS ::= BEGIN

          --  Nortel's Internet Thruway MIB 

          IMPORTS
                  enterprises    FROM RFC1155-SMI
                  DisplayString  FROM RFC1213-MIB
                  OBJECT-TYPE    FROM RFC-1212
                  TRAP-TYPE      FROM RFC-1215
		  IpAddress	 FROM RFC1155-SMI
		  Gauge		 FROM RFC1155-SMI;

          --   csg        - is for Internet Thruway Controller
          --   Components - represent the Variables for the CSG
          --                software components.

          nortel                OBJECT IDENTIFIER ::= { enterprises 562 }
          dialaccess            OBJECT IDENTIFIER ::= { nortel 14 }
          csg                   OBJECT IDENTIFIER ::= { dialaccess 2 }

          system                OBJECT IDENTIFIER ::= { csg 1 }
          components            OBJECT IDENTIFIER ::= { csg 2 }
          traps                 OBJECT IDENTIFIER ::= { csg 3 }
          alarms                OBJECT IDENTIFIER ::= { csg 4 }
          ncServer              OBJECT IDENTIFIER ::= { csg 5 }
	  ss7                   OBJECT IDENTIFIER ::= { csg 6 }
          omData                OBJECT IDENTIFIER ::= { csg 7 }

          disk                  OBJECT IDENTIFIER ::= { system 1 }

          linkOMs                OBJECT IDENTIFIER ::= { omData 1 }
          maintenanceOMs         OBJECT IDENTIFIER ::= { omData 2 }
          callOMs                OBJECT IDENTIFIER ::= { omData 3 }
          trunkGroupOMs          OBJECT IDENTIFIER ::= { omData 4 }
          phoneNumberOMs         OBJECT IDENTIFIER ::= { omData 5 }
          systemOMs              OBJECT IDENTIFIER ::= { omData 6 }
          nasOMs                 OBJECT IDENTIFIER ::= { omData 7 }
          

-- **NOTE** This enum indicates the possible events that can occur.
--          It is included here as comments for reference by the 
--          customers to this MIB.
--          The real code can be found in survman_include.hxx and this
--          comment block should be updated accordingly when the code
--          is modified.
--
-- These are the keys describing the events that have occured.
--
--typedef enum
--{
--  PARTITION_SPACE_KEY=1,      //  Disk Space issue
--  COMP_PROV_STATE_KEY,        //  Component not in provisioned state
--  COMP_DEBUG_KEY,             //  Debug Turned on for component X
--  HG_STATUS_KEY,              //  Home Gateway failure
--  NAS_STATUS_KEY,             //  Indicates nas failure
--  COMP_RESTART_ALARM_KEY,     //  Component has had excess restarts - alarm
--  SS7_MTP2_TRUNK_FAILURE_KEY, //  MTP2 trunk failure encountered
--  SS7_MTP3_CONGESTION_KEY,    //  MTP3 congestion encountered
--  SS7_LINK_FAILURE_KEY,       //  SS7 link failure
--  SS7_LINK_CONGESTION_KEY,    //  SS7 link congested
--  SS7_ISUP_FAILURE_KEY,       //  ISUP protocol stack failed
--  SS7_ISUP_CONGESTION_KEY,    //  ISUP protocol stack congested
--  SS7_FEP_CONGESTION_KEY,     //  Congestion in SS7's front end process
--  SS7_BEP_CONGESTION_KEY,     //  Congestion in SS7's back end process
--  PEER_STATUS_KEY,            //  Lost/Found Server
--  STATE_CHANGE_KEY,           //  State change occured
--  SS7_LINKSET_FAILURE_KEY,    //  SS7 linkset failure
--  SS7_DEST_INACCESSIBLE_KEY,  //  SS7 signalling destination inaccessible
--  SS7_DEST_CONGESTION_KEY,    //  SS7 signalling destination congested
--  SS7_LINK_ALIGN_FAILURE_KEY, //  SS7 link alignment failure
-- 
--  // Start of GENERIC keys
--  //
--  FILE_DELETE_KEY,            //  Warning file about to be deleted
--  NAS_REG_FAIL_KEY,           //  Indicates invalid registration attempt
--  BACKUP_INDICATION_KEY,      //  Backup reminder message
--  COMP_RESTART_KEY,           //  A component has restarted once
--  SYSMAN_RESTART_KEY,         //  Sysman indicated a restart has taken place
--  HG_NAS_CONFIG_MISMATCH_KEY, //  Sysman indicated a restart has taken place
--
--  MAX_EVENT_KEY               //  Highest event number.
--} event_key_name_t;


----------------------------------
------  Data Types           -----
----------------------------------

  TimeString ::= DisplayString
      
      --     format convention     
      --     Octets       Contents       Range
             ------       --------       -----
      --      1-4           Year         (0000 - 9999) 
      --      5             ' '          delimiter
      --      6-7           month        (01-12)
      --      8             ' '          delimiter
      --      9-10          day          (01-31)
      --      11            ' '          delimiter
      --      12-13         hour         (00-23)
      --      14            ' '          delimiter
      --      15-16         minutes      (00-59)
      --      17            ' '          delimiter
      --      18-19         seconds      (00-59)
      --      20            ' '          delimiter
      --      21            'Z'          Zulu time indicator

     
----------------------------------
--     Informational Tables     --
----------------------------------

  --------------------------------------------------------------------
  --
  -- The following section contains definitions of tables used
  -- to store information related to the operation of the CSG:
  -- for example, component and partition information, high-
  -- availability information, and SS7 linkset information.
  --
  -- Tables which store alarm information are defined in a 
  -- subsequent section of the MIB.
  --
  --------------------------------------------------------------------

  --------------------------------------------------------------------
  -- The following dynamic table is used for the Disk Partitions.
  --------------------------------------------------------------------
  -- 
  partitionTable OBJECT-TYPE
        SYNTAX SEQUENCE OF PartitionTableEntry
        ACCESS  not-accessible 
        STATUS  mandatory
        DESCRIPTION
          "The PartitionTable contains information about each disk
           partition on the CSG"
        ::= { disk 1}

  partitionTableEntry OBJECT-TYPE
        SYNTAX PartitionTableEntry
        ACCESS  not-accessible
        STATUS  mandatory
        DESCRIPTION
          "An entry in the PartitionTable. Indexed by partitionIndex"
        INDEX {partitionIndex}
        ::= {partitionTable 1}

  -- definition of PartitionSpaceStatus type
  PartitionSpaceStatus ::= INTEGER { spaceAlarmOff(1), spaceAlarmOn(2) }

  -- definition of PartitionTableEntry
  PartitionTableEntry ::= SEQUENCE {
        partitionIndex          INTEGER,
        partitionName           DisplayString,
        partitionPercentFull    INTEGER,
        partitionMegsFree       INTEGER,
        partitionSpaceStatus    PartitionSpaceStatus,
        partitionSpaceKey       INTEGER,
        partitionSpaceTimeStamp TimeString
      }
  
  partitionIndex OBJECT-TYPE
        SYNTAX INTEGER (1..4) 
        ACCESS not-accessible
        STATUS mandatory
        DESCRIPTION
          "Identifies partition number."
        ::={partitionTableEntry 1}
 
  partitionName OBJECT-TYPE
        SYNTAX DisplayString  
        ACCESS read-only
        STATUS mandatory
        DESCRIPTION
          "Identifies partition name."
        ::={partitionTableEntry 2}

  partitionPercentFull OBJECT-TYPE
        SYNTAX INTEGER (0..100) 
        ACCESS read-only
        STATUS mandatory
        DESCRIPTION
          "Indicates (in Percent) how full the disk is."
        ::={partitionTableEntry 3}
        
  partitionMegsFree OBJECT-TYPE
        SYNTAX INTEGER 
        ACCESS read-only
        STATUS mandatory
        DESCRIPTION
          "Indicates how many Megabytes are free on the partition."
        ::={partitionTableEntry 4}

  partitionSpaceStatus OBJECT-TYPE
        SYNTAX PartitionSpaceStatus
        ACCESS read-only
        STATUS mandatory
        DESCRIPTION
          "Indicates if there is currently a space alarm in progress."
        ::={partitionTableEntry 5}
     
  partitionSpaceKey OBJECT-TYPE
        SYNTAX INTEGER
        ACCESS read-only
        STATUS mandatory
        DESCRIPTION
          "Unique indicator for the partition space alarm."
        ::={partitionTableEntry 6}
     

  partitionSpaceTimeStamp OBJECT-TYPE
        SYNTAX TimeString 
        ACCESS read-only
        STATUS mandatory
        DESCRIPTION
          "Indicates the time of the last partitionSpaceStatus transition."
        ::={partitionTableEntry 7}

  --------------------------------------------------------------------
  -- The following dynamic table is used for information on all 
  -- Components running on the CSG.
  --------------------------------------------------------------------
  -- 
  componentTable OBJECT-TYPE 
        SYNTAX SEQUENCE OF ComponentTableEntry
        ACCESS  not-accessible 
        STATUS  mandatory
        DESCRIPTION
          "The ComponentTable contains information about all the 
           Components that should be running on the CSG."
        ::= { components 10 }

  componentTableEntry OBJECT-TYPE
        SYNTAX ComponentTableEntry
        ACCESS  not-accessible
        STATUS  mandatory
        DESCRIPTION
          "An entry in the ComponentTable.  componentTable entries 
           are indexed by componentIndex, which is an integer. "
        INDEX { componentIndex }
        ::= { componentTable 1 }

  -- definition of ComponentIndex
  ComponentIndex ::= INTEGER 
        { oolsproxy(1), climan(2), arm(3), 
          sem(4),       hgm(5),    survman(6),
          ss7scm(7),    ss7opm(8), ss7cheni(9) }

  -- definition of ComponentSysmanState
  ComponentSysmanState ::= INTEGER { inProvisionedState(1), 
                                     notInProvisionedState(2), 
                                     unknown(3) }

  -- definition of ComponentTableEntry
  ComponentTableEntry ::= SEQUENCE {
        componentIndex         ComponentIndex,
        componentName          DisplayString,
        compSecsInCurrentState INTEGER,
        compProvStateStatus    ComponentSysmanState,
        compProvStateKey       INTEGER,
        compProvStateTimeStamp TimeString,
        compDebugStatus        INTEGER,
        compDebugKey           INTEGER,
        compDebugTimeStamp     TimeString,
        compRestartStatus      INTEGER,
        compRestartKey         INTEGER,
        compRestartTimeStamp   TimeString
      }

  componentIndex OBJECT-TYPE
        SYNTAX ComponentIndex
        ACCESS not-accessible
        STATUS mandatory
        DESCRIPTION
          "Identifies the component entry with an enumerated list."
        ::= { componentTableEntry 1 }

  componentName OBJECT-TYPE
        SYNTAX DisplayString  
        ACCESS read-only
        STATUS mandatory
        DESCRIPTION
          "Identifies component name."
        ::={componentTableEntry 2}

  compSecsInCurrentState OBJECT-TYPE
        SYNTAX INTEGER
        ACCESS read-only
        STATUS mandatory
        DESCRIPTION
          "Indicates how many seconds a component has been running in its 
           current state. "
        ::= { componentTableEntry 3 }

  compProvStateStatus OBJECT-TYPE
        SYNTAX ComponentSysmanState
        ACCESS read-only
        STATUS mandatory
        DESCRIPTION
          "Indicates the current state of the particular CSG component.
           The states are one of the following:
                inProvisionedState(1), notInProvisionedState(2), unknown(3)"
        ::= { componentTableEntry 4 }
        
  compProvStateKey OBJECT-TYPE
        SYNTAX INTEGER
        ACCESS read-only
        STATUS mandatory
        DESCRIPTION
          "Unique indicator for the prov state alarm."
        ::= {componentTableEntry 5}
     
  compProvStateTimeStamp OBJECT-TYPE
        SYNTAX TimeString 
        ACCESS read-only
        STATUS mandatory
        DESCRIPTION
          "Indicates the time of the last state transition."
        ::={componentTableEntry 6}

  compDebugStatus OBJECT-TYPE
        SYNTAX INTEGER
        ACCESS read-only
        STATUS mandatory
        DESCRIPTION
          "Shows if the component is running with debug on."
        ::= { componentTableEntry 7 }

  compDebugKey OBJECT-TYPE
        SYNTAX INTEGER
        ACCESS read-only
        STATUS mandatory
        DESCRIPTION
          "Unique indicator for the debug state."
        ::= {componentTableEntry 8}
     
  compDebugTimeStamp OBJECT-TYPE
        SYNTAX TimeString 
        ACCESS read-only
        STATUS mandatory
        DESCRIPTION
          "Indicates the time of the last debug transition."
        ::={componentTableEntry 9}

  compRestartStatus OBJECT-TYPE
        SYNTAX INTEGER
        ACCESS read-only
        STATUS mandatory
        DESCRIPTION
          "Shows if the component has had multiple restarts recently."
        ::= { componentTableEntry 10 }

  compRestartKey OBJECT-TYPE
        SYNTAX INTEGER
        ACCESS read-only
        STATUS mandatory
        DESCRIPTION
          "Unique indicator for the multi-restart of components."
        ::= {componentTableEntry 11}
     
  compRestartTimeStamp OBJECT-TYPE
        SYNTAX TimeString 
        ACCESS read-only
        STATUS mandatory
        DESCRIPTION
         "Indicates the time of the last restart flagging."
        ::={componentTableEntry 12}
         
  --------------------------------------------------------------------
  -- The following dynamic table contains information about the link-
  -- sets provisioned on the CSG for SS7 signalling.
  --------------------------------------------------------------------
  -- 
  linksetTable OBJECT-TYPE 
        SYNTAX SEQUENCE OF LinksetTableEntry
        ACCESS  not-accessible 
        STATUS  mandatory
        DESCRIPTION
          "The linksetTable contains information about all the 
           linksets on the CSG."
        ::= { ss7 1 }

  linksetTableEntry OBJECT-TYPE
        SYNTAX LinksetTableEntry
        ACCESS  not-accessible
        STATUS  mandatory
        DESCRIPTION
          "An entry in the linksetTable.  Entries in the linkset
           table are indexed by linksetIndex, which is an integer."
        INDEX { linksetIndex }
        ::= { linksetTable 1 }

  -- definition of LinksetState
  LinksetState ::= INTEGER { available(1), unAvailable(2) }

  LinksetTableEntry ::= SEQUENCE {
        linksetIndex          INTEGER,
	linksetId             INTEGER,
        linksetAdjPointcode   INTEGER,
        linksetState          LinksetState
      }

  linksetIndex OBJECT-TYPE
        SYNTAX INTEGER
        ACCESS not-accessible
        STATUS mandatory
        DESCRIPTION
          "Identifies the n'th position in the table."
        ::= { linksetTableEntry 1 }

  linksetId OBJECT-TYPE
        SYNTAX INTEGER
        ACCESS read-only
        STATUS mandatory
        DESCRIPTION
          "The id of the linkset to be used as index."
        ::= { linksetTableEntry 2 }

  linksetAdjPointcode OBJECT-TYPE
        SYNTAX INTEGER
        ACCESS read-only
        STATUS mandatory
        DESCRIPTION
          "The adjacent pointcode of the linkset."
        ::= { linksetTableEntry 3 }

  linksetState OBJECT-TYPE
        SYNTAX LinksetState
        ACCESS read-only
        STATUS mandatory
        DESCRIPTION
          "The state of the linkset."
        ::= { linksetTableEntry 4 }

  --------------------------------------------------------------------
  -- The following dynamic table contains information about the links
  -- within each of the linksets provisioned on the CSG.
  --------------------------------------------------------------------
  -- 
  linkTable OBJECT-TYPE 
        SYNTAX SEQUENCE OF LinkTableEntry
        ACCESS  not-accessible 
        STATUS  mandatory
        DESCRIPTION
          "The linkTable contains information about the links
           in a given linkset on the CSG."
        ::= { ss7 2 }

  linkTableEntry OBJECT-TYPE
        SYNTAX LinkTableEntry
        ACCESS  not-accessible
        STATUS  mandatory
        DESCRIPTION
          "An entry in the linkTable.  Entries in the link table
           table are indexed by linksetIndex and linkIndex, which 
	   are both integers."
        INDEX { linksetIndex, linkIndex }
        ::= { linkTable 1 }

  -- definitions of LinkState, LinkInhibitionState, LinkCongestionState,
  -- and LinkAlignmentState. Note that in the code, the definitions
  -- of the enumerated types used to represent these states are in the 
  -- file /rbbvobs/ncdev/common/include/smgt_common.h
  --
  LinkState           ::= INTEGER { available(1), unAvailable(2) }

  LinkInhibitionState ::= INTEGER { unInhibited(1), 
				    localInhibited(2),
				    remoteInhibited(3),
				    localRemoteInhibited(4)
				  }

  LinkCongestionState ::= INTEGER { notCongested(1), congested(2) }

  LinkAlignmentState  ::= INTEGER { aligned(1), notAligned(2) }

  LinkTableEntry ::= SEQUENCE {
        linkIndex              INTEGER,
	linkId                 INTEGER,
	linkHostname           DisplayString,
	linkCardDeviceName     DisplayString,
	linkState              LinkState,
        linkInhibitionState    LinkInhibitionState,
        linkCongestionState    LinkCongestionState,
	linkAlignmentState     LinkAlignmentState,
	linkNumMSUReceived     INTEGER,
	linkNumMSUDiscarded    INTEGER,
	linkNumMSUTransmitted  INTEGER,
	linkNumSIFReceived     INTEGER,
	linkNumSIFTransmitted  INTEGER,
	linkNumAutoChangeovers INTEGER,
	linkNumUnexpectedMsgs  INTEGER
      }

  linkIndex OBJECT-TYPE
        SYNTAX INTEGER
        ACCESS not-accessible
        STATUS mandatory
        DESCRIPTION
          "Identifies the n'th position in the table."
        ::= { linkTableEntry 1 }

  linkId OBJECT-TYPE
        SYNTAX INTEGER
        ACCESS read-only
        STATUS mandatory
        DESCRIPTION
          "The id of the link."
        ::= { linkTableEntry 2 }

  linkHostname OBJECT-TYPE
        SYNTAX DisplayString
        ACCESS read-only
        STATUS mandatory
        DESCRIPTION
          "The hostname of the CSG to which this link is attached."
        ::= { linkTableEntry 3 }

  linkCardDeviceName OBJECT-TYPE
        SYNTAX DisplayString
        ACCESS read-only
        STATUS mandatory
        DESCRIPTION
          "The device name of the card upon which this link is hosted."
        ::= { linkTableEntry 4 }

  linkState OBJECT-TYPE
        SYNTAX LinkState
        ACCESS read-only
        STATUS mandatory
        DESCRIPTION
          "The state of the link."
        ::= { linkTableEntry 5 }

  linkInhibitionState OBJECT-TYPE
        SYNTAX LinkInhibitionState
        ACCESS read-only
        STATUS mandatory
        DESCRIPTION
          "The inhibition status of the link."
        ::= { linkTableEntry 6 }

  linkCongestionState OBJECT-TYPE
        SYNTAX LinkCongestionState
        ACCESS read-only
        STATUS mandatory
        DESCRIPTION
          "The congestion status of the link."
        ::= { linkTableEntry 7 }

  linkAlignmentState OBJECT-TYPE
        SYNTAX LinkAlignmentState
        ACCESS read-only
        STATUS mandatory
        DESCRIPTION
          "The alignment status of the link."
        ::= { linkTableEntry 8 }

  linkNumMSUReceived OBJECT-TYPE
        SYNTAX INTEGER
        ACCESS read-only
        STATUS mandatory
        DESCRIPTION
          "This object supplies the number of MSU's 
	   received by the link."
        ::= { linkTableEntry 9 }

  linkNumMSUDiscarded OBJECT-TYPE
        SYNTAX INTEGER
        ACCESS read-only
        STATUS mandatory
        DESCRIPTION
          "This object supplies the number of received
	   MSU's discarded by the link." 
        ::= { linkTableEntry 10 }

  linkNumMSUTransmitted OBJECT-TYPE
        SYNTAX INTEGER
        ACCESS read-only
        STATUS mandatory
        DESCRIPTION
          "This object supplies the number of MSU's
	   transmitted by the link."
        ::= { linkTableEntry 11 }

  linkNumSIFReceived OBJECT-TYPE
        SYNTAX INTEGER
        ACCESS read-only
        STATUS mandatory
        DESCRIPTION
          "This object supplies the number of SIF and
	   SIO octets received by the link."
        ::= { linkTableEntry 12 }

  linkNumSIFTransmitted OBJECT-TYPE
        SYNTAX INTEGER
        ACCESS read-only
        STATUS mandatory
        DESCRIPTION
          "This object supplies the number of SIF and
	   SIO octects transmitted by the link."
        ::= { linkTableEntry 13 }

  linkNumAutoChangeovers OBJECT-TYPE
        SYNTAX INTEGER
        ACCESS read-only
        STATUS mandatory
        DESCRIPTION
          "This object supplies the number of automatic
	   changeovers undergone by the link."
        ::= { linkTableEntry 14 }

  linkNumUnexpectedMsgs OBJECT-TYPE
        SYNTAX INTEGER
        ACCESS read-only
        STATUS mandatory
        DESCRIPTION
          "This object supplies the number of unexpected
	   messages received by the link."
        ::= { linkTableEntry 15 }


  ------------------------------------------------------------------------
  -- The following dynamic table contains information about the ss7 routes
  -- provisioned on the CSG.
  ------------------------------------------------------------------------
  -- 
  routeTable OBJECT-TYPE 
        SYNTAX SEQUENCE OF RouteTableEntry
        ACCESS  not-accessible 
        STATUS  mandatory
        DESCRIPTION
          "The routeTable contains information about the routes
           provisioned in the CSG complex."
        ::= { ss7 3 }

  routeTableEntry OBJECT-TYPE
        SYNTAX RouteTableEntry
        ACCESS  not-accessible
        STATUS  mandatory
        DESCRIPTION
          "An entry in the routeTable.  Entries in the route table are indexed by
           routeIndex, which is an integer."
        INDEX { routeIndex }
        ::= { routeTable 1 }

  -- definitions of RouteState.
  -- Note that in the code, the definitions
  -- of the enumerated types used to represent these states are defined in the 
  -- file /rbbvobs/ncdev/common/include/smgt_common.h
  --

  RouteState           ::= INTEGER { accessible(1), inaccessible(2), restricted(3) }


  RouteTableEntry ::= SEQUENCE {
        routeIndex              INTEGER,
        routeId                 DisplayString,
        routeDestPointCode      DisplayString,
        routeState              RouteState,
        routeRank               INTEGER,
        routeLinksetId          DisplayString

      }

  routeIndex OBJECT-TYPE
        SYNTAX INTEGER
        ACCESS not-accessible
        STATUS mandatory
        DESCRIPTION
          "Identifies the n'th position in the table."
        ::= { routeTableEntry 1 }

  routeId         OBJECT-TYPE
        SYNTAX DisplayString
        ACCESS read-only
        STATUS mandatory
        DESCRIPTION
          "The unique identifier of the route."
        ::= { routeTableEntry 2 }


  routeDestPointCode      OBJECT-TYPE
        SYNTAX DisplayString
        ACCESS read-only
        STATUS mandatory
        DESCRIPTION
          "The destination point code associated with this route."
        ::= { routeTableEntry 3 }

  routeState         OBJECT-TYPE
        SYNTAX RouteState
        ACCESS read-only
        STATUS mandatory
        DESCRIPTION
          "The current state of the route."
        ::= { routeTableEntry 4 }

  routeRank OBJECT-TYPE
        SYNTAX INTEGER
        ACCESS read-only
        STATUS mandatory
        DESCRIPTION
          "Rank assigned to this route."
        ::= { routeTableEntry 5 }


  routeLinksetId OBJECT-TYPE
        SYNTAX DisplayString
        ACCESS read-only
        STATUS mandatory
        DESCRIPTION
          "The linkset associated with this route."
        ::= { routeTableEntry 6 }

  ------------------------------------------------------------------------
  -- The following dynamic table contains information about the ss7 
  -- destinations provisioned on the CSG.
  ------------------------------------------------------------------------
  -- 
  destinationTable OBJECT-TYPE 
        SYNTAX SEQUENCE OF DestinationTableEntry
        ACCESS  not-accessible 
        STATUS  mandatory
        DESCRIPTION
          "The destinationTable contains information about the destinations
           provisioned in the CSG complex."
        ::= { ss7 4 }

  destinationTableEntry OBJECT-TYPE
        SYNTAX DestinationTableEntry
        ACCESS  not-accessible
        STATUS  mandatory
        DESCRIPTION
          "An entry in the destinationTable.  Entries in the destination table
           are indexed by destIndex, which is an integer."
        INDEX { destIndex }
        ::= { destinationTable 1 }

  -- definitions of DestinationState.
  -- Note that in the code, the definitions
  -- of the enumerated types used to represent these states are defined in the 
  -- file /rbbvobs/ncdev/common/include/smgt_common.h
  --

  DestinationState           ::= INTEGER { accessible(1), inaccessible(2), restricted(3) }


  DestinationTableEntry ::= SEQUENCE {
        destIndex               INTEGER,
        destPointCode           DisplayString,
        destState               DestinationState,
        destRuleId              INTEGER
      }

  destIndex OBJECT-TYPE
        SYNTAX INTEGER
        ACCESS not-accessible
        STATUS mandatory
        DESCRIPTION
          "Identifies the n'th position in the table."
        ::= { destinationTableEntry 1 }


  destPointCode      OBJECT-TYPE
        SYNTAX DisplayString
        ACCESS read-only
        STATUS mandatory
        DESCRIPTION
          "The destination point code of this destination."
        ::= { destinationTableEntry 2 }

  destState OBJECT-TYPE
        SYNTAX DestinationState
        ACCESS read-only
        STATUS mandatory
        DESCRIPTION
          "The current state of the destination."
        ::= { destinationTableEntry 3 }

  destRuleId OBJECT-TYPE
        SYNTAX INTEGER
        ACCESS read-only
        STATUS mandatory
        DESCRIPTION
          "Rule Identifier (for the routing table to be used) for this destination."
        ::= { destinationTableEntry 4 }

  --------------------------------------------------------------------
  -- Information related to High Availability
  --------------------------------------------------------------------
  -- 
    ncServerId OBJECT-TYPE
         SYNTAX INTEGER
         ACCESS read-only
         STATUS mandatory
         DESCRIPTION
            " The ServerId attribute value of the node."
         ::= { ncServer 2 }
 
    ncServerName OBJECT-TYPE
         SYNTAX DisplayString
         ACCESS read-only
         STATUS mandatory
         DESCRIPTION
            " The ServerName attribute value of the node."
         ::= { ncServer 3 }
 
    ncHostName OBJECT-TYPE
         SYNTAX DisplayString
         ACCESS read-only
         STATUS mandatory
         DESCRIPTION
            " The HostName attribute value of the node."
         ::= { ncServer 4 }
 
    ncEthernetName OBJECT-TYPE
         SYNTAX DisplayString
         ACCESS read-only
         STATUS mandatory
         DESCRIPTION
            " The EthernetName attribute value of the node."
         ::= { ncServer 5 }
 
    ncEthernetIP OBJECT-TYPE
         SYNTAX IpAddress
         ACCESS read-only
         STATUS mandatory
         DESCRIPTION
            " The EthernetIP attribute value of the node."
         ::= { ncServer 6 }
 
    ncClusterName OBJECT-TYPE
         SYNTAX DisplayString
         ACCESS read-only
         STATUS mandatory
         DESCRIPTION
            " The ClusterName attribute value of the node."
         ::= { ncServer 7 }
 
    ncClusterIP OBJECT-TYPE
         SYNTAX IpAddress
         ACCESS read-only
         STATUS mandatory
         DESCRIPTION
            " The ClusterIP attribute value of the node."
         ::= { ncServer 8 }
 
    ncOperationalState OBJECT-TYPE
         SYNTAX DisplayString
         ACCESS read-only
         STATUS mandatory
         DESCRIPTION
            " The OperationalState of the node.  
              Possible values are:
                UNKNOWN,
                ENABLED,
                ENABLED_NETDSC,
                ENABLED_NETPAR,
                DISABLED
            "
         ::= { ncServer 9 }

    ncStandbyState OBJECT-TYPE
         SYNTAX DisplayString
         ACCESS read-only
         STATUS mandatory
         DESCRIPTION
            " The StandbyState attribute value of the node.
              Possible values are:
                UNKNOWN,
                HOT_STANDBY,
                COLD_STANDBY,
                WARM_STANDBY,
                PROVIDING_SERVICE
            "
         ::= { ncServer 10 }
 
    ncAvailabilityState OBJECT-TYPE
         SYNTAX DisplayString
         ACCESS read-only
         STATUS mandatory
         DESCRIPTION
            " The AvailabilityState attribute value of the node.
              Possible values are:
                UNKNOWN,
                AVAILABLE,
                DEGRADED,
                OFFLINE
            "
         ::= { ncServer 11 }

    ncSoftwareVersion OBJECT-TYPE
         SYNTAX DisplayString
         ACCESS read-only
         STATUS mandatory
         DESCRIPTION
            " The SoftwareVersion attribute value of the node."
         ::= { ncServer 12 }
 
    UpgradeInProgress ::= INTEGER (0..2)
 
    ncUpgradeInProgress OBJECT-TYPE
         SYNTAX UpgradeInProgress
         ACCESS read-only
         STATUS mandatory
         DESCRIPTION
            " The UpgradeInProgress attribute value of the node.
              Possible values are:
                0 = UNKNOWN,
                1 = ACTIVE,
                2 = INACTIVE
            "
         ::= { ncServer 13 }


----------------------------------
------  Alarm Tables         -----
----------------------------------

  --------------------------------------------------------------------
  --
  -- In the following section the CSG alarm tables are defined. These
  -- dynamic tables contain information related to the alarms which
  -- are currently raised on the CSG.
  --
  --------------------------------------------------------------------

  --------------------------------------------------------------------
  -- The following dynamic table is used for Home Gateway's that 
  -- are currently alarmed.
  --------------------------------------------------------------------
  -- 
  hgAlarmTable OBJECT-TYPE 
        SYNTAX SEQUENCE OF HgAlarmTableEntry
        ACCESS  not-accessible 
        STATUS  mandatory
        DESCRIPTION
          "The HgAlarmTable contains information about all the 
           current HG alarms"
        ::= { alarms 10 }

  hgAlarmTableEntry OBJECT-TYPE
        SYNTAX HgAlarmTableEntry
        ACCESS  not-accessible
        STATUS  mandatory
        DESCRIPTION
          "An entry in the HgAlarmTable.  HgAlarmTable entries 
           are indexed by componentIndex, which is an integer."
        INDEX { hgIndex }
        ::= { hgAlarmTable 1 }
   
  HgAlarmTableEntry ::= SEQUENCE {
        hgIndex          INTEGER,
        hgName           DisplayString,
        hgKey            INTEGER,
        hgAlarmTimeStamp TimeString,
        hgIPAddress      IpAddress
      }

  hgIndex OBJECT-TYPE
        SYNTAX INTEGER
        ACCESS not-accessible
        STATUS mandatory
        DESCRIPTION
          "Identifies the n'th position in the table."
        ::= { hgAlarmTableEntry 1 }

  hgName OBJECT-TYPE
        SYNTAX DisplayString
        ACCESS read-only
        STATUS mandatory
        DESCRIPTION
          "The Home gateway to be used as index"
        ::= { hgAlarmTableEntry 2 }

  hgKey OBJECT-TYPE
        SYNTAX INTEGER
        ACCESS read-only 
        STATUS mandatory
        DESCRIPTION
          "Unique identifier for the HgFailure alarm "
        ::= { hgAlarmTableEntry 3 }

  hgAlarmTimeStamp OBJECT-TYPE
        SYNTAX TimeString 
        ACCESS read-only
        STATUS mandatory
        DESCRIPTION
          "Indicates the time of the HG Alarm."
        ::= { hgAlarmTableEntry 4 }

  hgIPAddress OBJECT-TYPE
        SYNTAX IpAddress
        ACCESS read-only
        STATUS mandatory
        DESCRIPTION
          "This object identifies the IP Address of the machine which 
           sent the alarm."
        ::= { hgAlarmTableEntry 5 }

  --------------------------------------------------------------------
  -- The following dynamic table is used for NAS that are currently
  -- alarmed.
  --------------------------------------------------------------------
  -- 
  nasAlarmTable OBJECT-TYPE
        SYNTAX SEQUENCE OF NasAlarmTableEntry
        ACCESS  not-accessible
        STATUS  mandatory
        DESCRIPTION
          "The NasAlarmTable contains information about all the
           current NAS alarms"
        ::= { alarms 11 }

  nasAlarmTableEntry OBJECT-TYPE
        SYNTAX NasAlarmTableEntry
        ACCESS  not-accessible
        STATUS  mandatory
        DESCRIPTION
          "An entry in the NasAlarmTable.  NasAlarmTable entries
           are indexed by nasIndex, which is an integer."
        INDEX { nasIndex }
        ::= { nasAlarmTable 1 }

  NasAlarmTableEntry ::= SEQUENCE { 
        nasIndex          INTEGER,
        nasName           DisplayString,
        nasKey            INTEGER,
        nasAlarmTimeStamp TimeString,
        nasIPAddress      IpAddress,
        nasCmplxName      DisplayString
      }

  nasIndex OBJECT-TYPE
        SYNTAX INTEGER
        ACCESS not-accessible
        STATUS mandatory
        DESCRIPTION
          "Identifies the n'th position in the table."
        ::= { nasAlarmTableEntry 1 }

  nasName OBJECT-TYPE
        SYNTAX DisplayString
        ACCESS read-only
        STATUS mandatory
        DESCRIPTION
          "The NAS Name"
        ::= { nasAlarmTableEntry 2 }

  nasKey OBJECT-TYPE
        SYNTAX INTEGER
        ACCESS read-only
        STATUS mandatory
        DESCRIPTION
          "Unique identifier for the NAS Failure alarm "
        ::= { nasAlarmTableEntry 3 }

  nasAlarmTimeStamp OBJECT-TYPE
        SYNTAX TimeString
        ACCESS read-only
        STATUS mandatory
        DESCRIPTION
          "Indicates the time of the NAS Alarm."
        ::= {nasAlarmTableEntry 4}

  nasIPAddress OBJECT-TYPE
        SYNTAX IpAddress
        ACCESS read-only
        STATUS mandatory
        DESCRIPTION
          "This object identifies the IP Address of the machine which 
           sent the alarm."
        ::= { nasAlarmTableEntry 5 }


  nasCmplxName OBJECT-TYPE
        SYNTAX DisplayString
        ACCESS read-only
        STATUS mandatory
        DESCRIPTION
          " The complex which this alarm is raised against."
        ::= { nasAlarmTableEntry 6 }
  --------------------------------------------------------------------
  -- The following dynamic table is used for SS7 Link Failure alarms.
  --------------------------------------------------------------------
  -- 
  ss7LinkFailureAlarmTable OBJECT-TYPE
        SYNTAX SEQUENCE OF SS7LinkFailureAlarmTableEntry
        ACCESS not-accessible
        STATUS mandatory
        DESCRIPTION
          "The SS7LinkFailureAlarmTable contains alarms for SS7 link
           failures."
        ::= { alarms 12 }

  ss7LinkFailureAlarmTableEntry OBJECT-TYPE
        SYNTAX SS7LinkFailureAlarmTableEntry
        ACCESS not-accessible
        STATUS mandatory
        DESCRIPTION
          "This object defines a row within the SS7 Link Failure Alarm Table.
           A row can be uniquely identified with the row index."
        INDEX { lfIndex }
        ::= { ss7LinkFailureAlarmTable 1 }

  SS7LinkFailureAlarmTableEntry ::= 
      SEQUENCE 
        {
        lfIndex          INTEGER,
        lfKey            INTEGER,
        lfIPAddress      IpAddress,
        lfLinkCode       INTEGER,
        lfTimeStamp      TimeString,
        lfName           DisplayString,
        lfCardId         DisplayString,
	lfLinkSet        DisplayString
      }

  lfIndex OBJECT-TYPE
        SYNTAX INTEGER
        ACCESS not-accessible
        STATUS mandatory
        DESCRIPTION
          "Identifies the row number in the table."
        ::= { ss7LinkFailureAlarmTableEntry 1 }

  lfKey OBJECT-TYPE
        SYNTAX INTEGER
        ACCESS read-only
        STATUS mandatory
        DESCRIPTION
          "Unique identifier for the alarm."
        ::= { ss7LinkFailureAlarmTableEntry 2 }
  
  lfIPAddress OBJECT-TYPE
        SYNTAX IpAddress
        ACCESS read-only
        STATUS mandatory
        DESCRIPTION
          "This object identifies the IP Address of the machine which 
           sent the alarm."
        ::= { ss7LinkFailureAlarmTableEntry 3 }

  lfLinkCode OBJECT-TYPE
        SYNTAX INTEGER
        ACCESS read-only
        STATUS mandatory
        DESCRIPTION
          "This object identifies the signalling link code (SLC) of the
	   failed link."
        ::= { ss7LinkFailureAlarmTableEntry 5 }

  lfTimeStamp OBJECT-TYPE
        SYNTAX TimeString 
        ACCESS read-only
        STATUS mandatory
        DESCRIPTION
         "Indicates the time of the alarm."
        ::= { ss7LinkFailureAlarmTableEntry 6 }

  lfName OBJECT-TYPE
        SYNTAX DisplayString
        ACCESS read-only
        STATUS mandatory
        DESCRIPTION
          "Indicates the configured name for the machine which sent the 
           alarm."
        ::= { ss7LinkFailureAlarmTableEntry 7 } 

  lfCardId OBJECT-TYPE
        SYNTAX DisplayString
        ACCESS read-only
        STATUS mandatory
        DESCRIPTION
          "This object identifies the device that hosts the failed link.
	   It provides a physical description of the device, as well as
	   its slot number."
        ::= { ss7LinkFailureAlarmTableEntry 8 }

  lfLinkSet OBJECT-TYPE
        SYNTAX DisplayString
        ACCESS read-only
        STATUS mandatory
        DESCRIPTION
          "This object identifies the linkset associated with the link
	   via its adjacent point code."
        ::= { ss7LinkFailureAlarmTableEntry 9 }

  ----------------------------------------------------------------------
  -- The following dynamic table is used for SS7 Link Congestion alarms.
  ----------------------------------------------------------------------
  -- 
  ss7LinkCongestionAlarmTable OBJECT-TYPE
        SYNTAX SEQUENCE OF SS7LinkCongestionAlarmTableEntry
        ACCESS not-accessible
        STATUS mandatory
        DESCRIPTION
          "The SS7LinkCongestionAlarmTable contains alarms to indicate
           congestion on an SS7 link."
        ::= { alarms 13 }

  ss7LinkCongestionAlarmTableEntry OBJECT-TYPE
        SYNTAX SS7LinkCongestionAlarmTableEntry
        ACCESS not-accessible
        STATUS mandatory
        DESCRIPTION
          "This object defines a row within the SS7 Link Congestion Alarm 
           Table.  A row can be uniquely identified with the row index."
        INDEX { lcIndex }
        ::= { ss7LinkCongestionAlarmTable 1 }

  SS7LinkCongestionAlarmTableEntry ::= SEQUENCE {
        lcIndex          INTEGER,
        lcKey            INTEGER,
        lcIPAddress      IpAddress,
        lcLinkCode       INTEGER,
        lcTimeStamp      TimeString,
        lcName           DisplayString,
        lcCardId         DisplayString,
	lcLinkSet        DisplayString
      }

  lcIndex OBJECT-TYPE
        SYNTAX INTEGER
        ACCESS not-accessible
        STATUS mandatory
        DESCRIPTION
          "Identifies the row number in the table."
        ::= { ss7LinkCongestionAlarmTableEntry 1 }

  lcKey OBJECT-TYPE
        SYNTAX INTEGER
        ACCESS read-only
        STATUS mandatory
        DESCRIPTION
          "Unique identifier for the alarm."
        ::= { ss7LinkCongestionAlarmTableEntry 2 }
  
  lcIPAddress OBJECT-TYPE
        SYNTAX IpAddress
        ACCESS read-only
        STATUS mandatory
        DESCRIPTION
          "This object identifies the IP Address of the machine which 
           sent the alarm."
        ::= { ss7LinkCongestionAlarmTableEntry 3 }

  lcLinkCode OBJECT-TYPE
        SYNTAX INTEGER
        ACCESS read-only
        STATUS mandatory
        DESCRIPTION
          "This object identifies the signalling link code (SLC) of
	   the affected link."
        ::= { ss7LinkCongestionAlarmTableEntry 4 }

  lcTimeStamp OBJECT-TYPE
        SYNTAX TimeString 
        ACCESS read-only
        STATUS mandatory
        DESCRIPTION
         "Indicates the time of the alarm."
        ::= { ss7LinkCongestionAlarmTableEntry 5 }

  lcName OBJECT-TYPE
        SYNTAX DisplayString
        ACCESS read-only
        STATUS mandatory
        DESCRIPTION
          "Indicates the configured name for the machine which sent the 
           alarm."
        ::= { ss7LinkCongestionAlarmTableEntry 6 } 

  lcCardId OBJECT-TYPE
        SYNTAX DisplayString
        ACCESS read-only
        STATUS mandatory
        DESCRIPTION
          "This object identifies the device that hosts the failed link.
	   It provides a physical description of the device, as well as
	   its slot number."
        ::= { ss7LinkCongestionAlarmTableEntry 7 }

  lcLinkSet OBJECT-TYPE
        SYNTAX DisplayString
        ACCESS read-only
        STATUS mandatory
        DESCRIPTION
          "This object identifies the linkset associated with the link
	   via its adjacent point code."
        ::= { ss7LinkCongestionAlarmTableEntry 8 }

  ----------------------------------------------------------------------
  -- The following dynamic table is used for SS7 ISUP Failure alarms.
  ----------------------------------------------------------------------
  -- 
  ss7ISUPFailureAlarmTable OBJECT-TYPE
        SYNTAX SEQUENCE OF SS7ISUPFailureAlarmTableEntry
        ACCESS not-accessible
        STATUS mandatory
        DESCRIPTION
          "The SS7ISUPFailureAlarmTable contains alarms for SS7 ISUP
           protocol stack failures."
        ::= { alarms 14 }

  ss7ISUPFailureAlarmTableEntry OBJECT-TYPE
        SYNTAX SS7ISUPFailureAlarmTableEntry
        ACCESS not-accessible
        STATUS mandatory
        DESCRIPTION
          "This object defines a row within the SS7 ISUP Failure Alarm Table.
           A row can be uniquely identified with the row index."
        INDEX { ifIndex }
        ::= { ss7ISUPFailureAlarmTable 1 }

  SS7ISUPFailureAlarmTableEntry ::= SEQUENCE { 
        ifIndex       INTEGER,
        ifKey         INTEGER,
        ifIPAddress   IpAddress,
        ifTimeStamp   TimeString,
        ifName        DisplayString
      }

  ifIndex OBJECT-TYPE
        SYNTAX INTEGER
        ACCESS not-accessible
        STATUS mandatory
        DESCRIPTION
          "Identifies the row number in the table."
        ::= { ss7ISUPFailureAlarmTableEntry 1 }

  ifKey OBJECT-TYPE
        SYNTAX INTEGER
        ACCESS read-only
        STATUS mandatory
        DESCRIPTION
          "Unique identifier for the alarm."
        ::= { ss7ISUPFailureAlarmTableEntry 2 }
  
  ifIPAddress OBJECT-TYPE
        SYNTAX IpAddress
        ACCESS read-only
        STATUS mandatory
        DESCRIPTION
          "This object identifies the IP Address of the machine which 
           sent the alarm."
        ::= { ss7ISUPFailureAlarmTableEntry 3 }

  ifTimeStamp OBJECT-TYPE
        SYNTAX TimeString 
        ACCESS read-only
        STATUS mandatory
        DESCRIPTION
         "Indicates the time of the alarm."
        ::= { ss7ISUPFailureAlarmTableEntry 4 }

  ifName OBJECT-TYPE
        SYNTAX DisplayString
        ACCESS read-only
        STATUS mandatory
        DESCRIPTION
          "Indicates the configured name for the machine which sent the 
           alarm."
        ::= { ss7ISUPFailureAlarmTableEntry 5 } 

  ----------------------------------------------------------------------
  -- The following dynamic table is used for ISUP Congestion alarms.
  ----------------------------------------------------------------------
  -- 
  ss7ISUPCongestionAlarmTable OBJECT-TYPE
        SYNTAX SEQUENCE OF SS7ISUPCongestionAlarmTableEntry
        ACCESS not-accessible
        STATUS mandatory
        DESCRIPTION
          "The SS7ISUPCongestionAlarmTable contains alarms to indicate
           congestion with an ISUP protocol stack."
        ::= { alarms 15 }

  ss7ISUPCongestionAlarmTableEntry OBJECT-TYPE
        SYNTAX SS7ISUPCongestionAlarmTableEntry
        ACCESS not-accessible
        STATUS mandatory
        DESCRIPTION
          "This object defines a row within the SS7 ISUP Congestion Alarm 
           Table.  A row can be uniquely identified with the row index."
        INDEX { icIndex }
        ::= { ss7ISUPCongestionAlarmTable 1 }

  SS7ISUPCongestionAlarmTableEntry ::= SEQUENCE {
        icIndex           INTEGER,
        icKey             INTEGER,
        icIPAddress       IpAddress,
        icCongestionLevel INTEGER,
        icTimeStamp       TimeString,
        icName            DisplayString
      }

  icIndex OBJECT-TYPE
        SYNTAX INTEGER
        ACCESS not-accessible
        STATUS mandatory
        DESCRIPTION
          "Identifies the row number in the table."
        ::= { ss7ISUPCongestionAlarmTableEntry 1 }

  icKey OBJECT-TYPE
        SYNTAX INTEGER
        ACCESS read-only
        STATUS mandatory
        DESCRIPTION
          "Unique identifier for the alarm."
        ::= { ss7ISUPCongestionAlarmTableEntry 2 }
  
  icIPAddress OBJECT-TYPE
        SYNTAX IpAddress
        ACCESS read-only
        STATUS mandatory
        DESCRIPTION
          "This object identifies the IP Address of the machine which 
           sent the alarm."
        ::= { ss7ISUPCongestionAlarmTableEntry 3 }

  icCongestionLevel OBJECT-TYPE
        SYNTAX INTEGER
        ACCESS read-only
        STATUS mandatory
        DESCRIPTION
          "This object indicates the congestion level with an ISUP protocol
           stack.  Possible congestion levels are:
                (0) Normal
                (1) Congestion
          "
        ::= { ss7ISUPCongestionAlarmTableEntry 4 }

  icTimeStamp OBJECT-TYPE
        SYNTAX TimeString 
        ACCESS read-only
        STATUS mandatory
        DESCRIPTION
         "Indicates the time of the alarm."
        ::= { ss7ISUPCongestionAlarmTableEntry 5 }

  icName OBJECT-TYPE
        SYNTAX DisplayString
        ACCESS read-only
        STATUS mandatory
        DESCRIPTION
          "Indicates the configured name for the machine which sent the 
           alarm."
        ::= { ss7ISUPCongestionAlarmTableEntry 6 } 

  ----------------------------------------------------------------------
  -- The following dynamic table is used for SS7 MTP3 Congestion alarms.
  ----------------------------------------------------------------------
  -- 
  ss7MTP3CongestionAlarmTable OBJECT-TYPE
        SYNTAX SEQUENCE OF SS7MTP3CongestionAlarmTableEntry
        ACCESS not-accessible
        STATUS mandatory
        DESCRIPTION
          "The SS7MTP3CongestionAlarmTable contains alarms to indicate
           congestion on an MTP3 link."
        ::= { alarms 16 }

  ss7MTP3CongestionAlarmTableEntry OBJECT-TYPE
        SYNTAX SS7MTP3CongestionAlarmTableEntry
        ACCESS not-accessible
        STATUS mandatory
        DESCRIPTION
          "This object defines a row within the SS7 MTP3 Congestion Alarm 
           Table.  A row can be uniquely identified with the row index."
        INDEX { mtp3Index }
        ::= { ss7MTP3CongestionAlarmTable 1 }

  SS7MTP3CongestionAlarmTableEntry ::= SEQUENCE {
        mtp3Index           INTEGER,
        mtp3Key             INTEGER,
        mtp3IPAddress       IpAddress,
        mtp3CongestionLevel INTEGER,
        mtp3TimeStamp       TimeString,
        mtp3Name            DisplayString
      }

  mtp3Index OBJECT-TYPE
        SYNTAX INTEGER
        ACCESS not-accessible
        STATUS mandatory
        DESCRIPTION
          "Identifies the row number in the table."
        ::= { ss7MTP3CongestionAlarmTableEntry 1 }

  mtp3Key OBJECT-TYPE
        SYNTAX INTEGER
        ACCESS read-only
        STATUS mandatory
        DESCRIPTION
          "Unique identifier for the alarm."
        ::= { ss7MTP3CongestionAlarmTableEntry 2 }
  
  mtp3IPAddress OBJECT-TYPE
        SYNTAX IpAddress
        ACCESS read-only
        STATUS mandatory
        DESCRIPTION
          "This object identifies the IP Address of the machine which 
           sent the alarm."
        ::= { ss7MTP3CongestionAlarmTableEntry 3 }

  mtp3CongestionLevel OBJECT-TYPE
        SYNTAX INTEGER
        ACCESS read-only
        STATUS mandatory
        DESCRIPTION
          "This object indicates the congestion level on a problem SS7 Link.
           Possible congestion values are: 
                (0) Normal
                (1) Minor
                (2) Major
                (3) Critical
          "
        ::= { ss7MTP3CongestionAlarmTableEntry 4 }

  mtp3TimeStamp OBJECT-TYPE
        SYNTAX TimeString 
        ACCESS read-only
        STATUS mandatory
        DESCRIPTION
         "Indicates the time of the alarm."
        ::= { ss7MTP3CongestionAlarmTableEntry 5 }

  mtp3Name OBJECT-TYPE
        SYNTAX DisplayString
        ACCESS read-only
        STATUS mandatory
        DESCRIPTION
          "Represents the configured name of the machine which sent the 
           alarm."
        ::= { ss7MTP3CongestionAlarmTableEntry 6 }

  ----------------------------------------------------------------------
  -- The following dynamic table is used for SS7 MTP2 trunk failure
  -- alarms.
  ----------------------------------------------------------------------
  -- 
  ss7MTP2TrunkFailureAlarmTable OBJECT-TYPE
        SYNTAX SEQUENCE OF SS7MTP2TrunkFailureAlarmTableEntry
        ACCESS not-accessible
        STATUS mandatory
        DESCRIPTION
          "The SS7MTP2TrunkFailureAlarmTable contains alarms to 
           indicate MTP2 trunk failures."
        ::= { alarms 17 }

  ss7MTP2TrunkFailureAlarmTableEntry OBJECT-TYPE
        SYNTAX SS7MTP2TrunkFailureAlarmTableEntry
        ACCESS not-accessible
        STATUS mandatory
        DESCRIPTION
          "This object defines a row within the SS7 MTP2 Failure Alarm 
           Table.  A row can be uniquely identified with the row index."
        INDEX { mtp2Index }
        ::= { ss7MTP2TrunkFailureAlarmTable 1 }

  -- definition of MTP2AlarmConditionType
  MTP2AlarmConditionType ::= INTEGER { fasError(1), 
                                       carrierLost(2), 
                                       synchroLost(3), 
                                       aisRcv(4), 
                                       remoteAlarmRcv(5), 
                                       tooHighBer(6) }

  SS7MTP2TrunkFailureAlarmTableEntry ::= SEQUENCE {
        mtp2Index           INTEGER,
        mtp2Key             INTEGER,
        mtp2IPAddress       IpAddress,
        mtp2Name            DisplayString,
        mtp2CardId          DisplayString,
        mtp2AlarmCondition  MTP2AlarmConditionType,
        mtp2TimeStamp       TimeString
      }

  mtp2Index OBJECT-TYPE
        SYNTAX INTEGER
        ACCESS not-accessible
        STATUS mandatory
        DESCRIPTION
          "Identifies the row number in the table."
        ::= { ss7MTP2TrunkFailureAlarmTableEntry 1 }

  mtp2Key OBJECT-TYPE
        SYNTAX INTEGER
        ACCESS read-only
        STATUS mandatory
        DESCRIPTION
          "Unique identifier for the alarm."
        ::= { ss7MTP2TrunkFailureAlarmTableEntry 2 }
  
  mtp2IPAddress OBJECT-TYPE
        SYNTAX IpAddress
        ACCESS read-only
        STATUS mandatory
        DESCRIPTION
          "This object identifies the IP Address of the machine which 
           sent the alarm."
        ::= { ss7MTP2TrunkFailureAlarmTableEntry 3 }

  mtp2Name OBJECT-TYPE
        SYNTAX DisplayString
        ACCESS read-only
        STATUS mandatory
        DESCRIPTION
          "This object identifies the configured name of the machine which
           sent the alarm."
        ::= { ss7MTP2TrunkFailureAlarmTableEntry 4 }

  mtp2CardId OBJECT-TYPE
        SYNTAX DisplayString
        ACCESS read-only
        STATUS mandatory
        DESCRIPTION
          "This object indicates the device upon which the affected
	   trunk is hosted. The string contains a physical description
	   of the device, as well as its slot number."
        ::= { ss7MTP2TrunkFailureAlarmTableEntry 5 }

  mtp2AlarmCondition OBJECT-TYPE
        SYNTAX MTP2AlarmConditionType
        ACCESS read-only
        STATUS mandatory
        DESCRIPTION
          "This object indicates which of the possible alarm conditions is
           in effect. Alarms are not nested: a new alarm is only reported
           if there is no current alarm condition."
        ::= { ss7MTP2TrunkFailureAlarmTableEntry 6 }

  mtp2TimeStamp OBJECT-TYPE
        SYNTAX TimeString 
        ACCESS read-only
        STATUS mandatory
        DESCRIPTION
         "Indicates the time of the alarm."
        ::= { ss7MTP2TrunkFailureAlarmTableEntry 7 }


  ----------------------------------------------------------------------
  -- The following dynamic table is used for SS7 Linkset Failure Alarms.
  ----------------------------------------------------------------------
  -- 
  ss7LinksetFailureAlarmTable OBJECT-TYPE
        SYNTAX SEQUENCE OF SS7LinksetFailureAlarmTableEntry
        ACCESS not-accessible
        STATUS mandatory
        DESCRIPTION
          "The SS7LinksetFailureAlarmTable contains alarms to indicate
           failure on an CSG linkset."
        ::= { alarms 18 }

  ss7LinksetFailureAlarmTableEntry OBJECT-TYPE
        SYNTAX SS7LinksetFailureAlarmTableEntry
        ACCESS not-accessible
        STATUS mandatory
        DESCRIPTION
          "This object defines a row within the SS7 Linkset Failure Alarm 
           Table.  A row can be uniquely identified with the row index."
        INDEX { lsFailureIndex }
        ::= { ss7LinksetFailureAlarmTable 1 }

  SS7LinksetFailureAlarmTableEntry ::= SEQUENCE {
        lsFailureIndex      INTEGER,
        lsFailureKey        INTEGER,
        lsFailureIPAddress  IpAddress,
        lsFailureName       DisplayString,
        lsFailurePointcode  DisplayString,
        lsFailureTimeStamp  TimeString
      }

  lsFailureIndex OBJECT-TYPE
        SYNTAX INTEGER
        ACCESS not-accessible
        STATUS mandatory
        DESCRIPTION
          "Identifies the row number in the table."
        ::= { ss7LinksetFailureAlarmTableEntry 1 }

  lsFailureKey OBJECT-TYPE
        SYNTAX INTEGER
        ACCESS read-only
        STATUS mandatory
        DESCRIPTION
          "Unique identifier for the alarm."
        ::= { ss7LinksetFailureAlarmTableEntry 2 }
  
  lsFailureIPAddress OBJECT-TYPE
        SYNTAX IpAddress
        ACCESS read-only
        STATUS mandatory
        DESCRIPTION
          "This object identifies the IP Address of the machine which 
           sent the alarm."
        ::= { ss7LinksetFailureAlarmTableEntry 3 }

  lsFailureName OBJECT-TYPE
        SYNTAX DisplayString
        ACCESS read-only
        STATUS mandatory
        DESCRIPTION
          "Represents the configured name of the machine which sent the 
           alarm."
        ::= { ss7LinksetFailureAlarmTableEntry 4 }

  lsFailurePointcode OBJECT-TYPE
        SYNTAX DisplayString
        ACCESS read-only
        STATUS mandatory
        DESCRIPTION
          "This object indicates the pointcode associated with the 
	   linkset."
        ::= { ss7LinksetFailureAlarmTableEntry 5 }

  lsFailureTimeStamp OBJECT-TYPE
        SYNTAX TimeString 
        ACCESS read-only
        STATUS mandatory
        DESCRIPTION
         "Indicates the time of the alarm."
        ::= { ss7LinksetFailureAlarmTableEntry 6 }

  ----------------------------------------------------------------------
  -- The following dynamic table is used for SS7 Destination Inaccessibile
  -- Alarms.
  ----------------------------------------------------------------------
  -- 
  ss7DestinationInaccessibleAlarmTable OBJECT-TYPE
        SYNTAX SEQUENCE OF SS7DestinationInaccessibleAlarmTableEntry
        ACCESS not-accessible
        STATUS mandatory
        DESCRIPTION
          "The SS7DestinationAccessAlarmTable contains alarms which indicate
           inaccessible signalling destinations."
        ::= { alarms 19 }

  ss7DestinationInaccessibleAlarmTableEntry OBJECT-TYPE
        SYNTAX SS7DestinationInaccessibleAlarmTableEntry
        ACCESS not-accessible
        STATUS mandatory
        DESCRIPTION
          "This object defines a row within the SS7 Destination 
           Inaccessible Alarm Table.  A row can be uniquely identified
           with the row index."
        INDEX { destInaccessIndex }
        ::= { ss7DestinationInaccessibleAlarmTable 1 }

  SS7DestinationInaccessibleAlarmTableEntry ::= SEQUENCE {
        destInaccessIndex       INTEGER,
        destInaccessKey         INTEGER,
        destInaccessIPAddress   IpAddress,
        destInaccessName        DisplayString,
        destInaccessPointcode   DisplayString,
        destInaccessTimeStamp   TimeString
      }

  destInaccessIndex OBJECT-TYPE
        SYNTAX INTEGER
        ACCESS not-accessible
        STATUS mandatory
        DESCRIPTION
          "Identifies the row number in the table."
        ::= { ss7DestinationInaccessibleAlarmTableEntry 1 }

  destInaccessKey OBJECT-TYPE
        SYNTAX INTEGER
        ACCESS read-only
        STATUS mandatory
        DESCRIPTION
          "Unique identifier for the alarm."
        ::= { ss7DestinationInaccessibleAlarmTableEntry 2 }
  
  destInaccessIPAddress OBJECT-TYPE
        SYNTAX IpAddress
        ACCESS read-only
        STATUS mandatory
        DESCRIPTION
          "This object identifies the IP Address of the machine which 
           sent the alarm."
        ::= { ss7DestinationInaccessibleAlarmTableEntry 3 }

  destInaccessName OBJECT-TYPE
        SYNTAX DisplayString
        ACCESS read-only
        STATUS mandatory
        DESCRIPTION
          "Represents the configured name of the machine which sent the 
           alarm."
        ::= { ss7DestinationInaccessibleAlarmTableEntry 4 }

  destInaccessPointcode OBJECT-TYPE
        SYNTAX DisplayString
        ACCESS read-only
        STATUS mandatory
        DESCRIPTION
          "This object indicates the point code of the inaccessible
  	     signalling destination."
        ::= { ss7DestinationInaccessibleAlarmTableEntry 5 }

  destInaccessTimeStamp OBJECT-TYPE
        SYNTAX TimeString 
        ACCESS read-only
        STATUS mandatory
        DESCRIPTION
         "Indicates the time of the alarm."
        ::= { ss7DestinationInaccessibleAlarmTableEntry 6 }

  ----------------------------------------------------------------------
  -- The following dynamic table is used for SS7 Destination Congested.
  ----------------------------------------------------------------------
  -- 
  ss7DestinationCongestedAlarmTable OBJECT-TYPE
        SYNTAX SEQUENCE OF SS7DestinationCongestedAlarmTableEntry
        ACCESS not-accessible
        STATUS mandatory
        DESCRIPTION
          "The SS7DestinationCongestedAlarmTable contains alarms to indicate
           congestion on the given destination."
        ::= { alarms 20 }

  ss7DestinationCongestedAlarmTableEntry OBJECT-TYPE
        SYNTAX SS7DestinationCongestedAlarmTableEntry
        ACCESS not-accessible
        STATUS mandatory
        DESCRIPTION
          "This object defines a row within the SS7 Destination Congestion
           Table.  A row can be uniquely identified with the row index."
        INDEX { destCongestIndex }
        ::= { ss7DestinationCongestedAlarmTable 1 }

  SS7DestinationCongestedAlarmTableEntry ::= SEQUENCE {
        destCongestIndex           INTEGER,
        destCongestKey             INTEGER,
        destCongestIPAddress       IpAddress,
        destCongestName            DisplayString,
        destCongestPointcode       DisplayString,
        destCongestCongestionLevel INTEGER,
        destCongestTimeStamp       TimeString
      }

  destCongestIndex OBJECT-TYPE
        SYNTAX INTEGER
        ACCESS not-accessible
        STATUS mandatory
        DESCRIPTION
          "Identifies the row number in the table."
        ::= { ss7DestinationCongestedAlarmTableEntry 1 }

  destCongestKey OBJECT-TYPE
        SYNTAX INTEGER
        ACCESS read-only
        STATUS mandatory
        DESCRIPTION
          "Unique identifier for the alarm."
        ::= { ss7DestinationCongestedAlarmTableEntry 2 }
  
  destCongestIPAddress OBJECT-TYPE
        SYNTAX IpAddress
        ACCESS read-only
        STATUS mandatory
        DESCRIPTION
          "This object identifies the IP Address of the machine which 
           sent the alarm."
        ::= { ss7DestinationCongestedAlarmTableEntry 3 }

  destCongestName OBJECT-TYPE
        SYNTAX DisplayString
        ACCESS read-only
        STATUS mandatory
        DESCRIPTION
          "Represents the configured name of the machine which sent the 
           alarm."
        ::= { ss7DestinationCongestedAlarmTableEntry 4 }

  destCongestPointcode OBJECT-TYPE
        SYNTAX DisplayString
        ACCESS read-only
        STATUS mandatory
        DESCRIPTION
          "This object indicates the pointcode of the congested destination."
        ::= { ss7DestinationCongestedAlarmTableEntry 5 }

  destCongestCongestionLevel OBJECT-TYPE
        SYNTAX INTEGER
        ACCESS read-only
        STATUS mandatory
        DESCRIPTION
          "This object indicates the congestion level on a problem SS7 pointcode.
           Possible congestion values are: 
                (0) Normal
                (1) Minor
                (2) Major
                (3) Critical
          "
        ::= { ss7DestinationCongestedAlarmTableEntry 6 }

  destCongestTimeStamp OBJECT-TYPE
        SYNTAX TimeString 
        ACCESS read-only
        STATUS mandatory
        DESCRIPTION
         "Indicates the time of the alarm."
        ::= { ss7DestinationCongestedAlarmTableEntry 7 }

  ----------------------------------------------------------------------
  -- The following dynamic table is used for SS7 Link Alignment Failures.
  ----------------------------------------------------------------------
  -- 
  ss7LinkAlignmentAlarmTable OBJECT-TYPE
        SYNTAX SEQUENCE OF SS7LinkAlignmentAlarmTableEntry
        ACCESS not-accessible
        STATUS mandatory
        DESCRIPTION
          "The SS7LinkAlignmentAlarmTable contains alarms to indicate
           congestion on the CSG."
        ::= { alarms 21 }

  ss7LinkAlignmentAlarmTableEntry OBJECT-TYPE
        SYNTAX SS7LinkAlignmentAlarmTableEntry
        ACCESS not-accessible
        STATUS mandatory
        DESCRIPTION
          "This object defines a row within the SS7 Link Alignment Alarm 
           Table.  A row can be uniquely identified with the row index."
        INDEX { linkAlignIndex }
        ::= { ss7LinkAlignmentAlarmTable 1 }

  SS7LinkAlignmentAlarmTableEntry ::= SEQUENCE {
        linkAlignIndex           INTEGER,
        linkAlignKey             INTEGER,
        linkAlignIPAddress       IpAddress,
        linkAlignName            DisplayString,
        linkAlignLinkCode        INTEGER,
        linkAlignTimeStamp       TimeString,
	linkAlignCardId          DisplayString,
	linkAlignLinkSet         DisplayString
      }

  linkAlignIndex OBJECT-TYPE
        SYNTAX INTEGER
        ACCESS not-accessible
        STATUS mandatory
        DESCRIPTION
          "Identifies the row number in the table."
        ::= { ss7LinkAlignmentAlarmTableEntry 1 }

  linkAlignKey OBJECT-TYPE
        SYNTAX INTEGER
        ACCESS read-only
        STATUS mandatory
        DESCRIPTION
          "Unique identifier for the alarm."
        ::= { ss7LinkAlignmentAlarmTableEntry 2 }
  
  linkAlignIPAddress OBJECT-TYPE
        SYNTAX IpAddress
        ACCESS read-only
        STATUS mandatory
        DESCRIPTION
          "This object identifies the IP Address of the machine which 
           sent the alarm."
        ::= { ss7LinkAlignmentAlarmTableEntry 3 }

  linkAlignName OBJECT-TYPE
        SYNTAX DisplayString
        ACCESS read-only
        STATUS mandatory
        DESCRIPTION
          "Represents the configured name of the machine which sent the 
           alarm."
        ::= { ss7LinkAlignmentAlarmTableEntry 4 }

  linkAlignLinkCode OBJECT-TYPE
        SYNTAX INTEGER
        ACCESS read-only
        STATUS mandatory
        DESCRIPTION
          "This object identifies the signalling link code (SLC) of
	   the affected link."
        ::= { ss7LinkAlignmentAlarmTableEntry 5 }

  linkAlignTimeStamp OBJECT-TYPE
        SYNTAX TimeString 
        ACCESS read-only
        STATUS mandatory
        DESCRIPTION
         "Indicates the time of the alarm."
        ::= { ss7LinkAlignmentAlarmTableEntry 6 }

  linkAlignCardId OBJECT-TYPE
        SYNTAX DisplayString
        ACCESS read-only
        STATUS mandatory
        DESCRIPTION
          "This object identifies the device that hosts the failed link.
	   It provides a physical description of the device, as well as
	   its slot number."
        ::= { ss7LinkAlignmentAlarmTableEntry 7 }

  linkAlignLinkSet OBJECT-TYPE
        SYNTAX DisplayString
        ACCESS read-only
        STATUS mandatory
        DESCRIPTION
          "This object identifies the linkset associated with the link
	   via its adjacent point code."
        ::= { ss7LinkAlignmentAlarmTableEntry 8 }

    csgComplexStateTrapInfo  OBJECT IDENTIFIER ::= { alarms 22 }


    cplxName OBJECT-TYPE
        SYNTAX DisplayString
        ACCESS read-only
        STATUS mandatory
        DESCRIPTION
          "CLLI, A unique identifier of the CSG Complex."
        ::={ csgComplexStateTrapInfo 1 }


    cplxLocEthernetName OBJECT-TYPE
         SYNTAX DisplayString
         ACCESS read-only
         STATUS mandatory
         DESCRIPTION
            " The EthernetName attribute value of the node."
         ::= { csgComplexStateTrapInfo 2 }
 
    cplxLocEthernetIP OBJECT-TYPE
         SYNTAX IpAddress
         ACCESS read-only
         STATUS mandatory
         DESCRIPTION
            " The EthernetIP attribute value of the node."
         ::= { csgComplexStateTrapInfo 3 }
 
    cplxLocOperationalState OBJECT-TYPE
         SYNTAX DisplayString
         ACCESS read-only
         STATUS mandatory
         DESCRIPTION
            " The OperationalState of the node.  
              Possible values are:
                UNKNOWN,
                ENABLED,
                ENABLED_NETDSC,
                ENABLED_NETPAR,
                DISABLED
            "
         ::= { csgComplexStateTrapInfo 4 }

    cplxLocStandbyState OBJECT-TYPE
         SYNTAX DisplayString
         ACCESS read-only
         STATUS mandatory
         DESCRIPTION
            " The StandbyState attribute value of the node.
              Possible values are:
                UNKNOWN,
                HOT_STANDBY,
                COLD_STANDBY,
                WARM_STANDBY,
                PROVIDING_SERVICE
            "
         ::= { csgComplexStateTrapInfo 5 }
 
    cplxLocAvailabilityState OBJECT-TYPE
         SYNTAX DisplayString
         ACCESS read-only
         STATUS mandatory
         DESCRIPTION
            " The AvailabilityState attribute value of the node.
              Possible values are:
                UNKNOWN,
                AVAILABLE,
                DEGRADED,
                OFFLINE
            "
         ::= { csgComplexStateTrapInfo 6 }

    cplxMateEthernetName OBJECT-TYPE
         SYNTAX DisplayString
         ACCESS read-only
         STATUS mandatory
         DESCRIPTION
            " The EthernetName attribute value of the mate node."
         ::= { csgComplexStateTrapInfo 7 }
 
    cplxMateEthernetIP OBJECT-TYPE
         SYNTAX IpAddress
         ACCESS read-only
         STATUS mandatory
         DESCRIPTION
            " The EthernetIP attribute value of the mate node."
         ::= { csgComplexStateTrapInfo 8 }
 
    cplxMateOperationalState OBJECT-TYPE
         SYNTAX DisplayString
         ACCESS read-only
         STATUS mandatory
         DESCRIPTION
            " The OperationalState of the mate node.  
              Possible values are:
                UNKNOWN,
                ENABLED,
                ENABLED_NETDSC,
                ENABLED_NETPAR,
                DISABLED
            "
         ::= { csgComplexStateTrapInfo 9 }

    cplxMateStandbyState OBJECT-TYPE
         SYNTAX DisplayString
         ACCESS read-only
         STATUS mandatory
         DESCRIPTION
            " The StandbyState attribute value of the mate node.
              Possible values are:
                UNKNOWN,
                HOT_STANDBY,
                COLD_STANDBY,
                WARM_STANDBY,
                PROVIDING_SERVICE
            "
         ::= { csgComplexStateTrapInfo 10 }
 
    cplxMateAvailabilityState OBJECT-TYPE
         SYNTAX DisplayString
         ACCESS read-only
         STATUS mandatory
         DESCRIPTION
            " The AvailabilityState attribute value of the mate node.
              Possible values are:
                UNKNOWN,
                AVAILABLE,
                DEGRADED,
                OFFLINE
            "
         ::= { csgComplexStateTrapInfo 11 }

  cplxAlarmStatus OBJECT-TYPE
        SYNTAX DisplayString
        ACCESS read-only
        STATUS mandatory
        DESCRIPTION
          "This object indicates the alarm status of the CSG Complex.
           Possible status are:
                NORMAL, 
                MAJOR,
                CRITICAL
          "
        ::= { csgComplexStateTrapInfo 12}


  ----------------------------------------------------------------------
  -- The following dynamic table contains the LostServer alarms.
  ----------------------------------------------------------------------
  -- 
  lostServerAlarmTable OBJECT-TYPE
        SYNTAX SEQUENCE OF LostServerAlarmTableEntry
        ACCESS not-accessible
        STATUS mandatory
        DESCRIPTION
          ""
        ::= { ncServer 1 }

  lostServerAlarmTableEntry OBJECT-TYPE
        SYNTAX LostServerAlarmTableEntry
        ACCESS not-accessible
        STATUS mandatory
        DESCRIPTION
          "This object defines a row within the Lost Server Alarm
           Table.  A row can be uniquely identified with the row index."
        INDEX { lsIndex }
        ::= { lostServerAlarmTable 1 }

  LostServerAlarmTableEntry ::= SEQUENCE {
        lsIndex         INTEGER,
        lsKey           INTEGER,
        lsIPAddress     IpAddress,
        lsName          DisplayString,
        lsTimeStamp     TimeString
      }

  lsIndex OBJECT-TYPE
        SYNTAX INTEGER
        ACCESS not-accessible
        STATUS mandatory
        DESCRIPTION
          "Identifies the row number in the table."
        ::= { lostServerAlarmTableEntry 1 }

  lsKey OBJECT-TYPE
        SYNTAX INTEGER
        ACCESS read-only
        STATUS mandatory
        DESCRIPTION
          "Unique identifier for the alarm."
        ::= { lostServerAlarmTableEntry 2 }
  
  lsIPAddress OBJECT-TYPE
        SYNTAX IpAddress
        ACCESS read-only
        STATUS mandatory
        DESCRIPTION
          "This object identifies the IP Address of the machine which 
           is lost."
        ::= { lostServerAlarmTableEntry 3 }

  lsName OBJECT-TYPE
        SYNTAX DisplayString
        ACCESS read-only
        STATUS mandatory
        DESCRIPTION
          "The configured name associated with the IP Address of the machine
           which sent the alarm."
        ::= { lostServerAlarmTableEntry 4 }

  lsTimeStamp OBJECT-TYPE
        SYNTAX TimeString 
        ACCESS read-only
        STATUS mandatory
        DESCRIPTION
         "Indicates the time of the alarm."
        ::= { lostServerAlarmTableEntry 5 }


----------------------------------
------  Alarm Status Bits    -----
----------------------------------

  -- 
  -- The following contructs use a packed bit representation to indicate
  -- which alarms are currently being filtered (e.g. alarmMaskInt1), or 
  -- which alarms are currently set (e.g. alarmStatusInt2).
  --
  -- Note that these constructs are defined as being of type Gauge. This 
  -- frees them from having a signed interpretation, thus allowing all 32
  -- bits to be used without risking an SNMP subsytem error if the most
  -- significant bit is set to 1.
  --

  alarmMaskInt1 OBJECT-TYPE
        SYNTAX Gauge 
        ACCESS read-write
        STATUS mandatory
        DESCRIPTION
          "The value of this bit mask reflects the current filtering policy
	   of CSG events and alarms. Management stations which wish to not
	   receive certain events or alarm types from the CSG can modify
	   this value as needed. Note, however, that changes in the 
	   filtration policy affect what is received by all management 
	   stations.
	   
	   Initially, the bit mask is set so that all bits are in a false 
	   state.  Each bit in a true state reflects a currently filtered 
	   event, alarm, or alarm type.

	   The actual bit position meanings are given below. Bit 0 is LSB.

	   Bits
               0  = Generic Normal Alarm
               1  = Generic Warning Alarm
               2  = Generic Minor Alarm
               3  = Generic Major Alarm
               4  = Generic Critical Alarm
               5  = Partition Space Alarm
               6  = Home Gateway Failure Alarm
               7  = Component Not In Provisioned State Alarm
               8  = Component Debug On Alarm
               9  = Component Multiple Restart Alarm
              10 = Component Restart Warning
              11 = NAS Registration Failure Warning
              12 = NAS Failure Alarm
              13 = File Deletion Warning
              14 = File Backup Warning
              15 = Sysman Restart Warning
              16 = File Access Warning
              17 = Home Gateway/NAS Provisioning Mismatch Warning
              18 = SS7 Link Failure Alarm
              19 = SS7 Link Congestion Alarm
              20 = ISUP Failure Alarm
              21 = ISUP Congestion Alarm
              22 = SS7 FEP Congestion Alarm
              23 = SS7 BEP Congestion Alarm
              24 = High Availability Peer Contact Lost Alarm
              25 = SS7 MTP3 Congestion Alarm
              26 = SS7 MTP2 Trunk Failure Alarm
	      27 = SS7 Linkset Failure Alarm
	      28 = SS7 Destination Inaccessible Alarm
              29 = SS7 Destination Congested Alarm
              30 = SS7 Link Alignment Failure Alarm
          "
         ::={alarms 1}
    
  --
  -- LIMITATION: We have a hardcoded limit of 16 components because
  --             of this chosen implementation.
  -- 
  alarmStatusInt1 OBJECT-TYPE
        SYNTAX Gauge 
        ACCESS read-only
        STATUS mandatory
        DESCRIPTION
          "The value of this bit mask indicates that current status of CSG 
           component alarms. Each components is represented by a single 
	   bit within the range occupied by each component alarm type.

           Each bit in a true state reflects a currently raised alarm. The
           actual bit position meanings are given below. Bit 0 is the LSB.

           Bits
            0-15 = Component Not In Provisioned State Alarm
           16-31 = Component Multi Restart Alarm
          "
         ::={alarms 2}

  --
  -- LIMITATION: We have a hardcoded limit of 16 components because
  --             of this chosen implementation.
  -- 
  alarmStatusInt2 OBJECT-TYPE
        SYNTAX Gauge 
        ACCESS read-only
        STATUS mandatory
        DESCRIPTION
          "The value of this bit mask indicates the current status of
	   active CSG alarms. Component-related alarms occupy a range of 
	   bits: each bit within that range represents the alarm status
	   for a particular component.

	   Each bit in a true state reflects a currently raised alarm. The
	   actual bit position meanings are given below. Bit 0 is the LSB.
                        
           Bits
            0-15 = Component Debug On Alarm
           16-23 = Partition Space Alarm
              24 = Home Gateway Failure Alarm
              25 = NAS Failure Alarm
              26 = SS7 Link Failure Alarm
              27 = SS7 Link Congestion Alarm
              28 = ISUP Failure Alarm
              29 = ISUP Congestion Alarm
              30 = High Availability Peer Contact Lost Alarm
              31 = SS7 MTP3 Congestion Alarm
          "
         ::={alarms 3}

  alarmStatusInt3 OBJECT-TYPE
        SYNTAX Gauge 
        ACCESS read-only
        STATUS mandatory
        DESCRIPTION
          "The value of this bit mask indicates the current status of
	   active CSG alarms.

	   Each bit in a true state reflects a currently raised alarm. The
	   actual bit position meanings are given below. Bit 0 is the LSB.
                        
           Bits
               0 = SS7 MTP2 Trunk Failure Alarm
               1 = SS7 Linkset Failure Alarm
               2 = SS7 Destination Inaccessible Alarm
               3 = SS7 Destination Congestion Alarm
               4 = SS7 Link Alignment Failure Alarm
               5 = CSG Complex Status Alarm
               6 = External Ethernet Alarm
          "
         ::={alarms 4}


----------------------------------
------  Alarm Status Bits    -----
----------------------------------

  --
  -- The following contruct use a packed bit representation to indicate
  -- which  alarms over and above that indicated in ( alarmMaskInt1) are currently being filtered
  --
  --

  alarmMaskInt2 OBJECT-TYPE
        SYNTAX Gauge
        ACCESS read-write
        STATUS mandatory
        DESCRIPTION
          "The value of this bit mask reflects the current additional filtering policy
           of CSG events and alarms. Management stations which wish to not
           receive certain events or alarm types from the CSG can modify
           this value as needed. Note, however, that changes in the
           filtration policy affect what is received by all management
           stations.

           Initially, the bit mask is set so that all bits are in a false
           state.  Each bit in a true state reflects a currently filtered
           event, alarm, or alarm type.

           The actual bit position meanings are given below. Bit 0 is LSB.

           Bits
               0  = External Ethernet Alarm
               1  = Cluster Information retrieval Alarm
          "
         ::={alarms 5}

----------------------------------
------  Trap Definitions     -----
----------------------------------

-- Traps will be four digits 
--      Digit 1 represents the subsystem for each trap
--              1 = system
--              2 = component
--              3 = SS7 system
--              4 = High Availability
--              9 = other
--
--      Digits 2 and 3 represent the unique id for trap within the subsystem.
--
--      Digit 4 represents the severity of the trap.
--              1 = normal 2 = warning 3 = minor 4 = major 5 = critical
--
--              NOTE: For each trap, the severity and its meaning are
--                    determined by the application who raised the event
--                    through Survman.
--
-- LIMITATION: We have a hardcoded limitation of 99 traps per subsystem
--             because of the chosen implementation.
--

  ----------------------------------------------------------------------
  -- Generic trap variables, data to send with Warnings.
  -- Not accessible for browsing.
  ----------------------------------------------------------------------
  -- 
  trapCompName OBJECT-TYPE
        SYNTAX DisplayString 
        ACCESS not-accessible
        STATUS mandatory
        DESCRIPTION
          "OID for the Component name."
        ::={traps 1}
        

  trapFileName OBJECT-TYPE
        SYNTAX DisplayString 
        ACCESS not-accessible
        STATUS mandatory
        DESCRIPTION
          "OID for file Name."
        ::={traps 2}

  trapDate OBJECT-TYPE
        SYNTAX TimeString 
        ACCESS not-accessible
        STATUS mandatory
        DESCRIPTION
          "OID for the date."
        ::={traps 3}

  trapGenericStr1 OBJECT-TYPE
        SYNTAX DisplayString
        ACCESS not-accessible
        STATUS mandatory
        DESCRIPTION
          "OID for the generic data."
        ::={traps 4}

  trapIdKey OBJECT-TYPE
        SYNTAX INTEGER
        ACCESS not-accessible
        STATUS mandatory
        DESCRIPTION
          "OID for the identification key."
        ::={traps 5}
        
  trapIPAddress OBJECT-TYPE
        SYNTAX IpAddress
        ACCESS not-accessible
        STATUS mandatory
        DESCRIPTION
          "OID for IP address."
        ::={traps 6}

  trapName OBJECT-TYPE
        SYNTAX DisplayString
        ACCESS not-accessible
        STATUS mandatory
        DESCRIPTION
          "OID for configured name associated with an IpAddress."
        ::={traps 7}

  trapTimeStamp OBJECT-TYPE
        SYNTAX DisplayString
        ACCESS not-accessible
        STATUS mandatory
        DESCRIPTION
          "Indicates the time at which the alarm occurred."
        ::={traps 8}


  ----------------------------------------------------------------------
  -- System Traps.
  ----------------------------------------------------------------------
  -- 
  diskSpaceClear TRAP-TYPE
        ENTERPRISE traps
        VARIABLES  {
          partitionSpaceKey,
          partitionIndex,
          partitionName,
          partitionPercentFull,
	  partitionSpaceTimeStamp
        }
        DESCRIPTION
          "The Trap generated when a disk partition has a space increase 
           after a previously sent DiskSpaceAlarm."
        ::= 1001
      
  diskSpaceAlarm TRAP-TYPE
        ENTERPRISE traps
        VARIABLES  {
          partitionSpaceKey,
          partitionIndex,
          partitionName,
          partitionPercentFull,
	  partitionSpaceTimeStamp
        }
        DESCRIPTION
          "The Trap generated when a disk partition is running out of space 
           provisioned state."
        ::= 1004

   etherCardTrapClear TRAP-TYPE
        ENTERPRISE traps
        DESCRIPTION
          " The Trap generated when the external ethernet card becomes available."
        ::= 1011

   etherCardTrapMajor TRAP-TYPE
        ENTERPRISE traps
        DESCRIPTION
          "The Trap generated when the external ethernet card is down." 
        ::= 1014

   etherCardTrapCritical TRAP-TYPE
        ENTERPRISE traps
        DESCRIPTION
          "The Trap generated when the external ethernet card is down."
        ::= 1015

  ----------------------------------------------------------------------
  -- Component Traps.
  ----------------------------------------------------------------------
  -- 
  compDebugOff TRAP-TYPE
        ENTERPRISE traps
        VARIABLES  {
          compDebugKey,
          componentIndex,
          componentName,
	  compDebugTimeStamp
        }
        DESCRIPTION
          "The Trap generated when a Component turns off its debug info." 
        ::= 2001

  compDebugOn TRAP-TYPE
        ENTERPRISE traps
        VARIABLES  {
          compDebugKey,
          componentIndex,
          componentName,
	  compDebugTimeStamp
        }
        DESCRIPTION
          "The Trap generated when a Component turns on its debug info." 
        ::= 2002

  compStateClear TRAP-TYPE
        ENTERPRISE traps
        VARIABLES  {
          compProvStateKey,
          componentIndex,
          componentName,
          compProvStateStatus,
          compSecsInCurrentState,
	  compProvStateTimeStamp
        }
        DESCRIPTION 
          "The Trap generated when a component goes to its provisioned 
           states after a CompStatusAlarm trap has been sent."
        ::= 2011 
      
  compStateAlarm TRAP-TYPE
        ENTERPRISE traps
        VARIABLES  {
          compProvStateKey,
          componentIndex,
          componentName,
          compProvStateStatus,
          compSecsInCurrentState,
	  compProvStateTimeStamp
        }
        DESCRIPTION 
          "The Trap generated when a component is not in it's
           provisioned state."
        ::= 2014 
      
  restartStateClear TRAP-TYPE
        ENTERPRISE traps
        VARIABLES  {
          compRestartKey,
          componentIndex,
          componentName,
          compRestartStatus,
	  compRestartTimeStamp
        }
        DESCRIPTION 
          "The Trap generated when a component goes to its provisioned 
           states after a RestartStateAlarm trap has been sent."
        ::= 2021 
      
  restartStateAlarm TRAP-TYPE
        ENTERPRISE traps
        VARIABLES  {
          compRestartKey,
          componentIndex,
          componentName,
          compRestartStatus,
	  compRestartTimeStamp
        }
        DESCRIPTION 
          "The Trap generated when a component restarts repeatedly."
        ::= 2024 
      
  ----------------------------------------------------------------------
  -- SS7 Traps.
  ----------------------------------------------------------------------
  -- 
  ss7LinkFailureAlarm TRAP-TYPE
        ENTERPRISE traps
        VARIABLES  {
          lfIndex,
          lfKey,
          lfIPAddress,
          lfLinkCode,
          lfName,
          lfCardId,
	  lfLinkSet,
	  lfTimeStamp
        }
        DESCRIPTION 
          "Trap generated for an SS7 link failure."
        ::= 3004 
      
  ss7LinkFailureClear TRAP-TYPE
        ENTERPRISE traps
        VARIABLES  {
          lfIndex,
          lfKey,
          lfIPAddress,
          lfLinkCode,
          lfName,
          lfCardId,
	  lfLinkSet,
	  lfTimeStamp
        }
        DESCRIPTION 
          "Trap generated to clear an SS7 link failure."
        ::= 3001 
      
  ss7LinkCongestionAlarm TRAP-TYPE
        ENTERPRISE traps
        VARIABLES  {
          lcIndex,
          lcKey,
          lcIPAddress,
          lcLinkCode,
          lcName,
          lcCardId,
	  lcLinkSet,
	  lcTimeStamp
        }
        DESCRIPTION 
          "Trap generated for congestion on an SS7 Link."
        ::= 3012 

  ss7LinkCongestionClear TRAP-TYPE
        ENTERPRISE traps
        VARIABLES  {
          lcIndex,
          lcKey,
          lcIPAddress,
          lcLinkCode,
          lcName,
          lcCardId,
	  lcLinkSet,
	  lcTimeStamp
        }
        DESCRIPTION 
          "Trap generated to indicate there is no longer congestion on 
           an SS7 link."
        ::= 3011
      
  ss7ISUPFailureAlarm TRAP-TYPE
        ENTERPRISE traps
        VARIABLES  {
          ifIndex,
          ifKey,
          ifIPAddress,
          ifName,
	  ifTimeStamp
        }
        DESCRIPTION 
          "Trap generated to indicate ISUP failure."
        ::= 3025 
      
  ss7ISUPFailureClear TRAP-TYPE
        ENTERPRISE traps
        VARIABLES  {
          ifIndex,
          ifKey,
          ifIPAddress,
          ifName,
	  ifTimeStamp
        }
        DESCRIPTION 
          "Trap generated to clear an ISUP failure alarm."
        ::= 3021 
      
  ss7ISUPCongestionAlarm TRAP-TYPE
        ENTERPRISE traps
        VARIABLES  {
          icIndex,
          icKey,
          icIPAddress,
          icCongestionLevel,
          icName,
	  icTimeStamp
        }
        DESCRIPTION 
          "Trap generated to indicate congestion with the ISUP protocol
           stack."
        ::= 3033 
      
  ss7ISUPCongestionClear TRAP-TYPE
        ENTERPRISE traps
        VARIABLES  {
          icIndex,
          icKey,
          icIPAddress,  
          icCongestionLevel,
          icName,
	  icTimeStamp
        }
        DESCRIPTION 
          "Trap generated to indicate there is no longer congestion with
           the ISUP protocol stack."
        ::= 3031 
      
  ss7FEPCongestionWarning TRAP-TYPE
        ENTERPRISE traps
        VARIABLES  {
          trapIdKey,
          trapIPAddress,
          trapName,
	  trapTimeStamp
        }
        DESCRIPTION 
          "Notification trap generated to indicate congestion encountered 
           by the SS7 front-end process."
        ::= 3042 
      
  ss7BEPCongestionWarning TRAP-TYPE
        ENTERPRISE traps
        VARIABLES  {
          trapIdKey,
          trapIPAddress,
          trapName,
	  trapTimeStamp
        }
        DESCRIPTION 
          "Notification trap generated to indicate congestion encountered 
           by the SS7 back-end process."
        ::= 3052 
      
  ss7MTP3CongestionMinor TRAP-TYPE
        ENTERPRISE traps
        VARIABLES  {
          mtp3Index,
          mtp3Key,
          mtp3IPAddress,
          mtp3Name,
	  mtp3TimeStamp
        }
        DESCRIPTION 
          "Trap generated for MTP3 congestion."
        ::= 3063 

  ss7MTP3CongestionMajor TRAP-TYPE
        ENTERPRISE traps
        VARIABLES  {
          mtp3Index,
          mtp3Key,
          mtp3IPAddress,
          mtp3Name,
	  mtp3TimeStamp
        }
        DESCRIPTION 
          "Trap generated for MTP3 congestion."
        ::= 3064
 
  ss7MTP3CongestionCritical TRAP-TYPE
        ENTERPRISE traps
        VARIABLES  {
          mtp3Index,
          mtp3Key,
          mtp3IPAddress,
          mtp3Name,
	  mtp3TimeStamp
        }
        DESCRIPTION 
          "Trap generated for MTP3 congestion."
        ::= 3065 

  ss7MTP3CongestionClear TRAP-TYPE
        ENTERPRISE traps
        VARIABLES  {
          mtp3Index,
          mtp3Key,
          mtp3IPAddress,
          mtp3Name,
	  mtp3TimeStamp
        }
        DESCRIPTION 
          "Trap generated to indicate there is no longer MTP3 congestion."
        ::= 3061
      
  ss7MTP2TrunkFailureAlarm TRAP-TYPE
        ENTERPRISE traps
        VARIABLES  {
          mtp2Index,
          mtp2Key,
          mtp2IPAddress,
          mtp2Name,
          mtp2CardId,
          mtp2AlarmCondition,
	  mtp2TimeStamp
        }
        DESCRIPTION 
          "Trap generated to indicate an MTP2 trunk failure condition."
        ::= 3075

  ss7MTP2TrunkFailureClear TRAP-TYPE
        ENTERPRISE traps
        VARIABLES  {
          mtp2Index,
          mtp2Key,
          mtp2IPAddress,
          mtp2Name,
          mtp2CardId,
	  mtp2TimeStamp
        }
        DESCRIPTION 
          "Trap generated to clear an MTP2 trunk failure alarm."
        ::= 3071

  ss7LinksetFailureAlarm TRAP-TYPE
        ENTERPRISE traps
        VARIABLES  {
          lsFailureIndex,
          lsFailureKey,
          lsFailureIPAddress,
          lsFailureName,
          lsFailurePointcode,
	  lsFailureTimeStamp
        }
        DESCRIPTION 
          "Trap generated to indicate a linkset failure."
        ::= 3085

  ss7LinksetFailureClear TRAP-TYPE
        ENTERPRISE traps
        VARIABLES  {
          lsFailureIndex,
          lsFailureKey,
          lsFailureIPAddress,
          lsFailureName,
          lsFailurePointcode,
	  lsFailureTimeStamp
        }
        DESCRIPTION 
          "Trap generated to clear a linkset failure alarm."
        ::= 3081

  ss7DestinationInaccessible TRAP-TYPE
        ENTERPRISE traps
        VARIABLES  {
          destInaccessIndex,
          destInaccessKey,
          destInaccessIPAddress,
          destInaccessName,
          destInaccessPointcode,
	  destInaccessTimeStamp
        }
        DESCRIPTION 
          "Trap generated to indicate that a signalling destination
           is inaccessible. A destination is considered inaccessible
           once Transfer Prohibited (TFP) messages are received which
           indicate that the route to that destination is prohibited."
        ::= 3092

  ss7DestinationAccessible TRAP-TYPE
        ENTERPRISE traps
        VARIABLES  {
          destInaccessIndex,
          destInaccessKey,
          destInaccessIPAddress,
          destInaccessName,
          destInaccessPointcode,
	  destInaccessTimeStamp
        }
        DESCRIPTION 
          "Trap generated to clear a destination inacessible alarm. An
           inaccessible signalling destination is considered accessible
           once Transfer Allowed (TFA) messages are sent along its
           prohibited signalling routes."
        ::= 3091

  ss7DestinationCongestedAlarm TRAP-TYPE
        ENTERPRISE traps
        VARIABLES  {
          destCongestIndex,
          destCongestKey,
          destCongestIPAddress,
          destCongestName,
          destCongestPointcode,
          destCongestCongestionLevel,
	  destCongestTimeStamp
        }
        DESCRIPTION 
          "Trap generated to indicate congestion at an SS7
           destination."
        ::= 3103

  ss7DestinationCongestedClear TRAP-TYPE
        ENTERPRISE traps
        VARIABLES  {
          destCongestIndex,
          destCongestKey,
          destCongestIPAddress,
          destCongestName,
          destCongestPointcode,
          destCongestCongestionLevel,
	  destCongestTimeStamp
        }
        DESCRIPTION 
          "Trap generated to indicate that there is no longer
           congestion at an SS7 destination."
        ::= 3101

  ss7LinkAlignmentFailureAlarm TRAP-TYPE
        ENTERPRISE traps
        VARIABLES  {
          linkAlignIndex,
          linkAlignKey,
          linkAlignIPAddress,
          linkAlignName,
          linkAlignLinkCode,
	  linkAlignCardId,
	  linkAlignLinkSet,
	  linkAlignTimeStamp
        }
        DESCRIPTION 
          "Trap generated to indicate alignment failure on a
           datalink."
        ::= 3114

  ss7LinkAlignmentFailureClear TRAP-TYPE
        ENTERPRISE traps
        VARIABLES  {
          linkAlignIndex,
          linkAlignKey,
          linkAlignIPAddress,
          linkAlignName,
          linkAlignLinkCode,
	  linkAlignCardId,
	  linkAlignLinkSet,
	  linkAlignTimeStamp
        }
        DESCRIPTION 
          "Trap generated to clear a datalink alignment failure
           alarm."
        ::= 3111

  ----------------------------------------------------------------------
  -- High Availability Traps.
  ----------------------------------------------------------------------
  -- 
   ncLostServerTrap TRAP-TYPE
        ENTERPRISE traps
        VARIABLES  {
          lsIndex,
          lsKey,
          lsName,
          lsIPAddress,
          lsTimeStamp
        }
        DESCRIPTION 
          "This trap is generated when the CSG loses contact with
           its peer in the cluster. The variables in this trap identify
           the server that has been lost. The originator of this trap is 
           implicitly defined." 
        ::= 4014 

   ncFoundServerTrap TRAP-TYPE
        ENTERPRISE traps
        VARIABLES  {
          lsIndex,
          lsKey,
          lsName,
          lsIPAddress,
          lsTimeStamp
        }
        DESCRIPTION
          "This trap is generated when the  initially comes into contact
           with or regains contact with its peer in the cluster. The variables 
           in this trap identify the server that has been found. The 
           originator of this trap is implicitly defined."
        ::= 4011

   ncStateChangeTrap TRAP-TYPE
        ENTERPRISE traps
        VARIABLES  {
          ncEthernetName,
          ncEthernetIP,
          ncOperationalState,
          ncStandbyState,
          ncAvailabilityState
        }
        DESCRIPTION
          "This trap is generated when any of the state values change."
        ::= 4022


   csgComplexStateTrapClear TRAP-TYPE
        ENTERPRISE traps
        VARIABLES  {
          cplxName,
          cplxLocEthernetName,
          cplxLocEthernetIP,
          cplxLocOperationalState,
          cplxLocStandbyState,
          cplxLocAvailabilityState,
          cplxMateEthernetName,
          cplxMateEthernetIP,
          cplxMateOperationalState,
          cplxMateStandbyState,
          cplxMateAvailabilityState,
          cplxAlarmStatus
        }
        DESCRIPTION
          "This trap is generated when any of the state values change
           Severity is determined only by the operational and standby states
           of both servers."
        ::= 4031

   csgComplexStateTrapMajor TRAP-TYPE
        ENTERPRISE traps
        VARIABLES  {
          cplxName,
          cplxLocEthernetName,
          cplxLocEthernetIP,
          cplxLocOperationalState,
          cplxLocStandbyState,
          cplxLocAvailabilityState,
          cplxMateEthernetName,
          cplxMateEthernetIP,
          cplxMateOperationalState,
          cplxMateStandbyState,
          cplxMateAvailabilityState,
          cplxAlarmStatus
        }
        DESCRIPTION
          "This trap is generated when any of the state values change
           Severity is determined only by the operational and standby states
           of both servers."
        ::= 4034

   csgComplexStateTrapCritical TRAP-TYPE
        ENTERPRISE traps
        VARIABLES  {
          cplxName,
          cplxLocEthernetName,
          cplxLocEthernetIP,
          cplxLocOperationalState,
          cplxLocStandbyState,
          cplxLocAvailabilityState,
          cplxMateEthernetName,
          cplxMateEthernetIP,
          cplxMateOperationalState,
          cplxMateStandbyState,
          cplxMateAvailabilityState,
          cplxAlarmStatus
        }
        DESCRIPTION
          "This trap is generated when any of the state values change
           Severity is determined only by the operational and standby states
           of both servers."
        ::= 4035


   cisRetrievalFailureTrapMajor TRAP-TYPE
        ENTERPRISE traps
        DESCRIPTION
          "This trap is generated when the TruCluster ASE information 
           retrieval attempts failed repeatedly. " 
        ::= 4044

  ----------------------------------------------------------------------
  -- Other misc traps.
  ----------------------------------------------------------------------
  -- 
  genericNormal TRAP-TYPE
        ENTERPRISE traps
        VARIABLES  {
          trapIdKey,
          trapGenericStr1,
	  trapTimeStamp
        }
        DESCRIPTION 
          "The Trap generated for generic normal priority text messages" 
        ::= 9001
      
  genericWarning TRAP-TYPE
        ENTERPRISE traps
        VARIABLES  {
          trapIdKey,
          trapGenericStr1,
	  trapTimeStamp
        }
        DESCRIPTION 
          "The Trap generated for generic warning priority text messages" 
        ::= 9002
      
  genericMinor TRAP-TYPE
        ENTERPRISE traps
        VARIABLES  {
          trapIdKey,
          trapGenericStr1,
	  trapTimeStamp
        }
        DESCRIPTION 
          "The Trap generated for generic minor priority text messages" 
        ::= 9003
      
  genericMajor TRAP-TYPE
        ENTERPRISE traps
        VARIABLES  {
          trapIdKey,
          trapGenericStr1,
	  trapTimeStamp
        }
        DESCRIPTION 
          "The Trap generated for generic major priority text messages" 
        ::= 9004
      
  genericCritical TRAP-TYPE
        ENTERPRISE traps
        VARIABLES  {
          trapIdKey,
          trapGenericStr1,
	  trapTimeStamp
        }
        DESCRIPTION 
          "The Trap generated for generic critical priority text messages" 
        ::= 9005
      
  hgStatusClear TRAP-TYPE
        ENTERPRISE traps
        VARIABLES  {
          hgKey,
          hgIndex,
          hgName,
          hgIPAddress,
	  hgAlarmTimeStamp
        }
        DESCRIPTION 
          "The Trap generated when a Home Gateway Status returns to 
           normal after having previously been in the failed status."
        ::= 9011 
      
  hgStatusAlarm TRAP-TYPE
        ENTERPRISE traps
        VARIABLES  {
          hgKey,
          hgIndex,
          hgName,
          hgIPAddress,
	  hgAlarmTimeStamp
        }
        DESCRIPTION 
          "The Trap generated when a Home Gateway is indicated to be failed."
        ::= 9014 

  nasStatusClear TRAP-TYPE
        ENTERPRISE traps
        VARIABLES  {
          nasKey,
          nasIndex,
          nasName,
          nasIPAddress,
	  nasAlarmTimeStamp,
          nasCmplxName
         }
         DESCRIPTION
           "The Trap generated when a rapport registers after
            having previously been in the failed status."
         ::= 9021

  nasStatusAlarm TRAP-TYPE
        ENTERPRISE traps
        VARIABLES  {
          nasKey,
          nasIndex,
          nasName,
          nasIPAddress,
	  nasAlarmTimeStamp,
          nasCmplxName
         }
         DESCRIPTION
           "The Trap generated when a Nas is indicated to be failed."
         ::= 9024


----------------------------------
--     LINK OM Data              --
----------------------------------

  --------------------------------------------------------------------
  --
  -- The following section contains definitions of tables and scalar 
  -- objects used to store LINK Data 
  --
  -- 
  -- It is an extension of LinkTable. Therefore has the same index set as LinkTable.
  --
  ----------------------------------------------------------------------------------

  linkOMTable OBJECT-TYPE
        SYNTAX SEQUENCE OF LinkOMTableEntry
        ACCESS  not-accessible 
        STATUS  mandatory
        DESCRIPTION
          "The LinkTable contains information about each signaling
           link on the CSG"
        ::= { linkOMs 1}

  linkOMTableEntry OBJECT-TYPE
        SYNTAX LinkOMTableEntry
        ACCESS  not-accessible
        STATUS  mandatory
        DESCRIPTION
          "An entry in the LinkTable. Indexed by linkIndex"
        INDEX { linksetIndex, linkIndex }
        ::= {linkOMTable 1}

  -- definition of LinkOMTableEntry
  LinkOMTableEntry ::= SEQUENCE {
        linkOMId               INTEGER,
        linkOMSetId            INTEGER,
        linkFailures           Counter,
        linkCongestions        Counter,
        linkInhibits           Counter,
        linkTransmittedMSUs    Counter,
        linkReceivedMSUs       Counter,
        linkRemoteProcOutages  Counter
   }

  linkOMId OBJECT-TYPE
        SYNTAX INTEGER
        ACCESS read-only
        STATUS mandatory
        DESCRIPTION
          "The id of the link."
        ::= { linkOMTableEntry 1 }

  linkOMSetId OBJECT-TYPE
        SYNTAX INTEGER
        ACCESS read-only
        STATUS mandatory
        DESCRIPTION
          "The id of the linkset."
        ::= { linkOMTableEntry 2 }

  
  linkFailures  OBJECT-TYPE
        SYNTAX Counter
        ACCESS read-only
        STATUS mandatory
        DESCRIPTION
          "Number of times this signaling link has failed."
        ::={linkOMTableEntry 3}

  linkCongestions  OBJECT-TYPE
        SYNTAX Counter
        ACCESS read-only
        STATUS mandatory
        DESCRIPTION
          "Number of times this signaling link has Congested."
        ::={linkOMTableEntry 4}

  linkInhibits   OBJECT-TYPE
        SYNTAX Counter
        ACCESS read-only
        STATUS mandatory
        DESCRIPTION
          "Number of times this signaling link has been inhibited."
        ::={linkOMTableEntry 5}
     

  linkTransmittedMSUs     OBJECT-TYPE
        SYNTAX Counter
        ACCESS read-only
        STATUS mandatory
        DESCRIPTION
          "Number of messages sent on this signaling link." 
        ::={linkOMTableEntry 6}

  linkReceivedMSUs OBJECT-TYPE
        SYNTAX Counter
        ACCESS read-only
        STATUS mandatory
        DESCRIPTION
          "Number of messages received on this signaling link." 
        ::={linkOMTableEntry 7}
  
  linkRemoteProcOutages OBJECT-TYPE
        SYNTAX Counter
        ACCESS read-only
        STATUS mandatory
        DESCRIPTION
          "Number of times the remote processor outgaes have been reported."
        ::={linkOMTableEntry 8 }



----------------------------------
--     Maintenance OM Data             --
----------------------------------

  --------------------------------------------------------------------
  --
  -- The following section contains definitions of all the  objects 
  -- used to store OM Data related to Maintenance 
  --
  --------------------------------------------------------------------

  bLATimerExpiries OBJECT-TYPE
        SYNTAX Counter
        ACCESS read-only
        STATUS mandatory
        DESCRIPTION
          "Number of times the BLA timer has expired."
        ::={maintenanceOMs 1 }

  rLCTimerExpiries OBJECT-TYPE
        SYNTAX Counter
        ACCESS read-only
        STATUS mandatory
        DESCRIPTION
          "Number of times the RLC timer has expired."
        ::={maintenanceOMs 2 }

  uBATimerExpiries OBJECT-TYPE
        SYNTAX Counter
        ACCESS read-only
        STATUS mandatory
        DESCRIPTION
          "Number of times the UBA timer has expired."
        ::={maintenanceOMs 3 }

  rSATimerExpiries OBJECT-TYPE
        SYNTAX Counter
        ACCESS read-only
        STATUS mandatory
        DESCRIPTION
          "Number of times the RSA timer has expired."
        ::={maintenanceOMs 4 }


----------------------------------
--     CALL OM Data             --
----------------------------------

  --------------------------------------------------------------------
  --
  -- The following section contains definitions of all the  objects
  -- used to store OM Data related to Calls
  --
  --------------------------------------------------------------------

  outCallAttempts OBJECT-TYPE
        SYNTAX Counter
        ACCESS read-only
        STATUS mandatory
        DESCRIPTION
          "Total number of outgoing call legs attempted."
        ::={callOMs 1 }

  outCallNormalCompletions OBJECT-TYPE
        SYNTAX Counter
        ACCESS read-only
        STATUS mandatory
        DESCRIPTION
          "Total number of outgoing call legs  completed normally."
        ::={callOMs 2 }

  outCallAbnormalCompletions OBJECT-TYPE
        SYNTAX Counter
        ACCESS read-only
        STATUS mandatory
        DESCRIPTION
          "Total number of  outgoing call legs completed abnormally."
        ::={callOMs 3 }


  userBusyOutCallRejects OBJECT-TYPE
        SYNTAX Counter
        ACCESS read-only
        STATUS mandatory
        DESCRIPTION
          "Total Number of outgoing call legs rejected due to user busy signal."
        ::={callOMs 4 }


  tempFailOutCallRejects OBJECT-TYPE
        SYNTAX Counter
        ACCESS read-only
        STATUS mandatory
        DESCRIPTION
          "Total Number of outgoing call legs rejected due to temporary failure."
        ::={callOMs 5 }


  userUnavailableOutCallRejects OBJECT-TYPE
        SYNTAX Counter
        ACCESS read-only
        STATUS mandatory
        DESCRIPTION
          "Total number of outgoing call legs failed due to user not available."
        ::={callOMs 6 }


  abnormalReleaseOutCallRejects OBJECT-TYPE
        SYNTAX Counter
        ACCESS read-only
        STATUS mandatory
        DESCRIPTION
          "Total Number of outgoing call legs rejected due to abnormal release."
        ::={callOMs 7 }


  otherOutCallRejects OBJECT-TYPE
        SYNTAX Counter
        ACCESS read-only
        STATUS mandatory
        DESCRIPTION
          "Total Number of outgoing call legs rejected due to other reasons."
        ::={callOMs 8 }


  cumulativeActiveOutCalls OBJECT-TYPE
        SYNTAX Counter
        ACCESS read-only
        STATUS mandatory
        DESCRIPTION
          "Cumulatvie Number of outgoing call legs active so far."
        ::={callOMs 9 }

  currentlyActiveOutCalls OBJECT-TYPE
        SYNTAX Counter
        ACCESS read-only
        STATUS mandatory
        DESCRIPTION
          "Total Number of outgoing call legs currently active."
        ::={callOMs 10 }

  currentlyActiveDigitalOutCalls OBJECT-TYPE
        SYNTAX Counter
        ACCESS read-only
        STATUS mandatory
        DESCRIPTION
          "Total Number of outgoing digital call legs currently active."
        ::={callOMs 11 }


  currentlyActiveAnalogOutCalls OBJECT-TYPE
        SYNTAX Counter
        ACCESS read-only
        STATUS mandatory
        DESCRIPTION
          "Total Number of outgoing analog call legs  currently active."
        ::={callOMs 12 }


  inCallAttempts OBJECT-TYPE
        SYNTAX Counter
        ACCESS read-only
        STATUS mandatory
        DESCRIPTION
          "Total number of incoming call legs attempted."
        ::={callOMs 13 }

  inCallNormalCompletions OBJECT-TYPE
        SYNTAX Counter
        ACCESS read-only
        STATUS mandatory
        DESCRIPTION
          "Total number of incoming call legs  completed normally."
        ::={callOMs 14 }

  inCallAbnormalCompletions OBJECT-TYPE
        SYNTAX Counter
        ACCESS read-only
        STATUS mandatory
        DESCRIPTION
          "Total number of  incoming call legs completed abnormally."
        ::={callOMs 15 }


  userBusyInCallRejects OBJECT-TYPE
        SYNTAX Counter
        ACCESS read-only
        STATUS mandatory
        DESCRIPTION
          "Total Number of incoming call legs rejected due to user busy signal."
        ::={callOMs 16 }


  tempFailInCallRejects OBJECT-TYPE
        SYNTAX Counter
        ACCESS read-only
        STATUS mandatory
        DESCRIPTION
          "Total Number of incoming call legs rejected due to temporary failure."
        ::={callOMs 17 }


  userUnavailableInCallRejects OBJECT-TYPE
        SYNTAX Counter
        ACCESS read-only
        STATUS mandatory
        DESCRIPTION
          "Total number of incoming call legs failed due to user not available."
        ::={callOMs 18 }


  abnormalReleaseInCallRejects OBJECT-TYPE
        SYNTAX Counter
        ACCESS read-only
        STATUS mandatory
        DESCRIPTION
          "Total Number of incoming call legs rejected due to abnormal release."
        ::={callOMs 19 }


  otherInCallRejects OBJECT-TYPE
        SYNTAX Counter
        ACCESS read-only
        STATUS mandatory
        DESCRIPTION
          "Total Number of incoming call legs rejected due to other reasons."
        ::={callOMs 20 }


  cumulativeActiveInCalls OBJECT-TYPE
        SYNTAX Counter
        ACCESS read-only
        STATUS mandatory
        DESCRIPTION
          "Cumulatvie Number of incoming call legs active so far."
        ::={callOMs 21 }

  currentlyActiveInCalls OBJECT-TYPE
        SYNTAX Counter
        ACCESS read-only
        STATUS mandatory
        DESCRIPTION
          "Total Number of incoming call legs currently active."
        ::={callOMs 22 }

  currentlyActiveDigitalInCalls OBJECT-TYPE
        SYNTAX Counter
        ACCESS read-only
        STATUS mandatory
        DESCRIPTION
          "Total Number of incoming digital call legs currently active."
        ::={callOMs 23 }


  currentlyActiveAnalogInCalls OBJECT-TYPE
        SYNTAX Counter
        ACCESS read-only
        STATUS mandatory
        DESCRIPTION
          "Total Number of incoming analog call legs  currently active."
        ::={callOMs 24 }


-------------------------------------------
--     CALL OM Data based on Trunk Group --
-------------------------------------------

  --------------------------------------------------------------------
  --
  -- The following section contains definitions of all the  objects
  -- used to store OM Data related to Calls on a trunk group basis.
  --
  --------------------------------------------------------------------

  ------------------------------------------------------------------------------------
  --
  -- The following dynamic table is used to store the OM data for a given trunk gourp.
  --
  ------------------------------------------------------------------------------------


  trunkCallOMTable OBJECT-TYPE
        SYNTAX SEQUENCE OF TrunkCallOMTableEntry
        ACCESS  not-accessible 
        STATUS  mandatory
        DESCRIPTION
          "The TrunkCallOMTable contains call related OMs on a trunk group basis"
        ::= { trunkGroupOMs 1}

  trunkCallOMTableEntry OBJECT-TYPE
        SYNTAX TrunkCallOMTableEntry
        ACCESS  not-accessible
        STATUS  mandatory
        DESCRIPTION
          "An entry in the TrunkCallOMTable. Indexed by trunkCallOMIndex."
        INDEX {trunkCallOMIndex}
        ::= {trunkCallOMTable 1}

  -- definition of TrunkCallOMTableEntry
  TrunkCallOMTableEntry ::= SEQUENCE {
        trunkCallOMIndex                INTEGER,
        trunkGroupCLLI                  DisplayString,
        numberOfCircuits                INTEGER,

         trunkOutCallAttempts                    Counter,
         trunkOutCallNormalCompletions           Counter,
         trunkOutCallAbnormalCompletions         Counter,
         trunkUserBusyOutCallRejects             Counter,
         trunkTempFailOutCallRejects             Counter,
         trunkUserUnavailableOutCallRejects      Counter,
         trunkAbnormalReleaseOutCallRejects      Counter,
         trunkOtherOutCallRejects                Counter,
         trunkCumulativeActiveOutCalls           Counter,
         trunkCurrentlyActiveOutCalls            Counter,
         trunkCurrentlyActiveDigitalOutCalls     Counter,
         trunkCurrentlyActiveAnalogOutCalls      Counter,

         trunkInCallAttempts                    Counter,
         trunkInCallNormalCompletions           Counter,
         trunkInCallAbnormalCompletions         Counter,
         trunkUserBusyInCallRejects             Counter,
         trunkTempFailInCallRejects             Counter,
         trunkUserUnavailableInCallRejects      Counter,
         trunkAbnormalReleaseInCallRejects      Counter,
         trunkOtherInCallRejects                Counter,
         trunkCumulativeActiveInCalls           Counter,
         trunkCurrentlyActiveInCalls            Counter,
         trunkCurrentlyActiveDigitalInCalls     Counter,
         trunkCurrentlyActiveAnalogInCalls      Counter,


         trunkAllActiveCalls                  Counter, 
         trunkOccupancyPerCCS                 INTEGER,
         trafficInCCSs                        Counter,
         trafficInCCSIncomings                Counter,
         localBusyInCCSs                      Counter,
         remoteBusyInCCSs                     Counter
      }
  
  trunkCallOMIndex     OBJECT-TYPE
        SYNTAX INTEGER 
        ACCESS not-accessible
        STATUS mandatory
        DESCRIPTION
          "Identifies a trunk group index."
        ::={trunkCallOMTableEntry 1}

  trunkGroupCLLI       OBJECT-TYPE
        SYNTAX DisplayString
        ACCESS read-only
        STATUS mandatory
        DESCRIPTION
          "The Common Language Location Identifier(CLLI), 
           a unique alphanumeric value to identify this Trunk Group."
        ::= { trunkCallOMTableEntry 2 }

   numberOfCircuits    OBJECT-TYPE
        SYNTAX INTEGER
        ACCESS read-only
        STATUS mandatory
        DESCRIPTION
          "Total Number of Circuits provisioned against this trunk group." 
        ::={trunkCallOMTableEntry 3 }
 
  trunkOutCallAttempts OBJECT-TYPE
        SYNTAX Counter
        ACCESS read-only
        STATUS mandatory
        DESCRIPTION
          "Total number of outgoing call legs attempted."
        ::={trunkCallOMTableEntry 4 }

  trunkOutCallNormalCompletions OBJECT-TYPE
        SYNTAX Counter
        ACCESS read-only
        STATUS mandatory
        DESCRIPTION
          "Total number of outgoing call legs  completed normally."
        ::={trunkCallOMTableEntry 5 }

  trunkOutCallAbnormalCompletions OBJECT-TYPE
        SYNTAX Counter
        ACCESS read-only
        STATUS mandatory
        DESCRIPTION
          "Total number of  outgoing call legs completed abnormally."
        ::={trunkCallOMTableEntry 6 }


  trunkUserBusyOutCallRejects OBJECT-TYPE
        SYNTAX Counter
        ACCESS read-only
        STATUS mandatory
        DESCRIPTION
          "Total Number of outgoing call legs rejected due to user busy signal."
        ::={trunkCallOMTableEntry 7 }


  trunkTempFailOutCallRejects OBJECT-TYPE
        SYNTAX Counter
        ACCESS read-only
        STATUS mandatory
        DESCRIPTION
          "Total Number of outgoing call legs rejected due to temporary failure."
        ::={trunkCallOMTableEntry 8 }


  trunkUserUnavailableOutCallRejects OBJECT-TYPE
        SYNTAX Counter
        ACCESS read-only
        STATUS mandatory
        DESCRIPTION
          "Total number of outgoing call legs failed due to user not available."
        ::={trunkCallOMTableEntry 9 }


  trunkAbnormalReleaseOutCallRejects OBJECT-TYPE
        SYNTAX Counter
        ACCESS read-only
        STATUS mandatory
        DESCRIPTION
          "Total Number of outgoing call legs rejected due to abnormal release."
        ::={trunkCallOMTableEntry 10 }


  trunkOtherOutCallRejects OBJECT-TYPE
        SYNTAX Counter
        ACCESS read-only
        STATUS mandatory
        DESCRIPTION
          "Total Number of outgoing call legs rejected due to other reasons."
        ::={trunkCallOMTableEntry 11 }


  trunkCumulativeActiveOutCalls OBJECT-TYPE
        SYNTAX Counter
        ACCESS read-only
        STATUS mandatory
        DESCRIPTION
          "Cumulatvie Number of outgoing call legs active so far."
        ::={trunkCallOMTableEntry 12 }

  trunkCurrentlyActiveOutCalls OBJECT-TYPE
        SYNTAX Counter
        ACCESS read-only
        STATUS mandatory
        DESCRIPTION
          "Total Number of outgoing call legs currently active."
        ::={trunkCallOMTableEntry 13 }

  trunkCurrentlyActiveDigitalOutCalls OBJECT-TYPE
        SYNTAX Counter
        ACCESS read-only
        STATUS mandatory
        DESCRIPTION
          "Total Number of outgoing digital call legs currently active."
        ::={trunkCallOMTableEntry 14 }


  trunkCurrentlyActiveAnalogOutCalls OBJECT-TYPE
        SYNTAX Counter
        ACCESS read-only
        STATUS mandatory
        DESCRIPTION
          "Total Number of outgoing analog call legs  currently active."
        ::={trunkCallOMTableEntry 15 }


  trunkInCallAttempts OBJECT-TYPE
        SYNTAX Counter
        ACCESS read-only
        STATUS mandatory
        DESCRIPTION
          "Total number of incoming call legs attempted."
        ::={trunkCallOMTableEntry 16 }

  trunkInCallNormalCompletions OBJECT-TYPE
        SYNTAX Counter
        ACCESS read-only
        STATUS mandatory
        DESCRIPTION
          "Total number of incoming call legs  completed normally."
        ::={trunkCallOMTableEntry 17 }

  trunkInCallAbnormalCompletions OBJECT-TYPE
        SYNTAX Counter
        ACCESS read-only
        STATUS mandatory
        DESCRIPTION
          "Total number of  incoming call legs completed abnormally."
        ::={trunkCallOMTableEntry 18 }


  trunkUserBusyInCallRejects OBJECT-TYPE
        SYNTAX Counter
        ACCESS read-only
        STATUS mandatory
        DESCRIPTION
          "Total Number of incoming call legs rejected due to user busy signal."
        ::={trunkCallOMTableEntry 19 }


  trunkTempFailInCallRejects OBJECT-TYPE
        SYNTAX Counter
        ACCESS read-only
        STATUS mandatory
        DESCRIPTION
          "Total Number of incoming call legs rejected due to temporary failure."
        ::={trunkCallOMTableEntry 20 }


  trunkUserUnavailableInCallRejects OBJECT-TYPE
        SYNTAX Counter
        ACCESS read-only
        STATUS mandatory
        DESCRIPTION
          "Total number of incoming call legs failed due to user not available."
        ::={trunkCallOMTableEntry 21 }


  trunkAbnormalReleaseInCallRejects OBJECT-TYPE
        SYNTAX Counter
        ACCESS read-only
        STATUS mandatory
        DESCRIPTION
          "Total Number of incoming call legs rejected due to abnormal release."
        ::={trunkCallOMTableEntry 22 }


  trunkOtherInCallRejects OBJECT-TYPE
        SYNTAX Counter
        ACCESS read-only
        STATUS mandatory
        DESCRIPTION
          "Total Number of incoming call legs rejected due to other reasons."
        ::={trunkCallOMTableEntry 23 }


  trunkCumulativeActiveInCalls OBJECT-TYPE
        SYNTAX Counter
        ACCESS read-only
        STATUS mandatory
        DESCRIPTION
          "Cumulatvie Number of incoming call legs active so far."
        ::={trunkCallOMTableEntry 24 }

  trunkCurrentlyActiveInCalls OBJECT-TYPE
        SYNTAX Counter
        ACCESS read-only
        STATUS mandatory
        DESCRIPTION
          "Total Number of incoming call legs currently active."
        ::={trunkCallOMTableEntry 25 }

  trunkCurrentlyActiveDigitalInCalls OBJECT-TYPE
        SYNTAX Counter
        ACCESS read-only
        STATUS mandatory
        DESCRIPTION
          "Total Number of incoming digital call legs currently active."
        ::={trunkCallOMTableEntry 26 }


  trunkCurrentlyActiveAnalogInCalls OBJECT-TYPE
        SYNTAX Counter
        ACCESS read-only
        STATUS mandatory
        DESCRIPTION
          "Total Number of incoming analog call legs  currently active."
        ::={trunkCallOMTableEntry 27 }


   trunkAllActiveCalls    OBJECT-TYPE
        SYNTAX INTEGER
        ACCESS read-only
        STATUS mandatory
        DESCRIPTION
          "Total number of currently active call legs (all type)."
        ::={trunkCallOMTableEntry 28 }


   trunkOccupancyPerCCS    OBJECT-TYPE
        SYNTAX INTEGER
        ACCESS read-only
        STATUS mandatory
        DESCRIPTION
          "Trunk occupancy in Centum Call Seconds."
        ::={trunkCallOMTableEntry 29 }

  trafficInCCSs OBJECT-TYPE
        SYNTAX Counter
        ACCESS read-only
        STATUS mandatory
        DESCRIPTION
          "Scanned om for tgms that are call busy"
        ::={trunkCallOMTableEntry 30 }

  trafficInCCSIncomings OBJECT-TYPE
        SYNTAX Counter
        ACCESS read-only
        STATUS mandatory
        DESCRIPTION
          "Scanned Om on tgms with an incoming call."
        ::={trunkCallOMTableEntry 31 }

  localBusyInCCSs OBJECT-TYPE
        SYNTAX Counter
        ACCESS read-only
        STATUS mandatory
        DESCRIPTION
          "Scanned om for tgms that are locally blocked."
        ::={trunkCallOMTableEntry 32 }

  remoteBusyInCCSs OBJECT-TYPE
        SYNTAX Counter
        ACCESS read-only
        STATUS mandatory
        DESCRIPTION
          "Scanned om for tgms that are remoteley blocked."
        ::={trunkCallOMTableEntry 33 }


  ------------------------------------------------------------------------------------
  --
  -- The following dynamic table is used to store the OM data for a given nas.
  --
  ------------------------------------------------------------------------------------


  nasCallOMTable OBJECT-TYPE
        SYNTAX SEQUENCE OF NasCallOMTableEntry
        ACCESS  not-accessible 
        STATUS  mandatory
        DESCRIPTION
          "The NasCallOMTable contains call related OMs on a nas basis"
        ::= { nasOMs 1}

  nasCallOMTableEntry OBJECT-TYPE
        SYNTAX NasCallOMTableEntry
        ACCESS  not-accessible
        STATUS  mandatory
        DESCRIPTION
          "An entry in the NasCallOMTable. Indexed by nasCallOMIndex."
        INDEX {nasCallOMIndex}
        ::= {nasCallOMTable 1}

  -- definition of NasCallOMTableEntry
  NasCallOMTableEntry ::= SEQUENCE {
         nasCallOMIndex                INTEGER,
         nasName1                  DisplayString,
         numberOfPorts               INTEGER,

         nasOutCallAttempts                    Counter,
         nasOutCallNormalCompletions           Counter,
         nasOutCallAbnormalCompletions         Counter,
         nasUserBusyOutCallRejects             Counter,
         nasTempFailOutCallRejects             Counter,
         nasUserUnavailableOutCallRejects      Counter,
         nasAbnormalReleaseOutCallRejects      Counter,
         nasOtherOutCallRejects                Counter,
         nasCumulativeActiveOutCalls           Counter,
         nasCurrentlyActiveOutCalls            Counter,
         nasCurrentlyActiveDigitalOutCalls     Counter,
         nasCurrentlyActiveAnalogOutCalls      Counter,

         nasInCallAttempts                    Counter,
         nasInCallNormalCompletions           Counter,
         nasInCallAbnormalCompletions         Counter,
         nasUserBusyInCallRejects             Counter,
         nasTempFailInCallRejects             Counter,
         nasUserUnavailableInCallRejects      Counter,
         nasAbnormalReleaseInCallRejects      Counter,
         nasOtherInCallRejects                Counter,
         nasCumulativeActiveInCalls           Counter,
         nasCurrentlyActiveInCalls            Counter,
         nasCurrentlyActiveDigitalInCalls     Counter,
         nasCurrentlyActiveAnalogInCalls      Counter,


         nasAllActiveCalls                  Counter, 
         nasMaxPortsUsed                    INTEGER,
         nasMinPortsUsed                    INTEGER, 
         nasCurrentlyInUsePorts             INTEGER
      }
  
  nasCallOMIndex     OBJECT-TYPE
        SYNTAX INTEGER 
        ACCESS not-accessible
        STATUS mandatory
        DESCRIPTION
          "Identifies a nas Call OM ."
        ::={nasCallOMTableEntry 1}

  nasName1       OBJECT-TYPE
        SYNTAX DisplayString
        ACCESS read-only
        STATUS mandatory
        DESCRIPTION
          "A unique alphanumeric value to identify this Nas."
        ::= { nasCallOMTableEntry 2 }

   numberOfPorts  OBJECT-TYPE
        SYNTAX INTEGER
        ACCESS read-only
        STATUS mandatory
        DESCRIPTION
          "Total Number of  Ports provisioned against this nas." 
        ::={nasCallOMTableEntry 3 }
 
  nasOutCallAttempts OBJECT-TYPE
        SYNTAX Counter
        ACCESS read-only
        STATUS mandatory
        DESCRIPTION
          "Total number of outgoing call legs attempted."
        ::={nasCallOMTableEntry 4 }

  nasOutCallNormalCompletions OBJECT-TYPE
        SYNTAX Counter
        ACCESS read-only
        STATUS mandatory
        DESCRIPTION
          "Total number of outgoing call legs  completed normally."
        ::={nasCallOMTableEntry 5 }

  nasOutCallAbnormalCompletions OBJECT-TYPE
        SYNTAX Counter
        ACCESS read-only
        STATUS mandatory
        DESCRIPTION
          "Total number of  outgoing call legs completed abnormally."
        ::={nasCallOMTableEntry 6 }


  nasUserBusyOutCallRejects OBJECT-TYPE
        SYNTAX Counter
        ACCESS read-only
        STATUS mandatory
        DESCRIPTION
          "Total Number of outgoing call legs rejected due to user busy signal."
        ::={nasCallOMTableEntry 7 }


  nasTempFailOutCallRejects OBJECT-TYPE
        SYNTAX Counter
        ACCESS read-only
        STATUS mandatory
        DESCRIPTION
          "Total Number of outgoing call legs rejected due to temporary failure."
        ::={nasCallOMTableEntry 8 }


  nasUserUnavailableOutCallRejects OBJECT-TYPE
        SYNTAX Counter
        ACCESS read-only
        STATUS mandatory
        DESCRIPTION
          "Total number of outgoing call legs failed due to user not available."
        ::={nasCallOMTableEntry 9 }


  nasAbnormalReleaseOutCallRejects OBJECT-TYPE
        SYNTAX Counter
        ACCESS read-only
        STATUS mandatory
        DESCRIPTION
          "Total Number of outgoing call legs rejected due to abnormal release."
        ::={nasCallOMTableEntry 10 }


  nasOtherOutCallRejects OBJECT-TYPE
        SYNTAX Counter
        ACCESS read-only
        STATUS mandatory
        DESCRIPTION
          "Total Number of outgoing call legs rejected due to other reasons."
        ::={nasCallOMTableEntry 11 }


  nasCumulativeActiveOutCalls OBJECT-TYPE
        SYNTAX Counter
        ACCESS read-only
        STATUS mandatory
        DESCRIPTION
          "Cumulatvie Number of outgoing call legs active so far."
        ::={nasCallOMTableEntry 12 }

  nasCurrentlyActiveOutCalls OBJECT-TYPE
        SYNTAX Counter
        ACCESS read-only
        STATUS mandatory
        DESCRIPTION
          "Total Number of outgoing call legs currently active."
        ::={nasCallOMTableEntry 13 }

  nasCurrentlyActiveDigitalOutCalls OBJECT-TYPE
        SYNTAX Counter
        ACCESS read-only
        STATUS mandatory
        DESCRIPTION
          "Total Number of outgoing digital call legs currently active."
        ::={nasCallOMTableEntry 14 }


  nasCurrentlyActiveAnalogOutCalls OBJECT-TYPE
        SYNTAX Counter
        ACCESS read-only
        STATUS mandatory
        DESCRIPTION
          "Total Number of outgoing analog call legs  currently active."
        ::={nasCallOMTableEntry 15 }


  nasInCallAttempts OBJECT-TYPE
        SYNTAX Counter
        ACCESS read-only
        STATUS mandatory
        DESCRIPTION
          "Total number of incoming call legs attempted."
        ::={nasCallOMTableEntry 16 }

  nasInCallNormalCompletions OBJECT-TYPE
        SYNTAX Counter
        ACCESS read-only
        STATUS mandatory
        DESCRIPTION
          "Total number of incoming call legs  completed normally."
        ::={nasCallOMTableEntry 17 }

  nasInCallAbnormalCompletions OBJECT-TYPE
        SYNTAX Counter
        ACCESS read-only
        STATUS mandatory
        DESCRIPTION
          "Total number of  incoming call legs completed abnormally."
        ::={nasCallOMTableEntry 18 }


  nasUserBusyInCallRejects OBJECT-TYPE
        SYNTAX Counter
        ACCESS read-only
        STATUS mandatory
        DESCRIPTION
          "Total Number of incoming call legs rejected due to user busy signal."
        ::={nasCallOMTableEntry 19 }


  nasTempFailInCallRejects OBJECT-TYPE
        SYNTAX Counter
        ACCESS read-only
        STATUS mandatory
        DESCRIPTION
          "Total Number of incoming call legs rejected due to temporary failure."
        ::={nasCallOMTableEntry 20 }


  nasUserUnavailableInCallRejects OBJECT-TYPE
        SYNTAX Counter
        ACCESS read-only
        STATUS mandatory
        DESCRIPTION
          "Total number of incoming call legs failed due to user not available."
        ::={nasCallOMTableEntry 21 }


  nasAbnormalReleaseInCallRejects OBJECT-TYPE
        SYNTAX Counter
        ACCESS read-only
        STATUS mandatory
        DESCRIPTION
          "Total Number of incoming call legs rejected due to abnormal release."
        ::={nasCallOMTableEntry 22 }


  nasOtherInCallRejects OBJECT-TYPE
        SYNTAX Counter
        ACCESS read-only
        STATUS mandatory
        DESCRIPTION
          "Total Number of incoming call legs rejected due to other reasons."
        ::={nasCallOMTableEntry 23 }


  nasCumulativeActiveInCalls OBJECT-TYPE
        SYNTAX Counter
        ACCESS read-only
        STATUS mandatory
        DESCRIPTION
          "Cumulatvie Number of incoming call legs active so far."
        ::={nasCallOMTableEntry 24 }

  nasCurrentlyActiveInCalls OBJECT-TYPE
        SYNTAX Counter
        ACCESS read-only
        STATUS mandatory
        DESCRIPTION
          "Total Number of incoming call legs currently active."
        ::={nasCallOMTableEntry 25 }

  nasCurrentlyActiveDigitalInCalls OBJECT-TYPE
        SYNTAX Counter
        ACCESS read-only
        STATUS mandatory
        DESCRIPTION
          "Total Number of incoming digital call legs currently active."
        ::={nasCallOMTableEntry 26 }


  nasCurrentlyActiveAnalogInCalls OBJECT-TYPE
        SYNTAX Counter
        ACCESS read-only
        STATUS mandatory
        DESCRIPTION
          "Total Number of incoming analog call legs  currently active."
        ::={nasCallOMTableEntry 27 }


   nasAllActiveCalls    OBJECT-TYPE
        SYNTAX INTEGER
        ACCESS read-only
        STATUS mandatory
        DESCRIPTION
          "Total number of currently active call legs (all type)."
        ::={nasCallOMTableEntry 28 }

   nasMaxPortsUsed    OBJECT-TYPE
        SYNTAX INTEGER
        ACCESS read-only
        STATUS mandatory
        DESCRIPTION
          "Maximum number of ports used in this nas since the last system restart."
        ::={nasCallOMTableEntry 29 }

   nasMinPortsUsed    OBJECT-TYPE
        SYNTAX INTEGER
        ACCESS read-only
        STATUS mandatory
        DESCRIPTION
          "Minimum number of ports used in this nas since the last system restart."
        ::={nasCallOMTableEntry 30 }

   nasCurrentlyInUsePorts    OBJECT-TYPE
        SYNTAX INTEGER
        ACCESS read-only
        STATUS mandatory
        DESCRIPTION
          "Number of ports currently in use."
        ::={nasCallOMTableEntry 31 }

---------------------------------------------------
--     CALL OM Data based on called phone number --
---------------------------------------------------

  --
  -- The following section contains definitions of all the  objects
  -- used to store OM Data related to Calls on a called phone number basis.
  --
  --------------------------------------------------------------------------

  ------------------------------------------------------------------------------------
  --
  -- The following dynamic table is used to store the OM data for a given phone number.
  --
  ------------------------------------------------------------------------------------

  phoneCallOMTable OBJECT-TYPE
        SYNTAX SEQUENCE OF PhoneCallOMTableEntry
        ACCESS  not-accessible 
        STATUS  mandatory
        DESCRIPTION
          "The PhoneCallOMTable contains call related OMs on a phone number basis"
        ::= { phoneNumberOMs 1}

  phoneCallOMTableEntry OBJECT-TYPE
        SYNTAX PhoneCallOMTableEntry
        ACCESS  not-accessible
        STATUS  mandatory
        DESCRIPTION
          "An entry in the PhoneCallOMTable. Indexed by phoneGroupIndex."
        INDEX {phoneCallOMIndex}
        ::= {phoneCallOMTable 1}

  -- definition of PhoneCallOMTableEntry
  PhoneCallOMTableEntry ::= SEQUENCE {
        phoneCallOMIndex                 INTEGER,
        phoneNumber                      DisplayString,

         phoneDialCallAttempts                    Counter,
         phoneDialCallNormalCompletions           Counter,
         phoneDialCallAbnormalCompletions         Counter,
         phoneUserBusyDialCallRejects             Counter,
         phoneTempFailDialCallRejects             Counter,
         phoneUserUnavailableDialCallRejects      Counter,
         phoneAbnormalReleaseDialCallRejects      Counter,
         phoneOtherDialCallRejects                Counter,
         phoneCumulativeActiveDialCalls           Counter,
         phoneCurrentlyActiveDialCalls            Counter,
         phoneCurrentlyActiveDigitalDialCalls     Counter,
         phoneCurrentlyActiveAnalogDialCalls      Counter

      }
  
  phoneCallOMIndex      OBJECT-TYPE
        SYNTAX INTEGER 
        ACCESS not-accessible
        STATUS mandatory
        DESCRIPTION
          "Uniquely identifies an entry in this table."
        ::={phoneCallOMTableEntry 1}

  phoneNumber           OBJECT-TYPE
        SYNTAX DisplayString
        ACCESS read-only
        STATUS mandatory
        DESCRIPTION
          "Phone number for the underlying Call OM record."
        ::={phoneCallOMTableEntry 2}

  phoneDialCallAttempts OBJECT-TYPE
        SYNTAX Counter
        ACCESS read-only
        STATUS mandatory
        DESCRIPTION
          "Total number of dial calls attempted."
        ::={phoneCallOMTableEntry 3 }

  phoneDialCallNormalCompletions OBJECT-TYPE
        SYNTAX Counter
        ACCESS read-only
        STATUS mandatory
        DESCRIPTION
          "Total number of dial calls  completed normally."
        ::={phoneCallOMTableEntry 4 }

  phoneDialCallAbnormalCompletions OBJECT-TYPE
        SYNTAX Counter
        ACCESS read-only
        STATUS mandatory
        DESCRIPTION
          "Total number of  dial calls completed abnormally."
        ::={phoneCallOMTableEntry 5 }


  phoneUserBusyDialCallRejects OBJECT-TYPE
        SYNTAX Counter
        ACCESS read-only
        STATUS mandatory
        DESCRIPTION
          "Total Number of dial calls rejected due to user busy signal."
        ::={phoneCallOMTableEntry 6 }


  phoneTempFailDialCallRejects OBJECT-TYPE
        SYNTAX Counter
        ACCESS read-only
        STATUS mandatory
        DESCRIPTION
          "Total Number of dial calls rejected due to temporary failure."
        ::={phoneCallOMTableEntry 7 }


  phoneUserUnavailableDialCallRejects OBJECT-TYPE
        SYNTAX Counter
        ACCESS read-only
        STATUS mandatory
        DESCRIPTION
          "Total number of dial calls failed due to user not available."
        ::={phoneCallOMTableEntry 8 }


  phoneAbnormalReleaseDialCallRejects OBJECT-TYPE
        SYNTAX Counter
        ACCESS read-only
        STATUS mandatory
        DESCRIPTION
          "Total Number of dial calls rejected due to abnormal release."
        ::={phoneCallOMTableEntry 9 }


  phoneOtherDialCallRejects OBJECT-TYPE
        SYNTAX Counter
        ACCESS read-only
        STATUS mandatory
        DESCRIPTION
          "Total Number of dial calls rejected due to other reasons."
        ::={phoneCallOMTableEntry 10 }


  phoneCumulativeActiveDialCalls OBJECT-TYPE
        SYNTAX Counter
        ACCESS read-only
        STATUS mandatory
        DESCRIPTION
          "Cumulatvie Number of dial calls active so far."
        ::={phoneCallOMTableEntry 11 }

  phoneCurrentlyActiveDialCalls OBJECT-TYPE
        SYNTAX Counter
        ACCESS read-only
        STATUS mandatory
        DESCRIPTION
          "Total Number of dial calls currently active."
        ::={phoneCallOMTableEntry 12 }

  phoneCurrentlyActiveDigitalDialCalls OBJECT-TYPE
        SYNTAX Counter
        ACCESS read-only
        STATUS mandatory
        DESCRIPTION
          "Total Number of digital dial calls currently active."
        ::={phoneCallOMTableEntry 13 }


  phoneCurrentlyActiveAnalogDialCalls OBJECT-TYPE
        SYNTAX Counter
        ACCESS read-only
        STATUS mandatory
        DESCRIPTION
          "Total Number of analog dial calls currently active."
        ::={phoneCallOMTableEntry 14 }



---------------------------------------------------
--     MIB for system level OM data              --
---------------------------------------------------

  -------------------------------------------------------------------
  --
  -- The following section contains definitions of all the  objects
  -- used to store this server's system level  OM Data.
  --
  -------------------------------------------------------------------

  csgComplexCLLI OBJECT-TYPE
        SYNTAX DisplayString
        ACCESS read-only
        STATUS mandatory
        DESCRIPTION
          "A unique identifier of the CSG Complex."
        ::={ systemOMs 1 }

  serverHostName      OBJECT-TYPE
        SYNTAX DisplayString
        ACCESS read-only
        STATUS mandatory
        DESCRIPTION
          "Host Name of this server."
        ::={ systemOMs 2}

  serverIpAddress     OBJECT-TYPE
        SYNTAX IpAddress
        ACCESS read-only
        STATUS mandatory
        DESCRIPTION
          "IP address of this server."
        ::={ systemOMs 3 }
 
  serverCLLI          OBJECT-TYPE
        SYNTAX DisplayString
        ACCESS read-only
        STATUS mandatory
        DESCRIPTION
          "A unique identifier of this server (common in the telco world)."
        ::={ systemOMs 4 }

  mateServerHostName      OBJECT-TYPE
        SYNTAX DisplayString
        ACCESS read-only
        STATUS mandatory
        DESCRIPTION
          "Host Name of this server."
        ::={ systemOMs 5 }

  mateServerIpAddress     OBJECT-TYPE
        SYNTAX IpAddress
        ACCESS read-only
        STATUS mandatory
        DESCRIPTION
          "IP address of this server."
        ::={ systemOMs 6 }

  serverMemSize       OBJECT-TYPE
        SYNTAX INTEGER
        ACCESS read-only
        STATUS mandatory
        DESCRIPTION
          "Memory size in mega bytes of this server."
        ::={ systemOMs 8 }

  provisionedDPCs OBJECT-TYPE
        SYNTAX INTEGER
        ACCESS read-only
        STATUS mandatory
        DESCRIPTION
          "Number of destination point codes provisioned."
        ::={ systemOMs 9 }

  provisionedCircuits OBJECT-TYPE
        SYNTAX INTEGER
        ACCESS read-only
        STATUS mandatory
        DESCRIPTION
          "Number of circuits provisioned."
        ::={ systemOMs 10 }

  inserviceCircuits OBJECT-TYPE
        SYNTAX INTEGER
        ACCESS read-only
        STATUS mandatory
        DESCRIPTION
          "Number of circuits in service.
           This number goes up or down at any given time."
        ::={ systemOMs 11 }

  provisionedNASes OBJECT-TYPE
        SYNTAX INTEGER
        ACCESS read-only
        STATUS mandatory
        DESCRIPTION
          "Number of NASes provisioned."
        ::={ systemOMs 12 }

  aliveNASes OBJECT-TYPE
        SYNTAX INTEGER
        ACCESS read-only
        STATUS mandatory
        DESCRIPTION
          "Number of NASes known to be alive.
           This number goes up or down at any given time."
        ::={ systemOMs 13 }

  inserviceNASes OBJECT-TYPE
        SYNTAX INTEGER
        ACCESS read-only
        STATUS mandatory
        DESCRIPTION
          "Number of NASes in service.
           This number goes up or down at any given time."
        ::={ systemOMs 14 }

  provsionedCards OBJECT-TYPE
        SYNTAX INTEGER
        ACCESS read-only
        STATUS mandatory
        DESCRIPTION
          "Number of NAS cards provisioned."
        ::={ systemOMs 15 }

  inserviceCards OBJECT-TYPE
        SYNTAX INTEGER
        ACCESS read-only
        STATUS mandatory
        DESCRIPTION
          "Number of NAS cards in service.
           This number goes up or down at any given time."
        ::={ systemOMs 16 }

  provisionedPorts OBJECT-TYPE
        SYNTAX INTEGER
        ACCESS read-only
        STATUS mandatory
        DESCRIPTION
          "Number of ports provisioned."
        ::={ systemOMs 17 }

  inservicePorts OBJECT-TYPE
        SYNTAX INTEGER
        ACCESS read-only
        STATUS mandatory
        DESCRIPTION
          "Number of ports in service.
           This number goes up or down at any given time."
        ::={ systemOMs 18 }

  userCPUUsage OBJECT-TYPE
        SYNTAX INTEGER
        ACCESS read-only
        STATUS mandatory
        DESCRIPTION
          "Percentage of CPU used in user domain. 
           Survman computes this value in every 600 seconds. The value
           stored in the MIB will be the last one computed."
        ::={ systemOMs 19 }

  systemCPUUsage OBJECT-TYPE
        SYNTAX INTEGER
        ACCESS read-only
        STATUS mandatory
        DESCRIPTION
          "Percentage of CPU used in system domain in this server. 
           Survman computes this value in every 600 seconds. The value
           stored in the MIB will be the last one computed."
        ::={ systemOMs 20 }

  totalCPUUsage OBJECT-TYPE
        SYNTAX INTEGER
        ACCESS read-only
        STATUS mandatory
        DESCRIPTION
          "Percentage of CPU used in total in this server 
           Survman computes this value in every 600 seconds. The value
           stored in the MIB will be the last one computed."
        ::={ systemOMs 21 }

  maxCPUUsage OBJECT-TYPE
        SYNTAX INTEGER
        ACCESS read-only
        STATUS mandatory
        DESCRIPTION
          "High water measurement.
           Maximum CPU Usage (%) in this  server.
           Survman computes this value in every 600 seconds. The value
           stored in the MIB will be the last one computed."
        ::={ systemOMs 22 }
 
  avgLoad  OBJECT-TYPE
        SYNTAX INTEGER
        ACCESS read-only
        STATUS mandatory
        DESCRIPTION
          "Average CPU load factor in this server.
           Survman computes this value in every 600 seconds. The value
           stored in the MIB will be the last one computed."
        ::={ systemOMs 23 }

  systemCallRate OBJECT-TYPE
        SYNTAX INTEGER
        ACCESS read-only
        STATUS mandatory
        DESCRIPTION
          "System Call rate (per second) in this Cserver.
           Survman computes this value in every 600 seconds. The value
           stored in the MIB will be the one computed the last time."
        ::={ systemOMs 24 }

  contextSwitchRate OBJECT-TYPE
        SYNTAX INTEGER
        ACCESS read-only
        STATUS mandatory
        DESCRIPTION
          "Process context switching rate (per second) in this server.
           Survman computes this value in every 600 seconds. The value
           stored in the MIB will be the one computed the last time."
        ::={ systemOMs 25 }

  lastUpdateOMFile OBJECT-TYPE
        SYNTAX DisplayString
        ACCESS read-only
        STATUS mandatory
        DESCRIPTION
          "Name of the last updated OM file."
        ::={ systemOMs 26 }

  -- 
END
