Nortel-MsCarrier-MscPassport-FrTraceRcvrMIB
DEFINITIONS ::= BEGIN



IMPORTS

      OBJECT-TYPE
   FROM RFC-1212

      mscPassportMIBs
   FROM Nortel-MsCarrier-MscPassport-UsefulDefinitionsMIB

      RowPointer,
      DisplayString,
      StorageType,
      RowStatus,
      Integer32,
      Unsigned32
   FROM Nortel-MsCarrier-MscPassport-StandardTextualConventionsMIB

      AsciiString,
      Hex,
      NonReplicated,
      HexString,
      EnterpriseDateAndTime,
      DigitString
   FROM Nortel-MsCarrier-MscPassport-TextualConventionsMIB

      mscTraceIndex,
      mscTraceRcvr,
      mscTraceSessionIndex,
      mscTraceRcvrIndex,
      mscTraceSession
   FROM Nortel-MsCarrier-MscPassport-TraceBaseMIB;




-- LAST-UPDATED   "9909010000Z"
-- ORGANIZATION   "Nortel Networks"
-- CONTACT-INFO   "
--         Nortel Carrier Data Network Management
--         
--         Postal:       P.O. Box 3511, Station C 
--                       Ottawa, Ontario 
--                       Canada  K1Y 4H7
--         
--         via the WEB:  http://www.nortelnetworks.com  
--                       select 'Contact Us' from the menu
--          
--         via phone:    1-800-4NORTEL"
-- DESCRIPTION
--    "The module describing the Nortel MsCarrier MscPassport
--     FrTraceRcvr Enterprise MIB."

frTraceRcvrMIB OBJECT IDENTIFIER ::= { mscPassportMIBs 139 }










-- Trace Rcvr/<string> FrameRelay
-- This component identifies the access method used by the receiver of 
-- the trace data as Frame Relay.

mscTraceRcvrFr OBJECT IDENTIFIER ::= { mscTraceRcvr 3 }



mscTraceRcvrFrRowStatusTable OBJECT-TYPE
   SYNTAX     SEQUENCE OF MscTraceRcvrFrRowStatusEntry
   ACCESS     not-accessible
   STATUS     mandatory
   DESCRIPTION
     "This entry controls the addition and deletion of 
      mscTraceRcvrFr components."
::= { mscTraceRcvrFr 1 }

mscTraceRcvrFrRowStatusEntry OBJECT-TYPE
   SYNTAX     MscTraceRcvrFrRowStatusEntry
   ACCESS     not-accessible
   STATUS     mandatory
   DESCRIPTION
     "A single entry in the table represents a single 
      mscTraceRcvrFr component."
   INDEX {
      mscTraceIndex,
      mscTraceRcvrIndex,
      mscTraceRcvrFrIndex }
::= { mscTraceRcvrFrRowStatusTable 1 }

MscTraceRcvrFrRowStatusEntry ::= SEQUENCE {
   mscTraceRcvrFrRowStatus
      RowStatus,
   mscTraceRcvrFrComponentName
      DisplayString,
   mscTraceRcvrFrStorageType
      StorageType,
   mscTraceRcvrFrIndex
      NonReplicated }

mscTraceRcvrFrRowStatus OBJECT-TYPE
   SYNTAX     RowStatus 
   ACCESS     read-write
   STATUS     mandatory
   DESCRIPTION
     "This variable is used as the basis for SNMP naming of
      mscTraceRcvrFr components.
      These components can be added and deleted."
::= { mscTraceRcvrFrRowStatusEntry 1 }

mscTraceRcvrFrComponentName OBJECT-TYPE
   SYNTAX     DisplayString 
   ACCESS     read-only
   STATUS     mandatory
   DESCRIPTION
     "This variable provides the component's string name for
      use with the ASCII Console Interface"
::= { mscTraceRcvrFrRowStatusEntry 2 }

mscTraceRcvrFrStorageType OBJECT-TYPE
   SYNTAX     StorageType 
   ACCESS     read-only
   STATUS     mandatory
   DESCRIPTION
     "This variable represents the storage type value for the
      mscTraceRcvrFr tables."
::= { mscTraceRcvrFrRowStatusEntry 4 }

mscTraceRcvrFrIndex OBJECT-TYPE
   SYNTAX     NonReplicated 
   ACCESS     not-accessible
   STATUS     mandatory
   DESCRIPTION
     "This variable represents the index for the mscTraceRcvrFr tables."
::= { mscTraceRcvrFrRowStatusEntry 10 }


-- Trace Rcvr/<string> Fr DataNetworkAddress
-- This component defines the calling end of the trace connection. It 
-- includes the set of attributes which apply to a Vc connection to a 
-- Frame Relay trace receiver.

mscTraceRcvrFrDna OBJECT IDENTIFIER ::= { mscTraceRcvrFr 2 }



mscTraceRcvrFrDnaRowStatusTable OBJECT-TYPE
   SYNTAX     SEQUENCE OF MscTraceRcvrFrDnaRowStatusEntry
   ACCESS     not-accessible
   STATUS     mandatory
   DESCRIPTION
     "This entry controls the addition and deletion of 
      mscTraceRcvrFrDna components."
::= { mscTraceRcvrFrDna 1 }

mscTraceRcvrFrDnaRowStatusEntry OBJECT-TYPE
   SYNTAX     MscTraceRcvrFrDnaRowStatusEntry
   ACCESS     not-accessible
   STATUS     mandatory
   DESCRIPTION
     "A single entry in the table represents a single 
      mscTraceRcvrFrDna component."
   INDEX {
      mscTraceIndex,
      mscTraceRcvrIndex,
      mscTraceRcvrFrIndex,
      mscTraceRcvrFrDnaIndex }
::= { mscTraceRcvrFrDnaRowStatusTable 1 }

MscTraceRcvrFrDnaRowStatusEntry ::= SEQUENCE {
   mscTraceRcvrFrDnaRowStatus
      RowStatus,
   mscTraceRcvrFrDnaComponentName
      DisplayString,
   mscTraceRcvrFrDnaStorageType
      StorageType,
   mscTraceRcvrFrDnaIndex
      NonReplicated }

mscTraceRcvrFrDnaRowStatus OBJECT-TYPE
   SYNTAX     RowStatus 
   ACCESS     read-only
   STATUS     mandatory
   DESCRIPTION
     "This variable is used as the basis for SNMP naming of
      mscTraceRcvrFrDna components.
      These components cannot be added nor deleted."
::= { mscTraceRcvrFrDnaRowStatusEntry 1 }

mscTraceRcvrFrDnaComponentName OBJECT-TYPE
   SYNTAX     DisplayString 
   ACCESS     read-only
   STATUS     mandatory
   DESCRIPTION
     "This variable provides the component's string name for
      use with the ASCII Console Interface"
::= { mscTraceRcvrFrDnaRowStatusEntry 2 }

mscTraceRcvrFrDnaStorageType OBJECT-TYPE
   SYNTAX     StorageType 
   ACCESS     read-only
   STATUS     mandatory
   DESCRIPTION
     "This variable represents the storage type value for the
      mscTraceRcvrFrDna tables."
::= { mscTraceRcvrFrDnaRowStatusEntry 4 }

mscTraceRcvrFrDnaIndex OBJECT-TYPE
   SYNTAX     NonReplicated 
   ACCESS     not-accessible
   STATUS     mandatory
   DESCRIPTION
     "This variable represents the index for the mscTraceRcvrFrDna tables."
::= { mscTraceRcvrFrDnaRowStatusEntry 10 }

mscTraceRcvrFrDnaAddressTable OBJECT-TYPE
   SYNTAX     SEQUENCE OF MscTraceRcvrFrDnaAddressEntry
   ACCESS     not-accessible
   STATUS     mandatory
   DESCRIPTION
     "This group contains attributes common to all Dnas. This group is 
      composed of two attributes which define a Dna. These attributes are 
      used to interpret the format of the address digits."
::= { mscTraceRcvrFrDna 10 }

mscTraceRcvrFrDnaAddressEntry OBJECT-TYPE
   SYNTAX     MscTraceRcvrFrDnaAddressEntry
   ACCESS     not-accessible
   STATUS     mandatory
   DESCRIPTION
     "An entry in the mscTraceRcvrFrDnaAddressTable."
   INDEX {
      mscTraceIndex,
      mscTraceRcvrIndex,
      mscTraceRcvrFrIndex,
      mscTraceRcvrFrDnaIndex }
::= { mscTraceRcvrFrDnaAddressTable 1 }

MscTraceRcvrFrDnaAddressEntry ::= SEQUENCE {
   mscTraceRcvrFrDnaNumberingPlanIndicator
      INTEGER,
   mscTraceRcvrFrDnaDataNetworkAddress
      DigitString }

mscTraceRcvrFrDnaNumberingPlanIndicator OBJECT-TYPE
   SYNTAX     INTEGER  {
                 x121(0),
                 e164(1) }
   ACCESS     read-write
   STATUS     mandatory
   DESCRIPTION
     "This attribute specifies the Numbering Plan Indicator (NPI) of the 
      Dna that is entered. The address may belong to an E.164 or X.121 
      plan."
   DEFVAL     { x121 }
::= { mscTraceRcvrFrDnaAddressEntry 1 }

mscTraceRcvrFrDnaDataNetworkAddress OBJECT-TYPE
   SYNTAX     DigitString (SIZE (1..15))
   ACCESS     read-write
   STATUS     mandatory
   DESCRIPTION
     "The Dna attribute contains digits which form a unique identifier for 
      the calling end of the trace connection. Dna digits are selected and 
      assigned by network operators. The maximum Dna length is 15 
      digits."
::= { mscTraceRcvrFrDnaAddressEntry 2 }

mscTraceRcvrFrDnaOutgoingOptionsTable OBJECT-TYPE
   SYNTAX     SEQUENCE OF MscTraceRcvrFrDnaOutgoingOptionsEntry
   ACCESS     not-accessible
   STATUS     mandatory
   DESCRIPTION
     "This group defines the call options for outgoing calls."
::= { mscTraceRcvrFrDna 11 }

mscTraceRcvrFrDnaOutgoingOptionsEntry OBJECT-TYPE
   SYNTAX     MscTraceRcvrFrDnaOutgoingOptionsEntry
   ACCESS     not-accessible
   STATUS     mandatory
   DESCRIPTION
     "An entry in the mscTraceRcvrFrDnaOutgoingOptionsTable."
   INDEX {
      mscTraceIndex,
      mscTraceRcvrIndex,
      mscTraceRcvrFrIndex,
      mscTraceRcvrFrDnaIndex }
::= { mscTraceRcvrFrDnaOutgoingOptionsTable 1 }

MscTraceRcvrFrDnaOutgoingOptionsEntry ::= SEQUENCE {
   mscTraceRcvrFrDnaOutCalls
      INTEGER,
   mscTraceRcvrFrDnaOutDefaultPriority
      INTEGER,
   mscTraceRcvrFrDnaOutIntl
      INTEGER,
   mscTraceRcvrFrDnaOutDefaultPathReliability
      INTEGER,
   mscTraceRcvrFrDnaOutPathReliabilityOverRide
      INTEGER,
   mscTraceRcvrFrDnaOutPathReliabilitySignal
      INTEGER,
   mscTraceRcvrFrDnaOutAccess
      INTEGER }

mscTraceRcvrFrDnaOutCalls OBJECT-TYPE
   SYNTAX     INTEGER  {
                 disallowed(0),
                 allowed(1) }
   ACCESS     read-only
   STATUS     mandatory
   DESCRIPTION
     "This attribute specifies that outgoing calls (from the DTE to the 
      network) can be made using this particular Dna component."
   DEFVAL     { allowed }
::= { mscTraceRcvrFrDnaOutgoingOptionsEntry 1 }

mscTraceRcvrFrDnaOutDefaultPriority OBJECT-TYPE
   SYNTAX     INTEGER  {
                 normal(0),
                 high(1) }
   ACCESS     read-write
   STATUS     mandatory
   DESCRIPTION
     "If this attribute is set to normal, then the default priority for 
      outgoing calls (from the DTE to the network) using this particular 
      Dna is normal priority when the priority is not specified in the call. 
      If this attribute is set to high then the default priority for outgoing 
      calls using this particular Dna is high priority."
   DEFVAL     { high }
::= { mscTraceRcvrFrDnaOutgoingOptionsEntry 7 }

mscTraceRcvrFrDnaOutIntl OBJECT-TYPE
   SYNTAX     INTEGER  {
                 disallowed(0),
                 allowed(1) }
   ACCESS     read-only
   STATUS     mandatory
   DESCRIPTION
     "This attribute specifies that outgoing international calls (from the 
      DTE to the network) can be made using this particular Dna.
      
      This attribute also controls access to another numbering plan, and 
      specifies that cross-numbering plan calls are allowed."
   DEFVAL     { allowed }
::= { mscTraceRcvrFrDnaOutgoingOptionsEntry 8 }

mscTraceRcvrFrDnaOutDefaultPathReliability OBJECT-TYPE
   SYNTAX     INTEGER  {
                 high(0),
                 normal(1) }
   ACCESS     read-only
   STATUS     mandatory
   DESCRIPTION
     "This attribute specifies the default reliability class of routing for all 
      calls (from the DTE to the network) using this particular Dna. The 
      chosen default reliability class of routing normally applies to all 
      packets (including the call packets) travelling into the network.
      A value of high specifies that packets are to be overflowed or 
      retransmitted at various routing levels. Typically high reliability 
      results in duplication and disordering of packets in the network, 
      when errors are detected or during link congestion. The VC handles 
      the duplication and disordering to ensure that packets are delivered 
      to the interface in the proper sequence and without duplication."
   DEFVAL     { high }
::= { mscTraceRcvrFrDnaOutgoingOptionsEntry 14 }

mscTraceRcvrFrDnaOutPathReliabilityOverRide OBJECT-TYPE
   SYNTAX     INTEGER  {
                 no(0),
                 yes(1) }
   ACCESS     read-only
   STATUS     mandatory
   DESCRIPTION
     "This attribute specifies that the called end of the connection will not 
      use the calling end provisioning data for reliability class of routing 
      to override the provisioning data at the called end."
   DEFVAL     { no }
::= { mscTraceRcvrFrDnaOutgoingOptionsEntry 15 }

mscTraceRcvrFrDnaOutPathReliabilitySignal OBJECT-TYPE
   SYNTAX     INTEGER  {
                 disallowed(0),
                 allowed(1) }
   ACCESS     read-only
   STATUS     mandatory
   DESCRIPTION
     "This attribute specifies that reliability routing signaling is not used."
   DEFVAL     { disallowed }
::= { mscTraceRcvrFrDnaOutgoingOptionsEntry 16 }

mscTraceRcvrFrDnaOutAccess OBJECT-TYPE
   SYNTAX     INTEGER  {
                 disallowed(0),
                 allowed(1) }
   ACCESS     read-write
   STATUS     mandatory
   DESCRIPTION
     "This attribute is an extension of the Closed User Group (CUG) 
      facility. If this attribute is set to a value of allowed, it specifies that 
      outgoing calls (from the DTE to the network) to the open (non-
      CUG) part of the network are permitted. It also permits outgoing 
      calls to interfaces that have Incoming Access capabilities. If set to a 
      value of disallowed, then such calls cannot be made using this Dna 
      (the calls will be cleared by the local DCE).
      This attribute corresponds to the ITU-T 'Closed User Group with 
      Outgoing Access' feature."
   DEFVAL     { disallowed }
::= { mscTraceRcvrFrDnaOutgoingOptionsEntry 17 }

mscTraceRcvrFrDnaIncomingOptionsTable OBJECT-TYPE
   SYNTAX     SEQUENCE OF MscTraceRcvrFrDnaIncomingOptionsEntry
   ACCESS     not-accessible
   STATUS     mandatory
   DESCRIPTION
     "This group defines the call options for incoming calls."
::= { mscTraceRcvrFrDna 12 }

mscTraceRcvrFrDnaIncomingOptionsEntry OBJECT-TYPE
   SYNTAX     MscTraceRcvrFrDnaIncomingOptionsEntry
   ACCESS     not-accessible
   STATUS     mandatory
   DESCRIPTION
     "An entry in the mscTraceRcvrFrDnaIncomingOptionsTable."
   INDEX {
      mscTraceIndex,
      mscTraceRcvrIndex,
      mscTraceRcvrFrIndex,
      mscTraceRcvrFrDnaIndex }
::= { mscTraceRcvrFrDnaIncomingOptionsTable 1 }

MscTraceRcvrFrDnaIncomingOptionsEntry ::= SEQUENCE {
   mscTraceRcvrFrDnaIncCalls
      INTEGER }

mscTraceRcvrFrDnaIncCalls OBJECT-TYPE
   SYNTAX     INTEGER  {
                 disallowed(0),
                 allowed(1) }
   ACCESS     read-only
   STATUS     mandatory
   DESCRIPTION
     "This attribute specifies that incoming calls (from the network to the 
      DTE) cannot be made to this Dna."
   DEFVAL     { disallowed }
::= { mscTraceRcvrFrDnaIncomingOptionsEntry 1 }

mscTraceRcvrFrDnaCallOptionsTable OBJECT-TYPE
   SYNTAX     SEQUENCE OF MscTraceRcvrFrDnaCallOptionsEntry
   ACCESS     not-accessible
   STATUS     mandatory
   DESCRIPTION
     "The CallOptions group defines additional options for calls which 
      are not specific to the direction of the call."
::= { mscTraceRcvrFrDna 13 }

mscTraceRcvrFrDnaCallOptionsEntry OBJECT-TYPE
   SYNTAX     MscTraceRcvrFrDnaCallOptionsEntry
   ACCESS     not-accessible
   STATUS     mandatory
   DESCRIPTION
     "An entry in the mscTraceRcvrFrDnaCallOptionsTable."
   INDEX {
      mscTraceIndex,
      mscTraceRcvrIndex,
      mscTraceRcvrFrIndex,
      mscTraceRcvrFrDnaIndex }
::= { mscTraceRcvrFrDnaCallOptionsTable 1 }

MscTraceRcvrFrDnaCallOptionsEntry ::= SEQUENCE {
   mscTraceRcvrFrDnaPacketSizes
      OCTET STRING,
   mscTraceRcvrFrDnaDefaultRecvFrmNetworkPacketSize
      INTEGER,
   mscTraceRcvrFrDnaDefaultSendToNetworkPacketSize
      INTEGER,
   mscTraceRcvrFrDnaCugFormat
      INTEGER }

mscTraceRcvrFrDnaPacketSizes OBJECT-TYPE
   SYNTAX     OCTET STRING (SIZE (2))
   ACCESS     read-only
   STATUS     mandatory
   DESCRIPTION
     "This attribute specifies the allowable packet sizes supported for calls 
      using this Dna.

      Description of bits:
      n16(0)
      n32(1)
      n64(2)
      n128(3)
      n256(4)
      n512(5)
      n1024(6)
      n2048(7)
      n4096(8)"
   DEFVAL     { '0100'H }
::= { mscTraceRcvrFrDnaCallOptionsEntry 2 }

mscTraceRcvrFrDnaDefaultRecvFrmNetworkPacketSize OBJECT-TYPE
   SYNTAX     INTEGER  {
                 n16(4),
                 n32(5),
                 n64(6),
                 n128(7),
                 n256(8),
                 n512(9),
                 n1024(10),
                 n2048(11),
                 n4096(12) }
   ACCESS     read-only
   STATUS     mandatory
   DESCRIPTION
     "This attribute specifies the default local receive packet size from 
      network to DTE for calls using this particular Dna."
   DEFVAL     { n2048 }
::= { mscTraceRcvrFrDnaCallOptionsEntry 3 }

mscTraceRcvrFrDnaDefaultSendToNetworkPacketSize OBJECT-TYPE
   SYNTAX     INTEGER  {
                 n16(4),
                 n32(5),
                 n64(6),
                 n128(7),
                 n256(8),
                 n512(9),
                 n1024(10),
                 n2048(11),
                 n4096(12) }
   ACCESS     read-only
   STATUS     mandatory
   DESCRIPTION
     "This attribute specifies the default local send packet size from DTE 
      to network for all calls using this particular Dna."
   DEFVAL     { n2048 }
::= { mscTraceRcvrFrDnaCallOptionsEntry 4 }

mscTraceRcvrFrDnaCugFormat OBJECT-TYPE
   SYNTAX     INTEGER  {
                 basic(0),
                 extended(1) }
   ACCESS     read-only
   STATUS     mandatory
   DESCRIPTION
     "This attribute specifies the format to signal CUG indices as basic or 
      extended. A basic CUG index format is two digits long. An 
      extended CUG index format is four digits long."
   DEFVAL     { basic }
::= { mscTraceRcvrFrDnaCallOptionsEntry 10 }


-- Trace Rcvr/<string> Fr Dna ClosedUserGroup
-- The ClosedUserGroup component defines options associated with a 
-- national or international closed user group identifier. When a Dna is 
-- defined with a Cug, calls to other Dnas which do not have the same 
-- Cug interlockCode defined are refused. When a Dna is not defined 
-- with a Cug, calls to other Dnas which have any Cug interlockCode 
-- defined are refused. The Dna attributes outAccess and incAccess 
-- can override these rules.
-- If this component is present, the Frame Relay interface which 
-- connects to the Frame Relay trace receiver must be provisioned 
-- with the same Cug interlockCode.

mscTraceRcvrFrDnaCug OBJECT IDENTIFIER ::= { mscTraceRcvrFrDna 2 }



mscTraceRcvrFrDnaCugRowStatusTable OBJECT-TYPE
   SYNTAX     SEQUENCE OF MscTraceRcvrFrDnaCugRowStatusEntry
   ACCESS     not-accessible
   STATUS     mandatory
   DESCRIPTION
     "This entry controls the addition and deletion of 
      mscTraceRcvrFrDnaCug components."
::= { mscTraceRcvrFrDnaCug 1 }

mscTraceRcvrFrDnaCugRowStatusEntry OBJECT-TYPE
   SYNTAX     MscTraceRcvrFrDnaCugRowStatusEntry
   ACCESS     not-accessible
   STATUS     mandatory
   DESCRIPTION
     "A single entry in the table represents a single 
      mscTraceRcvrFrDnaCug component."
   INDEX {
      mscTraceIndex,
      mscTraceRcvrIndex,
      mscTraceRcvrFrIndex,
      mscTraceRcvrFrDnaIndex,
      mscTraceRcvrFrDnaCugIndex }
::= { mscTraceRcvrFrDnaCugRowStatusTable 1 }

MscTraceRcvrFrDnaCugRowStatusEntry ::= SEQUENCE {
   mscTraceRcvrFrDnaCugRowStatus
      RowStatus,
   mscTraceRcvrFrDnaCugComponentName
      DisplayString,
   mscTraceRcvrFrDnaCugStorageType
      StorageType,
   mscTraceRcvrFrDnaCugIndex
      Integer32 }

mscTraceRcvrFrDnaCugRowStatus OBJECT-TYPE
   SYNTAX     RowStatus 
   ACCESS     read-write
   STATUS     mandatory
   DESCRIPTION
     "This variable is used as the basis for SNMP naming of
      mscTraceRcvrFrDnaCug components.
      These components can be added and deleted."
::= { mscTraceRcvrFrDnaCugRowStatusEntry 1 }

mscTraceRcvrFrDnaCugComponentName OBJECT-TYPE
   SYNTAX     DisplayString 
   ACCESS     read-only
   STATUS     mandatory
   DESCRIPTION
     "This variable provides the component's string name for
      use with the ASCII Console Interface"
::= { mscTraceRcvrFrDnaCugRowStatusEntry 2 }

mscTraceRcvrFrDnaCugStorageType OBJECT-TYPE
   SYNTAX     StorageType 
   ACCESS     read-only
   STATUS     mandatory
   DESCRIPTION
     "This variable represents the storage type value for the
      mscTraceRcvrFrDnaCug tables."
::= { mscTraceRcvrFrDnaCugRowStatusEntry 4 }

mscTraceRcvrFrDnaCugIndex OBJECT-TYPE
   SYNTAX     Integer32 (1..1)
   ACCESS     not-accessible
   STATUS     mandatory
   DESCRIPTION
     "This variable represents the index for the mscTraceRcvrFrDnaCug tables."
::= { mscTraceRcvrFrDnaCugRowStatusEntry 10 }

mscTraceRcvrFrDnaCugCugOptionsTable OBJECT-TYPE
   SYNTAX     SEQUENCE OF MscTraceRcvrFrDnaCugCugOptionsEntry
   ACCESS     not-accessible
   STATUS     mandatory
   DESCRIPTION
     "Attributes in this group define ClosedUserGroup options associated 
      with interlockCode. Dnas with the same CUG (interlockCode) can 
      make calls within this group. Various combinations of attributes are 
      defined under this option which permit or prevent calls in the same 
      CUG group."
::= { mscTraceRcvrFrDnaCug 10 }

mscTraceRcvrFrDnaCugCugOptionsEntry OBJECT-TYPE
   SYNTAX     MscTraceRcvrFrDnaCugCugOptionsEntry
   ACCESS     not-accessible
   STATUS     mandatory
   DESCRIPTION
     "An entry in the mscTraceRcvrFrDnaCugCugOptionsTable."
   INDEX {
      mscTraceIndex,
      mscTraceRcvrIndex,
      mscTraceRcvrFrIndex,
      mscTraceRcvrFrDnaIndex,
      mscTraceRcvrFrDnaCugIndex }
::= { mscTraceRcvrFrDnaCugCugOptionsTable 1 }

MscTraceRcvrFrDnaCugCugOptionsEntry ::= SEQUENCE {
   mscTraceRcvrFrDnaCugType
      INTEGER,
   mscTraceRcvrFrDnaCugDnic
      DigitString,
   mscTraceRcvrFrDnaCugInterlockCode
      Unsigned32,
   mscTraceRcvrFrDnaCugPreferential
      INTEGER,
   mscTraceRcvrFrDnaCugOutCalls
      INTEGER,
   mscTraceRcvrFrDnaCugIncCalls
      INTEGER,
   mscTraceRcvrFrDnaCugPrivileged
      INTEGER }

mscTraceRcvrFrDnaCugType OBJECT-TYPE
   SYNTAX     INTEGER  {
                 national(0),
                 international(1) }
   ACCESS     read-write
   STATUS     mandatory
   DESCRIPTION
     "This attribute specifies the CUG type as either national or 
      international. A national CUG has significance within the local 
      network only. An international CUG has significance across 
      network boundaries."
   DEFVAL     { national }
::= { mscTraceRcvrFrDnaCugCugOptionsEntry 1 }

mscTraceRcvrFrDnaCugDnic OBJECT-TYPE
   SYNTAX     DigitString (SIZE (4))
   ACCESS     read-write
   STATUS     mandatory
   DESCRIPTION
     "This attribute specifies the Data Network ID Code of the network 
      that is administering the international CUG. This attribute is not 
      used for a national CUG and should be left at its default value.
      The dnic value is not an arbitrary number. It is assigned by 
      international agreement and controlled by ITU-T."
   DEFVAL     { '30303030'H }  -- "0000"
::= { mscTraceRcvrFrDnaCugCugOptionsEntry 2 }

mscTraceRcvrFrDnaCugInterlockCode OBJECT-TYPE
   SYNTAX     Unsigned32 (0..65535)
   ACCESS     read-write
   STATUS     mandatory
   DESCRIPTION
     "This attribute specifies a numeric identifier of a national or 
      international closed user group. It is an arbitrary number. This 
      attribute may also be called CUG in some descriptions. Dnas 
      defined with this number can only make calls to Dnas defined with 
      the same interlockCode."
   DEFVAL     { 0 }
::= { mscTraceRcvrFrDnaCugCugOptionsEntry 3 }

mscTraceRcvrFrDnaCugPreferential OBJECT-TYPE
   SYNTAX     INTEGER  {
                 no(0),
                 yes(1) }
   ACCESS     read-only
   STATUS     mandatory
   DESCRIPTION
     "This attribute specifies that this Cug is to be used on all outgoing 
      calls to the Frame Relay trace receiver."
   DEFVAL     { yes }
::= { mscTraceRcvrFrDnaCugCugOptionsEntry 4 }

mscTraceRcvrFrDnaCugOutCalls OBJECT-TYPE
   SYNTAX     INTEGER  {
                 disallowed(0),
                 allowed(1) }
   ACCESS     read-only
   STATUS     mandatory
   DESCRIPTION
     "This attribute specifies that outgoing calls (from the DTE into the 
      network) can be made using this particular Cug."
   DEFVAL     { allowed }
::= { mscTraceRcvrFrDnaCugCugOptionsEntry 5 }

mscTraceRcvrFrDnaCugIncCalls OBJECT-TYPE
   SYNTAX     INTEGER  {
                 disallowed(0),
                 allowed(1) }
   ACCESS     read-only
   STATUS     mandatory
   DESCRIPTION
     "This attribute specifies that incoming calls (from the network to the 
      DTE) cannot be accepted using this Cug."
   DEFVAL     { disallowed }
::= { mscTraceRcvrFrDnaCugCugOptionsEntry 6 }

mscTraceRcvrFrDnaCugPrivileged OBJECT-TYPE
   SYNTAX     INTEGER  {
                 no(0),
                 yes(1) }
   ACCESS     read-only
   STATUS     mandatory
   DESCRIPTION
     "This attribute specifies that this Cug is privileged. For a call 
      between two closed user group Dnas to connect, at least one Dna 
      must have a privileged Cug."
   DEFVAL     { yes }
::= { mscTraceRcvrFrDnaCugCugOptionsEntry 7 }


-- Trace Rcvr/<string> Fr DirectCall
-- This component defines direct call options for the call to the Frame 
-- Relay trace receiver. The connection is initiated on receipt of a Start 
-- FrUni/n Trace command.

mscTraceRcvrFrDc OBJECT IDENTIFIER ::= { mscTraceRcvrFr 3 }



mscTraceRcvrFrDcRowStatusTable OBJECT-TYPE
   SYNTAX     SEQUENCE OF MscTraceRcvrFrDcRowStatusEntry
   ACCESS     not-accessible
   STATUS     mandatory
   DESCRIPTION
     "This entry controls the addition and deletion of 
      mscTraceRcvrFrDc components."
::= { mscTraceRcvrFrDc 1 }

mscTraceRcvrFrDcRowStatusEntry OBJECT-TYPE
   SYNTAX     MscTraceRcvrFrDcRowStatusEntry
   ACCESS     not-accessible
   STATUS     mandatory
   DESCRIPTION
     "A single entry in the table represents a single 
      mscTraceRcvrFrDc component."
   INDEX {
      mscTraceIndex,
      mscTraceRcvrIndex,
      mscTraceRcvrFrIndex,
      mscTraceRcvrFrDcIndex }
::= { mscTraceRcvrFrDcRowStatusTable 1 }

MscTraceRcvrFrDcRowStatusEntry ::= SEQUENCE {
   mscTraceRcvrFrDcRowStatus
      RowStatus,
   mscTraceRcvrFrDcComponentName
      DisplayString,
   mscTraceRcvrFrDcStorageType
      StorageType,
   mscTraceRcvrFrDcIndex
      NonReplicated }

mscTraceRcvrFrDcRowStatus OBJECT-TYPE
   SYNTAX     RowStatus 
   ACCESS     read-only
   STATUS     mandatory
   DESCRIPTION
     "This variable is used as the basis for SNMP naming of
      mscTraceRcvrFrDc components.
      These components cannot be added nor deleted."
::= { mscTraceRcvrFrDcRowStatusEntry 1 }

mscTraceRcvrFrDcComponentName OBJECT-TYPE
   SYNTAX     DisplayString 
   ACCESS     read-only
   STATUS     mandatory
   DESCRIPTION
     "This variable provides the component's string name for
      use with the ASCII Console Interface"
::= { mscTraceRcvrFrDcRowStatusEntry 2 }

mscTraceRcvrFrDcStorageType OBJECT-TYPE
   SYNTAX     StorageType 
   ACCESS     read-only
   STATUS     mandatory
   DESCRIPTION
     "This variable represents the storage type value for the
      mscTraceRcvrFrDc tables."
::= { mscTraceRcvrFrDcRowStatusEntry 4 }

mscTraceRcvrFrDcIndex OBJECT-TYPE
   SYNTAX     NonReplicated 
   ACCESS     not-accessible
   STATUS     mandatory
   DESCRIPTION
     "This variable represents the index for the mscTraceRcvrFrDc tables."
::= { mscTraceRcvrFrDcRowStatusEntry 10 }

mscTraceRcvrFrDcOptionsTable OBJECT-TYPE
   SYNTAX     SEQUENCE OF MscTraceRcvrFrDcOptionsEntry
   ACCESS     not-accessible
   STATUS     mandatory
   DESCRIPTION
     "The Options group defines attributes associated with the SVC direct 
      call."
::= { mscTraceRcvrFrDc 10 }

mscTraceRcvrFrDcOptionsEntry OBJECT-TYPE
   SYNTAX     MscTraceRcvrFrDcOptionsEntry
   ACCESS     not-accessible
   STATUS     mandatory
   DESCRIPTION
     "An entry in the mscTraceRcvrFrDcOptionsTable."
   INDEX {
      mscTraceIndex,
      mscTraceRcvrIndex,
      mscTraceRcvrFrIndex,
      mscTraceRcvrFrDcIndex }
::= { mscTraceRcvrFrDcOptionsTable 1 }

MscTraceRcvrFrDcOptionsEntry ::= SEQUENCE {
   mscTraceRcvrFrDcRemoteNpi
      INTEGER,
   mscTraceRcvrFrDcRemoteDna
      DigitString,
   mscTraceRcvrFrDcType
      INTEGER,
   mscTraceRcvrFrDcUserData
      HexString }

mscTraceRcvrFrDcRemoteNpi OBJECT-TYPE
   SYNTAX     INTEGER  {
                 x121(0),
                 e164(1) }
   ACCESS     read-write
   STATUS     mandatory
   DESCRIPTION
     "This attribute indicates the numbering plan used for the remoteDna."
   DEFVAL     { x121 }
::= { mscTraceRcvrFrDcOptionsEntry 3 }

mscTraceRcvrFrDcRemoteDna OBJECT-TYPE
   SYNTAX     DigitString (SIZE (1..15))
   ACCESS     read-write
   STATUS     mandatory
   DESCRIPTION
     "This attribute specifies the Data Network Address of the remote end 
      of the connection. This is the DNA of the Frame Relay trace 
      receiver which will receive the trace data."
::= { mscTraceRcvrFrDcOptionsEntry 4 }

mscTraceRcvrFrDcType OBJECT-TYPE
   SYNTAX     INTEGER  {
                 switched(0),
                 permanentMaster(1),
                 permanentSlave(2),
                 permanentBackupSlave(3) }
   ACCESS     read-only
   STATUS     mandatory
   DESCRIPTION
     "This attribute specifies the type of call as switched. For a switched 
      call, no information is defined at the remote end about the local end 
      of the connection."
   DEFVAL     { switched }
::= { mscTraceRcvrFrDcOptionsEntry 6 }

mscTraceRcvrFrDcUserData OBJECT-TYPE
   SYNTAX     HexString (SIZE (0..16))
   ACCESS     read-write
   STATUS     mandatory
   DESCRIPTION
     "This attribute contains the user data. It is a 0 to 16 byte length string 
      which is appended to the call request packet that is presented to the 
      called (destination) DTE."
   DEFVAL     { ''H }  -- ""
::= { mscTraceRcvrFrDcOptionsEntry 8 }

-- 
-- *** THIS SUBTREE CURRENTLY NOT IMPLEMENTED ***
-- 

-- Trace Session/<n> FrameRelay
-- This component identifies the access method used by the receiver of 
-- the trace data as Frame Relay.

mscTraceSessionFr OBJECT IDENTIFIER ::= { mscTraceSession 3 }



mscTraceSessionFrRowStatusTable OBJECT-TYPE
   SYNTAX     SEQUENCE OF MscTraceSessionFrRowStatusEntry
   ACCESS     not-accessible
   STATUS     mandatory
   DESCRIPTION
     "*** THIS TABLE CURRENTLY NOT IMPLEMENTED ***

      This entry controls the addition and deletion of 
      mscTraceSessionFr components."
::= { mscTraceSessionFr 1 }

mscTraceSessionFrRowStatusEntry OBJECT-TYPE
   SYNTAX     MscTraceSessionFrRowStatusEntry
   ACCESS     not-accessible
   STATUS     mandatory
   DESCRIPTION
     "A single entry in the table represents a single 
      mscTraceSessionFr component."
   INDEX {
      mscTraceIndex,
      mscTraceSessionIndex,
      mscTraceSessionFrIndex }
::= { mscTraceSessionFrRowStatusTable 1 }

MscTraceSessionFrRowStatusEntry ::= SEQUENCE {
   mscTraceSessionFrRowStatus
      RowStatus,
   mscTraceSessionFrComponentName
      DisplayString,
   mscTraceSessionFrStorageType
      StorageType,
   mscTraceSessionFrIndex
      NonReplicated }

mscTraceSessionFrRowStatus OBJECT-TYPE
   SYNTAX     RowStatus 
   ACCESS     read-only
   STATUS     mandatory
   DESCRIPTION
     "This variable is used as the basis for SNMP naming of
      mscTraceSessionFr components.
      These components cannot be added nor deleted."
::= { mscTraceSessionFrRowStatusEntry 1 }

mscTraceSessionFrComponentName OBJECT-TYPE
   SYNTAX     DisplayString 
   ACCESS     read-only
   STATUS     mandatory
   DESCRIPTION
     "This variable provides the component's string name for
      use with the ASCII Console Interface"
::= { mscTraceSessionFrRowStatusEntry 2 }

mscTraceSessionFrStorageType OBJECT-TYPE
   SYNTAX     StorageType 
   ACCESS     read-only
   STATUS     mandatory
   DESCRIPTION
     "This variable represents the storage type value for the
      mscTraceSessionFr tables."
::= { mscTraceSessionFrRowStatusEntry 4 }

mscTraceSessionFrIndex OBJECT-TYPE
   SYNTAX     NonReplicated 
   ACCESS     not-accessible
   STATUS     mandatory
   DESCRIPTION
     "This variable represents the index for the mscTraceSessionFr tables."
::= { mscTraceSessionFrRowStatusEntry 10 }

-- 
-- *** THIS SUBTREE CURRENTLY NOT IMPLEMENTED ***
-- 

-- This component defines attributes collected by Frame Relay Vc.

mscTraceSessionFrVc OBJECT IDENTIFIER ::= { mscTraceSessionFr 2 }



mscTraceSessionFrVcRowStatusTable OBJECT-TYPE
   SYNTAX     SEQUENCE OF MscTraceSessionFrVcRowStatusEntry
   ACCESS     not-accessible
   STATUS     mandatory
   DESCRIPTION
     "*** THIS TABLE CURRENTLY NOT IMPLEMENTED ***

      This entry controls the addition and deletion of 
      mscTraceSessionFrVc components."
::= { mscTraceSessionFrVc 1 }

mscTraceSessionFrVcRowStatusEntry OBJECT-TYPE
   SYNTAX     MscTraceSessionFrVcRowStatusEntry
   ACCESS     not-accessible
   STATUS     mandatory
   DESCRIPTION
     "A single entry in the table represents a single 
      mscTraceSessionFrVc component."
   INDEX {
      mscTraceIndex,
      mscTraceSessionIndex,
      mscTraceSessionFrIndex,
      mscTraceSessionFrVcIndex }
::= { mscTraceSessionFrVcRowStatusTable 1 }

MscTraceSessionFrVcRowStatusEntry ::= SEQUENCE {
   mscTraceSessionFrVcRowStatus
      RowStatus,
   mscTraceSessionFrVcComponentName
      DisplayString,
   mscTraceSessionFrVcStorageType
      StorageType,
   mscTraceSessionFrVcIndex
      NonReplicated }

mscTraceSessionFrVcRowStatus OBJECT-TYPE
   SYNTAX     RowStatus 
   ACCESS     read-only
   STATUS     mandatory
   DESCRIPTION
     "This variable is used as the basis for SNMP naming of
      mscTraceSessionFrVc components.
      These components cannot be added nor deleted."
::= { mscTraceSessionFrVcRowStatusEntry 1 }

mscTraceSessionFrVcComponentName OBJECT-TYPE
   SYNTAX     DisplayString 
   ACCESS     read-only
   STATUS     mandatory
   DESCRIPTION
     "This variable provides the component's string name for
      use with the ASCII Console Interface"
::= { mscTraceSessionFrVcRowStatusEntry 2 }

mscTraceSessionFrVcStorageType OBJECT-TYPE
   SYNTAX     StorageType 
   ACCESS     read-only
   STATUS     mandatory
   DESCRIPTION
     "This variable represents the storage type value for the
      mscTraceSessionFrVc tables."
::= { mscTraceSessionFrVcRowStatusEntry 4 }

mscTraceSessionFrVcIndex OBJECT-TYPE
   SYNTAX     NonReplicated 
   ACCESS     not-accessible
   STATUS     mandatory
   DESCRIPTION
     "This variable represents the index for the mscTraceSessionFrVc tables."
::= { mscTraceSessionFrVcRowStatusEntry 10 }

mscTraceSessionFrVcCadTable OBJECT-TYPE
   SYNTAX     SEQUENCE OF MscTraceSessionFrVcCadEntry
   ACCESS     not-accessible
   STATUS     mandatory
   DESCRIPTION
     "*** THIS TABLE CURRENTLY NOT IMPLEMENTED ***

      This group represents operational call data related to Frame Relay 
      Vc. It can be displayed only for Frame Relay Vc which is created by 
      application."
::= { mscTraceSessionFrVc 10 }

mscTraceSessionFrVcCadEntry OBJECT-TYPE
   SYNTAX     MscTraceSessionFrVcCadEntry
   ACCESS     not-accessible
   STATUS     mandatory
   DESCRIPTION
     "An entry in the mscTraceSessionFrVcCadTable."
   INDEX {
      mscTraceIndex,
      mscTraceSessionIndex,
      mscTraceSessionFrIndex,
      mscTraceSessionFrVcIndex }
::= { mscTraceSessionFrVcCadTable 1 }

MscTraceSessionFrVcCadEntry ::= SEQUENCE {
   mscTraceSessionFrVcType
      INTEGER,
   mscTraceSessionFrVcState
      INTEGER,
   mscTraceSessionFrVcPreviousState
      INTEGER,
   mscTraceSessionFrVcDiagnosticCode
      Unsigned32,
   mscTraceSessionFrVcPreviousDiagnosticCode
      Unsigned32,
   mscTraceSessionFrVcCalledNpi
      INTEGER,
   mscTraceSessionFrVcCalledDna
      DigitString,
   mscTraceSessionFrVcCalledLcn
      Unsigned32,
   mscTraceSessionFrVcCallingNpi
      INTEGER,
   mscTraceSessionFrVcCallingDna
      DigitString,
   mscTraceSessionFrVcCallingLcn
      Unsigned32,
   mscTraceSessionFrVcAccountingEnabled
      INTEGER,
   mscTraceSessionFrVcFastSelectCall
      INTEGER,
   mscTraceSessionFrVcPathReliability
      INTEGER,
   mscTraceSessionFrVcAccountingEnd
      INTEGER,
   mscTraceSessionFrVcPriority
      INTEGER,
   mscTraceSessionFrVcSegmentSize
      Unsigned32,
   mscTraceSessionFrVcMaxSubnetPktSize
      Unsigned32,
   mscTraceSessionFrVcRcosToNetwork
      INTEGER,
   mscTraceSessionFrVcRcosFromNetwork
      INTEGER,
   mscTraceSessionFrVcEmissionPriorityToNetwork
      INTEGER,
   mscTraceSessionFrVcEmissionPriorityFromNetwork
      INTEGER,
   mscTraceSessionFrVcDataPath
      AsciiString }

mscTraceSessionFrVcType OBJECT-TYPE
   SYNTAX     INTEGER  {
                 svc(0),
                 pvc(1),
                 spvc(2),
                 frf10spvc(3) }
   ACCESS     read-only
   STATUS     mandatory
   DESCRIPTION
     "This attribute displays the type of call, pvc,svc,spvc or frf10spvc."
::= { mscTraceSessionFrVcCadEntry 1 }

mscTraceSessionFrVcState OBJECT-TYPE
   SYNTAX     INTEGER  {
                 creating(0),
                 readyP1(1),
                 dteWaitingP2(2),
                 dceWaitingP3(3),
                 dataTransferP4(4),
                 unsupportedP5(5),
                 dteClearRequestP6(6),
                 dceClearIndicationP7(7),
                 termination(8) }
   ACCESS     read-only
   STATUS     mandatory
   DESCRIPTION
     "This attribute displays the state of call control. P5 state is not 
      supported but is listed for completness. Transitions from one state to 
      another take very short time. state most often displayed is 
      dataTransferP4."
::= { mscTraceSessionFrVcCadEntry 2 }

mscTraceSessionFrVcPreviousState OBJECT-TYPE
   SYNTAX     INTEGER  {
                 creating(0),
                 readyP1(1),
                 dteWaitingP2(2),
                 dceWaitingP3(3),
                 dataTransferP4(4),
                 unsupportedP5(5),
                 dteClearRequestP6(6),
                 dceClearIndicationP7(7),
                 termination(8) }
   ACCESS     read-only
   STATUS     mandatory
   DESCRIPTION
     "This attribute displays the previous state of call control. This is a 
      valuable field to determine how the processing is progressing."
::= { mscTraceSessionFrVcCadEntry 3 }

mscTraceSessionFrVcDiagnosticCode OBJECT-TYPE
   SYNTAX     Unsigned32 (0..255)
   ACCESS     read-only
   STATUS     mandatory
   DESCRIPTION
     "This attribute displays the internal substate of call control. It is used 
      to further refine state of call processing."
::= { mscTraceSessionFrVcCadEntry 4 }

mscTraceSessionFrVcPreviousDiagnosticCode OBJECT-TYPE
   SYNTAX     Unsigned32 (0..255)
   ACCESS     read-only
   STATUS     mandatory
   DESCRIPTION
     "This attribute displays the internal substate of call control. It is used 
      to further refine state of call processing."
::= { mscTraceSessionFrVcCadEntry 5 }

mscTraceSessionFrVcCalledNpi OBJECT-TYPE
   SYNTAX     INTEGER  {
                 x121(0),
                 e164(1) }
   ACCESS     read-only
   STATUS     mandatory
   DESCRIPTION
     "This attribute displays the Numbering Plan Indicator (NPI) of the 
      called end."
::= { mscTraceSessionFrVcCadEntry 6 }

mscTraceSessionFrVcCalledDna OBJECT-TYPE
   SYNTAX     DigitString (SIZE (1..15))
   ACCESS     read-only
   STATUS     mandatory
   DESCRIPTION
     "This attribute displays the Data Network Address (Dna) of the 
      called (destination) DTE to which this call is sent. This address if 
      defined at recieving end will complete Vc connection."
::= { mscTraceSessionFrVcCadEntry 7 }

mscTraceSessionFrVcCalledLcn OBJECT-TYPE
   SYNTAX     Unsigned32 (1..65535)
   ACCESS     read-only
   STATUS     mandatory
   DESCRIPTION
     "This attribute displays the Logical Channel Number of the called 
      end. It is valid only after both ends of Vc exchanged relevant 
      information."
::= { mscTraceSessionFrVcCadEntry 8 }

mscTraceSessionFrVcCallingNpi OBJECT-TYPE
   SYNTAX     INTEGER  {
                 x121(0),
                 e164(1) }
   ACCESS     read-only
   STATUS     mandatory
   DESCRIPTION
     "This attribute displays the Numbering Plan Indicator (NPI) of the 
      calling end."
::= { mscTraceSessionFrVcCadEntry 9 }

mscTraceSessionFrVcCallingDna OBJECT-TYPE
   SYNTAX     DigitString (SIZE (1..15))
   ACCESS     read-only
   STATUS     mandatory
   DESCRIPTION
     "This attribute displays the Data Network Address (Dna) of the 
      calling end."
::= { mscTraceSessionFrVcCadEntry 10 }

mscTraceSessionFrVcCallingLcn OBJECT-TYPE
   SYNTAX     Unsigned32 (1..65535)
   ACCESS     read-only
   STATUS     mandatory
   DESCRIPTION
     "This attribute displays the Logical Channel Number of the calling 
      end."
::= { mscTraceSessionFrVcCadEntry 11 }

mscTraceSessionFrVcAccountingEnabled OBJECT-TYPE
   SYNTAX     INTEGER  {
                 yes(0),
                 no(1) }
   ACCESS     read-only
   STATUS     mandatory
   DESCRIPTION
     "This attribute indicates that this optional section of accounting 
      record is suppressed or permitted. If accountingEnabled is yes, 
      conditions for generation of accounting record were met. These 
      conditions include billing options, vc recovery conditions and 
      Module wide accounting data options."
::= { mscTraceSessionFrVcCadEntry 12 }

mscTraceSessionFrVcFastSelectCall OBJECT-TYPE
   SYNTAX     INTEGER  {
                 no(0),
                 yes(1) }
   ACCESS     read-only
   STATUS     mandatory
   DESCRIPTION
     "This attribute displays that this is a fast select call."
::= { mscTraceSessionFrVcCadEntry 13 }

mscTraceSessionFrVcPathReliability OBJECT-TYPE
   SYNTAX     INTEGER  {
                 high(0),
                 normal(1) }
   ACCESS     read-only
   STATUS     mandatory
   DESCRIPTION
     "This attribute displays the path reliability."
::= { mscTraceSessionFrVcCadEntry 19 }

mscTraceSessionFrVcAccountingEnd OBJECT-TYPE
   SYNTAX     INTEGER  {
                 callingEnd(0),
                 calledEnd(1) }
   ACCESS     read-only
   STATUS     mandatory
   DESCRIPTION
     "This attribute indicates if this end should generate an accounting 
      record. Normally, callingEnd is the end to generate an accounting 
      record."
::= { mscTraceSessionFrVcCadEntry 20 }

mscTraceSessionFrVcPriority OBJECT-TYPE
   SYNTAX     INTEGER  {
                 normal(0),
                 high(1) }
   ACCESS     read-only
   STATUS     mandatory
   DESCRIPTION
     "This attribute displays whether the call is a normal or a high 
      priority call."
::= { mscTraceSessionFrVcCadEntry 21 }

mscTraceSessionFrVcSegmentSize OBJECT-TYPE
   SYNTAX     Unsigned32 (0..4096)
   ACCESS     read-only
   STATUS     mandatory
   DESCRIPTION
     "This attribute displays the segment size (in bytes) used on the call. 
      It is used to calculate the number of segments transmitted and 
      received."
::= { mscTraceSessionFrVcCadEntry 22 }

mscTraceSessionFrVcMaxSubnetPktSize OBJECT-TYPE
   SYNTAX     Unsigned32 (0..4096)
   ACCESS     read-only
   STATUS     mandatory
   DESCRIPTION
     "This attribute indicates the maximum packet size allowed on the Vc."
::= { mscTraceSessionFrVcCadEntry 27 }

mscTraceSessionFrVcRcosToNetwork OBJECT-TYPE
   SYNTAX     INTEGER  {
                 throughput(0),
                 delay(1),
                 multimedia(2) }
   ACCESS     read-only
   STATUS     mandatory
   DESCRIPTION
     "This attribute indicates the routing metric routing class of service to
      the network."
::= { mscTraceSessionFrVcCadEntry 28 }

mscTraceSessionFrVcRcosFromNetwork OBJECT-TYPE
   SYNTAX     INTEGER  {
                 throughput(0),
                 delay(1),
                 multimedia(2) }
   ACCESS     read-only
   STATUS     mandatory
   DESCRIPTION
     "This attribute displays the routing metric Routing Class of Service 
      from the Network."
::= { mscTraceSessionFrVcCadEntry 29 }

mscTraceSessionFrVcEmissionPriorityToNetwork OBJECT-TYPE
   SYNTAX     INTEGER  {
                 normal(0),
                 high(1),
                 interrupting(2) }
   ACCESS     read-only
   STATUS     mandatory
   DESCRIPTION
     "This attribute displays the network internal emission priotity to the 
      network."
::= { mscTraceSessionFrVcCadEntry 30 }

mscTraceSessionFrVcEmissionPriorityFromNetwork OBJECT-TYPE
   SYNTAX     INTEGER  {
                 normal(0),
                 high(1),
                 interrupting(2) }
   ACCESS     read-only
   STATUS     mandatory
   DESCRIPTION
     "This attribute displays the network internal emission priotity from 
      the network."
::= { mscTraceSessionFrVcCadEntry 31 }

mscTraceSessionFrVcDataPath OBJECT-TYPE
   SYNTAX     AsciiString (SIZE (0..32))
   ACCESS     read-only
   STATUS     mandatory
   DESCRIPTION
     "This attribute indicates the data path used by the connection. The 
      data path is provisioned in Dna and DirectCall components. The 
      displayed value of this attribute can be different from the 
      provisioned value.
      
      If the connection is using dprsOnly data path, the string 
      dprsOnly is displayed. (dynamic packet routing system)
      
      If the connection is using dprsMcsOnly data path, the string 
      dprsMcsOnly is displayed.
      
      If the connection is using dprsMcsFirst data path, the string 
      dprsMcsFirst is displayed."
::= { mscTraceSessionFrVcCadEntry 32 }

mscTraceSessionFrVcIntdTable OBJECT-TYPE
   SYNTAX     SEQUENCE OF MscTraceSessionFrVcIntdEntry
   ACCESS     not-accessible
   STATUS     mandatory
   DESCRIPTION
     "*** THIS TABLE CURRENTLY NOT IMPLEMENTED ***

      This group defines display of interval data collected by Vc. Data in 
      this group is variable and may depend on time when this display 
      command is issued."
::= { mscTraceSessionFrVc 11 }

mscTraceSessionFrVcIntdEntry OBJECT-TYPE
   SYNTAX     MscTraceSessionFrVcIntdEntry
   ACCESS     not-accessible
   STATUS     mandatory
   DESCRIPTION
     "An entry in the mscTraceSessionFrVcIntdTable."
   INDEX {
      mscTraceIndex,
      mscTraceSessionIndex,
      mscTraceSessionFrIndex,
      mscTraceSessionFrVcIndex }
::= { mscTraceSessionFrVcIntdTable 1 }

MscTraceSessionFrVcIntdEntry ::= SEQUENCE {
   mscTraceSessionFrVcCallReferenceNumber
      Hex,
   mscTraceSessionFrVcElapsedTimeTillNow
      Unsigned32,
   mscTraceSessionFrVcSegmentsRx
      Unsigned32,
   mscTraceSessionFrVcSegmentsSent
      Unsigned32,
   mscTraceSessionFrVcStartTime
      EnterpriseDateAndTime,
   mscTraceSessionFrVcCallReferenceNumberDecimal
      Unsigned32 }

mscTraceSessionFrVcCallReferenceNumber OBJECT-TYPE
   SYNTAX     Hex (0..16777215)
   ACCESS     read-only
   STATUS     obsolete
   DESCRIPTION
     "This attribute is obsolete. It is replaced by the callReferenceNumber 
      attribute to display the call reference number in decimal. The 
      SNMP reference for the callReferenceNumber attribute is 
      callReferenceNumberDecimal."
::= { mscTraceSessionFrVcIntdEntry 1 }

mscTraceSessionFrVcElapsedTimeTillNow OBJECT-TYPE
   SYNTAX     Unsigned32 (0..16777215)
   ACCESS     read-only
   STATUS     mandatory
   DESCRIPTION
     "This attribute displays the elapsed time representing the period of 
      this interval data. It is elapsed time in 0.1 second increments since 
      Vc started."
::= { mscTraceSessionFrVcIntdEntry 2 }

mscTraceSessionFrVcSegmentsRx OBJECT-TYPE
   SYNTAX     Unsigned32 (0..16777215)
   ACCESS     read-only
   STATUS     mandatory
   DESCRIPTION
     "This attribute displays the number of segments received at the time 
      command was issued. This is the segment received count 
      maintained by accounting at each end of the Vc. This counter is 
      updated only when the packet cannot be successfully delivered out 
      of the sink Vc and to the sink AP Conditions in which packets may 
      be discarded by the sink Vc include: missing packets due to subnet 
      discards, segmentation protocol violations due to subnet discard, 
      duplicated and out-of-ranged packets and packets that arrive while 
      Vc is in path recovery state."
::= { mscTraceSessionFrVcIntdEntry 3 }

mscTraceSessionFrVcSegmentsSent OBJECT-TYPE
   SYNTAX     Unsigned32 (0..16777215)
   ACCESS     read-only
   STATUS     mandatory
   DESCRIPTION
     "This attribute displays the number of segments sent at the time 
      command was issued. This is the segment sent count maintained by 
      accounting at the source Vc. Vc only counts packets that Vc thinks 
      can be delivered successfully into the subnet. In reality, these 
      packets may be dropped by trunking, for instance. This counter is 
      not updated when splitting fails, when Vc is in a path recovery state, 
      when packet forwarding fails to forward this packet and when 
      subsequent packets have to be discarded as we want to minimize the 
      chance of out-of-sequence and do not intentionally send out-of-
      sequenced packets into the subnet."
::= { mscTraceSessionFrVcIntdEntry 4 }

mscTraceSessionFrVcStartTime OBJECT-TYPE
   SYNTAX     EnterpriseDateAndTime (SIZE (0 | 19))
   ACCESS     read-only
   STATUS     mandatory
   DESCRIPTION
     "This attribute displays the start time of this interval period. If Vc 
      spans 12 hour time or time of day change startTime reflects new 
      time as recorded at 12 hour periods or time of day changes."
::= { mscTraceSessionFrVcIntdEntry 5 }

mscTraceSessionFrVcCallReferenceNumberDecimal OBJECT-TYPE
   SYNTAX     Unsigned32 (0..4294967295)
   ACCESS     read-only
   STATUS     mandatory
   DESCRIPTION
     "This attribute displays the call reference number which is a unique 
      number generated by the switch.The same Call Reference Number 
      is stored in the interval data (accounting record) at both ends of the 
      call. It can be used as one of the attributes in matching duplicate 
      records generated at each end of the call."
::= { mscTraceSessionFrVcIntdEntry 7 }

mscTraceSessionFrVcFrdTable OBJECT-TYPE
   SYNTAX     SEQUENCE OF MscTraceSessionFrVcFrdEntry
   ACCESS     not-accessible
   STATUS     mandatory
   DESCRIPTION
     "*** THIS TABLE CURRENTLY NOT IMPLEMENTED ***

      This group defines Frame Relay attributes collected by Frame Relay 
      Vc.
      The purpose of Vc attributes is to aid end users and verification 
      people to understand the Vc internal behavior. This is particularly 
      useful when the network has experienced abnormality and we want 
      to isolate problems and pinpoint trouble spots. 
      Attributes are collected on a per Vc basis. Until a need is identified, 
      statistics are not collected at a processor level. Each attribute is 
      stored in a 32 bit field and is initialized to zero when a Vc enters 
      into the data transfer state. When a PVC is disconnected and then 
      connected again, the attributes will be reset. Attributes cannot be 
      reset through other methods. 
      Frame Relay Vc uses a best effort data packet delivery protocol and 
      a different packet segmentation and combination methods from the 
      General Vc. The Frame Relay Vc uses the same call setup and 
      control mechanism (e.g. the support of non-flow control data 
      packets) as in a General Vc. Most General Vc statistics and internal 
      variables are used in a Frame Relay Vc and are displayed by 
      software developers"
::= { mscTraceSessionFrVc 12 }

mscTraceSessionFrVcFrdEntry OBJECT-TYPE
   SYNTAX     MscTraceSessionFrVcFrdEntry
   ACCESS     not-accessible
   STATUS     mandatory
   DESCRIPTION
     "An entry in the mscTraceSessionFrVcFrdTable."
   INDEX {
      mscTraceIndex,
      mscTraceSessionIndex,
      mscTraceSessionFrIndex,
      mscTraceSessionFrVcIndex }
::= { mscTraceSessionFrVcFrdTable 1 }

MscTraceSessionFrVcFrdEntry ::= SEQUENCE {
   mscTraceSessionFrVcFrmCongestedToSubnet
      Unsigned32,
   mscTraceSessionFrVcCannotForwardToSubnet
      Unsigned32,
   mscTraceSessionFrVcNotDataXferToSubnet
      Unsigned32,
   mscTraceSessionFrVcOutOfRangeFrmFromSubnet
      Unsigned32,
   mscTraceSessionFrVcCombErrorsFromSubnet
      Unsigned32,
   mscTraceSessionFrVcDuplicatesFromSubnet
      Unsigned32,
   mscTraceSessionFrVcNotDataXferFromSubnet
      Unsigned32,
   mscTraceSessionFrVcFrmLossTimeouts
      Unsigned32,
   mscTraceSessionFrVcOoSeqByteCntExceeded
      Unsigned32,
   mscTraceSessionFrVcPeakOoSeqPktCount
      Unsigned32,
   mscTraceSessionFrVcPeakOoSeqFrmForwarded
      Unsigned32,
   mscTraceSessionFrVcSendSequenceNumber
      Unsigned32,
   mscTraceSessionFrVcPktRetryTimeouts
      Unsigned32,
   mscTraceSessionFrVcPeakRetryQueueSize
      Unsigned32,
   mscTraceSessionFrVcSubnetRecoveries
      Unsigned32,
   mscTraceSessionFrVcOoSeqPktCntExceeded
      Unsigned32,
   mscTraceSessionFrVcPeakOoSeqByteCount
      Unsigned32 }

mscTraceSessionFrVcFrmCongestedToSubnet OBJECT-TYPE
   SYNTAX     Unsigned32 (0..5000)
   ACCESS     read-only
   STATUS     mandatory
   DESCRIPTION
     "This attribute displays the number of frames from link discarded 
      due to lack of resources. It keeps track of the number of frames 
      from link that have to be discarded. The discard reasons include 
      insufficient memory for splitting the frame into smaller subnet 
      packet size."
::= { mscTraceSessionFrVcFrdEntry 2 }

mscTraceSessionFrVcCannotForwardToSubnet OBJECT-TYPE
   SYNTAX     Unsigned32 (0..5000)
   ACCESS     read-only
   STATUS     mandatory
   DESCRIPTION
     "This attribute displays the number of discarded packets that can not 
      be forwarded into the subnet because of subnet congestion.
      Number of frames from link discarded due to failure in forwarding 
      a packet from Vc into the subnet.- This attribute is increased when 
      packet forwarding fails to forward a packet into the subnet. If a 
      frame is split into multiple subnet packets and a partial packet has 
      to be discarded, all subsequent partial packets that have not yet been 
      delivered to the subnet will be discarded as well."
::= { mscTraceSessionFrVcFrdEntry 3 }

mscTraceSessionFrVcNotDataXferToSubnet OBJECT-TYPE
   SYNTAX     Unsigned32 (0..5000)
   ACCESS     read-only
   STATUS     mandatory
   DESCRIPTION
     "This attribute records the number of frames from link discarded 
      when the Vc tries to recover from internal path failure."
::= { mscTraceSessionFrVcFrdEntry 4 }

mscTraceSessionFrVcOutOfRangeFrmFromSubnet OBJECT-TYPE
   SYNTAX     Unsigned32 (0..5000)
   ACCESS     read-only
   STATUS     mandatory
   DESCRIPTION
     "This attribute displays the number of frames from subnet discarded 
      due to out of sequence range for arriving too late."
::= { mscTraceSessionFrVcFrdEntry 5 }

mscTraceSessionFrVcCombErrorsFromSubnet OBJECT-TYPE
   SYNTAX     Unsigned32 (0..5000)
   ACCESS     read-only
   STATUS     mandatory
   DESCRIPTION
     "This attribute records the number of subnet packets discarded at the 
      sink Vc due to the Vc segmentation and combination protocol error. 
      Usually, this occurs when the subnet discards packets and thus this 
      statistics can be used to guest the number of subnet packets that are 
      not delivered to the Vc. It cannot be used as an actual measure 
      because some subnet packets may have been delivered to Vc but 
      have to be discarded because these are partial packets to a frame in 
      which some other partial packets have not been properly delivered 
      to Vc"
::= { mscTraceSessionFrVcFrdEntry 6 }

mscTraceSessionFrVcDuplicatesFromSubnet OBJECT-TYPE
   SYNTAX     Unsigned32 (0..5000)
   ACCESS     read-only
   STATUS     mandatory
   DESCRIPTION
     "This attribute displays the number of subnet packets discarded due 
      to duplication. Although packets are not retransmitted by the Frame 
      Relay Vc, it is possible for the subnet to retransmit packets. When 
      packets are out-of-sequenced and copies of the same packets arrive, 
      then this attribute is increased."
::= { mscTraceSessionFrVcFrdEntry 7 }

mscTraceSessionFrVcNotDataXferFromSubnet OBJECT-TYPE
   SYNTAX     Unsigned32 (0..5000)
   ACCESS     read-only
   STATUS     mandatory
   DESCRIPTION
     "This attribute displays the number of subnet packets discarded when 
      data transfer is suspended in Vc recovery."
::= { mscTraceSessionFrVcFrdEntry 8 }

mscTraceSessionFrVcFrmLossTimeouts OBJECT-TYPE
   SYNTAX     Unsigned32 (0..5000)
   ACCESS     read-only
   STATUS     mandatory
   DESCRIPTION
     "This attribute displays the number of lost frame timer expiries.
      When this count is excessive, the network is very congested and 
      packets have been discarded in the subnet."
::= { mscTraceSessionFrVcFrdEntry 9 }

mscTraceSessionFrVcOoSeqByteCntExceeded OBJECT-TYPE
   SYNTAX     Unsigned32 (0..5000)
   ACCESS     read-only
   STATUS     mandatory
   DESCRIPTION
     "This attribute displays the number times that the out of sequence 
      byte threshold is exceeded. When the threshold is exceeded, this 
      condition is treated as if the loss frame timer has expired and all 
      frames queued at the sink Vc are delivered to the AP. We need to 
      keep this count to examine if the threshold is engineered properly. 
      This should be used in conjunction with the peak value of out-of-
      sequenced queue and the number of times the loss frame timer has 
      expired. This count should be relatively small when compared with 
      loss frame timer expiry count."
::= { mscTraceSessionFrVcFrdEntry 10 }

mscTraceSessionFrVcPeakOoSeqPktCount OBJECT-TYPE
   SYNTAX     Unsigned32 (0..5000)
   ACCESS     read-only
   STATUS     mandatory
   DESCRIPTION
     "This attribute displays the frame relay peak packet count of the out 
      of sequence queue. This attribute records the maximum queue 
      length of the out-of-sequenced queue. The counter can be used to 
      deduce the message buffer requirement on a Vc."
::= { mscTraceSessionFrVcFrdEntry 11 }

mscTraceSessionFrVcPeakOoSeqFrmForwarded OBJECT-TYPE
   SYNTAX     Unsigned32 (0..5000)
   ACCESS     read-only
   STATUS     mandatory
   DESCRIPTION
     "This attribute displays the frame relay peak size of the 
      sequence packet queue. The subnet may deliver packets out-of-
      sequenced. These packets are then queued in an out-of-sequenced 
      queue, waiting for a packet with the expected sequence number to 
      come. When that packet arrives, this attribute records the maximum 
      number of packets that were out-of-sequenced, but now have 
      become in-sequenced. The statistics is used to measure expected 
      queue size due to normal subnet packet disorder (not due to subnet 
      packet discard). Current implementation also uses this statistics to 
      set a maximum size for the out-of-sequenced queue."
::= { mscTraceSessionFrVcFrdEntry 12 }

mscTraceSessionFrVcSendSequenceNumber OBJECT-TYPE
   SYNTAX     Unsigned32 (0..5000)
   ACCESS     read-only
   STATUS     mandatory
   DESCRIPTION
     "This attribute displays the Vc internal packet's send sequence 
      number. Note that a 'packet' in this context, may be either a user 
      data packet, or an OAM frame."
::= { mscTraceSessionFrVcFrdEntry 13 }

mscTraceSessionFrVcPktRetryTimeouts OBJECT-TYPE
   SYNTAX     Unsigned32 (0..5000)
   ACCESS     read-only
   STATUS     mandatory
   DESCRIPTION
     "This attribute displays the number of packets which have 
      retransmission time-outs. When this count is excessive, the network 
      is very congested and packets have been discarded in the subnet."
::= { mscTraceSessionFrVcFrdEntry 15 }

mscTraceSessionFrVcPeakRetryQueueSize OBJECT-TYPE
   SYNTAX     Unsigned32 (0..5000)
   ACCESS     read-only
   STATUS     mandatory
   DESCRIPTION
     "This attribute displays the peak size of retransmission queue.
      This attribute is used as an indicator of the acknowledgment 
      behavior across the subnet. Records the largest body of 
      unacknowledged packets."
::= { mscTraceSessionFrVcFrdEntry 16 }

mscTraceSessionFrVcSubnetRecoveries OBJECT-TYPE
   SYNTAX     Unsigned32 (0..5000)
   ACCESS     read-only
   STATUS     mandatory
   DESCRIPTION
     "This attribute displays the number of successful Vc recovery 
      attempts."
::= { mscTraceSessionFrVcFrdEntry 17 }

mscTraceSessionFrVcOoSeqPktCntExceeded OBJECT-TYPE
   SYNTAX     Unsigned32 (0..255)
   ACCESS     read-only
   STATUS     mandatory
   DESCRIPTION
     "This attribute displays the number times that the out of sequence 
      packet threshold is exceeded. When the threshold is exceeded, this 
      condition is treated as if the loss frame timer has expired and all 
      frames queued at the sink Vc are delivered to the AP. We need to 
      keep this count to examine if the threshold is engineered properly. 
      This should be used in conjunction with the peak value of out-of-
      sequenced queue and the number of times the loss frame timer has 
      expired. This count should be relatively small when compared with 
      loss frame timer expiry count."
::= { mscTraceSessionFrVcFrdEntry 19 }

mscTraceSessionFrVcPeakOoSeqByteCount OBJECT-TYPE
   SYNTAX     Unsigned32 (0..50000)
   ACCESS     read-only
   STATUS     mandatory
   DESCRIPTION
     "This attribute displays the frame relay peak byte count of the out of 
      sequence queue. This attribute records the maximum queue length 
      of the out-of-sequenced queue. The counter can be used to deduce 
      the message buffer requirement on a Vc."
::= { mscTraceSessionFrVcFrdEntry 20 }

mscTraceSessionFrVcDmepTable OBJECT-TYPE
   SYNTAX     SEQUENCE OF MscTraceSessionFrVcDmepEntry
   ACCESS     not-accessible
   STATUS     mandatory
   DESCRIPTION
     "*** THIS TABLE CURRENTLY NOT IMPLEMENTED ***

      This attribute displays the data path used by the connection. Data 
      path is provisioned in Dna and DirectCall components.
      
      If the connection is using dprsOnly data path, this attribute is 
      empty.
      
      If the connection is using dprsMcsOnly or dprsMcsFirst data path, 
      this attribute displays component name of the dprsMcsEndPoint."
::= { mscTraceSessionFrVc 417 }

mscTraceSessionFrVcDmepEntry OBJECT-TYPE
   SYNTAX     MscTraceSessionFrVcDmepEntry
   ACCESS     not-accessible
   STATUS     mandatory
   DESCRIPTION
     "An entry in the mscTraceSessionFrVcDmepTable."
   INDEX {
      mscTraceIndex,
      mscTraceSessionIndex,
      mscTraceSessionFrIndex,
      mscTraceSessionFrVcIndex,
      mscTraceSessionFrVcDmepValue }
::= { mscTraceSessionFrVcDmepTable 1 }

MscTraceSessionFrVcDmepEntry ::= SEQUENCE {
   mscTraceSessionFrVcDmepValue
      RowPointer }

mscTraceSessionFrVcDmepValue OBJECT-TYPE
   SYNTAX     RowPointer 
   ACCESS     read-only
   STATUS     mandatory
   DESCRIPTION
     "This variable represents both the value and the index for the
      mscTraceSessionFrVcDmepTable."
::= { mscTraceSessionFrVcDmepEntry 1 }




-- 
-- Version and Compliance statements
-- 



-- Object-Group Statement:
-- A list of all current accessible leaf objects.

-- OBJECTS { mscTraceSessionFrStorageType,
--           mscTraceSessionFrVcDmepValue,
--           mscTraceSessionFrVcDataPath,
--           mscTraceRcvrFrDnaOutDefaultPriority,
--           mscTraceRcvrFrDnaOutDefaultPathReliability,
--           mscTraceRcvrFrDnaIncCalls,
--           mscTraceSessionFrVcState,
--           mscTraceSessionFrVcPeakRetryQueueSize,
--           mscTraceSessionFrVcMaxSubnetPktSize,
--           mscTraceSessionFrVcRcosFromNetwork,
--           mscTraceRcvrFrDnaCugType,
--           mscTraceRcvrFrDnaCugRowStatus,
--           mscTraceSessionFrVcDuplicatesFromSubnet,
--           mscTraceSessionFrVcStartTime,
--           mscTraceRcvrFrDnaOutIntl,
--           mscTraceSessionFrVcSendSequenceNumber,
--           mscTraceSessionFrVcEmissionPriorityToNetwork,
--           mscTraceSessionFrVcAccountingEnd,
--           mscTraceSessionFrVcDiagnosticCode,
--           mscTraceRcvrFrDcUserData,
--           mscTraceRcvrFrDnaCugFormat,
--           mscTraceRcvrFrDnaRowStatus,
--           mscTraceRcvrFrDnaCugInterlockCode,
--           mscTraceRcvrFrDcStorageType,
--           mscTraceSessionFrRowStatus,
--           mscTraceRcvrFrStorageType,
--           mscTraceSessionFrVcPeakOoSeqByteCount,
--           mscTraceRcvrFrDnaCugComponentName,
--           mscTraceRcvrFrDnaCugDnic,
--           mscTraceSessionFrVcPriority,
--           mscTraceSessionFrVcPktRetryTimeouts,
--           mscTraceSessionFrVcOutOfRangeFrmFromSubnet,
--           mscTraceRcvrFrDcType,
--           mscTraceSessionFrVcCallReferenceNumberDecimal,
--           mscTraceSessionFrVcCalledDna,
--           mscTraceSessionFrVcType,
--           mscTraceRcvrFrDnaComponentName,
--           mscTraceSessionFrVcCalledNpi,
--           mscTraceSessionFrVcAccountingEnabled,
--           mscTraceSessionFrComponentName,
--           mscTraceSessionFrVcSegmentsSent,
--           mscTraceSessionFrVcElapsedTimeTillNow,
--           mscTraceSessionFrVcNotDataXferToSubnet,
--           mscTraceRcvrFrDnaPacketSizes,
--           mscTraceSessionFrVcPreviousState,
--           mscTraceRcvrFrDcRowStatus,
--           mscTraceSessionFrVcSubnetRecoveries,
--           mscTraceRcvrFrDnaOutPathReliabilityOverRide,
--           mscTraceRcvrFrDnaDefaultSendToNetworkPacketSize,
--           mscTraceSessionFrVcRowStatus,
--           mscTraceSessionFrVcComponentName,
--           mscTraceRcvrFrDcRemoteDna,
--           mscTraceRcvrFrDnaOutPathReliabilitySignal,
--           mscTraceRcvrFrDnaOutCalls,
--           mscTraceSessionFrVcFastSelectCall,
--           mscTraceSessionFrVcRcosToNetwork,
--           mscTraceSessionFrVcStorageType,
--           mscTraceSessionFrVcSegmentSize,
--           mscTraceRcvrFrDnaCugPreferential,
--           mscTraceRcvrFrDnaOutAccess,
--           mscTraceSessionFrVcEmissionPriorityFromNetwork,
--           mscTraceSessionFrVcFrmLossTimeouts,
--           mscTraceRcvrFrDcComponentName,
--           mscTraceSessionFrVcOoSeqByteCntExceeded,
--           mscTraceRcvrFrRowStatus,
--           mscTraceRcvrFrComponentName,
--           mscTraceSessionFrVcCombErrorsFromSubnet,
--           mscTraceSessionFrVcCallingDna,
--           mscTraceRcvrFrDnaNumberingPlanIndicator,
--           mscTraceSessionFrVcCallingNpi,
--           mscTraceSessionFrVcCallingLcn,
--           mscTraceSessionFrVcPeakOoSeqFrmForwarded,
--           mscTraceSessionFrVcSegmentsRx,
--           mscTraceSessionFrVcFrmCongestedToSubnet,
--           mscTraceSessionFrVcPeakOoSeqPktCount,
--           mscTraceSessionFrVcPreviousDiagnosticCode,
--           mscTraceRcvrFrDnaCugStorageType,
--           mscTraceSessionFrVcOoSeqPktCntExceeded,
--           mscTraceRcvrFrDnaCugPrivileged,
--           mscTraceSessionFrVcCalledLcn,
--           mscTraceSessionFrVcPathReliability,
--           mscTraceSessionFrVcCannotForwardToSubnet,
--           mscTraceRcvrFrDnaDefaultRecvFrmNetworkPacketSize,
--           mscTraceRcvrFrDnaCugOutCalls,
--           mscTraceRcvrFrDnaCugIncCalls,
--           mscTraceRcvrFrDnaDataNetworkAddress,
--           mscTraceSessionFrVcNotDataXferFromSubnet,
--           mscTraceRcvrFrDnaStorageType,
--           mscTraceRcvrFrDcRemoteNpi }
-- STATUS  mandatory
-- DESCRIPTION
--   "A list of all current accessible leaf objects."

frTraceRcvrGroup OBJECT IDENTIFIER ::= { frTraceRcvrMIB 1 }
frTraceRcvrGroupCA OBJECT IDENTIFIER ::= { frTraceRcvrGroup 1 }
frTraceRcvrGroupCA02 OBJECT IDENTIFIER ::= { frTraceRcvrGroupCA 3 }
frTraceRcvrGroupCA02A OBJECT IDENTIFIER ::= { frTraceRcvrGroupCA02 2 }



-- Agent-Capabilities Statement:

-- PRODUCT-RELEASE "MscPassport Release 1.2 FrTraceRcvr."
-- STATUS          mandatory
-- DESCRIPTION     "Carrier Passport FrTraceRcvr MIB: MIB Version CA02A,
--                  Software Version CA02S9C."
-- SUPPORTS        Nortel-MsCarrier-MscPassport-FrTraceRcvrMIB
--    INCLUDES     { frTraceRcvrGroupCA02A }

frTraceRcvrCapabilities OBJECT IDENTIFIER ::= { frTraceRcvrMIB 3 }
frTraceRcvrCapabilitiesCA OBJECT IDENTIFIER ::= { frTraceRcvrCapabilities 1 }
frTraceRcvrCapabilitiesCA02 OBJECT IDENTIFIER ::= { frTraceRcvrCapabilitiesCA 3 }
frTraceRcvrCapabilitiesCA02A OBJECT IDENTIFIER ::= { frTraceRcvrCapabilitiesCA02 2 }





END
