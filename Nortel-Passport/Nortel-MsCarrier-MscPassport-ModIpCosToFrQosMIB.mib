Nortel-MsCarrier-MscPassport-ModIpCosToFrQosMIB
DEFINITIONS ::= BEGIN



IMPORTS

      OBJECT-TYPE
   FROM RFC-1212

      mscPassportMIBs
   FROM Nortel-MsCarrier-MscPassport-UsefulDefinitionsMIB

      DisplayString,
      StorageType,
      RowStatus,
      Integer32,
      Unsigned32
   FROM Nortel-MsCarrier-MscPassport-StandardTextualConventionsMIB

      NonReplicated
   FROM Nortel-MsCarrier-MscPassport-TextualConventionsMIB

      mscModFrsIndex,
      mscModFrs
   FROM Nortel-MsCarrier-MscPassport-ModCommonMIB

      mscModIndex
   FROM Nortel-MsCarrier-MscPassport-BaseShelfMIB;




-- LAST-UPDATED   "9907300000Z"
-- ORGANIZATION   "Nortel Networks"
-- CONTACT-INFO   "
--         Nortel Carrier Data Network Management
--         
--         Postal:       P.O. Box 3511, Station C 
--                       Ottawa, Ontario 
--                       Canada  K1Y 4H7
--         
--         via the WEB:  http://www.nortelnetworks.com  
--                       select 'Contact Us' from the menu
--          
--         via phone:    1-800-4NORTEL"
-- DESCRIPTION
--    "The module describing the Nortel MsCarrier MscPassport
--     ModIpCosToFrQos Enterprise MIB."

modIpCosToFrQosMIB OBJECT IDENTIFIER ::= { mscPassportMIBs 81 }










-- Mod Frs IpCosToFrQos 
-- This component is used to define a number of general 
-- characteristics for all Frame Relay connections using Frame Relay 
-- IP Traffic management. All the modules in the network should have 
-- identical IpCosToFrQos attributes. If these attributes are not 
-- consistent across the network, then the service may be degraded. 

mscModFrsIpCosToFrQos OBJECT IDENTIFIER ::= { mscModFrs 4 }



mscModFrsIpCosToFrQosRowStatusTable OBJECT-TYPE
   SYNTAX     SEQUENCE OF MscModFrsIpCosToFrQosRowStatusEntry
   ACCESS     not-accessible
   STATUS     mandatory
   DESCRIPTION
     "This entry controls the addition and deletion of 
      mscModFrsIpCosToFrQos components."
::= { mscModFrsIpCosToFrQos 1 }

mscModFrsIpCosToFrQosRowStatusEntry OBJECT-TYPE
   SYNTAX     MscModFrsIpCosToFrQosRowStatusEntry
   ACCESS     not-accessible
   STATUS     mandatory
   DESCRIPTION
     "A single entry in the table represents a single 
      mscModFrsIpCosToFrQos component."
   INDEX {
      mscModIndex,
      mscModFrsIndex,
      mscModFrsIpCosToFrQosIndex }
::= { mscModFrsIpCosToFrQosRowStatusTable 1 }

MscModFrsIpCosToFrQosRowStatusEntry ::= SEQUENCE {
   mscModFrsIpCosToFrQosRowStatus
      RowStatus,
   mscModFrsIpCosToFrQosComponentName
      DisplayString,
   mscModFrsIpCosToFrQosStorageType
      StorageType,
   mscModFrsIpCosToFrQosIndex
      NonReplicated }

mscModFrsIpCosToFrQosRowStatus OBJECT-TYPE
   SYNTAX     RowStatus 
   ACCESS     read-only
   STATUS     mandatory
   DESCRIPTION
     "This variable is used as the basis for SNMP naming of
      mscModFrsIpCosToFrQos components.
      These components cannot be added nor deleted."
::= { mscModFrsIpCosToFrQosRowStatusEntry 1 }

mscModFrsIpCosToFrQosComponentName OBJECT-TYPE
   SYNTAX     DisplayString 
   ACCESS     read-only
   STATUS     mandatory
   DESCRIPTION
     "This variable provides the component's string name for
      use with the ASCII Console Interface"
::= { mscModFrsIpCosToFrQosRowStatusEntry 2 }

mscModFrsIpCosToFrQosStorageType OBJECT-TYPE
   SYNTAX     StorageType 
   ACCESS     read-only
   STATUS     mandatory
   DESCRIPTION
     "This variable represents the storage type value for the
      mscModFrsIpCosToFrQos tables."
::= { mscModFrsIpCosToFrQosRowStatusEntry 4 }

mscModFrsIpCosToFrQosIndex OBJECT-TYPE
   SYNTAX     NonReplicated 
   ACCESS     not-accessible
   STATUS     mandatory
   DESCRIPTION
     "This variable represents the index for the mscModFrsIpCosToFrQos tables."
::= { mscModFrsIpCosToFrQosRowStatusEntry 10 }


-- Mod Frs IpCosToFrQos TypeOfServiceMapping/n
-- This component represents the type of service mappings for Frame 
-- Relay connections using Frame Relay IP Traffic Management. 
-- 
-- The instance corresponds to a particular IP TOS value. All 256 
-- possible instances are always present. Instances of this component 
-- cannot be deleted.

mscModFrsIpCosToFrQosTosm OBJECT IDENTIFIER ::= { mscModFrsIpCosToFrQos 2 }



mscModFrsIpCosToFrQosTosmRowStatusTable OBJECT-TYPE
   SYNTAX     SEQUENCE OF MscModFrsIpCosToFrQosTosmRowStatusEntry
   ACCESS     not-accessible
   STATUS     mandatory
   DESCRIPTION
     "This entry controls the addition and deletion of 
      mscModFrsIpCosToFrQosTosm components."
::= { mscModFrsIpCosToFrQosTosm 1 }

mscModFrsIpCosToFrQosTosmRowStatusEntry OBJECT-TYPE
   SYNTAX     MscModFrsIpCosToFrQosTosmRowStatusEntry
   ACCESS     not-accessible
   STATUS     mandatory
   DESCRIPTION
     "A single entry in the table represents a single 
      mscModFrsIpCosToFrQosTosm component."
   INDEX {
      mscModIndex,
      mscModFrsIndex,
      mscModFrsIpCosToFrQosIndex,
      mscModFrsIpCosToFrQosTosmIndex }
::= { mscModFrsIpCosToFrQosTosmRowStatusTable 1 }

MscModFrsIpCosToFrQosTosmRowStatusEntry ::= SEQUENCE {
   mscModFrsIpCosToFrQosTosmRowStatus
      RowStatus,
   mscModFrsIpCosToFrQosTosmComponentName
      DisplayString,
   mscModFrsIpCosToFrQosTosmStorageType
      StorageType,
   mscModFrsIpCosToFrQosTosmIndex
      Integer32 }

mscModFrsIpCosToFrQosTosmRowStatus OBJECT-TYPE
   SYNTAX     RowStatus 
   ACCESS     read-write
   STATUS     mandatory
   DESCRIPTION
     "This variable is used as the basis for SNMP naming of
      mscModFrsIpCosToFrQosTosm components.
      These components can be added."
::= { mscModFrsIpCosToFrQosTosmRowStatusEntry 1 }

mscModFrsIpCosToFrQosTosmComponentName OBJECT-TYPE
   SYNTAX     DisplayString 
   ACCESS     read-only
   STATUS     mandatory
   DESCRIPTION
     "This variable provides the component's string name for
      use with the ASCII Console Interface"
::= { mscModFrsIpCosToFrQosTosmRowStatusEntry 2 }

mscModFrsIpCosToFrQosTosmStorageType OBJECT-TYPE
   SYNTAX     StorageType 
   ACCESS     read-only
   STATUS     mandatory
   DESCRIPTION
     "This variable represents the storage type value for the
      mscModFrsIpCosToFrQosTosm tables."
::= { mscModFrsIpCosToFrQosTosmRowStatusEntry 4 }

mscModFrsIpCosToFrQosTosmIndex OBJECT-TYPE
   SYNTAX     Integer32 (0..255)
   ACCESS     not-accessible
   STATUS     mandatory
   DESCRIPTION
     "This variable represents the index for the mscModFrsIpCosToFrQosTosm tables."
::= { mscModFrsIpCosToFrQosTosmRowStatusEntry 10 }

mscModFrsIpCosToFrQosTosmProvTable OBJECT-TYPE
   SYNTAX     SEQUENCE OF MscModFrsIpCosToFrQosTosmProvEntry
   ACCESS     not-accessible
   STATUS     mandatory
   DESCRIPTION
     "This group specifies the mapping from the IP type of service value 
      to the egress emission priority and discard priority. Any changes to 
      TOS mappings will immediately take effect on new calls."
::= { mscModFrsIpCosToFrQosTosm 10 }

mscModFrsIpCosToFrQosTosmProvEntry OBJECT-TYPE
   SYNTAX     MscModFrsIpCosToFrQosTosmProvEntry
   ACCESS     not-accessible
   STATUS     mandatory
   DESCRIPTION
     "An entry in the mscModFrsIpCosToFrQosTosmProvTable."
   INDEX {
      mscModIndex,
      mscModFrsIndex,
      mscModFrsIpCosToFrQosIndex,
      mscModFrsIpCosToFrQosTosmIndex }
::= { mscModFrsIpCosToFrQosTosmProvTable 1 }

MscModFrsIpCosToFrQosTosmProvEntry ::= SEQUENCE {
   mscModFrsIpCosToFrQosTosmEmissionPriority
      Unsigned32,
   mscModFrsIpCosToFrQosTosmDiscardPriority
      INTEGER }

mscModFrsIpCosToFrQosTosmEmissionPriority OBJECT-TYPE
   SYNTAX     Unsigned32 (0..3)
   ACCESS     read-write
   STATUS     mandatory
   DESCRIPTION
     "This attribute specifies the egress emission priority at the Frame 
      Relay interface. A value of 3 specifies the highest priority, whereas 
      a value of 0 specifies the lowest priority.
      
      Changes to this attribute effect only new calls."
   DEFVAL     { 0 }
::= { mscModFrsIpCosToFrQosTosmProvEntry 1 }

mscModFrsIpCosToFrQosTosmDiscardPriority OBJECT-TYPE
   SYNTAX     INTEGER  {
                 normal(0),
                 high(1) }
   ACCESS     read-write
   STATUS     mandatory
   DESCRIPTION
     "This attribute specifies the egress discard priority at the Frame 
      Relay interface. A value of normal specifies the lowest priority 
      (more readily discarded), whereas a value of high specifies the 
      highest priority (less readily discarded).
      
      Changes to this attribute effect only new calls."
   DEFVAL     { normal }
::= { mscModFrsIpCosToFrQosTosmProvEntry 2 }




-- 
-- Version and Compliance statements
-- 



-- Object-Group Statement:
-- A list of all current accessible leaf objects.

-- OBJECTS { mscModFrsIpCosToFrQosTosmStorageType,
--           mscModFrsIpCosToFrQosTosmRowStatus,
--           mscModFrsIpCosToFrQosTosmComponentName,
--           mscModFrsIpCosToFrQosTosmEmissionPriority,
--           mscModFrsIpCosToFrQosTosmDiscardPriority,
--           mscModFrsIpCosToFrQosComponentName,
--           mscModFrsIpCosToFrQosStorageType,
--           mscModFrsIpCosToFrQosRowStatus }
-- STATUS  mandatory
-- DESCRIPTION
--   "A list of all current accessible leaf objects."

modIpCosToFrQosGroup OBJECT IDENTIFIER ::= { modIpCosToFrQosMIB 1 }
modIpCosToFrQosGroupCA OBJECT IDENTIFIER ::= { modIpCosToFrQosGroup 1 }
modIpCosToFrQosGroupCA02 OBJECT IDENTIFIER ::= { modIpCosToFrQosGroupCA 3 }
modIpCosToFrQosGroupCA02A OBJECT IDENTIFIER ::= { modIpCosToFrQosGroupCA02 2 }



-- Agent-Capabilities Statement:

-- PRODUCT-RELEASE "MscPassport Release 1.2 ModIpCosToFrQos."
-- STATUS          mandatory
-- DESCRIPTION     "Carrier Passport ModIpCosToFrQos MIB: MIB Version CA02A,
--                  Software Version CA02S9C."
-- SUPPORTS        Nortel-MsCarrier-MscPassport-ModIpCosToFrQosMIB
--    INCLUDES     { modIpCosToFrQosGroupCA02A }

modIpCosToFrQosCapabilities OBJECT IDENTIFIER ::= { modIpCosToFrQosMIB 3 }
modIpCosToFrQosCapabilitiesCA OBJECT IDENTIFIER ::= { modIpCosToFrQosCapabilities 1 }
modIpCosToFrQosCapabilitiesCA02 OBJECT IDENTIFIER ::= { modIpCosToFrQosCapabilitiesCA 3 }
modIpCosToFrQosCapabilitiesCA02A OBJECT IDENTIFIER ::= { modIpCosToFrQosCapabilitiesCA02 2 }





END
