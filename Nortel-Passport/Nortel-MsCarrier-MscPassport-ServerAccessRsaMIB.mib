Nortel-MsCarrier-MscPassport-ServerAccessRsaMIB
DEFINITIONS ::= BEGIN



IMPORTS

      OBJECT-TYPE
   FROM RFC-1212

      mscPassportMIBs,
      mscComponents
   FROM Nortel-MsCarrier-MscPassport-UsefulDefinitionsMIB

      Counter32,
      RowPointer,
      DisplayString,
      StorageType,
      RowStatus,
      Integer32,
      Unsigned32
   FROM Nortel-MsCarrier-MscPassport-StandardTextualConventionsMIB

      AsciiString,
      Hex,
      NonReplicated,
      EnterpriseDateAndTime,
      Link,
      AsciiStringIndex,
      DigitString
   FROM Nortel-MsCarrier-MscPassport-TextualConventionsMIB;




-- LAST-UPDATED   "9909010000Z"
-- ORGANIZATION   "Nortel Networks"
-- CONTACT-INFO   "
--         Nortel Carrier Data Network Management
--         
--         Postal:       P.O. Box 3511, Station C 
--                       Ottawa, Ontario 
--                       Canada  K1Y 4H7
--         
--         via the WEB:  http://www.nortelnetworks.com  
--                       select 'Contact Us' from the menu
--          
--         via phone:    1-800-4NORTEL"
-- DESCRIPTION
--    "The module describing the Nortel MsCarrier MscPassport
--     ServerAccessRsa Enterprise MIB."

serverAccessRsaMIB OBJECT IDENTIFIER ::= { mscPassportMIBs 116 }










-- RemoteServerAgent/<string>
-- The Rsa component provides non-Passport based applications 
-- access to Passport servers via a Frame Relay SVC connection. The 
-- Rsa component can be provisioned on any Passport module in the 
-- network. Multiple Rsa components can be provisioned for load 
-- sharing and/or backup purposes. The component instance value is a 
-- unique string within the module.

mscRsa OBJECT IDENTIFIER ::= { mscComponents 108 }



mscRsaRowStatusTable OBJECT-TYPE
   SYNTAX     SEQUENCE OF MscRsaRowStatusEntry
   ACCESS     not-accessible
   STATUS     mandatory
   DESCRIPTION
     "This entry controls the addition and deletion of 
      mscRsa components."
::= { mscRsa 1 }

mscRsaRowStatusEntry OBJECT-TYPE
   SYNTAX     MscRsaRowStatusEntry
   ACCESS     not-accessible
   STATUS     mandatory
   DESCRIPTION
     "A single entry in the table represents a single 
      mscRsa component."
   INDEX {
      mscRsaIndex }
::= { mscRsaRowStatusTable 1 }

MscRsaRowStatusEntry ::= SEQUENCE {
   mscRsaRowStatus
      RowStatus,
   mscRsaComponentName
      DisplayString,
   mscRsaStorageType
      StorageType,
   mscRsaIndex
      AsciiStringIndex }

mscRsaRowStatus OBJECT-TYPE
   SYNTAX     RowStatus 
   ACCESS     read-write
   STATUS     mandatory
   DESCRIPTION
     "This variable is used as the basis for SNMP naming of
      mscRsa components.
      These components can be added and deleted."
::= { mscRsaRowStatusEntry 1 }

mscRsaComponentName OBJECT-TYPE
   SYNTAX     DisplayString 
   ACCESS     read-only
   STATUS     mandatory
   DESCRIPTION
     "This variable provides the component's string name for
      use with the ASCII Console Interface"
::= { mscRsaRowStatusEntry 2 }

mscRsaStorageType OBJECT-TYPE
   SYNTAX     StorageType 
   ACCESS     read-only
   STATUS     mandatory
   DESCRIPTION
     "This variable represents the storage type value for the
      mscRsa tables."
::= { mscRsaRowStatusEntry 4 }

mscRsaIndex OBJECT-TYPE
   SYNTAX     AsciiStringIndex (SIZE (1..8))
   ACCESS     not-accessible
   STATUS     mandatory
   DESCRIPTION
     "This variable represents the index for the mscRsa tables."
::= { mscRsaRowStatusEntry 10 }

mscRsaOptionsTable OBJECT-TYPE
   SYNTAX     SEQUENCE OF MscRsaOptionsEntry
   ACCESS     not-accessible
   STATUS     mandatory
   DESCRIPTION
     "The Options group defines provisionable attributes associated with 
      the Rsa component."
::= { mscRsa 10 }

mscRsaOptionsEntry OBJECT-TYPE
   SYNTAX     MscRsaOptionsEntry
   ACCESS     not-accessible
   STATUS     mandatory
   DESCRIPTION
     "An entry in the mscRsaOptionsTable."
   INDEX {
      mscRsaIndex }
::= { mscRsaOptionsTable 1 }

MscRsaOptionsEntry ::= SEQUENCE {
   mscRsaLogicalProcessor
      Link }

mscRsaLogicalProcessor OBJECT-TYPE
   SYNTAX     Link 
   ACCESS     read-write
   STATUS     mandatory
   DESCRIPTION
     "This attribute specifies the logical processor on which the RSA 
      process will execute."
::= { mscRsaOptionsEntry 2 }

mscRsaStateTable OBJECT-TYPE
   SYNTAX     SEQUENCE OF MscRsaStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscRsa 11 }

mscRsaStateEntry OBJECT-TYPE
   SYNTAX     MscRsaStateEntry
   ACCESS     not-accessible
   STATUS     mandatory
   DESCRIPTION
     "An entry in the mscRsaStateTable."
   INDEX {
      mscRsaIndex }
::= { mscRsaStateTable 1 }

MscRsaStateEntry ::= SEQUENCE {
   mscRsaAdminState
      INTEGER,
   mscRsaOperationalState
      INTEGER,
   mscRsaUsageState
      INTEGER }

mscRsaAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscRsaStateEntry 1 }

mscRsaOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscRsaStateEntry 2 }

mscRsaUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscRsaStateEntry 3 }

mscRsaOperationalTable OBJECT-TYPE
   SYNTAX     SEQUENCE OF MscRsaOperationalEntry
   ACCESS     not-accessible
   STATUS     mandatory
   DESCRIPTION
     "The Operational group defines operational attributes associated 
      with the Rsa component."
::= { mscRsa 12 }

mscRsaOperationalEntry OBJECT-TYPE
   SYNTAX     MscRsaOperationalEntry
   ACCESS     not-accessible
   STATUS     mandatory
   DESCRIPTION
     "An entry in the mscRsaOperationalTable."
   INDEX {
      mscRsaIndex }
::= { mscRsaOperationalTable 1 }

MscRsaOperationalEntry ::= SEQUENCE {
   mscRsaMaxRsiConnections
      INTEGER,
   mscRsaRsiConnections
      INTEGER }

mscRsaMaxRsiConnections OBJECT-TYPE
   SYNTAX     INTEGER (1000)
   ACCESS     read-only
   STATUS     mandatory
   DESCRIPTION
     "This attribute specifies the maximum number of RSI connections 
      which can be supported by this Rsa."
::= { mscRsaOperationalEntry 2 }

mscRsaRsiConnections OBJECT-TYPE
   SYNTAX     INTEGER (0..1000)
   ACCESS     read-only
   STATUS     mandatory
   DESCRIPTION
     "This attribute specifies the number of active RSI connections 
      currently supported by the Rsa component."
::= { mscRsaOperationalEntry 3 }


-- Rsa/n DataNetworkAddress
-- This is the description of the Remote Server Agent Dna component. 
-- It includes the attributes which apply to a Vc between the RSI and 
-- RSA.

mscRsaDna OBJECT IDENTIFIER ::= { mscRsa 2 }



mscRsaDnaRowStatusTable OBJECT-TYPE
   SYNTAX     SEQUENCE OF MscRsaDnaRowStatusEntry
   ACCESS     not-accessible
   STATUS     mandatory
   DESCRIPTION
     "This entry controls the addition and deletion of 
      mscRsaDna components."
::= { mscRsaDna 1 }

mscRsaDnaRowStatusEntry OBJECT-TYPE
   SYNTAX     MscRsaDnaRowStatusEntry
   ACCESS     not-accessible
   STATUS     mandatory
   DESCRIPTION
     "A single entry in the table represents a single 
      mscRsaDna component."
   INDEX {
      mscRsaIndex,
      mscRsaDnaIndex }
::= { mscRsaDnaRowStatusTable 1 }

MscRsaDnaRowStatusEntry ::= SEQUENCE {
   mscRsaDnaRowStatus
      RowStatus,
   mscRsaDnaComponentName
      DisplayString,
   mscRsaDnaStorageType
      StorageType,
   mscRsaDnaIndex
      NonReplicated }

mscRsaDnaRowStatus OBJECT-TYPE
   SYNTAX     RowStatus 
   ACCESS     read-only
   STATUS     mandatory
   DESCRIPTION
     "This variable is used as the basis for SNMP naming of
      mscRsaDna components.
      These components cannot be added nor deleted."
::= { mscRsaDnaRowStatusEntry 1 }

mscRsaDnaComponentName OBJECT-TYPE
   SYNTAX     DisplayString 
   ACCESS     read-only
   STATUS     mandatory
   DESCRIPTION
     "This variable provides the component's string name for
      use with the ASCII Console Interface"
::= { mscRsaDnaRowStatusEntry 2 }

mscRsaDnaStorageType OBJECT-TYPE
   SYNTAX     StorageType 
   ACCESS     read-only
   STATUS     mandatory
   DESCRIPTION
     "This variable represents the storage type value for the
      mscRsaDna tables."
::= { mscRsaDnaRowStatusEntry 4 }

mscRsaDnaIndex OBJECT-TYPE
   SYNTAX     NonReplicated 
   ACCESS     not-accessible
   STATUS     mandatory
   DESCRIPTION
     "This variable represents the index for the mscRsaDna tables."
::= { mscRsaDnaRowStatusEntry 10 }

mscRsaDnaAddressTable OBJECT-TYPE
   SYNTAX     SEQUENCE OF MscRsaDnaAddressEntry
   ACCESS     not-accessible
   STATUS     mandatory
   DESCRIPTION
     "The Address group contains attributes common to all Dna's. Every 
      Dna used in the network is defined with this group of 2 attributes. 
      The string of address digits is complemented by the type of address 
      or Npi. These attributes are used to interpret the format of the 
      address digits."
::= { mscRsaDna 10 }

mscRsaDnaAddressEntry OBJECT-TYPE
   SYNTAX     MscRsaDnaAddressEntry
   ACCESS     not-accessible
   STATUS     mandatory
   DESCRIPTION
     "An entry in the mscRsaDnaAddressTable."
   INDEX {
      mscRsaIndex,
      mscRsaDnaIndex }
::= { mscRsaDnaAddressTable 1 }

MscRsaDnaAddressEntry ::= SEQUENCE {
   mscRsaDnaNumberingPlanIndicator
      INTEGER,
   mscRsaDnaDataNetworkAddress
      DigitString }

mscRsaDnaNumberingPlanIndicator OBJECT-TYPE
   SYNTAX     INTEGER  {
                 x121(0),
                 e164(1) }
   ACCESS     read-write
   STATUS     mandatory
   DESCRIPTION
     "This attribute indicates the Numbering Plan Indicator (NPI) of the 
      Dna that is entered. An address may belong to the X.121 or E.164 
      numbering plans. X.121 is used in packet switched data networks."
   DEFVAL     { x121 }
::= { mscRsaDnaAddressEntry 1 }

mscRsaDnaDataNetworkAddress OBJECT-TYPE
   SYNTAX     DigitString (SIZE (1..15))
   ACCESS     read-write
   STATUS     mandatory
   DESCRIPTION
     "The Dna attribute contains digits which form a unique identifier of 
      the customer interface. It can be compared (approximation only) to 
      a telephone number where each phone number identifies a unique 
      telephone set. Dna digits are selected and assigned by network 
      operators."
::= { mscRsaDnaAddressEntry 2 }

mscRsaDnaOutgoingOptionsTable OBJECT-TYPE
   SYNTAX     SEQUENCE OF MscRsaDnaOutgoingOptionsEntry
   ACCESS     not-accessible
   STATUS     mandatory
   DESCRIPTION
     "The OutgoingOptions group defines call options of a Dna for calls 
      which are made out of the interface represented by the Dna. These 
      options are not used for calls arriving to the interface represented by 
      the Dna."
::= { mscRsaDna 11 }

mscRsaDnaOutgoingOptionsEntry OBJECT-TYPE
   SYNTAX     MscRsaDnaOutgoingOptionsEntry
   ACCESS     not-accessible
   STATUS     mandatory
   DESCRIPTION
     "An entry in the mscRsaDnaOutgoingOptionsTable."
   INDEX {
      mscRsaIndex,
      mscRsaDnaIndex }
::= { mscRsaDnaOutgoingOptionsTable 1 }

MscRsaDnaOutgoingOptionsEntry ::= SEQUENCE {
   mscRsaDnaOutCalls
      INTEGER }

mscRsaDnaOutCalls OBJECT-TYPE
   SYNTAX     INTEGER  {
                 disallowed(0),
                 allowed(1) }
   ACCESS     read-only
   STATUS     mandatory
   DESCRIPTION
     "This attribute, if set to a value of allowed indicates that outgoing 
      calls (from the DTE to the network) can be made using this 
      particular Dna. If set to a value of disallowed, then outgoing calls 
      cannot be made using this Dna - such calls will be cleared by the 
      local DCE. This attribute corresponds to the ITU-T 'Outgoing Calls 
      Barred' feature for Dnas in that outgoing calls are barred if this 
      attribute is set to a value of disallowed. Either outCalls, or incCalls 
      (or both) must be set to a value of allowed for this Dna to be usable."
   DEFVAL     { disallowed }
::= { mscRsaDnaOutgoingOptionsEntry 1 }

mscRsaDnaIncomingOptionsTable OBJECT-TYPE
   SYNTAX     SEQUENCE OF MscRsaDnaIncomingOptionsEntry
   ACCESS     not-accessible
   STATUS     mandatory
   DESCRIPTION
     "IncomingOptions defines the set of options for incoming calls. 
      These options are used for calls arriving to the interface represented 
      by the Dna. For calls originated from the interface, 
      IncomingOptions attributes are not used."
::= { mscRsaDna 12 }

mscRsaDnaIncomingOptionsEntry OBJECT-TYPE
   SYNTAX     MscRsaDnaIncomingOptionsEntry
   ACCESS     not-accessible
   STATUS     mandatory
   DESCRIPTION
     "An entry in the mscRsaDnaIncomingOptionsTable."
   INDEX {
      mscRsaIndex,
      mscRsaDnaIndex }
::= { mscRsaDnaIncomingOptionsTable 1 }

MscRsaDnaIncomingOptionsEntry ::= SEQUENCE {
   mscRsaDnaIncCalls
      INTEGER,
   mscRsaDnaIncAccess
      INTEGER }

mscRsaDnaIncCalls OBJECT-TYPE
   SYNTAX     INTEGER  {
                 disallowed(0),
                 allowed(1) }
   ACCESS     read-only
   STATUS     mandatory
   DESCRIPTION
     "This attribute, if set to a value of allowed indicates that incoming 
      calls (from the network to the DTE) can be made to this Dna. If set 
      to a value of disallowed, then incoming calls cannot be made to this 
      Dna - such calls will be cleared by the local DCE. This attribute 
      corresponds to the ITU-T 'Incoming Calls Barred' feature for Dna's 
      in that incoming calls are barred if this attribute is set to a value of 
      disallowed.
      Either outCalls, or incCalls (or both) must be set to a value of 
      allowed for this Dna to be usable."
   DEFVAL     { allowed }
::= { mscRsaDnaIncomingOptionsEntry 1 }

mscRsaDnaIncAccess OBJECT-TYPE
   SYNTAX     INTEGER  {
                 disallowed(0),
                 allowed(1) }
   ACCESS     read-write
   STATUS     mandatory
   DESCRIPTION
     "This attribute is an extension of the Closed User Group (CUG) 
      facility, as follows:
      This attribute, if set to a value of allowed indicates that incoming 
      calls (from the network to the DTE) from the open (non-CUG) part 
      of the network are permitted. It also permits incoming calls from 
      DTEs that have Outgoing Access capabilities. If set to a value of 
      disallowed, then such calls cannot be made to this Dna - such calls 
      will be cleared by the local DCE.
      This attribute corresponds to the ITU-T 'Closed User Group with 
      Incoming Access' feature for Dnas in that incoming access is 
      granted if this attribute is set to a value of allowed."
   DEFVAL     { disallowed }
::= { mscRsaDnaIncomingOptionsEntry 9 }


-- Rsa/n Dna ClosedUserGroup
-- ClosedUserGroup defines options associated with a national or 
-- international Cug Identifier. Other Dnas in the network can have 
-- Cugs defined which group these Dnas by Cug interlockCode. If 
-- Dnas are defined with Cugs, calls from Dnas which do not have the 
-- same interlockCode defined are refused. Attributes incAccess and 
-- outAccess can override this rule.

mscRsaDnaCug OBJECT IDENTIFIER ::= { mscRsaDna 2 }



mscRsaDnaCugRowStatusTable OBJECT-TYPE
   SYNTAX     SEQUENCE OF MscRsaDnaCugRowStatusEntry
   ACCESS     not-accessible
   STATUS     mandatory
   DESCRIPTION
     "This entry controls the addition and deletion of 
      mscRsaDnaCug components."
::= { mscRsaDnaCug 1 }

mscRsaDnaCugRowStatusEntry OBJECT-TYPE
   SYNTAX     MscRsaDnaCugRowStatusEntry
   ACCESS     not-accessible
   STATUS     mandatory
   DESCRIPTION
     "A single entry in the table represents a single 
      mscRsaDnaCug component."
   INDEX {
      mscRsaIndex,
      mscRsaDnaIndex,
      mscRsaDnaCugIndex }
::= { mscRsaDnaCugRowStatusTable 1 }

MscRsaDnaCugRowStatusEntry ::= SEQUENCE {
   mscRsaDnaCugRowStatus
      RowStatus,
   mscRsaDnaCugComponentName
      DisplayString,
   mscRsaDnaCugStorageType
      StorageType,
   mscRsaDnaCugIndex
      Integer32 }

mscRsaDnaCugRowStatus OBJECT-TYPE
   SYNTAX     RowStatus 
   ACCESS     read-write
   STATUS     mandatory
   DESCRIPTION
     "This variable is used as the basis for SNMP naming of
      mscRsaDnaCug components.
      These components can be added and deleted."
::= { mscRsaDnaCugRowStatusEntry 1 }

mscRsaDnaCugComponentName OBJECT-TYPE
   SYNTAX     DisplayString 
   ACCESS     read-only
   STATUS     mandatory
   DESCRIPTION
     "This variable provides the component's string name for
      use with the ASCII Console Interface"
::= { mscRsaDnaCugRowStatusEntry 2 }

mscRsaDnaCugStorageType OBJECT-TYPE
   SYNTAX     StorageType 
   ACCESS     read-only
   STATUS     mandatory
   DESCRIPTION
     "This variable represents the storage type value for the
      mscRsaDnaCug tables."
::= { mscRsaDnaCugRowStatusEntry 4 }

mscRsaDnaCugIndex OBJECT-TYPE
   SYNTAX     Integer32 (0..255)
   ACCESS     not-accessible
   STATUS     mandatory
   DESCRIPTION
     "This variable represents the index for the mscRsaDnaCug tables."
::= { mscRsaDnaCugRowStatusEntry 10 }

mscRsaDnaCugCugOptionsTable OBJECT-TYPE
   SYNTAX     SEQUENCE OF MscRsaDnaCugCugOptionsEntry
   ACCESS     not-accessible
   STATUS     mandatory
   DESCRIPTION
     "Attributes in this group define ClosedUserGroup options associated 
      with this particular interlockCode. Dna's with the same Cug 
      (interlockCode) can make calls within this group. Various 
      combinations which permit or prevent calls in the same Cug group 
      are defined here."
::= { mscRsaDnaCug 10 }

mscRsaDnaCugCugOptionsEntry OBJECT-TYPE
   SYNTAX     MscRsaDnaCugCugOptionsEntry
   ACCESS     not-accessible
   STATUS     mandatory
   DESCRIPTION
     "An entry in the mscRsaDnaCugCugOptionsTable."
   INDEX {
      mscRsaIndex,
      mscRsaDnaIndex,
      mscRsaDnaCugIndex }
::= { mscRsaDnaCugCugOptionsTable 1 }

MscRsaDnaCugCugOptionsEntry ::= SEQUENCE {
   mscRsaDnaCugType
      INTEGER,
   mscRsaDnaCugDnic
      DigitString,
   mscRsaDnaCugInterlockCode
      Unsigned32,
   mscRsaDnaCugPreferential
      INTEGER,
   mscRsaDnaCugOutCalls
      INTEGER,
   mscRsaDnaCugIncCalls
      INTEGER,
   mscRsaDnaCugPrivileged
      INTEGER }

mscRsaDnaCugType OBJECT-TYPE
   SYNTAX     INTEGER  {
                 national(0),
                 international(1) }
   ACCESS     read-write
   STATUS     mandatory
   DESCRIPTION
     "This attribute specifies the Cug type - the Cug is either a national 
      Cug, or an international Cug. International closed user groups are 
      usually established between DTEs for which there is an X.75 
      Gateway between; whereas national closed user groups are usually 
      established between DTEs for which there is no X.75 Gateway 
      between. (National Cugs cannot normally traverse an X.75 
      Gateway).
      If this attribute is set to national, then the Cug is a national Cug, in 
      which case, the dnic should be left at its default value since it is not 
      part of a national Cug. If this attribute is set to international, then 
      the Cug is an international Cug, in which case, the dnic should be 
      set appropriately as part of the Cug interlockCode."
   DEFVAL     { national }
::= { mscRsaDnaCugCugOptionsEntry 1 }

mscRsaDnaCugDnic OBJECT-TYPE
   SYNTAX     DigitString (SIZE (4))
   ACCESS     read-write
   STATUS     mandatory
   DESCRIPTION
     "This attribute specifies the dnic (Data Network ID Code) of the Cug 
      by which packet networks are identified. This attribute is not 
      applicable if the Cug is a national Cug, as specified by the Cug type 
      attribute. There are usually 1 or 2 dnics assigned per country, for 
      public networks. The U.S. is an exception where each BOC has a 
      dnic. Also, a group of private networks can have its own dnic.
      dnic value is not an arbitrary number. It is assigned by international 
      agreement and controlled by ITU-T."
   DEFVAL     { '30303030'H }  -- "0000"
::= { mscRsaDnaCugCugOptionsEntry 2 }

mscRsaDnaCugInterlockCode OBJECT-TYPE
   SYNTAX     Unsigned32 (0..65535)
   ACCESS     read-write
   STATUS     mandatory
   DESCRIPTION
     "This attribute specifies the Cug identifier of a national or 
      international Cug call. It is an arbitrary number and it also can be 
      called Cug in some descriptions. Interfaces (Dna's) defined with 
      this number can make calls to Dna's with the same interlockCode."
   DEFVAL     { 0 }
::= { mscRsaDnaCugCugOptionsEntry 3 }

mscRsaDnaCugPreferential OBJECT-TYPE
   SYNTAX     INTEGER  {
                 no(0),
                 yes(1) }
   ACCESS     read-only
   STATUS     mandatory
   DESCRIPTION
     "This attribute, if set to yes indicates that this Cug is the preferential 
      Cug, in which case it will be used during the call establishment 
      phase if the DTE has not explicitly specified a Cug index in the call 
      request packet. If set to no, then this Cug is not the preferential 
      Cug.
      Only one of the Cugs associated with a particular Dna can be the 
      preferential Cug - only one Cug can have this attribute set to yes."
   DEFVAL     { no }
::= { mscRsaDnaCugCugOptionsEntry 4 }

mscRsaDnaCugOutCalls OBJECT-TYPE
   SYNTAX     INTEGER  {
                 disallowed(0),
                 allowed(1) }
   ACCESS     read-only
   STATUS     mandatory
   DESCRIPTION
     "This attribute, if set to allowed indicates that outgoing calls (from 
      the DTE into the network) can be made using this particular Cug. If 
      set to a value of disallowed, then outgoing calls cannot be made 
      using this Cug - such calls will be cleared by the local DCE.
      This attribute corresponds to the ITU-T 'Outgoing Calls Barred' 
      feature for Cugs in that outgoing calls are barred if this attribute is 
      set to a value of disallowed."
   DEFVAL     { disallowed }
::= { mscRsaDnaCugCugOptionsEntry 5 }

mscRsaDnaCugIncCalls OBJECT-TYPE
   SYNTAX     INTEGER  {
                 disallowed(0),
                 allowed(1) }
   ACCESS     read-only
   STATUS     mandatory
   DESCRIPTION
     "This attribute, if set to allowed indicates that incoming calls (from 
      the network to the DTE) can be made using this particular Cug. If 
      set to disallowed, then incoming calls cannot be made using this 
      Cug - such calls will be cleared by the local DCE.
      This attribute corresponds to the ITU-T 'Incoming Calls Barred' 
      feature for Cugs in that incoming calls are barred if this attribute is 
      set to a value of disallowed."
   DEFVAL     { allowed }
::= { mscRsaDnaCugCugOptionsEntry 6 }

mscRsaDnaCugPrivileged OBJECT-TYPE
   SYNTAX     INTEGER  {
                 no(0),
                 yes(1) }
   ACCESS     read-only
   STATUS     mandatory
   DESCRIPTION
     "This attribute, if set to yes indicates that this Cug is a privileged 
      Cug. In DPN, at least one side of a call setup within a Cug must 
      have the Cug as a privileged Cug. If set to no, then the Cug is not 
      privileged.
      If both the local DTE and the remote DTE subscribe to the Cug, but 
      it is not privileged, then the call will be cleared. This attribute is 
      typically used for a host DTE which must accept calls from many 
      other DTEs in which case the other DTEs cannot call one another, 
      but can call the host. In this example, the host would have the 
      privileged Cug, and the other DTEs would belong to the same Cug, 
      but it would not be privileged."
   DEFVAL     { yes }
::= { mscRsaDnaCugCugOptionsEntry 7 }


-- Rsa/<string> VncsAccess
-- The VncsAccess component provides access to the Passport Voice 
-- Networking Call Server.

mscRsaVncsAccess OBJECT IDENTIFIER ::= { mscRsa 3 }



mscRsaVncsAccessRowStatusTable OBJECT-TYPE
   SYNTAX     SEQUENCE OF MscRsaVncsAccessRowStatusEntry
   ACCESS     not-accessible
   STATUS     mandatory
   DESCRIPTION
     "This entry controls the addition and deletion of 
      mscRsaVncsAccess components."
::= { mscRsaVncsAccess 1 }

mscRsaVncsAccessRowStatusEntry OBJECT-TYPE
   SYNTAX     MscRsaVncsAccessRowStatusEntry
   ACCESS     not-accessible
   STATUS     mandatory
   DESCRIPTION
     "A single entry in the table represents a single 
      mscRsaVncsAccess component."
   INDEX {
      mscRsaIndex,
      mscRsaVncsAccessIndex }
::= { mscRsaVncsAccessRowStatusTable 1 }

MscRsaVncsAccessRowStatusEntry ::= SEQUENCE {
   mscRsaVncsAccessRowStatus
      RowStatus,
   mscRsaVncsAccessComponentName
      DisplayString,
   mscRsaVncsAccessStorageType
      StorageType,
   mscRsaVncsAccessIndex
      NonReplicated }

mscRsaVncsAccessRowStatus OBJECT-TYPE
   SYNTAX     RowStatus 
   ACCESS     read-write
   STATUS     mandatory
   DESCRIPTION
     "This variable is used as the basis for SNMP naming of
      mscRsaVncsAccess components.
      These components can be added and deleted."
::= { mscRsaVncsAccessRowStatusEntry 1 }

mscRsaVncsAccessComponentName OBJECT-TYPE
   SYNTAX     DisplayString 
   ACCESS     read-only
   STATUS     mandatory
   DESCRIPTION
     "This variable provides the component's string name for
      use with the ASCII Console Interface"
::= { mscRsaVncsAccessRowStatusEntry 2 }

mscRsaVncsAccessStorageType OBJECT-TYPE
   SYNTAX     StorageType 
   ACCESS     read-only
   STATUS     mandatory
   DESCRIPTION
     "This variable represents the storage type value for the
      mscRsaVncsAccess tables."
::= { mscRsaVncsAccessRowStatusEntry 4 }

mscRsaVncsAccessIndex OBJECT-TYPE
   SYNTAX     NonReplicated 
   ACCESS     not-accessible
   STATUS     mandatory
   DESCRIPTION
     "This variable represents the index for the mscRsaVncsAccess tables."
::= { mscRsaVncsAccessRowStatusEntry 10 }

mscRsaVncsAccessProvisionedTable OBJECT-TYPE
   SYNTAX     SEQUENCE OF MscRsaVncsAccessProvisionedEntry
   ACCESS     not-accessible
   STATUS     mandatory
   DESCRIPTION
     "The Provisioned group defines provisioned attributes associated 
      with the VncsAccess component."
::= { mscRsaVncsAccess 10 }

mscRsaVncsAccessProvisionedEntry OBJECT-TYPE
   SYNTAX     MscRsaVncsAccessProvisionedEntry
   ACCESS     not-accessible
   STATUS     mandatory
   DESCRIPTION
     "An entry in the mscRsaVncsAccessProvisionedTable."
   INDEX {
      mscRsaIndex,
      mscRsaVncsAccessIndex }
::= { mscRsaVncsAccessProvisionedTable 1 }

MscRsaVncsAccessProvisionedEntry ::= SEQUENCE {
   mscRsaVncsAccessTimeToLive
      INTEGER }

mscRsaVncsAccessTimeToLive OBJECT-TYPE
   SYNTAX     INTEGER (1..5)
   ACCESS     read-write
   STATUS     mandatory
   DESCRIPTION
     "This attribute specifies the length of time VNCS requests are 
      allowed to remain queued for transmission before they are 
      considered too old and are discarded. This attribute should be set in 
      considereation with the voice application timeout interval."
   DEFVAL     { 2 }
::= { mscRsaVncsAccessProvisionedEntry 1 }

mscRsaVncsAccessStateTable OBJECT-TYPE
   SYNTAX     SEQUENCE OF MscRsaVncsAccessStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscRsaVncsAccess 11 }

mscRsaVncsAccessStateEntry OBJECT-TYPE
   SYNTAX     MscRsaVncsAccessStateEntry
   ACCESS     not-accessible
   STATUS     mandatory
   DESCRIPTION
     "An entry in the mscRsaVncsAccessStateTable."
   INDEX {
      mscRsaIndex,
      mscRsaVncsAccessIndex }
::= { mscRsaVncsAccessStateTable 1 }

MscRsaVncsAccessStateEntry ::= SEQUENCE {
   mscRsaVncsAccessAdminState
      INTEGER,
   mscRsaVncsAccessOperationalState
      INTEGER,
   mscRsaVncsAccessUsageState
      INTEGER }

mscRsaVncsAccessAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscRsaVncsAccessStateEntry 1 }

mscRsaVncsAccessOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscRsaVncsAccessStateEntry 2 }

mscRsaVncsAccessUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscRsaVncsAccessStateEntry 3 }

mscRsaVncsAccessOperationalTable OBJECT-TYPE
   SYNTAX     SEQUENCE OF MscRsaVncsAccessOperationalEntry
   ACCESS     not-accessible
   STATUS     mandatory
   DESCRIPTION
     "The Operational group defines operational attributes associated 
      with the VncsAccess component."
::= { mscRsaVncsAccess 12 }

mscRsaVncsAccessOperationalEntry OBJECT-TYPE
   SYNTAX     MscRsaVncsAccessOperationalEntry
   ACCESS     not-accessible
   STATUS     mandatory
   DESCRIPTION
     "An entry in the mscRsaVncsAccessOperationalTable."
   INDEX {
      mscRsaIndex,
      mscRsaVncsAccessIndex }
::= { mscRsaVncsAccessOperationalTable 1 }

MscRsaVncsAccessOperationalEntry ::= SEQUENCE {
   mscRsaVncsAccessRequestsSent
      Counter32,
   mscRsaVncsAccessRepliesReceived
      Counter32,
   mscRsaVncsAccessRequestsQueued
      INTEGER,
   mscRsaVncsAccessRequestsDiscarded
      Counter32 }

mscRsaVncsAccessRequestsSent OBJECT-TYPE
   SYNTAX     Counter32 
   ACCESS     read-only
   STATUS     mandatory
   DESCRIPTION
     "This attribute counts the number of translation requests sent to 
      VNCS. This counter wraps to zero when it reaches its maximum 
      value."
::= { mscRsaVncsAccessOperationalEntry 1 }

mscRsaVncsAccessRepliesReceived OBJECT-TYPE
   SYNTAX     Counter32 
   ACCESS     read-only
   STATUS     mandatory
   DESCRIPTION
     "This attribute counts the number of translation replies received from 
      VNCS. This counter wraps to zero when it reaches its maximum 
      value."
::= { mscRsaVncsAccessOperationalEntry 2 }

mscRsaVncsAccessRequestsQueued OBJECT-TYPE
   SYNTAX     INTEGER (0..65535)
   ACCESS     read-only
   STATUS     mandatory
   DESCRIPTION
     "This attribute indicates the number of translation requests queued 
      for transmission to VNCS."
   DEFVAL     { 0 }
::= { mscRsaVncsAccessOperationalEntry 3 }

mscRsaVncsAccessRequestsDiscarded OBJECT-TYPE
   SYNTAX     Counter32 
   ACCESS     read-only
   STATUS     mandatory
   DESCRIPTION
     "This attribute counts the number of translation requests discarded 
      before being sent to VNCS. Requests are discarded if the queue 
      becomes too large or the VNCS server is unavailable. This counter 
      wraps to zero when it reaches its maximum value."
::= { mscRsaVncsAccessOperationalEntry 4 }

-- 
-- *** THIS SUBTREE CURRENTLY NOT IMPLEMENTED ***
-- 

-- Rsa/<string> Connection/n
-- Rsi Connection/n
-- The Connection component contains information relating to the 
-- connection between the RSA and RSI. This component is named by 
-- the logical channel number of the connection. 

mscRsaConnection OBJECT IDENTIFIER ::= { mscRsa 4 }



mscRsaConnectionRowStatusTable OBJECT-TYPE
   SYNTAX     SEQUENCE OF MscRsaConnectionRowStatusEntry
   ACCESS     not-accessible
   STATUS     mandatory
   DESCRIPTION
     "*** THIS TABLE CURRENTLY NOT IMPLEMENTED ***

      This entry controls the addition and deletion of 
      mscRsaConnection components."
::= { mscRsaConnection 1 }

mscRsaConnectionRowStatusEntry OBJECT-TYPE
   SYNTAX     MscRsaConnectionRowStatusEntry
   ACCESS     not-accessible
   STATUS     mandatory
   DESCRIPTION
     "A single entry in the table represents a single 
      mscRsaConnection component."
   INDEX {
      mscRsaIndex,
      mscRsaConnectionIndex }
::= { mscRsaConnectionRowStatusTable 1 }

MscRsaConnectionRowStatusEntry ::= SEQUENCE {
   mscRsaConnectionRowStatus
      RowStatus,
   mscRsaConnectionComponentName
      DisplayString,
   mscRsaConnectionStorageType
      StorageType,
   mscRsaConnectionIndex
      Integer32 }

mscRsaConnectionRowStatus OBJECT-TYPE
   SYNTAX     RowStatus 
   ACCESS     read-only
   STATUS     mandatory
   DESCRIPTION
     "This variable is used as the basis for SNMP naming of
      mscRsaConnection components.
      These components cannot be added nor deleted."
::= { mscRsaConnectionRowStatusEntry 1 }

mscRsaConnectionComponentName OBJECT-TYPE
   SYNTAX     DisplayString 
   ACCESS     read-only
   STATUS     mandatory
   DESCRIPTION
     "This variable provides the component's string name for
      use with the ASCII Console Interface"
::= { mscRsaConnectionRowStatusEntry 2 }

mscRsaConnectionStorageType OBJECT-TYPE
   SYNTAX     StorageType 
   ACCESS     read-only
   STATUS     mandatory
   DESCRIPTION
     "This variable represents the storage type value for the
      mscRsaConnection tables."
::= { mscRsaConnectionRowStatusEntry 4 }

mscRsaConnectionIndex OBJECT-TYPE
   SYNTAX     Integer32 (1..1000)
   ACCESS     not-accessible
   STATUS     mandatory
   DESCRIPTION
     "This variable represents the index for the mscRsaConnection tables."
::= { mscRsaConnectionRowStatusEntry 10 }

mscRsaConnectionOperationalTable OBJECT-TYPE
   SYNTAX     SEQUENCE OF MscRsaConnectionOperationalEntry
   ACCESS     not-accessible
   STATUS     mandatory
   DESCRIPTION
     "*** THIS TABLE CURRENTLY NOT IMPLEMENTED ***

      The Operational group defines operational attributes associated 
      with the Connection component."
::= { mscRsaConnection 10 }

mscRsaConnectionOperationalEntry OBJECT-TYPE
   SYNTAX     MscRsaConnectionOperationalEntry
   ACCESS     not-accessible
   STATUS     mandatory
   DESCRIPTION
     "An entry in the mscRsaConnectionOperationalTable."
   INDEX {
      mscRsaIndex,
      mscRsaConnectionIndex }
::= { mscRsaConnectionOperationalTable 1 }

MscRsaConnectionOperationalEntry ::= SEQUENCE {
   mscRsaConnectionRemoteName
      AsciiString,
   mscRsaConnectionCallState
      INTEGER }

mscRsaConnectionRemoteName OBJECT-TYPE
   SYNTAX     AsciiString (SIZE (0..32))
   ACCESS     read-only
   STATUS     mandatory
   DESCRIPTION
     "This attribute specifies an ASCII string identifier for the remote 
      module which is retrieved from the call request as user data."
::= { mscRsaConnectionOperationalEntry 1 }

mscRsaConnectionCallState OBJECT-TYPE
   SYNTAX     INTEGER  {
                 initializing(0),
                 creatingVc(1),
                 calling(2),
                 acceptingCall(3),
                 registeringFmo(4),
                 establishingLapf(5),
                 dataTransfer(6),
                 clearingCall(7),
                 terminating(8),
                 terminatingVc(9),
                 terminated(10) }
   ACCESS     read-only
   STATUS     mandatory
   DESCRIPTION
     "This attribute indicates the state of the connection. The normal state 
      for the connection is dataTransfer. The other states are transient 
      states used to setup or clear the connection."
::= { mscRsaConnectionOperationalEntry 2 }

mscRsaConnectionServerStatsTable OBJECT-TYPE
   SYNTAX     SEQUENCE OF MscRsaConnectionServerStatsEntry
   ACCESS     not-accessible
   STATUS     mandatory
   DESCRIPTION
     "*** THIS TABLE CURRENTLY NOT IMPLEMENTED ***

      The ServerStatistics group provides individual server usage 
      statistics for the connection."
::= { mscRsaConnection 11 }

mscRsaConnectionServerStatsEntry OBJECT-TYPE
   SYNTAX     MscRsaConnectionServerStatsEntry
   ACCESS     not-accessible
   STATUS     mandatory
   DESCRIPTION
     "An entry in the mscRsaConnectionServerStatsTable."
   INDEX {
      mscRsaIndex,
      mscRsaConnectionIndex }
::= { mscRsaConnectionServerStatsTable 1 }

MscRsaConnectionServerStatsEntry ::= SEQUENCE {
   mscRsaConnectionVncsRequests
      Counter32,
   mscRsaConnectionVncsReplies
      Counter32 }

mscRsaConnectionVncsRequests OBJECT-TYPE
   SYNTAX     Counter32 
   ACCESS     read-only
   STATUS     mandatory
   DESCRIPTION
     "This attribute counts the number of VNCS translation requests sent 
      or received on this connection."
::= { mscRsaConnectionServerStatsEntry 1 }

mscRsaConnectionVncsReplies OBJECT-TYPE
   SYNTAX     Counter32 
   ACCESS     read-only
   STATUS     mandatory
   DESCRIPTION
     "This attribute counts the number of VNCS translation replies sent or 
      received on this connection."
::= { mscRsaConnectionServerStatsEntry 2 }

mscRsaConnectionLapfStatusTable OBJECT-TYPE
   SYNTAX     SEQUENCE OF MscRsaConnectionLapfStatusEntry
   ACCESS     not-accessible
   STATUS     mandatory
   DESCRIPTION
     "*** THIS TABLE CURRENTLY NOT IMPLEMENTED ***

      This group contains the LAPF status."
::= { mscRsaConnection 12 }

mscRsaConnectionLapfStatusEntry OBJECT-TYPE
   SYNTAX     MscRsaConnectionLapfStatusEntry
   ACCESS     not-accessible
   STATUS     mandatory
   DESCRIPTION
     "An entry in the mscRsaConnectionLapfStatusTable."
   INDEX {
      mscRsaIndex,
      mscRsaConnectionIndex }
::= { mscRsaConnectionLapfStatusTable 1 }

MscRsaConnectionLapfStatusEntry ::= SEQUENCE {
   mscRsaConnectionLapfState
      INTEGER,
   mscRsaConnectionLapfQueueSize
      Counter32 }

mscRsaConnectionLapfState OBJECT-TYPE
   SYNTAX     INTEGER  {
                 disconnected(1),
                 linkSetup(2),
                 disconnectRequest(4),
                 informationTransfer(5),
                 waitingAck(7) }
   ACCESS     read-only
   STATUS     mandatory
   DESCRIPTION
     "This attribute shows the current state of the LAPF interface. The 
      normal states are informationTransfer and waitingAck. Since the 
      LAPF interface is not over a physical link the other states are 
      transitional."
::= { mscRsaConnectionLapfStatusEntry 1 }

mscRsaConnectionLapfQueueSize OBJECT-TYPE
   SYNTAX     Counter32 
   ACCESS     read-only
   STATUS     mandatory
   DESCRIPTION
     "This attribute indicates the number of frames in the LAPF transmit 
      queue."
::= { mscRsaConnectionLapfStatusEntry 4 }

mscRsaConnectionLapfStatsTable OBJECT-TYPE
   SYNTAX     SEQUENCE OF MscRsaConnectionLapfStatsEntry
   ACCESS     not-accessible
   STATUS     mandatory
   DESCRIPTION
     "*** THIS TABLE CURRENTLY NOT IMPLEMENTED ***

      This group contains the LAPF statistics."
::= { mscRsaConnection 13 }

mscRsaConnectionLapfStatsEntry OBJECT-TYPE
   SYNTAX     MscRsaConnectionLapfStatsEntry
   ACCESS     not-accessible
   STATUS     mandatory
   DESCRIPTION
     "An entry in the mscRsaConnectionLapfStatsTable."
   INDEX {
      mscRsaIndex,
      mscRsaConnectionIndex }
::= { mscRsaConnectionLapfStatsTable 1 }

MscRsaConnectionLapfStatsEntry ::= SEQUENCE {
   mscRsaConnectionLapfStateChanges
      Counter32,
   mscRsaConnectionLapfRemoteBusy
      Counter32,
   mscRsaConnectionLapfAckTimeouts
      Counter32,
   mscRsaConnectionLapfRejectFramesRx
      Counter32,
   mscRsaConnectionLapfIFramesTx
      Counter32,
   mscRsaConnectionLapfIFramesTxDiscarded
      Counter32,
   mscRsaConnectionLapfIFramesRx
      Counter32,
   mscRsaConnectionLapfIFramesRxDiscarded
      Counter32 }

mscRsaConnectionLapfStateChanges OBJECT-TYPE
   SYNTAX     Counter32 
   ACCESS     read-only
   STATUS     mandatory
   DESCRIPTION
     "This attribute counts the number of times the LAPF interface has 
      changed state. While the LAPF interface is in informationTransfer 
      state, this counter will increment on each expiry of idleProbeTimer 
      as its state goes from informationTransfer to waitingAck and back. 
      When this count reaches maximum, it wraps to zero."
::= { mscRsaConnectionLapfStatsEntry 1 }

mscRsaConnectionLapfRemoteBusy OBJECT-TYPE
   SYNTAX     Counter32 
   ACCESS     read-only
   STATUS     mandatory
   DESCRIPTION
     "This attribute counts the number of times transmission of an I-frame 
      was unsuccessful due to a perceived remote busy condition 
      (window closed or remote busy). When this count reaches 
      maximum, it wraps to zero."
::= { mscRsaConnectionLapfStatsEntry 2 }

mscRsaConnectionLapfAckTimeouts OBJECT-TYPE
   SYNTAX     Counter32 
   ACCESS     read-only
   STATUS     mandatory
   DESCRIPTION
     "This attribute counts the number of times the ackTimer has expired. 
      Frequent increments of this counter indicate improper values have 
      been chosen for ackTimer and ackDelayTimer between the local 
      and remote ends. When this count reaches maximum, it wraps to 
      zero."
::= { mscRsaConnectionLapfStatsEntry 3 }

mscRsaConnectionLapfRejectFramesRx OBJECT-TYPE
   SYNTAX     Counter32 
   ACCESS     read-only
   STATUS     mandatory
   DESCRIPTION
     "This attribute counts the number of REJ frames received. When this 
      count reaches maximum, it wraps to zero."
::= { mscRsaConnectionLapfStatsEntry 4 }

mscRsaConnectionLapfIFramesTx OBJECT-TYPE
   SYNTAX     Counter32 
   ACCESS     read-only
   STATUS     mandatory
   DESCRIPTION
     "This attribute counts the number of I-frames transmitted. An I-
      frame may be counted more than once if there are retransmissions. 
      When this count reaches maximum, it wraps to zero."
::= { mscRsaConnectionLapfStatsEntry 5 }

mscRsaConnectionLapfIFramesTxDiscarded OBJECT-TYPE
   SYNTAX     Counter32 
   ACCESS     read-only
   STATUS     mandatory
   DESCRIPTION
     "This attribute counts the number of transmit I-frames that have been 
      discarded. Discard reasons may be one of the following:
      1.		The frame length is beyond allowed limit.
      2.		The LAPF interface is in disconnected state.
      3.		The transmit queue has been purged because the queue length
      has reached the reset threshold.
      When this count reaches maximum, it wraps to zero."
::= { mscRsaConnectionLapfStatsEntry 6 }

mscRsaConnectionLapfIFramesRx OBJECT-TYPE
   SYNTAX     Counter32 
   ACCESS     read-only
   STATUS     mandatory
   DESCRIPTION
     "This attribute counts the number of I-frames received. When this 
      count reaches maximum, it wraps to zero."
::= { mscRsaConnectionLapfStatsEntry 7 }

mscRsaConnectionLapfIFramesRxDiscarded OBJECT-TYPE
   SYNTAX     Counter32 
   ACCESS     read-only
   STATUS     mandatory
   DESCRIPTION
     "This attribute counts the number of received I-frames that have been 
      discarded. The discard reasons are:
      1.	Incorrect frame size.
      2.	Frame is out of sequence.
      3.	Frame received while not in informationTransfer or waitingAck 
      state.
      When this count reaches maximum, it wraps to zero."
::= { mscRsaConnectionLapfStatsEntry 8 }

-- 
-- *** THIS SUBTREE CURRENTLY NOT IMPLEMENTED ***
-- 

-- This component defines attributes collected by Frame Relay Vc.

mscRsaConnectionVc OBJECT IDENTIFIER ::= { mscRsaConnection 2 }



mscRsaConnectionVcRowStatusTable OBJECT-TYPE
   SYNTAX     SEQUENCE OF MscRsaConnectionVcRowStatusEntry
   ACCESS     not-accessible
   STATUS     mandatory
   DESCRIPTION
     "*** THIS TABLE CURRENTLY NOT IMPLEMENTED ***

      This entry controls the addition and deletion of 
      mscRsaConnectionVc components."
::= { mscRsaConnectionVc 1 }

mscRsaConnectionVcRowStatusEntry OBJECT-TYPE
   SYNTAX     MscRsaConnectionVcRowStatusEntry
   ACCESS     not-accessible
   STATUS     mandatory
   DESCRIPTION
     "A single entry in the table represents a single 
      mscRsaConnectionVc component."
   INDEX {
      mscRsaIndex,
      mscRsaConnectionIndex,
      mscRsaConnectionVcIndex }
::= { mscRsaConnectionVcRowStatusTable 1 }

MscRsaConnectionVcRowStatusEntry ::= SEQUENCE {
   mscRsaConnectionVcRowStatus
      RowStatus,
   mscRsaConnectionVcComponentName
      DisplayString,
   mscRsaConnectionVcStorageType
      StorageType,
   mscRsaConnectionVcIndex
      NonReplicated }

mscRsaConnectionVcRowStatus OBJECT-TYPE
   SYNTAX     RowStatus 
   ACCESS     read-only
   STATUS     mandatory
   DESCRIPTION
     "This variable is used as the basis for SNMP naming of
      mscRsaConnectionVc components.
      These components cannot be added nor deleted."
::= { mscRsaConnectionVcRowStatusEntry 1 }

mscRsaConnectionVcComponentName OBJECT-TYPE
   SYNTAX     DisplayString 
   ACCESS     read-only
   STATUS     mandatory
   DESCRIPTION
     "This variable provides the component's string name for
      use with the ASCII Console Interface"
::= { mscRsaConnectionVcRowStatusEntry 2 }

mscRsaConnectionVcStorageType OBJECT-TYPE
   SYNTAX     StorageType 
   ACCESS     read-only
   STATUS     mandatory
   DESCRIPTION
     "This variable represents the storage type value for the
      mscRsaConnectionVc tables."
::= { mscRsaConnectionVcRowStatusEntry 4 }

mscRsaConnectionVcIndex OBJECT-TYPE
   SYNTAX     NonReplicated 
   ACCESS     not-accessible
   STATUS     mandatory
   DESCRIPTION
     "This variable represents the index for the mscRsaConnectionVc tables."
::= { mscRsaConnectionVcRowStatusEntry 10 }

mscRsaConnectionVcCadTable OBJECT-TYPE
   SYNTAX     SEQUENCE OF MscRsaConnectionVcCadEntry
   ACCESS     not-accessible
   STATUS     mandatory
   DESCRIPTION
     "*** THIS TABLE CURRENTLY NOT IMPLEMENTED ***

      This group represents operational call data related to Frame Relay 
      Vc. It can be displayed only for Frame Relay Vc which is created by 
      application."
::= { mscRsaConnectionVc 10 }

mscRsaConnectionVcCadEntry OBJECT-TYPE
   SYNTAX     MscRsaConnectionVcCadEntry
   ACCESS     not-accessible
   STATUS     mandatory
   DESCRIPTION
     "An entry in the mscRsaConnectionVcCadTable."
   INDEX {
      mscRsaIndex,
      mscRsaConnectionIndex,
      mscRsaConnectionVcIndex }
::= { mscRsaConnectionVcCadTable 1 }

MscRsaConnectionVcCadEntry ::= SEQUENCE {
   mscRsaConnectionVcType
      INTEGER,
   mscRsaConnectionVcState
      INTEGER,
   mscRsaConnectionVcPreviousState
      INTEGER,
   mscRsaConnectionVcDiagnosticCode
      Unsigned32,
   mscRsaConnectionVcPreviousDiagnosticCode
      Unsigned32,
   mscRsaConnectionVcCalledNpi
      INTEGER,
   mscRsaConnectionVcCalledDna
      DigitString,
   mscRsaConnectionVcCalledLcn
      Unsigned32,
   mscRsaConnectionVcCallingNpi
      INTEGER,
   mscRsaConnectionVcCallingDna
      DigitString,
   mscRsaConnectionVcCallingLcn
      Unsigned32,
   mscRsaConnectionVcAccountingEnabled
      INTEGER,
   mscRsaConnectionVcFastSelectCall
      INTEGER,
   mscRsaConnectionVcPathReliability
      INTEGER,
   mscRsaConnectionVcAccountingEnd
      INTEGER,
   mscRsaConnectionVcPriority
      INTEGER,
   mscRsaConnectionVcSegmentSize
      Unsigned32,
   mscRsaConnectionVcMaxSubnetPktSize
      Unsigned32,
   mscRsaConnectionVcRcosToNetwork
      INTEGER,
   mscRsaConnectionVcRcosFromNetwork
      INTEGER,
   mscRsaConnectionVcEmissionPriorityToNetwork
      INTEGER,
   mscRsaConnectionVcEmissionPriorityFromNetwork
      INTEGER,
   mscRsaConnectionVcDataPath
      AsciiString }

mscRsaConnectionVcType OBJECT-TYPE
   SYNTAX     INTEGER  {
                 svc(0),
                 pvc(1),
                 spvc(2),
                 frf10spvc(3) }
   ACCESS     read-only
   STATUS     mandatory
   DESCRIPTION
     "This attribute displays the type of call, pvc,svc,spvc or frf10spvc."
::= { mscRsaConnectionVcCadEntry 1 }

mscRsaConnectionVcState OBJECT-TYPE
   SYNTAX     INTEGER  {
                 creating(0),
                 readyP1(1),
                 dteWaitingP2(2),
                 dceWaitingP3(3),
                 dataTransferP4(4),
                 unsupportedP5(5),
                 dteClearRequestP6(6),
                 dceClearIndicationP7(7),
                 termination(8) }
   ACCESS     read-only
   STATUS     mandatory
   DESCRIPTION
     "This attribute displays the state of call control. P5 state is not 
      supported but is listed for completness. Transitions from one state to 
      another take very short time. state most often displayed is 
      dataTransferP4."
::= { mscRsaConnectionVcCadEntry 2 }

mscRsaConnectionVcPreviousState OBJECT-TYPE
   SYNTAX     INTEGER  {
                 creating(0),
                 readyP1(1),
                 dteWaitingP2(2),
                 dceWaitingP3(3),
                 dataTransferP4(4),
                 unsupportedP5(5),
                 dteClearRequestP6(6),
                 dceClearIndicationP7(7),
                 termination(8) }
   ACCESS     read-only
   STATUS     mandatory
   DESCRIPTION
     "This attribute displays the previous state of call control. This is a 
      valuable field to determine how the processing is progressing."
::= { mscRsaConnectionVcCadEntry 3 }

mscRsaConnectionVcDiagnosticCode OBJECT-TYPE
   SYNTAX     Unsigned32 (0..255)
   ACCESS     read-only
   STATUS     mandatory
   DESCRIPTION
     "This attribute displays the internal substate of call control. It is used 
      to further refine state of call processing."
::= { mscRsaConnectionVcCadEntry 4 }

mscRsaConnectionVcPreviousDiagnosticCode OBJECT-TYPE
   SYNTAX     Unsigned32 (0..255)
   ACCESS     read-only
   STATUS     mandatory
   DESCRIPTION
     "This attribute displays the internal substate of call control. It is used 
      to further refine state of call processing."
::= { mscRsaConnectionVcCadEntry 5 }

mscRsaConnectionVcCalledNpi OBJECT-TYPE
   SYNTAX     INTEGER  {
                 x121(0),
                 e164(1) }
   ACCESS     read-only
   STATUS     mandatory
   DESCRIPTION
     "This attribute displays the Numbering Plan Indicator (NPI) of the 
      called end."
::= { mscRsaConnectionVcCadEntry 6 }

mscRsaConnectionVcCalledDna OBJECT-TYPE
   SYNTAX     DigitString (SIZE (1..15))
   ACCESS     read-only
   STATUS     mandatory
   DESCRIPTION
     "This attribute displays the Data Network Address (Dna) of the 
      called (destination) DTE to which this call is sent. This address if 
      defined at recieving end will complete Vc connection."
::= { mscRsaConnectionVcCadEntry 7 }

mscRsaConnectionVcCalledLcn OBJECT-TYPE
   SYNTAX     Unsigned32 (1..65535)
   ACCESS     read-only
   STATUS     mandatory
   DESCRIPTION
     "This attribute displays the Logical Channel Number of the called 
      end. It is valid only after both ends of Vc exchanged relevant 
      information."
::= { mscRsaConnectionVcCadEntry 8 }

mscRsaConnectionVcCallingNpi OBJECT-TYPE
   SYNTAX     INTEGER  {
                 x121(0),
                 e164(1) }
   ACCESS     read-only
   STATUS     mandatory
   DESCRIPTION
     "This attribute displays the Numbering Plan Indicator (NPI) of the 
      calling end."
::= { mscRsaConnectionVcCadEntry 9 }

mscRsaConnectionVcCallingDna OBJECT-TYPE
   SYNTAX     DigitString (SIZE (1..15))
   ACCESS     read-only
   STATUS     mandatory
   DESCRIPTION
     "This attribute displays the Data Network Address (Dna) of the 
      calling end."
::= { mscRsaConnectionVcCadEntry 10 }

mscRsaConnectionVcCallingLcn OBJECT-TYPE
   SYNTAX     Unsigned32 (1..65535)
   ACCESS     read-only
   STATUS     mandatory
   DESCRIPTION
     "This attribute displays the Logical Channel Number of the calling 
      end."
::= { mscRsaConnectionVcCadEntry 11 }

mscRsaConnectionVcAccountingEnabled OBJECT-TYPE
   SYNTAX     INTEGER  {
                 yes(0),
                 no(1) }
   ACCESS     read-only
   STATUS     mandatory
   DESCRIPTION
     "This attribute indicates that this optional section of accounting 
      record is suppressed or permitted. If accountingEnabled is yes, 
      conditions for generation of accounting record were met. These 
      conditions include billing options, vc recovery conditions and 
      Module wide accounting data options."
::= { mscRsaConnectionVcCadEntry 12 }

mscRsaConnectionVcFastSelectCall OBJECT-TYPE
   SYNTAX     INTEGER  {
                 no(0),
                 yes(1) }
   ACCESS     read-only
   STATUS     mandatory
   DESCRIPTION
     "This attribute displays that this is a fast select call."
::= { mscRsaConnectionVcCadEntry 13 }

mscRsaConnectionVcPathReliability OBJECT-TYPE
   SYNTAX     INTEGER  {
                 high(0),
                 normal(1) }
   ACCESS     read-only
   STATUS     mandatory
   DESCRIPTION
     "This attribute displays the path reliability."
::= { mscRsaConnectionVcCadEntry 19 }

mscRsaConnectionVcAccountingEnd OBJECT-TYPE
   SYNTAX     INTEGER  {
                 callingEnd(0),
                 calledEnd(1) }
   ACCESS     read-only
   STATUS     mandatory
   DESCRIPTION
     "This attribute indicates if this end should generate an accounting 
      record. Normally, callingEnd is the end to generate an accounting 
      record."
::= { mscRsaConnectionVcCadEntry 20 }

mscRsaConnectionVcPriority OBJECT-TYPE
   SYNTAX     INTEGER  {
                 normal(0),
                 high(1) }
   ACCESS     read-only
   STATUS     mandatory
   DESCRIPTION
     "This attribute displays whether the call is a normal or a high 
      priority call."
::= { mscRsaConnectionVcCadEntry 21 }

mscRsaConnectionVcSegmentSize OBJECT-TYPE
   SYNTAX     Unsigned32 (0..4096)
   ACCESS     read-only
   STATUS     mandatory
   DESCRIPTION
     "This attribute displays the segment size (in bytes) used on the call. 
      It is used to calculate the number of segments transmitted and 
      received."
::= { mscRsaConnectionVcCadEntry 22 }

mscRsaConnectionVcMaxSubnetPktSize OBJECT-TYPE
   SYNTAX     Unsigned32 (0..4096)
   ACCESS     read-only
   STATUS     mandatory
   DESCRIPTION
     "This attribute indicates the maximum packet size allowed on the Vc."
::= { mscRsaConnectionVcCadEntry 27 }

mscRsaConnectionVcRcosToNetwork OBJECT-TYPE
   SYNTAX     INTEGER  {
                 throughput(0),
                 delay(1),
                 multimedia(2) }
   ACCESS     read-only
   STATUS     mandatory
   DESCRIPTION
     "This attribute indicates the routing metric routing class of service to
      the network."
::= { mscRsaConnectionVcCadEntry 28 }

mscRsaConnectionVcRcosFromNetwork OBJECT-TYPE
   SYNTAX     INTEGER  {
                 throughput(0),
                 delay(1),
                 multimedia(2) }
   ACCESS     read-only
   STATUS     mandatory
   DESCRIPTION
     "This attribute displays the routing metric Routing Class of Service 
      from the Network."
::= { mscRsaConnectionVcCadEntry 29 }

mscRsaConnectionVcEmissionPriorityToNetwork OBJECT-TYPE
   SYNTAX     INTEGER  {
                 normal(0),
                 high(1),
                 interrupting(2) }
   ACCESS     read-only
   STATUS     mandatory
   DESCRIPTION
     "This attribute displays the network internal emission priotity to the 
      network."
::= { mscRsaConnectionVcCadEntry 30 }

mscRsaConnectionVcEmissionPriorityFromNetwork OBJECT-TYPE
   SYNTAX     INTEGER  {
                 normal(0),
                 high(1),
                 interrupting(2) }
   ACCESS     read-only
   STATUS     mandatory
   DESCRIPTION
     "This attribute displays the network internal emission priotity from 
      the network."
::= { mscRsaConnectionVcCadEntry 31 }

mscRsaConnectionVcDataPath OBJECT-TYPE
   SYNTAX     AsciiString (SIZE (0..32))
   ACCESS     read-only
   STATUS     mandatory
   DESCRIPTION
     "This attribute indicates the data path used by the connection. The 
      data path is provisioned in Dna and DirectCall components. The 
      displayed value of this attribute can be different from the 
      provisioned value.
      
      If the connection is using dprsOnly data path, the string 
      dprsOnly is displayed. (dynamic packet routing system)
      
      If the connection is using dprsMcsOnly data path, the string 
      dprsMcsOnly is displayed.
      
      If the connection is using dprsMcsFirst data path, the string 
      dprsMcsFirst is displayed."
::= { mscRsaConnectionVcCadEntry 32 }

mscRsaConnectionVcIntdTable OBJECT-TYPE
   SYNTAX     SEQUENCE OF MscRsaConnectionVcIntdEntry
   ACCESS     not-accessible
   STATUS     mandatory
   DESCRIPTION
     "*** THIS TABLE CURRENTLY NOT IMPLEMENTED ***

      This group defines display of interval data collected by Vc. Data in 
      this group is variable and may depend on time when this display 
      command is issued."
::= { mscRsaConnectionVc 11 }

mscRsaConnectionVcIntdEntry OBJECT-TYPE
   SYNTAX     MscRsaConnectionVcIntdEntry
   ACCESS     not-accessible
   STATUS     mandatory
   DESCRIPTION
     "An entry in the mscRsaConnectionVcIntdTable."
   INDEX {
      mscRsaIndex,
      mscRsaConnectionIndex,
      mscRsaConnectionVcIndex }
::= { mscRsaConnectionVcIntdTable 1 }

MscRsaConnectionVcIntdEntry ::= SEQUENCE {
   mscRsaConnectionVcCallReferenceNumber
      Hex,
   mscRsaConnectionVcElapsedTimeTillNow
      Unsigned32,
   mscRsaConnectionVcSegmentsRx
      Unsigned32,
   mscRsaConnectionVcSegmentsSent
      Unsigned32,
   mscRsaConnectionVcStartTime
      EnterpriseDateAndTime,
   mscRsaConnectionVcCallReferenceNumberDecimal
      Unsigned32 }

mscRsaConnectionVcCallReferenceNumber OBJECT-TYPE
   SYNTAX     Hex (0..16777215)
   ACCESS     read-only
   STATUS     obsolete
   DESCRIPTION
     "This attribute is obsolete. It is replaced by the callReferenceNumber 
      attribute to display the call reference number in decimal. The 
      SNMP reference for the callReferenceNumber attribute is 
      callReferenceNumberDecimal."
::= { mscRsaConnectionVcIntdEntry 1 }

mscRsaConnectionVcElapsedTimeTillNow OBJECT-TYPE
   SYNTAX     Unsigned32 (0..16777215)
   ACCESS     read-only
   STATUS     mandatory
   DESCRIPTION
     "This attribute displays the elapsed time representing the period of 
      this interval data. It is elapsed time in 0.1 second increments since 
      Vc started."
::= { mscRsaConnectionVcIntdEntry 2 }

mscRsaConnectionVcSegmentsRx OBJECT-TYPE
   SYNTAX     Unsigned32 (0..16777215)
   ACCESS     read-only
   STATUS     mandatory
   DESCRIPTION
     "This attribute displays the number of segments received at the time 
      command was issued. This is the segment received count 
      maintained by accounting at each end of the Vc. This counter is 
      updated only when the packet cannot be successfully delivered out 
      of the sink Vc and to the sink AP Conditions in which packets may 
      be discarded by the sink Vc include: missing packets due to subnet 
      discards, segmentation protocol violations due to subnet discard, 
      duplicated and out-of-ranged packets and packets that arrive while 
      Vc is in path recovery state."
::= { mscRsaConnectionVcIntdEntry 3 }

mscRsaConnectionVcSegmentsSent OBJECT-TYPE
   SYNTAX     Unsigned32 (0..16777215)
   ACCESS     read-only
   STATUS     mandatory
   DESCRIPTION
     "This attribute displays the number of segments sent at the time 
      command was issued. This is the segment sent count maintained by 
      accounting at the source Vc. Vc only counts packets that Vc thinks 
      can be delivered successfully into the subnet. In reality, these 
      packets may be dropped by trunking, for instance. This counter is 
      not updated when splitting fails, when Vc is in a path recovery state, 
      when packet forwarding fails to forward this packet and when 
      subsequent packets have to be discarded as we want to minimize the 
      chance of out-of-sequence and do not intentionally send out-of-
      sequenced packets into the subnet."
::= { mscRsaConnectionVcIntdEntry 4 }

mscRsaConnectionVcStartTime OBJECT-TYPE
   SYNTAX     EnterpriseDateAndTime (SIZE (0 | 19))
   ACCESS     read-only
   STATUS     mandatory
   DESCRIPTION
     "This attribute displays the start time of this interval period. If Vc 
      spans 12 hour time or time of day change startTime reflects new 
      time as recorded at 12 hour periods or time of day changes."
::= { mscRsaConnectionVcIntdEntry 5 }

mscRsaConnectionVcCallReferenceNumberDecimal OBJECT-TYPE
   SYNTAX     Unsigned32 (0..4294967295)
   ACCESS     read-only
   STATUS     mandatory
   DESCRIPTION
     "This attribute displays the call reference number which is a unique 
      number generated by the switch.The same Call Reference Number 
      is stored in the interval data (accounting record) at both ends of the 
      call. It can be used as one of the attributes in matching duplicate 
      records generated at each end of the call."
::= { mscRsaConnectionVcIntdEntry 7 }

mscRsaConnectionVcFrdTable OBJECT-TYPE
   SYNTAX     SEQUENCE OF MscRsaConnectionVcFrdEntry
   ACCESS     not-accessible
   STATUS     mandatory
   DESCRIPTION
     "*** THIS TABLE CURRENTLY NOT IMPLEMENTED ***

      This group defines Frame Relay attributes collected by Frame Relay 
      Vc.
      The purpose of Vc attributes is to aid end users and verification 
      people to understand the Vc internal behavior. This is particularly 
      useful when the network has experienced abnormality and we want 
      to isolate problems and pinpoint trouble spots. 
      Attributes are collected on a per Vc basis. Until a need is identified, 
      statistics are not collected at a processor level. Each attribute is 
      stored in a 32 bit field and is initialized to zero when a Vc enters 
      into the data transfer state. When a PVC is disconnected and then 
      connected again, the attributes will be reset. Attributes cannot be 
      reset through other methods. 
      Frame Relay Vc uses a best effort data packet delivery protocol and 
      a different packet segmentation and combination methods from the 
      General Vc. The Frame Relay Vc uses the same call setup and 
      control mechanism (e.g. the support of non-flow control data 
      packets) as in a General Vc. Most General Vc statistics and internal 
      variables are used in a Frame Relay Vc and are displayed by 
      software developers"
::= { mscRsaConnectionVc 12 }

mscRsaConnectionVcFrdEntry OBJECT-TYPE
   SYNTAX     MscRsaConnectionVcFrdEntry
   ACCESS     not-accessible
   STATUS     mandatory
   DESCRIPTION
     "An entry in the mscRsaConnectionVcFrdTable."
   INDEX {
      mscRsaIndex,
      mscRsaConnectionIndex,
      mscRsaConnectionVcIndex }
::= { mscRsaConnectionVcFrdTable 1 }

MscRsaConnectionVcFrdEntry ::= SEQUENCE {
   mscRsaConnectionVcFrmCongestedToSubnet
      Unsigned32,
   mscRsaConnectionVcCannotForwardToSubnet
      Unsigned32,
   mscRsaConnectionVcNotDataXferToSubnet
      Unsigned32,
   mscRsaConnectionVcOutOfRangeFrmFromSubnet
      Unsigned32,
   mscRsaConnectionVcCombErrorsFromSubnet
      Unsigned32,
   mscRsaConnectionVcDuplicatesFromSubnet
      Unsigned32,
   mscRsaConnectionVcNotDataXferFromSubnet
      Unsigned32,
   mscRsaConnectionVcFrmLossTimeouts
      Unsigned32,
   mscRsaConnectionVcOoSeqByteCntExceeded
      Unsigned32,
   mscRsaConnectionVcPeakOoSeqPktCount
      Unsigned32,
   mscRsaConnectionVcPeakOoSeqFrmForwarded
      Unsigned32,
   mscRsaConnectionVcSendSequenceNumber
      Unsigned32,
   mscRsaConnectionVcPktRetryTimeouts
      Unsigned32,
   mscRsaConnectionVcPeakRetryQueueSize
      Unsigned32,
   mscRsaConnectionVcSubnetRecoveries
      Unsigned32,
   mscRsaConnectionVcOoSeqPktCntExceeded
      Unsigned32,
   mscRsaConnectionVcPeakOoSeqByteCount
      Unsigned32 }

mscRsaConnectionVcFrmCongestedToSubnet OBJECT-TYPE
   SYNTAX     Unsigned32 (0..5000)
   ACCESS     read-only
   STATUS     mandatory
   DESCRIPTION
     "This attribute displays the number of frames from link discarded 
      due to lack of resources. It keeps track of the number of frames 
      from link that have to be discarded. The discard reasons include 
      insufficient memory for splitting the frame into smaller subnet 
      packet size."
::= { mscRsaConnectionVcFrdEntry 2 }

mscRsaConnectionVcCannotForwardToSubnet OBJECT-TYPE
   SYNTAX     Unsigned32 (0..5000)
   ACCESS     read-only
   STATUS     mandatory
   DESCRIPTION
     "This attribute displays the number of discarded packets that can not 
      be forwarded into the subnet because of subnet congestion.
      Number of frames from link discarded due to failure in forwarding 
      a packet from Vc into the subnet.- This attribute is increased when 
      packet forwarding fails to forward a packet into the subnet. If a 
      frame is split into multiple subnet packets and a partial packet has 
      to be discarded, all subsequent partial packets that have not yet been 
      delivered to the subnet will be discarded as well."
::= { mscRsaConnectionVcFrdEntry 3 }

mscRsaConnectionVcNotDataXferToSubnet OBJECT-TYPE
   SYNTAX     Unsigned32 (0..5000)
   ACCESS     read-only
   STATUS     mandatory
   DESCRIPTION
     "This attribute records the number of frames from link discarded 
      when the Vc tries to recover from internal path failure."
::= { mscRsaConnectionVcFrdEntry 4 }

mscRsaConnectionVcOutOfRangeFrmFromSubnet OBJECT-TYPE
   SYNTAX     Unsigned32 (0..5000)
   ACCESS     read-only
   STATUS     mandatory
   DESCRIPTION
     "This attribute displays the number of frames from subnet discarded 
      due to out of sequence range for arriving too late."
::= { mscRsaConnectionVcFrdEntry 5 }

mscRsaConnectionVcCombErrorsFromSubnet OBJECT-TYPE
   SYNTAX     Unsigned32 (0..5000)
   ACCESS     read-only
   STATUS     mandatory
   DESCRIPTION
     "This attribute records the number of subnet packets discarded at the 
      sink Vc due to the Vc segmentation and combination protocol error. 
      Usually, this occurs when the subnet discards packets and thus this 
      statistics can be used to guest the number of subnet packets that are 
      not delivered to the Vc. It cannot be used as an actual measure 
      because some subnet packets may have been delivered to Vc but 
      have to be discarded because these are partial packets to a frame in 
      which some other partial packets have not been properly delivered 
      to Vc"
::= { mscRsaConnectionVcFrdEntry 6 }

mscRsaConnectionVcDuplicatesFromSubnet OBJECT-TYPE
   SYNTAX     Unsigned32 (0..5000)
   ACCESS     read-only
   STATUS     mandatory
   DESCRIPTION
     "This attribute displays the number of subnet packets discarded due 
      to duplication. Although packets are not retransmitted by the Frame 
      Relay Vc, it is possible for the subnet to retransmit packets. When 
      packets are out-of-sequenced and copies of the same packets arrive, 
      then this attribute is increased."
::= { mscRsaConnectionVcFrdEntry 7 }

mscRsaConnectionVcNotDataXferFromSubnet OBJECT-TYPE
   SYNTAX     Unsigned32 (0..5000)
   ACCESS     read-only
   STATUS     mandatory
   DESCRIPTION
     "This attribute displays the number of subnet packets discarded when 
      data transfer is suspended in Vc recovery."
::= { mscRsaConnectionVcFrdEntry 8 }

mscRsaConnectionVcFrmLossTimeouts OBJECT-TYPE
   SYNTAX     Unsigned32 (0..5000)
   ACCESS     read-only
   STATUS     mandatory
   DESCRIPTION
     "This attribute displays the number of lost frame timer expiries.
      When this count is excessive, the network is very congested and 
      packets have been discarded in the subnet."
::= { mscRsaConnectionVcFrdEntry 9 }

mscRsaConnectionVcOoSeqByteCntExceeded OBJECT-TYPE
   SYNTAX     Unsigned32 (0..5000)
   ACCESS     read-only
   STATUS     mandatory
   DESCRIPTION
     "This attribute displays the number times that the out of sequence 
      byte threshold is exceeded. When the threshold is exceeded, this 
      condition is treated as if the loss frame timer has expired and all 
      frames queued at the sink Vc are delivered to the AP. We need to 
      keep this count to examine if the threshold is engineered properly. 
      This should be used in conjunction with the peak value of out-of-
      sequenced queue and the number of times the loss frame timer has 
      expired. This count should be relatively small when compared with 
      loss frame timer expiry count."
::= { mscRsaConnectionVcFrdEntry 10 }

mscRsaConnectionVcPeakOoSeqPktCount OBJECT-TYPE
   SYNTAX     Unsigned32 (0..5000)
   ACCESS     read-only
   STATUS     mandatory
   DESCRIPTION
     "This attribute displays the frame relay peak packet count of the out 
      of sequence queue. This attribute records the maximum queue 
      length of the out-of-sequenced queue. The counter can be used to 
      deduce the message buffer requirement on a Vc."
::= { mscRsaConnectionVcFrdEntry 11 }

mscRsaConnectionVcPeakOoSeqFrmForwarded OBJECT-TYPE
   SYNTAX     Unsigned32 (0..5000)
   ACCESS     read-only
   STATUS     mandatory
   DESCRIPTION
     "This attribute displays the frame relay peak size of the 
      sequence packet queue. The subnet may deliver packets out-of-
      sequenced. These packets are then queued in an out-of-sequenced 
      queue, waiting for a packet with the expected sequence number to 
      come. When that packet arrives, this attribute records the maximum 
      number of packets that were out-of-sequenced, but now have 
      become in-sequenced. The statistics is used to measure expected 
      queue size due to normal subnet packet disorder (not due to subnet 
      packet discard). Current implementation also uses this statistics to 
      set a maximum size for the out-of-sequenced queue."
::= { mscRsaConnectionVcFrdEntry 12 }

mscRsaConnectionVcSendSequenceNumber OBJECT-TYPE
   SYNTAX     Unsigned32 (0..5000)
   ACCESS     read-only
   STATUS     mandatory
   DESCRIPTION
     "This attribute displays the Vc internal packet's send sequence 
      number. Note that a 'packet' in this context, may be either a user 
      data packet, or an OAM frame."
::= { mscRsaConnectionVcFrdEntry 13 }

mscRsaConnectionVcPktRetryTimeouts OBJECT-TYPE
   SYNTAX     Unsigned32 (0..5000)
   ACCESS     read-only
   STATUS     mandatory
   DESCRIPTION
     "This attribute displays the number of packets which have 
      retransmission time-outs. When this count is excessive, the network 
      is very congested and packets have been discarded in the subnet."
::= { mscRsaConnectionVcFrdEntry 15 }

mscRsaConnectionVcPeakRetryQueueSize OBJECT-TYPE
   SYNTAX     Unsigned32 (0..5000)
   ACCESS     read-only
   STATUS     mandatory
   DESCRIPTION
     "This attribute displays the peak size of retransmission queue.
      This attribute is used as an indicator of the acknowledgment 
      behavior across the subnet. Records the largest body of 
      unacknowledged packets."
::= { mscRsaConnectionVcFrdEntry 16 }

mscRsaConnectionVcSubnetRecoveries OBJECT-TYPE
   SYNTAX     Unsigned32 (0..5000)
   ACCESS     read-only
   STATUS     mandatory
   DESCRIPTION
     "This attribute displays the number of successful Vc recovery 
      attempts."
::= { mscRsaConnectionVcFrdEntry 17 }

mscRsaConnectionVcOoSeqPktCntExceeded OBJECT-TYPE
   SYNTAX     Unsigned32 (0..255)
   ACCESS     read-only
   STATUS     mandatory
   DESCRIPTION
     "This attribute displays the number times that the out of sequence 
      packet threshold is exceeded. When the threshold is exceeded, this 
      condition is treated as if the loss frame timer has expired and all 
      frames queued at the sink Vc are delivered to the AP. We need to 
      keep this count to examine if the threshold is engineered properly. 
      This should be used in conjunction with the peak value of out-of-
      sequenced queue and the number of times the loss frame timer has 
      expired. This count should be relatively small when compared with 
      loss frame timer expiry count."
::= { mscRsaConnectionVcFrdEntry 19 }

mscRsaConnectionVcPeakOoSeqByteCount OBJECT-TYPE
   SYNTAX     Unsigned32 (0..50000)
   ACCESS     read-only
   STATUS     mandatory
   DESCRIPTION
     "This attribute displays the frame relay peak byte count of the out of 
      sequence queue. This attribute records the maximum queue length 
      of the out-of-sequenced queue. The counter can be used to deduce 
      the message buffer requirement on a Vc."
::= { mscRsaConnectionVcFrdEntry 20 }

mscRsaConnectionVcDmepTable OBJECT-TYPE
   SYNTAX     SEQUENCE OF MscRsaConnectionVcDmepEntry
   ACCESS     not-accessible
   STATUS     mandatory
   DESCRIPTION
     "*** THIS TABLE CURRENTLY NOT IMPLEMENTED ***

      This attribute displays the data path used by the connection. Data 
      path is provisioned in Dna and DirectCall components.
      
      If the connection is using dprsOnly data path, this attribute is 
      empty.
      
      If the connection is using dprsMcsOnly or dprsMcsFirst data path, 
      this attribute displays component name of the dprsMcsEndPoint."
::= { mscRsaConnectionVc 417 }

mscRsaConnectionVcDmepEntry OBJECT-TYPE
   SYNTAX     MscRsaConnectionVcDmepEntry
   ACCESS     not-accessible
   STATUS     mandatory
   DESCRIPTION
     "An entry in the mscRsaConnectionVcDmepTable."
   INDEX {
      mscRsaIndex,
      mscRsaConnectionIndex,
      mscRsaConnectionVcIndex,
      mscRsaConnectionVcDmepValue }
::= { mscRsaConnectionVcDmepTable 1 }

MscRsaConnectionVcDmepEntry ::= SEQUENCE {
   mscRsaConnectionVcDmepValue
      RowPointer }

mscRsaConnectionVcDmepValue OBJECT-TYPE
   SYNTAX     RowPointer 
   ACCESS     read-only
   STATUS     mandatory
   DESCRIPTION
     "This variable represents both the value and the index for the
      mscRsaConnectionVcDmepTable."
::= { mscRsaConnectionVcDmepEntry 1 }




-- 
-- Version and Compliance statements
-- 



-- Object-Group Statement:
-- A list of all current accessible leaf objects.

-- OBJECTS { mscRsaConnectionVcCannotForwardToSubnet,
--           mscRsaDnaIncCalls,
--           mscRsaConnectionVcCalledDna,
--           mscRsaConnectionVcType,
--           mscRsaDnaIncAccess,
--           mscRsaConnectionVcSegmentsSent,
--           mscRsaVncsAccessRequestsSent,
--           mscRsaConnectionVcPreviousState,
--           mscRsaConnectionVcSubnetRecoveries,
--           mscRsaConnectionVcOoSeqPktCntExceeded,
--           mscRsaConnectionVcPeakRetryQueueSize,
--           mscRsaDnaRowStatus,
--           mscRsaConnectionLapfState,
--           mscRsaVncsAccessStorageType,
--           mscRsaVncsAccessRequestsQueued,
--           mscRsaConnectionVcSegmentSize,
--           mscRsaDnaCugComponentName,
--           mscRsaConnectionVcEmissionPriorityFromNetwork,
--           mscRsaConnectionCallState,
--           mscRsaConnectionVcFastSelectCall,
--           mscRsaDnaCugInterlockCode,
--           mscRsaConnectionVcComponentName,
--           mscRsaDnaNumberingPlanIndicator,
--           mscRsaVncsAccessAdminState,
--           mscRsaLogicalProcessor,
--           mscRsaConnectionVcMaxSubnetPktSize,
--           mscRsaDnaCugOutCalls,
--           mscRsaVncsAccessRowStatus,
--           mscRsaConnectionLapfAckTimeouts,
--           mscRsaConnectionVcPriority,
--           mscRsaConnectionVcPathReliability,
--           mscRsaConnectionVcSendSequenceNumber,
--           mscRsaConnectionVcOoSeqByteCntExceeded,
--           mscRsaDnaCugPreferential,
--           mscRsaConnectionLapfStateChanges,
--           mscRsaConnectionVcCallingNpi,
--           mscRsaConnectionVcState,
--           mscRsaComponentName,
--           mscRsaVncsAccessUsageState,
--           mscRsaConnectionLapfIFramesTx,
--           mscRsaVncsAccessOperationalState,
--           mscRsaMaxRsiConnections,
--           mscRsaConnectionVcEmissionPriorityToNetwork,
--           mscRsaDnaCugStorageType,
--           mscRsaConnectionVcPeakOoSeqByteCount,
--           mscRsaConnectionLapfQueueSize,
--           mscRsaDnaCugPrivileged,
--           mscRsaRsiConnections,
--           mscRsaDnaCugIncCalls,
--           mscRsaConnectionVcStorageType,
--           mscRsaConnectionLapfIFramesRxDiscarded,
--           mscRsaConnectionVcFrmLossTimeouts,
--           mscRsaConnectionVncsReplies,
--           mscRsaVncsAccessRepliesReceived,
--           mscRsaVncsAccessTimeToLive,
--           mscRsaConnectionVcAccountingEnd,
--           mscRsaConnectionVcCalledNpi,
--           mscRsaConnectionVcElapsedTimeTillNow,
--           mscRsaConnectionComponentName,
--           mscRsaConnectionVcPeakOoSeqPktCount,
--           mscRsaDnaCugRowStatus,
--           mscRsaConnectionVcNotDataXferToSubnet,
--           mscRsaConnectionLapfRemoteBusy,
--           mscRsaConnectionVcCallReferenceNumberDecimal,
--           mscRsaConnectionVcRowStatus,
--           mscRsaConnectionVcRcosToNetwork,
--           mscRsaStorageType,
--           mscRsaConnectionVcPreviousDiagnosticCode,
--           mscRsaVncsAccessRequestsDiscarded,
--           mscRsaDnaCugDnic,
--           mscRsaConnectionLapfIFramesTxDiscarded,
--           mscRsaConnectionLapfIFramesRx,
--           mscRsaConnectionRemoteName,
--           mscRsaDnaComponentName,
--           mscRsaConnectionVcCombErrorsFromSubnet,
--           mscRsaConnectionVcCallingDna,
--           mscRsaConnectionVcDataPath,
--           mscRsaAdminState,
--           mscRsaConnectionVcPeakOoSeqFrmForwarded,
--           mscRsaConnectionVcSegmentsRx,
--           mscRsaConnectionVcFrmCongestedToSubnet,
--           mscRsaRowStatus,
--           mscRsaConnectionVncsRequests,
--           mscRsaDnaOutCalls,
--           mscRsaConnectionVcAccountingEnabled,
--           mscRsaConnectionVcNotDataXferFromSubnet,
--           mscRsaConnectionStorageType,
--           mscRsaConnectionVcDmepValue,
--           mscRsaUsageState,
--           mscRsaVncsAccessComponentName,
--           mscRsaConnectionVcCalledLcn,
--           mscRsaConnectionVcRcosFromNetwork,
--           mscRsaConnectionVcDuplicatesFromSubnet,
--           mscRsaConnectionVcStartTime,
--           mscRsaOperationalState,
--           mscRsaConnectionVcDiagnosticCode,
--           mscRsaConnectionLapfRejectFramesRx,
--           mscRsaDnaDataNetworkAddress,
--           mscRsaConnectionRowStatus,
--           mscRsaConnectionVcCallingLcn,
--           mscRsaDnaStorageType,
--           mscRsaDnaCugType,
--           mscRsaConnectionVcPktRetryTimeouts,
--           mscRsaConnectionVcOutOfRangeFrmFromSubnet }
-- STATUS  mandatory
-- DESCRIPTION
--   "A list of all current accessible leaf objects."

serverAccessRsaGroup OBJECT IDENTIFIER ::= { serverAccessRsaMIB 1 }
serverAccessRsaGroupCA OBJECT IDENTIFIER ::= { serverAccessRsaGroup 1 }
serverAccessRsaGroupCA02 OBJECT IDENTIFIER ::= { serverAccessRsaGroupCA 3 }
serverAccessRsaGroupCA02A OBJECT IDENTIFIER ::= { serverAccessRsaGroupCA02 2 }



-- Agent-Capabilities Statement:

-- PRODUCT-RELEASE "MscPassport Release 1.2 ServerAccessRsa."
-- STATUS          mandatory
-- DESCRIPTION     "Carrier Passport ServerAccessRsa MIB: MIB Version CA02A,
--                  Software Version CA02S9C."
-- SUPPORTS        Nortel-MsCarrier-MscPassport-ServerAccessRsaMIB
--    INCLUDES     { serverAccessRsaGroupCA02A }

serverAccessRsaCapabilities OBJECT IDENTIFIER ::= { serverAccessRsaMIB 3 }
serverAccessRsaCapabilitiesCA OBJECT IDENTIFIER ::= { serverAccessRsaCapabilities 1 }
serverAccessRsaCapabilitiesCA02 OBJECT IDENTIFIER ::= { serverAccessRsaCapabilitiesCA 3 }
serverAccessRsaCapabilitiesCA02A OBJECT IDENTIFIER ::= { serverAccessRsaCapabilitiesCA02 2 }





END
