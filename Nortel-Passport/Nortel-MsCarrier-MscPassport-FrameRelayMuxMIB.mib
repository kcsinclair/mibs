Nortel-MsCarrier-MscPassport-FrameRelayMuxMIB
DEFINITIONS ::= BEGIN



IMPORTS

      OBJECT-TYPE
   FROM RFC-1212

      mscPassportMIBs,
      mscComponents
   FROM Nortel-MsCarrier-MscPassport-UsefulDefinitionsMIB

      Counter32,
      RowPointer,
      DisplayString,
      StorageType,
      RowStatus,
      InterfaceIndex,
      Gauge32,
      Integer32,
      Unsigned32
   FROM Nortel-MsCarrier-MscPassport-StandardTextualConventionsMIB

      NonReplicated,
      PassportCounter64,
      Link
   FROM Nortel-MsCarrier-MscPassport-TextualConventionsMIB;




-- LAST-UPDATED   "9909010000Z"
-- ORGANIZATION   "Nortel Networks"
-- CONTACT-INFO   "
--         Nortel Carrier Data Network Management
--         
--         Postal:       P.O. Box 3511, Station C 
--                       Ottawa, Ontario 
--                       Canada  K1Y 4H7
--         
--         via the WEB:  http://www.nortelnetworks.com  
--                       select 'Contact Us' from the menu
--          
--         via phone:    1-800-4NORTEL"
-- DESCRIPTION
--    "The module describing the Nortel MsCarrier MscPassport
--     FrameRelayMux Enterprise MIB."

frameRelayMuxMIB OBJECT IDENTIFIER ::= { mscPassportMIBs 38 }










-- FrMux/n
-- This component defines an instance of the Frame Relay 
-- Multiplexer/Demultiplexer used by the DpnGateway as a frame 
-- relay transport mechanism. The component instance value n is a 
-- unique positive integer within a module.

mscFrMux OBJECT IDENTIFIER ::= { mscComponents 112 }



mscFrMuxRowStatusTable OBJECT-TYPE
   SYNTAX     SEQUENCE OF MscFrMuxRowStatusEntry
   ACCESS     not-accessible
   STATUS     mandatory
   DESCRIPTION
     "This entry controls the addition and deletion of 
      mscFrMux components."
::= { mscFrMux 1 }

mscFrMuxRowStatusEntry OBJECT-TYPE
   SYNTAX     MscFrMuxRowStatusEntry
   ACCESS     not-accessible
   STATUS     mandatory
   DESCRIPTION
     "A single entry in the table represents a single 
      mscFrMux component."
   INDEX {
      mscFrMuxIndex }
::= { mscFrMuxRowStatusTable 1 }

MscFrMuxRowStatusEntry ::= SEQUENCE {
   mscFrMuxRowStatus
      RowStatus,
   mscFrMuxComponentName
      DisplayString,
   mscFrMuxStorageType
      StorageType,
   mscFrMuxIndex
      Integer32 }

mscFrMuxRowStatus OBJECT-TYPE
   SYNTAX     RowStatus 
   ACCESS     read-write
   STATUS     mandatory
   DESCRIPTION
     "This variable is used as the basis for SNMP naming of
      mscFrMux components.
      These components can be added and deleted."
::= { mscFrMuxRowStatusEntry 1 }

mscFrMuxComponentName OBJECT-TYPE
   SYNTAX     DisplayString 
   ACCESS     read-only
   STATUS     mandatory
   DESCRIPTION
     "This variable provides the component's string name for
      use with the ASCII Console Interface"
::= { mscFrMuxRowStatusEntry 2 }

mscFrMuxStorageType OBJECT-TYPE
   SYNTAX     StorageType 
   ACCESS     read-only
   STATUS     mandatory
   DESCRIPTION
     "This variable represents the storage type value for the
      mscFrMux tables."
::= { mscFrMuxRowStatusEntry 4 }

mscFrMuxIndex OBJECT-TYPE
   SYNTAX     Integer32 (1..65535)
   ACCESS     not-accessible
   STATUS     mandatory
   DESCRIPTION
     "This variable represents the index for the mscFrMux tables."
::= { mscFrMuxRowStatusEntry 10 }

mscFrMuxOperStatusTable OBJECT-TYPE
   SYNTAX     SEQUENCE OF MscFrMuxOperStatusEntry
   ACCESS     not-accessible
   STATUS     mandatory
   DESCRIPTION
     "This group includes the Operational Status attribute. This attribute 
      defines the current operational state of this component."
::= { mscFrMux 8 }

mscFrMuxOperStatusEntry OBJECT-TYPE
   SYNTAX     MscFrMuxOperStatusEntry
   ACCESS     not-accessible
   STATUS     mandatory
   DESCRIPTION
     "An entry in the mscFrMuxOperStatusTable."
   INDEX {
      mscFrMuxIndex }
::= { mscFrMuxOperStatusTable 1 }

MscFrMuxOperStatusEntry ::= SEQUENCE {
   mscFrMuxSnmpOperStatus
      INTEGER }

mscFrMuxSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { mscFrMuxOperStatusEntry 1 }

mscFrMuxIfEntryTable OBJECT-TYPE
   SYNTAX     SEQUENCE OF MscFrMuxIfEntryEntry
   ACCESS     not-accessible
   STATUS     mandatory
   DESCRIPTION
     "This group contains the provisionable attributes for the ifEntry."
::= { mscFrMux 9 }

mscFrMuxIfEntryEntry OBJECT-TYPE
   SYNTAX     MscFrMuxIfEntryEntry
   ACCESS     not-accessible
   STATUS     mandatory
   DESCRIPTION
     "An entry in the mscFrMuxIfEntryTable."
   INDEX {
      mscFrMuxIndex }
::= { mscFrMuxIfEntryTable 1 }

MscFrMuxIfEntryEntry ::= SEQUENCE {
   mscFrMuxIfAdminStatus
      INTEGER,
   mscFrMuxIfIndex
      InterfaceIndex }

mscFrMuxIfAdminStatus OBJECT-TYPE
   SYNTAX     INTEGER  {
                 up(1),
                 down(2),
                 testing(3) }
   ACCESS     read-write
   STATUS     mandatory
   DESCRIPTION
     "The desired state of the interface. The up state indicates the 
      interface is operational. The down state indicates the interface is not 
      operational. The testing state indicates that no operational packets 
      can be passed."
   DEFVAL     { up }
::= { mscFrMuxIfEntryEntry 1 }

mscFrMuxIfIndex OBJECT-TYPE
   SYNTAX     InterfaceIndex (1..65535)
   ACCESS     read-only
   STATUS     mandatory
   DESCRIPTION
     "This is the index for the IfEntry. Its value is automatically initialized 
      during the provisioning process."
::= { mscFrMuxIfEntryEntry 2 }

mscFrMuxCidDataTable OBJECT-TYPE
   SYNTAX     SEQUENCE OF MscFrMuxCidDataEntry
   ACCESS     not-accessible
   STATUS     mandatory
   DESCRIPTION
     "This group contains the attribute for a component's Customer 
      Identifier (CID). Refer to the attribute description for a detailed 
      explanation of CIDs."
::= { mscFrMux 10 }

mscFrMuxCidDataEntry OBJECT-TYPE
   SYNTAX     MscFrMuxCidDataEntry
   ACCESS     not-accessible
   STATUS     mandatory
   DESCRIPTION
     "An entry in the mscFrMuxCidDataTable."
   INDEX {
      mscFrMuxIndex }
::= { mscFrMuxCidDataTable 1 }

MscFrMuxCidDataEntry ::= SEQUENCE {
   mscFrMuxCustomerIdentifier
      Unsigned32 }

mscFrMuxCustomerIdentifier OBJECT-TYPE
   SYNTAX     Unsigned32 (0 | 1..8191)
   ACCESS     read-write
   STATUS     mandatory
   DESCRIPTION
     "This attribute holds the Customer Identifier (CID).
      
      Every component has a CID. If a component has a cid attribute, the 
      component's CID is the provisioned value of that attribute; 
      otherwise the component inherits the CID of its parent. The top-
      level component has a CID of 0.
      
      Every operator session also has a CID, which is the CID 
      provisioned for the operator's user ID. An operator will see only the 
      stream data for components having a matching CID. Also, the 
      operator will be allowed to issue commands for only those 
      components which have a matching CID.
      
      An operator CID of 0 is used to identify the Network Manager 
      (referred to as 'NetMan' in DPN). This CID matches the CID of 
      any component. Values 1 to 8191 inclusive (equivalent to 'basic 
      CIDs' in DPN) may be assigned to specific customers."
   DEFVAL     { 0 }
::= { mscFrMuxCidDataEntry 1 }

mscFrMuxStateTable OBJECT-TYPE
   SYNTAX     SEQUENCE OF MscFrMuxStateEntry
   ACCESS     not-accessible
   STATUS     mandatory
   DESCRIPTION
     "This group contains the three OSI State attributes and the six OSI 
      Status attributes. The descriptions generically indicate what each 
      attribute implies about the component. Note that not all the values 
      and state combinations described here are supported by every 
      component which uses this group. For component-specific 
      information and the valid state combinations, refer to NTP 241-
      7001-150, Passport Operations and Maintenance Guide."
::= { mscFrMux 11 }

mscFrMuxStateEntry OBJECT-TYPE
   SYNTAX     MscFrMuxStateEntry
   ACCESS     not-accessible
   STATUS     mandatory
   DESCRIPTION
     "An entry in the mscFrMuxStateTable."
   INDEX {
      mscFrMuxIndex }
::= { mscFrMuxStateTable 1 }

MscFrMuxStateEntry ::= SEQUENCE {
   mscFrMuxAdminState
      INTEGER,
   mscFrMuxOperationalState
      INTEGER,
   mscFrMuxUsageState
      INTEGER,
   mscFrMuxAvailabilityStatus
      OCTET STRING,
   mscFrMuxProceduralStatus
      OCTET STRING,
   mscFrMuxControlStatus
      OCTET STRING,
   mscFrMuxAlarmStatus
      OCTET STRING,
   mscFrMuxStandbyStatus
      INTEGER,
   mscFrMuxUnknownStatus
      INTEGER }

mscFrMuxAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component.
      
      The OSI Status attributes, if supported by the component, may 
      provide more details, qualifying the state of the component."
   DEFVAL     { unlocked }
::= { mscFrMuxStateEntry 1 }

mscFrMuxOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle.
      
      The OSI Status attributes, if supported by the component, may 
      provide more details, qualifying the state of the component."
   DEFVAL     { disabled }
::= { mscFrMuxStateEntry 2 }

mscFrMuxUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time.
      
      The OSI Status attributes, if supported by the component, may 
      provide more details, qualifying the state of the component."
   DEFVAL     { idle }
::= { mscFrMuxStateEntry 3 }

mscFrMuxAvailabilityStatus OBJECT-TYPE
   SYNTAX     OCTET STRING (SIZE (2))
   ACCESS     read-only
   STATUS     mandatory
   DESCRIPTION
     "If supported by the component, this attribute indicates the OSI 
      Availability status of the component. Note that, even though it is 
      defined as a multi-valued set, at most one value is shown to the user.
      
      When no values are in the set, this indicates that either the attribute 
      is not supported or that none of the status conditions described 
      below are present.
      
      The value inTest indicates that the resource is undergoing a test 
      procedure. If adminState is locked or shuttingDown, the normal 
      users are precluded from using the resource and controlStatus is 
      reservedForTest. Tests that do not exclude additional users can be 
      present in any operational or administrative state but the 
      reservedForTest condition should not be present.
      
      The value failed indicates that the component has an internal fault 
      that prevents it from operating. The operationalState is disabled.
      
      The value dependency indicates that the component cannot operate 
      because some other resource on which it depends is unavailable. 
      The operationalState is disabled.
      
      The value powerOff indicates the resource requires power to be 
      applied and it is not powered on. The operationalState is disabled.
      
      The value offLine indicates the resource requires a routine 
      operation (either manual, automatic, or both) to be performed to 
      place it on-line and make it available for use. The operationalState 
      is disabled.
      
      The value offDuty indicates the resource is inactive in accordance 
      with a predetermined time schedule. In the absence of other 
      disabling conditions, the operationalState is enabled or disabled.
      
      The value degraded indicates the service provided by the 
      component is degraded in some way, such as in speed or operating 
      capacity. However, the resource remains available for service. The 
      operationalState is enabled.
      
      The value notInstalled indicates the resource is not present. The 
      operationalState is disabled.
      
      The value logFull is not used.

      Description of bits:
      inTest(0)
      failed(1)
      powerOff(2)
      offLine(3)
      offDuty(4)
      dependency(5)
      degraded(6)
      notInstalled(7)
      logFull(8)"
::= { mscFrMuxStateEntry 4 }

mscFrMuxProceduralStatus OBJECT-TYPE
   SYNTAX     OCTET STRING (SIZE (1))
   ACCESS     read-only
   STATUS     mandatory
   DESCRIPTION
     "If supported by the component, this attribute indicates the OSI 
      Procedural status of the component. Note that, even though it is 
      defined as a multi-valued set, at most one value is shown to the user.
      
      When no values are in the set, this indicates that either the attribute 
      is not supported or that none of the status conditions described 
      below are present.
      
      The value initializationRequired indicates (for a resource which 
      doesn't initialize autonomously) that initialization is required before 
      it can perform its normal functions, and this procedure has not been 
      initiated. The operationalState is disabled.
      
      The value notInitialized indicates (for a resource which does 
      initialize autonomously) that initialization is required before it can 
      perform its normal functions, and this procedure has not been 
      initiated. The operationalState may be enabled or disabled.
      
      The value initializing indicates that initialization has been initiated 
      but is not yet complete. The operationalState may be enabled or 
      disabled.
      
      The value reporting indicates the resource has completed some 
      processing operation and is notifying the results. The 
      operationalState is enabled.
      
      The value terminating indicates the component is in a termination 
      phase. If the resource doesn't reinitialize autonomously, 
      operationalState is disabled; otherwise it is enabled or disabled.

      Description of bits:
      initializationRequired(0)
      notInitialized(1)
      initializing(2)
      reporting(3)
      terminating(4)"
::= { mscFrMuxStateEntry 5 }

mscFrMuxControlStatus OBJECT-TYPE
   SYNTAX     OCTET STRING (SIZE (1))
   ACCESS     read-only
   STATUS     mandatory
   DESCRIPTION
     "If supported by the component, this attribute indicates the OSI 
      Control status of the component. Note that, even though it is defined 
      as a multi-valued set, at most one value is shown to the user.
      
      When no values are in the set, this indicates that either the attribute 
      is not supported or that none of the status conditions described 
      below are present.
      
      The value subjectToTest indicates the resource is available but tests 
      may be conducted simultaneously at unpredictable times, which 
      may cause it to exhibit unusual characteristics.
      
      The value partOfServicesLocked indicates that part of the service is 
      restricted from users of a resource. The adminState is unlocked.
      
      The value reservedForTest indicates that the component is 
      administratively unavailable because it is undergoing a test 
      procedure. The adminState is locked.
      
      The value suspended indicates that the service has been 
      administratively suspended.

      Description of bits:
      subjectToTest(0)
      partOfServicesLocked(1)
      reservedForTest(2)
      suspended(3)"
::= { mscFrMuxStateEntry 6 }

mscFrMuxAlarmStatus OBJECT-TYPE
   SYNTAX     OCTET STRING (SIZE (1))
   ACCESS     read-only
   STATUS     mandatory
   DESCRIPTION
     "If supported by the component, this attribute indicates the OSI 
      Alarm status of the component. Note that, even though it is defined 
      as a multi-valued set, at most one value is shown to the user.
      
      When no values are in the set, this indicates that either the attribute 
      is not supported or that none of the status conditions described 
      below are present.
      
      The value underRepair indicates the component is currently being 
      repaired. The operationalState is enabled or disabled.
      
      The value critical indicates one or more critical alarms are 
      outstanding against the component. Other, less severe, alarms may 
      also be outstanding. The operationalState is enabled or disabled.
      
      The value major indicates one or more major alarms are 
      outstanding against the component. Other, less severe, alarms may 
      also be outstanding. The operationalState is enabled or disabled.
      
      The value minor indicates one or more minor alarms are 
      outstanding against the component. Other, less severe, alarms may 
      also be outstanding. The operationalState is enabled or disabled.
      
      The value alarmOutstanding generically indicates that an alarm of 
      some severity is outstanding against the component.

      Description of bits:
      underRepair(0)
      critical(1)
      major(2)
      minor(3)
      alarmOutstanding(4)"
::= { mscFrMuxStateEntry 7 }

mscFrMuxStandbyStatus OBJECT-TYPE
   SYNTAX     INTEGER  {
                 hotStandby(0),
                 coldStandby(1),
                 providingService(2),
                 notSet(15) }
   ACCESS     read-only
   STATUS     mandatory
   DESCRIPTION
     "If supported by the component, this attribute indicates the OSI 
      Standby status of the component.
      
      The value notSet indicates that either the attribute is not supported 
      or that none of the status conditions described below are present. 
      Note that this is a non-standard value, used because the original 
      specification indicated this attribute was set-valued and thus, did not 
      provide a value to indicate that none of the other three are 
      applicable.
      
      The value hotStandby indicates that the resource is not providing 
      service but will be immediately able to take over the role of the 
      resource to be backed up, without initialization activity, and 
      containing the same information as the resource to be backed up.
      
      The value coldStandby indicates the resource is a backup for 
      another resource but will not be immediately able to take over the 
      role of the backed up resource and will require some initialization 
      activity.
      
      The value providingService indicates that this component, as a 
      backup resource, is currently backing up another resource."
   DEFVAL     { notSet }
::= { mscFrMuxStateEntry 8 }

mscFrMuxUnknownStatus OBJECT-TYPE
   SYNTAX     INTEGER  {
                 false(0),
                 true(1) }
   ACCESS     read-only
   STATUS     mandatory
   DESCRIPTION
     "This attribute indicates the OSI Unknown status of the component.
      
      The value false indicates that all of the other OSI State and Status 
      attribute values can be considered accurate.
      
      The value true indicates that the actual state of the component is not 
      known for sure."
   DEFVAL     { false }
::= { mscFrMuxStateEntry 9 }

mscFrMuxStatsTable OBJECT-TYPE
   SYNTAX     SEQUENCE OF MscFrMuxStatsEntry
   ACCESS     not-accessible
   STATUS     mandatory
   DESCRIPTION
     "This group contains the statistics about the operational behavior of 
      the FrMux at the interface level."
::= { mscFrMux 12 }

mscFrMuxStatsEntry OBJECT-TYPE
   SYNTAX     MscFrMuxStatsEntry
   ACCESS     not-accessible
   STATUS     mandatory
   DESCRIPTION
     "An entry in the mscFrMuxStatsTable."
   INDEX {
      mscFrMuxIndex }
::= { mscFrMuxStatsTable 1 }

MscFrMuxStatsEntry ::= SEQUENCE {
   mscFrMuxLastUnknownDlci
      Unsigned32,
   mscFrMuxUnknownDlciFramesFromIf
      Counter32,
   mscFrMuxInvalidHeaderFramesFromIf
      Counter32,
   mscFrMuxTimeFramerCongested
      Counter32 }

mscFrMuxLastUnknownDlci OBJECT-TYPE
   SYNTAX     Unsigned32 (0..1023)
   ACCESS     read-only
   STATUS     mandatory
   DESCRIPTION
     "This attribute identifies the most recent DLCI which user frames 
      were received on, for which a Dlci has not been provisioned on the 
      interface."
   DEFVAL     { 0 }
::= { mscFrMuxStatsEntry 1 }

mscFrMuxUnknownDlciFramesFromIf OBJECT-TYPE
   SYNTAX     Counter32 
   ACCESS     read-only
   STATUS     mandatory
   DESCRIPTION
     "This attribute counts frames received from the interface with an 
      unknown DLCI (Dlci which is not provisioned). When the 
      maximum is reached the count wraps to zero."
::= { mscFrMuxStatsEntry 2 }

mscFrMuxInvalidHeaderFramesFromIf OBJECT-TYPE
   SYNTAX     Counter32 
   ACCESS     read-only
   STATUS     mandatory
   DESCRIPTION
     "This attribute counts the number of frames received from the 
      interface with an invalid header format. When the maximum is 
      reached the count wraps to zero."
::= { mscFrMuxStatsEntry 3 }

mscFrMuxTimeFramerCongested OBJECT-TYPE
   SYNTAX     Counter32 
   ACCESS     read-only
   STATUS     mandatory
   DESCRIPTION
     "This attribute accumulates the time (in msec) during which Framer 
      congestion has been observed in the direction towards the interface. 
      The overload causing this statistic to increase may be caused by 
      oversubscription. When this count reaches maximum, it wraps to 
      zero."
::= { mscFrMuxStatsEntry 4 }


-- FrUni/n Framer
-- FrNni/n Framer
-- FrAtm/n Framer
-- This component controls link layer framing for application 
-- components sending and receiving data on a link interface. It is also 
-- through Framer, that an application component is associated with a 
-- specific hardware link interface.
-- 
-- The Framer component provides provisionable attributes related to 
-- datapath aspects of the hardware interface (such as crc and frame 
-- length) rather than interface specific attributes (such as modem 
-- leads and clocking) which are associated with specific hardware 
-- components (such as V35/n or DS1/n). The Framer component also 
-- provides a provisionable attribute which binds the application 
-- component to a specific hardware component.
-- 
-- The Framer component contains operational attributes for link 
-- interface datapath statistics (such as frame counts and aborts).
-- 

mscFrMuxFramer OBJECT IDENTIFIER ::= { mscFrMux 2 }



mscFrMuxFramerRowStatusTable OBJECT-TYPE
   SYNTAX     SEQUENCE OF MscFrMuxFramerRowStatusEntry
   ACCESS     not-accessible
   STATUS     mandatory
   DESCRIPTION
     "This entry controls the addition and deletion of 
      mscFrMuxFramer components."
::= { mscFrMuxFramer 1 }

mscFrMuxFramerRowStatusEntry OBJECT-TYPE
   SYNTAX     MscFrMuxFramerRowStatusEntry
   ACCESS     not-accessible
   STATUS     mandatory
   DESCRIPTION
     "A single entry in the table represents a single 
      mscFrMuxFramer component."
   INDEX {
      mscFrMuxIndex,
      mscFrMuxFramerIndex }
::= { mscFrMuxFramerRowStatusTable 1 }

MscFrMuxFramerRowStatusEntry ::= SEQUENCE {
   mscFrMuxFramerRowStatus
      RowStatus,
   mscFrMuxFramerComponentName
      DisplayString,
   mscFrMuxFramerStorageType
      StorageType,
   mscFrMuxFramerIndex
      NonReplicated }

mscFrMuxFramerRowStatus OBJECT-TYPE
   SYNTAX     RowStatus 
   ACCESS     read-only
   STATUS     mandatory
   DESCRIPTION
     "This variable is used as the basis for SNMP naming of
      mscFrMuxFramer components.
      These components cannot be added nor deleted."
::= { mscFrMuxFramerRowStatusEntry 1 }

mscFrMuxFramerComponentName OBJECT-TYPE
   SYNTAX     DisplayString 
   ACCESS     read-only
   STATUS     mandatory
   DESCRIPTION
     "This variable provides the component's string name for
      use with the ASCII Console Interface"
::= { mscFrMuxFramerRowStatusEntry 2 }

mscFrMuxFramerStorageType OBJECT-TYPE
   SYNTAX     StorageType 
   ACCESS     read-only
   STATUS     mandatory
   DESCRIPTION
     "This variable represents the storage type value for the
      mscFrMuxFramer tables."
::= { mscFrMuxFramerRowStatusEntry 4 }

mscFrMuxFramerIndex OBJECT-TYPE
   SYNTAX     NonReplicated 
   ACCESS     not-accessible
   STATUS     mandatory
   DESCRIPTION
     "This variable represents the index for the mscFrMuxFramer tables."
::= { mscFrMuxFramerRowStatusEntry 10 }

mscFrMuxFramerProvTable OBJECT-TYPE
   SYNTAX     SEQUENCE OF MscFrMuxFramerProvEntry
   ACCESS     not-accessible
   STATUS     mandatory
   DESCRIPTION
     "This group contains the base provisioning data for the Framer 
      component. Application or hardware interface specific provisioning 
      data is contained in other provisionable Framer groups."
::= { mscFrMuxFramer 10 }

mscFrMuxFramerProvEntry OBJECT-TYPE
   SYNTAX     MscFrMuxFramerProvEntry
   ACCESS     not-accessible
   STATUS     mandatory
   DESCRIPTION
     "An entry in the mscFrMuxFramerProvTable."
   INDEX {
      mscFrMuxIndex,
      mscFrMuxFramerIndex }
::= { mscFrMuxFramerProvTable 1 }

MscFrMuxFramerProvEntry ::= SEQUENCE {
   mscFrMuxFramerInterfaceName
      Link }

mscFrMuxFramerInterfaceName OBJECT-TYPE
   SYNTAX     Link 
   ACCESS     read-write
   STATUS     mandatory
   DESCRIPTION
     "This attribute contains a hardware component name.
      
      The attribute associates the application with a specific link. This 
      defines the module processor on which Framer's parent component 
      (as well as Framer itself) will run."
::= { mscFrMuxFramerProvEntry 1 }

mscFrMuxFramerLinkTable OBJECT-TYPE
   SYNTAX     SEQUENCE OF MscFrMuxFramerLinkEntry
   ACCESS     not-accessible
   STATUS     mandatory
   DESCRIPTION
     "This group contains attributes defining the framing of data on the 
      link interface."
::= { mscFrMuxFramer 11 }

mscFrMuxFramerLinkEntry OBJECT-TYPE
   SYNTAX     MscFrMuxFramerLinkEntry
   ACCESS     not-accessible
   STATUS     mandatory
   DESCRIPTION
     "An entry in the mscFrMuxFramerLinkTable."
   INDEX {
      mscFrMuxIndex,
      mscFrMuxFramerIndex }
::= { mscFrMuxFramerLinkTable 1 }

MscFrMuxFramerLinkEntry ::= SEQUENCE {
   mscFrMuxFramerDataInversion
      INTEGER,
   mscFrMuxFramerFrameCrcType
      INTEGER,
   mscFrMuxFramerFlagsBetweenFrames
      Unsigned32 }

mscFrMuxFramerDataInversion OBJECT-TYPE
   SYNTAX     INTEGER  {
                 off(0),
                 on(16) }
   ACCESS     read-write
   STATUS     mandatory
   DESCRIPTION
     "This attribute determines whether data bits are to be inverted (1 to 0 
      and 0 to 1) before transmission of frames to the interface. If the 
      value of this attribute is On, the incoming data bits will also be 
      inverted when frames are received from the link before being 
      processed.
      
      This option is typically used in hdlc framing mode when inversion 
      is used to guarantee 1's density.
      
      Note that aborts (in hdlc and interrupting modes) are corrupted 
      when data is inverted.
      
      This attribute may only take its default value for non-MSA cards."
   DEFVAL     { off }
::= { mscFrMuxFramerLinkEntry 2 }

mscFrMuxFramerFrameCrcType OBJECT-TYPE
   SYNTAX     INTEGER  {
                 crc16(0),
                 crc32(1),
                 noCrc(2) }
   ACCESS     read-write
   STATUS     mandatory
   DESCRIPTION
     "This attribute defines the type of CRC used. 
      
      The CRC value calculated is appended to the end of the frames 
      transmitted to the link. The CRC value is removed from the end of 
      frames received from the link and checked for correctness.
      NoCrc means that CRC is not used.
      
      This attribute may take only its default value for non-MSA cards."
   DEFVAL     { crc16 }
::= { mscFrMuxFramerLinkEntry 3 }

mscFrMuxFramerFlagsBetweenFrames OBJECT-TYPE
   SYNTAX     Unsigned32 (1..16)
   ACCESS     read-write
   STATUS     mandatory
   DESCRIPTION
     "This attribute defines the number of flags that are inserted between 
      frames sent to the link interface."
   DEFVAL     { 1 }
::= { mscFrMuxFramerLinkEntry 4 }

mscFrMuxFramerStateTable OBJECT-TYPE
   SYNTAX     SEQUENCE OF MscFrMuxFramerStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscFrMuxFramer 12 }

mscFrMuxFramerStateEntry OBJECT-TYPE
   SYNTAX     MscFrMuxFramerStateEntry
   ACCESS     not-accessible
   STATUS     mandatory
   DESCRIPTION
     "An entry in the mscFrMuxFramerStateTable."
   INDEX {
      mscFrMuxIndex,
      mscFrMuxFramerIndex }
::= { mscFrMuxFramerStateTable 1 }

MscFrMuxFramerStateEntry ::= SEQUENCE {
   mscFrMuxFramerAdminState
      INTEGER,
   mscFrMuxFramerOperationalState
      INTEGER,
   mscFrMuxFramerUsageState
      INTEGER }

mscFrMuxFramerAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscFrMuxFramerStateEntry 1 }

mscFrMuxFramerOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscFrMuxFramerStateEntry 2 }

mscFrMuxFramerUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscFrMuxFramerStateEntry 3 }

mscFrMuxFramerStatsTable OBJECT-TYPE
   SYNTAX     SEQUENCE OF MscFrMuxFramerStatsEntry
   ACCESS     not-accessible
   STATUS     mandatory
   DESCRIPTION
     "This group contains the operational statistics data for a Framer 
      component."
::= { mscFrMuxFramer 13 }

mscFrMuxFramerStatsEntry OBJECT-TYPE
   SYNTAX     MscFrMuxFramerStatsEntry
   ACCESS     not-accessible
   STATUS     mandatory
   DESCRIPTION
     "An entry in the mscFrMuxFramerStatsTable."
   INDEX {
      mscFrMuxIndex,
      mscFrMuxFramerIndex }
::= { mscFrMuxFramerStatsTable 1 }

MscFrMuxFramerStatsEntry ::= SEQUENCE {
   mscFrMuxFramerFrmToIf
      Counter32,
   mscFrMuxFramerFrmFromIf
      Counter32,
   mscFrMuxFramerOctetFromIf
      Counter32,
   mscFrMuxFramerAborts
      Counter32,
   mscFrMuxFramerCrcErrors
      Counter32,
   mscFrMuxFramerLrcErrors
      Counter32,
   mscFrMuxFramerNonOctetErrors
      Counter32,
   mscFrMuxFramerOverruns
      Counter32,
   mscFrMuxFramerUnderruns
      Counter32,
   mscFrMuxFramerLargeFrmErrors
      Counter32,
   mscFrMuxFramerFrmModeErrors
      Counter32,
   mscFrMuxFramerFrmToIf64
      PassportCounter64,
   mscFrMuxFramerFrmFromIf64
      PassportCounter64,
   mscFrMuxFramerOctetFromIf64
      PassportCounter64 }

mscFrMuxFramerFrmToIf OBJECT-TYPE
   SYNTAX     Counter32 
   ACCESS     read-only
   STATUS     obsolete
   DESCRIPTION
     "The number of frames transmitted to the link interface by Framer.
      
      Note: This does not include the number of frames transmitted 
      directly to the hardware queue, thus bypassing the Framer 
      component."
::= { mscFrMuxFramerStatsEntry 1 }

mscFrMuxFramerFrmFromIf OBJECT-TYPE
   SYNTAX     Counter32 
   ACCESS     read-only
   STATUS     obsolete
   DESCRIPTION
     "The number of frames received from the link interface by Framer."
::= { mscFrMuxFramerStatsEntry 2 }

mscFrMuxFramerOctetFromIf OBJECT-TYPE
   SYNTAX     Counter32 
   ACCESS     read-only
   STATUS     obsolete
   DESCRIPTION
     "The number of bytes received from the link interface by Framer."
::= { mscFrMuxFramerStatsEntry 3 }

mscFrMuxFramerAborts OBJECT-TYPE
   SYNTAX     Counter32 
   ACCESS     read-only
   STATUS     mandatory
   DESCRIPTION
     "This attribute is the total number of aborts received."
::= { mscFrMuxFramerStatsEntry 4 }

mscFrMuxFramerCrcErrors OBJECT-TYPE
   SYNTAX     Counter32 
   ACCESS     read-only
   STATUS     mandatory
   DESCRIPTION
     "This attribute is the total number of frames with CRC errors, 
      occurring in the receive direction from the link."
::= { mscFrMuxFramerStatsEntry 5 }

mscFrMuxFramerLrcErrors OBJECT-TYPE
   SYNTAX     Counter32 
   ACCESS     read-only
   STATUS     mandatory
   DESCRIPTION
     "This attribute is the total number of frames with LRC errors, 
      occurring in the Tx link prior to transmission onto the link."
::= { mscFrMuxFramerStatsEntry 6 }

mscFrMuxFramerNonOctetErrors OBJECT-TYPE
   SYNTAX     Counter32 
   ACCESS     read-only
   STATUS     mandatory
   DESCRIPTION
     "This attribute is the total number of frames that were non octet 
      aligned."
::= { mscFrMuxFramerStatsEntry 7 }

mscFrMuxFramerOverruns OBJECT-TYPE
   SYNTAX     Counter32 
   ACCESS     read-only
   STATUS     mandatory
   DESCRIPTION
     "This attribute is the total number of frames received from the link 
      for which overruns occurred."
::= { mscFrMuxFramerStatsEntry 8 }

mscFrMuxFramerUnderruns OBJECT-TYPE
   SYNTAX     Counter32 
   ACCESS     read-only
   STATUS     mandatory
   DESCRIPTION
     "This attribute is the total number of frames transmitted to the link 
      for which underruns occurred."
::= { mscFrMuxFramerStatsEntry 9 }

mscFrMuxFramerLargeFrmErrors OBJECT-TYPE
   SYNTAX     Counter32 
   ACCESS     read-only
   STATUS     mandatory
   DESCRIPTION
     "This attribute is the total number of frames received which were too 
      large. The frame execeeded the maximumFrameLengthLimit 
      provisioned attribute or it contained more than the 255 block 
      hardware limit."
::= { mscFrMuxFramerStatsEntry 10 }

mscFrMuxFramerFrmModeErrors OBJECT-TYPE
   SYNTAX     Counter32 
   ACCESS     read-only
   STATUS     mandatory
   DESCRIPTION
     "This attribute is the total number of frames detected with framing 
      mode errors. A framingModeError is flagged when frames are 
      inconsistent with the specified framingType, that is when 
      interrupting frames are used while running in hdlc mode."
::= { mscFrMuxFramerStatsEntry 11 }

mscFrMuxFramerFrmToIf64 OBJECT-TYPE
   SYNTAX     PassportCounter64 
   ACCESS     read-only
   STATUS     mandatory
   DESCRIPTION
     "The number of frames transmitted to the link interface by Framer.
      
      Note: This does not include the number of frames transmitted 
      directly to the hardware queue, thus bypassing the Framer 
      component."
::= { mscFrMuxFramerStatsEntry 14 }

mscFrMuxFramerFrmFromIf64 OBJECT-TYPE
   SYNTAX     PassportCounter64 
   ACCESS     read-only
   STATUS     mandatory
   DESCRIPTION
     "The number of frames received from the link interface by Framer."
::= { mscFrMuxFramerStatsEntry 15 }

mscFrMuxFramerOctetFromIf64 OBJECT-TYPE
   SYNTAX     PassportCounter64 
   ACCESS     read-only
   STATUS     mandatory
   DESCRIPTION
     "The number of bytes received from the link interface by Framer."
::= { mscFrMuxFramerStatsEntry 16 }

mscFrMuxFramerUtilTable OBJECT-TYPE
   SYNTAX     SEQUENCE OF MscFrMuxFramerUtilEntry
   ACCESS     not-accessible
   STATUS     mandatory
   DESCRIPTION
     "This group contains the link utilizaiton operational data for a 
      Framer component."
::= { mscFrMuxFramer 14 }

mscFrMuxFramerUtilEntry OBJECT-TYPE
   SYNTAX     MscFrMuxFramerUtilEntry
   ACCESS     not-accessible
   STATUS     mandatory
   DESCRIPTION
     "An entry in the mscFrMuxFramerUtilTable."
   INDEX {
      mscFrMuxIndex,
      mscFrMuxFramerIndex }
::= { mscFrMuxFramerUtilTable 1 }

MscFrMuxFramerUtilEntry ::= SEQUENCE {
   mscFrMuxFramerNormPrioLinkUtilToIf
      Gauge32,
   mscFrMuxFramerNormPrioLinkUtilFromIf
      Gauge32 }

mscFrMuxFramerNormPrioLinkUtilToIf OBJECT-TYPE
   SYNTAX     Gauge32 (0..100)
   ACCESS     read-only
   STATUS     mandatory
   DESCRIPTION
     "This attribute is the utilization of the normal and high priority data 
      traffic (interruptable traffic) sent to the link as a percentage of the 
      available bandwidth on the link. Note that this indluces traffic with 
      Transfer Priorities (TP) of 0, 6 and 9 and/or Emission Priority of 2 
      and 3. The utilization is the average for the last minute."
   DEFVAL     { 0 }
::= { mscFrMuxFramerUtilEntry 1 }

mscFrMuxFramerNormPrioLinkUtilFromIf OBJECT-TYPE
   SYNTAX     Gauge32 (0..100)
   ACCESS     read-only
   STATUS     mandatory
   DESCRIPTION
     "This attribute is the utilization of the normal and high priority data 
      traffic (interruptable traffic) received from the link as a percentage 
      of the available bandwidth on the link. Note that this includes traffic 
      with Transfer Priorities (TP) of 0, 6 and 9 and/or Emission Priority 
      of 2 and 3. The utilization is the average for the last minute."
   DEFVAL     { 0 }
::= { mscFrMuxFramerUtilEntry 3 }


-- FrMux/n Lmi
-- This component defines the parameters for implementing the Local 
-- Management Interface protocol.

mscFrMuxLmi OBJECT IDENTIFIER ::= { mscFrMux 3 }



mscFrMuxLmiRowStatusTable OBJECT-TYPE
   SYNTAX     SEQUENCE OF MscFrMuxLmiRowStatusEntry
   ACCESS     not-accessible
   STATUS     mandatory
   DESCRIPTION
     "This entry controls the addition and deletion of 
      mscFrMuxLmi components."
::= { mscFrMuxLmi 1 }

mscFrMuxLmiRowStatusEntry OBJECT-TYPE
   SYNTAX     MscFrMuxLmiRowStatusEntry
   ACCESS     not-accessible
   STATUS     mandatory
   DESCRIPTION
     "A single entry in the table represents a single 
      mscFrMuxLmi component."
   INDEX {
      mscFrMuxIndex,
      mscFrMuxLmiIndex }
::= { mscFrMuxLmiRowStatusTable 1 }

MscFrMuxLmiRowStatusEntry ::= SEQUENCE {
   mscFrMuxLmiRowStatus
      RowStatus,
   mscFrMuxLmiComponentName
      DisplayString,
   mscFrMuxLmiStorageType
      StorageType,
   mscFrMuxLmiIndex
      NonReplicated }

mscFrMuxLmiRowStatus OBJECT-TYPE
   SYNTAX     RowStatus 
   ACCESS     read-only
   STATUS     mandatory
   DESCRIPTION
     "This variable is used as the basis for SNMP naming of
      mscFrMuxLmi components.
      These components cannot be added nor deleted."
::= { mscFrMuxLmiRowStatusEntry 1 }

mscFrMuxLmiComponentName OBJECT-TYPE
   SYNTAX     DisplayString 
   ACCESS     read-only
   STATUS     mandatory
   DESCRIPTION
     "This variable provides the component's string name for
      use with the ASCII Console Interface"
::= { mscFrMuxLmiRowStatusEntry 2 }

mscFrMuxLmiStorageType OBJECT-TYPE
   SYNTAX     StorageType 
   ACCESS     read-only
   STATUS     mandatory
   DESCRIPTION
     "This variable represents the storage type value for the
      mscFrMuxLmi tables."
::= { mscFrMuxLmiRowStatusEntry 4 }

mscFrMuxLmiIndex OBJECT-TYPE
   SYNTAX     NonReplicated 
   ACCESS     not-accessible
   STATUS     mandatory
   DESCRIPTION
     "This variable represents the index for the mscFrMuxLmi tables."
::= { mscFrMuxLmiRowStatusEntry 10 }

mscFrMuxLmiProvTable OBJECT-TYPE
   SYNTAX     SEQUENCE OF MscFrMuxLmiProvEntry
   ACCESS     not-accessible
   STATUS     mandatory
   DESCRIPTION
     "This group contains the provisionable attributes of the Local 
      Management Interface component of the FrMux. The Local 
      Management Interface of the FrMux is always User Side Procedure 
      of the User Network Interface (USP-UNI)."
::= { mscFrMuxLmi 10 }

mscFrMuxLmiProvEntry OBJECT-TYPE
   SYNTAX     MscFrMuxLmiProvEntry
   ACCESS     not-accessible
   STATUS     mandatory
   DESCRIPTION
     "An entry in the mscFrMuxLmiProvTable."
   INDEX {
      mscFrMuxIndex,
      mscFrMuxLmiIndex }
::= { mscFrMuxLmiProvTable 1 }

MscFrMuxLmiProvEntry ::= SEQUENCE {
   mscFrMuxLmiProcedures
      INTEGER,
   mscFrMuxLmiLinkVerificationTimer
      Unsigned32,
   mscFrMuxLmiFullStatusPollingCycles
      Unsigned32,
   mscFrMuxLmiErrorEventThreshold
      Unsigned32,
   mscFrMuxLmiEventCount
      Unsigned32 }

mscFrMuxLmiProcedures OBJECT-TYPE
   SYNTAX     INTEGER  {
                 none(0),
                 vendorForum(1),
                 ansi(2),
                 ccitt(3) }
   ACCESS     read-write
   STATUS     mandatory
   DESCRIPTION
     "This attribute selects the procedures to be used for the Local 
      Management Interface. The following are the supported procedures:
      none	:	 No Local Management Interface procedure is active. 
      vendorForum	:	Local Management Interface procedure according to 
      the Vendor Forum specification is active. DLCI 1023 is used for the 
      LMI protocol.
      ansi: 	Local Management Interface procedure according to the 
      ANSI specification is active. DLCI 0 is used for the LMI protocol.
      ccitt: Local Management Interface procedure according to the 
      CCITT specification is active. DLCI 0 is used for the LMI protocol."
   DEFVAL     { ccitt }
::= { mscFrMuxLmiProvEntry 1 }

mscFrMuxLmiLinkVerificationTimer OBJECT-TYPE
   SYNTAX     Unsigned32 (5 | 10 | 15 | 20 | 25 | 30)
   ACCESS     read-write
   STATUS     mandatory
   DESCRIPTION
     "This attribute specifies the time interval (in seconds) at which the 
      FrMux sends Status Enquiry messages to the interface. Exchange of 
      Status Enquiry and Status Report messages constitutes a polling 
      cycle, so this attribute may also be interpreted as time interval at 
      which the FrMux initiates polling cycles. It must be less than 
      checkPointTimer (t392) configured at the other end of the Frame 
      Relay interface.
      
      This attribute corresponds to t391 of the ANSI and CCITT 
      specifications, and nT1 of the Vendor Forum specification."
   DEFVAL     { 10 }
::= { mscFrMuxLmiProvEntry 2 }

mscFrMuxLmiFullStatusPollingCycles OBJECT-TYPE
   SYNTAX     Unsigned32 (1..255)
   ACCESS     read-write
   STATUS     mandatory
   DESCRIPTION
     "This attribute specifies every which polling cycle the FrMux sends a 
      full STATUS ENQUIRY to the interface. Every 
      fullStatusPollingCycles polling cycles the FrMux sends a full 
      STATUS ENQUIRY. In all other cycles of a sequence of 
      fullStatusPollingCycles polling cycles the FrMux sends a keep alive 
      STATUS ENQUIRY. 
      
      This attribute corresponds to n391 of the ANSI and CCITT 
      specifications and nN1 of the Vendor Forum specification."
   DEFVAL     { 6 }
::= { mscFrMuxLmiProvEntry 3 }

mscFrMuxLmiErrorEventThreshold OBJECT-TYPE
   SYNTAX     Unsigned32 (1..10)
   ACCESS     read-write
   STATUS     mandatory
   DESCRIPTION
     "This attribute specifies the number of error events which, if they 
      occur within eventCount events, will cause a protocol error 
      condition (protocolStatus = errorCondition). The error condition is 
      cleared after eventCount sequential correct events occur 
      (protocolStatus = normalCondition). 
      
      An event is one of the following: (1) expiry of the 
      linkVerificationTimer (t391), (2) reception of a STATUS message. 
      An error event is one of the following: (1)non-receipt of the 
      STATUS message in t391 seconds, (2)invalid STATUS message, (3) 
      invalid sequence number. 
      
      This attribute corresponds to n392 of the ANSI and CCITT 
      specifications and nN2 of the Vendor Forum Specification. 
      
      This attribute must be less than or equal to eventCount."
   DEFVAL     { 3 }
::= { mscFrMuxLmiProvEntry 4 }

mscFrMuxLmiEventCount OBJECT-TYPE
   SYNTAX     Unsigned32 (1..10)
   ACCESS     read-write
   STATUS     mandatory
   DESCRIPTION
     "This attribute specifies the number of contiguous events within 
      which no more than eventErrorThreshold error events are allowed.
      
      This attribute corresponds to n392 of the ANSI and CCITT 
      specifications and nN3 of the Vendor Forum Specification. 
      
      This attribute must be greater than or equal to errorEventThreshold."
   DEFVAL     { 4 }
::= { mscFrMuxLmiProvEntry 5 }

mscFrMuxLmiStateTable OBJECT-TYPE
   SYNTAX     SEQUENCE OF MscFrMuxLmiStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscFrMuxLmi 11 }

mscFrMuxLmiStateEntry OBJECT-TYPE
   SYNTAX     MscFrMuxLmiStateEntry
   ACCESS     not-accessible
   STATUS     mandatory
   DESCRIPTION
     "An entry in the mscFrMuxLmiStateTable."
   INDEX {
      mscFrMuxIndex,
      mscFrMuxLmiIndex }
::= { mscFrMuxLmiStateTable 1 }

MscFrMuxLmiStateEntry ::= SEQUENCE {
   mscFrMuxLmiAdminState
      INTEGER,
   mscFrMuxLmiOperationalState
      INTEGER,
   mscFrMuxLmiUsageState
      INTEGER }

mscFrMuxLmiAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscFrMuxLmiStateEntry 1 }

mscFrMuxLmiOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscFrMuxLmiStateEntry 2 }

mscFrMuxLmiUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscFrMuxLmiStateEntry 3 }

mscFrMuxLmiPsiTable OBJECT-TYPE
   SYNTAX     SEQUENCE OF MscFrMuxLmiPsiEntry
   ACCESS     not-accessible
   STATUS     mandatory
   DESCRIPTION
     "This group provides the protocol status of the Local Management 
      Interface of this FrMux."
::= { mscFrMuxLmi 12 }

mscFrMuxLmiPsiEntry OBJECT-TYPE
   SYNTAX     MscFrMuxLmiPsiEntry
   ACCESS     not-accessible
   STATUS     mandatory
   DESCRIPTION
     "An entry in the mscFrMuxLmiPsiTable."
   INDEX {
      mscFrMuxIndex,
      mscFrMuxLmiIndex }
::= { mscFrMuxLmiPsiTable 1 }

MscFrMuxLmiPsiEntry ::= SEQUENCE {
   mscFrMuxLmiProtocolStatus
      INTEGER }

mscFrMuxLmiProtocolStatus OBJECT-TYPE
   SYNTAX     INTEGER  {
                 errorCondition(0),
                 normalCondition(1) }
   ACCESS     read-only
   STATUS     mandatory
   DESCRIPTION
     "This attribute indicates whether the Lmi is in an error condition or 
      whether the protocol is behaving normally. When operating with no 
      LMI protocol (procedures = none), this attribute will always be set 
      to normalCondition. When operating with an LMI protocol 
      (procedures set to one of venforForum, ansi, ccitt), this attribute is 
      set to errorCondition when errorEventThreshold of the last 
      eventCount events are in error. 
      The error condition is cleared when eventCount consecutive good 
      events take place.
      The consequence of an error condition is that all Dlci's on this 
      interface become disabled and there is no data flow in either 
      direction."
   DEFVAL     { normalCondition }
::= { mscFrMuxLmiPsiEntry 1 }

mscFrMuxLmiStatsTable OBJECT-TYPE
   SYNTAX     SEQUENCE OF MscFrMuxLmiStatsEntry
   ACCESS     not-accessible
   STATUS     mandatory
   DESCRIPTION
     "This group contains the operational statistics for the FrMux Local 
      Management Interface."
::= { mscFrMuxLmi 13 }

mscFrMuxLmiStatsEntry OBJECT-TYPE
   SYNTAX     MscFrMuxLmiStatsEntry
   ACCESS     not-accessible
   STATUS     mandatory
   DESCRIPTION
     "An entry in the mscFrMuxLmiStatsTable."
   INDEX {
      mscFrMuxIndex,
      mscFrMuxLmiIndex }
::= { mscFrMuxLmiStatsTable 1 }

MscFrMuxLmiStatsEntry ::= SEQUENCE {
   mscFrMuxLmiKeepAliveStatusEnqToIf
      Counter32,
   mscFrMuxLmiFullStatusEnqToIf
      Counter32,
   mscFrMuxLmiProtocolErrors
      Counter32,
   mscFrMuxLmiUnexpectedIes
      Counter32,
   mscFrMuxLmiSequenceErrors
      Counter32,
   mscFrMuxLmiUnexpectedReports
      Counter32,
   mscFrMuxLmiNoStatusReportCount
      Counter32 }

mscFrMuxLmiKeepAliveStatusEnqToIf OBJECT-TYPE
   SYNTAX     Counter32 
   ACCESS     read-only
   STATUS     mandatory
   DESCRIPTION
     "This attribute counts the number of keep alive STATUS ENQUIRY 
      messages sent to the interface. When the maximum count is reached 
      it wraps to zero."
::= { mscFrMuxLmiStatsEntry 1 }

mscFrMuxLmiFullStatusEnqToIf OBJECT-TYPE
   SYNTAX     Counter32 
   ACCESS     read-only
   STATUS     mandatory
   DESCRIPTION
     "This attribute counts the number of full STATUS ENQUIRY 
      messages sent to the interface. When the maximum count is reached 
      it wraps to zero."
::= { mscFrMuxLmiStatsEntry 2 }

mscFrMuxLmiProtocolErrors OBJECT-TYPE
   SYNTAX     Counter32 
   ACCESS     read-only
   STATUS     mandatory
   DESCRIPTION
     "This attribute counts the number of Local Management Interface 
      protocol errors. Protocol errors include (1) protocol message format 
      errors, (2) protocol timer expiry errors, and (3) sequence errors. 
      When the maximum count is reached it wraps to zero."
::= { mscFrMuxLmiStatsEntry 3 }

mscFrMuxLmiUnexpectedIes OBJECT-TYPE
   SYNTAX     Counter32 
   ACCESS     read-only
   STATUS     mandatory
   DESCRIPTION
     "This attribute counts the number of frames received with an 
      Information Element identifier that is unknown or unexpected. 
      When the maximum count is reached, this counter wraps to zero."
::= { mscFrMuxLmiStatsEntry 4 }

mscFrMuxLmiSequenceErrors OBJECT-TYPE
   SYNTAX     Counter32 
   ACCESS     read-only
   STATUS     mandatory
   DESCRIPTION
     "This attribute counts the number of Local Management Interface 
      sequence errors. A sequence error is receipt of an LMI message 
      with a receive sequence number not equal to the last send sequence 
      number. When the maximum count is reached the counter wraps to 
      zero."
::= { mscFrMuxLmiStatsEntry 5 }

mscFrMuxLmiUnexpectedReports OBJECT-TYPE
   SYNTAX     Counter32 
   ACCESS     read-only
   STATUS     mandatory
   DESCRIPTION
     "This attribute counts the number of frames received on the Local 
      Management Interface with an unknown or unexpected report type. 
      When the maximum count is reached the counter wraps to zero."
::= { mscFrMuxLmiStatsEntry 6 }

mscFrMuxLmiNoStatusReportCount OBJECT-TYPE
   SYNTAX     Counter32 
   ACCESS     read-only
   STATUS     mandatory
   DESCRIPTION
     "This attribute counts the number of times when no status report or 
      an invalid status report comes from the external network. This 
      attribute is incremented in two cases: 
      i) after a status enquiry is sent out and t391 timer expires without 
      having a status report received.
      ii) an invalid status report is received.
      When the maximum count is reached it wraps to zero."
::= { mscFrMuxLmiStatsEntry 7 }


-- FrMux/n Dlci/n
-- This component is responsible for the Frame Relay U-plane (User-
-- plane) protocol for the specified instance. The instance value is used 
-- to identify the logical connection, multiplexed within the physical 
-- channel, with which a frame is associated. All frames carried within 
-- a particular physical channel and having the same DLCI value are 
-- associated with the same logical connection.

mscFrMuxDlci OBJECT IDENTIFIER ::= { mscFrMux 4 }



mscFrMuxDlciRowStatusTable OBJECT-TYPE
   SYNTAX     SEQUENCE OF MscFrMuxDlciRowStatusEntry
   ACCESS     not-accessible
   STATUS     mandatory
   DESCRIPTION
     "This entry controls the addition and deletion of 
      mscFrMuxDlci components."
::= { mscFrMuxDlci 1 }

mscFrMuxDlciRowStatusEntry OBJECT-TYPE
   SYNTAX     MscFrMuxDlciRowStatusEntry
   ACCESS     not-accessible
   STATUS     mandatory
   DESCRIPTION
     "A single entry in the table represents a single 
      mscFrMuxDlci component."
   INDEX {
      mscFrMuxIndex,
      mscFrMuxDlciIndex }
::= { mscFrMuxDlciRowStatusTable 1 }

MscFrMuxDlciRowStatusEntry ::= SEQUENCE {
   mscFrMuxDlciRowStatus
      RowStatus,
   mscFrMuxDlciComponentName
      DisplayString,
   mscFrMuxDlciStorageType
      StorageType,
   mscFrMuxDlciIndex
      Integer32 }

mscFrMuxDlciRowStatus OBJECT-TYPE
   SYNTAX     RowStatus 
   ACCESS     read-write
   STATUS     mandatory
   DESCRIPTION
     "This variable is used as the basis for SNMP naming of
      mscFrMuxDlci components.
      These components can be added and deleted."
::= { mscFrMuxDlciRowStatusEntry 1 }

mscFrMuxDlciComponentName OBJECT-TYPE
   SYNTAX     DisplayString 
   ACCESS     read-only
   STATUS     mandatory
   DESCRIPTION
     "This variable provides the component's string name for
      use with the ASCII Console Interface"
::= { mscFrMuxDlciRowStatusEntry 2 }

mscFrMuxDlciStorageType OBJECT-TYPE
   SYNTAX     StorageType 
   ACCESS     read-only
   STATUS     mandatory
   DESCRIPTION
     "This variable represents the storage type value for the
      mscFrMuxDlci tables."
::= { mscFrMuxDlciRowStatusEntry 4 }

mscFrMuxDlciIndex OBJECT-TYPE
   SYNTAX     Integer32 (16..1007)
   ACCESS     not-accessible
   STATUS     mandatory
   DESCRIPTION
     "This variable represents the index for the mscFrMuxDlci tables."
::= { mscFrMuxDlciRowStatusEntry 10 }

mscFrMuxDlciOperTable OBJECT-TYPE
   SYNTAX     SEQUENCE OF MscFrMuxDlciOperEntry
   ACCESS     not-accessible
   STATUS     mandatory
   DESCRIPTION
     "This group contains the name of the application associated with this 
      Dlci."
::= { mscFrMuxDlci 10 }

mscFrMuxDlciOperEntry OBJECT-TYPE
   SYNTAX     MscFrMuxDlciOperEntry
   ACCESS     not-accessible
   STATUS     mandatory
   DESCRIPTION
     "An entry in the mscFrMuxDlciOperTable."
   INDEX {
      mscFrMuxIndex,
      mscFrMuxDlciIndex }
::= { mscFrMuxDlciOperTable 1 }

MscFrMuxDlciOperEntry ::= SEQUENCE {
   mscFrMuxDlciApplicationName
      RowPointer }

mscFrMuxDlciApplicationName OBJECT-TYPE
   SYNTAX     RowPointer 
   ACCESS     read-only
   STATUS     mandatory
   DESCRIPTION
     "This attribute contains the name of the application associated with 
      this Dlci."
::= { mscFrMuxDlciOperEntry 1 }

mscFrMuxDlciStateTable OBJECT-TYPE
   SYNTAX     SEQUENCE OF MscFrMuxDlciStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscFrMuxDlci 11 }

mscFrMuxDlciStateEntry OBJECT-TYPE
   SYNTAX     MscFrMuxDlciStateEntry
   ACCESS     not-accessible
   STATUS     mandatory
   DESCRIPTION
     "An entry in the mscFrMuxDlciStateTable."
   INDEX {
      mscFrMuxIndex,
      mscFrMuxDlciIndex }
::= { mscFrMuxDlciStateTable 1 }

MscFrMuxDlciStateEntry ::= SEQUENCE {
   mscFrMuxDlciAdminState
      INTEGER,
   mscFrMuxDlciOperationalState
      INTEGER,
   mscFrMuxDlciUsageState
      INTEGER }

mscFrMuxDlciAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscFrMuxDlciStateEntry 1 }

mscFrMuxDlciOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscFrMuxDlciStateEntry 2 }

mscFrMuxDlciUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscFrMuxDlciStateEntry 3 }

mscFrMuxDlciAbitTable OBJECT-TYPE
   SYNTAX     SEQUENCE OF MscFrMuxDlciAbitEntry
   ACCESS     not-accessible
   STATUS     mandatory
   DESCRIPTION
     "This group contains the A-Bit status information for this Dlci."
::= { mscFrMuxDlci 12 }

mscFrMuxDlciAbitEntry OBJECT-TYPE
   SYNTAX     MscFrMuxDlciAbitEntry
   ACCESS     not-accessible
   STATUS     mandatory
   DESCRIPTION
     "An entry in the mscFrMuxDlciAbitTable."
   INDEX {
      mscFrMuxIndex,
      mscFrMuxDlciIndex }
::= { mscFrMuxDlciAbitTable 1 }

MscFrMuxDlciAbitEntry ::= SEQUENCE {
   mscFrMuxDlciABitStatusFromIf
      INTEGER }

mscFrMuxDlciABitStatusFromIf OBJECT-TYPE
   SYNTAX     INTEGER  {
                 inactive(0),
                 active(1) }
   ACCESS     read-only
   STATUS     mandatory
   DESCRIPTION
     "This attribute is the most recent A-Bit status received from the 
      interface."
   DEFVAL     { inactive }
::= { mscFrMuxDlciAbitEntry 1 }

mscFrMuxDlciStatsTable OBJECT-TYPE
   SYNTAX     SEQUENCE OF MscFrMuxDlciStatsEntry
   ACCESS     not-accessible
   STATUS     mandatory
   DESCRIPTION
     "This group contains the operational statistics for the FrMux Dlci."
::= { mscFrMuxDlci 13 }

mscFrMuxDlciStatsEntry OBJECT-TYPE
   SYNTAX     MscFrMuxDlciStatsEntry
   ACCESS     not-accessible
   STATUS     mandatory
   DESCRIPTION
     "An entry in the mscFrMuxDlciStatsTable."
   INDEX {
      mscFrMuxIndex,
      mscFrMuxDlciIndex }
::= { mscFrMuxDlciStatsTable 1 }

MscFrMuxDlciStatsEntry ::= SEQUENCE {
   mscFrMuxDlciFrmToIf
      Counter32,
   mscFrMuxDlciBytesToIf
      PassportCounter64,
   mscFrMuxDlciFrmFromIf
      Counter32,
   mscFrMuxDlciDeFrmFromIf
      Counter32,
   mscFrMuxDlciBytesFromIf
      PassportCounter64,
   mscFrMuxDlciDeBytesFromIf
      PassportCounter64,
   mscFrMuxDlciFecnFrmToIf
      Counter32,
   mscFrMuxDlciFecnFrmFromIf
      Counter32,
   mscFrMuxDlciBecnFrmToIf
      Counter32,
   mscFrMuxDlciBecnFrmFromIf
      Counter32,
   mscFrMuxDlciDiscCongestedFromIf
      Counter32,
   mscFrMuxDlciDiscCongestedFromIfBytes
      Counter32,
   mscFrMuxDlciDiscDeCongestedFromIf
      Counter32,
   mscFrMuxDlciDiscDeCongestedFromIfBytes
      Counter32,
   mscFrMuxDlciErrorShortFrmFromIf
      Counter32,
   mscFrMuxDlciErrorLongFrmFromIf
      Counter32 }

mscFrMuxDlciFrmToIf OBJECT-TYPE
   SYNTAX     Counter32 
   ACCESS     read-only
   STATUS     mandatory
   DESCRIPTION
     "This attribute counts the frames sent to the interface. When the 
      maximum count is reached the count wraps to zero."
::= { mscFrMuxDlciStatsEntry 1 }

mscFrMuxDlciBytesToIf OBJECT-TYPE
   SYNTAX     PassportCounter64 
   ACCESS     read-only
   STATUS     mandatory
   DESCRIPTION
     "This attribute counts the bytes sent to the interface. When the 
      maximum count is reached the count wraps to zero."
::= { mscFrMuxDlciStatsEntry 2 }

mscFrMuxDlciFrmFromIf OBJECT-TYPE
   SYNTAX     Counter32 
   ACCESS     read-only
   STATUS     mandatory
   DESCRIPTION
     "This attribute counts the frames received from the interface. Frames 
      that are discarded are not included in this count. When the 
      maximum count is reached the count wraps to zero."
::= { mscFrMuxDlciStatsEntry 3 }

mscFrMuxDlciDeFrmFromIf OBJECT-TYPE
   SYNTAX     Counter32 
   ACCESS     read-only
   STATUS     mandatory
   DESCRIPTION
     "This attribute counts the frames received from the interface with the 
      Discard Eligibility (DE) bit set. When the count reaches maximum 
      it wraps to zero."
::= { mscFrMuxDlciStatsEntry 4 }

mscFrMuxDlciBytesFromIf OBJECT-TYPE
   SYNTAX     PassportCounter64 
   ACCESS     read-only
   STATUS     mandatory
   DESCRIPTION
     "This attribute counts the bytes received from the interface. Frames 
      that are discarded are not included in this count. When the 
      maximum count is reached the count wraps to zero."
::= { mscFrMuxDlciStatsEntry 5 }

mscFrMuxDlciDeBytesFromIf OBJECT-TYPE
   SYNTAX     PassportCounter64 
   ACCESS     read-only
   STATUS     mandatory
   DESCRIPTION
     "This attribute counts the bytes received from the interface with the 
      Discard Eligibility (DE) bit set. When the count reaches maximum 
      it wraps to zero."
::= { mscFrMuxDlciStatsEntry 6 }

mscFrMuxDlciFecnFrmToIf OBJECT-TYPE
   SYNTAX     Counter32 
   ACCESS     read-only
   STATUS     mandatory
   DESCRIPTION
     "This attribute counts the frames sent to the interface with the 
      Forward Explicit Congestion Notification (FECN) bit set. When the 
      count reaches maximum it wraps to zero."
::= { mscFrMuxDlciStatsEntry 7 }

mscFrMuxDlciFecnFrmFromIf OBJECT-TYPE
   SYNTAX     Counter32 
   ACCESS     read-only
   STATUS     mandatory
   DESCRIPTION
     "This attribute counts the frames received from the interface with the 
      Forward Explicit Congestion Notification (FECN) bit set. When the 
      count reaches maximum it wraps to zero."
::= { mscFrMuxDlciStatsEntry 8 }

mscFrMuxDlciBecnFrmToIf OBJECT-TYPE
   SYNTAX     Counter32 
   ACCESS     read-only
   STATUS     mandatory
   DESCRIPTION
     "This attribute counts the frames sent to the interface with the 
      Backward Explicit Congestion Notification (BECN) bit set. When 
      the count reaches maximum it wraps to zero."
::= { mscFrMuxDlciStatsEntry 9 }

mscFrMuxDlciBecnFrmFromIf OBJECT-TYPE
   SYNTAX     Counter32 
   ACCESS     read-only
   STATUS     mandatory
   DESCRIPTION
     "This attribute counts the frames received from the interface with the 
      Backward Explicit Congestion Notification (BECN) bit set. When 
      the count reaches maximum it wraps to zero."
::= { mscFrMuxDlciStatsEntry 10 }

mscFrMuxDlciDiscCongestedFromIf OBJECT-TYPE
   SYNTAX     Counter32 
   ACCESS     read-only
   STATUS     mandatory
   DESCRIPTION
     "This attribute counts the number of frames discarded in the receive 
      direction due to local congestion. When this count reaches 
      maximum, it wraps to zero."
::= { mscFrMuxDlciStatsEntry 11 }

mscFrMuxDlciDiscCongestedFromIfBytes OBJECT-TYPE
   SYNTAX     Counter32 
   ACCESS     read-only
   STATUS     mandatory
   DESCRIPTION
     "This attribute counts the number of bytes discarded in the receive 
      direction due to local congestion. When this count reaches 
      maximum, it wraps to zero."
::= { mscFrMuxDlciStatsEntry 12 }

mscFrMuxDlciDiscDeCongestedFromIf OBJECT-TYPE
   SYNTAX     Counter32 
   ACCESS     read-only
   STATUS     mandatory
   DESCRIPTION
     "This attribute counts the number of discard eligible (DE=1) frames 
      discarded in the receive direction due to local congestion. When this 
      count reaches maximum, it wraps to zero."
::= { mscFrMuxDlciStatsEntry 13 }

mscFrMuxDlciDiscDeCongestedFromIfBytes OBJECT-TYPE
   SYNTAX     Counter32 
   ACCESS     read-only
   STATUS     mandatory
   DESCRIPTION
     "This attribute counts the number of bytes of discard eligible (DE=1) 
      traffic discarded in the receive direction due to local congestion. 
      When the maximum count is reached the count wraps to zero."
::= { mscFrMuxDlciStatsEntry 14 }

mscFrMuxDlciErrorShortFrmFromIf OBJECT-TYPE
   SYNTAX     Counter32 
   ACCESS     read-only
   STATUS     mandatory
   DESCRIPTION
     "This attribute counts the frames received with 0 octets in the 
      information field. When the count reaches maximum it wraps to 
      zero."
::= { mscFrMuxDlciStatsEntry 15 }

mscFrMuxDlciErrorLongFrmFromIf OBJECT-TYPE
   SYNTAX     Counter32 
   ACCESS     read-only
   STATUS     mandatory
   DESCRIPTION
     "This attribute counts the frames received with number of octets in 
      the information field greater than the maximum frame size 
      provisioned in the component pointed to by the applicationName. 
      When the count reaches maximum it wraps to zero. Frames whose 
      lengths are greater than the hardware receive buffer are discarded by 
      the Framer and are therefore not included in this count."
::= { mscFrMuxDlciStatsEntry 16 }


-- FrMux/n Dlci/n ApplicationInfo
-- This component contains provisionable attributes of this Dlci.

mscFrMuxDlciApplInfo OBJECT IDENTIFIER ::= { mscFrMuxDlci 2 }



mscFrMuxDlciApplInfoRowStatusTable OBJECT-TYPE
   SYNTAX     SEQUENCE OF MscFrMuxDlciApplInfoRowStatusEntry
   ACCESS     not-accessible
   STATUS     mandatory
   DESCRIPTION
     "This entry controls the addition and deletion of 
      mscFrMuxDlciApplInfo components."
::= { mscFrMuxDlciApplInfo 1 }

mscFrMuxDlciApplInfoRowStatusEntry OBJECT-TYPE
   SYNTAX     MscFrMuxDlciApplInfoRowStatusEntry
   ACCESS     not-accessible
   STATUS     mandatory
   DESCRIPTION
     "A single entry in the table represents a single 
      mscFrMuxDlciApplInfo component."
   INDEX {
      mscFrMuxIndex,
      mscFrMuxDlciIndex,
      mscFrMuxDlciApplInfoIndex }
::= { mscFrMuxDlciApplInfoRowStatusTable 1 }

MscFrMuxDlciApplInfoRowStatusEntry ::= SEQUENCE {
   mscFrMuxDlciApplInfoRowStatus
      RowStatus,
   mscFrMuxDlciApplInfoComponentName
      DisplayString,
   mscFrMuxDlciApplInfoStorageType
      StorageType,
   mscFrMuxDlciApplInfoIndex
      NonReplicated }

mscFrMuxDlciApplInfoRowStatus OBJECT-TYPE
   SYNTAX     RowStatus 
   ACCESS     read-only
   STATUS     mandatory
   DESCRIPTION
     "This variable is used as the basis for SNMP naming of
      mscFrMuxDlciApplInfo components.
      These components cannot be added nor deleted."
::= { mscFrMuxDlciApplInfoRowStatusEntry 1 }

mscFrMuxDlciApplInfoComponentName OBJECT-TYPE
   SYNTAX     DisplayString 
   ACCESS     read-only
   STATUS     mandatory
   DESCRIPTION
     "This variable provides the component's string name for
      use with the ASCII Console Interface"
::= { mscFrMuxDlciApplInfoRowStatusEntry 2 }

mscFrMuxDlciApplInfoStorageType OBJECT-TYPE
   SYNTAX     StorageType 
   ACCESS     read-only
   STATUS     mandatory
   DESCRIPTION
     "This variable represents the storage type value for the
      mscFrMuxDlciApplInfo tables."
::= { mscFrMuxDlciApplInfoRowStatusEntry 4 }

mscFrMuxDlciApplInfoIndex OBJECT-TYPE
   SYNTAX     NonReplicated 
   ACCESS     not-accessible
   STATUS     mandatory
   DESCRIPTION
     "This variable represents the index for the mscFrMuxDlciApplInfo tables."
::= { mscFrMuxDlciApplInfoRowStatusEntry 10 }

mscFrMuxDlciApplInfoProvTable OBJECT-TYPE
   SYNTAX     SEQUENCE OF MscFrMuxDlciApplInfoProvEntry
   ACCESS     not-accessible
   STATUS     mandatory
   DESCRIPTION
     "This group contains provisionable attributes of this Dlci."
::= { mscFrMuxDlciApplInfo 11 }

mscFrMuxDlciApplInfoProvEntry OBJECT-TYPE
   SYNTAX     MscFrMuxDlciApplInfoProvEntry
   ACCESS     not-accessible
   STATUS     mandatory
   DESCRIPTION
     "An entry in the mscFrMuxDlciApplInfoProvTable."
   INDEX {
      mscFrMuxIndex,
      mscFrMuxDlciIndex,
      mscFrMuxDlciApplInfoIndex }
::= { mscFrMuxDlciApplInfoProvTable 1 }

MscFrMuxDlciApplInfoProvEntry ::= SEQUENCE {
   mscFrMuxDlciApplInfoApplicationName
      Link }

mscFrMuxDlciApplInfoApplicationName OBJECT-TYPE
   SYNTAX     Link 
   ACCESS     read-write
   STATUS     mandatory
   DESCRIPTION
     "This attribute is the link to the application associated with this Dlci."
::= { mscFrMuxDlciApplInfoProvEntry 1 }




-- 
-- Version and Compliance statements
-- 



-- Object-Group Statement:
-- A list of all current accessible leaf objects.

-- OBJECTS { mscFrMuxDlciErrorShortFrmFromIf,
--           mscFrMuxDlciComponentName,
--           mscFrMuxCustomerIdentifier,
--           mscFrMuxLmiFullStatusEnqToIf,
--           mscFrMuxFramerNonOctetErrors,
--           mscFrMuxFramerDataInversion,
--           mscFrMuxFramerUsageState,
--           mscFrMuxLmiSequenceErrors,
--           mscFrMuxFramerNormPrioLinkUtilFromIf,
--           mscFrMuxDlciApplInfoStorageType,
--           mscFrMuxAdminState,
--           mscFrMuxFramerComponentName,
--           mscFrMuxUsageState,
--           mscFrMuxDlciOperationalState,
--           mscFrMuxDlciDeBytesFromIf,
--           mscFrMuxDlciDiscCongestedFromIfBytes,
--           mscFrMuxFramerInterfaceName,
--           mscFrMuxComponentName,
--           mscFrMuxLmiStorageType,
--           mscFrMuxProceduralStatus,
--           mscFrMuxFramerUnderruns,
--           mscFrMuxUnknownDlciFramesFromIf,
--           mscFrMuxDlciDeFrmFromIf,
--           mscFrMuxFramerOperationalState,
--           mscFrMuxDlciErrorLongFrmFromIf,
--           mscFrMuxOperationalState,
--           mscFrMuxFramerFrmModeErrors,
--           mscFrMuxLmiProtocolStatus,
--           mscFrMuxDlciBecnFrmFromIf,
--           mscFrMuxLmiAdminState,
--           mscFrMuxInvalidHeaderFramesFromIf,
--           mscFrMuxFramerLrcErrors,
--           mscFrMuxDlciFecnFrmFromIf,
--           mscFrMuxFramerFrmFromIf64,
--           mscFrMuxDlciApplInfoRowStatus,
--           mscFrMuxDlciFrmToIf,
--           mscFrMuxLmiRowStatus,
--           mscFrMuxLmiUsageState,
--           mscFrMuxFramerAborts,
--           mscFrMuxLmiEventCount,
--           mscFrMuxDlciBytesFromIf,
--           mscFrMuxLmiLinkVerificationTimer,
--           mscFrMuxDlciBecnFrmToIf,
--           mscFrMuxAvailabilityStatus,
--           mscFrMuxDlciFrmFromIf,
--           mscFrMuxFramerOctetFromIf64,
--           mscFrMuxRowStatus,
--           mscFrMuxSnmpOperStatus,
--           mscFrMuxLmiUnexpectedIes,
--           mscFrMuxIfIndex,
--           mscFrMuxDlciAdminState,
--           mscFrMuxAlarmStatus,
--           mscFrMuxLmiComponentName,
--           mscFrMuxLmiErrorEventThreshold,
--           mscFrMuxLastUnknownDlci,
--           mscFrMuxDlciApplInfoApplicationName,
--           mscFrMuxLmiKeepAliveStatusEnqToIf,
--           mscFrMuxUnknownStatus,
--           mscFrMuxStandbyStatus,
--           mscFrMuxLmiProcedures,
--           mscFrMuxDlciDiscDeCongestedFromIf,
--           mscFrMuxFramerFlagsBetweenFrames,
--           mscFrMuxStorageType,
--           mscFrMuxLmiProtocolErrors,
--           mscFrMuxLmiOperationalState,
--           mscFrMuxLmiUnexpectedReports,
--           mscFrMuxFramerCrcErrors,
--           mscFrMuxLmiFullStatusPollingCycles,
--           mscFrMuxDlciStorageType,
--           mscFrMuxDlciApplInfoComponentName,
--           mscFrMuxDlciDiscDeCongestedFromIfBytes,
--           mscFrMuxTimeFramerCongested,
--           mscFrMuxDlciRowStatus,
--           mscFrMuxFramerNormPrioLinkUtilToIf,
--           mscFrMuxFramerFrameCrcType,
--           mscFrMuxFramerAdminState,
--           mscFrMuxDlciApplicationName,
--           mscFrMuxDlciDiscCongestedFromIf,
--           mscFrMuxDlciBytesToIf,
--           mscFrMuxControlStatus,
--           mscFrMuxFramerLargeFrmErrors,
--           mscFrMuxFramerStorageType,
--           mscFrMuxDlciFecnFrmToIf,
--           mscFrMuxFramerRowStatus,
--           mscFrMuxFramerFrmToIf64,
--           mscFrMuxDlciABitStatusFromIf,
--           mscFrMuxLmiNoStatusReportCount,
--           mscFrMuxDlciUsageState,
--           mscFrMuxIfAdminStatus,
--           mscFrMuxFramerOverruns }
-- STATUS  mandatory
-- DESCRIPTION
--   "A list of all current accessible leaf objects."

frameRelayMuxGroup OBJECT IDENTIFIER ::= { frameRelayMuxMIB 1 }
frameRelayMuxGroupCA OBJECT IDENTIFIER ::= { frameRelayMuxGroup 1 }
frameRelayMuxGroupCA02 OBJECT IDENTIFIER ::= { frameRelayMuxGroupCA 3 }
frameRelayMuxGroupCA02A OBJECT IDENTIFIER ::= { frameRelayMuxGroupCA02 2 }



-- Agent-Capabilities Statement:

-- PRODUCT-RELEASE "MscPassport Release 1.2 FrameRelayMux."
-- STATUS          mandatory
-- DESCRIPTION     "Carrier Passport FrameRelayMux MIB: MIB Version CA02A,
--                  Software Version CA02S9C."
-- SUPPORTS        Nortel-MsCarrier-MscPassport-FrameRelayMuxMIB
--    INCLUDES     { frameRelayMuxGroupCA02A }

frameRelayMuxCapabilities OBJECT IDENTIFIER ::= { frameRelayMuxMIB 3 }
frameRelayMuxCapabilitiesCA OBJECT IDENTIFIER ::= { frameRelayMuxCapabilities 1 }
frameRelayMuxCapabilitiesCA02 OBJECT IDENTIFIER ::= { frameRelayMuxCapabilitiesCA 3 }
frameRelayMuxCapabilitiesCA02A OBJECT IDENTIFIER ::= { frameRelayMuxCapabilitiesCA02 2 }





END
