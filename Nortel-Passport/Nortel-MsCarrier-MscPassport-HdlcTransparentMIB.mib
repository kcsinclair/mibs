Nortel-MsCarrier-MscPassport-HdlcTransparentMIB
DEFINITIONS ::= BEGIN



IMPORTS

      OBJECT-TYPE
   FROM RFC-1212

      mscPassportMIBs,
      mscComponents
   FROM Nortel-MsCarrier-MscPassport-UsefulDefinitionsMIB

      Counter32,
      DisplayString,
      StorageType,
      RowStatus,
      InterfaceIndex,
      Gauge32,
      Integer32,
      Unsigned32
   FROM Nortel-MsCarrier-MscPassport-StandardTextualConventionsMIB

      AsciiString,
      NonReplicated,
      EnterpriseDateAndTime,
      PassportCounter64,
      Link
   FROM Nortel-MsCarrier-MscPassport-TextualConventionsMIB;




-- LAST-UPDATED   "9909010000Z"
-- ORGANIZATION   "Nortel Networks"
-- CONTACT-INFO   "
--         Nortel Carrier Data Network Management
--         
--         Postal:       P.O. Box 3511, Station C 
--                       Ottawa, Ontario 
--                       Canada  K1Y 4H7
--         
--         via the WEB:  http://www.nortelnetworks.com  
--                       select 'Contact Us' from the menu
--          
--         via phone:    1-800-4NORTEL"
-- DESCRIPTION
--    "The module describing the Nortel MsCarrier MscPassport
--     HdlcTransparent Enterprise MIB."

hdlcTransparentMIB OBJECT IDENTIFIER ::= { mscPassportMIBs 47 }










-- HTDS/<n>
-- The HDLC Transparent Data Service (HTDS) component defines 
-- the characteristics of an instance of the HDLC transparent data 
-- service.
-- One instance of this component is required by each DS1, E1, V35 
-- or V11 channel which is offering HDLC transparent traffic.
-- The instance number is arbitrary.

mscHtds OBJECT IDENTIFIER ::= { mscComponents 82 }



mscHtdsRowStatusTable OBJECT-TYPE
   SYNTAX     SEQUENCE OF MscHtdsRowStatusEntry
   ACCESS     not-accessible
   STATUS     mandatory
   DESCRIPTION
     "This entry controls the addition and deletion of 
      mscHtds components."
::= { mscHtds 1 }

mscHtdsRowStatusEntry OBJECT-TYPE
   SYNTAX     MscHtdsRowStatusEntry
   ACCESS     not-accessible
   STATUS     mandatory
   DESCRIPTION
     "A single entry in the table represents a single 
      mscHtds component."
   INDEX {
      mscHtdsIndex }
::= { mscHtdsRowStatusTable 1 }

MscHtdsRowStatusEntry ::= SEQUENCE {
   mscHtdsRowStatus
      RowStatus,
   mscHtdsComponentName
      DisplayString,
   mscHtdsStorageType
      StorageType,
   mscHtdsIndex
      Integer32 }

mscHtdsRowStatus OBJECT-TYPE
   SYNTAX     RowStatus 
   ACCESS     read-write
   STATUS     mandatory
   DESCRIPTION
     "This variable is used as the basis for SNMP naming of
      mscHtds components.
      These components can be added and deleted."
::= { mscHtdsRowStatusEntry 1 }

mscHtdsComponentName OBJECT-TYPE
   SYNTAX     DisplayString 
   ACCESS     read-only
   STATUS     mandatory
   DESCRIPTION
     "This variable provides the component's string name for
      use with the ASCII Console Interface"
::= { mscHtdsRowStatusEntry 2 }

mscHtdsStorageType OBJECT-TYPE
   SYNTAX     StorageType 
   ACCESS     read-only
   STATUS     mandatory
   DESCRIPTION
     "This variable represents the storage type value for the
      mscHtds tables."
::= { mscHtdsRowStatusEntry 4 }

mscHtdsIndex OBJECT-TYPE
   SYNTAX     Integer32 (1..65535)
   ACCESS     not-accessible
   STATUS     mandatory
   DESCRIPTION
     "This variable represents the index for the mscHtds tables."
::= { mscHtdsRowStatusEntry 10 }

mscHtdsCidDataTable OBJECT-TYPE
   SYNTAX     SEQUENCE OF MscHtdsCidDataEntry
   ACCESS     not-accessible
   STATUS     mandatory
   DESCRIPTION
     "This group contains the attribute for a component's Customer 
      Identifier (CID). Refer to the attribute description for a detailed 
      explanation of CIDs."
::= { mscHtds 10 }

mscHtdsCidDataEntry OBJECT-TYPE
   SYNTAX     MscHtdsCidDataEntry
   ACCESS     not-accessible
   STATUS     mandatory
   DESCRIPTION
     "An entry in the mscHtdsCidDataTable."
   INDEX {
      mscHtdsIndex }
::= { mscHtdsCidDataTable 1 }

MscHtdsCidDataEntry ::= SEQUENCE {
   mscHtdsCustomerIdentifier
      Unsigned32 }

mscHtdsCustomerIdentifier OBJECT-TYPE
   SYNTAX     Unsigned32 (0 | 1..8191)
   ACCESS     read-write
   STATUS     mandatory
   DESCRIPTION
     "This attribute holds the Customer Identifier (CID).
      
      Every component has a CID. If a component has a cid attribute, the 
      component's CID is the provisioned value of that attribute; 
      otherwise the component inherits the CID of its parent. The top-
      level component has a CID of 0.
      
      Every operator session also has a CID, which is the CID 
      provisioned for the operator's user ID. An operator will see only the 
      stream data for components having a matching CID. Also, the 
      operator will be allowed to issue commands for only those 
      components which have a matching CID.
      
      An operator CID of 0 is used to identify the Network Manager 
      (referred to as 'NetMan' in DPN). This CID matches the CID of 
      any component. Values 1 to 8191 inclusive (equivalent to 'basic 
      CIDs' in DPN) may be assigned to specific customers."
   DEFVAL     { 0 }
::= { mscHtdsCidDataEntry 1 }

mscHtdsIfEntryTable OBJECT-TYPE
   SYNTAX     SEQUENCE OF MscHtdsIfEntryEntry
   ACCESS     not-accessible
   STATUS     mandatory
   DESCRIPTION
     "This group contains the provisionable attributes for the ifEntry."
::= { mscHtds 11 }

mscHtdsIfEntryEntry OBJECT-TYPE
   SYNTAX     MscHtdsIfEntryEntry
   ACCESS     not-accessible
   STATUS     mandatory
   DESCRIPTION
     "An entry in the mscHtdsIfEntryTable."
   INDEX {
      mscHtdsIndex }
::= { mscHtdsIfEntryTable 1 }

MscHtdsIfEntryEntry ::= SEQUENCE {
   mscHtdsIfAdminStatus
      INTEGER,
   mscHtdsIfIndex
      InterfaceIndex }

mscHtdsIfAdminStatus OBJECT-TYPE
   SYNTAX     INTEGER  {
                 up(1),
                 down(2),
                 testing(3) }
   ACCESS     read-write
   STATUS     mandatory
   DESCRIPTION
     "The desired state of the interface. The up state indicates the 
      interface is operational. The down state indicates the interface is not 
      operational. The testing state indicates that no operational packets 
      can be passed."
   DEFVAL     { up }
::= { mscHtdsIfEntryEntry 1 }

mscHtdsIfIndex OBJECT-TYPE
   SYNTAX     InterfaceIndex (1..65535)
   ACCESS     read-only
   STATUS     mandatory
   DESCRIPTION
     "This is the index for the IfEntry. Its value is automatically initialized 
      during the provisioning process."
::= { mscHtdsIfEntryEntry 2 }

mscHtdsOperStatusTable OBJECT-TYPE
   SYNTAX     SEQUENCE OF MscHtdsOperStatusEntry
   ACCESS     not-accessible
   STATUS     mandatory
   DESCRIPTION
     "This group includes the Operational Status attribute. This attribute 
      defines the current operational state of this component."
::= { mscHtds 12 }

mscHtdsOperStatusEntry OBJECT-TYPE
   SYNTAX     MscHtdsOperStatusEntry
   ACCESS     not-accessible
   STATUS     mandatory
   DESCRIPTION
     "An entry in the mscHtdsOperStatusTable."
   INDEX {
      mscHtdsIndex }
::= { mscHtdsOperStatusTable 1 }

MscHtdsOperStatusEntry ::= SEQUENCE {
   mscHtdsSnmpOperStatus
      INTEGER }

mscHtdsSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { mscHtdsOperStatusEntry 1 }

mscHtdsStateTable OBJECT-TYPE
   SYNTAX     SEQUENCE OF MscHtdsStateEntry
   ACCESS     not-accessible
   STATUS     mandatory
   DESCRIPTION
     "This group contains the three OSI State attributes and the six OSI 
      Status attributes. The descriptions generically indicate what each 
      attribute implies about the component. Note that not all the values 
      and state combinations described here are supported by every 
      component which uses this group. For component-specific 
      information and the valid state combinations, refer to NTP 241-
      7001-150, Passport Operations and Maintenance Guide."
::= { mscHtds 13 }

mscHtdsStateEntry OBJECT-TYPE
   SYNTAX     MscHtdsStateEntry
   ACCESS     not-accessible
   STATUS     mandatory
   DESCRIPTION
     "An entry in the mscHtdsStateTable."
   INDEX {
      mscHtdsIndex }
::= { mscHtdsStateTable 1 }

MscHtdsStateEntry ::= SEQUENCE {
   mscHtdsAdminState
      INTEGER,
   mscHtdsOperationalState
      INTEGER,
   mscHtdsUsageState
      INTEGER,
   mscHtdsAvailabilityStatus
      OCTET STRING,
   mscHtdsProceduralStatus
      OCTET STRING,
   mscHtdsControlStatus
      OCTET STRING,
   mscHtdsAlarmStatus
      OCTET STRING,
   mscHtdsStandbyStatus
      INTEGER,
   mscHtdsUnknownStatus
      INTEGER }

mscHtdsAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component.
      
      The OSI Status attributes, if supported by the component, may 
      provide more details, qualifying the state of the component."
   DEFVAL     { unlocked }
::= { mscHtdsStateEntry 1 }

mscHtdsOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle.
      
      The OSI Status attributes, if supported by the component, may 
      provide more details, qualifying the state of the component."
   DEFVAL     { disabled }
::= { mscHtdsStateEntry 2 }

mscHtdsUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time.
      
      The OSI Status attributes, if supported by the component, may 
      provide more details, qualifying the state of the component."
   DEFVAL     { idle }
::= { mscHtdsStateEntry 3 }

mscHtdsAvailabilityStatus OBJECT-TYPE
   SYNTAX     OCTET STRING (SIZE (2))
   ACCESS     read-only
   STATUS     mandatory
   DESCRIPTION
     "If supported by the component, this attribute indicates the OSI 
      Availability status of the component. Note that, even though it is 
      defined as a multi-valued set, at most one value is shown to the user.
      
      When no values are in the set, this indicates that either the attribute 
      is not supported or that none of the status conditions described 
      below are present.
      
      The value inTest indicates that the resource is undergoing a test 
      procedure. If adminState is locked or shuttingDown, the normal 
      users are precluded from using the resource and controlStatus is 
      reservedForTest. Tests that do not exclude additional users can be 
      present in any operational or administrative state but the 
      reservedForTest condition should not be present.
      
      The value failed indicates that the component has an internal fault 
      that prevents it from operating. The operationalState is disabled.
      
      The value dependency indicates that the component cannot operate 
      because some other resource on which it depends is unavailable. 
      The operationalState is disabled.
      
      The value powerOff indicates the resource requires power to be 
      applied and it is not powered on. The operationalState is disabled.
      
      The value offLine indicates the resource requires a routine 
      operation (either manual, automatic, or both) to be performed to 
      place it on-line and make it available for use. The operationalState 
      is disabled.
      
      The value offDuty indicates the resource is inactive in accordance 
      with a predetermined time schedule. In the absence of other 
      disabling conditions, the operationalState is enabled or disabled.
      
      The value degraded indicates the service provided by the 
      component is degraded in some way, such as in speed or operating 
      capacity. However, the resource remains available for service. The 
      operationalState is enabled.
      
      The value notInstalled indicates the resource is not present. The 
      operationalState is disabled.
      
      The value logFull is not used.

      Description of bits:
      inTest(0)
      failed(1)
      powerOff(2)
      offLine(3)
      offDuty(4)
      dependency(5)
      degraded(6)
      notInstalled(7)
      logFull(8)"
::= { mscHtdsStateEntry 4 }

mscHtdsProceduralStatus OBJECT-TYPE
   SYNTAX     OCTET STRING (SIZE (1))
   ACCESS     read-only
   STATUS     mandatory
   DESCRIPTION
     "If supported by the component, this attribute indicates the OSI 
      Procedural status of the component. Note that, even though it is 
      defined as a multi-valued set, at most one value is shown to the user.
      
      When no values are in the set, this indicates that either the attribute 
      is not supported or that none of the status conditions described 
      below are present.
      
      The value initializationRequired indicates (for a resource which 
      doesn't initialize autonomously) that initialization is required before 
      it can perform its normal functions, and this procedure has not been 
      initiated. The operationalState is disabled.
      
      The value notInitialized indicates (for a resource which does 
      initialize autonomously) that initialization is required before it can 
      perform its normal functions, and this procedure has not been 
      initiated. The operationalState may be enabled or disabled.
      
      The value initializing indicates that initialization has been initiated 
      but is not yet complete. The operationalState may be enabled or 
      disabled.
      
      The value reporting indicates the resource has completed some 
      processing operation and is notifying the results. The 
      operationalState is enabled.
      
      The value terminating indicates the component is in a termination 
      phase. If the resource doesn't reinitialize autonomously, 
      operationalState is disabled; otherwise it is enabled or disabled.

      Description of bits:
      initializationRequired(0)
      notInitialized(1)
      initializing(2)
      reporting(3)
      terminating(4)"
::= { mscHtdsStateEntry 5 }

mscHtdsControlStatus OBJECT-TYPE
   SYNTAX     OCTET STRING (SIZE (1))
   ACCESS     read-only
   STATUS     mandatory
   DESCRIPTION
     "If supported by the component, this attribute indicates the OSI 
      Control status of the component. Note that, even though it is defined 
      as a multi-valued set, at most one value is shown to the user.
      
      When no values are in the set, this indicates that either the attribute 
      is not supported or that none of the status conditions described 
      below are present.
      
      The value subjectToTest indicates the resource is available but tests 
      may be conducted simultaneously at unpredictable times, which 
      may cause it to exhibit unusual characteristics.
      
      The value partOfServicesLocked indicates that part of the service is 
      restricted from users of a resource. The adminState is unlocked.
      
      The value reservedForTest indicates that the component is 
      administratively unavailable because it is undergoing a test 
      procedure. The adminState is locked.
      
      The value suspended indicates that the service has been 
      administratively suspended.

      Description of bits:
      subjectToTest(0)
      partOfServicesLocked(1)
      reservedForTest(2)
      suspended(3)"
::= { mscHtdsStateEntry 6 }

mscHtdsAlarmStatus OBJECT-TYPE
   SYNTAX     OCTET STRING (SIZE (1))
   ACCESS     read-only
   STATUS     mandatory
   DESCRIPTION
     "If supported by the component, this attribute indicates the OSI 
      Alarm status of the component. Note that, even though it is defined 
      as a multi-valued set, at most one value is shown to the user.
      
      When no values are in the set, this indicates that either the attribute 
      is not supported or that none of the status conditions described 
      below are present.
      
      The value underRepair indicates the component is currently being 
      repaired. The operationalState is enabled or disabled.
      
      The value critical indicates one or more critical alarms are 
      outstanding against the component. Other, less severe, alarms may 
      also be outstanding. The operationalState is enabled or disabled.
      
      The value major indicates one or more major alarms are 
      outstanding against the component. Other, less severe, alarms may 
      also be outstanding. The operationalState is enabled or disabled.
      
      The value minor indicates one or more minor alarms are 
      outstanding against the component. Other, less severe, alarms may 
      also be outstanding. The operationalState is enabled or disabled.
      
      The value alarmOutstanding generically indicates that an alarm of 
      some severity is outstanding against the component.

      Description of bits:
      underRepair(0)
      critical(1)
      major(2)
      minor(3)
      alarmOutstanding(4)"
::= { mscHtdsStateEntry 7 }

mscHtdsStandbyStatus OBJECT-TYPE
   SYNTAX     INTEGER  {
                 hotStandby(0),
                 coldStandby(1),
                 providingService(2),
                 notSet(15) }
   ACCESS     read-only
   STATUS     mandatory
   DESCRIPTION
     "If supported by the component, this attribute indicates the OSI 
      Standby status of the component.
      
      The value notSet indicates that either the attribute is not supported 
      or that none of the status conditions described below are present. 
      Note that this is a non-standard value, used because the original 
      specification indicated this attribute was set-valued and thus, did not 
      provide a value to indicate that none of the other three are 
      applicable.
      
      The value hotStandby indicates that the resource is not providing 
      service but will be immediately able to take over the role of the 
      resource to be backed up, without initialization activity, and 
      containing the same information as the resource to be backed up.
      
      The value coldStandby indicates the resource is a backup for 
      another resource but will not be immediately able to take over the 
      role of the backed up resource and will require some initialization 
      activity.
      
      The value providingService indicates that this component, as a 
      backup resource, is currently backing up another resource."
   DEFVAL     { notSet }
::= { mscHtdsStateEntry 8 }

mscHtdsUnknownStatus OBJECT-TYPE
   SYNTAX     INTEGER  {
                 false(0),
                 true(1) }
   ACCESS     read-only
   STATUS     mandatory
   DESCRIPTION
     "This attribute indicates the OSI Unknown status of the component.
      
      The value false indicates that all of the other OSI State and Status 
      attribute values can be considered accurate.
      
      The value true indicates that the actual state of the component is not 
      known for sure."
   DEFVAL     { false }
::= { mscHtdsStateEntry 9 }


-- 
-- Htds/n Framer
-- 
-- The Framer component controls link layer framing for application 
-- components sending and receiving data on a link interface. It is also 
-- through Framer, that an application component is associated with a 
-- specific hardware link interface.
-- 
-- The Framer component provides provisionable attributes related to 
-- datapath aspects of the hardware interface (such as crc and frame 
-- length) rather than interface specific attributes (such as modem 
-- leads and clocking) which are associated with specific hardware 
-- components (such as V35/n or DS1/n). The Framer component also 
-- provides a provisionable attribute which binds the application 
-- component to a specific hardware component.
-- 
-- The Framer component contains operational attributes for link 
-- interface datapath statistics (such as frame counts and aborts).
-- 

mscHtdsFramer OBJECT IDENTIFIER ::= { mscHtds 2 }



mscHtdsFramerRowStatusTable OBJECT-TYPE
   SYNTAX     SEQUENCE OF MscHtdsFramerRowStatusEntry
   ACCESS     not-accessible
   STATUS     mandatory
   DESCRIPTION
     "This entry controls the addition and deletion of 
      mscHtdsFramer components."
::= { mscHtdsFramer 1 }

mscHtdsFramerRowStatusEntry OBJECT-TYPE
   SYNTAX     MscHtdsFramerRowStatusEntry
   ACCESS     not-accessible
   STATUS     mandatory
   DESCRIPTION
     "A single entry in the table represents a single 
      mscHtdsFramer component."
   INDEX {
      mscHtdsIndex,
      mscHtdsFramerIndex }
::= { mscHtdsFramerRowStatusTable 1 }

MscHtdsFramerRowStatusEntry ::= SEQUENCE {
   mscHtdsFramerRowStatus
      RowStatus,
   mscHtdsFramerComponentName
      DisplayString,
   mscHtdsFramerStorageType
      StorageType,
   mscHtdsFramerIndex
      NonReplicated }

mscHtdsFramerRowStatus OBJECT-TYPE
   SYNTAX     RowStatus 
   ACCESS     read-only
   STATUS     mandatory
   DESCRIPTION
     "This variable is used as the basis for SNMP naming of
      mscHtdsFramer components.
      These components cannot be added nor deleted."
::= { mscHtdsFramerRowStatusEntry 1 }

mscHtdsFramerComponentName OBJECT-TYPE
   SYNTAX     DisplayString 
   ACCESS     read-only
   STATUS     mandatory
   DESCRIPTION
     "This variable provides the component's string name for
      use with the ASCII Console Interface"
::= { mscHtdsFramerRowStatusEntry 2 }

mscHtdsFramerStorageType OBJECT-TYPE
   SYNTAX     StorageType 
   ACCESS     read-only
   STATUS     mandatory
   DESCRIPTION
     "This variable represents the storage type value for the
      mscHtdsFramer tables."
::= { mscHtdsFramerRowStatusEntry 4 }

mscHtdsFramerIndex OBJECT-TYPE
   SYNTAX     NonReplicated 
   ACCESS     not-accessible
   STATUS     mandatory
   DESCRIPTION
     "This variable represents the index for the mscHtdsFramer tables."
::= { mscHtdsFramerRowStatusEntry 10 }

mscHtdsFramerProvTable OBJECT-TYPE
   SYNTAX     SEQUENCE OF MscHtdsFramerProvEntry
   ACCESS     not-accessible
   STATUS     mandatory
   DESCRIPTION
     "This group contains the base provisioning data for the Framer 
      component. Application or hardware interface specific provisioning 
      data is contained in other provisionable Framer groups."
::= { mscHtdsFramer 10 }

mscHtdsFramerProvEntry OBJECT-TYPE
   SYNTAX     MscHtdsFramerProvEntry
   ACCESS     not-accessible
   STATUS     mandatory
   DESCRIPTION
     "An entry in the mscHtdsFramerProvTable."
   INDEX {
      mscHtdsIndex,
      mscHtdsFramerIndex }
::= { mscHtdsFramerProvTable 1 }

MscHtdsFramerProvEntry ::= SEQUENCE {
   mscHtdsFramerInterfaceName
      Link }

mscHtdsFramerInterfaceName OBJECT-TYPE
   SYNTAX     Link 
   ACCESS     read-write
   STATUS     mandatory
   DESCRIPTION
     "This attribute contains a hardware component name.
      
      The attribute associates the application with a specific link. This 
      defines the module processor on which Framer's parent component 
      (as well as Framer itself) will run."
::= { mscHtdsFramerProvEntry 1 }

mscHtdsFramerLinkTable OBJECT-TYPE
   SYNTAX     SEQUENCE OF MscHtdsFramerLinkEntry
   ACCESS     not-accessible
   STATUS     mandatory
   DESCRIPTION
     "This group contains attributes defining the framing of data on the 
      link interface."
::= { mscHtdsFramer 11 }

mscHtdsFramerLinkEntry OBJECT-TYPE
   SYNTAX     MscHtdsFramerLinkEntry
   ACCESS     not-accessible
   STATUS     mandatory
   DESCRIPTION
     "An entry in the mscHtdsFramerLinkTable."
   INDEX {
      mscHtdsIndex,
      mscHtdsFramerIndex }
::= { mscHtdsFramerLinkTable 1 }

MscHtdsFramerLinkEntry ::= SEQUENCE {
   mscHtdsFramerDataInversion
      INTEGER,
   mscHtdsFramerNonOctetData
      INTEGER,
   mscHtdsFramerFrameCrcType
      INTEGER,
   mscHtdsFramerFlagsBetweenFrames
      Unsigned32,
   mscHtdsFramerLineSignalTransport
      INTEGER }

mscHtdsFramerDataInversion OBJECT-TYPE
   SYNTAX     INTEGER  {
                 off(0),
                 on(16) }
   ACCESS     read-write
   STATUS     mandatory
   DESCRIPTION
     "This attribute determines whether data bits are to be inverted (1 to 0 
      and 0 to 1) before transmission of frames to the interface. If the 
      value of this attribute is On, the incoming data bits will also be 
      inverted when frames are received from the link before being 
      processed.
      
      This option is typically used in hdlc framing mode when inversion 
      is used to guarantee 1's density.
      
      Note that aborts (in hdlc and interrupting modes) are corrupted 
      when data is inverted."
   DEFVAL     { off }
::= { mscHtdsFramerLinkEntry 2 }

mscHtdsFramerNonOctetData OBJECT-TYPE
   SYNTAX     INTEGER  {
                 no(0),
                 yes(1) }
   ACCESS     read-write
   STATUS     mandatory
   DESCRIPTION
     "This attribute determines whether the data being received has the 
      potential to be non-octet aligned. If it is set to yes, then neither crc 
      checking and generation or abort detection will be functional."
   DEFVAL     { no }
::= { mscHtdsFramerLinkEntry 3 }

mscHtdsFramerFrameCrcType OBJECT-TYPE
   SYNTAX     INTEGER  {
                 crc16(0),
                 crc32(1),
                 noCrc(2) }
   ACCESS     read-write
   STATUS     mandatory
   DESCRIPTION
     "This attribute defines the type of CRC used. 
      
      The CRC value calculated is appended to the end of the frames 
      transmitted to the link. The CRC value is removed from the end of 
      frames received from the link and checked for correctness.
      NoCrc means that CRC is not used."
   DEFVAL     { crc16 }
::= { mscHtdsFramerLinkEntry 4 }

mscHtdsFramerFlagsBetweenFrames OBJECT-TYPE
   SYNTAX     Unsigned32 (1..16)
   ACCESS     read-write
   STATUS     mandatory
   DESCRIPTION
     "This attribute defines the number of flags that are inserted between 
      frames sent to the link interface."
   DEFVAL     { 1 }
::= { mscHtdsFramerLinkEntry 5 }

mscHtdsFramerLineSignalTransport OBJECT-TYPE
   SYNTAX     INTEGER  {
                 off(0),
                 on(1) }
   ACCESS     read-write
   STATUS     mandatory
   DESCRIPTION
     "This attribute determines how modem status lead information on a 
      V35 or V11 port is handled. When the value of the attribute is set to 
      on, line signal changes are passed transparently through the 
      network to the remote end of the connection, where they are passed 
      out on that end's outgoing leads. When the value of the attribute is 
      set to off, line signal changes are not transparently passed through 
      the network. Both ends must be provisioned to support this function 
      for line signal transport to work. It is highly recommended that line 
      signal interpretation is set to 'don't care' on the associated vport 
      component (ie. vport attributes readyLineState and 
      dataTransferLineState)."
   DEFVAL     { off }
::= { mscHtdsFramerLinkEntry 8 }

mscHtdsFramerStateTable OBJECT-TYPE
   SYNTAX     SEQUENCE OF MscHtdsFramerStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscHtdsFramer 12 }

mscHtdsFramerStateEntry OBJECT-TYPE
   SYNTAX     MscHtdsFramerStateEntry
   ACCESS     not-accessible
   STATUS     mandatory
   DESCRIPTION
     "An entry in the mscHtdsFramerStateTable."
   INDEX {
      mscHtdsIndex,
      mscHtdsFramerIndex }
::= { mscHtdsFramerStateTable 1 }

MscHtdsFramerStateEntry ::= SEQUENCE {
   mscHtdsFramerAdminState
      INTEGER,
   mscHtdsFramerOperationalState
      INTEGER,
   mscHtdsFramerUsageState
      INTEGER }

mscHtdsFramerAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscHtdsFramerStateEntry 1 }

mscHtdsFramerOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscHtdsFramerStateEntry 2 }

mscHtdsFramerUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscHtdsFramerStateEntry 3 }

mscHtdsFramerStatsTable OBJECT-TYPE
   SYNTAX     SEQUENCE OF MscHtdsFramerStatsEntry
   ACCESS     not-accessible
   STATUS     mandatory
   DESCRIPTION
     "This group contains the operational statistics data for a Framer 
      component."
::= { mscHtdsFramer 13 }

mscHtdsFramerStatsEntry OBJECT-TYPE
   SYNTAX     MscHtdsFramerStatsEntry
   ACCESS     not-accessible
   STATUS     mandatory
   DESCRIPTION
     "An entry in the mscHtdsFramerStatsTable."
   INDEX {
      mscHtdsIndex,
      mscHtdsFramerIndex }
::= { mscHtdsFramerStatsTable 1 }

MscHtdsFramerStatsEntry ::= SEQUENCE {
   mscHtdsFramerFrmToIf
      Counter32,
   mscHtdsFramerFrmFromIf
      Counter32,
   mscHtdsFramerOctetFromIf
      Counter32,
   mscHtdsFramerAborts
      Counter32,
   mscHtdsFramerCrcErrors
      Counter32,
   mscHtdsFramerLrcErrors
      Counter32,
   mscHtdsFramerNonOctetErrors
      Counter32,
   mscHtdsFramerOverruns
      Counter32,
   mscHtdsFramerUnderruns
      Counter32,
   mscHtdsFramerLargeFrmErrors
      Counter32 }

mscHtdsFramerFrmToIf OBJECT-TYPE
   SYNTAX     Counter32 
   ACCESS     read-only
   STATUS     mandatory
   DESCRIPTION
     "This attribute counts the number of frames transmitted to the link 
      interface by Framer.
      This count wraps to zero after reaching its maximum value."
::= { mscHtdsFramerStatsEntry 1 }

mscHtdsFramerFrmFromIf OBJECT-TYPE
   SYNTAX     Counter32 
   ACCESS     read-only
   STATUS     mandatory
   DESCRIPTION
     "This attribute counts the number of frames received from the link 
      interface by Framer.
      This count wraps to zero after reaching its maximum value."
::= { mscHtdsFramerStatsEntry 2 }

mscHtdsFramerOctetFromIf OBJECT-TYPE
   SYNTAX     Counter32 
   ACCESS     read-only
   STATUS     mandatory
   DESCRIPTION
     "The number of bytes received from the link interface by Framer."
::= { mscHtdsFramerStatsEntry 3 }

mscHtdsFramerAborts OBJECT-TYPE
   SYNTAX     Counter32 
   ACCESS     read-only
   STATUS     mandatory
   DESCRIPTION
     "This attribute counts the total number of aborts received.
      This count wraps to zero after reaching its maximum value."
::= { mscHtdsFramerStatsEntry 4 }

mscHtdsFramerCrcErrors OBJECT-TYPE
   SYNTAX     Counter32 
   ACCESS     read-only
   STATUS     mandatory
   DESCRIPTION
     "This attribute counts the total number of frames with CRC errors.
      This count wraps to zero after reaching its maximum value."
::= { mscHtdsFramerStatsEntry 5 }

mscHtdsFramerLrcErrors OBJECT-TYPE
   SYNTAX     Counter32 
   ACCESS     read-only
   STATUS     mandatory
   DESCRIPTION
     "This attribute counts the total number of frames with LRC errors.
      This count wraps to zero after reaching its maximum value."
::= { mscHtdsFramerStatsEntry 6 }

mscHtdsFramerNonOctetErrors OBJECT-TYPE
   SYNTAX     Counter32 
   ACCESS     read-only
   STATUS     mandatory
   DESCRIPTION
     "This attribute counts the total number of frames that were non octet 
      aligned.
      This count wraps to zero after reaching its maximum value."
::= { mscHtdsFramerStatsEntry 7 }

mscHtdsFramerOverruns OBJECT-TYPE
   SYNTAX     Counter32 
   ACCESS     read-only
   STATUS     mandatory
   DESCRIPTION
     "This attribute counts the total number of frames received from the 
      link for which overruns occurred.
      This count wraps to zero after reaching its maximum value."
::= { mscHtdsFramerStatsEntry 8 }

mscHtdsFramerUnderruns OBJECT-TYPE
   SYNTAX     Counter32 
   ACCESS     read-only
   STATUS     mandatory
   DESCRIPTION
     "This attribute counts the total number of frames transmitted to the 
      link for which underruns occurred.
      This count wraps to zero after reaching its maximum value."
::= { mscHtdsFramerStatsEntry 9 }

mscHtdsFramerLargeFrmErrors OBJECT-TYPE
   SYNTAX     Counter32 
   ACCESS     read-only
   STATUS     mandatory
   DESCRIPTION
     "This attribute counts the total number of frames received which 
      were too large. The frame was longer than 8 kbytes or it contained 
      more than the 255 block hardware limit.
      This count wraps to zero after reaching its maximum value."
::= { mscHtdsFramerStatsEntry 10 }

mscHtdsFramerUtilTable OBJECT-TYPE
   SYNTAX     SEQUENCE OF MscHtdsFramerUtilEntry
   ACCESS     not-accessible
   STATUS     mandatory
   DESCRIPTION
     "This group contains the link utilization operational data for a 
      Framer component."
::= { mscHtdsFramer 14 }

mscHtdsFramerUtilEntry OBJECT-TYPE
   SYNTAX     MscHtdsFramerUtilEntry
   ACCESS     not-accessible
   STATUS     mandatory
   DESCRIPTION
     "An entry in the mscHtdsFramerUtilTable."
   INDEX {
      mscHtdsIndex,
      mscHtdsFramerIndex }
::= { mscHtdsFramerUtilTable 1 }

MscHtdsFramerUtilEntry ::= SEQUENCE {
   mscHtdsFramerNormPrioLinkUtilToIf
      Gauge32,
   mscHtdsFramerNormPrioLinkUtilFromIf
      Gauge32 }

mscHtdsFramerNormPrioLinkUtilToIf OBJECT-TYPE
   SYNTAX     Gauge32 (0..100)
   ACCESS     read-only
   STATUS     mandatory
   DESCRIPTION
     "This attribute is the utilization of the normal priority data sent to the 
      link as a percentage of the available bandwidth allocated for the 
      service on the link. The utilization is the average for the last minute."
   DEFVAL     { 0 }
::= { mscHtdsFramerUtilEntry 1 }

mscHtdsFramerNormPrioLinkUtilFromIf OBJECT-TYPE
   SYNTAX     Gauge32 (0..100)
   ACCESS     read-only
   STATUS     mandatory
   DESCRIPTION
     "This attribute is the utilization of the normal priority data received 
      from the link as a percentage of the available bandwidth allocated 
      for the service on the link. The utilization is the average for the last 
      minute."
   DEFVAL     { 0 }
::= { mscHtdsFramerUtilEntry 3 }


-- Htds/n PLC
-- This is the description of the PLC Component for the Htds service. 

mscHtdsPlc OBJECT IDENTIFIER ::= { mscHtds 3 }



mscHtdsPlcRowStatusTable OBJECT-TYPE
   SYNTAX     SEQUENCE OF MscHtdsPlcRowStatusEntry
   ACCESS     not-accessible
   STATUS     mandatory
   DESCRIPTION
     "This entry controls the addition and deletion of 
      mscHtdsPlc components."
::= { mscHtdsPlc 1 }

mscHtdsPlcRowStatusEntry OBJECT-TYPE
   SYNTAX     MscHtdsPlcRowStatusEntry
   ACCESS     not-accessible
   STATUS     mandatory
   DESCRIPTION
     "A single entry in the table represents a single 
      mscHtdsPlc component."
   INDEX {
      mscHtdsIndex,
      mscHtdsPlcIndex }
::= { mscHtdsPlcRowStatusTable 1 }

MscHtdsPlcRowStatusEntry ::= SEQUENCE {
   mscHtdsPlcRowStatus
      RowStatus,
   mscHtdsPlcComponentName
      DisplayString,
   mscHtdsPlcStorageType
      StorageType,
   mscHtdsPlcIndex
      NonReplicated }

mscHtdsPlcRowStatus OBJECT-TYPE
   SYNTAX     RowStatus 
   ACCESS     read-only
   STATUS     mandatory
   DESCRIPTION
     "This variable is used as the basis for SNMP naming of
      mscHtdsPlc components.
      These components cannot be added nor deleted."
::= { mscHtdsPlcRowStatusEntry 1 }

mscHtdsPlcComponentName OBJECT-TYPE
   SYNTAX     DisplayString 
   ACCESS     read-only
   STATUS     mandatory
   DESCRIPTION
     "This variable provides the component's string name for
      use with the ASCII Console Interface"
::= { mscHtdsPlcRowStatusEntry 2 }

mscHtdsPlcStorageType OBJECT-TYPE
   SYNTAX     StorageType 
   ACCESS     read-only
   STATUS     mandatory
   DESCRIPTION
     "This variable represents the storage type value for the
      mscHtdsPlc tables."
::= { mscHtdsPlcRowStatusEntry 4 }

mscHtdsPlcIndex OBJECT-TYPE
   SYNTAX     NonReplicated 
   ACCESS     not-accessible
   STATUS     mandatory
   DESCRIPTION
     "This variable represents the index for the mscHtdsPlc tables."
::= { mscHtdsPlcRowStatusEntry 10 }

mscHtdsPlcProvTable OBJECT-TYPE
   SYNTAX     SEQUENCE OF MscHtdsPlcProvEntry
   ACCESS     not-accessible
   STATUS     mandatory
   DESCRIPTION
     "This group contains all provisionable attributes for a permanent 
      logical connection. Note that all of the attributes are valid and 
      provisionable on both ends of a connection. However with the 
      exception of remoteName, all operational attributes are derived 
      from the originating end provisioning, which may be either end 
      unless remoteName is not provisioned on one end."
::= { mscHtdsPlc 10 }

mscHtdsPlcProvEntry OBJECT-TYPE
   SYNTAX     MscHtdsPlcProvEntry
   ACCESS     not-accessible
   STATUS     mandatory
   DESCRIPTION
     "An entry in the mscHtdsPlcProvTable."
   INDEX {
      mscHtdsIndex,
      mscHtdsPlcIndex }
::= { mscHtdsPlcProvTable 1 }

MscHtdsPlcProvEntry ::= SEQUENCE {
   mscHtdsPlcRemoteName
      AsciiString,
   mscHtdsPlcSetupPriority
      Unsigned32,
   mscHtdsPlcHoldingPriority
      Unsigned32,
   mscHtdsPlcRequiredTxBandwidth
      Unsigned32,
   mscHtdsPlcRequiredRxBandwidth
      Unsigned32,
   mscHtdsPlcRequiredTrafficType
      INTEGER,
   mscHtdsPlcPermittedTrunkTypes
      OCTET STRING,
   mscHtdsPlcRequiredSecurity
      Unsigned32,
   mscHtdsPlcRequiredCustomerParm
      Unsigned32,
   mscHtdsPlcPathAttributeToMinimize
      INTEGER,
   mscHtdsPlcMaximumAcceptableCost
      Unsigned32,
   mscHtdsPlcMaximumAcceptableDelay
      Unsigned32,
   mscHtdsPlcEmissionPriority
      Unsigned32,
   mscHtdsPlcDiscardPriority
      Unsigned32,
   mscHtdsPlcPathType
      INTEGER,
   mscHtdsPlcPathFailureAction
      INTEGER,
   mscHtdsPlcBumpPreference
      INTEGER,
   mscHtdsPlcOptimization
      INTEGER,
   mscHtdsPlcAddressToCall
      AsciiString,
   mscHtdsPlcLocalAddress
      AsciiString,
   mscHtdsPlcMaximumAcceptableGatewayCost
      Unsigned32 }

mscHtdsPlcRemoteName OBJECT-TYPE
   SYNTAX     AsciiString (SIZE (0..40))
   ACCESS     read-write
   STATUS     mandatory
   DESCRIPTION
     "This attribute is the PLC's remote end point's address in the format 
      of a Passport component name. The syntax of a component is:
      'em/node type/instance'. For an alternative representation of end 
      point's addresses, see addressToCall and localAddress PLC 
      attributes. When using Passport component name representation, 
      end points are identified using a node name and a service name. As 
      an example, the end point component for a third Htds service on 
      node MoonBase is: 'EM/MoonBase HTDS/3'. If the remoteName is 
      provisioned, it must match the name of the remote end or the 
      connection will not be established even if the remote end is 
      provisioned correctly. If no remoteName is provisioned, then this 
      LC will accept connections from any other remote LC and it will 
      not originate calls. Connections establish faster and are unique if 
      both ends are provisioned with remoteName. 
      RemoteName should be used when the remote end of the connection 
      resides within the same topology region. If it resides in a different 
      topology region, then addressToCall and localAddress PLC 
      attributes should be used. When both remoteName and 
      addressToCall are provisioned, addressToCall takes precedence. 
      That is, connection will be established to the service specified by 
      addressToCall.
      These strings are case insensitive, but the complete component 
      name must be input."
   DEFVAL     { ''H }  -- ""
::= { mscHtdsPlcProvEntry 2 }

mscHtdsPlcSetupPriority OBJECT-TYPE
   SYNTAX     Unsigned32 (0..4)
   ACCESS     read-write
   STATUS     mandatory
   DESCRIPTION
     "This attribute gives the priority at which a path is established. 
      Zero(0) is the highest priority and four(4) is the lowest. When 
      PORS establishes a path through the network, it uses the 
      setupPriority attribute to determine its potential for bumping 
      established paths to acquire their bandwidth. The holdingPriority, a 
      complementary attribute of this component, indicates the priority a 
      path maintains once it is established. A new path can bump an 
      existing path if the new path's setupPriority is higher (numerically 
      less) than the existing path's holdingPriority."
   DEFVAL     { 2 }
::= { mscHtdsPlcProvEntry 3 }

mscHtdsPlcHoldingPriority OBJECT-TYPE
   SYNTAX     Unsigned32 (0..4)
   ACCESS     read-write
   STATUS     mandatory
   DESCRIPTION
     "This attribute gives the priority that a path holds once it is 
      established. Zero(0) is the highest priority and four(4) is the lowest. 
      A path's holdingPriority determines its likelihood of being bumped 
      by a new path to acquire its bandwidth. The setupPriority, a 
      complementary attribute, indicates the priority of a path at 
      establishment time. A new path can bump an existing path if the 
      new path's setupPriority is higher (numerically less) than the 
      existing path's holdingPriority."
   DEFVAL     { 2 }
::= { mscHtdsPlcProvEntry 4 }

mscHtdsPlcRequiredTxBandwidth OBJECT-TYPE
   SYNTAX     Unsigned32 (0..4294967295)
   ACCESS     read-write
   STATUS     mandatory
   DESCRIPTION
     "This attribute gives the bandwidth (in bits per second) reserved by a 
      path on each of the trunks of its route. This attribute represents the 
      bandwidth for traffic outgoing to the remote end point. This value 
      should be chosen to achieve the amount of statistical bandwidth 
      sharing that is desired by the network administration. This 
      reservation is not enforced and is used to determine how many paths 
      can be supported on a trunk. Both ends should be provisioned with 
      the correct values allowing for the fact that Transmit at this end 
      represents Receive at the remote end. Note that when the values do 
      not correspond the originating end of the connection determines the 
      value."
   DEFVAL     { 64000 }
::= { mscHtdsPlcProvEntry 5 }

mscHtdsPlcRequiredRxBandwidth OBJECT-TYPE
   SYNTAX     Unsigned32 (0..4294967295)
   ACCESS     read-write
   STATUS     mandatory
   DESCRIPTION
     "This attribute gives the bandwidth (in bits per second) reserved by a 
      path on each of trunks of its route. This attribute represents the 
      bandwidth for traffic incoming from the remote end point. This 
      value should be chosen to achieve the amount of statistical 
      bandwidth sharing that is desired by the network administration. 
      This reservation is not enforced and is used to determine how many 
      paths can be supported on a trunk. Both ends should be provisioned 
      with the correct values allowing for the fact that Transmit at this end 
      represents Receive at the remote end. Note that when the values do 
      not correspond the originating end of the connection determines the 
      value."
   DEFVAL     { 64000 }
::= { mscHtdsPlcProvEntry 6 }

mscHtdsPlcRequiredTrafficType OBJECT-TYPE
   SYNTAX     INTEGER  {
                 voice(0),
                 data(1),
                 video(2),
                 trafficType1(3),
                 trafficType2(4),
                 trafficType3(5),
                 trafficType4(6),
                 trafficType5(7) }
   ACCESS     read-write
   STATUS     mandatory
   DESCRIPTION
     "This attribute indicates the type of traffic transmitted over the path. 
      There are eight(8) possible traffic types, and the path can transmit 
      only one of them. The originating end of the connection determines 
      the type. These are arbitrary designations for traffic type. The voice, 
      data and video traffic types are defined, and five(5) other arbitrary 
      traffic types can be defined by the network administration. This 
      attribute is used in the route selection process to restrict the route to 
      trunks that support this traffic type. The supportedTrafficType trunk 
      attribute lists all the types of traffic allowed on the trunk. For 
      example, if requiredTrafficType is specified as trafficType1 then 
      only trunks that include trafficType1 in supportedTrafficType, will 
      be candidates for this connection."
   DEFVAL     { data }
::= { mscHtdsPlcProvEntry 7 }

mscHtdsPlcPermittedTrunkTypes OBJECT-TYPE
   SYNTAX     OCTET STRING (SIZE (1))
   ACCESS     read-write
   STATUS     mandatory
   DESCRIPTION
     "This attribute lists up to eight(8) types of trunk that can be used on 
      the route. The terrestrial and satellite trunk types have been 
      defined, leaving six(6) remaining arbitrary types that can be defined 
      by the network administration. The trunk's type is indicated in the 
      trunkType attribute of the Trunk component. When selecting a 
      route, PORS only chooses trunks whose trunkType are in the 
      permittedTrunkTypes for the path.

      Description of bits:
      terrestrial(0)
      satellite(1)
      trunkType1(2)
      trunkType2(3)
      trunkType3(4)
      trunkType4(5)
      trunkType5(6)
      trunkType6(7)"
   DEFVAL     { 'f8'H }
::= { mscHtdsPlcProvEntry 8 }

mscHtdsPlcRequiredSecurity OBJECT-TYPE
   SYNTAX     Unsigned32 (0..7)
   ACCESS     read-write
   STATUS     mandatory
   DESCRIPTION
     "This attribute indicates the required minimum level of security of 
      the trunks on the route. Zero(0) represents the most secure and 
      seven(7) represents the least secure. The trunk's security is 
      indicated by the trunkSecurity attribute of the Trunk component, 
      and has values identical in range and meaning to the 
      requiredSecurity attribute. PORS ensures that any route selected 
      does not contain a trunk whose trunkSecurity attribute is 
      numerically greater than the requiredSecurity."
   DEFVAL     { 4 }
::= { mscHtdsPlcProvEntry 9 }

mscHtdsPlcRequiredCustomerParm OBJECT-TYPE
   SYNTAX     Unsigned32 (0..7)
   ACCESS     read-write
   STATUS     mandatory
   DESCRIPTION
     "This attribute indicates the allowed customer defined parameter of 
      the trunks on the route. Its value, a number from zero(0) to 
      seven(7), is chosen by a network administration to have a meaning 
      specific to their network, thus allowing them to customize the use of 
      their trunks. A complementary trunk attribute, customerParameter, 
      also has a value from zero(0) to seven(7). The route selection 
      process does not consider trunks whose customerParameter is 
      greater than the requiredCustomerParameter of the path."
   DEFVAL     { 4 }
::= { mscHtdsPlcProvEntry 10 }

mscHtdsPlcPathAttributeToMinimize OBJECT-TYPE
   SYNTAX     INTEGER  {
                 cost(0),
                 delay(1) }
   ACCESS     read-write
   STATUS     mandatory
   DESCRIPTION
     "This attribute indicates whether a route is selected on the basis of 
      minimizing the cost or the delay. Each trunk has a cost and a delay 
      metric associated with it. The cost or delay of a route is the sum of 
      the cost or delay metrics of all the trunks on the route. The route 
      selection algorithm uses this attribute as the minimization criteria. If 
      more than one route is found while using this attribute as the 
      minimization criteria, then the route with the smallest non-
      minimization metric is chosen amongst the equivalent routes."
   DEFVAL     { cost }
::= { mscHtdsPlcProvEntry 11 }

mscHtdsPlcMaximumAcceptableCost OBJECT-TYPE
   SYNTAX     Unsigned32 (0..65535)
   ACCESS     read-write
   STATUS     mandatory
   DESCRIPTION
     "This attribute indicates an upper bound on the cost metric of a route, 
      which is the sum of the cost metrics of all trunks on the route. The 
      cost metric is the trunkCost attribute of the Trunk component. This 
      attribute is used to accept or reject a path after the route selection 
      algorithm has been applied, regardless of the minimization criteria. 
      It is possible that there may not be a route with an acceptable cost."
   DEFVAL     { 1280 }
::= { mscHtdsPlcProvEntry 12 }

mscHtdsPlcMaximumAcceptableDelay OBJECT-TYPE
   SYNTAX     Unsigned32 (0..100000)
   ACCESS     read-write
   STATUS     mandatory
   DESCRIPTION
     "This attribute indicates an upper bound on the delay of a route, 
      which is the sum of the delay of all trunks on the route. It should be 
      provisioned with a reasonable maximum acceptable delay for the 
      end to end one way delay of a 512 byte packet.
      Note that the delay for a trunk can be a provisioned (with override) 
      or measured value on the trunk. PORs does not recommend using 
      override for the delay on a trunk since this has little added value for 
      PORs traffic.
      Remember, that the trunk measuredRoundTripDelay (ms) 
      discovered through the Trunk staging protocols, divided by two and 
      truncated, to provide the one way delay, is used to populate the 
      topological database. The value includes emission, propagation, and 
      queuing delays. A 512 byte data packet is used to perform the 
      measurement. This value is updated periodically by Trunks and 
      reflects the operating delay of the trunk. PORs uses this attribute to 
      accept or reject a path after the route selection algorithm has been 
      applied, regardless of the minimization criteria."
   DEFVAL     { 100000 }
::= { mscHtdsPlcProvEntry 13 }

mscHtdsPlcEmissionPriority OBJECT-TYPE
   SYNTAX     Unsigned32 (1..2)
   ACCESS     read-write
   STATUS     mandatory
   DESCRIPTION
     "This attribute indicates the urgency with which packets on the path 
      are emitted by the trunks on the route. EmissionPriority of Zero(0) 
      indicates the highest emission priority, while two (2) indicates the 
      lowest emission priority. Packets with a higher emissionPriority (or 
      numerically less) are serviced and sent out before the packets of 
      lower emissionPriority (or numerically higher)."
   DEFVAL     { 1 }
::= { mscHtdsPlcProvEntry 14 }

mscHtdsPlcDiscardPriority OBJECT-TYPE
   SYNTAX     Unsigned32 (1..3)
   ACCESS     read-write
   STATUS     mandatory
   DESCRIPTION
     "This attribute indicates the importance of the packets on the path. 
      One(1) is used for paths carrying the most important traffic, and 
      three(3) is used for paths carrying the least important traffic. 
      Packets with lower discardPriority(numerically higher) are 
      discarded after packets with a higher discardPriority(numerically 
      lower)."
   DEFVAL     { 2 }
::= { mscHtdsPlcProvEntry 15 }

mscHtdsPlcPathType OBJECT-TYPE
   SYNTAX     INTEGER  {
                 normal(0),
                 manual(1),
                 forced(2) }
   ACCESS     read-write
   STATUS     mandatory
   DESCRIPTION
     "This attribute specifies if the path for this PLC is determined 
      automatically or by static provisioning. The default (normal) is to 
      automatically choose a route with Route Selection. Normal 
      pathTypes require less provisioning and can dynamically handle 
      path failures. The other pathTypes are both manual pathTypes 
      where the operator must specify, through provisioning, a static route 
      termed the manualPath. A manual pathType connection is nearly 
      identical to a normal path type connection with the exception that 
      the route is pre-provisioned. For a manual pathType, bandwidth 
      reservations are respected along the path exactly as in a normal 
      path. The last type, the forced pathType, is also a manual path but 
      regardless of the bandwidth available the route is granted provided 
      the trunks are operational and there are sufficient Logical Channels 
      (LChs). 
      The forced pathType could result in over committing the reserved 
      bandwidth allowed on a trunk. A better way to achieve the effects of 
      a forced pathType is to use a manual pathType with setupPriority = 
      0 and holdingPriority = 0. In this manner the path will reserve 
      correct bandwidth and it will bump other paths if required while not 
      being bumped itself."
   DEFVAL     { normal }
::= { mscHtdsPlcProvEntry 16 }

mscHtdsPlcPathFailureAction OBJECT-TYPE
   SYNTAX     INTEGER  {
                 disconnectConnection(0),
                 reRoutePath(1) }
   ACCESS     read-write
   STATUS     mandatory
   DESCRIPTION
     "This attribute is used to specify whether the application can tolerate 
      momentary interruption of a path while a new path is selected. If 
      disconnectConnection is chosen, the application is informed as 
      soon as possible about a failure by disconnection. If the attribute is 
      set to reRoutePath, the path may attempt an immediate reroute, 
      provided the failure is a recoverable failure. If rerouting fails the 
      application is informed of the failure. 
      With this option set to reRoutePath the LCo may wait up to 30 
      seconds before informing the service of complete disconnection in 
      order to allow both ends to attempt to reconnect. Note that if PLC 
      components are different at both ends only the calling end is 
      allowed to reconnect.
      All pathTypes respect this attribute. Also on a manualPath with 
      both ends provisioned with independent paths (at least with respect 
      to the failure) this option will have the desired effect that the path is 
      rerouted without complete disconnection at both ends."
   DEFVAL     { reRoutePath }
::= { mscHtdsPlcProvEntry 17 }

mscHtdsPlcBumpPreference OBJECT-TYPE
   SYNTAX     INTEGER  {
                 bumpWhenNecessary(0),
                 bumpToObtainBestRoute(1) }
   ACCESS     read-write
   STATUS     mandatory
   DESCRIPTION
     "This attribute controls when bumping occurs in the route selection 
      process. A connection with higher (numerically less) setupPriority 
      may bump a connection with lower (numerically higher) 
      holdingPriority in order to acquire its bandwidth and be established. 
      By default, bumping occurs only when it is necessary. That is, a 
      connection will bump another connection only if there is no other 
      way for the connection to be established. A connection may be set 
      to always bump in order to find the best route it may have."
   DEFVAL     { bumpWhenNecessary }
::= { mscHtdsPlcProvEntry 18 }

mscHtdsPlcOptimization OBJECT-TYPE
   SYNTAX     INTEGER  {
                 disabled(0),
                 enabled(1) }
   ACCESS     read-write
   STATUS     mandatory
   DESCRIPTION
     "This attribute is used to specify whether this connection should 
      attempt to optimize its path when requested by the routing PORS 
      component. Every path is as optimal as it can be when it is 
      established, but as network traffic patterns and configurations 
      change this path may no longer be as optimal as it could be. The 
      PORS connection manager on a module requests circuits to 
      optimize at the optimization interval."
   DEFVAL     { enabled }
::= { mscHtdsPlcProvEntry 19 }

mscHtdsPlcAddressToCall OBJECT-TYPE
   SYNTAX     AsciiString (SIZE (0..40))
   ACCESS     read-write
   STATUS     mandatory
   DESCRIPTION
     "This attribute is the PLC's remote end point's address in the format 
      of a NSAP address. As such it must consist of a string of hex digits 
      although not all 40 digits must be specified. For an alternative 
      representation of end point's addresses, see romoteName attribute. 
      If the addressToCall is provisioned, it must match localAddress 
      provisioned on the remote end or the connection will not be 
      established. Connections establish faster and are unique if both ends 
      are provisioned with addressToCall. AddressToCall must be used 
      when the romote end of the connection resides in different topology 
      region. If it resides in the same topology region, then romoteName 
      may be used. When both remoteName and addressToCall are 
      provisioned, addressToCall takes precedence. That is, connection 
      will be established to the service specified by addressToCall."
   DEFVAL     { ''H }  -- ""
::= { mscHtdsPlcProvEntry 20 }

mscHtdsPlcLocalAddress OBJECT-TYPE
   SYNTAX     AsciiString (SIZE (0..40))
   ACCESS     read-write
   STATUS     mandatory
   DESCRIPTION
     "This attribute is the PLC's end point address in the format of an 
      NSAP address. As such it must consist of a string of hex digits 
      although not all 40 digits must be specified. LocalAddress must 
      share a prefix with MOD nodePrefix or one of MOD 
      alternatePorsPrefixes for this node, otherwise PORS will not be able 
      to route calls to this service. LocalAddress is used in conjunction 
      with addressToCall. That is, the end responsible for originating 
      calls must have addressToCall provisioned, while the end 
      responsible for terminationg calls must have localAddress 
      provisioned. In such a case, addressToCall on the originating end 
      must match exactly the localAddress of the terminating end. Note 
      that both ends may be originating and terminating at the same time. 
      That is, both ends may have addressToCall and localAddress 
      provisioned as long as addressToCall and localAddress on different 
      ends are identical."
   DEFVAL     { ''H }  -- ""
::= { mscHtdsPlcProvEntry 21 }

mscHtdsPlcMaximumAcceptableGatewayCost OBJECT-TYPE
   SYNTAX     Unsigned32 (0..65535)
   ACCESS     read-write
   STATUS     mandatory
   DESCRIPTION
     "This attribute indicates an upper bound on the gateway cost metric 
      of a route, which is the sum of the gateway cost metrics of all 
      gateway links on the route. It has the same semantics as the 
      maximumAcceptableCost except that gateway cost metrics are used 
      instead of trunk cost metrics. Gateway cost metrics are provisioned 
      under Trunk Address component of a gateway link specifying a 
      gateway costs of reaching an address through the link."
   DEFVAL     { 2048 }
::= { mscHtdsPlcProvEntry 22 }

mscHtdsPlcMpathTable OBJECT-TYPE
   SYNTAX     SEQUENCE OF MscHtdsPlcMpathEntry
   ACCESS     not-accessible
   STATUS     mandatory
   DESCRIPTION
     "This attribute is optional and specifies the sequence of trunks to be 
      used as the route for the path, thus bypassing PORS' automatic 
      route selection. If the path fails the validation, no other path can be 
      selected1. This attribute should only be used in special cases since 
      the route selection algorithm is able to find and maintain the best 
      routes. A related path attribute, the pathType, determines if this 
      route will be used as a manual or forced path type. 
      As an example, the trunk component name for the third trunk on 
      node MoonBase is 'EM/MoonBase Trk/3'. Note that only the first 
      end of the trunk that the packet would encounter is provisioned. 
      These strings are case insensitive but the complete component name 
      must be input. 
      
      Note 1: the trunk designation must be a 3-letter form, e.g., 'trk'. 
      Note 2: only the outbound trunks component names are used to 
      provision the manualPath.
      
      Note 3: It is recommended to have two independent routes specified 
      for a manual path by specifying a different manualPath (non-
      symmetric) for each end. In this case, there is no way to select 
      which route will be used (first up wins) but if one path is torn down 
      due to a failure then the other manualPath may be used to reroute 
      the path."
::= { mscHtdsPlc 265 }

mscHtdsPlcMpathEntry OBJECT-TYPE
   SYNTAX     MscHtdsPlcMpathEntry
   ACCESS     not-accessible
   STATUS     mandatory
   DESCRIPTION
     "An entry in the mscHtdsPlcMpathTable."
   INDEX {
      mscHtdsIndex,
      mscHtdsPlcIndex,
      mscHtdsPlcMpathIndex }
::= { mscHtdsPlcMpathTable 1 }

MscHtdsPlcMpathEntry ::= SEQUENCE {
   mscHtdsPlcMpathIndex
      Integer32,
   mscHtdsPlcMpathValue
      AsciiString }

mscHtdsPlcMpathIndex OBJECT-TYPE
   SYNTAX     Integer32 (0..9)
   ACCESS     not-accessible
   STATUS     mandatory
   DESCRIPTION
     "This variable represents the mscHtdsPlcMpathTable
      specific index for the mscHtdsPlcMpathTable."
::= { mscHtdsPlcMpathEntry 1 }

mscHtdsPlcMpathValue OBJECT-TYPE
   SYNTAX     AsciiString (SIZE (0..40))
   ACCESS     read-write
   STATUS     mandatory
   DESCRIPTION
     "This variable represents an individual value for the
      mscHtdsPlcMpathTable."
::= { mscHtdsPlcMpathEntry 2 }


-- ...Lc
-- This component contains all of the operation attributes for a Path 
-- Oriented Logical Connection.

mscHtdsLCo OBJECT IDENTIFIER ::= { mscHtds 4 }



mscHtdsLCoRowStatusTable OBJECT-TYPE
   SYNTAX     SEQUENCE OF MscHtdsLCoRowStatusEntry
   ACCESS     not-accessible
   STATUS     mandatory
   DESCRIPTION
     "This entry controls the addition and deletion of 
      mscHtdsLCo components."
::= { mscHtdsLCo 1 }

mscHtdsLCoRowStatusEntry OBJECT-TYPE
   SYNTAX     MscHtdsLCoRowStatusEntry
   ACCESS     not-accessible
   STATUS     mandatory
   DESCRIPTION
     "A single entry in the table represents a single 
      mscHtdsLCo component."
   INDEX {
      mscHtdsIndex,
      mscHtdsLCoIndex }
::= { mscHtdsLCoRowStatusTable 1 }

MscHtdsLCoRowStatusEntry ::= SEQUENCE {
   mscHtdsLCoRowStatus
      RowStatus,
   mscHtdsLCoComponentName
      DisplayString,
   mscHtdsLCoStorageType
      StorageType,
   mscHtdsLCoIndex
      NonReplicated }

mscHtdsLCoRowStatus OBJECT-TYPE
   SYNTAX     RowStatus 
   ACCESS     read-only
   STATUS     mandatory
   DESCRIPTION
     "This variable is used as the basis for SNMP naming of
      mscHtdsLCo components.
      These components cannot be added nor deleted."
::= { mscHtdsLCoRowStatusEntry 1 }

mscHtdsLCoComponentName OBJECT-TYPE
   SYNTAX     DisplayString 
   ACCESS     read-only
   STATUS     mandatory
   DESCRIPTION
     "This variable provides the component's string name for
      use with the ASCII Console Interface"
::= { mscHtdsLCoRowStatusEntry 2 }

mscHtdsLCoStorageType OBJECT-TYPE
   SYNTAX     StorageType 
   ACCESS     read-only
   STATUS     mandatory
   DESCRIPTION
     "This variable represents the storage type value for the
      mscHtdsLCo tables."
::= { mscHtdsLCoRowStatusEntry 4 }

mscHtdsLCoIndex OBJECT-TYPE
   SYNTAX     NonReplicated 
   ACCESS     not-accessible
   STATUS     mandatory
   DESCRIPTION
     "This variable represents the index for the mscHtdsLCo tables."
::= { mscHtdsLCoRowStatusEntry 10 }

mscHtdsLCoPathDataTable OBJECT-TYPE
   SYNTAX     SEQUENCE OF MscHtdsLCoPathDataEntry
   ACCESS     not-accessible
   STATUS     mandatory
   DESCRIPTION
     "This group contains all operational attributes for the path oriented 
      LCo."
::= { mscHtdsLCo 10 }

mscHtdsLCoPathDataEntry OBJECT-TYPE
   SYNTAX     MscHtdsLCoPathDataEntry
   ACCESS     not-accessible
   STATUS     mandatory
   DESCRIPTION
     "An entry in the mscHtdsLCoPathDataTable."
   INDEX {
      mscHtdsIndex,
      mscHtdsLCoIndex }
::= { mscHtdsLCoPathDataTable 1 }

MscHtdsLCoPathDataEntry ::= SEQUENCE {
   mscHtdsLCoState
      INTEGER,
   mscHtdsLCoOverrideRemoteName
      AsciiString,
   mscHtdsLCoEnd
      INTEGER,
   mscHtdsLCoCostMetric
      Unsigned32,
   mscHtdsLCoDelayMetric
      Unsigned32,
   mscHtdsLCoRoundTripDelay
      Unsigned32,
   mscHtdsLCoSetupPriority
      Unsigned32,
   mscHtdsLCoHoldingPriority
      Unsigned32,
   mscHtdsLCoRequiredTxBandwidth
      Gauge32,
   mscHtdsLCoRequiredRxBandwidth
      Gauge32,
   mscHtdsLCoRequiredTrafficType
      INTEGER,
   mscHtdsLCoPermittedTrunkTypes
      OCTET STRING,
   mscHtdsLCoRequiredSecurity
      Unsigned32,
   mscHtdsLCoRequiredCustomerParameter
      Unsigned32,
   mscHtdsLCoEmissionPriority
      Unsigned32,
   mscHtdsLCoDiscardPriority
      Unsigned32,
   mscHtdsLCoPathType
      INTEGER,
   mscHtdsLCoRetryCount
      Unsigned32,
   mscHtdsLCoPathFailureCount
      Unsigned32,
   mscHtdsLCoReasonForNoRoute
      INTEGER,
   mscHtdsLCoLastTearDownReason
      INTEGER,
   mscHtdsLCoPathFailureAction
      INTEGER,
   mscHtdsLCoBumpPreference
      INTEGER,
   mscHtdsLCoOptimization
      INTEGER,
   mscHtdsLCoPathUpDateTime
      EnterpriseDateAndTime }

mscHtdsLCoState OBJECT-TYPE
   SYNTAX     INTEGER  {
                 pathDown(0),
                 selectingRoute(1),
                 connecting(2),
                 pathUp(3),
                 pathDownRetrying(4) }
   ACCESS     read-only
   STATUS     mandatory
   DESCRIPTION
     "This attribute reflects the current state of the connection. The 
      pathDown state indicates a connection that has no remote end 
      provisioned or the application has not yet signalled for a path. The 
      selectingRoute state occurs when a request has been sent to route 
      selector and it has not yet responded. The connectingState occurs 
      while a path is being established. The pathUp state is the normal 
      operational state of a path. The pathDownRetrying state indicates a 
      path that attempted route selection but received no route and is now 
      waiting to retry route selection again."
::= { mscHtdsLCoPathDataEntry 1 }

mscHtdsLCoOverrideRemoteName OBJECT-TYPE
   SYNTAX     AsciiString (SIZE (0..40))
   ACCESS     read-write
   STATUS     mandatory
   DESCRIPTION
     "If set and the current PLC remoteName is blank this remoteName 
      will override the blank PLC remoteName. Usually you would set 
      this attribute and then lock/unlock the service component which 
      will result in this new overrideRemoteName being used as if it had 
      been provisioned into the PLC remoteName. The advantage of this 
      attribute is that the connection's remoteName can be changed 
      immediately without having to 'activate prov' but the disadvantage 
      is that the overrideRemoteName is not permanent and if the card or 
      switch is reset the override will be lost."
::= { mscHtdsLCoPathDataEntry 2 }

mscHtdsLCoEnd OBJECT-TYPE
   SYNTAX     INTEGER  {
                 calling(0),
                 called(1) }
   ACCESS     read-only
   STATUS     mandatory
   DESCRIPTION
     "This attribute identifies whether this is the calling or called end of 
      the path."
::= { mscHtdsLCoPathDataEntry 3 }

mscHtdsLCoCostMetric OBJECT-TYPE
   SYNTAX     Unsigned32 (0..65535)
   ACCESS     read-only
   STATUS     mandatory
   DESCRIPTION
     "This attribute gives the route's total cost metric. It is calculated as 
      the sum of the cost metric of all trunks in the path at the time the 
      connection was established. The cost metric of a trunk is defined by 
      the trunkCost attribute of the Trunk component. The costMetric for 
      an LCo that is originated and terminated on the same module is 0."
::= { mscHtdsLCoPathDataEntry 4 }

mscHtdsLCoDelayMetric OBJECT-TYPE
   SYNTAX     Unsigned32 (0..100000)
   ACCESS     read-only
   STATUS     mandatory
   DESCRIPTION
     "This attribute gives the total delay of the route as the one way delay 
      for a 512 byte packet. It is calculated as the sum of the delays of all 
      trunks in the path stored in topology at the time the connection was 
      established. The delay for an LCo that is originated and terminated 
      on the same module is 0."
::= { mscHtdsLCoPathDataEntry 5 }

mscHtdsLCoRoundTripDelay OBJECT-TYPE
   SYNTAX     Unsigned32 (0..200000)
   ACCESS     read-only
   STATUS     mandatory
   DESCRIPTION
     "This attribute contains the time taken for a packet (cell) of 44 bytes 
      to be transmitted to the remote LCo and return to this LCo. The 
      number reported is given in milliseconds to the nearest millisecond. 
      A value of one millisecond is reported if the time is less than 1 
      millisecond even though the delay may be less than 1 Millisecond 
      when the LCo is originated and terminated on the same module."
::= { mscHtdsLCoPathDataEntry 6 }

mscHtdsLCoSetupPriority OBJECT-TYPE
   SYNTAX     Unsigned32 (0..4)
   ACCESS     read-only
   STATUS     mandatory
   DESCRIPTION
     "This attribute gives the priority at which the current path is 
      established. Zero is the highest priority and four is the lowest. The 
      holdingPriority, a complementary attribute of this component, 
      indicates the priority a path maintains once it is established."
::= { mscHtdsLCoPathDataEntry 7 }

mscHtdsLCoHoldingPriority OBJECT-TYPE
   SYNTAX     Unsigned32 (0..4)
   ACCESS     read-only
   STATUS     mandatory
   DESCRIPTION
     "This attribute gives the priority at which a path holds its current 
      path once the path is established. Zero is the highest priority and 
      four is the lowest. The setupPriority, a complementary attribute, 
      indicates the priority of a path at establishment time."
::= { mscHtdsLCoPathDataEntry 8 }

mscHtdsLCoRequiredTxBandwidth OBJECT-TYPE
   SYNTAX     Gauge32 (0..4294967295)
   ACCESS     read-only
   STATUS     mandatory
   DESCRIPTION
     "This attribute gives the actual bandwidth (in bits per second) 
      reserved by this path on each of the trunks of its route. This attribute 
      represents the bandwidth for traffic outgoing to the remote end 
      point. The originating end of the connection determines this value."
::= { mscHtdsLCoPathDataEntry 9 }

mscHtdsLCoRequiredRxBandwidth OBJECT-TYPE
   SYNTAX     Gauge32 (0..4294967295)
   ACCESS     read-only
   STATUS     mandatory
   DESCRIPTION
     "This attribute gives the actual bandwidth (in bits per second) 
      reserved by this path on each of trunks of its route. This attribute 
      represents the bandwidth for traffic incoming from the remote end 
      point. The originating end of the connection determines this value"
::= { mscHtdsLCoPathDataEntry 10 }

mscHtdsLCoRequiredTrafficType OBJECT-TYPE
   SYNTAX     INTEGER  {
                 voice(0),
                 data(1),
                 video(2),
                 trafficType1(3),
                 trafficType2(4),
                 trafficType3(5),
                 trafficType4(6),
                 trafficType5(7) }
   ACCESS     read-only
   STATUS     mandatory
   DESCRIPTION
     "This operational attribute indicates the type of traffic transmitted 
      over the path. There are eight possible traffic types, and the path can 
      transmit only one of them. The originating end of the connection 
      determines the type. These are arbitrary designations for traffic 
      type. The voice, data and video traffic types are defined, and five 
      other arbitrary traffic types can be defined by the network 
      administration. This attribute is used in the route selection process 
      to restrict the route to trunks that support this traffic type. The 
      supportedTrafficType trunk attribute lists all the types of traffic 
      allowed on the trunk. For example, if requiredTrafficType is 
      specified as trafficType1 then only trunks that include trafficType1 
      in supportedTrafficType, will be candidates for this connection."
::= { mscHtdsLCoPathDataEntry 11 }

mscHtdsLCoPermittedTrunkTypes OBJECT-TYPE
   SYNTAX     OCTET STRING (SIZE (1))
   ACCESS     read-only
   STATUS     mandatory
   DESCRIPTION
     "This operational attribute lists up to eight types of trunk that can be 
      used on the route. The originating end of the connection determines 
      the types. The terrestrial and satellite trunk types have been 
      defined, leaving six remaining arbitrary types that can be defined by 
      the network administration. The trunk's type is indicated in the 
      trunkType attribute of the Trunk component. When selecting a 
      route, PORS only chooses trunks whose trunkType are in the 
      permittedTrunkTypes for the path.

      Description of bits:
      terrestrial(0)
      satellite(1)
      trunkType1(2)
      trunkType2(3)
      trunkType3(4)
      trunkType4(5)
      trunkType5(6)
      trunkType6(7)"
::= { mscHtdsLCoPathDataEntry 12 }

mscHtdsLCoRequiredSecurity OBJECT-TYPE
   SYNTAX     Unsigned32 (0..7)
   ACCESS     read-only
   STATUS     mandatory
   DESCRIPTION
     "This attribute indicates the required minimum level of security of 
      the trunks on the route. Zero represents the most secure and seven 
      represents the least secure. The trunk's security is indicated by the 
      trunkSecurity attribute of the Trunk component, and has values 
      identical in range and meaning to the requiredSecurity attribute. 
      PORS ensures that any route selected does not contain a trunk 
      whose trunkSecurity attribute is numerically greater than the 
      requiredSecurity."
::= { mscHtdsLCoPathDataEntry 13 }

mscHtdsLCoRequiredCustomerParameter OBJECT-TYPE
   SYNTAX     Unsigned32 (0..7)
   ACCESS     read-only
   STATUS     mandatory
   DESCRIPTION
     "This attribute indicates the allowed customer defined parameter of 
      the trunks on the route.The originating end of the connection 
      determines the customer defined parameter. Its value, a number 
      from zero to seven, is chosen by a network administration to have a 
      meaning specific to their network, thus allowing them to customize 
      the use of their trunks. A complementary trunk attribute, 
      customerParameter, also has a value from zero to seven. The route 
      selection process does not consider trunks whose 
      customerParameter is greater than the requiredCustomerParameter 
      of the path."
::= { mscHtdsLCoPathDataEntry 14 }

mscHtdsLCoEmissionPriority OBJECT-TYPE
   SYNTAX     Unsigned32 (0..2)
   ACCESS     read-only
   STATUS     mandatory
   DESCRIPTION
     "This attribute indicates the urgency with which packets on the path 
      are emitted by the trunks on the route. The originating end of the 
      connection selects the emissionPriority. EmissionPriority of zero 
      indicates the highest emission priority, while two indicates the 
      lowest emission priority. Packets with a higher emissionPriority (or 
      numerically less) are serviced and sent out before the packets of 
      lower emissionPriority (or numerically higher)."
::= { mscHtdsLCoPathDataEntry 15 }

mscHtdsLCoDiscardPriority OBJECT-TYPE
   SYNTAX     Unsigned32 (1..3)
   ACCESS     read-only
   STATUS     mandatory
   DESCRIPTION
     "This attribute indicates the importance of the packets on the 
      path.The originating end of the connection sets discardPriority. One 
      is used for paths carrying the most important traffic, and three is 
      used for paths carrying the least important traffic. Packets with 
      lower discardPriority(numerically lower) are discarded after 
      packets with a higher discardPriority(numerically higher)."
::= { mscHtdsLCoPathDataEntry 16 }

mscHtdsLCoPathType OBJECT-TYPE
   SYNTAX     INTEGER  {
                 normal(0),
                 manual(1),
                 forced(2) }
   ACCESS     read-only
   STATUS     mandatory
   DESCRIPTION
     "This attribute indicates whether the path for this PLC was 
      determined automatically or by static provisioning. Normal 
      pathTypes are selected automatically by Route Selector.The other 
      pathTypes are both manual pathTypes where the operator must 
      specify, through provisioning, a static route termed the manualPath. 
      A manual pathType connection is nearly identical to a normal path 
      type connection with the exception that the route is pre-provisioned. 
      For a manual pathType, bandwidth reservations are respected along 
      the path exactly as in a normal path. The last type, the forced 
      pathType, is also a manual path but regardless of the bandwidth 
      available the route is granted provided the trunks are operational 
      and there are sufficient Logical Channels (LChs).
      
      The forced pathType could result in over committing the reserved 
      bandwidth allowed on a trunk. A better way to achieve the effects of 
      a forced pathType is to use a manual pathType with setupPriority = 
      0 and holdingPriority = 0. In this manner the path will reserve 
      correct bandwidth and it will bump other paths if required while not 
      being bumped itself."
::= { mscHtdsLCoPathDataEntry 17 }

mscHtdsLCoRetryCount OBJECT-TYPE
   SYNTAX     Unsigned32 (0..255)
   ACCESS     read-only
   STATUS     mandatory
   DESCRIPTION
     "This attribute is the count of the number of times the path chosen 
      during route selection could not be instantiated. This count should 
      be three or below if the network is performing adequately. A high 
      value indicates that the route selection is often performed using an 
      out-of-date view of available network bandwidth and/or topology.
      This attribute will only increase at the calling end of the connection.
      This attribute is reset each time a path reconnects and stops 
      counting when it reaches its maximum value."
::= { mscHtdsLCoPathDataEntry 18 }

mscHtdsLCoPathFailureCount OBJECT-TYPE
   SYNTAX     Unsigned32 (0..65535)
   ACCESS     read-only
   STATUS     mandatory
   DESCRIPTION
     "This attribute is the count of the number of times the path has 
      successfully connected. It is set to zero the first time the path is up. 
      If a path fails anytime after connecting this count will be 
      incremented when the path is up again. Failed route requests do not 
      count in this statistic. See retryCount above. This attribute stops 
      counting at its maximum value."
::= { mscHtdsLCoPathDataEntry 19 }

mscHtdsLCoReasonForNoRoute OBJECT-TYPE
   SYNTAX     INTEGER  {
                 none(0),
                 destinationNameTooLong(1),
                 destinationNotSpecified(2),
                 unknownDestinationName(3),
                 incorrectDestination(4),
                 incorrectDestinationEndPoint(5),
                 unknownSource(6),
                 unknownDestination(7),
                 sameNode(8),
                 routeCostTooMuch(9),
                 routesDelayTooLong(10),
                 attributesNotMet(11),
                 anError(12),
                 attributeProfileProblem(13),
                 manualPathIndexProblem(14) }
   ACCESS     read-only
   STATUS     mandatory
   DESCRIPTION
     "This attribute is the route selection's reasonForNoRoute and 
      provides a brief reason for which a route was not selected. The 
      reasons are essentially self-explanatory. Perhaps two reasons for no 
      route require some explanation. The reason 
      unknownRemoteNodeName is issued when the remote node name 
      is not in the topological database. The reason plcAttributesNotMet 
      is issued when there is no network connectivity at a level specified 
      by the PLC attributes. This reason is also issued when there is no 
      physical connectivity between two end nodes."
   DEFVAL     { none }
::= { mscHtdsLCoPathDataEntry 20 }

mscHtdsLCoLastTearDownReason OBJECT-TYPE
   SYNTAX     INTEGER  {
                 none(0),
                 normalShutDown(1),
                 insufficientTxLcOrBandwidth(2),
                 insufficientRxLcOrBandwidth(3),
                 trunkFailure(4),
                 trunkCardFailure(5),
                 operatorForced(6),
                 lostLcnClash(7),
                 networkCongestion(8),
                 trunkNotFound(9),
                 farEndNotFound(10),
                 wrongModuleReached(11),
                 farEndBusy(12),
                 callLoopedBack(13),
                 unknownReason(14),
                 farEndNotReady(15),
                 remoteNameMismatch(16),
                 serviceTypeMismatch(17),
                 reconnectFromFarEnd(18),
                 bumped(19),
                 accessCardFailure(20),
                 optimized(21),
                 overrideRemoteName(22),
                 trunkOrFarEndDidNotSupportMode(23) }
   ACCESS     read-only
   STATUS     mandatory
   DESCRIPTION
     "This attribute reflects the last tear down reason for a connection 
      (LCo). In many cases this displays the reason for a momentary 
      service interruption. This attribute applies to the last path failure 
      only. If a path is no longer up, this may give an indication to the 
      reason that the path has failed. In many cases an alarm will also be 
      generated with more specific information. The following is a brief 
      description of the reasons:
      none - This path has no information for the teardown this is typical 
      of a path provisioned with no remoteName that has not been up.
      normalShutDown - This path has gone down due to normal call 
      termination.
      insufficientTxLcOrBandwidth - At present there is either no 
      available bandwidth or logical channel numbers available on one or 
      more of the trunks for this path in the transmit direction.
      insufficientRxLcOrBandwidth - At present there is either no 
      available bandwidth or logical channel numbers available on one or 
      more of the trunks for this path in the receive direction.
      trunkFailure- A trunk on the path has failed or has gone down due 
      to a provisioning change of a critical attribute.
      trunkCardFailure- A trunk FP card has failed along the path.
      accessCardFailure- The FP on which the peer access service was 
      running has failed.
      operatorForced- The path has terminated due to the operator 
      locking a trunk along the path.
      lostLcnClash- The path has terminated because the PA's at both 
      ends of an intermediate trunk have allocated the same LC to 
      different calls. When this happens both calls must go down and then 
      try to come up again a fraction of a second later (effectively 
      ensuring that they will now be assigned different LC's). It is normal 
      to get the odd clash especially when the PA's usedLC is 
      approaching the PA's maxLC.
      networkCongestion - The path has failed due to control information 
      being lost and not recoverable.
      trunkNotFound - Occurs on a manual path usually. Check for 
      trunks not up or names provisioned incorrectly.
      farEndNotFound - The far end is not provisioned or is not up. 
      Check remote Name.
      wrongModuleReached - This may occur on a manual path. Check 
      provisioning for correct trunk and service names. For a normal 
      path, the network Topology may be changing check remoteName.
      farEndBusy - The far end has been reached but it is busy. Check 
      remoteName and remote end provisioning.
      callLoopedBack - This LCo is provisioned to call itself. Re-
      provision since this is invalid.
      unknownReason - The failure was not resolved.
      farEndNotReady - The remote end was reached but the connection 
      was refused due to the remote end not being enabled.
      remoteNameMismatch - The remote end has alarmed and rejected 
      this setup due to remoteName provisioning.
      serviceTypeMismatch - The remote Service Type does not match 
      this service type. Check provisioning.
      reconnectFromFarEnd - The remote end re-established this 
      connection. Check the remote end lastTearDownReason to 
      determine the real reason.
      bumped - Another call bumped this path from a trunk to get 
      bandwidth (or an LC) which it required to come up. This other path 
      had a higher setupPriority than this path's holdingPriority hence it 
      was allowed to steal the bandwidth (or LC) from this path.
      optimized - This call has been rerouted due to the optimization 
      feature. The call is still active this just indicates why the path 
      changed.
      trunkOrFarEndDidNotSupportMode - This call was unable to 
      complete because a mode required by the service was not supported 
      by one of the trunks the route went through or by the far end service 
      it connected to. Currently the only mode that this applies to is the 
      map/mux mode on TRUNK PA ATM component. Map mode was 
      required by the application (CES/FrAtm etc.) but was not available 
      on the TRUNK PA ATM component through which the call was 
      routed or the far end CES/FrAtm component did not specify the 
      same mode."
   DEFVAL     { none }
::= { mscHtdsLCoPathDataEntry 21 }

mscHtdsLCoPathFailureAction OBJECT-TYPE
   SYNTAX     INTEGER  {
                 disconnectConnection(0),
                 reRoutePath(1) }
   ACCESS     read-only
   STATUS     mandatory
   DESCRIPTION
     "This attribute displays whether the application is set to tolerate 
      momentary interruption of a path while a new path is selected. If 
      disconnectConnection is displayed, the application is informed as 
      soon as possible about a failure by disconnection. If the attribute 
      displays reRoutePath, the path may attempt an immediate reroute, 
      provided the failure is a recoverable failure. If rerouting fails the 
      application is informed of the failure. 
      With this option set to reRoutePath the LCo may wait up to 30 
      seconds before informing the service of complete disconnection in 
      order to allow both ends to attempt to reconnect. Note that if PLC 
      components are different at both ends only the calling end is 
      allowed to reconnect.
      
      All pathTypes respect this attribute. Also on a manualPath with 
      both ends provisioned with independent paths (at least with respect 
      to the failure) this option will have the desired effect that the path is 
      rerouted without complete disconnection at both ends"
::= { mscHtdsLCoPathDataEntry 22 }

mscHtdsLCoBumpPreference OBJECT-TYPE
   SYNTAX     INTEGER  {
                 bumpWhenNecessary(0),
                 bumpToObtainBestRoute(1) }
   ACCESS     read-only
   STATUS     mandatory
   DESCRIPTION
     "This attribute specifies when bumping will occur during route 
      selection process. Bumping may occur when necessary or always. It 
      will be necessary for a connection to bump if there is not enough 
      resources for the connection to be established and these resources 
      are occupied by a connection whose setupPriority is lower 
      (numerically higher) than the connection's setupPriority. A 
      connection may also always bump in order to obtain the best route."
::= { mscHtdsLCoPathDataEntry 23 }

mscHtdsLCoOptimization OBJECT-TYPE
   SYNTAX     INTEGER  {
                 disabled(0),
                 enabled(1) }
   ACCESS     read-only
   STATUS     mandatory
   DESCRIPTION
     "This attribute is used to specify whether this connection should 
      attempt to optimize its path when requested by the routing PORS 
      component. Every path is as optimal as it can be when it is 
      established, but as network traffic patterns and configurations 
      change this path may no longer be as optimal as it could be. The 
      PORS connection manager on a module requests circuits to 
      optimize at the optimization interval."
::= { mscHtdsLCoPathDataEntry 24 }

mscHtdsLCoPathUpDateTime OBJECT-TYPE
   SYNTAX     EnterpriseDateAndTime (SIZE (0 | 19))
   ACCESS     read-only
   STATUS     mandatory
   DESCRIPTION
     "This is the time stamp when the current path was established or 
      reestablished."
::= { mscHtdsLCoPathDataEntry 25 }

mscHtdsLCoStatsTable OBJECT-TYPE
   SYNTAX     SEQUENCE OF MscHtdsLCoStatsEntry
   ACCESS     not-accessible
   STATUS     mandatory
   DESCRIPTION
     "This group contains the operational statistics attributes for the path 
      oriented LCo."
::= { mscHtdsLCo 11 }

mscHtdsLCoStatsEntry OBJECT-TYPE
   SYNTAX     MscHtdsLCoStatsEntry
   ACCESS     not-accessible
   STATUS     mandatory
   DESCRIPTION
     "An entry in the mscHtdsLCoStatsTable."
   INDEX {
      mscHtdsIndex,
      mscHtdsLCoIndex }
::= { mscHtdsLCoStatsTable 1 }

MscHtdsLCoStatsEntry ::= SEQUENCE {
   mscHtdsLCoPktsToNetwork
      PassportCounter64,
   mscHtdsLCoBytesToNetwork
      PassportCounter64,
   mscHtdsLCoPktsFromNetwork
      PassportCounter64,
   mscHtdsLCoBytesFromNetwork
      PassportCounter64 }

mscHtdsLCoPktsToNetwork OBJECT-TYPE
   SYNTAX     PassportCounter64 
   ACCESS     read-only
   STATUS     mandatory
   DESCRIPTION
     "This attribute counts the number of packets transmitted to the 
      network over this Logical Connection."
::= { mscHtdsLCoStatsEntry 1 }

mscHtdsLCoBytesToNetwork OBJECT-TYPE
   SYNTAX     PassportCounter64 
   ACCESS     read-only
   STATUS     mandatory
   DESCRIPTION
     "This attribute counts the number of bytes sent to the network over 
      this Logical Connection."
::= { mscHtdsLCoStatsEntry 2 }

mscHtdsLCoPktsFromNetwork OBJECT-TYPE
   SYNTAX     PassportCounter64 
   ACCESS     read-only
   STATUS     mandatory
   DESCRIPTION
     "This attribute counts the number of packets received from the 
      remote LCo via the network."
::= { mscHtdsLCoStatsEntry 3 }

mscHtdsLCoBytesFromNetwork OBJECT-TYPE
   SYNTAX     PassportCounter64 
   ACCESS     read-only
   STATUS     mandatory
   DESCRIPTION
     "This attribute counts the number of bytes received from the remote 
      LCo via the network."
::= { mscHtdsLCoStatsEntry 4 }

mscHtdsLCoPathTable OBJECT-TYPE
   SYNTAX     SEQUENCE OF MscHtdsLCoPathEntry
   ACCESS     not-accessible
   STATUS     mandatory
   DESCRIPTION
     "This attribute contains the trunk component names over which the 
      path has been instantiated and the remote end point name 
      terminating the path."
::= { mscHtdsLCo 264 }

mscHtdsLCoPathEntry OBJECT-TYPE
   SYNTAX     MscHtdsLCoPathEntry
   ACCESS     not-accessible
   STATUS     mandatory
   DESCRIPTION
     "An entry in the mscHtdsLCoPathTable."
   INDEX {
      mscHtdsIndex,
      mscHtdsLCoIndex,
      mscHtdsLCoPathValue }
::= { mscHtdsLCoPathTable 1 }

MscHtdsLCoPathEntry ::= SEQUENCE {
   mscHtdsLCoPathValue
      AsciiString }

mscHtdsLCoPathValue OBJECT-TYPE
   SYNTAX     AsciiString (SIZE (0..40))
   ACCESS     read-only
   STATUS     mandatory
   DESCRIPTION
     "This variable represents both the value and the index for the
      mscHtdsLCoPathTable."
::= { mscHtdsLCoPathEntry 1 }




-- 
-- Version and Compliance statements
-- 



-- Object-Group Statement:
-- A list of all current accessible leaf objects.

-- OBJECTS { mscHtdsAdminState,
--           mscHtdsLCoLastTearDownReason,
--           mscHtdsFramerFrmToIf,
--           mscHtdsLCoDelayMetric,
--           mscHtdsFramerDataInversion,
--           mscHtdsPlcEmissionPriority,
--           mscHtdsLCoPathFailureAction,
--           mscHtdsRowStatus,
--           mscHtdsFramerNonOctetData,
--           mscHtdsFramerLineSignalTransport,
--           mscHtdsCustomerIdentifier,
--           mscHtdsLCoRowStatus,
--           mscHtdsLCoEnd,
--           mscHtdsFramerNonOctetErrors,
--           mscHtdsPlcPathType,
--           mscHtdsFramerUsageState,
--           mscHtdsProceduralStatus,
--           mscHtdsPlcComponentName,
--           mscHtdsPlcRequiredCustomerParm,
--           mscHtdsLCoHoldingPriority,
--           mscHtdsFramerComponentName,
--           mscHtdsUsageState,
--           mscHtdsPlcDiscardPriority,
--           mscHtdsFramerUnderruns,
--           mscHtdsFramerInterfaceName,
--           mscHtdsComponentName,
--           mscHtdsLCoState,
--           mscHtdsLCoPathUpDateTime,
--           mscHtdsFramerNormPrioLinkUtilFromIf,
--           mscHtdsLCoRoundTripDelay,
--           mscHtdsLCoPathType,
--           mscHtdsAlarmStatus,
--           mscHtdsLCoComponentName,
--           mscHtdsFramerOperationalState,
--           mscHtdsLCoOverrideRemoteName,
--           mscHtdsPlcRequiredTxBandwidth,
--           mscHtdsFramerLargeFrmErrors,
--           mscHtdsLCoDiscardPriority,
--           mscHtdsOperationalState,
--           mscHtdsPlcAddressToCall,
--           mscHtdsLCoRequiredTxBandwidth,
--           mscHtdsPlcRequiredSecurity,
--           mscHtdsPlcRequiredRxBandwidth,
--           mscHtdsPlcRemoteName,
--           mscHtdsLCoBytesFromNetwork,
--           mscHtdsFramerLrcErrors,
--           mscHtdsLCoPermittedTrunkTypes,
--           mscHtdsPlcPathAttributeToMinimize,
--           mscHtdsLCoCostMetric,
--           mscHtdsLCoRequiredTrafficType,
--           mscHtdsLCoPktsFromNetwork,
--           mscHtdsLCoEmissionPriority,
--           mscHtdsLCoPathValue,
--           mscHtdsFramerAborts,
--           mscHtdsLCoPktsToNetwork,
--           mscHtdsPlcPathFailureAction,
--           mscHtdsLCoRequiredRxBandwidth,
--           mscHtdsLCoPathFailureCount,
--           mscHtdsPlcStorageType,
--           mscHtdsPlcHoldingPriority,
--           mscHtdsUnknownStatus,
--           mscHtdsPlcMaximumAcceptableDelay,
--           mscHtdsPlcMaximumAcceptableCost,
--           mscHtdsAvailabilityStatus,
--           mscHtdsLCoBytesToNetwork,
--           mscHtdsLCoRequiredCustomerParameter,
--           mscHtdsSnmpOperStatus,
--           mscHtdsIfIndex,
--           mscHtdsFramerNormPrioLinkUtilToIf,
--           mscHtdsPlcPermittedTrunkTypes,
--           mscHtdsPlcMpathValue,
--           mscHtdsLCoStorageType,
--           mscHtdsFramerFrmFromIf,
--           mscHtdsFramerCrcErrors,
--           mscHtdsFramerStorageType,
--           mscHtdsStandbyStatus,
--           mscHtdsLCoRetryCount,
--           mscHtdsPlcRequiredTrafficType,
--           mscHtdsFramerFlagsBetweenFrames,
--           mscHtdsStorageType,
--           mscHtdsIfAdminStatus,
--           mscHtdsPlcOptimization,
--           mscHtdsPlcLocalAddress,
--           mscHtdsPlcMaximumAcceptableGatewayCost,
--           mscHtdsLCoOptimization,
--           mscHtdsFramerOctetFromIf,
--           mscHtdsLCoRequiredSecurity,
--           mscHtdsPlcSetupPriority,
--           mscHtdsLCoBumpPreference,
--           mscHtdsLCoReasonForNoRoute,
--           mscHtdsFramerFrameCrcType,
--           mscHtdsFramerAdminState,
--           mscHtdsFramerRowStatus,
--           mscHtdsLCoSetupPriority,
--           mscHtdsFramerOverruns,
--           mscHtdsPlcRowStatus,
--           mscHtdsPlcBumpPreference,
--           mscHtdsControlStatus }
-- STATUS  mandatory
-- DESCRIPTION
--   "A list of all current accessible leaf objects."

hdlcTransparentGroup OBJECT IDENTIFIER ::= { hdlcTransparentMIB 1 }
hdlcTransparentGroupCA OBJECT IDENTIFIER ::= { hdlcTransparentGroup 1 }
hdlcTransparentGroupCA02 OBJECT IDENTIFIER ::= { hdlcTransparentGroupCA 3 }
hdlcTransparentGroupCA02A OBJECT IDENTIFIER ::= { hdlcTransparentGroupCA02 2 }



-- Agent-Capabilities Statement:

-- PRODUCT-RELEASE "MscPassport Release 1.2 HdlcTransparent."
-- STATUS          mandatory
-- DESCRIPTION     "Carrier Passport HdlcTransparent MIB: MIB Version CA02A,
--                  Software Version CA02S9C."
-- SUPPORTS        Nortel-MsCarrier-MscPassport-HdlcTransparentMIB
--    INCLUDES     { hdlcTransparentGroupCA02A }

hdlcTransparentCapabilities OBJECT IDENTIFIER ::= { hdlcTransparentMIB 3 }
hdlcTransparentCapabilitiesCA OBJECT IDENTIFIER ::= { hdlcTransparentCapabilities 1 }
hdlcTransparentCapabilitiesCA02 OBJECT IDENTIFIER ::= { hdlcTransparentCapabilitiesCA 3 }
hdlcTransparentCapabilitiesCA02A OBJECT IDENTIFIER ::= { hdlcTransparentCapabilitiesCA02 2 }





END
