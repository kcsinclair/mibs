Nortel-MsCarrier-MscPassport-MpaNetworkLinkMIB
DEFINITIONS ::= BEGIN



IMPORTS

      OBJECT-TYPE
   FROM RFC-1212

      mscPassportMIBs,
      mscComponents
   FROM Nortel-MsCarrier-MscPassport-UsefulDefinitionsMIB

      Counter32,
      RowPointer,
      DisplayString,
      StorageType,
      RowStatus,
      InterfaceIndex,
      Gauge32,
      Integer32,
      Unsigned32
   FROM Nortel-MsCarrier-MscPassport-StandardTextualConventionsMIB

      AsciiString,
      Hex,
      NonReplicated,
      HexString,
      EnterpriseDateAndTime,
      PassportCounter64,
      Link,
      DigitString,
      Unsigned64
   FROM Nortel-MsCarrier-MscPassport-TextualConventionsMIB;




-- LAST-UPDATED   "9909010000Z"
-- ORGANIZATION   "Nortel Networks"
-- CONTACT-INFO   "
--         Nortel Carrier Data Network Management
--         
--         Postal:       P.O. Box 3511, Station C 
--                       Ottawa, Ontario 
--                       Canada  K1Y 4H7
--         
--         via the WEB:  http://www.nortelnetworks.com  
--                       select 'Contact Us' from the menu
--          
--         via phone:    1-800-4NORTEL"
-- DESCRIPTION
--    "The module describing the Nortel MsCarrier MscPassport
--     MpaNetworkLink Enterprise MIB."

mpaNetworkLinkMIB OBJECT IDENTIFIER ::= { mscPassportMIBs 119 }










-- MpaNetworkLink/<n>
-- This component defines an instance of the MPA Network Link 
-- (MPANL) service. The component instance value n is a unique 
-- positive integer within a module.

mscMpanl OBJECT IDENTIFIER ::= { mscComponents 123 }



mscMpanlRowStatusTable OBJECT-TYPE
   SYNTAX     SEQUENCE OF MscMpanlRowStatusEntry
   ACCESS     not-accessible
   STATUS     mandatory
   DESCRIPTION
     "This entry controls the addition and deletion of 
      mscMpanl components."
::= { mscMpanl 1 }

mscMpanlRowStatusEntry OBJECT-TYPE
   SYNTAX     MscMpanlRowStatusEntry
   ACCESS     not-accessible
   STATUS     mandatory
   DESCRIPTION
     "A single entry in the table represents a single 
      mscMpanl component."
   INDEX {
      mscMpanlIndex }
::= { mscMpanlRowStatusTable 1 }

MscMpanlRowStatusEntry ::= SEQUENCE {
   mscMpanlRowStatus
      RowStatus,
   mscMpanlComponentName
      DisplayString,
   mscMpanlStorageType
      StorageType,
   mscMpanlIndex
      Integer32 }

mscMpanlRowStatus OBJECT-TYPE
   SYNTAX     RowStatus 
   ACCESS     read-write
   STATUS     mandatory
   DESCRIPTION
     "This variable is used as the basis for SNMP naming of
      mscMpanl components.
      These components can be added and deleted."
::= { mscMpanlRowStatusEntry 1 }

mscMpanlComponentName OBJECT-TYPE
   SYNTAX     DisplayString 
   ACCESS     read-only
   STATUS     mandatory
   DESCRIPTION
     "This variable provides the component's string name for
      use with the ASCII Console Interface"
::= { mscMpanlRowStatusEntry 2 }

mscMpanlStorageType OBJECT-TYPE
   SYNTAX     StorageType 
   ACCESS     read-only
   STATUS     mandatory
   DESCRIPTION
     "This variable represents the storage type value for the
      mscMpanl tables."
::= { mscMpanlRowStatusEntry 4 }

mscMpanlIndex OBJECT-TYPE
   SYNTAX     Integer32 (1..65535)
   ACCESS     not-accessible
   STATUS     mandatory
   DESCRIPTION
     "This variable represents the index for the mscMpanl tables."
::= { mscMpanlRowStatusEntry 10 }

mscMpanlCidDataTable OBJECT-TYPE
   SYNTAX     SEQUENCE OF MscMpanlCidDataEntry
   ACCESS     not-accessible
   STATUS     mandatory
   DESCRIPTION
     "This group contains the attribute for the MPANL component's 
      Customer Identifier (CID). Refer to the attribute description for a 
      detailed explanation of CIDs."
::= { mscMpanl 10 }

mscMpanlCidDataEntry OBJECT-TYPE
   SYNTAX     MscMpanlCidDataEntry
   ACCESS     not-accessible
   STATUS     mandatory
   DESCRIPTION
     "An entry in the mscMpanlCidDataTable."
   INDEX {
      mscMpanlIndex }
::= { mscMpanlCidDataTable 1 }

MscMpanlCidDataEntry ::= SEQUENCE {
   mscMpanlCustomerIdentifier
      Unsigned32 }

mscMpanlCustomerIdentifier OBJECT-TYPE
   SYNTAX     Unsigned32 (0 | 1..8191)
   ACCESS     read-only
   STATUS     mandatory
   DESCRIPTION
     "This attribute holds the Customer Identifier (CID).
      
      Every component has a CID. If a component has a cid attribute, the 
      component's CID is the provisioned value of that attribute; 
      otherwise the component inherits the CID of its parent. The top-
      level component has a CID of 0.
      
      Every operator session also has a CID, which is the CID 
      provisioned for the operator's user ID. An operator will see only the 
      stream data for components having a matching CID. Also, the 
      operator will be allowed to issue commands for only those 
      components which have a matching CID.
      
      An operator CID of 0 is used to identify the Network Manager 
      (referred to as 'NetMan' in DPN). This CID matches the CID of 
      any component. Values 1 to 8191 inclusive (equivalent to 'basic 
      CIDs' in DPN) may be assigned to specific customers."
   DEFVAL     { 0 }
::= { mscMpanlCidDataEntry 1 }

mscMpanlProvTable OBJECT-TYPE
   SYNTAX     SEQUENCE OF MscMpanlProvEntry
   ACCESS     not-accessible
   STATUS     mandatory
   DESCRIPTION
     "This group contains provisionable attributes of the MPANL service."
::= { mscMpanl 12 }

mscMpanlProvEntry OBJECT-TYPE
   SYNTAX     MscMpanlProvEntry
   ACCESS     not-accessible
   STATUS     mandatory
   DESCRIPTION
     "An entry in the mscMpanlProvTable."
   INDEX {
      mscMpanlIndex }
::= { mscMpanlProvTable 1 }

MscMpanlProvEntry ::= SEQUENCE {
   mscMpanlCommentText
      AsciiString }

mscMpanlCommentText OBJECT-TYPE
   SYNTAX     AsciiString (SIZE (0..40))
   ACCESS     read-write
   STATUS     mandatory
   DESCRIPTION
     "This attribute specifies the name the customer wishes to associate 
      with this MPANL interface."
::= { mscMpanlProvEntry 1 }

mscMpanlEmissionPriorityQsTable OBJECT-TYPE
   SYNTAX     SEQUENCE OF MscMpanlEmissionPriorityQsEntry
   ACCESS     not-accessible
   STATUS     mandatory
   DESCRIPTION
     "This group contains the provisionable attribute to specifie the 
      number of Frame Relay egress emission priority queues to be used 
      on that Frame Relay Interface"
::= { mscMpanl 13 }

mscMpanlEmissionPriorityQsEntry OBJECT-TYPE
   SYNTAX     MscMpanlEmissionPriorityQsEntry
   ACCESS     not-accessible
   STATUS     mandatory
   DESCRIPTION
     "An entry in the mscMpanlEmissionPriorityQsTable."
   INDEX {
      mscMpanlIndex }
::= { mscMpanlEmissionPriorityQsTable 1 }

MscMpanlEmissionPriorityQsEntry ::= SEQUENCE {
   mscMpanlNumberOfEmissionQs
      Unsigned32 }

mscMpanlNumberOfEmissionQs OBJECT-TYPE
   SYNTAX     Unsigned32 (2 | 4)
   ACCESS     read-only
   STATUS     mandatory
   DESCRIPTION
     "This attribute specifies the number of egress emission priority 
      queues that will be used for that Frame Relay interface. The 
      possible values of this attribute are 2 or 4:
      For V.35, V.11, HSSI, E1, DS1, E3, DS3 or 8pDS1 the possible 
      values are: 2 (in which case they are hardware queues), or 4 (in 
      which case they are software queues).
      For DS1C, E1C or DS3C the possible values are 2, 4 (in all cases 
      they are software queues)."
   DEFVAL     { 4 }
::= { mscMpanlEmissionPriorityQsEntry 1 }

mscMpanlStateTable OBJECT-TYPE
   SYNTAX     SEQUENCE OF MscMpanlStateEntry
   ACCESS     not-accessible
   STATUS     mandatory
   DESCRIPTION
     "This group contains the three OSI State attributes and the six OSI 
      Status attributes. The descriptions generically indicate what each 
      attribute implies about the component. Note that not all the values 
      and state combinations described here are supported by every 
      component which uses this group. For component-specific 
      information and the valid state combinations, refer to NTP 241-
      7001-150, Passport Operations and Maintenance Guide."
::= { mscMpanl 14 }

mscMpanlStateEntry OBJECT-TYPE
   SYNTAX     MscMpanlStateEntry
   ACCESS     not-accessible
   STATUS     mandatory
   DESCRIPTION
     "An entry in the mscMpanlStateTable."
   INDEX {
      mscMpanlIndex }
::= { mscMpanlStateTable 1 }

MscMpanlStateEntry ::= SEQUENCE {
   mscMpanlAdminState
      INTEGER,
   mscMpanlOperationalState
      INTEGER,
   mscMpanlUsageState
      INTEGER,
   mscMpanlAvailabilityStatus
      OCTET STRING,
   mscMpanlProceduralStatus
      OCTET STRING,
   mscMpanlControlStatus
      OCTET STRING,
   mscMpanlAlarmStatus
      OCTET STRING,
   mscMpanlStandbyStatus
      INTEGER,
   mscMpanlUnknownStatus
      INTEGER }

mscMpanlAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component.
      
      The OSI Status attributes, if supported by the component, may 
      provide more details, qualifying the state of the component."
   DEFVAL     { unlocked }
::= { mscMpanlStateEntry 1 }

mscMpanlOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle.
      
      The OSI Status attributes, if supported by the component, may 
      provide more details, qualifying the state of the component."
   DEFVAL     { disabled }
::= { mscMpanlStateEntry 2 }

mscMpanlUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time.
      
      The OSI Status attributes, if supported by the component, may 
      provide more details, qualifying the state of the component."
   DEFVAL     { idle }
::= { mscMpanlStateEntry 3 }

mscMpanlAvailabilityStatus OBJECT-TYPE
   SYNTAX     OCTET STRING (SIZE (2))
   ACCESS     read-only
   STATUS     mandatory
   DESCRIPTION
     "If supported by the component, this attribute indicates the OSI 
      Availability status of the component. Note that, even though it is 
      defined as a multi-valued set, at most one value is shown to the user.
      
      When no values are in the set, this indicates that either the attribute 
      is not supported or that none of the status conditions described 
      below are present.
      
      The value inTest indicates that the resource is undergoing a test 
      procedure. If adminState is locked or shuttingDown, the normal 
      users are precluded from using the resource and controlStatus is 
      reservedForTest. Tests that do not exclude additional users can be 
      present in any operational or administrative state but the 
      reservedForTest condition should not be present.
      
      The value failed indicates that the component has an internal fault 
      that prevents it from operating. The operationalState is disabled.
      
      The value dependency indicates that the component cannot operate 
      because some other resource on which it depends is unavailable. 
      The operationalState is disabled.
      
      The value powerOff indicates the resource requires power to be 
      applied and it is not powered on. The operationalState is disabled.
      
      The value offLine indicates the resource requires a routine 
      operation (either manual, automatic, or both) to be performed to 
      place it on-line and make it available for use. The operationalState 
      is disabled.
      
      The value offDuty indicates the resource is inactive in accordance 
      with a predetermined time schedule. In the absence of other 
      disabling conditions, the operationalState is enabled or disabled.
      
      The value degraded indicates the service provided by the 
      component is degraded in some way, such as in speed or operating 
      capacity. However, the resource remains available for service. The 
      operationalState is enabled.
      
      The value notInstalled indicates the resource is not present. The 
      operationalState is disabled.
      
      The value logFull is not used.

      Description of bits:
      inTest(0)
      failed(1)
      powerOff(2)
      offLine(3)
      offDuty(4)
      dependency(5)
      degraded(6)
      notInstalled(7)
      logFull(8)"
::= { mscMpanlStateEntry 4 }

mscMpanlProceduralStatus OBJECT-TYPE
   SYNTAX     OCTET STRING (SIZE (1))
   ACCESS     read-only
   STATUS     mandatory
   DESCRIPTION
     "If supported by the component, this attribute indicates the OSI 
      Procedural status of the component. Note that, even though it is 
      defined as a multi-valued set, at most one value is shown to the user.
      
      When no values are in the set, this indicates that either the attribute 
      is not supported or that none of the status conditions described 
      below are present.
      
      The value initializationRequired indicates (for a resource which 
      doesn't initialize autonomously) that initialization is required before 
      it can perform its normal functions, and this procedure has not been 
      initiated. The operationalState is disabled.
      
      The value notInitialized indicates (for a resource which does 
      initialize autonomously) that initialization is required before it can 
      perform its normal functions, and this procedure has not been 
      initiated. The operationalState may be enabled or disabled.
      
      The value initializing indicates that initialization has been initiated 
      but is not yet complete. The operationalState may be enabled or 
      disabled.
      
      The value reporting indicates the resource has completed some 
      processing operation and is notifying the results. The 
      operationalState is enabled.
      
      The value terminating indicates the component is in a termination 
      phase. If the resource doesn't reinitialize autonomously, 
      operationalState is disabled; otherwise it is enabled or disabled.

      Description of bits:
      initializationRequired(0)
      notInitialized(1)
      initializing(2)
      reporting(3)
      terminating(4)"
::= { mscMpanlStateEntry 5 }

mscMpanlControlStatus OBJECT-TYPE
   SYNTAX     OCTET STRING (SIZE (1))
   ACCESS     read-only
   STATUS     mandatory
   DESCRIPTION
     "If supported by the component, this attribute indicates the OSI 
      Control status of the component. Note that, even though it is defined 
      as a multi-valued set, at most one value is shown to the user.
      
      When no values are in the set, this indicates that either the attribute 
      is not supported or that none of the status conditions described 
      below are present.
      
      The value subjectToTest indicates the resource is available but tests 
      may be conducted simultaneously at unpredictable times, which 
      may cause it to exhibit unusual characteristics.
      
      The value partOfServicesLocked indicates that part of the service is 
      restricted from users of a resource. The adminState is unlocked.
      
      The value reservedForTest indicates that the component is 
      administratively unavailable because it is undergoing a test 
      procedure. The adminState is locked.
      
      The value suspended indicates that the service has been 
      administratively suspended.

      Description of bits:
      subjectToTest(0)
      partOfServicesLocked(1)
      reservedForTest(2)
      suspended(3)"
::= { mscMpanlStateEntry 6 }

mscMpanlAlarmStatus OBJECT-TYPE
   SYNTAX     OCTET STRING (SIZE (1))
   ACCESS     read-only
   STATUS     mandatory
   DESCRIPTION
     "If supported by the component, this attribute indicates the OSI 
      Alarm status of the component. Note that, even though it is defined 
      as a multi-valued set, at most one value is shown to the user.
      
      When no values are in the set, this indicates that either the attribute 
      is not supported or that none of the status conditions described 
      below are present.
      
      The value underRepair indicates the component is currently being 
      repaired. The operationalState is enabled or disabled.
      
      The value critical indicates one or more critical alarms are 
      outstanding against the component. Other, less severe, alarms may 
      also be outstanding. The operationalState is enabled or disabled.
      
      The value major indicates one or more major alarms are 
      outstanding against the component. Other, less severe, alarms may 
      also be outstanding. The operationalState is enabled or disabled.
      
      The value minor indicates one or more minor alarms are 
      outstanding against the component. Other, less severe, alarms may 
      also be outstanding. The operationalState is enabled or disabled.
      
      The value alarmOutstanding generically indicates that an alarm of 
      some severity is outstanding against the component.

      Description of bits:
      underRepair(0)
      critical(1)
      major(2)
      minor(3)
      alarmOutstanding(4)"
::= { mscMpanlStateEntry 7 }

mscMpanlStandbyStatus OBJECT-TYPE
   SYNTAX     INTEGER  {
                 hotStandby(0),
                 coldStandby(1),
                 providingService(2),
                 notSet(15) }
   ACCESS     read-only
   STATUS     mandatory
   DESCRIPTION
     "If supported by the component, this attribute indicates the OSI 
      Standby status of the component.
      
      The value notSet indicates that either the attribute is not supported 
      or that none of the status conditions described below are present. 
      Note that this is a non-standard value, used because the original 
      specification indicated this attribute was set-valued and thus, did not 
      provide a value to indicate that none of the other three are 
      applicable.
      
      The value hotStandby indicates that the resource is not providing 
      service but will be immediately able to take over the role of the 
      resource to be backed up, without initialization activity, and 
      containing the same information as the resource to be backed up.
      
      The value coldStandby indicates the resource is a backup for 
      another resource but will not be immediately able to take over the 
      role of the backed up resource and will require some initialization 
      activity.
      
      The value providingService indicates that this component, as a 
      backup resource, is currently backing up another resource."
   DEFVAL     { notSet }
::= { mscMpanlStateEntry 8 }

mscMpanlUnknownStatus OBJECT-TYPE
   SYNTAX     INTEGER  {
                 false(0),
                 true(1) }
   ACCESS     read-only
   STATUS     mandatory
   DESCRIPTION
     "This attribute indicates the OSI Unknown status of the component.
      
      The value false indicates that all of the other OSI State and Status 
      attribute values can be considered accurate.
      
      The value true indicates that the actual state of the component is not 
      known for sure."
   DEFVAL     { false }
::= { mscMpanlStateEntry 9 }

mscMpanlStatsTable OBJECT-TYPE
   SYNTAX     SEQUENCE OF MscMpanlStatsEntry
   ACCESS     not-accessible
   STATUS     mandatory
   DESCRIPTION
     "FrUni/n Statistics
      This group contains the statistics about the operational behavior of 
      the service at the interface level."
::= { mscMpanl 16 }

mscMpanlStatsEntry OBJECT-TYPE
   SYNTAX     MscMpanlStatsEntry
   ACCESS     not-accessible
   STATUS     mandatory
   DESCRIPTION
     "An entry in the mscMpanlStatsTable."
   INDEX {
      mscMpanlIndex }
::= { mscMpanlStatsTable 1 }

MscMpanlStatsEntry ::= SEQUENCE {
   mscMpanlLastUnknownDlci
      Unsigned32,
   mscMpanlUnknownDlciFramesFromIf
      Counter32,
   mscMpanlInvalidHeaderFramesFromIf
      Counter32 }

mscMpanlLastUnknownDlci OBJECT-TYPE
   SYNTAX     Unsigned32 (0..1023)
   ACCESS     read-only
   STATUS     mandatory
   DESCRIPTION
     "This attribute identifies the most recent DLCI which user frames 
      were received on for which a DLCI has not been provisioned on the 
      port."
   DEFVAL     { 0 }
::= { mscMpanlStatsEntry 1 }

mscMpanlUnknownDlciFramesFromIf OBJECT-TYPE
   SYNTAX     Counter32 
   ACCESS     read-only
   STATUS     mandatory
   DESCRIPTION
     "This attribute contains a count of the number of frames received 
      from the interface with an unknown DLCI (DLCI which is not 
      provisioned). When the maximum is reached the count wraps to 
      zero."
::= { mscMpanlStatsEntry 2 }

mscMpanlInvalidHeaderFramesFromIf OBJECT-TYPE
   SYNTAX     Counter32 
   ACCESS     read-only
   STATUS     mandatory
   DESCRIPTION
     "This attribute counts the number of frames received from the 
      interface with an invalid header format. When the maximum is 
      reached the count wraps to zero."
::= { mscMpanlStatsEntry 3 }

mscMpanlTrafficStatsTable OBJECT-TYPE
   SYNTAX     SEQUENCE OF MscMpanlTrafficStatsEntry
   ACCESS     not-accessible
   STATUS     mandatory
   DESCRIPTION
     "This operational group provides the traffic statistics of the service at 
      the interface level. Each attribute type is a non-negative integer 
      which monotonically increases until it reaches a maximum value, at 
      which point it wraps around and starts increasing again from zero."
::= { mscMpanl 17 }

mscMpanlTrafficStatsEntry OBJECT-TYPE
   SYNTAX     MscMpanlTrafficStatsEntry
   ACCESS     not-accessible
   STATUS     mandatory
   DESCRIPTION
     "An entry in the mscMpanlTrafficStatsTable."
   INDEX {
      mscMpanlIndex }
::= { mscMpanlTrafficStatsTable 1 }

MscMpanlTrafficStatsEntry ::= SEQUENCE {
   mscMpanlFrmToIf
      Unsigned32,
   mscMpanlOctetToIf
      Unsigned32,
   mscMpanlFrmFromIf
      Unsigned32,
   mscMpanlOctetFromIf
      Unsigned32 }

mscMpanlFrmToIf OBJECT-TYPE
   SYNTAX     Unsigned32 (0..4294967295)
   ACCESS     read-only
   STATUS     mandatory
   DESCRIPTION
     "This attribute counts frames transmitted to the interface. This count 
      may differ from its framer couterpart because Voice over Frame 
      Relay function may fragment and pack the Frame Relay frames 
      before transmission. When the maximum is reached the count 
      wraps to zero."
::= { mscMpanlTrafficStatsEntry 1 }

mscMpanlOctetToIf OBJECT-TYPE
   SYNTAX     Unsigned32 (0..4294967295)
   ACCESS     read-only
   STATUS     mandatory
   DESCRIPTION
     "This attribute counts octets transmitted to the interface. This count 
      may differ from its framer couterpart because Voice over Frame 
      Relay function may fragment and pack the Frame Relay frames 
      before transmission. When the maximum is reached the count 
      wraps to zero."
::= { mscMpanlTrafficStatsEntry 2 }

mscMpanlFrmFromIf OBJECT-TYPE
   SYNTAX     Unsigned32 (0..4294967295)
   ACCESS     read-only
   STATUS     mandatory
   DESCRIPTION
     "This attribute counts frames received from the interface. This count 
      may differ from its framer couterpart because Voice over Frame 
      Relay function may fragment and pack the Frame Relay frames 
      before transmission. When the maximum is reached the count 
      wraps to zero."
::= { mscMpanlTrafficStatsEntry 3 }

mscMpanlOctetFromIf OBJECT-TYPE
   SYNTAX     Unsigned32 (0..4294967295)
   ACCESS     read-only
   STATUS     mandatory
   DESCRIPTION
     "This attribute counts octets received from the interface. This count 
      may differ from its framer couterpart because Voice over Frame 
      Relay function may fragment and pack the Frame Relay frames 
      before transmission. When the maximum is reached the count 
      wraps to zero."
::= { mscMpanlTrafficStatsEntry 4 }

mscMpanlIfEntryTable OBJECT-TYPE
   SYNTAX     SEQUENCE OF MscMpanlIfEntryEntry
   ACCESS     not-accessible
   STATUS     mandatory
   DESCRIPTION
     "This group contains the provisionable attributes for the ifEntry."
::= { mscMpanl 23 }

mscMpanlIfEntryEntry OBJECT-TYPE
   SYNTAX     MscMpanlIfEntryEntry
   ACCESS     not-accessible
   STATUS     mandatory
   DESCRIPTION
     "An entry in the mscMpanlIfEntryTable."
   INDEX {
      mscMpanlIndex }
::= { mscMpanlIfEntryTable 1 }

MscMpanlIfEntryEntry ::= SEQUENCE {
   mscMpanlIfAdminStatus
      INTEGER,
   mscMpanlIfIndex
      InterfaceIndex }

mscMpanlIfAdminStatus OBJECT-TYPE
   SYNTAX     INTEGER  {
                 up(1),
                 down(2),
                 testing(3) }
   ACCESS     read-write
   STATUS     mandatory
   DESCRIPTION
     "The desired state of the interface. The up state indicates the 
      interface is operational. The down state indicates the interface is not 
      operational. The testing state indicates that no operational packets 
      can be passed."
   DEFVAL     { up }
::= { mscMpanlIfEntryEntry 1 }

mscMpanlIfIndex OBJECT-TYPE
   SYNTAX     InterfaceIndex (1..65535)
   ACCESS     read-only
   STATUS     mandatory
   DESCRIPTION
     "This is the index for the IfEntry. Its value is automatically initialized 
      during the provisioning process."
::= { mscMpanlIfEntryEntry 2 }

mscMpanlOperStatusTable OBJECT-TYPE
   SYNTAX     SEQUENCE OF MscMpanlOperStatusEntry
   ACCESS     not-accessible
   STATUS     mandatory
   DESCRIPTION
     "This group includes the Operational Status attribute. This attribute 
      defines the current operational state of this component."
::= { mscMpanl 24 }

mscMpanlOperStatusEntry OBJECT-TYPE
   SYNTAX     MscMpanlOperStatusEntry
   ACCESS     not-accessible
   STATUS     mandatory
   DESCRIPTION
     "An entry in the mscMpanlOperStatusTable."
   INDEX {
      mscMpanlIndex }
::= { mscMpanlOperStatusTable 1 }

MscMpanlOperStatusEntry ::= SEQUENCE {
   mscMpanlSnmpOperStatus
      INTEGER }

mscMpanlSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { mscMpanlOperStatusEntry 1 }

mscMpanlOperTable OBJECT-TYPE
   SYNTAX     SEQUENCE OF MscMpanlOperEntry
   ACCESS     not-accessible
   STATUS     mandatory
   DESCRIPTION
     "This group contains miscelleneous operational attributes of the 
      MPANL service."
::= { mscMpanl 25 }

mscMpanlOperEntry OBJECT-TYPE
   SYNTAX     MscMpanlOperEntry
   ACCESS     not-accessible
   STATUS     mandatory
   DESCRIPTION
     "An entry in the mscMpanlOperTable."
   INDEX {
      mscMpanlIndex }
::= { mscMpanlOperTable 1 }

MscMpanlOperEntry ::= SEQUENCE {
   mscMpanlRoundTripDelay
      Unsigned32 }

mscMpanlRoundTripDelay OBJECT-TYPE
   SYNTAX     Unsigned32 (0..10000)
   ACCESS     read-only
   STATUS     mandatory
   DESCRIPTION
     "This attribute indicates the round trip delay of the MPANL 
      interface. The round trip delay measurement is only made when this 
      attribute is displayed. The measured value is rounded up to the next 
      millisecond. 
      
      This attribute has the value 0, if the delay measurement cannot be 
      made."
::= { mscMpanlOperEntry 1 }

mscMpanlFrmToIfByQueueTable OBJECT-TYPE
   SYNTAX     SEQUENCE OF MscMpanlFrmToIfByQueueEntry
   ACCESS     not-accessible
   STATUS     mandatory
   DESCRIPTION
     "This attribute counts the total number of frames transmitted to the 
      interface per egress emission priority queue since the component 
      has been activated. There is potentially a maximum of 4 emission 
      priority queues. The number of available egress queues varies 
      according to the value of the provisionable attribute 
      numberOfEmissionQs. Egress queue 0 has the lowest priority, while 
      egress queue 3 has the highest priority."
::= { mscMpanl 350 }

mscMpanlFrmToIfByQueueEntry OBJECT-TYPE
   SYNTAX     MscMpanlFrmToIfByQueueEntry
   ACCESS     not-accessible
   STATUS     mandatory
   DESCRIPTION
     "An entry in the mscMpanlFrmToIfByQueueTable."
   INDEX {
      mscMpanlIndex,
      mscMpanlFrmToIfByQueueIndex }
::= { mscMpanlFrmToIfByQueueTable 1 }

MscMpanlFrmToIfByQueueEntry ::= SEQUENCE {
   mscMpanlFrmToIfByQueueIndex
      Integer32,
   mscMpanlFrmToIfByQueueValue
      Unsigned32 }

mscMpanlFrmToIfByQueueIndex OBJECT-TYPE
   SYNTAX     Integer32 (0..3)
   ACCESS     not-accessible
   STATUS     mandatory
   DESCRIPTION
     "This variable represents the index for the mscMpanlFrmToIfByQueueTable."
::= { mscMpanlFrmToIfByQueueEntry 1 }

mscMpanlFrmToIfByQueueValue OBJECT-TYPE
   SYNTAX     Unsigned32 (0..4294967295)
   ACCESS     read-only
   STATUS     mandatory
   DESCRIPTION
     "This variable represents an individual value for the
      mscMpanlFrmToIfByQueueTable."
::= { mscMpanlFrmToIfByQueueEntry 2 }

mscMpanlOctetToIfByQueueTable OBJECT-TYPE
   SYNTAX     SEQUENCE OF MscMpanlOctetToIfByQueueEntry
   ACCESS     not-accessible
   STATUS     mandatory
   DESCRIPTION
     "This attribute counts the total number of octets transmitted from the 
      service to the interface per emission priority queue since the 
      component has been activated. There is potentially a maximum of 4 
      emission priority queues. The number of available egress queues 
      varies according to the value of the provisionable attribute 
      numberOfEmissionQs. Egress queue 0 has the lowest priority, while 
      egress queue 3 has the highest priority."
::= { mscMpanl 351 }

mscMpanlOctetToIfByQueueEntry OBJECT-TYPE
   SYNTAX     MscMpanlOctetToIfByQueueEntry
   ACCESS     not-accessible
   STATUS     mandatory
   DESCRIPTION
     "An entry in the mscMpanlOctetToIfByQueueTable."
   INDEX {
      mscMpanlIndex,
      mscMpanlOctetToIfByQueueIndex }
::= { mscMpanlOctetToIfByQueueTable 1 }

MscMpanlOctetToIfByQueueEntry ::= SEQUENCE {
   mscMpanlOctetToIfByQueueIndex
      Integer32,
   mscMpanlOctetToIfByQueueValue
      Unsigned32 }

mscMpanlOctetToIfByQueueIndex OBJECT-TYPE
   SYNTAX     Integer32 (0..3)
   ACCESS     not-accessible
   STATUS     mandatory
   DESCRIPTION
     "This variable represents the index for the mscMpanlOctetToIfByQueueTable."
::= { mscMpanlOctetToIfByQueueEntry 1 }

mscMpanlOctetToIfByQueueValue OBJECT-TYPE
   SYNTAX     Unsigned32 (0..4294967295)
   ACCESS     read-only
   STATUS     mandatory
   DESCRIPTION
     "This variable represents an individual value for the
      mscMpanlOctetToIfByQueueTable."
::= { mscMpanlOctetToIfByQueueEntry 2 }


-- Mpanl/<n> DataNetworkAddress
-- This component contains the attributes necessary for creating a 
-- virtual circuit. These attributes indicate the default call setup 
-- capabilities for the interface.

mscMpanlDna OBJECT IDENTIFIER ::= { mscMpanl 2 }



mscMpanlDnaRowStatusTable OBJECT-TYPE
   SYNTAX     SEQUENCE OF MscMpanlDnaRowStatusEntry
   ACCESS     not-accessible
   STATUS     mandatory
   DESCRIPTION
     "This entry controls the addition and deletion of 
      mscMpanlDna components."
::= { mscMpanlDna 1 }

mscMpanlDnaRowStatusEntry OBJECT-TYPE
   SYNTAX     MscMpanlDnaRowStatusEntry
   ACCESS     not-accessible
   STATUS     mandatory
   DESCRIPTION
     "A single entry in the table represents a single 
      mscMpanlDna component."
   INDEX {
      mscMpanlIndex,
      mscMpanlDnaIndex }
::= { mscMpanlDnaRowStatusTable 1 }

MscMpanlDnaRowStatusEntry ::= SEQUENCE {
   mscMpanlDnaRowStatus
      RowStatus,
   mscMpanlDnaComponentName
      DisplayString,
   mscMpanlDnaStorageType
      StorageType,
   mscMpanlDnaIndex
      NonReplicated }

mscMpanlDnaRowStatus OBJECT-TYPE
   SYNTAX     RowStatus 
   ACCESS     read-only
   STATUS     mandatory
   DESCRIPTION
     "This variable is used as the basis for SNMP naming of
      mscMpanlDna components.
      These components cannot be added nor deleted."
::= { mscMpanlDnaRowStatusEntry 1 }

mscMpanlDnaComponentName OBJECT-TYPE
   SYNTAX     DisplayString 
   ACCESS     read-only
   STATUS     mandatory
   DESCRIPTION
     "This variable provides the component's string name for
      use with the ASCII Console Interface"
::= { mscMpanlDnaRowStatusEntry 2 }

mscMpanlDnaStorageType OBJECT-TYPE
   SYNTAX     StorageType 
   ACCESS     read-only
   STATUS     mandatory
   DESCRIPTION
     "This variable represents the storage type value for the
      mscMpanlDna tables."
::= { mscMpanlDnaRowStatusEntry 4 }

mscMpanlDnaIndex OBJECT-TYPE
   SYNTAX     NonReplicated 
   ACCESS     not-accessible
   STATUS     mandatory
   DESCRIPTION
     "This variable represents the index for the mscMpanlDna tables."
::= { mscMpanlDnaRowStatusEntry 10 }

mscMpanlDnaOutgoingOptionsTable OBJECT-TYPE
   SYNTAX     SEQUENCE OF MscMpanlDnaOutgoingOptionsEntry
   ACCESS     not-accessible
   STATUS     mandatory
   DESCRIPTION
     "DnaOutOptionsProv group defines call options of a Dna for calls 
      which are made out of the interface represented by Dna. All these 
      options are not used for calls arriving to the interface represented by 
      Dna."
::= { mscMpanlDna 11 }

mscMpanlDnaOutgoingOptionsEntry OBJECT-TYPE
   SYNTAX     MscMpanlDnaOutgoingOptionsEntry
   ACCESS     not-accessible
   STATUS     mandatory
   DESCRIPTION
     "An entry in the mscMpanlDnaOutgoingOptionsTable."
   INDEX {
      mscMpanlIndex,
      mscMpanlDnaIndex }
::= { mscMpanlDnaOutgoingOptionsTable 1 }

MscMpanlDnaOutgoingOptionsEntry ::= SEQUENCE {
   mscMpanlDnaDefaultTransferPriority
      INTEGER }

mscMpanlDnaDefaultTransferPriority OBJECT-TYPE
   SYNTAX     INTEGER  {
                 n0(0),
                 n1(1),
                 n2(2),
                 n3(3),
                 n4(4),
                 n5(5),
                 n6(6),
                 n7(7),
                 n8(8),
                 n9(9),
                 n10(10),
                 n11(11),
                 n12(12),
                 n13(13),
                 n14(14),
                 n15(15) }
   ACCESS     read-write
   STATUS     mandatory
   DESCRIPTION
     "This attribute specifies the default transfer priority to network for all 
      outgoing calls using this particular Dna.
      
      The transfer priority is a preference configured for an application 
      according to its delay-sensitivity requirement. Frames with higher 
      transfer priority are served by the network before the frames with 
      lower priority. The transfer priority standard is defined to have 16 
      levels from 0 to 15.
      
      Each transfer priority n, where n indicates the transfer priority 
      index, contains a default setting for routing class of service 
      (multimedia, delay or throughput) and frame relay egress queue 
      (depending on the number of supported egress queues on the remote 
      end interface) specified by the routingClassOfService and 
      emissionPriority attributes provisioned in the Mod Frs DprsNet 
      Tpm/n component. The default mapping can be altered by a user if 
      required.
      
      The default defaultTransferPriority is 0."
   DEFVAL     { n0 }
::= { mscMpanlDnaOutgoingOptionsEntry 18 }

mscMpanlDnaCallOptionsTable OBJECT-TYPE
   SYNTAX     SEQUENCE OF MscMpanlDnaCallOptionsEntry
   ACCESS     not-accessible
   STATUS     mandatory
   DESCRIPTION
     "DnaCallOptions group defines additional options for calls not 
      related directly to direction of a call."
::= { mscMpanlDna 13 }

mscMpanlDnaCallOptionsEntry OBJECT-TYPE
   SYNTAX     MscMpanlDnaCallOptionsEntry
   ACCESS     not-accessible
   STATUS     mandatory
   DESCRIPTION
     "An entry in the mscMpanlDnaCallOptionsTable."
   INDEX {
      mscMpanlIndex,
      mscMpanlDnaIndex }
::= { mscMpanlDnaCallOptionsTable 1 }

MscMpanlDnaCallOptionsEntry ::= SEQUENCE {
   mscMpanlDnaAccountClass
      Unsigned32,
   mscMpanlDnaAccountCollection
      OCTET STRING,
   mscMpanlDnaServiceExchange
      Unsigned32,
   mscMpanlDnaEgressAccounting
      INTEGER }

mscMpanlDnaAccountClass OBJECT-TYPE
   SYNTAX     Unsigned32 (0..255)
   ACCESS     read-write
   STATUS     mandatory
   DESCRIPTION
     "This attribute specifies the accounting class which is reserved for 
      network operations usage. Its value is returned in the accounting 
      record in the local and remote service type attributes. Use of this 
      attribute is decided by network operator.
      This attribute is returned by the local VC in the accounting record 
      for all calls setup using this particular DNA."
   DEFVAL     { 0 }
::= { mscMpanlDnaCallOptionsEntry 10 }

mscMpanlDnaAccountCollection OBJECT-TYPE
   SYNTAX     OCTET STRING (SIZE (1))
   ACCESS     read-write
   STATUS     mandatory
   DESCRIPTION
     "This set attribute indicates that accounting records are to be 
      collected by the network for the various reasons: billing, test, study, 
      auditing.  The last of the parameters, force, indicates that 
      accounting records are to be collected irrespective of other 
      collection reasons.  The force option is available for X.75 Gateways 
      only. If none of these reasons are set, then accounting will be 
      suppressed.
      To set a specific accounting collection reason, the reason is entered 
      and the corresponding bit in the structure is set to a value of 1. To 
      turn off a specific accounting collection reason, the reason is 
      entered preceeded with the '^' character, and the corresponding bit 
      in the structure is set to a value of 0.
      The bit placement for the accounting collection reasons is as 
      follows:
      Bit 0  - Bill
      Bit 1  - Test
      Bit 2  - Study
      Bit 3  - Audit
      Bit 4  - Force

      Description of bits:
      bill(0)
      test(1)
      study(2)
      audit(3)
      force(4)"
   DEFVAL     { '80'H }
::= { mscMpanlDnaCallOptionsEntry 11 }

mscMpanlDnaServiceExchange OBJECT-TYPE
   SYNTAX     Unsigned32 (0..255)
   ACCESS     read-write
   STATUS     mandatory
   DESCRIPTION
     "This attribute is an arbitrary number, Data Service Exchange, as 
      entered by the network operator and reported in accounting record. 
      It is converted into an internal 8-bit integer value for use in the 
      accounting record as well as in various X.25 and X.75 Tariff 
      utilities."
   DEFVAL     { 0 }
::= { mscMpanlDnaCallOptionsEntry 12 }

mscMpanlDnaEgressAccounting OBJECT-TYPE
   SYNTAX     INTEGER  {
                 no(0),
                 yes(1) }
   ACCESS     read-write
   STATUS     mandatory
   DESCRIPTION
     "This attribute specifies if Egress accounting is enabled by the 
      MPANL service. Disabling of Egress accounting means that only 
      segment counts are collected by VC and there are no frame relay 
      counts in accounting records for the MPANL service. Enabling of 
      Egress accounting means that the accounting records for MPANL 
      contain frame relay specific counts."
   DEFVAL     { no }
::= { mscMpanlDnaCallOptionsEntry 13 }


-- 
-- Mpanl/<n> Framer
-- The Framer component controls link layer framing for application 
-- components sending and receiving data on a link interface. It is also 
-- through Framer, that an application component is associated with a 
-- specific hardware link interface.
-- 
-- The Framer component provides provisionable attributes related to 
-- datapath aspects of the hardware interface (such as crc and frame 
-- length) rather than interface specific attributes (such as modem 
-- leads and clocking) which are associated with specific hardware 
-- components (such as V35/n or DS1/n). The Framer component also 
-- provides a provisionable attribute which binds the application 
-- component to a specific hardware component.
-- 
-- The Framer component contains operational attributes for link 
-- interface datapath statistics (such as frame counts and aborts).
-- 

mscMpanlFramer OBJECT IDENTIFIER ::= { mscMpanl 3 }



mscMpanlFramerRowStatusTable OBJECT-TYPE
   SYNTAX     SEQUENCE OF MscMpanlFramerRowStatusEntry
   ACCESS     not-accessible
   STATUS     mandatory
   DESCRIPTION
     "This entry controls the addition and deletion of 
      mscMpanlFramer components."
::= { mscMpanlFramer 1 }

mscMpanlFramerRowStatusEntry OBJECT-TYPE
   SYNTAX     MscMpanlFramerRowStatusEntry
   ACCESS     not-accessible
   STATUS     mandatory
   DESCRIPTION
     "A single entry in the table represents a single 
      mscMpanlFramer component."
   INDEX {
      mscMpanlIndex,
      mscMpanlFramerIndex }
::= { mscMpanlFramerRowStatusTable 1 }

MscMpanlFramerRowStatusEntry ::= SEQUENCE {
   mscMpanlFramerRowStatus
      RowStatus,
   mscMpanlFramerComponentName
      DisplayString,
   mscMpanlFramerStorageType
      StorageType,
   mscMpanlFramerIndex
      NonReplicated }

mscMpanlFramerRowStatus OBJECT-TYPE
   SYNTAX     RowStatus 
   ACCESS     read-write
   STATUS     mandatory
   DESCRIPTION
     "This variable is used as the basis for SNMP naming of
      mscMpanlFramer components.
      These components can be added and deleted."
::= { mscMpanlFramerRowStatusEntry 1 }

mscMpanlFramerComponentName OBJECT-TYPE
   SYNTAX     DisplayString 
   ACCESS     read-only
   STATUS     mandatory
   DESCRIPTION
     "This variable provides the component's string name for
      use with the ASCII Console Interface"
::= { mscMpanlFramerRowStatusEntry 2 }

mscMpanlFramerStorageType OBJECT-TYPE
   SYNTAX     StorageType 
   ACCESS     read-only
   STATUS     mandatory
   DESCRIPTION
     "This variable represents the storage type value for the
      mscMpanlFramer tables."
::= { mscMpanlFramerRowStatusEntry 4 }

mscMpanlFramerIndex OBJECT-TYPE
   SYNTAX     NonReplicated 
   ACCESS     not-accessible
   STATUS     mandatory
   DESCRIPTION
     "This variable represents the index for the mscMpanlFramer tables."
::= { mscMpanlFramerRowStatusEntry 10 }

mscMpanlFramerProvTable OBJECT-TYPE
   SYNTAX     SEQUENCE OF MscMpanlFramerProvEntry
   ACCESS     not-accessible
   STATUS     mandatory
   DESCRIPTION
     "This group contains the base provisioning data for the Framer 
      component. Application or hardware interface specific provisioning 
      data is contained in other provisionable Framer groups."
::= { mscMpanlFramer 10 }

mscMpanlFramerProvEntry OBJECT-TYPE
   SYNTAX     MscMpanlFramerProvEntry
   ACCESS     not-accessible
   STATUS     mandatory
   DESCRIPTION
     "An entry in the mscMpanlFramerProvTable."
   INDEX {
      mscMpanlIndex,
      mscMpanlFramerIndex }
::= { mscMpanlFramerProvTable 1 }

MscMpanlFramerProvEntry ::= SEQUENCE {
   mscMpanlFramerInterfaceName
      Link }

mscMpanlFramerInterfaceName OBJECT-TYPE
   SYNTAX     Link 
   ACCESS     read-write
   STATUS     mandatory
   DESCRIPTION
     "This attribute contains a hardware component name.
      
      The attribute associates the application with a specific link. This 
      defines the module processor on which Framer's parent component 
      (as well as Framer itself) will run."
::= { mscMpanlFramerProvEntry 1 }

mscMpanlFramerLinkTable OBJECT-TYPE
   SYNTAX     SEQUENCE OF MscMpanlFramerLinkEntry
   ACCESS     not-accessible
   STATUS     mandatory
   DESCRIPTION
     "This group contains attributes defining the framing of data on the 
      link interface."
::= { mscMpanlFramer 11 }

mscMpanlFramerLinkEntry OBJECT-TYPE
   SYNTAX     MscMpanlFramerLinkEntry
   ACCESS     not-accessible
   STATUS     mandatory
   DESCRIPTION
     "An entry in the mscMpanlFramerLinkTable."
   INDEX {
      mscMpanlIndex,
      mscMpanlFramerIndex }
::= { mscMpanlFramerLinkTable 1 }

MscMpanlFramerLinkEntry ::= SEQUENCE {
   mscMpanlFramerDataInversion
      INTEGER,
   mscMpanlFramerFrameCrcType
      INTEGER,
   mscMpanlFramerFlagsBetweenFrames
      Unsigned32 }

mscMpanlFramerDataInversion OBJECT-TYPE
   SYNTAX     INTEGER  {
                 off(0),
                 on(16) }
   ACCESS     read-write
   STATUS     mandatory
   DESCRIPTION
     "This attribute determines whether data bits are to be inverted (1 to 0 
      and 0 to 1) before transmission of frames to the interface. If the 
      value of this attribute is On, the incoming data bits will also be 
      inverted when frames are received from the link before being 
      processed.
      
      This option is typically used in hdlc framing mode when inversion 
      is used to guarantee 1's density.
      
      Note that aborts (in hdlc and interrupting modes) are corrupted 
      when data is inverted.
      
      This attribute may only take its default value for non-MSA cards."
   DEFVAL     { off }
::= { mscMpanlFramerLinkEntry 2 }

mscMpanlFramerFrameCrcType OBJECT-TYPE
   SYNTAX     INTEGER  {
                 crc16(0),
                 crc32(1),
                 noCrc(2) }
   ACCESS     read-write
   STATUS     mandatory
   DESCRIPTION
     "This attribute defines the type of CRC used. 
      
      The CRC value calculated is appended to the end of the frames 
      transmitted to the link. The CRC value is removed from the end of 
      frames received from the link and checked for correctness.
      NoCrc means that CRC is not used.
      
      This attribute may take only its default value for non-MSA cards."
   DEFVAL     { crc16 }
::= { mscMpanlFramerLinkEntry 3 }

mscMpanlFramerFlagsBetweenFrames OBJECT-TYPE
   SYNTAX     Unsigned32 (1..16)
   ACCESS     read-write
   STATUS     mandatory
   DESCRIPTION
     "This attribute defines the number of flags that are inserted between 
      frames sent to the link interface."
   DEFVAL     { 1 }
::= { mscMpanlFramerLinkEntry 4 }

mscMpanlFramerStateTable OBJECT-TYPE
   SYNTAX     SEQUENCE OF MscMpanlFramerStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscMpanlFramer 12 }

mscMpanlFramerStateEntry OBJECT-TYPE
   SYNTAX     MscMpanlFramerStateEntry
   ACCESS     not-accessible
   STATUS     mandatory
   DESCRIPTION
     "An entry in the mscMpanlFramerStateTable."
   INDEX {
      mscMpanlIndex,
      mscMpanlFramerIndex }
::= { mscMpanlFramerStateTable 1 }

MscMpanlFramerStateEntry ::= SEQUENCE {
   mscMpanlFramerAdminState
      INTEGER,
   mscMpanlFramerOperationalState
      INTEGER,
   mscMpanlFramerUsageState
      INTEGER }

mscMpanlFramerAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscMpanlFramerStateEntry 1 }

mscMpanlFramerOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscMpanlFramerStateEntry 2 }

mscMpanlFramerUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscMpanlFramerStateEntry 3 }

mscMpanlFramerStatsTable OBJECT-TYPE
   SYNTAX     SEQUENCE OF MscMpanlFramerStatsEntry
   ACCESS     not-accessible
   STATUS     mandatory
   DESCRIPTION
     "This group contains the operational statistics data for a Framer 
      component."
::= { mscMpanlFramer 13 }

mscMpanlFramerStatsEntry OBJECT-TYPE
   SYNTAX     MscMpanlFramerStatsEntry
   ACCESS     not-accessible
   STATUS     mandatory
   DESCRIPTION
     "An entry in the mscMpanlFramerStatsTable."
   INDEX {
      mscMpanlIndex,
      mscMpanlFramerIndex }
::= { mscMpanlFramerStatsTable 1 }

MscMpanlFramerStatsEntry ::= SEQUENCE {
   mscMpanlFramerFrmToIf
      Counter32,
   mscMpanlFramerFrmFromIf
      Counter32,
   mscMpanlFramerOctetFromIf
      Counter32,
   mscMpanlFramerAborts
      Counter32,
   mscMpanlFramerCrcErrors
      Counter32,
   mscMpanlFramerLrcErrors
      Counter32,
   mscMpanlFramerNonOctetErrors
      Counter32,
   mscMpanlFramerOverruns
      Counter32,
   mscMpanlFramerUnderruns
      Counter32,
   mscMpanlFramerLargeFrmErrors
      Counter32,
   mscMpanlFramerFrmModeErrors
      Counter32,
   mscMpanlFramerFrmToIf64
      PassportCounter64,
   mscMpanlFramerFrmFromIf64
      PassportCounter64,
   mscMpanlFramerOctetFromIf64
      PassportCounter64 }

mscMpanlFramerFrmToIf OBJECT-TYPE
   SYNTAX     Counter32 
   ACCESS     read-only
   STATUS     obsolete
   DESCRIPTION
     "The number of frames transmitted to the link interface by Framer.
      
      Note: This does not include the number of frames transmitted 
      directly to the hardware queue, thus bypassing the Framer 
      component."
::= { mscMpanlFramerStatsEntry 1 }

mscMpanlFramerFrmFromIf OBJECT-TYPE
   SYNTAX     Counter32 
   ACCESS     read-only
   STATUS     obsolete
   DESCRIPTION
     "The number of frames received from the link interface by Framer."
::= { mscMpanlFramerStatsEntry 2 }

mscMpanlFramerOctetFromIf OBJECT-TYPE
   SYNTAX     Counter32 
   ACCESS     read-only
   STATUS     obsolete
   DESCRIPTION
     "The number of bytes received from the link interface by Framer."
::= { mscMpanlFramerStatsEntry 3 }

mscMpanlFramerAborts OBJECT-TYPE
   SYNTAX     Counter32 
   ACCESS     read-only
   STATUS     mandatory
   DESCRIPTION
     "This attribute is the total number of aborts received."
::= { mscMpanlFramerStatsEntry 4 }

mscMpanlFramerCrcErrors OBJECT-TYPE
   SYNTAX     Counter32 
   ACCESS     read-only
   STATUS     mandatory
   DESCRIPTION
     "This attribute is the total number of frames with CRC errors, 
      occurring in the receive direction from the link."
::= { mscMpanlFramerStatsEntry 5 }

mscMpanlFramerLrcErrors OBJECT-TYPE
   SYNTAX     Counter32 
   ACCESS     read-only
   STATUS     mandatory
   DESCRIPTION
     "This attribute is the total number of frames with LRC errors, 
      occurring in the Tx link prior to transmission onto the link."
::= { mscMpanlFramerStatsEntry 6 }

mscMpanlFramerNonOctetErrors OBJECT-TYPE
   SYNTAX     Counter32 
   ACCESS     read-only
   STATUS     mandatory
   DESCRIPTION
     "This attribute is the total number of frames that were non octet 
      aligned."
::= { mscMpanlFramerStatsEntry 7 }

mscMpanlFramerOverruns OBJECT-TYPE
   SYNTAX     Counter32 
   ACCESS     read-only
   STATUS     mandatory
   DESCRIPTION
     "This attribute is the total number of frames received from the link 
      for which overruns occurred."
::= { mscMpanlFramerStatsEntry 8 }

mscMpanlFramerUnderruns OBJECT-TYPE
   SYNTAX     Counter32 
   ACCESS     read-only
   STATUS     mandatory
   DESCRIPTION
     "This attribute is the total number of frames transmitted to the link 
      for which underruns occurred."
::= { mscMpanlFramerStatsEntry 9 }

mscMpanlFramerLargeFrmErrors OBJECT-TYPE
   SYNTAX     Counter32 
   ACCESS     read-only
   STATUS     mandatory
   DESCRIPTION
     "This attribute is the total number of frames received which were too 
      large. The frame execeeded the maximumFrameLengthLimit 
      provisioned attribute or it contained more than the 255 block 
      hardware limit."
::= { mscMpanlFramerStatsEntry 10 }

mscMpanlFramerFrmModeErrors OBJECT-TYPE
   SYNTAX     Counter32 
   ACCESS     read-only
   STATUS     mandatory
   DESCRIPTION
     "This attribute is the total number of frames detected with framing 
      mode errors. A framingModeError is flagged when frames are 
      inconsistent with the specified framingType, that is when 
      interrupting frames are used while running in hdlc mode."
::= { mscMpanlFramerStatsEntry 11 }

mscMpanlFramerFrmToIf64 OBJECT-TYPE
   SYNTAX     PassportCounter64 
   ACCESS     read-only
   STATUS     mandatory
   DESCRIPTION
     "The number of frames transmitted to the link interface by Framer.
      
      Note: This does not include the number of frames transmitted 
      directly to the hardware queue, thus bypassing the Framer 
      component."
::= { mscMpanlFramerStatsEntry 14 }

mscMpanlFramerFrmFromIf64 OBJECT-TYPE
   SYNTAX     PassportCounter64 
   ACCESS     read-only
   STATUS     mandatory
   DESCRIPTION
     "The number of frames received from the link interface by Framer."
::= { mscMpanlFramerStatsEntry 15 }

mscMpanlFramerOctetFromIf64 OBJECT-TYPE
   SYNTAX     PassportCounter64 
   ACCESS     read-only
   STATUS     mandatory
   DESCRIPTION
     "The number of bytes received from the link interface by Framer."
::= { mscMpanlFramerStatsEntry 16 }

mscMpanlFramerUtilTable OBJECT-TYPE
   SYNTAX     SEQUENCE OF MscMpanlFramerUtilEntry
   ACCESS     not-accessible
   STATUS     mandatory
   DESCRIPTION
     "This group contains the link utilizaiton operational data for a 
      Framer component."
::= { mscMpanlFramer 14 }

mscMpanlFramerUtilEntry OBJECT-TYPE
   SYNTAX     MscMpanlFramerUtilEntry
   ACCESS     not-accessible
   STATUS     mandatory
   DESCRIPTION
     "An entry in the mscMpanlFramerUtilTable."
   INDEX {
      mscMpanlIndex,
      mscMpanlFramerIndex }
::= { mscMpanlFramerUtilTable 1 }

MscMpanlFramerUtilEntry ::= SEQUENCE {
   mscMpanlFramerNormPrioLinkUtilToIf
      Gauge32,
   mscMpanlFramerNormPrioLinkUtilFromIf
      Gauge32 }

mscMpanlFramerNormPrioLinkUtilToIf OBJECT-TYPE
   SYNTAX     Gauge32 (0..100)
   ACCESS     read-only
   STATUS     mandatory
   DESCRIPTION
     "This attribute is the utilization of the normal and high priority data 
      traffic (interruptable traffic) sent to the link as a percentage of the 
      available bandwidth on the link. Note that this indluces traffic with 
      Transfer Priorities (TP) of 0, 6 and 9 and/or Emission Priority of 2 
      and 3. The utilization is the average for the last minute."
   DEFVAL     { 0 }
::= { mscMpanlFramerUtilEntry 1 }

mscMpanlFramerNormPrioLinkUtilFromIf OBJECT-TYPE
   SYNTAX     Gauge32 (0..100)
   ACCESS     read-only
   STATUS     mandatory
   DESCRIPTION
     "This attribute is the utilization of the normal and high priority data 
      traffic (interruptable traffic) received from the link as a percentage 
      of the available bandwidth on the link. Note that this includes traffic 
      with Transfer Priorities (TP) of 0, 6 and 9 and/or Emission Priority 
      of 2 and 3. The utilization is the average for the last minute."
   DEFVAL     { 0 }
::= { mscMpanlFramerUtilEntry 3 }

-- 
-- *** THIS SUBTREE CURRENTLY NOT IMPLEMENTED ***
-- 

-- Mpanl/<n> PrefixDataNetworkAddress/<npi>,<dna>
-- This component identifies a prefixDNA provided by the MPA DTE 
-- via the the MPANL protocol. It has no attributes because all of the 
-- relevant information is contained in the indices of this component. 
-- The first index is the numbering plan indicator (x121/e164) and the 
-- second index is the prefixDNA digits. 

mscMpanlPrefixDna OBJECT IDENTIFIER ::= { mscMpanl 4 }



mscMpanlPrefixDnaRowStatusTable OBJECT-TYPE
   SYNTAX     SEQUENCE OF MscMpanlPrefixDnaRowStatusEntry
   ACCESS     not-accessible
   STATUS     mandatory
   DESCRIPTION
     "*** THIS TABLE CURRENTLY NOT IMPLEMENTED ***

      This entry controls the addition and deletion of 
      mscMpanlPrefixDna components."
::= { mscMpanlPrefixDna 1 }

mscMpanlPrefixDnaRowStatusEntry OBJECT-TYPE
   SYNTAX     MscMpanlPrefixDnaRowStatusEntry
   ACCESS     not-accessible
   STATUS     mandatory
   DESCRIPTION
     "A single entry in the table represents a single 
      mscMpanlPrefixDna component."
   INDEX {
      mscMpanlIndex,
      mscMpanlPrefixDnaNumberingPlanIndicatorIndex,
      mscMpanlPrefixDnaDataNetworkAddressIndex }
::= { mscMpanlPrefixDnaRowStatusTable 1 }

MscMpanlPrefixDnaRowStatusEntry ::= SEQUENCE {
   mscMpanlPrefixDnaRowStatus
      RowStatus,
   mscMpanlPrefixDnaComponentName
      DisplayString,
   mscMpanlPrefixDnaStorageType
      StorageType,
   mscMpanlPrefixDnaNumberingPlanIndicatorIndex
      INTEGER,
   mscMpanlPrefixDnaDataNetworkAddressIndex
      DigitString }

mscMpanlPrefixDnaRowStatus OBJECT-TYPE
   SYNTAX     RowStatus 
   ACCESS     read-only
   STATUS     mandatory
   DESCRIPTION
     "This variable is used as the basis for SNMP naming of
      mscMpanlPrefixDna components.
      These components cannot be added nor deleted."
::= { mscMpanlPrefixDnaRowStatusEntry 1 }

mscMpanlPrefixDnaComponentName OBJECT-TYPE
   SYNTAX     DisplayString 
   ACCESS     read-only
   STATUS     mandatory
   DESCRIPTION
     "This variable provides the component's string name for
      use with the ASCII Console Interface"
::= { mscMpanlPrefixDnaRowStatusEntry 2 }

mscMpanlPrefixDnaStorageType OBJECT-TYPE
   SYNTAX     StorageType 
   ACCESS     read-only
   STATUS     mandatory
   DESCRIPTION
     "This variable represents the storage type value for the
      mscMpanlPrefixDna tables."
::= { mscMpanlPrefixDnaRowStatusEntry 4 }

mscMpanlPrefixDnaNumberingPlanIndicatorIndex OBJECT-TYPE
   SYNTAX     INTEGER  {
                 x121(0),
                 e164(1) }
   ACCESS     not-accessible
   STATUS     mandatory
   DESCRIPTION
     "This variable represents an index for the mscMpanlPrefixDna tables."
::= { mscMpanlPrefixDnaRowStatusEntry 10 }

mscMpanlPrefixDnaDataNetworkAddressIndex OBJECT-TYPE
   SYNTAX     DigitString (SIZE (1..15))
   ACCESS     not-accessible
   STATUS     mandatory
   DESCRIPTION
     "This variable represents an index for the mscMpanlPrefixDna tables."
::= { mscMpanlPrefixDnaRowStatusEntry 11 }

-- 
-- *** THIS SUBTREE CURRENTLY NOT IMPLEMENTED ***
-- 

-- Mpanl/n DataLinkConnectionIdentifier/n
-- This component is responsible for the Frame Relay U-plane (User-
-- plane) protocol for the specified instance. There can be many 
-- instances of Dlci for each Mpanl. The instance value is used to 
-- identify the logical connection, multiplexed within the physical 
-- channel, with which a frame is associated. All frames carried within 
-- a particular physical channel and having the same DLCI value are 
-- associated with the same logical connection.
-- 
-- A DLCI refers to a switched virtual circuit (SVC) which is created 
-- dynamically through signaling.

mscMpanlDlci OBJECT IDENTIFIER ::= { mscMpanl 5 }



mscMpanlDlciRowStatusTable OBJECT-TYPE
   SYNTAX     SEQUENCE OF MscMpanlDlciRowStatusEntry
   ACCESS     not-accessible
   STATUS     mandatory
   DESCRIPTION
     "*** THIS TABLE CURRENTLY NOT IMPLEMENTED ***

      This entry controls the addition and deletion of 
      mscMpanlDlci components."
::= { mscMpanlDlci 1 }

mscMpanlDlciRowStatusEntry OBJECT-TYPE
   SYNTAX     MscMpanlDlciRowStatusEntry
   ACCESS     not-accessible
   STATUS     mandatory
   DESCRIPTION
     "A single entry in the table represents a single 
      mscMpanlDlci component."
   INDEX {
      mscMpanlIndex,
      mscMpanlDlciIndex }
::= { mscMpanlDlciRowStatusTable 1 }

MscMpanlDlciRowStatusEntry ::= SEQUENCE {
   mscMpanlDlciRowStatus
      RowStatus,
   mscMpanlDlciComponentName
      DisplayString,
   mscMpanlDlciStorageType
      StorageType,
   mscMpanlDlciIndex
      Integer32 }

mscMpanlDlciRowStatus OBJECT-TYPE
   SYNTAX     RowStatus 
   ACCESS     read-only
   STATUS     mandatory
   DESCRIPTION
     "This variable is used as the basis for SNMP naming of
      mscMpanlDlci components.
      These components cannot be added nor deleted."
::= { mscMpanlDlciRowStatusEntry 1 }

mscMpanlDlciComponentName OBJECT-TYPE
   SYNTAX     DisplayString 
   ACCESS     read-only
   STATUS     mandatory
   DESCRIPTION
     "This variable provides the component's string name for
      use with the ASCII Console Interface"
::= { mscMpanlDlciRowStatusEntry 2 }

mscMpanlDlciStorageType OBJECT-TYPE
   SYNTAX     StorageType 
   ACCESS     read-only
   STATUS     mandatory
   DESCRIPTION
     "This variable represents the storage type value for the
      mscMpanlDlci tables."
::= { mscMpanlDlciRowStatusEntry 4 }

mscMpanlDlciIndex OBJECT-TYPE
   SYNTAX     Integer32 (17..1007)
   ACCESS     not-accessible
   STATUS     mandatory
   DESCRIPTION
     "This variable represents the index for the mscMpanlDlci tables."
::= { mscMpanlDlciRowStatusEntry 10 }

mscMpanlDlciStateTable OBJECT-TYPE
   SYNTAX     SEQUENCE OF MscMpanlDlciStateEntry
   ACCESS     not-accessible
   STATUS     mandatory
   DESCRIPTION
     "*** THIS TABLE CURRENTLY NOT IMPLEMENTED ***

      This group contains the three OSI State attributes and the six OSI 
      Status attributes. The descriptions generically indicate what each 
      attribute implies about the component. Note that not all the values 
      and state combinations described here are supported by every 
      component which uses this group. For component-specific 
      information and the valid state combinations, refer to NTP 241-
      7001-150, Passport Operations and Maintenance Guide."
::= { mscMpanlDlci 10 }

mscMpanlDlciStateEntry OBJECT-TYPE
   SYNTAX     MscMpanlDlciStateEntry
   ACCESS     not-accessible
   STATUS     mandatory
   DESCRIPTION
     "An entry in the mscMpanlDlciStateTable."
   INDEX {
      mscMpanlIndex,
      mscMpanlDlciIndex }
::= { mscMpanlDlciStateTable 1 }

MscMpanlDlciStateEntry ::= SEQUENCE {
   mscMpanlDlciAdminState
      INTEGER,
   mscMpanlDlciOperationalState
      INTEGER,
   mscMpanlDlciUsageState
      INTEGER,
   mscMpanlDlciAvailabilityStatus
      OCTET STRING,
   mscMpanlDlciProceduralStatus
      OCTET STRING,
   mscMpanlDlciControlStatus
      OCTET STRING,
   mscMpanlDlciAlarmStatus
      OCTET STRING,
   mscMpanlDlciStandbyStatus
      INTEGER,
   mscMpanlDlciUnknownStatus
      INTEGER }

mscMpanlDlciAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component.
      
      The OSI Status attributes, if supported by the component, may 
      provide more details, qualifying the state of the component."
   DEFVAL     { unlocked }
::= { mscMpanlDlciStateEntry 1 }

mscMpanlDlciOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle.
      
      The OSI Status attributes, if supported by the component, may 
      provide more details, qualifying the state of the component."
   DEFVAL     { disabled }
::= { mscMpanlDlciStateEntry 2 }

mscMpanlDlciUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time.
      
      The OSI Status attributes, if supported by the component, may 
      provide more details, qualifying the state of the component."
   DEFVAL     { idle }
::= { mscMpanlDlciStateEntry 3 }

mscMpanlDlciAvailabilityStatus OBJECT-TYPE
   SYNTAX     OCTET STRING (SIZE (2))
   ACCESS     read-only
   STATUS     mandatory
   DESCRIPTION
     "If supported by the component, this attribute indicates the OSI 
      Availability status of the component. Note that, even though it is 
      defined as a multi-valued set, at most one value is shown to the user.
      
      When no values are in the set, this indicates that either the attribute 
      is not supported or that none of the status conditions described 
      below are present.
      
      The value inTest indicates that the resource is undergoing a test 
      procedure. If adminState is locked or shuttingDown, the normal 
      users are precluded from using the resource and controlStatus is 
      reservedForTest. Tests that do not exclude additional users can be 
      present in any operational or administrative state but the 
      reservedForTest condition should not be present.
      
      The value failed indicates that the component has an internal fault 
      that prevents it from operating. The operationalState is disabled.
      
      The value dependency indicates that the component cannot operate 
      because some other resource on which it depends is unavailable. 
      The operationalState is disabled.
      
      The value powerOff indicates the resource requires power to be 
      applied and it is not powered on. The operationalState is disabled.
      
      The value offLine indicates the resource requires a routine 
      operation (either manual, automatic, or both) to be performed to 
      place it on-line and make it available for use. The operationalState 
      is disabled.
      
      The value offDuty indicates the resource is inactive in accordance 
      with a predetermined time schedule. In the absence of other 
      disabling conditions, the operationalState is enabled or disabled.
      
      The value degraded indicates the service provided by the 
      component is degraded in some way, such as in speed or operating 
      capacity. However, the resource remains available for service. The 
      operationalState is enabled.
      
      The value notInstalled indicates the resource is not present. The 
      operationalState is disabled.
      
      The value logFull is not used.

      Description of bits:
      inTest(0)
      failed(1)
      powerOff(2)
      offLine(3)
      offDuty(4)
      dependency(5)
      degraded(6)
      notInstalled(7)
      logFull(8)"
::= { mscMpanlDlciStateEntry 4 }

mscMpanlDlciProceduralStatus OBJECT-TYPE
   SYNTAX     OCTET STRING (SIZE (1))
   ACCESS     read-only
   STATUS     mandatory
   DESCRIPTION
     "If supported by the component, this attribute indicates the OSI 
      Procedural status of the component. Note that, even though it is 
      defined as a multi-valued set, at most one value is shown to the user.
      
      When no values are in the set, this indicates that either the attribute 
      is not supported or that none of the status conditions described 
      below are present.
      
      The value initializationRequired indicates (for a resource which 
      doesn't initialize autonomously) that initialization is required before 
      it can perform its normal functions, and this procedure has not been 
      initiated. The operationalState is disabled.
      
      The value notInitialized indicates (for a resource which does 
      initialize autonomously) that initialization is required before it can 
      perform its normal functions, and this procedure has not been 
      initiated. The operationalState may be enabled or disabled.
      
      The value initializing indicates that initialization has been initiated 
      but is not yet complete. The operationalState may be enabled or 
      disabled.
      
      The value reporting indicates the resource has completed some 
      processing operation and is notifying the results. The 
      operationalState is enabled.
      
      The value terminating indicates the component is in a termination 
      phase. If the resource doesn't reinitialize autonomously, 
      operationalState is disabled; otherwise it is enabled or disabled.

      Description of bits:
      initializationRequired(0)
      notInitialized(1)
      initializing(2)
      reporting(3)
      terminating(4)"
::= { mscMpanlDlciStateEntry 5 }

mscMpanlDlciControlStatus OBJECT-TYPE
   SYNTAX     OCTET STRING (SIZE (1))
   ACCESS     read-only
   STATUS     mandatory
   DESCRIPTION
     "If supported by the component, this attribute indicates the OSI 
      Control status of the component. Note that, even though it is defined 
      as a multi-valued set, at most one value is shown to the user.
      
      When no values are in the set, this indicates that either the attribute 
      is not supported or that none of the status conditions described 
      below are present.
      
      The value subjectToTest indicates the resource is available but tests 
      may be conducted simultaneously at unpredictable times, which 
      may cause it to exhibit unusual characteristics.
      
      The value partOfServicesLocked indicates that part of the service is 
      restricted from users of a resource. The adminState is unlocked.
      
      The value reservedForTest indicates that the component is 
      administratively unavailable because it is undergoing a test 
      procedure. The adminState is locked.
      
      The value suspended indicates that the service has been 
      administratively suspended.

      Description of bits:
      subjectToTest(0)
      partOfServicesLocked(1)
      reservedForTest(2)
      suspended(3)"
::= { mscMpanlDlciStateEntry 6 }

mscMpanlDlciAlarmStatus OBJECT-TYPE
   SYNTAX     OCTET STRING (SIZE (1))
   ACCESS     read-only
   STATUS     mandatory
   DESCRIPTION
     "If supported by the component, this attribute indicates the OSI 
      Alarm status of the component. Note that, even though it is defined 
      as a multi-valued set, at most one value is shown to the user.
      
      When no values are in the set, this indicates that either the attribute 
      is not supported or that none of the status conditions described 
      below are present.
      
      The value underRepair indicates the component is currently being 
      repaired. The operationalState is enabled or disabled.
      
      The value critical indicates one or more critical alarms are 
      outstanding against the component. Other, less severe, alarms may 
      also be outstanding. The operationalState is enabled or disabled.
      
      The value major indicates one or more major alarms are 
      outstanding against the component. Other, less severe, alarms may 
      also be outstanding. The operationalState is enabled or disabled.
      
      The value minor indicates one or more minor alarms are 
      outstanding against the component. Other, less severe, alarms may 
      also be outstanding. The operationalState is enabled or disabled.
      
      The value alarmOutstanding generically indicates that an alarm of 
      some severity is outstanding against the component.

      Description of bits:
      underRepair(0)
      critical(1)
      major(2)
      minor(3)
      alarmOutstanding(4)"
::= { mscMpanlDlciStateEntry 7 }

mscMpanlDlciStandbyStatus OBJECT-TYPE
   SYNTAX     INTEGER  {
                 hotStandby(0),
                 coldStandby(1),
                 providingService(2),
                 notSet(15) }
   ACCESS     read-only
   STATUS     mandatory
   DESCRIPTION
     "If supported by the component, this attribute indicates the OSI 
      Standby status of the component.
      
      The value notSet indicates that either the attribute is not supported 
      or that none of the status conditions described below are present. 
      Note that this is a non-standard value, used because the original 
      specification indicated this attribute was set-valued and thus, did not 
      provide a value to indicate that none of the other three are 
      applicable.
      
      The value hotStandby indicates that the resource is not providing 
      service but will be immediately able to take over the role of the 
      resource to be backed up, without initialization activity, and 
      containing the same information as the resource to be backed up.
      
      The value coldStandby indicates the resource is a backup for 
      another resource but will not be immediately able to take over the 
      role of the backed up resource and will require some initialization 
      activity.
      
      The value providingService indicates that this component, as a 
      backup resource, is currently backing up another resource."
   DEFVAL     { notSet }
::= { mscMpanlDlciStateEntry 8 }

mscMpanlDlciUnknownStatus OBJECT-TYPE
   SYNTAX     INTEGER  {
                 false(0),
                 true(1) }
   ACCESS     read-only
   STATUS     mandatory
   DESCRIPTION
     "This attribute indicates the OSI Unknown status of the component.
      
      The value false indicates that all of the other OSI State and Status 
      attribute values can be considered accurate.
      
      The value true indicates that the actual state of the component is not 
      known for sure."
   DEFVAL     { false }
::= { mscMpanlDlciStateEntry 9 }

mscMpanlDlciCalldTable OBJECT-TYPE
   SYNTAX     SEQUENCE OF MscMpanlDlciCalldEntry
   ACCESS     not-accessible
   STATUS     mandatory
   DESCRIPTION
     "*** THIS TABLE CURRENTLY NOT IMPLEMENTED ***

      This group of attributes describes the characteristics of the call such 
      as call type and call state."
::= { mscMpanlDlci 11 }

mscMpanlDlciCalldEntry OBJECT-TYPE
   SYNTAX     MscMpanlDlciCalldEntry
   ACCESS     not-accessible
   STATUS     mandatory
   DESCRIPTION
     "An entry in the mscMpanlDlciCalldTable."
   INDEX {
      mscMpanlIndex,
      mscMpanlDlciIndex }
::= { mscMpanlDlciCalldTable 1 }

MscMpanlDlciCalldEntry ::= SEQUENCE {
   mscMpanlDlciQ933CallState
      INTEGER,
   mscMpanlDlciQ933CallReference
      Unsigned32 }

mscMpanlDlciQ933CallState OBJECT-TYPE
   SYNTAX     INTEGER  {
                 null(0),
                 callInitiated(1),
                 outgoingCallProceeding(3),
                 callPresent(6),
                 incomingCallProceeding(9),
                 active(10),
                 disconnectRequest(11),
                 disconnectIndication(12),
                 releaseRequest(19),
                 notApplicable(20) }
   ACCESS     read-only
   STATUS     mandatory
   DESCRIPTION
     "This attribute indicates the Q.933 state of an SVC call. In the 
      description that follows, 'local' refers to the user who has initiated 
      the SETUP request, and 'remote' refers to the user to whom the 
      local user wishes to connect.
      
      State description:
      In the null state, the network has neither received nor sent call setup 
      requests for this DLCI.
      In the callInitiated state, the network has received a SETUP 
      message from the local user.
      In the outgoingCallProceeding state, the network has sent a CALL 
      PROCEEDING message to the local user in response to the SETUP 
      message.
      In the callPresent state, the network has sent a SETUP message to 
      the remote user.
      In the incomingCallProceeding state, the network has received a 
      CALL PROCEEDING message from the remote user in response to 
      a SETUP message.
      In the active state, either the network has sent a CONNECT 
      message to the local user, or the network has received a CONNECT 
      from the remote user.
      In the disconnectRequest state, the network has received a 
      DISCONNECT message from the local user.
      In the disconnectIndication state, the network has sent a 
      DISCONNECT to the local user.
      In the releaseRequest state, the network has sent out a RELEASE 
      message to the local user.
      The notApplicable state indicates that this attribute is meaningless 
      because the DLCI is a PVC."
::= { mscMpanlDlciCalldEntry 2 }

mscMpanlDlciQ933CallReference OBJECT-TYPE
   SYNTAX     Unsigned32 (0..32767)
   ACCESS     read-only
   STATUS     mandatory
   DESCRIPTION
     "This attribute indicates the Q.933 call reference number associated 
      with this DLCI."
::= { mscMpanlDlciCalldEntry 3 }

mscMpanlDlciSpOpTable OBJECT-TYPE
   SYNTAX     SEQUENCE OF MscMpanlDlciSpOpEntry
   ACCESS     not-accessible
   STATUS     mandatory
   DESCRIPTION
     "*** THIS TABLE CURRENTLY NOT IMPLEMENTED ***

      This group contains the service parameters specific to this instance 
      of Dlci."
::= { mscMpanlDlci 12 }

mscMpanlDlciSpOpEntry OBJECT-TYPE
   SYNTAX     MscMpanlDlciSpOpEntry
   ACCESS     not-accessible
   STATUS     mandatory
   DESCRIPTION
     "An entry in the mscMpanlDlciSpOpTable."
   INDEX {
      mscMpanlIndex,
      mscMpanlDlciIndex }
::= { mscMpanlDlciSpOpTable 1 }

MscMpanlDlciSpOpEntry ::= SEQUENCE {
   mscMpanlDlciMaximumFrameSize
      Unsigned32,
   mscMpanlDlciCommittedBurstSize
      Unsigned32,
   mscMpanlDlciExcessBurstSize
      Unsigned32,
   mscMpanlDlciAccounting
      INTEGER,
   mscMpanlDlciEmissionPriorityToIf
      INTEGER,
   mscMpanlDlciTransferPriToNwk
      Unsigned32,
   mscMpanlDlciTransferPriFromNwk
      Unsigned32 }

mscMpanlDlciMaximumFrameSize OBJECT-TYPE
   SYNTAX     Unsigned32 (1..4096)
   ACCESS     read-only
   STATUS     mandatory
   DESCRIPTION
     "This attribute specifies the maximum number of octets which may 
      be included in the information field. The frame relay header and 
      CRC octets are not included in this definition. This attribute 
      corresponds to the dN1 parameter described in the Frame Relay 
      Vendor Forum Specification."
::= { mscMpanlDlciSpOpEntry 1 }

mscMpanlDlciCommittedBurstSize OBJECT-TYPE
   SYNTAX     Unsigned32 (0..50000000)
   ACCESS     read-only
   STATUS     mandatory
   DESCRIPTION
     "This attribute indicates the committed burst size (Bc) in bits. bc is 
      the amount of data that a network agrees to transfer under normal 
      conditions over a measurement interval (t). Data marked DE=1 is 
      not accounted for in Bc.
      
      This attribute should be ignored when rateEnforcement is off."
::= { mscMpanlDlciSpOpEntry 4 }

mscMpanlDlciExcessBurstSize OBJECT-TYPE
   SYNTAX     Unsigned32 (0..50000000)
   ACCESS     read-only
   STATUS     mandatory
   DESCRIPTION
     "This attribute indicates the excess burst size (Be) in bits. Be is the 
      amount of uncommitted data that the network will attempt to deliver 
      over measurement interval T. Data marked DE=1 by the user or by 
      the network is accounted for here.
      
      This attribute should be ignored when rateEnforcement is off."
::= { mscMpanlDlciSpOpEntry 5 }

mscMpanlDlciAccounting OBJECT-TYPE
   SYNTAX     INTEGER  {
                 off(0),
                 on(1) }
   ACCESS     read-only
   STATUS     mandatory
   DESCRIPTION
     "This attribute indicates whether accounting data collection and 
      record generation is turned on at this DLCI. For accounting data 
      collection and record generation to be occur, the accountingOn 
      attribute must be on and at least one of the accountCollection 
      options in the DataNetworkAddress component must be selected."
::= { mscMpanlDlciSpOpEntry 8 }

mscMpanlDlciEmissionPriorityToIf OBJECT-TYPE
   SYNTAX     INTEGER (0 | 1 | 2 | 3)
   ACCESS     read-only
   STATUS     mandatory
   DESCRIPTION
     "This attribute indicates the emission priority of frames sent to the 
      interface. A larger value denotes a higher priority."
::= { mscMpanlDlciSpOpEntry 9 }

mscMpanlDlciTransferPriToNwk OBJECT-TYPE
   SYNTAX     Unsigned32 (0..15)
   ACCESS     read-only
   STATUS     mandatory
   DESCRIPTION
     "This attribute indicates the priority at which data is transferred to 
      the network.
      
      The transfer priority is a preference configured for an application 
      according to its delay-sensitivity requirement. Frames with higher 
      transfer priority are served by the network before the frames with 
      lower priority. The transfer priority standard is defined to have 16 
      indices from 0 to 15.
      
      Each transfer priority n, where n specifies the transfer priority 
      index, contains a default setting for routing class of service 
      (multimedia, delay or throughput) and frame relay egress queue 
      (depending on the number of supported egress queues on the remote 
      end interface) specified by the routingClassOfService and 
      emissionPriority attributes provisioned in the Mod Frs DprsNet 
      Tpm/n component. The default mapping can be altered by a user if 
      required."
::= { mscMpanlDlciSpOpEntry 10 }

mscMpanlDlciTransferPriFromNwk OBJECT-TYPE
   SYNTAX     Unsigned32 (0..15)
   ACCESS     read-only
   STATUS     mandatory
   DESCRIPTION
     "This attribute indicates the priority at which data is transferred from 
      the network.
      
      The transfer priority is a preference configured for an application 
      according to its delay-sensitivity requirement. Frames with higher 
      transfer priority are served by the network before the frames with 
      lower priority. The transfer priority standard is defined to have 16 
      indices from 0 to 15.
      
      Each transfer priority n, where n specifies the transfer priority 
      index, contains a default setting for routing class of service 
      (multimedia, delay or throughput) and frame relay egress queue 
      (depending on the number of supported egress queues on the remote 
      end interface) specified by the routingClassOfService and 
      emissionPriority attributes provisioned in the Mod Frs DprsNet 
      Tpm/n component. The default mapping can be altered by a user if 
      required."
::= { mscMpanlDlciSpOpEntry 11 }

mscMpanlDlciStatsTable OBJECT-TYPE
   SYNTAX     SEQUENCE OF MscMpanlDlciStatsEntry
   ACCESS     not-accessible
   STATUS     mandatory
   DESCRIPTION
     "*** THIS TABLE CURRENTLY NOT IMPLEMENTED ***

      This group contains the operational statistics for the MPANL Data 
      Link Connection Identifier."
::= { mscMpanlDlci 13 }

mscMpanlDlciStatsEntry OBJECT-TYPE
   SYNTAX     MscMpanlDlciStatsEntry
   ACCESS     not-accessible
   STATUS     mandatory
   DESCRIPTION
     "An entry in the mscMpanlDlciStatsTable."
   INDEX {
      mscMpanlIndex,
      mscMpanlDlciIndex }
::= { mscMpanlDlciStatsTable 1 }

MscMpanlDlciStatsEntry ::= SEQUENCE {
   mscMpanlDlciFrmToIf
      Unsigned32,
   mscMpanlDlciFecnFrmToIf
      Unsigned32,
   mscMpanlDlciBecnFrmToIf
      Unsigned32,
   mscMpanlDlciBciToSubnet
      Unsigned32,
   mscMpanlDlciDeFrmToIf
      Unsigned32,
   mscMpanlDlciDiscCongestedToIf
      Unsigned32,
   mscMpanlDlciDiscDeCongestedToIf
      Unsigned32,
   mscMpanlDlciFrmFromIf
      Unsigned32,
   mscMpanlDlciFecnFrmFromIf
      Unsigned32,
   mscMpanlDlciBecnFrmFromIf
      Unsigned32,
   mscMpanlDlciFciFromSubnet
      Unsigned32,
   mscMpanlDlciBciFromSubnet
      Unsigned32,
   mscMpanlDlciDeFrmFromIf
      Unsigned32,
   mscMpanlDlciExcessFrmFromIf
      Unsigned32,
   mscMpanlDlciDiscExcessFromIf
      Unsigned32,
   mscMpanlDlciDiscFrameAbit
      Unsigned32,
   mscMpanlDlciDiscCongestedFromIf
      Unsigned32,
   mscMpanlDlciDiscDeCongestedFromIf
      Unsigned32,
   mscMpanlDlciErrorShortFrmFromIf
      Unsigned32,
   mscMpanlDlciErrorLongFrmFromIf
      Unsigned32,
   mscMpanlDlciBecnFrmSetByService
      Unsigned32,
   mscMpanlDlciBytesToIf
      Unsigned32,
   mscMpanlDlciDeBytesToIf
      Unsigned32,
   mscMpanlDlciDiscCongestedToIfBytes
      Unsigned32,
   mscMpanlDlciDiscDeCongestedToIfBytes
      Unsigned32,
   mscMpanlDlciBytesFromIf
      Unsigned32,
   mscMpanlDlciDeBytesFromIf
      Unsigned32,
   mscMpanlDlciExcessBytesFromIf
      Unsigned32,
   mscMpanlDlciDiscExcessFromIfBytes
      Unsigned32,
   mscMpanlDlciDiscByteAbit
      Unsigned32,
   mscMpanlDlciDiscCongestedFromIfBytes
      Unsigned32,
   mscMpanlDlciDiscDeCongestedFromIfBytes
      Unsigned32,
   mscMpanlDlciErrorLongBytesFromIf
      Unsigned32,
   mscMpanlDlciTransferPriorityToNetwork
      INTEGER,
   mscMpanlDlciTransferPriorityFromNetwork
      INTEGER }

mscMpanlDlciFrmToIf OBJECT-TYPE
   SYNTAX     Unsigned32 (0..4294967295)
   ACCESS     read-only
   STATUS     mandatory
   DESCRIPTION
     "This attribute counts the frames sent out the interface. When the 
      maximum count is reached the count wraps to zero."
   DEFVAL     { 0 }
::= { mscMpanlDlciStatsEntry 1 }

mscMpanlDlciFecnFrmToIf OBJECT-TYPE
   SYNTAX     Unsigned32 (0..4294967295)
   ACCESS     read-only
   STATUS     mandatory
   DESCRIPTION
     "This attribute counts the frames sent to the interface with the 
      Forward Explicit Congestion Notification (FECN) bit set. When the 
      count reaches maximum it wraps to zero."
   DEFVAL     { 0 }
::= { mscMpanlDlciStatsEntry 2 }

mscMpanlDlciBecnFrmToIf OBJECT-TYPE
   SYNTAX     Unsigned32 (0..4294967295)
   ACCESS     read-only
   STATUS     mandatory
   DESCRIPTION
     "This attribute counts the frames sent to the interface with the 
      Backward Explicit Congestion Notification (BECN) bit set. When 
      the count reaches maximum it wraps to zero."
   DEFVAL     { 0 }
::= { mscMpanlDlciStatsEntry 3 }

mscMpanlDlciBciToSubnet OBJECT-TYPE
   SYNTAX     Unsigned32 (0..4294967295)
   ACCESS     read-only
   STATUS     mandatory
   DESCRIPTION
     "This attribute counts the frames sent into the network with the 
      Backward Congestion Indication (BCI) bit set. When the count 
      reaches maximum it wraps to zero."
   DEFVAL     { 0 }
::= { mscMpanlDlciStatsEntry 4 }

mscMpanlDlciDeFrmToIf OBJECT-TYPE
   SYNTAX     Unsigned32 (0..4294967295)
   ACCESS     read-only
   STATUS     mandatory
   DESCRIPTION
     "This attribute counts the frames sent to the interface with the 
      Discard Eligibility (DE) bit set. When the count reaches maximum 
      it wraps to zero."
   DEFVAL     { 0 }
::= { mscMpanlDlciStatsEntry 5 }

mscMpanlDlciDiscCongestedToIf OBJECT-TYPE
   SYNTAX     Unsigned32 (0..4294967295)
   ACCESS     read-only
   STATUS     mandatory
   DESCRIPTION
     "This attribute counts the number of frame discards at the MPANL 
      service due to local congestion in the direction toward the interface. 
      When this count reaches maximum, it wraps to zero."
   DEFVAL     { 0 }
::= { mscMpanlDlciStatsEntry 6 }

mscMpanlDlciDiscDeCongestedToIf OBJECT-TYPE
   SYNTAX     Unsigned32 (0..4294967295)
   ACCESS     read-only
   STATUS     mandatory
   DESCRIPTION
     "This attribute counts the number of discarded frames, with the 
      Discard Eligibility (DE) bit set, at the MPANL service, due to local 
      congestion in the direction toward the interface. When this count 
      reaches maximum, it wraps to zero."
   DEFVAL     { 0 }
::= { mscMpanlDlciStatsEntry 7 }

mscMpanlDlciFrmFromIf OBJECT-TYPE
   SYNTAX     Unsigned32 (0..4294967295)
   ACCESS     read-only
   STATUS     mandatory
   DESCRIPTION
     "This attribute counts the frames received from the interface. Frames 
      that are discarded due to error or excess are not counted. When the 
      maximum count is reached the count wraps to zero."
   DEFVAL     { 0 }
::= { mscMpanlDlciStatsEntry 8 }

mscMpanlDlciFecnFrmFromIf OBJECT-TYPE
   SYNTAX     Unsigned32 (0..4294967295)
   ACCESS     read-only
   STATUS     mandatory
   DESCRIPTION
     "This attribute counts the frames received from the interface with the 
      Forward Explicit Congestion Notification (FECN) bit set. When the 
      count reaches maximum it wraps to zero."
   DEFVAL     { 0 }
::= { mscMpanlDlciStatsEntry 9 }

mscMpanlDlciBecnFrmFromIf OBJECT-TYPE
   SYNTAX     Unsigned32 (0..4294967295)
   ACCESS     read-only
   STATUS     mandatory
   DESCRIPTION
     "This attribute counts the frames received from the interface with the 
      Backward Explicit Congestion Notification (BECN) bit set. When 
      the count reaches maximum it wraps to zero."
   DEFVAL     { 0 }
::= { mscMpanlDlciStatsEntry 10 }

mscMpanlDlciFciFromSubnet OBJECT-TYPE
   SYNTAX     Unsigned32 (0..4294967295)
   ACCESS     read-only
   STATUS     mandatory
   DESCRIPTION
     "This attribute counts the frames received from the network with the 
      Forward Congestion Indication (FCI) bit set. When the count 
      reaches maximum it wraps to zero."
   DEFVAL     { 0 }
::= { mscMpanlDlciStatsEntry 11 }

mscMpanlDlciBciFromSubnet OBJECT-TYPE
   SYNTAX     Unsigned32 (0..4294967295)
   ACCESS     read-only
   STATUS     mandatory
   DESCRIPTION
     "This attribute counts the frames received from the network with the 
      Backward Congestion Indication (BCI) bit set. When the count 
      reaches maximum it wraps to zero."
   DEFVAL     { 0 }
::= { mscMpanlDlciStatsEntry 12 }

mscMpanlDlciDeFrmFromIf OBJECT-TYPE
   SYNTAX     Unsigned32 (0..4294967295)
   ACCESS     read-only
   STATUS     mandatory
   DESCRIPTION
     "This attribute counts the frames received from the interface with the 
      Discard Eligibility (DE) bit set. When the count reaches maximum 
      it wraps to zero."
   DEFVAL     { 0 }
::= { mscMpanlDlciStatsEntry 13 }

mscMpanlDlciExcessFrmFromIf OBJECT-TYPE
   SYNTAX     Unsigned32 (0..4294967295)
   ACCESS     read-only
   STATUS     mandatory
   DESCRIPTION
     "This attribute counts the frames received from the interface with the 
      Discard Eligibility (DE) bit clear, but subsequently set by the 
      network due to rate enforcement. When the count reaches 
      maximum it wraps to zero."
   DEFVAL     { 0 }
::= { mscMpanlDlciStatsEntry 14 }

mscMpanlDlciDiscExcessFromIf OBJECT-TYPE
   SYNTAX     Unsigned32 (0..4294967295)
   ACCESS     read-only
   STATUS     mandatory
   DESCRIPTION
     "This attribute counts the frames which were discarded due to rate 
      enforcement. When the count reaches maximum it wraps to zero."
   DEFVAL     { 0 }
::= { mscMpanlDlciStatsEntry 15 }

mscMpanlDlciDiscFrameAbit OBJECT-TYPE
   SYNTAX     Unsigned32 (0..4294967295)
   ACCESS     read-only
   STATUS     mandatory
   DESCRIPTION
     "This attribute counts the number of frame discards at the MPANL 
      Service, due to an inactive PVC status, in the direction toward the 
      network. When this count reaches maximum, it wraps to zero."
   DEFVAL     { 0 }
::= { mscMpanlDlciStatsEntry 16 }

mscMpanlDlciDiscCongestedFromIf OBJECT-TYPE
   SYNTAX     Unsigned32 (0..4294967295)
   ACCESS     read-only
   STATUS     mandatory
   DESCRIPTION
     "This attribute counts the number of frame discards at the MPANL 
      service due to local congestion in the direction toward the network. 
      When this count reaches maximum, it wraps to zero."
   DEFVAL     { 0 }
::= { mscMpanlDlciStatsEntry 17 }

mscMpanlDlciDiscDeCongestedFromIf OBJECT-TYPE
   SYNTAX     Unsigned32 (0..4294967295)
   ACCESS     read-only
   STATUS     mandatory
   DESCRIPTION
     "This attribute counts the number of discarded frames, with the 
      Discard Eligibility (DE) bit set, at the MPANL service, due to local 
      congestion, in the direction toward the network. When this count 
      reaches maximum, it wraps to zero."
   DEFVAL     { 0 }
::= { mscMpanlDlciStatsEntry 18 }

mscMpanlDlciErrorShortFrmFromIf OBJECT-TYPE
   SYNTAX     Unsigned32 (0..4294967295)
   ACCESS     read-only
   STATUS     mandatory
   DESCRIPTION
     "This attribute counts the frames received with 0 octets in the 
      information field. When the count reaches maximum it wraps to 
      zero."
   DEFVAL     { 0 }
::= { mscMpanlDlciStatsEntry 19 }

mscMpanlDlciErrorLongFrmFromIf OBJECT-TYPE
   SYNTAX     Unsigned32 (0..4294967295)
   ACCESS     read-only
   STATUS     mandatory
   DESCRIPTION
     "This attribute counts the frames received with number of octets in 
      the information field greater than the subscribed maximum. When 
      the count reaches maximum it wraps to zero. Frames whose lengths 
      are greater than the hardware receive buffer are ignored by the 
      hardware and are therefore not included in this count."
   DEFVAL     { 0 }
::= { mscMpanlDlciStatsEntry 20 }

mscMpanlDlciBecnFrmSetByService OBJECT-TYPE
   SYNTAX     Unsigned32 (0..4294967295)
   ACCESS     read-only
   STATUS     mandatory
   DESCRIPTION
     "This attribute counts the number of frames with BECN set by the 
      MPANL service. It is incremented whenever the MPANL service 
      sets BECN on a frame upon detecting local congestion. This count 
      is incremented regardless of whether the frame already bears a set 
      BECN bit since its use is to determine the place of congestion. 
      When the count reaches maximum, it wraps to zero."
   DEFVAL     { 0 }
::= { mscMpanlDlciStatsEntry 21 }

mscMpanlDlciBytesToIf OBJECT-TYPE
   SYNTAX     Unsigned32 (0..4294967295)
   ACCESS     read-only
   STATUS     mandatory
   DESCRIPTION
     "This attribute counts the bytes sent out the interface. When the 
      maximum count is reached the count wraps to zero."
   DEFVAL     { 0 }
::= { mscMpanlDlciStatsEntry 22 }

mscMpanlDlciDeBytesToIf OBJECT-TYPE
   SYNTAX     Unsigned32 (0..4294967295)
   ACCESS     read-only
   STATUS     mandatory
   DESCRIPTION
     "This attribute counts the bytes sent to the interface with the Discard 
      Eligibility (DE) bit set. When the count reaches maximum it wraps 
      to zero."
   DEFVAL     { 0 }
::= { mscMpanlDlciStatsEntry 23 }

mscMpanlDlciDiscCongestedToIfBytes OBJECT-TYPE
   SYNTAX     Unsigned32 (0..4294967295)
   ACCESS     read-only
   STATUS     mandatory
   DESCRIPTION
     "This attribute counts the number of byte discards at the MPANL 
      service due to local congestion in the direction toward the link. 
      When this count reaches maximum, it wraps to zero."
   DEFVAL     { 0 }
::= { mscMpanlDlciStatsEntry 24 }

mscMpanlDlciDiscDeCongestedToIfBytes OBJECT-TYPE
   SYNTAX     Unsigned32 (0..4294967295)
   ACCESS     read-only
   STATUS     mandatory
   DESCRIPTION
     "This attribute counts the number of discard eligible (DE=1) byte 
      discards at the MPANL service due to local congestion in the 
      direction toward the link. When the maximum count is reached the 
      count wraps to zero."
   DEFVAL     { 0 }
::= { mscMpanlDlciStatsEntry 25 }

mscMpanlDlciBytesFromIf OBJECT-TYPE
   SYNTAX     Unsigned32 (0..4294967295)
   ACCESS     read-only
   STATUS     mandatory
   DESCRIPTION
     "This attribute counts the bytes received from the interface. Bytes 
      that are discarded due to error or excess are not counted. When the 
      maximum count is reached the count wraps to zero."
   DEFVAL     { 0 }
::= { mscMpanlDlciStatsEntry 26 }

mscMpanlDlciDeBytesFromIf OBJECT-TYPE
   SYNTAX     Unsigned32 (0..4294967295)
   ACCESS     read-only
   STATUS     mandatory
   DESCRIPTION
     "This attribute counts the bytes received from the interface with the 
      Discard Eligibility (DE) bit set. When the count reaches maximum 
      it wraps to zero."
   DEFVAL     { 0 }
::= { mscMpanlDlciStatsEntry 27 }

mscMpanlDlciExcessBytesFromIf OBJECT-TYPE
   SYNTAX     Unsigned32 (0..4294967295)
   ACCESS     read-only
   STATUS     mandatory
   DESCRIPTION
     "This attribute counts the bytes received from the interface with the 
      Discard Eligibility (DE) bit clear, but subsequently set by the 
      network due to rate enforcement. When the count reaches 
      maximum it wraps to zero."
   DEFVAL     { 0 }
::= { mscMpanlDlciStatsEntry 28 }

mscMpanlDlciDiscExcessFromIfBytes OBJECT-TYPE
   SYNTAX     Unsigned32 (0..4294967295)
   ACCESS     read-only
   STATUS     mandatory
   DESCRIPTION
     "This attribute counts the bytes which were discarded due to rate 
      enforcement. When the count reaches maximum it wraps to zero."
   DEFVAL     { 0 }
::= { mscMpanlDlciStatsEntry 29 }

mscMpanlDlciDiscByteAbit OBJECT-TYPE
   SYNTAX     Unsigned32 (0..4294967295)
   ACCESS     read-only
   STATUS     mandatory
   DESCRIPTION
     "This attribute counts the bytes which were discarded due to aBit 
      turned off."
   DEFVAL     { 0 }
::= { mscMpanlDlciStatsEntry 30 }

mscMpanlDlciDiscCongestedFromIfBytes OBJECT-TYPE
   SYNTAX     Unsigned32 (0..4294967295)
   ACCESS     read-only
   STATUS     mandatory
   DESCRIPTION
     "This attribute counts the number of byte discards at the MPANL 
      service due to local congestion in the direction toward the network. 
      When this count reaches maximum, it wraps to zero."
   DEFVAL     { 0 }
::= { mscMpanlDlciStatsEntry 31 }

mscMpanlDlciDiscDeCongestedFromIfBytes OBJECT-TYPE
   SYNTAX     Unsigned32 (0..4294967295)
   ACCESS     read-only
   STATUS     mandatory
   DESCRIPTION
     "This attribute counts the number of discard eligible (DE=1) byte 
      discards at the MPANL service due to local congestion in the 
      direction toward the network. When the maximum count is reached 
      the count wraps to zero."
   DEFVAL     { 0 }
::= { mscMpanlDlciStatsEntry 32 }

mscMpanlDlciErrorLongBytesFromIf OBJECT-TYPE
   SYNTAX     Unsigned32 (0..4294967295)
   ACCESS     read-only
   STATUS     mandatory
   DESCRIPTION
     "This attribute counts the bytes received with number of octets in the 
      information field greater than the subscribed maximum. When the 
      count reaches maximum it wraps to zero. Bytes whose lengths are 
      greater than the hardware receive buffer are ignored by the 
      hardware and are therefore not included in this count."
   DEFVAL     { 0 }
::= { mscMpanlDlciStatsEntry 34 }

mscMpanlDlciTransferPriorityToNetwork OBJECT-TYPE
   SYNTAX     INTEGER  {
                 n0(0),
                 n1(1),
                 n2(2),
                 n3(3),
                 n4(4),
                 n5(5),
                 n6(6),
                 n7(7),
                 n8(8),
                 n9(9),
                 n10(10),
                 n11(11),
                 n12(12),
                 n13(13),
                 n14(14),
                 n15(15) }
   ACCESS     read-only
   STATUS     obsolete
   DESCRIPTION
     "This attribute is obsolete. It is replaced by attribute 
      transferPriorityToNetwork under group 
      FrsNniDataLinkConnectionIdentifierServiceParametersOp."
::= { mscMpanlDlciStatsEntry 37 }

mscMpanlDlciTransferPriorityFromNetwork OBJECT-TYPE
   SYNTAX     INTEGER  {
                 n0(0),
                 n1(1),
                 n2(2),
                 n3(3),
                 n4(4),
                 n5(5),
                 n6(6),
                 n7(7),
                 n8(8),
                 n9(9),
                 n10(10),
                 n11(11),
                 n12(12),
                 n13(13),
                 n14(14),
                 n15(15) }
   ACCESS     read-only
   STATUS     obsolete
   DESCRIPTION
     "This attribute is obsolete. It is replaced by attribute 
      transferPriorityFromNetwork under group 
      FrsNniDataLinkConnectionIdentifierServiceParametersOp."
::= { mscMpanlDlciStatsEntry 38 }

mscMpanlDlciIntTable OBJECT-TYPE
   SYNTAX     SEQUENCE OF MscMpanlDlciIntEntry
   ACCESS     not-accessible
   STATUS     mandatory
   DESCRIPTION
     "*** THIS TABLE CURRENTLY NOT IMPLEMENTED ***

      This group contains the operational statistics for the MPANL Data 
      Link Connection Identifier interval data."
::= { mscMpanlDlci 14 }

mscMpanlDlciIntEntry OBJECT-TYPE
   SYNTAX     MscMpanlDlciIntEntry
   ACCESS     not-accessible
   STATUS     mandatory
   DESCRIPTION
     "An entry in the mscMpanlDlciIntTable."
   INDEX {
      mscMpanlIndex,
      mscMpanlDlciIndex }
::= { mscMpanlDlciIntTable 1 }

MscMpanlDlciIntEntry ::= SEQUENCE {
   mscMpanlDlciStartTime
      EnterpriseDateAndTime,
   mscMpanlDlciTotalIngressBytes
      Unsigned64,
   mscMpanlDlciTotalEgressBytes
      Unsigned64,
   mscMpanlDlciEirIngressBytes
      Unsigned64,
   mscMpanlDlciEirEgressBytes
      Unsigned64,
   mscMpanlDlciDiscardedBytes
      Unsigned64,
   mscMpanlDlciTotalIngressSegFrm
      Unsigned32,
   mscMpanlDlciTotalEgressSegFrm
      Unsigned32,
   mscMpanlDlciEirIngressSegFrm
      Unsigned32,
   mscMpanlDlciEirEgressSegFrm
      Unsigned32,
   mscMpanlDlciDiscardedSegFrm
      Unsigned32,
   mscMpanlDlciCallReferenceNumber
      Unsigned32,
   mscMpanlDlciElapsedDifference
      Unsigned32 }

mscMpanlDlciStartTime OBJECT-TYPE
   SYNTAX     EnterpriseDateAndTime (SIZE (0 | 19))
   ACCESS     read-only
   STATUS     mandatory
   DESCRIPTION
     "This attribute indicates the start time of this interval period. If the 
      Vc spans 12 hour time or time of day change, startTime reflects new 
      time as recorded at 12 hour periods or time of day changes. A new 
      interval period is started each time an accounting record is 
      generated."
::= { mscMpanlDlciIntEntry 1 }

mscMpanlDlciTotalIngressBytes OBJECT-TYPE
   SYNTAX     Unsigned64 (SIZE (8))
   ACCESS     read-only
   STATUS     mandatory
   DESCRIPTION
     "This attribute counts the total bytes received from the interface 
      since the start of the interval period. The start of the interval period 
      is captured in the startTime attribute. The count is reset to zero 
      when an accounting record is generated."
::= { mscMpanlDlciIntEntry 2 }

mscMpanlDlciTotalEgressBytes OBJECT-TYPE
   SYNTAX     Unsigned64 (SIZE (8))
   ACCESS     read-only
   STATUS     mandatory
   DESCRIPTION
     "This attribute counts the total bytes sent to the interface since the 
      start of the interval period. The start of the interval period is 
      captured in the startTime attribute. The count is reset to zero when 
      an accounting record is generated."
::= { mscMpanlDlciIntEntry 3 }

mscMpanlDlciEirIngressBytes OBJECT-TYPE
   SYNTAX     Unsigned64 (SIZE (8))
   ACCESS     read-only
   STATUS     mandatory
   DESCRIPTION
     "This attribute counts the total bytes with the Discard Eligibility 
      (DE) bit set sent to the subnet since the start of the interval period. 
      The start of the interval period is captured in the startTime attribute. 
      The count is reset to zero when an accounting record is generated."
::= { mscMpanlDlciIntEntry 4 }

mscMpanlDlciEirEgressBytes OBJECT-TYPE
   SYNTAX     Unsigned64 (SIZE (8))
   ACCESS     read-only
   STATUS     mandatory
   DESCRIPTION
     "This attribute counts the total bytes with the Discard Eligibility 
      (DE) bit set sent to the interface since the start of the interval 
      period. The start of the interval period is captured in the startTime 
      attribute. The count is reset to zero when an accounting record is 
      generated."
::= { mscMpanlDlciIntEntry 5 }

mscMpanlDlciDiscardedBytes OBJECT-TYPE
   SYNTAX     Unsigned64 (SIZE (8))
   ACCESS     read-only
   STATUS     mandatory
   DESCRIPTION
     "This attribute counts the total bytes in invalid frames received from 
      the interface and discarded at the DLCI since the start of the interval 
      period. This count is a sum of octets in frames discarded due to the 
      number of octets in the information field greater than the subscribed 
      maximum or equal to 0, due to aBit turned off, or due to rate 
      enforcement. The start of the interval period is captured in the 
      startTime attribute. The count is reset to zero when an accounting 
      record is generated."
::= { mscMpanlDlciIntEntry 6 }

mscMpanlDlciTotalIngressSegFrm OBJECT-TYPE
   SYNTAX     Unsigned32 (0..4294967295)
   ACCESS     read-only
   STATUS     mandatory
   DESCRIPTION
     "If the value of the unitsCounted attribute in moduleData component 
      is segments, this attribute counts the total number of segments in 
      frames received from the interface since the start of the interval 
      period. If the value of the unitsCounted attribute in moduleData 
      component is frames, this attribute counts the total number of 
      frames received from the interface since the start of the interval 
      period. The start of the interval period is captured in the startTime 
      attribute. The count is reset to zero when an accounting record is 
      generated."
   DEFVAL     { 0 }
::= { mscMpanlDlciIntEntry 7 }

mscMpanlDlciTotalEgressSegFrm OBJECT-TYPE
   SYNTAX     Unsigned32 (0..4294967295)
   ACCESS     read-only
   STATUS     mandatory
   DESCRIPTION
     "If the value of the unitsCounted attribute in moduleData component 
      is segments, this attribute counts the total number of segments in 
      frames sent to the interface since the start of the interval period. If 
      the value of the unitsCounted attribute in moduleData component is 
      frames, this attribute counts the total number of frames sent to the 
      interface since the start of the interval period. The start of the 
      interval period is captured in the startTime attribute. The count is 
      reset to zero when an accounting record is generated."
   DEFVAL     { 0 }
::= { mscMpanlDlciIntEntry 8 }

mscMpanlDlciEirIngressSegFrm OBJECT-TYPE
   SYNTAX     Unsigned32 (0..4294967295)
   ACCESS     read-only
   STATUS     mandatory
   DESCRIPTION
     "If the value of the unitsCounted attribute in moduleData component 
      is segments, this attribute counts the number of segments in frames 
      with the Discard Eligibility (DE) bit set sent to the subnet since the 
      start of the interval period. If the value of the unitsCounted attribute 
      in moduleData component is frames, this attribute counts the 
      number of frames with the Discard Eligibility (DE) bit set sent to 
      the subnet since the start of the interval period. The start of the 
      interval period is captured in the startTime attribute. The count is 
      reset to zero when an accounting record is generated."
   DEFVAL     { 0 }
::= { mscMpanlDlciIntEntry 9 }

mscMpanlDlciEirEgressSegFrm OBJECT-TYPE
   SYNTAX     Unsigned32 (0..4294967295)
   ACCESS     read-only
   STATUS     mandatory
   DESCRIPTION
     "If the value of the unitsCounted attribute in moduleData component 
      is segments, this attribute counts the number of segments in frames 
      with the Discard Eligibility (DE) bit set sent to the interface since 
      the start of the interval period. If the value of the unitsCounted 
      attribute in moduleData component is frames, this attribute counts 
      the number of frames with the Discard Eligibility (DE) bit set sent 
      to the interface since the start of the interval period. The start of the 
      interval period is captured in the startTime attribute. The count is 
      reset to zero when an accounting record is generated."
   DEFVAL     { 0 }
::= { mscMpanlDlciIntEntry 10 }

mscMpanlDlciDiscardedSegFrm OBJECT-TYPE
   SYNTAX     Unsigned32 (0..4294967295)
   ACCESS     read-only
   STATUS     mandatory
   DESCRIPTION
     "If the value of the unitsCounted attribute in moduleData component 
      is segments, this attribute counts the number of segments in invalid 
      frames received from the interface and discarded at the DLCI. If the 
      value of the unitsCounted attribute in moduleData component is 
      frames, this attribute counts the number of invalid frames received 
      from the interface and discarded at the DLCI. Segments of frames 
      are counted since the start of the interval period. The count is reset 
      to zero when an accounting record is generated. The count is a sum 
      of segments in frames or frames discarded due to the number of 
      octets in the information field greater than the subscribed maximum 
      or equal to 0, due to aBit turned off, or due to rate enforcement."
   DEFVAL     { 0 }
::= { mscMpanlDlciIntEntry 11 }

mscMpanlDlciCallReferenceNumber OBJECT-TYPE
   SYNTAX     Unsigned32 (0..4294967295)
   ACCESS     read-only
   STATUS     mandatory
   DESCRIPTION
     "This attribute displays the call reference number which is a unique 
      number generated by the switch.The same Call Reference Number 
      is stored in the interval data (accounting record) at both ends of the 
      call. It can be used as one of the attributes in matching duplicate 
      records generated at each end of the call."
   DEFVAL     { 0 }
::= { mscMpanlDlciIntEntry 17 }

mscMpanlDlciElapsedDifference OBJECT-TYPE
   SYNTAX     Unsigned32 (0..4294967295)
   ACCESS     read-only
   STATUS     mandatory
   DESCRIPTION
     "This attribute displays the elapsed time representing the period of 
      this interval data. It is elapsed time in 0.1 second increments since 
      the call started."
   DEFVAL     { 0 }
::= { mscMpanlDlciIntEntry 18 }

mscMpanlDlciAbitTable OBJECT-TYPE
   SYNTAX     SEQUENCE OF MscMpanlDlciAbitEntry
   ACCESS     not-accessible
   STATUS     mandatory
   DESCRIPTION
     "*** THIS TABLE CURRENTLY NOT IMPLEMENTED ***

      This group contains the A-Bit status information for this Data Link 
      Connection Identifier.
      
      A-Bit status information is only applicable for SPVCs. For SVCs, 
      the values of attributes under this group are all notApplicable."
::= { mscMpanlDlci 15 }

mscMpanlDlciAbitEntry OBJECT-TYPE
   SYNTAX     MscMpanlDlciAbitEntry
   ACCESS     not-accessible
   STATUS     mandatory
   DESCRIPTION
     "An entry in the mscMpanlDlciAbitTable."
   INDEX {
      mscMpanlIndex,
      mscMpanlDlciIndex }
::= { mscMpanlDlciAbitTable 1 }

MscMpanlDlciAbitEntry ::= SEQUENCE {
   mscMpanlDlciABitStatusToIf
      INTEGER,
   mscMpanlDlciABitReasonToIf
      INTEGER,
   mscMpanlDlciABitStatusFromIf
      INTEGER,
   mscMpanlDlciABitReasonFromIf
      INTEGER,
   mscMpanlDlciLoopbackState
      INTEGER }

mscMpanlDlciABitStatusToIf OBJECT-TYPE
   SYNTAX     INTEGER  {
                 inactive(0),
                 active(1),
                 notApplicable(2) }
   ACCESS     read-only
   STATUS     mandatory
   DESCRIPTION
     "This attribute is the most recent A-Bit status sent to the interface. 
      The A-Bit status is originated from the SPVC end point at the 
      remote end of the Passport subnet and it is relayed to the interface 
      by Mpanl. When an inactive setting is sent out, Mpanl will discard 
      any data offered from the interface. When an active setting is sent 
      out, Mpanl will try to relay all data offered from the interface to the 
      other end of the SPVC."
   DEFVAL     { inactive }
::= { mscMpanlDlciAbitEntry 1 }

mscMpanlDlciABitReasonToIf OBJECT-TYPE
   SYNTAX     INTEGER  {
                 notApplicable(0),
                 remoteUserSignaled(1),
                 remoteLmiError(3),
                 remoteLinkDown(5),
                 vcDown(6) }
   ACCESS     read-only
   STATUS     mandatory
   DESCRIPTION
     "This attribute provides the reason (if any) for an inactive status to be 
      sent to the interface. This reason is not applicable for an active 
      status.
      
      A-Bit status reason description:
      The A-Bit status reason is notApplicable when the A-Bit status is 
      active.
      The A-Bit status reason is remoteUserSignaled if the SPVC end 
      point originating the A-Bit status has detected that the virtual circuit 
      is down at the remote network through the LMI protocol. The 
      SPVC end point must be running network site LMI protocol for this 
      A-Bit status reason to be sent.
      The A-Bit status reason is remoteLmiError if the LMI protocol is 
      down at the SPVC end point originating this A-Bit status reason.
      The A-Bit status reason is remoteLinkDown if the physical 
      interface is disabled at the SPVC end point originating this A-Bit 
      status reason.
      The A-Bit reason is vcDown if no A-Bit status has been sent to the 
      interface (i.e., no A-Bit status has been relayed)."
   DEFVAL     { vcDown }
::= { mscMpanlDlciAbitEntry 2 }

mscMpanlDlciABitStatusFromIf OBJECT-TYPE
   SYNTAX     INTEGER  {
                 inactive(0),
                 active(1),
                 notApplicable(2) }
   ACCESS     read-only
   STATUS     mandatory
   DESCRIPTION
     "This attribute is the most recent A-Bit status received from the 
      interface. It is an indication from the equipment attached to the 
      interface on whether it is ready to accept data. Mpanl relays the A-
      Bit status from interface to the other end of the SPVC. When an 
      inactive setting is received, Mpanl will discard any data offered 
      from the subnet. When an active setting is received, Mpanl will try 
      to relay all data offered from the subnet to the interface."
   DEFVAL     { inactive }
::= { mscMpanlDlciAbitEntry 3 }

mscMpanlDlciABitReasonFromIf OBJECT-TYPE
   SYNTAX     INTEGER  {
                 notApplicable(0),
                 remoteUserSignaled(1),
                 remoteLmiError(3),
                 remoteLinkDown(5),
                 vcDown(6) }
   ACCESS     read-only
   STATUS     mandatory
   DESCRIPTION
     "This attribute provides the reason (if any) for an inactive status to be 
      sent to the subnet. This reason is not applicable for an active status.
      
      A-Bit status reason description:
      The A-Bit status reason is notApplicable when the A-Bit status is 
      active.
      The A-Bit status reason is remoteUserSignaled if the SPVC end 
      point originating the A-Bit status has detected that the DLCI is 
      inactive at the remote network through the LMI protocol. The 
      SPVC end point must be running network site LMI protocol for this 
      A-Bit status reason to be sent.
      The A-Bit status reason is remoteLmiError if the LMI protocol is 
      down at the SPVC end point originating this A-Bit status reason.
      The A-Bit status reason is remoteLinkDown if the physical 
      interface is disabled at the SPVC end point originating this A-Bit 
      status reason.
      The A-Bit reason is vcDown if no A-Bit status has been received 
      from the interface (i.e., no A-Bit status has been relayed)."
   DEFVAL     { vcDown }
::= { mscMpanlDlciAbitEntry 4 }

mscMpanlDlciLoopbackState OBJECT-TYPE
   SYNTAX     INTEGER  {
                 off(0),
                 on(1) }
   ACCESS     read-only
   STATUS     mandatory
   DESCRIPTION
     "This attribute has the value on when the DLCI is in loopback mode 
      and off otherwise. This loopback command verbs start and stop are 
      used to initiate and terminate the loopback mode for a DLCI. While 
      loopbackState is on, an active A-bit signal will be reliably 
      propagated across the subnet to the remote DLCI."
   DEFVAL     { off }
::= { mscMpanlDlciAbitEntry 5 }

-- 
-- *** THIS SUBTREE CURRENTLY NOT IMPLEMENTED ***
-- 

-- FrUni/n Dlci/n LoopBack	
-- FrNni/n Dlci/n LoopBack		
-- This component is the data loopback tool for the parent DLCI.

mscMpanlDlciLb OBJECT IDENTIFIER ::= { mscMpanlDlci 2 }



mscMpanlDlciLbRowStatusTable OBJECT-TYPE
   SYNTAX     SEQUENCE OF MscMpanlDlciLbRowStatusEntry
   ACCESS     not-accessible
   STATUS     mandatory
   DESCRIPTION
     "*** THIS TABLE CURRENTLY NOT IMPLEMENTED ***

      This entry controls the addition and deletion of 
      mscMpanlDlciLb components."
::= { mscMpanlDlciLb 1 }

mscMpanlDlciLbRowStatusEntry OBJECT-TYPE
   SYNTAX     MscMpanlDlciLbRowStatusEntry
   ACCESS     not-accessible
   STATUS     mandatory
   DESCRIPTION
     "A single entry in the table represents a single 
      mscMpanlDlciLb component."
   INDEX {
      mscMpanlIndex,
      mscMpanlDlciIndex,
      mscMpanlDlciLbIndex }
::= { mscMpanlDlciLbRowStatusTable 1 }

MscMpanlDlciLbRowStatusEntry ::= SEQUENCE {
   mscMpanlDlciLbRowStatus
      RowStatus,
   mscMpanlDlciLbComponentName
      DisplayString,
   mscMpanlDlciLbStorageType
      StorageType,
   mscMpanlDlciLbIndex
      NonReplicated }

mscMpanlDlciLbRowStatus OBJECT-TYPE
   SYNTAX     RowStatus 
   ACCESS     read-only
   STATUS     mandatory
   DESCRIPTION
     "This variable is used as the basis for SNMP naming of
      mscMpanlDlciLb components.
      These components cannot be added nor deleted."
::= { mscMpanlDlciLbRowStatusEntry 1 }

mscMpanlDlciLbComponentName OBJECT-TYPE
   SYNTAX     DisplayString 
   ACCESS     read-only
   STATUS     mandatory
   DESCRIPTION
     "This variable provides the component's string name for
      use with the ASCII Console Interface"
::= { mscMpanlDlciLbRowStatusEntry 2 }

mscMpanlDlciLbStorageType OBJECT-TYPE
   SYNTAX     StorageType 
   ACCESS     read-only
   STATUS     mandatory
   DESCRIPTION
     "This variable represents the storage type value for the
      mscMpanlDlciLb tables."
::= { mscMpanlDlciLbRowStatusEntry 4 }

mscMpanlDlciLbIndex OBJECT-TYPE
   SYNTAX     NonReplicated 
   ACCESS     not-accessible
   STATUS     mandatory
   DESCRIPTION
     "This variable represents the index for the mscMpanlDlciLb tables."
::= { mscMpanlDlciLbRowStatusEntry 10 }

mscMpanlDlciLbStatsTable OBJECT-TYPE
   SYNTAX     SEQUENCE OF MscMpanlDlciLbStatsEntry
   ACCESS     not-accessible
   STATUS     mandatory
   DESCRIPTION
     "*** THIS TABLE CURRENTLY NOT IMPLEMENTED ***

      This group contains all the statistics for the data loopback tool."
::= { mscMpanlDlciLb 10 }

mscMpanlDlciLbStatsEntry OBJECT-TYPE
   SYNTAX     MscMpanlDlciLbStatsEntry
   ACCESS     not-accessible
   STATUS     mandatory
   DESCRIPTION
     "An entry in the mscMpanlDlciLbStatsTable."
   INDEX {
      mscMpanlIndex,
      mscMpanlDlciIndex,
      mscMpanlDlciLbIndex }
::= { mscMpanlDlciLbStatsTable 1 }

MscMpanlDlciLbStatsEntry ::= SEQUENCE {
   mscMpanlDlciLbLocalTotalFrm
      Unsigned32,
   mscMpanlDlciLbLocalTotalBytes
      Unsigned32,
   mscMpanlDlciLbLocalFecnFrm
      Unsigned32,
   mscMpanlDlciLbLocalBecnFrm
      Unsigned32,
   mscMpanlDlciLbLocalDeFrm
      Unsigned32,
   mscMpanlDlciLbLocalDeBytes
      Unsigned32,
   mscMpanlDlciLbRemoteTotalFrm
      Unsigned32,
   mscMpanlDlciLbRemoteTotalBytes
      Unsigned32,
   mscMpanlDlciLbRemoteFecnFrm
      Unsigned32,
   mscMpanlDlciLbRemoteBecnFrm
      Unsigned32,
   mscMpanlDlciLbRemoteDeFrm
      Unsigned32,
   mscMpanlDlciLbRemoteDeBytes
      Unsigned32 }

mscMpanlDlciLbLocalTotalFrm OBJECT-TYPE
   SYNTAX     Unsigned32 (0..4294967295)
   ACCESS     read-only
   STATUS     mandatory
   DESCRIPTION
     "This attribute records the number of frames looped back to the link 
      since loopback was last started."
   DEFVAL     { 0 }
::= { mscMpanlDlciLbStatsEntry 1 }

mscMpanlDlciLbLocalTotalBytes OBJECT-TYPE
   SYNTAX     Unsigned32 (0..4294967295)
   ACCESS     read-only
   STATUS     mandatory
   DESCRIPTION
     "This attribute records the number of bytes looped back to the link 
      since loopback mode was started."
   DEFVAL     { 0 }
::= { mscMpanlDlciLbStatsEntry 2 }

mscMpanlDlciLbLocalFecnFrm OBJECT-TYPE
   SYNTAX     Unsigned32 (0..4294967295)
   ACCESS     read-only
   STATUS     mandatory
   DESCRIPTION
     "This attribute records the number of frames with the Forward 
      Explicit Congestion Notification (FECN) bit set, looped back to the 
      link since the loopback mode was started."
   DEFVAL     { 0 }
::= { mscMpanlDlciLbStatsEntry 3 }

mscMpanlDlciLbLocalBecnFrm OBJECT-TYPE
   SYNTAX     Unsigned32 (0..4294967295)
   ACCESS     read-only
   STATUS     mandatory
   DESCRIPTION
     "This attribute records the number of frames with the Backward 
      Explicit Congestion Notification (BECN) bit set, looped back to the 
      link since the loopback mode was started."
   DEFVAL     { 0 }
::= { mscMpanlDlciLbStatsEntry 4 }

mscMpanlDlciLbLocalDeFrm OBJECT-TYPE
   SYNTAX     Unsigned32 (0..4294967295)
   ACCESS     read-only
   STATUS     mandatory
   DESCRIPTION
     "This attribute records the number of frames with the Discard 
      Eligibility (DE) bit set, looped back to the link since the loopback 
      mode was started."
   DEFVAL     { 0 }
::= { mscMpanlDlciLbStatsEntry 5 }

mscMpanlDlciLbLocalDeBytes OBJECT-TYPE
   SYNTAX     Unsigned32 (0..4294967295)
   ACCESS     read-only
   STATUS     mandatory
   DESCRIPTION
     "This attribute records the number of bytes in frames with the 
      Discard Eligibility (DE) bit set, looped back to the link since the 
      loopback mode was started."
   DEFVAL     { 0 }
::= { mscMpanlDlciLbStatsEntry 6 }

mscMpanlDlciLbRemoteTotalFrm OBJECT-TYPE
   SYNTAX     Unsigned32 (0..4294967295)
   ACCESS     read-only
   STATUS     mandatory
   DESCRIPTION
     "This attribute records the number of frames looped back to the 
      subnet since loopback was last started."
   DEFVAL     { 0 }
::= { mscMpanlDlciLbStatsEntry 7 }

mscMpanlDlciLbRemoteTotalBytes OBJECT-TYPE
   SYNTAX     Unsigned32 (0..4294967295)
   ACCESS     read-only
   STATUS     mandatory
   DESCRIPTION
     "This attribute records the number of bytes looped back to the subnet 
      since loopback was last started."
   DEFVAL     { 0 }
::= { mscMpanlDlciLbStatsEntry 8 }

mscMpanlDlciLbRemoteFecnFrm OBJECT-TYPE
   SYNTAX     Unsigned32 (0..4294967295)
   ACCESS     read-only
   STATUS     mandatory
   DESCRIPTION
     "This attribute records the number of frames with the Forward 
      Explicit Congestion Notification (FECN) bit set, looped back to the 
      subnet since the loopback mode was started."
   DEFVAL     { 0 }
::= { mscMpanlDlciLbStatsEntry 9 }

mscMpanlDlciLbRemoteBecnFrm OBJECT-TYPE
   SYNTAX     Unsigned32 (0..4294967295)
   ACCESS     read-only
   STATUS     mandatory
   DESCRIPTION
     "This attribute records the number of frames with the Backward 
      Explicit Congestion Notification (BECN) bit set, looped back to the 
      subnet since the loopback mode was started."
   DEFVAL     { 0 }
::= { mscMpanlDlciLbStatsEntry 10 }

mscMpanlDlciLbRemoteDeFrm OBJECT-TYPE
   SYNTAX     Unsigned32 (0..4294967295)
   ACCESS     read-only
   STATUS     mandatory
   DESCRIPTION
     "This attribute records the number of frames with the Discard 
      Eligibility (DE) bit set, looped back to the subnet since the 
      loopback mode was started."
   DEFVAL     { 0 }
::= { mscMpanlDlciLbStatsEntry 13 }

mscMpanlDlciLbRemoteDeBytes OBJECT-TYPE
   SYNTAX     Unsigned32 (0..4294967295)
   ACCESS     read-only
   STATUS     mandatory
   DESCRIPTION
     "This attribute records the number of bytes in frames with the 
      Discard Eligibility (DE) bit set, looped back to the subnet since the 
      loopback mode was started."
   DEFVAL     { 0 }
::= { mscMpanlDlciLbStatsEntry 14 }

-- 
-- *** THIS SUBTREE CURRENTLY NOT IMPLEMENTED ***
-- 

-- Mpanl/<n> Dlci/<n> Vc
-- This component defines attributes collected by Mpanl/n Dlci/n Vc.

mscMpanlDlciVc OBJECT IDENTIFIER ::= { mscMpanlDlci 3 }



mscMpanlDlciVcRowStatusTable OBJECT-TYPE
   SYNTAX     SEQUENCE OF MscMpanlDlciVcRowStatusEntry
   ACCESS     not-accessible
   STATUS     mandatory
   DESCRIPTION
     "*** THIS TABLE CURRENTLY NOT IMPLEMENTED ***

      This entry controls the addition and deletion of 
      mscMpanlDlciVc components."
::= { mscMpanlDlciVc 1 }

mscMpanlDlciVcRowStatusEntry OBJECT-TYPE
   SYNTAX     MscMpanlDlciVcRowStatusEntry
   ACCESS     not-accessible
   STATUS     mandatory
   DESCRIPTION
     "A single entry in the table represents a single 
      mscMpanlDlciVc component."
   INDEX {
      mscMpanlIndex,
      mscMpanlDlciIndex,
      mscMpanlDlciVcIndex }
::= { mscMpanlDlciVcRowStatusTable 1 }

MscMpanlDlciVcRowStatusEntry ::= SEQUENCE {
   mscMpanlDlciVcRowStatus
      RowStatus,
   mscMpanlDlciVcComponentName
      DisplayString,
   mscMpanlDlciVcStorageType
      StorageType,
   mscMpanlDlciVcIndex
      NonReplicated }

mscMpanlDlciVcRowStatus OBJECT-TYPE
   SYNTAX     RowStatus 
   ACCESS     read-only
   STATUS     mandatory
   DESCRIPTION
     "This variable is used as the basis for SNMP naming of
      mscMpanlDlciVc components.
      These components cannot be added nor deleted."
::= { mscMpanlDlciVcRowStatusEntry 1 }

mscMpanlDlciVcComponentName OBJECT-TYPE
   SYNTAX     DisplayString 
   ACCESS     read-only
   STATUS     mandatory
   DESCRIPTION
     "This variable provides the component's string name for
      use with the ASCII Console Interface"
::= { mscMpanlDlciVcRowStatusEntry 2 }

mscMpanlDlciVcStorageType OBJECT-TYPE
   SYNTAX     StorageType 
   ACCESS     read-only
   STATUS     mandatory
   DESCRIPTION
     "This variable represents the storage type value for the
      mscMpanlDlciVc tables."
::= { mscMpanlDlciVcRowStatusEntry 4 }

mscMpanlDlciVcIndex OBJECT-TYPE
   SYNTAX     NonReplicated 
   ACCESS     not-accessible
   STATUS     mandatory
   DESCRIPTION
     "This variable represents the index for the mscMpanlDlciVc tables."
::= { mscMpanlDlciVcRowStatusEntry 10 }

mscMpanlDlciVcCadTable OBJECT-TYPE
   SYNTAX     SEQUENCE OF MscMpanlDlciVcCadEntry
   ACCESS     not-accessible
   STATUS     mandatory
   DESCRIPTION
     "*** THIS TABLE CURRENTLY NOT IMPLEMENTED ***

      This group represents operational call data related to Frame Relay 
      Vc. It can be displayed only for Frame Relay Vc which is created by 
      application."
::= { mscMpanlDlciVc 10 }

mscMpanlDlciVcCadEntry OBJECT-TYPE
   SYNTAX     MscMpanlDlciVcCadEntry
   ACCESS     not-accessible
   STATUS     mandatory
   DESCRIPTION
     "An entry in the mscMpanlDlciVcCadTable."
   INDEX {
      mscMpanlIndex,
      mscMpanlDlciIndex,
      mscMpanlDlciVcIndex }
::= { mscMpanlDlciVcCadTable 1 }

MscMpanlDlciVcCadEntry ::= SEQUENCE {
   mscMpanlDlciVcType
      INTEGER,
   mscMpanlDlciVcState
      INTEGER,
   mscMpanlDlciVcPreviousState
      INTEGER,
   mscMpanlDlciVcDiagnosticCode
      Unsigned32,
   mscMpanlDlciVcPreviousDiagnosticCode
      Unsigned32,
   mscMpanlDlciVcCalledNpi
      INTEGER,
   mscMpanlDlciVcCalledDna
      DigitString,
   mscMpanlDlciVcCalledLcn
      Unsigned32,
   mscMpanlDlciVcCallingNpi
      INTEGER,
   mscMpanlDlciVcCallingDna
      DigitString,
   mscMpanlDlciVcCallingLcn
      Unsigned32,
   mscMpanlDlciVcAccountingEnabled
      INTEGER,
   mscMpanlDlciVcFastSelectCall
      INTEGER,
   mscMpanlDlciVcPathReliability
      INTEGER,
   mscMpanlDlciVcAccountingEnd
      INTEGER,
   mscMpanlDlciVcPriority
      INTEGER,
   mscMpanlDlciVcSegmentSize
      Unsigned32,
   mscMpanlDlciVcMaxSubnetPktSize
      Unsigned32,
   mscMpanlDlciVcRcosToNetwork
      INTEGER,
   mscMpanlDlciVcRcosFromNetwork
      INTEGER,
   mscMpanlDlciVcEmissionPriorityToNetwork
      INTEGER,
   mscMpanlDlciVcEmissionPriorityFromNetwork
      INTEGER,
   mscMpanlDlciVcDataPath
      AsciiString }

mscMpanlDlciVcType OBJECT-TYPE
   SYNTAX     INTEGER  {
                 svc(0),
                 pvc(1),
                 spvc(2),
                 frf10spvc(3) }
   ACCESS     read-only
   STATUS     mandatory
   DESCRIPTION
     "This attribute displays the type of call, pvc,svc,spvc or frf10spvc."
::= { mscMpanlDlciVcCadEntry 1 }

mscMpanlDlciVcState OBJECT-TYPE
   SYNTAX     INTEGER  {
                 creating(0),
                 readyP1(1),
                 dteWaitingP2(2),
                 dceWaitingP3(3),
                 dataTransferP4(4),
                 unsupportedP5(5),
                 dteClearRequestP6(6),
                 dceClearIndicationP7(7),
                 termination(8) }
   ACCESS     read-only
   STATUS     mandatory
   DESCRIPTION
     "This attribute displays the state of call control. P5 state is not 
      supported but is listed for completness. Transitions from one state to 
      another take very short time. state most often displayed is 
      dataTransferP4."
::= { mscMpanlDlciVcCadEntry 2 }

mscMpanlDlciVcPreviousState OBJECT-TYPE
   SYNTAX     INTEGER  {
                 creating(0),
                 readyP1(1),
                 dteWaitingP2(2),
                 dceWaitingP3(3),
                 dataTransferP4(4),
                 unsupportedP5(5),
                 dteClearRequestP6(6),
                 dceClearIndicationP7(7),
                 termination(8) }
   ACCESS     read-only
   STATUS     mandatory
   DESCRIPTION
     "This attribute displays the previous state of call control. This is a 
      valuable field to determine how the processing is progressing."
::= { mscMpanlDlciVcCadEntry 3 }

mscMpanlDlciVcDiagnosticCode OBJECT-TYPE
   SYNTAX     Unsigned32 (0..255)
   ACCESS     read-only
   STATUS     mandatory
   DESCRIPTION
     "This attribute displays the internal substate of call control. It is used 
      to further refine state of call processing."
::= { mscMpanlDlciVcCadEntry 4 }

mscMpanlDlciVcPreviousDiagnosticCode OBJECT-TYPE
   SYNTAX     Unsigned32 (0..255)
   ACCESS     read-only
   STATUS     mandatory
   DESCRIPTION
     "This attribute displays the internal substate of call control. It is used 
      to further refine state of call processing."
::= { mscMpanlDlciVcCadEntry 5 }

mscMpanlDlciVcCalledNpi OBJECT-TYPE
   SYNTAX     INTEGER  {
                 x121(0),
                 e164(1) }
   ACCESS     read-only
   STATUS     mandatory
   DESCRIPTION
     "This attribute displays the Numbering Plan Indicator (NPI) of the 
      called end."
::= { mscMpanlDlciVcCadEntry 6 }

mscMpanlDlciVcCalledDna OBJECT-TYPE
   SYNTAX     DigitString (SIZE (1..15))
   ACCESS     read-only
   STATUS     mandatory
   DESCRIPTION
     "This attribute displays the Data Network Address (Dna) of the 
      called (destination) DTE to which this call is sent. This address if 
      defined at recieving end will complete Vc connection."
::= { mscMpanlDlciVcCadEntry 7 }

mscMpanlDlciVcCalledLcn OBJECT-TYPE
   SYNTAX     Unsigned32 (1..65535)
   ACCESS     read-only
   STATUS     mandatory
   DESCRIPTION
     "This attribute displays the Logical Channel Number of the called 
      end. It is valid only after both ends of Vc exchanged relevant 
      information."
::= { mscMpanlDlciVcCadEntry 8 }

mscMpanlDlciVcCallingNpi OBJECT-TYPE
   SYNTAX     INTEGER  {
                 x121(0),
                 e164(1) }
   ACCESS     read-only
   STATUS     mandatory
   DESCRIPTION
     "This attribute displays the Numbering Plan Indicator (NPI) of the 
      calling end."
::= { mscMpanlDlciVcCadEntry 9 }

mscMpanlDlciVcCallingDna OBJECT-TYPE
   SYNTAX     DigitString (SIZE (1..15))
   ACCESS     read-only
   STATUS     mandatory
   DESCRIPTION
     "This attribute displays the Data Network Address (Dna) of the 
      calling end."
::= { mscMpanlDlciVcCadEntry 10 }

mscMpanlDlciVcCallingLcn OBJECT-TYPE
   SYNTAX     Unsigned32 (1..65535)
   ACCESS     read-only
   STATUS     mandatory
   DESCRIPTION
     "This attribute displays the Logical Channel Number of the calling 
      end."
::= { mscMpanlDlciVcCadEntry 11 }

mscMpanlDlciVcAccountingEnabled OBJECT-TYPE
   SYNTAX     INTEGER  {
                 yes(0),
                 no(1) }
   ACCESS     read-only
   STATUS     mandatory
   DESCRIPTION
     "This attribute indicates that this optional section of accounting 
      record is suppressed or permitted. If accountingEnabled is yes, 
      conditions for generation of accounting record were met. These 
      conditions include billing options, vc recovery conditions and 
      Module wide accounting data options."
::= { mscMpanlDlciVcCadEntry 12 }

mscMpanlDlciVcFastSelectCall OBJECT-TYPE
   SYNTAX     INTEGER  {
                 no(0),
                 yes(1) }
   ACCESS     read-only
   STATUS     mandatory
   DESCRIPTION
     "This attribute displays that this is a fast select call."
::= { mscMpanlDlciVcCadEntry 13 }

mscMpanlDlciVcPathReliability OBJECT-TYPE
   SYNTAX     INTEGER  {
                 high(0),
                 normal(1) }
   ACCESS     read-only
   STATUS     mandatory
   DESCRIPTION
     "This attribute displays the path reliability."
::= { mscMpanlDlciVcCadEntry 19 }

mscMpanlDlciVcAccountingEnd OBJECT-TYPE
   SYNTAX     INTEGER  {
                 callingEnd(0),
                 calledEnd(1) }
   ACCESS     read-only
   STATUS     mandatory
   DESCRIPTION
     "This attribute indicates if this end should generate an accounting 
      record. Normally, callingEnd is the end to generate an accounting 
      record."
::= { mscMpanlDlciVcCadEntry 20 }

mscMpanlDlciVcPriority OBJECT-TYPE
   SYNTAX     INTEGER  {
                 normal(0),
                 high(1) }
   ACCESS     read-only
   STATUS     mandatory
   DESCRIPTION
     "This attribute displays whether the call is a normal or a high 
      priority call."
::= { mscMpanlDlciVcCadEntry 21 }

mscMpanlDlciVcSegmentSize OBJECT-TYPE
   SYNTAX     Unsigned32 (0..4096)
   ACCESS     read-only
   STATUS     mandatory
   DESCRIPTION
     "This attribute displays the segment size (in bytes) used on the call. 
      It is used to calculate the number of segments transmitted and 
      received."
::= { mscMpanlDlciVcCadEntry 22 }

mscMpanlDlciVcMaxSubnetPktSize OBJECT-TYPE
   SYNTAX     Unsigned32 (0..4096)
   ACCESS     read-only
   STATUS     mandatory
   DESCRIPTION
     "This attribute indicates the maximum packet size allowed on the Vc."
::= { mscMpanlDlciVcCadEntry 27 }

mscMpanlDlciVcRcosToNetwork OBJECT-TYPE
   SYNTAX     INTEGER  {
                 throughput(0),
                 delay(1),
                 multimedia(2) }
   ACCESS     read-only
   STATUS     mandatory
   DESCRIPTION
     "This attribute indicates the routing metric routing class of service to
      the network."
::= { mscMpanlDlciVcCadEntry 28 }

mscMpanlDlciVcRcosFromNetwork OBJECT-TYPE
   SYNTAX     INTEGER  {
                 throughput(0),
                 delay(1),
                 multimedia(2) }
   ACCESS     read-only
   STATUS     mandatory
   DESCRIPTION
     "This attribute displays the routing metric Routing Class of Service 
      from the Network."
::= { mscMpanlDlciVcCadEntry 29 }

mscMpanlDlciVcEmissionPriorityToNetwork OBJECT-TYPE
   SYNTAX     INTEGER  {
                 normal(0),
                 high(1),
                 interrupting(2) }
   ACCESS     read-only
   STATUS     mandatory
   DESCRIPTION
     "This attribute displays the network internal emission priotity to the 
      network."
::= { mscMpanlDlciVcCadEntry 30 }

mscMpanlDlciVcEmissionPriorityFromNetwork OBJECT-TYPE
   SYNTAX     INTEGER  {
                 normal(0),
                 high(1),
                 interrupting(2) }
   ACCESS     read-only
   STATUS     mandatory
   DESCRIPTION
     "This attribute displays the network internal emission priotity from 
      the network."
::= { mscMpanlDlciVcCadEntry 31 }

mscMpanlDlciVcDataPath OBJECT-TYPE
   SYNTAX     AsciiString (SIZE (0..32))
   ACCESS     read-only
   STATUS     mandatory
   DESCRIPTION
     "This attribute indicates the data path used by the connection. The 
      data path is provisioned in Dna and DirectCall components. The 
      displayed value of this attribute can be different from the 
      provisioned value.
      
      If the connection is using dprsOnly data path, the string 
      dprsOnly is displayed. (dynamic packet routing system)
      
      If the connection is using dprsMcsOnly data path, the string 
      dprsMcsOnly is displayed.
      
      If the connection is using dprsMcsFirst data path, the string 
      dprsMcsFirst is displayed."
::= { mscMpanlDlciVcCadEntry 32 }

mscMpanlDlciVcIntdTable OBJECT-TYPE
   SYNTAX     SEQUENCE OF MscMpanlDlciVcIntdEntry
   ACCESS     not-accessible
   STATUS     mandatory
   DESCRIPTION
     "*** THIS TABLE CURRENTLY NOT IMPLEMENTED ***

      This group defines display of interval data collected by Vc. Data in 
      this group is variable and may depend on time when this display 
      command is issued."
::= { mscMpanlDlciVc 11 }

mscMpanlDlciVcIntdEntry OBJECT-TYPE
   SYNTAX     MscMpanlDlciVcIntdEntry
   ACCESS     not-accessible
   STATUS     mandatory
   DESCRIPTION
     "An entry in the mscMpanlDlciVcIntdTable."
   INDEX {
      mscMpanlIndex,
      mscMpanlDlciIndex,
      mscMpanlDlciVcIndex }
::= { mscMpanlDlciVcIntdTable 1 }

MscMpanlDlciVcIntdEntry ::= SEQUENCE {
   mscMpanlDlciVcCallReferenceNumber
      Hex,
   mscMpanlDlciVcElapsedTimeTillNow
      Unsigned32,
   mscMpanlDlciVcSegmentsRx
      Unsigned32,
   mscMpanlDlciVcSegmentsSent
      Unsigned32,
   mscMpanlDlciVcStartTime
      EnterpriseDateAndTime,
   mscMpanlDlciVcCallReferenceNumberDecimal
      Unsigned32 }

mscMpanlDlciVcCallReferenceNumber OBJECT-TYPE
   SYNTAX     Hex (0..16777215)
   ACCESS     read-only
   STATUS     obsolete
   DESCRIPTION
     "This attribute is obsolete. It is replaced by the callReferenceNumber 
      attribute to display the call reference number in decimal. The 
      SNMP reference for the callReferenceNumber attribute is 
      callReferenceNumberDecimal."
::= { mscMpanlDlciVcIntdEntry 1 }

mscMpanlDlciVcElapsedTimeTillNow OBJECT-TYPE
   SYNTAX     Unsigned32 (0..16777215)
   ACCESS     read-only
   STATUS     mandatory
   DESCRIPTION
     "This attribute displays the elapsed time representing the period of 
      this interval data. It is elapsed time in 0.1 second increments since 
      Vc started."
::= { mscMpanlDlciVcIntdEntry 2 }

mscMpanlDlciVcSegmentsRx OBJECT-TYPE
   SYNTAX     Unsigned32 (0..16777215)
   ACCESS     read-only
   STATUS     mandatory
   DESCRIPTION
     "This attribute displays the number of segments received at the time 
      command was issued. This is the segment received count 
      maintained by accounting at each end of the Vc. This counter is 
      updated only when the packet cannot be successfully delivered out 
      of the sink Vc and to the sink AP Conditions in which packets may 
      be discarded by the sink Vc include: missing packets due to subnet 
      discards, segmentation protocol violations due to subnet discard, 
      duplicated and out-of-ranged packets and packets that arrive while 
      Vc is in path recovery state."
::= { mscMpanlDlciVcIntdEntry 3 }

mscMpanlDlciVcSegmentsSent OBJECT-TYPE
   SYNTAX     Unsigned32 (0..16777215)
   ACCESS     read-only
   STATUS     mandatory
   DESCRIPTION
     "This attribute displays the number of segments sent at the time 
      command was issued. This is the segment sent count maintained by 
      accounting at the source Vc. Vc only counts packets that Vc thinks 
      can be delivered successfully into the subnet. In reality, these 
      packets may be dropped by trunking, for instance. This counter is 
      not updated when splitting fails, when Vc is in a path recovery state, 
      when packet forwarding fails to forward this packet and when 
      subsequent packets have to be discarded as we want to minimize the 
      chance of out-of-sequence and do not intentionally send out-of-
      sequenced packets into the subnet."
::= { mscMpanlDlciVcIntdEntry 4 }

mscMpanlDlciVcStartTime OBJECT-TYPE
   SYNTAX     EnterpriseDateAndTime (SIZE (0 | 19))
   ACCESS     read-only
   STATUS     mandatory
   DESCRIPTION
     "This attribute displays the start time of this interval period. If Vc 
      spans 12 hour time or time of day change startTime reflects new 
      time as recorded at 12 hour periods or time of day changes."
::= { mscMpanlDlciVcIntdEntry 5 }

mscMpanlDlciVcCallReferenceNumberDecimal OBJECT-TYPE
   SYNTAX     Unsigned32 (0..4294967295)
   ACCESS     read-only
   STATUS     mandatory
   DESCRIPTION
     "This attribute displays the call reference number which is a unique 
      number generated by the switch.The same Call Reference Number 
      is stored in the interval data (accounting record) at both ends of the 
      call. It can be used as one of the attributes in matching duplicate 
      records generated at each end of the call."
::= { mscMpanlDlciVcIntdEntry 7 }

mscMpanlDlciVcFrdTable OBJECT-TYPE
   SYNTAX     SEQUENCE OF MscMpanlDlciVcFrdEntry
   ACCESS     not-accessible
   STATUS     mandatory
   DESCRIPTION
     "*** THIS TABLE CURRENTLY NOT IMPLEMENTED ***

      This group defines Frame Relay attributes collected by Frame Relay 
      Vc.
      The purpose of Vc attributes is to aid end users and verification 
      people to understand the Vc internal behavior. This is particularly 
      useful when the network has experienced abnormality and we want 
      to isolate problems and pinpoint trouble spots. 
      Attributes are collected on a per Vc basis. Until a need is identified, 
      statistics are not collected at a processor level. Each attribute is 
      stored in a 32 bit field and is initialized to zero when a Vc enters 
      into the data transfer state. When a PVC is disconnected and then 
      connected again, the attributes will be reset. Attributes cannot be 
      reset through other methods. 
      Frame Relay Vc uses a best effort data packet delivery protocol and 
      a different packet segmentation and combination methods from the 
      General Vc. The Frame Relay Vc uses the same call setup and 
      control mechanism (e.g. the support of non-flow control data 
      packets) as in a General Vc. Most General Vc statistics and internal 
      variables are used in a Frame Relay Vc and are displayed by 
      software developers"
::= { mscMpanlDlciVc 12 }

mscMpanlDlciVcFrdEntry OBJECT-TYPE
   SYNTAX     MscMpanlDlciVcFrdEntry
   ACCESS     not-accessible
   STATUS     mandatory
   DESCRIPTION
     "An entry in the mscMpanlDlciVcFrdTable."
   INDEX {
      mscMpanlIndex,
      mscMpanlDlciIndex,
      mscMpanlDlciVcIndex }
::= { mscMpanlDlciVcFrdTable 1 }

MscMpanlDlciVcFrdEntry ::= SEQUENCE {
   mscMpanlDlciVcFrmCongestedToSubnet
      Unsigned32,
   mscMpanlDlciVcCannotForwardToSubnet
      Unsigned32,
   mscMpanlDlciVcNotDataXferToSubnet
      Unsigned32,
   mscMpanlDlciVcOutOfRangeFrmFromSubnet
      Unsigned32,
   mscMpanlDlciVcCombErrorsFromSubnet
      Unsigned32,
   mscMpanlDlciVcDuplicatesFromSubnet
      Unsigned32,
   mscMpanlDlciVcNotDataXferFromSubnet
      Unsigned32,
   mscMpanlDlciVcFrmLossTimeouts
      Unsigned32,
   mscMpanlDlciVcOoSeqByteCntExceeded
      Unsigned32,
   mscMpanlDlciVcPeakOoSeqPktCount
      Unsigned32,
   mscMpanlDlciVcPeakOoSeqFrmForwarded
      Unsigned32,
   mscMpanlDlciVcSendSequenceNumber
      Unsigned32,
   mscMpanlDlciVcPktRetryTimeouts
      Unsigned32,
   mscMpanlDlciVcPeakRetryQueueSize
      Unsigned32,
   mscMpanlDlciVcSubnetRecoveries
      Unsigned32,
   mscMpanlDlciVcOoSeqPktCntExceeded
      Unsigned32,
   mscMpanlDlciVcPeakOoSeqByteCount
      Unsigned32 }

mscMpanlDlciVcFrmCongestedToSubnet OBJECT-TYPE
   SYNTAX     Unsigned32 (0..5000)
   ACCESS     read-only
   STATUS     mandatory
   DESCRIPTION
     "This attribute displays the number of frames from link discarded 
      due to lack of resources. It keeps track of the number of frames 
      from link that have to be discarded. The discard reasons include 
      insufficient memory for splitting the frame into smaller subnet 
      packet size."
::= { mscMpanlDlciVcFrdEntry 2 }

mscMpanlDlciVcCannotForwardToSubnet OBJECT-TYPE
   SYNTAX     Unsigned32 (0..5000)
   ACCESS     read-only
   STATUS     mandatory
   DESCRIPTION
     "This attribute displays the number of discarded packets that can not 
      be forwarded into the subnet because of subnet congestion.
      Number of frames from link discarded due to failure in forwarding 
      a packet from Vc into the subnet.- This attribute is increased when 
      packet forwarding fails to forward a packet into the subnet. If a 
      frame is split into multiple subnet packets and a partial packet has 
      to be discarded, all subsequent partial packets that have not yet been 
      delivered to the subnet will be discarded as well."
::= { mscMpanlDlciVcFrdEntry 3 }

mscMpanlDlciVcNotDataXferToSubnet OBJECT-TYPE
   SYNTAX     Unsigned32 (0..5000)
   ACCESS     read-only
   STATUS     mandatory
   DESCRIPTION
     "This attribute records the number of frames from link discarded 
      when the Vc tries to recover from internal path failure."
::= { mscMpanlDlciVcFrdEntry 4 }

mscMpanlDlciVcOutOfRangeFrmFromSubnet OBJECT-TYPE
   SYNTAX     Unsigned32 (0..5000)
   ACCESS     read-only
   STATUS     mandatory
   DESCRIPTION
     "This attribute displays the number of frames from subnet discarded 
      due to out of sequence range for arriving too late."
::= { mscMpanlDlciVcFrdEntry 5 }

mscMpanlDlciVcCombErrorsFromSubnet OBJECT-TYPE
   SYNTAX     Unsigned32 (0..5000)
   ACCESS     read-only
   STATUS     mandatory
   DESCRIPTION
     "This attribute records the number of subnet packets discarded at the 
      sink Vc due to the Vc segmentation and combination protocol error. 
      Usually, this occurs when the subnet discards packets and thus this 
      statistics can be used to guest the number of subnet packets that are 
      not delivered to the Vc. It cannot be used as an actual measure 
      because some subnet packets may have been delivered to Vc but 
      have to be discarded because these are partial packets to a frame in 
      which some other partial packets have not been properly delivered 
      to Vc"
::= { mscMpanlDlciVcFrdEntry 6 }

mscMpanlDlciVcDuplicatesFromSubnet OBJECT-TYPE
   SYNTAX     Unsigned32 (0..5000)
   ACCESS     read-only
   STATUS     mandatory
   DESCRIPTION
     "This attribute displays the number of subnet packets discarded due 
      to duplication. Although packets are not retransmitted by the Frame 
      Relay Vc, it is possible for the subnet to retransmit packets. When 
      packets are out-of-sequenced and copies of the same packets arrive, 
      then this attribute is increased."
::= { mscMpanlDlciVcFrdEntry 7 }

mscMpanlDlciVcNotDataXferFromSubnet OBJECT-TYPE
   SYNTAX     Unsigned32 (0..5000)
   ACCESS     read-only
   STATUS     mandatory
   DESCRIPTION
     "This attribute displays the number of subnet packets discarded when 
      data transfer is suspended in Vc recovery."
::= { mscMpanlDlciVcFrdEntry 8 }

mscMpanlDlciVcFrmLossTimeouts OBJECT-TYPE
   SYNTAX     Unsigned32 (0..5000)
   ACCESS     read-only
   STATUS     mandatory
   DESCRIPTION
     "This attribute displays the number of lost frame timer expiries.
      When this count is excessive, the network is very congested and 
      packets have been discarded in the subnet."
::= { mscMpanlDlciVcFrdEntry 9 }

mscMpanlDlciVcOoSeqByteCntExceeded OBJECT-TYPE
   SYNTAX     Unsigned32 (0..5000)
   ACCESS     read-only
   STATUS     mandatory
   DESCRIPTION
     "This attribute displays the number times that the out of sequence 
      byte threshold is exceeded. When the threshold is exceeded, this 
      condition is treated as if the loss frame timer has expired and all 
      frames queued at the sink Vc are delivered to the AP. We need to 
      keep this count to examine if the threshold is engineered properly. 
      This should be used in conjunction with the peak value of out-of-
      sequenced queue and the number of times the loss frame timer has 
      expired. This count should be relatively small when compared with 
      loss frame timer expiry count."
::= { mscMpanlDlciVcFrdEntry 10 }

mscMpanlDlciVcPeakOoSeqPktCount OBJECT-TYPE
   SYNTAX     Unsigned32 (0..5000)
   ACCESS     read-only
   STATUS     mandatory
   DESCRIPTION
     "This attribute displays the frame relay peak packet count of the out 
      of sequence queue. This attribute records the maximum queue 
      length of the out-of-sequenced queue. The counter can be used to 
      deduce the message buffer requirement on a Vc."
::= { mscMpanlDlciVcFrdEntry 11 }

mscMpanlDlciVcPeakOoSeqFrmForwarded OBJECT-TYPE
   SYNTAX     Unsigned32 (0..5000)
   ACCESS     read-only
   STATUS     mandatory
   DESCRIPTION
     "This attribute displays the frame relay peak size of the 
      sequence packet queue. The subnet may deliver packets out-of-
      sequenced. These packets are then queued in an out-of-sequenced 
      queue, waiting for a packet with the expected sequence number to 
      come. When that packet arrives, this attribute records the maximum 
      number of packets that were out-of-sequenced, but now have 
      become in-sequenced. The statistics is used to measure expected 
      queue size due to normal subnet packet disorder (not due to subnet 
      packet discard). Current implementation also uses this statistics to 
      set a maximum size for the out-of-sequenced queue."
::= { mscMpanlDlciVcFrdEntry 12 }

mscMpanlDlciVcSendSequenceNumber OBJECT-TYPE
   SYNTAX     Unsigned32 (0..5000)
   ACCESS     read-only
   STATUS     mandatory
   DESCRIPTION
     "This attribute displays the Vc internal packet's send sequence 
      number. Note that a 'packet' in this context, may be either a user 
      data packet, or an OAM frame."
::= { mscMpanlDlciVcFrdEntry 13 }

mscMpanlDlciVcPktRetryTimeouts OBJECT-TYPE
   SYNTAX     Unsigned32 (0..5000)
   ACCESS     read-only
   STATUS     mandatory
   DESCRIPTION
     "This attribute displays the number of packets which have 
      retransmission time-outs. When this count is excessive, the network 
      is very congested and packets have been discarded in the subnet."
::= { mscMpanlDlciVcFrdEntry 15 }

mscMpanlDlciVcPeakRetryQueueSize OBJECT-TYPE
   SYNTAX     Unsigned32 (0..5000)
   ACCESS     read-only
   STATUS     mandatory
   DESCRIPTION
     "This attribute displays the peak size of retransmission queue.
      This attribute is used as an indicator of the acknowledgment 
      behavior across the subnet. Records the largest body of 
      unacknowledged packets."
::= { mscMpanlDlciVcFrdEntry 16 }

mscMpanlDlciVcSubnetRecoveries OBJECT-TYPE
   SYNTAX     Unsigned32 (0..5000)
   ACCESS     read-only
   STATUS     mandatory
   DESCRIPTION
     "This attribute displays the number of successful Vc recovery 
      attempts."
::= { mscMpanlDlciVcFrdEntry 17 }

mscMpanlDlciVcOoSeqPktCntExceeded OBJECT-TYPE
   SYNTAX     Unsigned32 (0..255)
   ACCESS     read-only
   STATUS     mandatory
   DESCRIPTION
     "This attribute displays the number times that the out of sequence 
      packet threshold is exceeded. When the threshold is exceeded, this 
      condition is treated as if the loss frame timer has expired and all 
      frames queued at the sink Vc are delivered to the AP. We need to 
      keep this count to examine if the threshold is engineered properly. 
      This should be used in conjunction with the peak value of out-of-
      sequenced queue and the number of times the loss frame timer has 
      expired. This count should be relatively small when compared with 
      loss frame timer expiry count."
::= { mscMpanlDlciVcFrdEntry 19 }

mscMpanlDlciVcPeakOoSeqByteCount OBJECT-TYPE
   SYNTAX     Unsigned32 (0..50000)
   ACCESS     read-only
   STATUS     mandatory
   DESCRIPTION
     "This attribute displays the frame relay peak byte count of the out of 
      sequence queue. This attribute records the maximum queue length 
      of the out-of-sequenced queue. The counter can be used to deduce 
      the message buffer requirement on a Vc."
::= { mscMpanlDlciVcFrdEntry 20 }

mscMpanlDlciVcDmepTable OBJECT-TYPE
   SYNTAX     SEQUENCE OF MscMpanlDlciVcDmepEntry
   ACCESS     not-accessible
   STATUS     mandatory
   DESCRIPTION
     "*** THIS TABLE CURRENTLY NOT IMPLEMENTED ***

      This attribute displays the data path used by the connection. Data 
      path is provisioned in Dna and DirectCall components.
      
      If the connection is using dprsOnly data path, this attribute is 
      empty.
      
      If the connection is using dprsMcsOnly or dprsMcsFirst data path, 
      this attribute displays component name of the dprsMcsEndPoint."
::= { mscMpanlDlciVc 417 }

mscMpanlDlciVcDmepEntry OBJECT-TYPE
   SYNTAX     MscMpanlDlciVcDmepEntry
   ACCESS     not-accessible
   STATUS     mandatory
   DESCRIPTION
     "An entry in the mscMpanlDlciVcDmepTable."
   INDEX {
      mscMpanlIndex,
      mscMpanlDlciIndex,
      mscMpanlDlciVcIndex,
      mscMpanlDlciVcDmepValue }
::= { mscMpanlDlciVcDmepTable 1 }

MscMpanlDlciVcDmepEntry ::= SEQUENCE {
   mscMpanlDlciVcDmepValue
      RowPointer }

mscMpanlDlciVcDmepValue OBJECT-TYPE
   SYNTAX     RowPointer 
   ACCESS     read-only
   STATUS     mandatory
   DESCRIPTION
     "This variable represents both the value and the index for the
      mscMpanlDlciVcDmepTable."
::= { mscMpanlDlciVcDmepEntry 1 }

-- 
-- *** THIS SUBTREE CURRENTLY NOT IMPLEMENTED ***
-- 

-- Mpanl/n Dlci/m LCo
-- This component contains all of the operation attributes for a Path 
-- Oriented Logical Connection.

mscMpanlDlciLCo OBJECT IDENTIFIER ::= { mscMpanlDlci 4 }



mscMpanlDlciLCoRowStatusTable OBJECT-TYPE
   SYNTAX     SEQUENCE OF MscMpanlDlciLCoRowStatusEntry
   ACCESS     not-accessible
   STATUS     mandatory
   DESCRIPTION
     "*** THIS TABLE CURRENTLY NOT IMPLEMENTED ***

      This entry controls the addition and deletion of 
      mscMpanlDlciLCo components."
::= { mscMpanlDlciLCo 1 }

mscMpanlDlciLCoRowStatusEntry OBJECT-TYPE
   SYNTAX     MscMpanlDlciLCoRowStatusEntry
   ACCESS     not-accessible
   STATUS     mandatory
   DESCRIPTION
     "A single entry in the table represents a single 
      mscMpanlDlciLCo component."
   INDEX {
      mscMpanlIndex,
      mscMpanlDlciIndex,
      mscMpanlDlciLCoIndex }
::= { mscMpanlDlciLCoRowStatusTable 1 }

MscMpanlDlciLCoRowStatusEntry ::= SEQUENCE {
   mscMpanlDlciLCoRowStatus
      RowStatus,
   mscMpanlDlciLCoComponentName
      DisplayString,
   mscMpanlDlciLCoStorageType
      StorageType,
   mscMpanlDlciLCoIndex
      NonReplicated }

mscMpanlDlciLCoRowStatus OBJECT-TYPE
   SYNTAX     RowStatus 
   ACCESS     read-only
   STATUS     mandatory
   DESCRIPTION
     "This variable is used as the basis for SNMP naming of
      mscMpanlDlciLCo components.
      These components cannot be added nor deleted."
::= { mscMpanlDlciLCoRowStatusEntry 1 }

mscMpanlDlciLCoComponentName OBJECT-TYPE
   SYNTAX     DisplayString 
   ACCESS     read-only
   STATUS     mandatory
   DESCRIPTION
     "This variable provides the component's string name for
      use with the ASCII Console Interface"
::= { mscMpanlDlciLCoRowStatusEntry 2 }

mscMpanlDlciLCoStorageType OBJECT-TYPE
   SYNTAX     StorageType 
   ACCESS     read-only
   STATUS     mandatory
   DESCRIPTION
     "This variable represents the storage type value for the
      mscMpanlDlciLCo tables."
::= { mscMpanlDlciLCoRowStatusEntry 4 }

mscMpanlDlciLCoIndex OBJECT-TYPE
   SYNTAX     NonReplicated 
   ACCESS     not-accessible
   STATUS     mandatory
   DESCRIPTION
     "This variable represents the index for the mscMpanlDlciLCo tables."
::= { mscMpanlDlciLCoRowStatusEntry 10 }

mscMpanlDlciLCoPathDataTable OBJECT-TYPE
   SYNTAX     SEQUENCE OF MscMpanlDlciLCoPathDataEntry
   ACCESS     not-accessible
   STATUS     mandatory
   DESCRIPTION
     "*** THIS TABLE CURRENTLY NOT IMPLEMENTED ***

      This group contains all operational attributes for the path oriented 
      LCo."
::= { mscMpanlDlciLCo 10 }

mscMpanlDlciLCoPathDataEntry OBJECT-TYPE
   SYNTAX     MscMpanlDlciLCoPathDataEntry
   ACCESS     not-accessible
   STATUS     mandatory
   DESCRIPTION
     "An entry in the mscMpanlDlciLCoPathDataTable."
   INDEX {
      mscMpanlIndex,
      mscMpanlDlciIndex,
      mscMpanlDlciLCoIndex }
::= { mscMpanlDlciLCoPathDataTable 1 }

MscMpanlDlciLCoPathDataEntry ::= SEQUENCE {
   mscMpanlDlciLCoState
      INTEGER,
   mscMpanlDlciLCoEnd
      INTEGER,
   mscMpanlDlciLCoCostMetric
      Unsigned32,
   mscMpanlDlciLCoDelayMetric
      Unsigned32,
   mscMpanlDlciLCoRoundTripDelay
      Unsigned32,
   mscMpanlDlciLCoSetupPriority
      Unsigned32,
   mscMpanlDlciLCoHoldingPriority
      Unsigned32,
   mscMpanlDlciLCoRequiredTxBandwidth
      Gauge32,
   mscMpanlDlciLCoRequiredRxBandwidth
      Gauge32,
   mscMpanlDlciLCoRequiredTrafficType
      INTEGER,
   mscMpanlDlciLCoPermittedTrunkTypes
      OCTET STRING,
   mscMpanlDlciLCoRequiredSecurity
      Unsigned32,
   mscMpanlDlciLCoRequiredCustomerParameter
      Unsigned32,
   mscMpanlDlciLCoEmissionPriority
      Unsigned32,
   mscMpanlDlciLCoDiscardPriority
      Unsigned32,
   mscMpanlDlciLCoRetryCount
      Unsigned32,
   mscMpanlDlciLCoPathFailureCount
      Unsigned32,
   mscMpanlDlciLCoReasonForNoRoute
      INTEGER,
   mscMpanlDlciLCoLastTearDownReason
      INTEGER,
   mscMpanlDlciLCoPathFailureAction
      INTEGER,
   mscMpanlDlciLCoBumpPreference
      INTEGER,
   mscMpanlDlciLCoOptimization
      INTEGER,
   mscMpanlDlciLCoPathUpDateTime
      EnterpriseDateAndTime }

mscMpanlDlciLCoState OBJECT-TYPE
   SYNTAX     INTEGER  {
                 pathDown(0),
                 selectingRoute(1),
                 connecting(2),
                 pathUp(3),
                 pathDownRetrying(4) }
   ACCESS     read-only
   STATUS     mandatory
   DESCRIPTION
     "This attribute reflects the current state of the connection. The 
      pathDown state indicates that the application has not yet signalled 
      for a path. The selectingRoute state occurs when a request has been 
      sent to the route selector and it has not yet responded. The 
      connectingState occurs while a path is being established. The 
      pathUp state is the normal operational state of a path. The 
      pathDownRetrying state indicates a path that attempted route 
      selection but received no route and is now waiting to retry route 
      selection again."
::= { mscMpanlDlciLCoPathDataEntry 1 }

mscMpanlDlciLCoEnd OBJECT-TYPE
   SYNTAX     INTEGER  {
                 calling(0),
                 called(1) }
   ACCESS     read-only
   STATUS     mandatory
   DESCRIPTION
     "This attribute identifies whether this is the calling or called end of 
      the path."
::= { mscMpanlDlciLCoPathDataEntry 3 }

mscMpanlDlciLCoCostMetric OBJECT-TYPE
   SYNTAX     Unsigned32 (0..65535)
   ACCESS     read-only
   STATUS     mandatory
   DESCRIPTION
     "This attribute gives the route's total cost metric. It is calculated as 
      the sum of the cost metric of all trunks in the path at the time the 
      connection was established. The cost metric of a trunk is defined by 
      the trunkCost attribute of the Trunk component. The costMetric for 
      an LCo that is originated and terminated on the same module is 0."
::= { mscMpanlDlciLCoPathDataEntry 4 }

mscMpanlDlciLCoDelayMetric OBJECT-TYPE
   SYNTAX     Unsigned32 (0..100000)
   ACCESS     read-only
   STATUS     mandatory
   DESCRIPTION
     "This attribute gives the total delay of the route as the one way delay 
      for a 512 byte packet. It is calculated as the sum of the delays of all 
      trunks in the path stored in topology at the time the connection was 
      established. The delay for an LCo that is originated and terminated 
      on the same module is 0."
::= { mscMpanlDlciLCoPathDataEntry 5 }

mscMpanlDlciLCoRoundTripDelay OBJECT-TYPE
   SYNTAX     Unsigned32 (0..200000)
   ACCESS     read-only
   STATUS     mandatory
   DESCRIPTION
     "This attribute contains the time taken for a packet (cell) of 44 bytes 
      to be transmitted to the remote LCo and return to this LCo. The 
      number reported is given in milliseconds to the nearest millisecond. 
      A value of one millisecond is reported if the time is less than 1 
      millisecond even though the delay may be less than 1 millisecond 
      when the LCo is originated and terminated on the same module."
::= { mscMpanlDlciLCoPathDataEntry 6 }

mscMpanlDlciLCoSetupPriority OBJECT-TYPE
   SYNTAX     Unsigned32 (0..4)
   ACCESS     read-only
   STATUS     mandatory
   DESCRIPTION
     "This attribute gives the priority at which the current path is 
      established. Zero is the highest priority and four is the lowest. The 
      holdingPriority, a complementary attribute of this component, 
      indicates the priority a path maintains once it is established."
::= { mscMpanlDlciLCoPathDataEntry 7 }

mscMpanlDlciLCoHoldingPriority OBJECT-TYPE
   SYNTAX     Unsigned32 (0..4)
   ACCESS     read-only
   STATUS     mandatory
   DESCRIPTION
     "This attribute gives the priority at which a path holds its current 
      path once the path is established. Zero is the highest priority and 
      four is the lowest. The setupPriority, a complementary attribute, 
      indicates the priority of a path at establishment time."
::= { mscMpanlDlciLCoPathDataEntry 8 }

mscMpanlDlciLCoRequiredTxBandwidth OBJECT-TYPE
   SYNTAX     Gauge32 (0..2048000)
   ACCESS     read-only
   STATUS     mandatory
   DESCRIPTION
     "This attribute gives the actual bandwidth (in bits per second) 
      reserved by this path on each of the trunks of its route. This attribute 
      represents the bandwidth for traffic outgoing to the remote end 
      point. The originating end of the connection determines this value."
::= { mscMpanlDlciLCoPathDataEntry 9 }

mscMpanlDlciLCoRequiredRxBandwidth OBJECT-TYPE
   SYNTAX     Gauge32 (0..2048000)
   ACCESS     read-only
   STATUS     mandatory
   DESCRIPTION
     "This attribute gives the actual bandwidth (in bits per second) 
      reserved by this path on each of trunks of its route. This attribute 
      represents the bandwidth for traffic incoming from the remote end 
      point. The originating end of the connection determines this value"
::= { mscMpanlDlciLCoPathDataEntry 10 }

mscMpanlDlciLCoRequiredTrafficType OBJECT-TYPE
   SYNTAX     INTEGER  {
                 voice(0),
                 data(1),
                 video(2),
                 trafficType1(3),
                 trafficType2(4),
                 trafficType3(5),
                 trafficType4(6),
                 trafficType5(7) }
   ACCESS     read-only
   STATUS     mandatory
   DESCRIPTION
     "This operational attribute indicates the type of traffic transmitted 
      over the path. There are eight possible traffic types, and the path can 
      transmit only one of them. The originating end of the connection 
      determines the type. These are arbitrary designations for traffic 
      type. The voice, data and video traffic types are defined, and five 
      other arbitrary traffic types can be defined by the network 
      administration. This attribute is used in the route selection process 
      to restrict the route to trunks that support this traffic type. The 
      supportedTrafficType trunk attribute lists all the types of traffic 
      allowed on the trunk. For example, if requiredTrafficType is 
      specified as trafficType1 then only trunks that include trafficType1 
      in supportedTrafficType, will be candidates for this connection."
::= { mscMpanlDlciLCoPathDataEntry 11 }

mscMpanlDlciLCoPermittedTrunkTypes OBJECT-TYPE
   SYNTAX     OCTET STRING (SIZE (1))
   ACCESS     read-only
   STATUS     mandatory
   DESCRIPTION
     "This operational attribute lists up to eight types of trunk that can be 
      used on the route. The originating end of the connection determines 
      the types. The terrestrial and satellite trunk types have been 
      defined, leaving six remaining arbitrary types that can be defined by 
      the network administration. The trunk's type is indicated in the 
      trunkType attribute of the Trunk component. When selecting a 
      route, PORS only chooses trunks whose trunkType are in the 
      permittedTrunkTypes for the path.

      Description of bits:
      terrestrial(0)
      satellite(1)
      trunkType1(2)
      trunkType2(3)
      trunkType3(4)
      trunkType4(5)
      trunkType5(6)
      trunkType6(7)"
::= { mscMpanlDlciLCoPathDataEntry 12 }

mscMpanlDlciLCoRequiredSecurity OBJECT-TYPE
   SYNTAX     Unsigned32 (0..7)
   ACCESS     read-only
   STATUS     mandatory
   DESCRIPTION
     "This attribute indicates the required minimum level of security of 
      the trunks on the route. Zero represents the most secure and seven 
      represents the least secure. The trunk's security is indicated by the 
      trunkSecurity attribute of the Trunk component, and has values 
      identical in range and meaning to the requiredSecurity attribute. 
      PORS ensures that any route selected does not contain a trunk 
      whose trunkSecurity attribute is numerically greater than the 
      requiredSecurity."
::= { mscMpanlDlciLCoPathDataEntry 13 }

mscMpanlDlciLCoRequiredCustomerParameter OBJECT-TYPE
   SYNTAX     Unsigned32 (0..7)
   ACCESS     read-only
   STATUS     mandatory
   DESCRIPTION
     "This attribute indicates the allowed customer defined parameter of 
      the trunks on the route.The originating end of the connection 
      determines the customer defined parameter. Its value, a number 
      from zero to seven, is chosen by a network administration to have a 
      meaning specific to their network, thus allowing them to customize 
      the use of their trunks. A complementary trunk attribute, 
      customerParameter, also has a value from zero to seven. The route 
      selection process does not consider trunks whose 
      customerParameter is greater than the requiredCustomerParameter 
      of the path."
::= { mscMpanlDlciLCoPathDataEntry 14 }

mscMpanlDlciLCoEmissionPriority OBJECT-TYPE
   SYNTAX     Unsigned32 (0..2)
   ACCESS     read-only
   STATUS     mandatory
   DESCRIPTION
     "This attribute indicates the urgency with which packets on the path 
      are emitted by the trunks on the route. The originating end of the 
      connection selects the emissionPriority. EmissionPriority of zero 
      indicates the highest emission priority, while two indicates the 
      lowest emission priority. Packets with a higher emissionPriority (or 
      numerically less) are serviced and sent out before the packets of 
      lower emissionPriority (or numerically higher)."
::= { mscMpanlDlciLCoPathDataEntry 15 }

mscMpanlDlciLCoDiscardPriority OBJECT-TYPE
   SYNTAX     Unsigned32 (1..3)
   ACCESS     read-only
   STATUS     mandatory
   DESCRIPTION
     "This attribute indicates the importance of the packets on the 
      path.The originating end of the connection sets discardPriority. One 
      is used for paths carrying the most important traffic, and three is 
      used for paths carrying the least important traffic. Packets with 
      lower discardPriority(numerically lower) are discarded after 
      packets with a higher discardPriority(numerically higher)."
::= { mscMpanlDlciLCoPathDataEntry 16 }

mscMpanlDlciLCoRetryCount OBJECT-TYPE
   SYNTAX     Unsigned32 (0..255)
   ACCESS     read-only
   STATUS     mandatory
   DESCRIPTION
     "This attribute is the count of the number of times the path chosen 
      during route selection could not be instantiated. This count should 
      be three or below if the network is performing adequately. A high 
      value indicates that the route selection is often performed using an 
      out-of-date view of available network bandwidth and/or topology.
      This attribute will only increase at the calling end of the connection.
      This attribute is reset each time a path reconnects and stops 
      counting when it reaches its maximum value."
::= { mscMpanlDlciLCoPathDataEntry 18 }

mscMpanlDlciLCoPathFailureCount OBJECT-TYPE
   SYNTAX     Unsigned32 (0..65535)
   ACCESS     read-only
   STATUS     mandatory
   DESCRIPTION
     "This attribute is the count of the number of times the path has 
      successfully reconnected. It is set to zero the first time the path is 
      up. If a path fails anytime after connecting, this count will be 
      incremented when the path is up again. Failed route requests do not 
      count in this statistic. See retryCount(rcount) - page 78. This 
      attribute stops counting at its maximum value."
::= { mscMpanlDlciLCoPathDataEntry 19 }

mscMpanlDlciLCoReasonForNoRoute OBJECT-TYPE
   SYNTAX     INTEGER  {
                 none(0),
                 destinationNameTooLong(1),
                 destinationNotSpecified(2),
                 unknownDestinationName(3),
                 incorrectDestination(4),
                 incorrectDestinationEndPoint(5),
                 unknownSource(6),
                 unknownDestination(7),
                 sameNode(8),
                 routeCostTooMuch(9),
                 routesDelayTooLong(10),
                 attributesNotMet(11),
                 anError(12),
                 attributeProfileProblem(13),
                 manualPathIndexProblem(14) }
   ACCESS     read-only
   STATUS     mandatory
   DESCRIPTION
     "This attribute is the route selection's reasonForNoRoute and 
      provides a brief reason for which a route was not selected. The 
      reasons are essentially self-explanatory."
   DEFVAL     { none }
::= { mscMpanlDlciLCoPathDataEntry 20 }

mscMpanlDlciLCoLastTearDownReason OBJECT-TYPE
   SYNTAX     INTEGER  {
                 none(0),
                 normalShutDown(1),
                 insufficientTxLcOrBandwidth(2),
                 insufficientRxLcOrBandwidth(3),
                 trunkFailure(4),
                 trunkCardFailure(5),
                 operatorForced(6),
                 lostLcnClash(7),
                 networkCongestion(8),
                 trunkNotFound(9),
                 farEndNotFound(10),
                 wrongModuleReached(11),
                 farEndBusy(12),
                 callLoopedBack(13),
                 unknownReason(14),
                 farEndNotReady(15),
                 remoteNameMismatch(16),
                 serviceTypeMismatch(17),
                 reconnectFromFarEnd(18),
                 bumped(19),
                 accessCardFailure(20),
                 optimized(21),
                 overrideRemoteName(22) }
   ACCESS     read-only
   STATUS     mandatory
   DESCRIPTION
     "This attribute reflects the last tear down reason for a connection 
      (LCo). In many cases this displays the reason for a momentary 
      service interruption. This attribute applies to the last path failure 
      only. If a path is no longer up, this may indicate why the path has 
      failed. In many cases an alarm will also be generated with more 
      specific information. The following is a brief description of the 
      reasons:
      none - This path has no information for the teardown. 
      normalShutDown - This path has gone down due to normal call 
      termination.
      insufficientTxLcOrBandwidth - At present there is either no 
      available bandwidth or logical channel numbers available on one or 
      more of the trunks for this path in the transmit direction.
      insufficientRxLcOrBandwidth - At present there is either no 
      available bandwidth or logical channel numbers available on one or 
      more of the trunks for this path in the receive direction.
      trunkFailure- A trunk on the path has failed or has gone down due 
      to a provisioning change of a critical attribute.
      trunkCardFailure- A trunk FP card has failed along the path.
      accessCardFailure- The FP on which the peer access service was 
      running has failed.
      operatorForced- The path has terminated due to the operator 
      locking a trunk along the path.
      lostLcnClash- The path has terminated because the PAs at both 
      ends of an intermediate trunk have allocated the same LC to 
      different calls. When this happens both calls must go down and then 
      try to come up again a fraction of a second later (effectively 
      ensuring that they will now be assigned different LCs). It is normal 
      to get the odd clash especially when the PA's usedLC is 
      approaching the PA's maxLC.
      networkCongestion - The path has failed due to control information 
      being lost and not recoverable.
      trunkNotFound - Occurs on a manual path usually. Check for 
      trunks not up or names provisioned incorrectly.
      farEndNotFound - The far end is not provisioned or is not up. 
      Check remote Name.
      wrongModuleReached - This may occur on a manual path. Check 
      provisioning for correct trunk and service names. For a normal 
      path, the network Topology may be changing. Check remote 
      provisioned DNA.
      farEndBusy - The far end has been reached but it is busy. Check 
      remote provisioned DNA and remote end provisioning.
      unknownReason - The failure was not resolved.
      farEndNotReady - The remote end was reached but the connection 
      was refused due to the remote end not being enabled.
      serviceTypeMismatch - The remote service type does not match 
      this service type. Check provisioning.
      reconnectFromFarEnd - The remote end re-established this 
      connection. Check the remote end lastTearDownReason to 
      determine the real reason.
      bumped - Another call bumped this path from a trunk to get 
      bandwidth (or an LC) which it required to come up. This other path 
      had a higher setupPriority than this path's holdingPriority, hence it 
      was allowed to steal the bandwidth (or LC) from this path.
      optimized - This call has been rerouted due to the optimization 
      feature. The call is still active; this just indicates why the path 
      changed."
   DEFVAL     { none }
::= { mscMpanlDlciLCoPathDataEntry 21 }

mscMpanlDlciLCoPathFailureAction OBJECT-TYPE
   SYNTAX     INTEGER  {
                 disconnectConnection(0),
                 reRoutePath(1) }
   ACCESS     read-only
   STATUS     mandatory
   DESCRIPTION
     "This attribute displays whether the application is set to tolerate a 
      momentary interruption of a path while a new path is selected. If 
      disconnectConnection is displayed, the application is informed as 
      soon as possible about a failure by disconnection. If the attribute 
      displays reRoutePath, the path may attempt an immediate reroute, 
      provided the failure is a recoverable failure. If rerouting fails the 
      application is informed of the failure. 
      With this option set to reRoutePath the LCo may wait up to 30 
      seconds before informing the service of complete disconnection in 
      order to allow both ends to attempt to reconnect. All pathTypes 
      respect this attribute. Also, on a manualPath with both ends 
      provisioned with independent paths (at least with respect to the 
      failure) this option will have the desired effect that the path is 
      rerouted without complete disconnection at both ends."
::= { mscMpanlDlciLCoPathDataEntry 22 }

mscMpanlDlciLCoBumpPreference OBJECT-TYPE
   SYNTAX     INTEGER  {
                 bumpWhenNecessary(0),
                 bumpToObtainBestRoute(1) }
   ACCESS     read-only
   STATUS     mandatory
   DESCRIPTION
     "This attribute specifies when bumping will occur during the route 
      selection process. Bumping may occur when necessary or always. It 
      will be necessary for a connection to bump if there is not enough 
      resources for the connection to be established and these resources 
      are occupied by a connection whose holdingPriority is lower 
      (numerically higher) than the connection's setupPriority. A 
      connection may also always bump in order to obtain the best route."
::= { mscMpanlDlciLCoPathDataEntry 23 }

mscMpanlDlciLCoOptimization OBJECT-TYPE
   SYNTAX     INTEGER  {
                 disabled(0),
                 enabled(1) }
   ACCESS     read-only
   STATUS     mandatory
   DESCRIPTION
     "This attribute is used to specify whether this connection should 
      attempt to optimize its path when requested by the routing PORS 
      component. Every path is as optimal as it can be when it is 
      established, but as network traffic patterns and configurations 
      change this path may no longer be as optimal as it could be. The 
      PORS connection manager on a module requests circuits to 
      optimize at the optimization interval."
::= { mscMpanlDlciLCoPathDataEntry 24 }

mscMpanlDlciLCoPathUpDateTime OBJECT-TYPE
   SYNTAX     EnterpriseDateAndTime (SIZE (0 | 19))
   ACCESS     read-only
   STATUS     mandatory
   DESCRIPTION
     "This is the time stamp when the current path was established or 
      reestablished."
::= { mscMpanlDlciLCoPathDataEntry 25 }

mscMpanlDlciLCoStatsTable OBJECT-TYPE
   SYNTAX     SEQUENCE OF MscMpanlDlciLCoStatsEntry
   ACCESS     not-accessible
   STATUS     mandatory
   DESCRIPTION
     "*** THIS TABLE CURRENTLY NOT IMPLEMENTED ***

      This group contains the operational statistics attributes for the path 
      oriented LCo."
::= { mscMpanlDlciLCo 11 }

mscMpanlDlciLCoStatsEntry OBJECT-TYPE
   SYNTAX     MscMpanlDlciLCoStatsEntry
   ACCESS     not-accessible
   STATUS     mandatory
   DESCRIPTION
     "An entry in the mscMpanlDlciLCoStatsTable."
   INDEX {
      mscMpanlIndex,
      mscMpanlDlciIndex,
      mscMpanlDlciLCoIndex }
::= { mscMpanlDlciLCoStatsTable 1 }

MscMpanlDlciLCoStatsEntry ::= SEQUENCE {
   mscMpanlDlciLCoPktsToNetwork
      PassportCounter64,
   mscMpanlDlciLCoBytesToNetwork
      PassportCounter64,
   mscMpanlDlciLCoPktsFromNetwork
      PassportCounter64,
   mscMpanlDlciLCoBytesFromNetwork
      PassportCounter64 }

mscMpanlDlciLCoPktsToNetwork OBJECT-TYPE
   SYNTAX     PassportCounter64 
   ACCESS     read-only
   STATUS     mandatory
   DESCRIPTION
     "This attribute counts the number of packets transmitted to the 
      network over this Logical Connection."
::= { mscMpanlDlciLCoStatsEntry 1 }

mscMpanlDlciLCoBytesToNetwork OBJECT-TYPE
   SYNTAX     PassportCounter64 
   ACCESS     read-only
   STATUS     mandatory
   DESCRIPTION
     "This attribute counts the number of bytes sent to the network over 
      this Logical Connection."
::= { mscMpanlDlciLCoStatsEntry 2 }

mscMpanlDlciLCoPktsFromNetwork OBJECT-TYPE
   SYNTAX     PassportCounter64 
   ACCESS     read-only
   STATUS     mandatory
   DESCRIPTION
     "This attribute counts the number of packets received from the 
      remote LCo via the network. This attribute wraps to 0."
::= { mscMpanlDlciLCoStatsEntry 3 }

mscMpanlDlciLCoBytesFromNetwork OBJECT-TYPE
   SYNTAX     PassportCounter64 
   ACCESS     read-only
   STATUS     mandatory
   DESCRIPTION
     "This attribute counts the number of bytes received from the remote 
      LCo via the network. This attribute wraps to 0."
::= { mscMpanlDlciLCoStatsEntry 4 }

mscMpanlDlciLCoCallDataTable OBJECT-TYPE
   SYNTAX     SEQUENCE OF MscMpanlDlciLCoCallDataEntry
   ACCESS     not-accessible
   STATUS     mandatory
   DESCRIPTION
     "*** THIS TABLE CURRENTLY NOT IMPLEMENTED ***

      This group contains all operational attributes for the path oriented 
      LCo."
::= { mscMpanlDlciLCo 12 }

mscMpanlDlciLCoCallDataEntry OBJECT-TYPE
   SYNTAX     MscMpanlDlciLCoCallDataEntry
   ACCESS     not-accessible
   STATUS     mandatory
   DESCRIPTION
     "An entry in the mscMpanlDlciLCoCallDataTable."
   INDEX {
      mscMpanlIndex,
      mscMpanlDlciIndex,
      mscMpanlDlciLCoIndex }
::= { mscMpanlDlciLCoCallDataTable 1 }

MscMpanlDlciLCoCallDataEntry ::= SEQUENCE {
   mscMpanlDlciLCoCallingNpi
      INTEGER,
   mscMpanlDlciLCoCallingDna
      DigitString,
   mscMpanlDlciLCoElapsedTimeTillNow
      Unsigned32,
   mscMpanlDlciLCoCallReferenceNumber
      Hex,
   mscMpanlDlciLCoCalledNpi
      INTEGER,
   mscMpanlDlciLCoCalledDna
      DigitString }

mscMpanlDlciLCoCallingNpi OBJECT-TYPE
   SYNTAX     INTEGER  {
                 x121(0),
                 e164(1) }
   ACCESS     read-only
   STATUS     mandatory
   DESCRIPTION
     "This attribute displays the Numbering Plan Indicator (NPI) of the 
      calling end."
   DEFVAL     { x121 }
::= { mscMpanlDlciLCoCallDataEntry 27 }

mscMpanlDlciLCoCallingDna OBJECT-TYPE
   SYNTAX     DigitString (SIZE (0..15))
   ACCESS     read-only
   STATUS     mandatory
   DESCRIPTION
     "This attribute displays the Data Network Address (DNA) of the 
      calling end."
::= { mscMpanlDlciLCoCallDataEntry 28 }

mscMpanlDlciLCoElapsedTimeTillNow OBJECT-TYPE
   SYNTAX     Unsigned32 (0..16777215)
   ACCESS     read-only
   STATUS     mandatory
   DESCRIPTION
     "This attribute displays the total duration in tenths of miliseconds 
      that a connection has been up for a call."
::= { mscMpanlDlciLCoCallDataEntry 30 }

mscMpanlDlciLCoCallReferenceNumber OBJECT-TYPE
   SYNTAX     Hex (0..16777215)
   ACCESS     read-only
   STATUS     mandatory
   DESCRIPTION
     "This attribute displays the call reference number which is a unique 
      number generated by the switch.The same Call Reference Number 
      is stored in the interval data (accounting record) at both ends of the 
      call. It can be used as one of the attributes in matching duplicate 
      records generated at each end of the call."
::= { mscMpanlDlciLCoCallDataEntry 31 }

mscMpanlDlciLCoCalledNpi OBJECT-TYPE
   SYNTAX     INTEGER  {
                 x121(0),
                 e164(1) }
   ACCESS     read-only
   STATUS     mandatory
   DESCRIPTION
     "This attribute indicates the Numbering Plan Indicator (NPI) of the 
      called end."
   DEFVAL     { x121 }
::= { mscMpanlDlciLCoCallDataEntry 33 }

mscMpanlDlciLCoCalledDna OBJECT-TYPE
   SYNTAX     DigitString (SIZE (0..15))
   ACCESS     read-only
   STATUS     mandatory
   DESCRIPTION
     "This attribute indicates the Data Network Address (DNA) of the 
      called (destination) DTE to which this call is sent. This address if 
      defined at the receiving end will complete the logical connection."
::= { mscMpanlDlciLCoCallDataEntry 34 }

mscMpanlDlciLCoPathTable OBJECT-TYPE
   SYNTAX     SEQUENCE OF MscMpanlDlciLCoPathEntry
   ACCESS     not-accessible
   STATUS     mandatory
   DESCRIPTION
     "*** THIS TABLE CURRENTLY NOT IMPLEMENTED ***

      This attribute contains the trunk component names over which the 
      path has been instantiated and the remote end point name 
      terminating the path."
::= { mscMpanlDlciLCo 401 }

mscMpanlDlciLCoPathEntry OBJECT-TYPE
   SYNTAX     MscMpanlDlciLCoPathEntry
   ACCESS     not-accessible
   STATUS     mandatory
   DESCRIPTION
     "An entry in the mscMpanlDlciLCoPathTable."
   INDEX {
      mscMpanlIndex,
      mscMpanlDlciIndex,
      mscMpanlDlciLCoIndex,
      mscMpanlDlciLCoPathValue }
::= { mscMpanlDlciLCoPathTable 1 }

MscMpanlDlciLCoPathEntry ::= SEQUENCE {
   mscMpanlDlciLCoPathValue
      AsciiString }

mscMpanlDlciLCoPathValue OBJECT-TYPE
   SYNTAX     AsciiString (SIZE (0..40))
   ACCESS     read-only
   STATUS     mandatory
   DESCRIPTION
     "This variable represents both the value and the index for the
      mscMpanlDlciLCoPathTable."
::= { mscMpanlDlciLCoPathEntry 1 }

-- 
-- *** THIS SUBTREE CURRENTLY NOT IMPLEMENTED ***
-- 

-- Mpanl/n Dlci/n JunctorVc
-- This component extends the GVC connectivity across MPANL. It 
-- allows applications in a Legacy Data Module (LDM) subnet to 
-- establish GVC connections with applications in the Magellan 
-- subnet.

mscMpanlDlciJvc OBJECT IDENTIFIER ::= { mscMpanlDlci 5 }



mscMpanlDlciJvcRowStatusTable OBJECT-TYPE
   SYNTAX     SEQUENCE OF MscMpanlDlciJvcRowStatusEntry
   ACCESS     not-accessible
   STATUS     mandatory
   DESCRIPTION
     "*** THIS TABLE CURRENTLY NOT IMPLEMENTED ***

      This entry controls the addition and deletion of 
      mscMpanlDlciJvc components."
::= { mscMpanlDlciJvc 1 }

mscMpanlDlciJvcRowStatusEntry OBJECT-TYPE
   SYNTAX     MscMpanlDlciJvcRowStatusEntry
   ACCESS     not-accessible
   STATUS     mandatory
   DESCRIPTION
     "A single entry in the table represents a single 
      mscMpanlDlciJvc component."
   INDEX {
      mscMpanlIndex,
      mscMpanlDlciIndex,
      mscMpanlDlciJvcIndex }
::= { mscMpanlDlciJvcRowStatusTable 1 }

MscMpanlDlciJvcRowStatusEntry ::= SEQUENCE {
   mscMpanlDlciJvcRowStatus
      RowStatus,
   mscMpanlDlciJvcComponentName
      DisplayString,
   mscMpanlDlciJvcStorageType
      StorageType,
   mscMpanlDlciJvcIndex
      NonReplicated }

mscMpanlDlciJvcRowStatus OBJECT-TYPE
   SYNTAX     RowStatus 
   ACCESS     read-only
   STATUS     mandatory
   DESCRIPTION
     "This variable is used as the basis for SNMP naming of
      mscMpanlDlciJvc components.
      These components cannot be added nor deleted."
::= { mscMpanlDlciJvcRowStatusEntry 1 }

mscMpanlDlciJvcComponentName OBJECT-TYPE
   SYNTAX     DisplayString 
   ACCESS     read-only
   STATUS     mandatory
   DESCRIPTION
     "This variable provides the component's string name for
      use with the ASCII Console Interface"
::= { mscMpanlDlciJvcRowStatusEntry 2 }

mscMpanlDlciJvcStorageType OBJECT-TYPE
   SYNTAX     StorageType 
   ACCESS     read-only
   STATUS     mandatory
   DESCRIPTION
     "This variable represents the storage type value for the
      mscMpanlDlciJvc tables."
::= { mscMpanlDlciJvcRowStatusEntry 4 }

mscMpanlDlciJvcIndex OBJECT-TYPE
   SYNTAX     NonReplicated 
   ACCESS     not-accessible
   STATUS     mandatory
   DESCRIPTION
     "This variable represents the index for the mscMpanlDlciJvc tables."
::= { mscMpanlDlciJvcRowStatusEntry 10 }

mscMpanlDlciJvcOperTable OBJECT-TYPE
   SYNTAX     SEQUENCE OF MscMpanlDlciJvcOperEntry
   ACCESS     not-accessible
   STATUS     mandatory
   DESCRIPTION
     "*** THIS TABLE CURRENTLY NOT IMPLEMENTED ***

      This group contains the operational attributes of the Jvc component."
::= { mscMpanlDlciJvc 10 }

mscMpanlDlciJvcOperEntry OBJECT-TYPE
   SYNTAX     MscMpanlDlciJvcOperEntry
   ACCESS     not-accessible
   STATUS     mandatory
   DESCRIPTION
     "An entry in the mscMpanlDlciJvcOperTable."
   INDEX {
      mscMpanlIndex,
      mscMpanlDlciIndex,
      mscMpanlDlciJvcIndex }
::= { mscMpanlDlciJvcOperTable 1 }

MscMpanlDlciJvcOperEntry ::= SEQUENCE {
   mscMpanlDlciJvcCurrentState
      INTEGER,
   mscMpanlDlciJvcPreviousState
      INTEGER,
   mscMpanlDlciJvcCallingNpi
      INTEGER,
   mscMpanlDlciJvcCallingAddress
      DigitString,
   mscMpanlDlciJvcCallingLcn
      Unsigned32,
   mscMpanlDlciJvcCalledNpi
      INTEGER,
   mscMpanlDlciJvcCalledAddress
      DigitString,
   mscMpanlDlciJvcCalledLcn
      Unsigned32 }

mscMpanlDlciJvcCurrentState OBJECT-TYPE
   SYNTAX     INTEGER  {
                 null(0),
                 callRequest(1),
                 callIndication(2),
                 callBlockPresent(3),
                 active(4),
                 discInitiated(5),
                 discPktPresent(6),
                 callDisconnected(7),
                 callTerminated(8) }
   ACCESS     read-only
   STATUS     mandatory
   DESCRIPTION
     "This attribute indicates the current state of the JVC process.
      The state can be one of:
      null:	 waiting for an incoming call or a call request from MPANL,
      callRequest: waiting for the call connected from MPANL,
      callIndication: waiting for the call packet from MPANL,
      callBlockPresent: waiting for the Raccept packet from the subnet,
      active: relaying packets between the subnet and MPANL,
      discInitiated: not used by the DCE JVC,
      discPktPresent: not used by the DCE JVC,
      callDisconnected: waiting for the termination request from 
      MPANL,
      callTerminated: waiting for the termination by MPANL."
::= { mscMpanlDlciJvcOperEntry 1 }

mscMpanlDlciJvcPreviousState OBJECT-TYPE
   SYNTAX     INTEGER  {
                 null(0),
                 callRequest(1),
                 callIndication(2),
                 callBlockPresent(3),
                 active(4),
                 discInitiated(5),
                 discPktPresent(6),
                 callDisconnected(7),
                 callTerminated(8) }
   ACCESS     read-only
   STATUS     mandatory
   DESCRIPTION
     "This attribute indicates the previous state of the JVC process.
      The state can be one of:
      null:	 waiting for an incoming call or a call request from MPANL,
      callRequest: waiting for the call connected from MPANL,
      callIndication: waiting for the call packet from MPANL,
      callBlockPresent: waiting for the Raccept packet from the subnet,
      active: relaying packets between the subnet and MPANL,
      discInitiated: not used by the DCE JVC,
      discPktPresent: not used by the DCE JVC,
      callDisconnected: waiting for the termination request from 
      MPANL,
      callTerminated: waiting for the termination by MPANL."
::= { mscMpanlDlciJvcOperEntry 2 }

mscMpanlDlciJvcCallingNpi OBJECT-TYPE
   SYNTAX     INTEGER  {
                 x121(0),
                 e164(1) }
   ACCESS     read-only
   STATUS     mandatory
   DESCRIPTION
     "This attribute contains the numbering plan indicator of the calling 
      address. This attribute value is retrieved from the call packet."
::= { mscMpanlDlciJvcOperEntry 6 }

mscMpanlDlciJvcCallingAddress OBJECT-TYPE
   SYNTAX     DigitString (SIZE (1..15))
   ACCESS     read-only
   STATUS     mandatory
   DESCRIPTION
     "This attribute contains the calling DataNetworkAddress of the 
      interface. It includes the DNIC (first 4 digits) for X.121, and the CC 
      (Country Code) for the E.164 address of the calling end. The 
      maximum length of this attribute is 15 digits. This attribute value is 
      retrieved from the call packet."
::= { mscMpanlDlciJvcOperEntry 7 }

mscMpanlDlciJvcCallingLcn OBJECT-TYPE
   SYNTAX     Unsigned32 (1..4095)
   ACCESS     read-only
   STATUS     mandatory
   DESCRIPTION
     "This attribute contains the calling LCN (logical channel number) of 
      the interface. This number is assigned to the call request at the 
      calling end. This attribute value is retrieved from the call packet."
::= { mscMpanlDlciJvcOperEntry 8 }

mscMpanlDlciJvcCalledNpi OBJECT-TYPE
   SYNTAX     INTEGER  {
                 x121(0),
                 e164(1) }
   ACCESS     read-only
   STATUS     mandatory
   DESCRIPTION
     "This attribute contains the numbering plan indicator of the called 
      address. This attribute value is retrieved from the call packet."
::= { mscMpanlDlciJvcOperEntry 9 }

mscMpanlDlciJvcCalledAddress OBJECT-TYPE
   SYNTAX     DigitString (SIZE (1..15))
   ACCESS     read-only
   STATUS     mandatory
   DESCRIPTION
     "This attribute contains the called DataNetworkAddress of the 
      interface. It includes the DNIC (first 4 digits) for X.121, and the CC 
      (Country Code) for the E.164 address of the called end. The 
      maximum length of this attribute is 15 digits. This attribute value is 
      retrieved from the Raccept packet."
::= { mscMpanlDlciJvcOperEntry 10 }

mscMpanlDlciJvcCalledLcn OBJECT-TYPE
   SYNTAX     Unsigned32 (1..4095)
   ACCESS     read-only
   STATUS     mandatory
   DESCRIPTION
     "This attribute contains the called LCN (logical channel number) of 
      the interface. This number is assigned to the call request at the 
      called end. This attribute value is retrieved from the Raccept packet."
::= { mscMpanlDlciJvcOperEntry 11 }

mscMpanlDlciJvcStatTable OBJECT-TYPE
   SYNTAX     SEQUENCE OF MscMpanlDlciJvcStatEntry
   ACCESS     not-accessible
   STATUS     mandatory
   DESCRIPTION
     "*** THIS TABLE CURRENTLY NOT IMPLEMENTED ***

      This group contains the statistics collected by the Jvc component."
::= { mscMpanlDlciJvc 11 }

mscMpanlDlciJvcStatEntry OBJECT-TYPE
   SYNTAX     MscMpanlDlciJvcStatEntry
   ACCESS     not-accessible
   STATUS     mandatory
   DESCRIPTION
     "An entry in the mscMpanlDlciJvcStatTable."
   INDEX {
      mscMpanlIndex,
      mscMpanlDlciIndex,
      mscMpanlDlciJvcIndex }
::= { mscMpanlDlciJvcStatTable 1 }

MscMpanlDlciJvcStatEntry ::= SEQUENCE {
   mscMpanlDlciJvcPacketsFromSubnet
      Unsigned32,
   mscMpanlDlciJvcPacketsToSubnet
      Unsigned32,
   mscMpanlDlciJvcPacketsDiscarded
      Unsigned32,
   mscMpanlDlciJvcProtocolErrors
      Unsigned32 }

mscMpanlDlciJvcPacketsFromSubnet OBJECT-TYPE
   SYNTAX     Unsigned32 (0..4294967295)
   ACCESS     read-only
   STATUS     mandatory
   DESCRIPTION
     "This attribute counts all packets including control packets received 
      from the subnet. This number reflects also the packets sent to the 
      MPANL process since the JVC does not drop or generate packets in 
      this direction.The value of this attribute wraps to 0 when the 
      maximum value is reached."
::= { mscMpanlDlciJvcStatEntry 1 }

mscMpanlDlciJvcPacketsToSubnet OBJECT-TYPE
   SYNTAX     Unsigned32 (0..4294967295)
   ACCESS     read-only
   STATUS     mandatory
   DESCRIPTION
     "This attribute counts all packets including control packets sent into 
      the subnet. This number includes Renew Call Timer Packets that are 
      generated by the JVC. The value of this attribute wraps to 0 when 
      the maximum value is reached."
::= { mscMpanlDlciJvcStatEntry 2 }

mscMpanlDlciJvcPacketsDiscarded OBJECT-TYPE
   SYNTAX     Unsigned32 (0..4294967295)
   ACCESS     read-only
   STATUS     mandatory
   DESCRIPTION
     "This attribute counts discarded packets that can not be forwarded 
      into the subnet because of subnet congestion. This attribute is 
      increased when packet forwarding fails to forward a packet into the 
      subnet."
::= { mscMpanlDlciJvcStatEntry 3 }

mscMpanlDlciJvcProtocolErrors OBJECT-TYPE
   SYNTAX     Unsigned32 (0..4294967295)
   ACCESS     read-only
   STATUS     mandatory
   DESCRIPTION
     "This attribute counts the number of protocol errors detected by the 
      JVC in both the MPANL and the subnet directions. A protocol error 
      is counted in the following cases:
      - reception of a packet from MPANL while waiting for a Raccept 
      packet from the subnet,
      - reception of a packet from the subnet following a call packet and 
      before the callAccepted is received from MPANL,
      - reception of a packet from the subnet or from MPANL that is 
      shorter than the subnet header.
      The value of this attribute wraps to 0 when the maximum value is 
      reached."
::= { mscMpanlDlciJvcStatEntry 4 }


-- Mpanl/<n> Signaling
-- This component defines the Q.933 and Q.922 (LAPF) parameters 
-- for Frame Relay switched virtual circuits at the Mpanl interface.

mscMpanlSig OBJECT IDENTIFIER ::= { mscMpanl 6 }



mscMpanlSigRowStatusTable OBJECT-TYPE
   SYNTAX     SEQUENCE OF MscMpanlSigRowStatusEntry
   ACCESS     not-accessible
   STATUS     mandatory
   DESCRIPTION
     "This entry controls the addition and deletion of 
      mscMpanlSig components."
::= { mscMpanlSig 1 }

mscMpanlSigRowStatusEntry OBJECT-TYPE
   SYNTAX     MscMpanlSigRowStatusEntry
   ACCESS     not-accessible
   STATUS     mandatory
   DESCRIPTION
     "A single entry in the table represents a single 
      mscMpanlSig component."
   INDEX {
      mscMpanlIndex,
      mscMpanlSigIndex }
::= { mscMpanlSigRowStatusTable 1 }

MscMpanlSigRowStatusEntry ::= SEQUENCE {
   mscMpanlSigRowStatus
      RowStatus,
   mscMpanlSigComponentName
      DisplayString,
   mscMpanlSigStorageType
      StorageType,
   mscMpanlSigIndex
      NonReplicated }

mscMpanlSigRowStatus OBJECT-TYPE
   SYNTAX     RowStatus 
   ACCESS     read-only
   STATUS     mandatory
   DESCRIPTION
     "This variable is used as the basis for SNMP naming of
      mscMpanlSig components.
      These components cannot be added nor deleted."
::= { mscMpanlSigRowStatusEntry 1 }

mscMpanlSigComponentName OBJECT-TYPE
   SYNTAX     DisplayString 
   ACCESS     read-only
   STATUS     mandatory
   DESCRIPTION
     "This variable provides the component's string name for
      use with the ASCII Console Interface"
::= { mscMpanlSigRowStatusEntry 2 }

mscMpanlSigStorageType OBJECT-TYPE
   SYNTAX     StorageType 
   ACCESS     read-only
   STATUS     mandatory
   DESCRIPTION
     "This variable represents the storage type value for the
      mscMpanlSig tables."
::= { mscMpanlSigRowStatusEntry 4 }

mscMpanlSigIndex OBJECT-TYPE
   SYNTAX     NonReplicated 
   ACCESS     not-accessible
   STATUS     mandatory
   DESCRIPTION
     "This variable represents the index for the mscMpanlSig tables."
::= { mscMpanlSigRowStatusEntry 10 }

mscMpanlSigSysParmsTable OBJECT-TYPE
   SYNTAX     SEQUENCE OF MscMpanlSigSysParmsEntry
   ACCESS     not-accessible
   STATUS     mandatory
   DESCRIPTION
     "This group contains the provisionable Q.933 system parameters."
::= { mscMpanlSig 13 }

mscMpanlSigSysParmsEntry OBJECT-TYPE
   SYNTAX     MscMpanlSigSysParmsEntry
   ACCESS     not-accessible
   STATUS     mandatory
   DESCRIPTION
     "An entry in the mscMpanlSigSysParmsTable."
   INDEX {
      mscMpanlIndex,
      mscMpanlSigIndex }
::= { mscMpanlSigSysParmsTable 1 }

MscMpanlSigSysParmsEntry ::= SEQUENCE {
   mscMpanlSigCallSetupTimer
      Unsigned32,
   mscMpanlSigDisconnectTimer
      Unsigned32,
   mscMpanlSigReleaseTimer
      Unsigned32,
   mscMpanlSigCallProceedingTimer
      Unsigned32,
   mscMpanlSigNetworkType
      INTEGER }

mscMpanlSigCallSetupTimer OBJECT-TYPE
   SYNTAX     Unsigned32 (1..255)
   ACCESS     read-write
   STATUS     mandatory
   DESCRIPTION
     "This attribute specifies the time the network will wait for a response 
      to the SETUP message sent to the called user. Upon timer expiry, 
      the SETUP message is retransmitted. The second expiry of this 
      timer causes the call to be cleared. This value is specified in 
      seconds."
   DEFVAL     { 4 }
::= { mscMpanlSigSysParmsEntry 1 }

mscMpanlSigDisconnectTimer OBJECT-TYPE
   SYNTAX     Unsigned32 (1..255)
   ACCESS     read-write
   STATUS     mandatory
   DESCRIPTION
     "This attribute specifies the time the network will wait for a response 
      to the DISCONNECT message sent to the user. Upon timer expiry, 
      the RELEASE message is sent. This value is specified in seconds."
   DEFVAL     { 30 }
::= { mscMpanlSigSysParmsEntry 2 }

mscMpanlSigReleaseTimer OBJECT-TYPE
   SYNTAX     Unsigned32 (1..255)
   ACCESS     read-write
   STATUS     mandatory
   DESCRIPTION
     "This attribute specifies the time the network will wait for a response 
      to the RELEASE message sent to the user. Upon timer expiry, the 
      RELEASE message is retransmitted. The second expiry of the timer 
      causes the call to be released. This value is specified in seconds."
   DEFVAL     { 4 }
::= { mscMpanlSigSysParmsEntry 3 }

mscMpanlSigCallProceedingTimer OBJECT-TYPE
   SYNTAX     Unsigned32 (1..255)
   ACCESS     read-write
   STATUS     mandatory
   DESCRIPTION
     "This attribute specifies the time the network will wait for the 
      CONNECT message from the called user after the network has 
      received the optional CALL PROCEEDING message from the 
      called user. Upon timer expiry, the call is cleared. This value is 
      specified in seconds."
   DEFVAL     { 10 }
::= { mscMpanlSigSysParmsEntry 4 }

mscMpanlSigNetworkType OBJECT-TYPE
   SYNTAX     INTEGER  {
                 private(1),
                 public(2) }
   ACCESS     read-write
   STATUS     mandatory
   DESCRIPTION
     "This attribute specifies whether this Frame Relay service is running 
      on a public or a private network. This value is used solely in 
      populating applicable information elements within those Q.933 
      messages that require a public or private network indication."
   DEFVAL     { private }
::= { mscMpanlSigSysParmsEntry 5 }

mscMpanlSigLapfSysTable OBJECT-TYPE
   SYNTAX     SEQUENCE OF MscMpanlSigLapfSysEntry
   ACCESS     not-accessible
   STATUS     mandatory
   DESCRIPTION
     "This group contains the provisionable attributes for the SVC data 
      link layer. The data link layer is governed primarily through ITU 
      specification Q.922, and operates over DLCI 0.."
::= { mscMpanlSig 14 }

mscMpanlSigLapfSysEntry OBJECT-TYPE
   SYNTAX     MscMpanlSigLapfSysEntry
   ACCESS     not-accessible
   STATUS     mandatory
   DESCRIPTION
     "An entry in the mscMpanlSigLapfSysTable."
   INDEX {
      mscMpanlIndex,
      mscMpanlSigIndex }
::= { mscMpanlSigLapfSysTable 1 }

MscMpanlSigLapfSysEntry ::= SEQUENCE {
   mscMpanlSigWindowSize
      Unsigned32,
   mscMpanlSigRetransmitLimit
      Unsigned32,
   mscMpanlSigAckTimer
      Unsigned32,
   mscMpanlSigAckDelayTimer
      Unsigned32,
   mscMpanlSigIdleProbeTimer
      Unsigned32 }

mscMpanlSigWindowSize OBJECT-TYPE
   SYNTAX     Unsigned32 (1..127)
   ACCESS     read-write
   STATUS     mandatory
   DESCRIPTION
     "This attribute specifies the window size. This is the maximum 
      number of unacknowledged sequenced frames that may be 
      outstanding from or to this interface at any one time."
   DEFVAL     { 7 }
::= { mscMpanlSigLapfSysEntry 2 }

mscMpanlSigRetransmitLimit OBJECT-TYPE
   SYNTAX     Unsigned32 (0..20)
   ACCESS     read-write
   STATUS     mandatory
   DESCRIPTION
     "This attribute specifies the number of times a frame can be 
      retransmitted by the SVC data link layer before appropriate 
      recovery action is taken."
   DEFVAL     { 3 }
::= { mscMpanlSigLapfSysEntry 3 }

mscMpanlSigAckTimer OBJECT-TYPE
   SYNTAX     Unsigned32 (1000..10000)
   ACCESS     read-write
   STATUS     mandatory
   DESCRIPTION
     "This attribute specifies the period in milliseconds that the network 
      will wait for an acknowledgment to a sent frame. The value set for 
      ackTimer must be less than the value set for idleProbeTimer."
   DEFVAL     { 1500 }
::= { mscMpanlSigLapfSysEntry 4 }

mscMpanlSigAckDelayTimer OBJECT-TYPE
   SYNTAX     Unsigned32 (0..10000)
   ACCESS     read-write
   STATUS     mandatory
   DESCRIPTION
     "This attribute specifies the maximum period in milliseconds that the 
      network will wait before sending an acknowledgment for a received 
      in-sequence I-frame. A value of 0 means there will be no delay in 
      acknowledgment."
   DEFVAL     { 0 }
::= { mscMpanlSigLapfSysEntry 5 }

mscMpanlSigIdleProbeTimer OBJECT-TYPE
   SYNTAX     Unsigned32 (1000..65535000)
   ACCESS     read-write
   STATUS     mandatory
   DESCRIPTION
     "This attribute specifies the time period in milliseconds the link will 
      be permitted to remain idle (that is, no frames are exchanged on the 
      data link). Upon expiry of this timer, the network's side link layer 
      polls its peer for status. The value set for idleProbeTimer must be 
      greater than the value set for ackTimer."
   DEFVAL     { 30000 }
::= { mscMpanlSigLapfSysEntry 6 }

mscMpanlSigSvcaccTable OBJECT-TYPE
   SYNTAX     SEQUENCE OF MscMpanlSigSvcaccEntry
   ACCESS     not-accessible
   STATUS     mandatory
   DESCRIPTION
     "This group contains the provisionable attribute to define the 
      defaultAccounting attribute.."
::= { mscMpanlSig 15 }

mscMpanlSigSvcaccEntry OBJECT-TYPE
   SYNTAX     MscMpanlSigSvcaccEntry
   ACCESS     not-accessible
   STATUS     mandatory
   DESCRIPTION
     "An entry in the mscMpanlSigSvcaccTable."
   INDEX {
      mscMpanlIndex,
      mscMpanlSigIndex }
::= { mscMpanlSigSvcaccTable 1 }

MscMpanlSigSvcaccEntry ::= SEQUENCE {
   mscMpanlSigDefaultAccounting
      INTEGER }

mscMpanlSigDefaultAccounting OBJECT-TYPE
   SYNTAX     INTEGER  {
                 off(0),
                 on(1) }
   ACCESS     read-write
   STATUS     mandatory
   DESCRIPTION
     "This attribute specifies whether accounting data collection and 
      record generation is turned on at this DLCI. For accounting data 
      collection and record generation to be turned on, the 
      defaultAccounting bit and at least one of the accountCollection 
      bits in the FrsDataNetworkAddress component must be set to on."
   DEFVAL     { on }
::= { mscMpanlSigSvcaccEntry 1 }

mscMpanlSigStateTable OBJECT-TYPE
   SYNTAX     SEQUENCE OF MscMpanlSigStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscMpanlSig 16 }

mscMpanlSigStateEntry OBJECT-TYPE
   SYNTAX     MscMpanlSigStateEntry
   ACCESS     not-accessible
   STATUS     mandatory
   DESCRIPTION
     "An entry in the mscMpanlSigStateTable."
   INDEX {
      mscMpanlIndex,
      mscMpanlSigIndex }
::= { mscMpanlSigStateTable 1 }

MscMpanlSigStateEntry ::= SEQUENCE {
   mscMpanlSigAdminState
      INTEGER,
   mscMpanlSigOperationalState
      INTEGER,
   mscMpanlSigUsageState
      INTEGER }

mscMpanlSigAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscMpanlSigStateEntry 1 }

mscMpanlSigOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscMpanlSigStateEntry 2 }

mscMpanlSigUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscMpanlSigStateEntry 3 }

mscMpanlSigStatsTable OBJECT-TYPE
   SYNTAX     SEQUENCE OF MscMpanlSigStatsEntry
   ACCESS     not-accessible
   STATUS     mandatory
   DESCRIPTION
     "This group contains the statistics related to the SVC signaling layer 
      at the interface level."
::= { mscMpanlSig 17 }

mscMpanlSigStatsEntry OBJECT-TYPE
   SYNTAX     MscMpanlSigStatsEntry
   ACCESS     not-accessible
   STATUS     mandatory
   DESCRIPTION
     "An entry in the mscMpanlSigStatsTable."
   INDEX {
      mscMpanlIndex,
      mscMpanlSigIndex }
::= { mscMpanlSigStatsTable 1 }

MscMpanlSigStatsEntry ::= SEQUENCE {
   mscMpanlSigCurrentNumberOfSvcCalls
      Unsigned32,
   mscMpanlSigInCalls
      Counter32,
   mscMpanlSigInCallsRefused
      Counter32,
   mscMpanlSigOutCalls
      Counter32,
   mscMpanlSigOutCallsFailed
      Counter32,
   mscMpanlSigProtocolErrors
      Counter32,
   mscMpanlSigQualityOfServiceNotAvailable
      Counter32,
   mscMpanlSigSetupTimeout
      Counter32,
   mscMpanlSigLastCauseInStatusMsgReceived
      Unsigned32,
   mscMpanlSigLastStateInStatusMsgReceived
      INTEGER,
   mscMpanlSigLastDlciReceivedStatus
      Unsigned32,
   mscMpanlSigLastQ933StateReceivedStatus
      INTEGER,
   mscMpanlSigLastTimeMsgBlockCongested
      EnterpriseDateAndTime,
   mscMpanlSigLastDlciWithMsgBlockCongestion
      Unsigned32 }

mscMpanlSigCurrentNumberOfSvcCalls OBJECT-TYPE
   SYNTAX     Unsigned32 (0..991)
   ACCESS     read-only
   STATUS     mandatory
   DESCRIPTION
     "This attribute shows the number of Frame Relay SVCs currently 
      existing on this interface."
::= { mscMpanlSigStatsEntry 1 }

mscMpanlSigInCalls OBJECT-TYPE
   SYNTAX     Counter32 
   ACCESS     read-only
   STATUS     mandatory
   DESCRIPTION
     "This attribute indicates the current number of incoming SVCs on 
      this interface (that is,  the number of SVCs for which this interface 
      represents the destination end of the call)."
::= { mscMpanlSigStatsEntry 4 }

mscMpanlSigInCallsRefused OBJECT-TYPE
   SYNTAX     Counter32 
   ACCESS     read-only
   STATUS     mandatory
   DESCRIPTION
     "This attribute counts the number of incoming SVC call requests that 
      are rejected by either this interface or by the called user. When this 
      count reaches maximum, it wraps to zero."
::= { mscMpanlSigStatsEntry 5 }

mscMpanlSigOutCalls OBJECT-TYPE
   SYNTAX     Counter32 
   ACCESS     read-only
   STATUS     mandatory
   DESCRIPTION
     "This attribute shows the current number of outgoing SVCs on this 
      interface (that is,  the number of SVCs for which this interface 
      represents the source end of the call)."
::= { mscMpanlSigStatsEntry 6 }

mscMpanlSigOutCallsFailed OBJECT-TYPE
   SYNTAX     Counter32 
   ACCESS     read-only
   STATUS     mandatory
   DESCRIPTION
     "This attribute counts the number of outgoing SVC call requests that 
      are rejected by either this interface, or by the network side of the 
      destination end, or by the called user. When this count reaches 
      maximum, it wraps to zero."
::= { mscMpanlSigStatsEntry 7 }

mscMpanlSigProtocolErrors OBJECT-TYPE
   SYNTAX     Counter32 
   ACCESS     read-only
   STATUS     mandatory
   DESCRIPTION
     "This attribute counts the number of times a Q.933 protocol error has 
      occurred. Any one of the following events constitutes a protocol 
      error:
      1. In the user-signaled Link Layer Core Parameters IE within the
      SETUP or CONNECT messages, Cir, Bc and Be are all zero;
      2. In the user-signaled Link Layer Core Parameters IE within the
      SETUP or CONNECT messages, Cir is zero but Bc is 
      non-zero, or Bc is zero but Cir is non-zero;
      3. In the user-signaled Link Layer Core Parameters IE within the
      SETUP or CONNECT messages, the minimum acceptable Cir
      is greater than Cir;
      4. At the destination end, any of the destination to source direction 
      link layer core parameters has been increased in the 
      CONNECT message from the called user;
      5. At the destination end, the destination to source direction Cir
      in the CONNECT message is smaller than the corresponding 
      minimum acceptable Cir signaled to the called user;
      6. At the source end, any of the source to destination direction 
      link layer core parameters in the CONNECT message from the 
      destination end has been increased;
      7. At the source end, the source to destination direction Cir, after
      negotiation, is smaller than the corresponding minimum
      acceptable Cir;
      8. The network has received a STATUS message from the user
      with an incompatible Q.933 state.	
      
      When this count reaches maximum, it wraps to zero."
::= { mscMpanlSigStatsEntry 8 }

mscMpanlSigQualityOfServiceNotAvailable OBJECT-TYPE
   SYNTAX     Counter32 
   ACCESS     read-only
   STATUS     mandatory
   DESCRIPTION
     "This attribute counts the number of incoming and outgoing SVCs 
      that are rejected because the quality of service requested cannot be 
      met by the network. When this count reaches maximum, it wraps to 
      zero."
::= { mscMpanlSigStatsEntry 9 }

mscMpanlSigSetupTimeout OBJECT-TYPE
   SYNTAX     Counter32 
   ACCESS     read-only
   STATUS     mandatory
   DESCRIPTION
     "This attribute counts the number of times the T303 setup timer has 
      expired. When this count reaches maximum, it wraps to zero."
::= { mscMpanlSigStatsEntry 10 }

mscMpanlSigLastCauseInStatusMsgReceived OBJECT-TYPE
   SYNTAX     Unsigned32 (0..255)
   ACCESS     read-only
   STATUS     mandatory
   DESCRIPTION
     "This attribute shows the cause value in the last received user's 
      STATUS message to an existing call. The DLCI to which this 
      STATUS message applies is specified in the lastDlciReceivedStatus 
      attribute.
      
      The initial value of this attribute is 0 which means that no STATUS 
      message has been received for an existing call."
::= { mscMpanlSigStatsEntry 11 }

mscMpanlSigLastStateInStatusMsgReceived OBJECT-TYPE
   SYNTAX     INTEGER  {
                 null(0),
                 callInitiated(1),
                 n2(2),
                 outgoingCallProceeding(3),
                 n4(4),
                 n5(5),
                 callPresent(6),
                 n7(7),
                 n8(8),
                 incomingCallProceeding(9),
                 active(10),
                 disconnectRequest(11),
                 disconnectIndication(12),
                 n13(13),
                 n14(14),
                 n15(15),
                 n16(16),
                 n17(17),
                 n18(18),
                 releaseRequest(19),
                 notApplicable(20),
                 n21(21),
                 n22(22),
                 n23(23),
                 n24(24),
                 n25(25),
                 n26(26),
                 n27(27),
                 n28(28),
                 n29(29),
                 n30(30),
                 n31(31),
                 n32(32),
                 n33(33),
                 n34(34),
                 n35(35),
                 n36(36),
                 n37(37),
                 n38(38),
                 n39(39),
                 n40(40),
                 n41(41),
                 n42(42),
                 n43(43),
                 n44(44),
                 n45(45),
                 n46(46),
                 n47(47),
                 n48(48),
                 n49(49),
                 n50(50),
                 n51(51),
                 n52(52),
                 n53(53),
                 n54(54),
                 n55(55),
                 n56(56),
                 n57(57),
                 n58(58),
                 n59(59),
                 n60(60),
                 n61(61),
                 n62(62),
                 n63(63) }
   ACCESS     read-only
   STATUS     mandatory
   DESCRIPTION
     "This attribute shows the state value in the last received user's 
      STATUS message to an existing call. The DLCI to which this 
      STATUS message applies is specified in the lastDlciReceivedStatus 
      attribute.
      
      The initial value of this attribute is notApplicable."
::= { mscMpanlSigStatsEntry 12 }

mscMpanlSigLastDlciReceivedStatus OBJECT-TYPE
   SYNTAX     Unsigned32 (0 | 17..1007)
   ACCESS     read-only
   STATUS     mandatory
   DESCRIPTION
     "This attribute shows the value of the DLCI that has most recently 
      received a STATUS message from the user.
      
      The initial value of this attribute is 0."
::= { mscMpanlSigStatsEntry 13 }

mscMpanlSigLastQ933StateReceivedStatus OBJECT-TYPE
   SYNTAX     INTEGER  {
                 null(0),
                 callInitiated(1),
                 outgoingCallProceeding(3),
                 callPresent(6),
                 incomingCallProceeding(9),
                 active(10),
                 disconnectRequest(11),
                 disconnectIndication(12),
                 releaseRequest(19),
                 notApplicable(20) }
   ACCESS     read-only
   STATUS     mandatory
   DESCRIPTION
     "This attribute shows the network Q.933 state of the DLCI that has 
      most recently received a STATUS message from the user. The DLCI 
      to which this STATUS message applies is specified in the 
      lastDlciReceivedStatus attribute.
      
      The initial value of this attribute is notApplicable."
::= { mscMpanlSigStatsEntry 14 }

mscMpanlSigLastTimeMsgBlockCongested OBJECT-TYPE
   SYNTAX     EnterpriseDateAndTime (SIZE (0 | 16))
   ACCESS     read-only
   STATUS     mandatory
   DESCRIPTION
     "This attribute displays the most recent time that an SVC DLCI has 
      failed to get a message block due to message block congestion. 
      Exceptional behavior can occur due to this. The DLCI that has most 
      recently encountered this is indicated by the 
      lastDlciWithMsgBlockCongestion attribute. However, all SVC 
      DLCIs may be affected.
      
      The initial value of this attribute is 0000-00-00 00:00."
::= { mscMpanlSigStatsEntry 15 }

mscMpanlSigLastDlciWithMsgBlockCongestion OBJECT-TYPE
   SYNTAX     Unsigned32 (0 | 16..1007)
   ACCESS     read-only
   STATUS     mandatory
   DESCRIPTION
     "This attribute shows the value of the DLCI that has most recently 
      failed to get a message block due to message block congestion.
      
      The initial value of this attribute is 0."
::= { mscMpanlSigStatsEntry 16 }

mscMpanlSigLapfStatusTable OBJECT-TYPE
   SYNTAX     SEQUENCE OF MscMpanlSigLapfStatusEntry
   ACCESS     not-accessible
   STATUS     mandatory
   DESCRIPTION
     "This group contains the Q.922 SVC data link layer status."
::= { mscMpanlSig 18 }

mscMpanlSigLapfStatusEntry OBJECT-TYPE
   SYNTAX     MscMpanlSigLapfStatusEntry
   ACCESS     not-accessible
   STATUS     mandatory
   DESCRIPTION
     "An entry in the mscMpanlSigLapfStatusTable."
   INDEX {
      mscMpanlIndex,
      mscMpanlSigIndex }
::= { mscMpanlSigLapfStatusTable 1 }

MscMpanlSigLapfStatusEntry ::= SEQUENCE {
   mscMpanlSigCurrentState
      INTEGER,
   mscMpanlSigLastStateChangeReason
      INTEGER,
   mscMpanlSigFrmrReceive
      HexString,
   mscMpanlSigCurrentQueueSize
      Counter32 }

mscMpanlSigCurrentState OBJECT-TYPE
   SYNTAX     INTEGER  {
                 disconnected(1),
                 linkSetup(2),
                 disconnectRequest(4),
                 informationTransfer(5),
                 waitingAck(7) }
   ACCESS     read-only
   STATUS     mandatory
   DESCRIPTION
     "This attribute shows the current state of the SVC data link layer 
      interface."
::= { mscMpanlSigLapfStatusEntry 1 }

mscMpanlSigLastStateChangeReason OBJECT-TYPE
   SYNTAX     INTEGER  {
                 notStarted(1),
                 abmeEntered(3),
                 abmeReset(5),
                 dmReceived(6),
                 dmSent(7),
                 discReceived(8),
                 discSent(9),
                 frmrReceived(10),
                 n200RetranTimeOut(12),
                 other(13) }
   ACCESS     read-only
   STATUS     mandatory
   DESCRIPTION
     "This attribute shows the reason for the most recent state change.
      notStarted - this is the default state after SVC data link has just been 
      created.
      abmeEntered - SVC data link has entered Asynchronous Balanced 
      Mode after SABME or UA has been received.
      abmeReset - the data link has been reset.
      dmReceived - DM response received.
      dmSent - DM sent.
      discReceived - DISC response received.
      discSent - DISC sent.
      frmrReceived - FRMR received.
      n200RetranTimeOut - retransmitLimit has been exceeded.
      other - unspecified state change reasons. The most likely reason for 
      this is the transition from state waitingAck to state 
      informationTransfer."
::= { mscMpanlSigLapfStatusEntry 2 }

mscMpanlSigFrmrReceive OBJECT-TYPE
   SYNTAX     HexString (SIZE (0..8))
   ACCESS     read-only
   STATUS     mandatory
   DESCRIPTION
     "This attribute shows the information field of the FRMR most 
      recently received."
::= { mscMpanlSigLapfStatusEntry 3 }

mscMpanlSigCurrentQueueSize OBJECT-TYPE
   SYNTAX     Counter32 
   ACCESS     read-only
   STATUS     mandatory
   DESCRIPTION
     "This attribute shows the current number of frames in the SVC data 
      link layer transmit queue."
::= { mscMpanlSigLapfStatusEntry 4 }

mscMpanlSigLapfStatsTable OBJECT-TYPE
   SYNTAX     SEQUENCE OF MscMpanlSigLapfStatsEntry
   ACCESS     not-accessible
   STATUS     mandatory
   DESCRIPTION
     "This group contains the statistics for the SVC data link layer."
::= { mscMpanlSig 19 }

mscMpanlSigLapfStatsEntry OBJECT-TYPE
   SYNTAX     MscMpanlSigLapfStatsEntry
   ACCESS     not-accessible
   STATUS     mandatory
   DESCRIPTION
     "An entry in the mscMpanlSigLapfStatsTable."
   INDEX {
      mscMpanlIndex,
      mscMpanlSigIndex }
::= { mscMpanlSigLapfStatsTable 1 }

MscMpanlSigLapfStatsEntry ::= SEQUENCE {
   mscMpanlSigStateChange
      Counter32,
   mscMpanlSigRemoteBusy
      Counter32,
   mscMpanlSigReceiveRejectFrame
      Counter32,
   mscMpanlSigAckTimeout
      Counter32,
   mscMpanlSigIFramesTransmitted
      Counter32,
   mscMpanlSigIFramesTxDiscarded
      Counter32,
   mscMpanlSigIFramesReceived
      Counter32,
   mscMpanlSigIFramesRcvdDiscarded
      Counter32 }

mscMpanlSigStateChange OBJECT-TYPE
   SYNTAX     Counter32 
   ACCESS     read-only
   STATUS     mandatory
   DESCRIPTION
     "This attribute counts the number of times the SVC data link layer 
      interface has changed state. Frequent state changes may indicate a 
      problem with the line quality. While the data link layer is in 
      informationTransfer state, this counter will increment on each 
      expiry of idleProbeTimer as its state goes from 
      informationTransfer to waitingAck and back. When this count 
      reaches maximum, it wraps to zero."
::= { mscMpanlSigLapfStatsEntry 1 }

mscMpanlSigRemoteBusy OBJECT-TYPE
   SYNTAX     Counter32 
   ACCESS     read-only
   STATUS     mandatory
   DESCRIPTION
     "This attribute counts the number of times transmission of an I-frame 
      was unsuccessful due to a perceived remote busy condition 
      (window closed or remote busy). When this count reaches 
      maximum, it wraps to zero."
::= { mscMpanlSigLapfStatsEntry 2 }

mscMpanlSigReceiveRejectFrame OBJECT-TYPE
   SYNTAX     Counter32 
   ACCESS     read-only
   STATUS     mandatory
   DESCRIPTION
     "This attribute counts the number of REJ frames received by the 
      interface. When this count reaches maximum, it wraps to zero."
::= { mscMpanlSigLapfStatsEntry 3 }

mscMpanlSigAckTimeout OBJECT-TYPE
   SYNTAX     Counter32 
   ACCESS     read-only
   STATUS     mandatory
   DESCRIPTION
     "This attribute counts the number of times the ackTimer has expired. 
      Frequent increments of this counter indicate a problem at the link or 
      improper values have been chosen for ackTimer and ackDelayTimer 
      between the local and remote sides. When this count reaches 
      maximum, it wraps to zero."
::= { mscMpanlSigLapfStatsEntry 4 }

mscMpanlSigIFramesTransmitted OBJECT-TYPE
   SYNTAX     Counter32 
   ACCESS     read-only
   STATUS     mandatory
   DESCRIPTION
     "This attribute counts the number of SVC I-frames transmitted to the 
      interface on DLCI 0. An I-frame may be counted more than once if 
      there are retransmissions at the SVC data link layer. When this 
      count reaches maximum, it wraps to zero."
::= { mscMpanlSigLapfStatsEntry 5 }

mscMpanlSigIFramesTxDiscarded OBJECT-TYPE
   SYNTAX     Counter32 
   ACCESS     read-only
   STATUS     mandatory
   DESCRIPTION
     "This attribute counts the number of SVC I-frames that are bound for 
      the link but have been discarded. Discard reasons may be one of the 
      following:
      1.	the frame length is beyond allow limit.
      2.	the SVC data link layer is in disconnected state.
      3. 	the transmit queue has been purged because the queue length 
      has reached the reset threshold.
      4.	the transmit queue or the queue waiting for acknowledgment
      has been 			purged because the link cannot be re-established.
      
      When this count reaches maximum, it wraps to zero."
::= { mscMpanlSigLapfStatsEntry 6 }

mscMpanlSigIFramesReceived OBJECT-TYPE
   SYNTAX     Counter32 
   ACCESS     read-only
   STATUS     mandatory
   DESCRIPTION
     "This attribute counts the number of SVC I-frames received from the 
      interface. When this count reaches maximum, it wraps to zero."
::= { mscMpanlSigLapfStatsEntry 7 }

mscMpanlSigIFramesRcvdDiscarded OBJECT-TYPE
   SYNTAX     Counter32 
   ACCESS     read-only
   STATUS     mandatory
   DESCRIPTION
     "This attribute counts the number of SVC I-frames received but have 
      been discarded. The discard reasons are:
      1.	 incorrect frame size
      2. frame is out of sequence
      3. frame received while the network side of the SVC data link
      layer is not in the informationTransfer or waitingAck state.
      
      When this count reaches maximum, it wraps to zero."
::= { mscMpanlSigLapfStatsEntry 8 }


-- Mpanl/<n> SignalingMpanl
-- 
-- This component contains attributes relating to the MPANL 
-- signaling DLCI at the MPANL interface. This includes operational 
-- Q.922 (LAPF) information for this DLCI.

mscMpanlSigMpanl OBJECT IDENTIFIER ::= { mscMpanl 7 }



mscMpanlSigMpanlRowStatusTable OBJECT-TYPE
   SYNTAX     SEQUENCE OF MscMpanlSigMpanlRowStatusEntry
   ACCESS     not-accessible
   STATUS     mandatory
   DESCRIPTION
     "This entry controls the addition and deletion of 
      mscMpanlSigMpanl components."
::= { mscMpanlSigMpanl 1 }

mscMpanlSigMpanlRowStatusEntry OBJECT-TYPE
   SYNTAX     MscMpanlSigMpanlRowStatusEntry
   ACCESS     not-accessible
   STATUS     mandatory
   DESCRIPTION
     "A single entry in the table represents a single 
      mscMpanlSigMpanl component."
   INDEX {
      mscMpanlIndex,
      mscMpanlSigMpanlIndex }
::= { mscMpanlSigMpanlRowStatusTable 1 }

MscMpanlSigMpanlRowStatusEntry ::= SEQUENCE {
   mscMpanlSigMpanlRowStatus
      RowStatus,
   mscMpanlSigMpanlComponentName
      DisplayString,
   mscMpanlSigMpanlStorageType
      StorageType,
   mscMpanlSigMpanlIndex
      NonReplicated }

mscMpanlSigMpanlRowStatus OBJECT-TYPE
   SYNTAX     RowStatus 
   ACCESS     read-only
   STATUS     mandatory
   DESCRIPTION
     "This variable is used as the basis for SNMP naming of
      mscMpanlSigMpanl components.
      These components cannot be added nor deleted."
::= { mscMpanlSigMpanlRowStatusEntry 1 }

mscMpanlSigMpanlComponentName OBJECT-TYPE
   SYNTAX     DisplayString 
   ACCESS     read-only
   STATUS     mandatory
   DESCRIPTION
     "This variable provides the component's string name for
      use with the ASCII Console Interface"
::= { mscMpanlSigMpanlRowStatusEntry 2 }

mscMpanlSigMpanlStorageType OBJECT-TYPE
   SYNTAX     StorageType 
   ACCESS     read-only
   STATUS     mandatory
   DESCRIPTION
     "This variable represents the storage type value for the
      mscMpanlSigMpanl tables."
::= { mscMpanlSigMpanlRowStatusEntry 4 }

mscMpanlSigMpanlIndex OBJECT-TYPE
   SYNTAX     NonReplicated 
   ACCESS     not-accessible
   STATUS     mandatory
   DESCRIPTION
     "This variable represents the index for the mscMpanlSigMpanl tables."
::= { mscMpanlSigMpanlRowStatusEntry 10 }

mscMpanlSigMpanlStateTable OBJECT-TYPE
   SYNTAX     SEQUENCE OF MscMpanlSigMpanlStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscMpanlSigMpanl 10 }

mscMpanlSigMpanlStateEntry OBJECT-TYPE
   SYNTAX     MscMpanlSigMpanlStateEntry
   ACCESS     not-accessible
   STATUS     mandatory
   DESCRIPTION
     "An entry in the mscMpanlSigMpanlStateTable."
   INDEX {
      mscMpanlIndex,
      mscMpanlSigMpanlIndex }
::= { mscMpanlSigMpanlStateTable 1 }

MscMpanlSigMpanlStateEntry ::= SEQUENCE {
   mscMpanlSigMpanlAdminState
      INTEGER,
   mscMpanlSigMpanlOperationalState
      INTEGER,
   mscMpanlSigMpanlUsageState
      INTEGER }

mscMpanlSigMpanlAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscMpanlSigMpanlStateEntry 1 }

mscMpanlSigMpanlOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscMpanlSigMpanlStateEntry 2 }

mscMpanlSigMpanlUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscMpanlSigMpanlStateEntry 3 }

mscMpanlSigMpanlProfileTable OBJECT-TYPE
   SYNTAX     SEQUENCE OF MscMpanlSigMpanlProfileEntry
   ACCESS     not-accessible
   STATUS     mandatory
   DESCRIPTION
     "This group contains attributes which are populated by the 
      information received from the MPA in the Profile Association 
      command of the MPANL protocol."
::= { mscMpanlSigMpanl 11 }

mscMpanlSigMpanlProfileEntry OBJECT-TYPE
   SYNTAX     MscMpanlSigMpanlProfileEntry
   ACCESS     not-accessible
   STATUS     mandatory
   DESCRIPTION
     "An entry in the mscMpanlSigMpanlProfileTable."
   INDEX {
      mscMpanlIndex,
      mscMpanlSigMpanlIndex }
::= { mscMpanlSigMpanlProfileTable 1 }

MscMpanlSigMpanlProfileEntry ::= SEQUENCE {
   mscMpanlSigMpanlDteCustomerId
      Unsigned32,
   mscMpanlSigMpanlDteNodeId
      Unsigned32,
   mscMpanlSigMpanlDteComponentName
      AsciiString,
   mscMpanlSigMpanlHighestDlci
      Unsigned32 }

mscMpanlSigMpanlDteCustomerId OBJECT-TYPE
   SYNTAX     Unsigned32 (0 | 1..8191)
   ACCESS     read-only
   STATUS     mandatory
   DESCRIPTION
     "This attribute indicates the Customer ID of the MPA connected to 
      this Mpanl interface."
::= { mscMpanlSigMpanlProfileEntry 1 }

mscMpanlSigMpanlDteNodeId OBJECT-TYPE
   SYNTAX     Unsigned32 (1..4095)
   ACCESS     read-only
   STATUS     mandatory
   DESCRIPTION
     "This attribute indicates the nodeId that uniquely identifies the MPA 
      connected to this Mpanl interface."
::= { mscMpanlSigMpanlProfileEntry 2 }

mscMpanlSigMpanlDteComponentName OBJECT-TYPE
   SYNTAX     AsciiString (SIZE (1..255))
   ACCESS     read-only
   STATUS     mandatory
   DESCRIPTION
     "This attribute indicates the component name provided by the MPA 
      connected to this MPANL interface."
::= { mscMpanlSigMpanlProfileEntry 3 }

mscMpanlSigMpanlHighestDlci OBJECT-TYPE
   SYNTAX     Unsigned32 (0 | 17..1007)
   ACCESS     read-only
   STATUS     mandatory
   DESCRIPTION
     "This gives the highest DLCI that the Mpanl interface will assign to 
      an SVC. This value is populated by information provided in the 
      DLCI Range Information Element of the MPANL Profile 
      Association command received from the MPA."
::= { mscMpanlSigMpanlProfileEntry 4 }

mscMpanlSigMpanlStatsTable OBJECT-TYPE
   SYNTAX     SEQUENCE OF MscMpanlSigMpanlStatsEntry
   ACCESS     not-accessible
   STATUS     mandatory
   DESCRIPTION
     "This group contains the statistics related to the Mpanl signaling 
      layer at the interface level."
::= { mscMpanlSigMpanl 12 }

mscMpanlSigMpanlStatsEntry OBJECT-TYPE
   SYNTAX     MscMpanlSigMpanlStatsEntry
   ACCESS     not-accessible
   STATUS     mandatory
   DESCRIPTION
     "An entry in the mscMpanlSigMpanlStatsTable."
   INDEX {
      mscMpanlIndex,
      mscMpanlSigMpanlIndex }
::= { mscMpanlSigMpanlStatsTable 1 }

MscMpanlSigMpanlStatsEntry ::= SEQUENCE {
   mscMpanlSigMpanlProtocolErrors
      Counter32,
   mscMpanlSigMpanlSap0CommandsRx
      Counter32,
   mscMpanlSigMpanlSap0CommandsTx
      Counter32,
   mscMpanlSigMpanlSapXCommandsRx
      Counter32,
   mscMpanlSigMpanlSapXCommandsTx
      Counter32 }

mscMpanlSigMpanlProtocolErrors OBJECT-TYPE
   SYNTAX     Counter32 
   ACCESS     read-only
   STATUS     mandatory
   DESCRIPTION
     "This attribute counts the number of times an Mpanl protocol error 
      has occurred. Any one of the following events constitutes a protocol 
      error:
      1. DNA association before profile association.
      2. Mandatory IE absent in SAPcommands.
      3. Invalid length of IE/sub-info fields in SAP command.
      When this count reaches maximum, it wraps to zero."
::= { mscMpanlSigMpanlStatsEntry 1 }

mscMpanlSigMpanlSap0CommandsRx OBJECT-TYPE
   SYNTAX     Counter32 
   ACCESS     read-only
   STATUS     mandatory
   DESCRIPTION
     "This attribute counts the number of SAP-0 commands received on 
      the MPANL DLCI 16. This counter wraps to zero."
::= { mscMpanlSigMpanlStatsEntry 2 }

mscMpanlSigMpanlSap0CommandsTx OBJECT-TYPE
   SYNTAX     Counter32 
   ACCESS     read-only
   STATUS     mandatory
   DESCRIPTION
     "This attribute counts the number of SAP-0 commands sent on the 
      MPANL DLCI 16. This counter wraps to zero."
::= { mscMpanlSigMpanlStatsEntry 3 }

mscMpanlSigMpanlSapXCommandsRx OBJECT-TYPE
   SYNTAX     Counter32 
   ACCESS     read-only
   STATUS     mandatory
   DESCRIPTION
     "This attribute counts the number of SAP-X commands received on 
      the MPANL DLCI 16. This counter wraps to zero."
::= { mscMpanlSigMpanlStatsEntry 4 }

mscMpanlSigMpanlSapXCommandsTx OBJECT-TYPE
   SYNTAX     Counter32 
   ACCESS     read-only
   STATUS     mandatory
   DESCRIPTION
     "This attribute counts the number of SAP-X commands sent on the 
      MPANL DLCI 16. This counter wraps to zero."
::= { mscMpanlSigMpanlStatsEntry 5 }

mscMpanlSigMpanlLapfStatusTable OBJECT-TYPE
   SYNTAX     SEQUENCE OF MscMpanlSigMpanlLapfStatusEntry
   ACCESS     not-accessible
   STATUS     mandatory
   DESCRIPTION
     "This group contains the Q.922 SVC data link layer status."
::= { mscMpanlSigMpanl 13 }

mscMpanlSigMpanlLapfStatusEntry OBJECT-TYPE
   SYNTAX     MscMpanlSigMpanlLapfStatusEntry
   ACCESS     not-accessible
   STATUS     mandatory
   DESCRIPTION
     "An entry in the mscMpanlSigMpanlLapfStatusTable."
   INDEX {
      mscMpanlIndex,
      mscMpanlSigMpanlIndex }
::= { mscMpanlSigMpanlLapfStatusTable 1 }

MscMpanlSigMpanlLapfStatusEntry ::= SEQUENCE {
   mscMpanlSigMpanlCurrentState
      INTEGER,
   mscMpanlSigMpanlLastStateChangeReason
      INTEGER,
   mscMpanlSigMpanlFrmrReceive
      HexString,
   mscMpanlSigMpanlCurrentQueueSize
      Counter32 }

mscMpanlSigMpanlCurrentState OBJECT-TYPE
   SYNTAX     INTEGER  {
                 disconnected(1),
                 linkSetup(2),
                 disconnectRequest(4),
                 informationTransfer(5),
                 waitingAck(7) }
   ACCESS     read-only
   STATUS     mandatory
   DESCRIPTION
     "This attribute shows the current state of the SVC data link layer 
      interface."
::= { mscMpanlSigMpanlLapfStatusEntry 1 }

mscMpanlSigMpanlLastStateChangeReason OBJECT-TYPE
   SYNTAX     INTEGER  {
                 notStarted(1),
                 abmeEntered(3),
                 abmeReset(5),
                 dmReceived(6),
                 dmSent(7),
                 discReceived(8),
                 discSent(9),
                 frmrReceived(10),
                 n200RetranTimeOut(12),
                 other(13) }
   ACCESS     read-only
   STATUS     mandatory
   DESCRIPTION
     "This attribute shows the reason for the most recent state change.
      notStarted - this is the default state after SVC data link has just been 
      created.
      abmeEntered - SVC data link has entered Asynchronous Balanced 
      Mode after SABME or UA has been received.
      abmeReset - the data link has been reset.
      dmReceived - DM response received.
      dmSent - DM sent.
      discReceived - DISC response received.
      discSent - DISC sent.
      frmrReceived - FRMR received.
      n200RetranTimeOut - retransmitLimit has been exceeded.
      other - unspecified state change reasons. The most likely reason for 
      this is the transition from state waitingAck to state 
      informationTransfer."
::= { mscMpanlSigMpanlLapfStatusEntry 2 }

mscMpanlSigMpanlFrmrReceive OBJECT-TYPE
   SYNTAX     HexString (SIZE (0..8))
   ACCESS     read-only
   STATUS     mandatory
   DESCRIPTION
     "This attribute shows the information field of the FRMR most 
      recently received."
::= { mscMpanlSigMpanlLapfStatusEntry 3 }

mscMpanlSigMpanlCurrentQueueSize OBJECT-TYPE
   SYNTAX     Counter32 
   ACCESS     read-only
   STATUS     mandatory
   DESCRIPTION
     "This attribute shows the current number of frames in the SVC data 
      link layer transmit queue."
::= { mscMpanlSigMpanlLapfStatusEntry 4 }

mscMpanlSigMpanlLapfStatsTable OBJECT-TYPE
   SYNTAX     SEQUENCE OF MscMpanlSigMpanlLapfStatsEntry
   ACCESS     not-accessible
   STATUS     mandatory
   DESCRIPTION
     "This group contains the statistics for the SVC data link layer."
::= { mscMpanlSigMpanl 14 }

mscMpanlSigMpanlLapfStatsEntry OBJECT-TYPE
   SYNTAX     MscMpanlSigMpanlLapfStatsEntry
   ACCESS     not-accessible
   STATUS     mandatory
   DESCRIPTION
     "An entry in the mscMpanlSigMpanlLapfStatsTable."
   INDEX {
      mscMpanlIndex,
      mscMpanlSigMpanlIndex }
::= { mscMpanlSigMpanlLapfStatsTable 1 }

MscMpanlSigMpanlLapfStatsEntry ::= SEQUENCE {
   mscMpanlSigMpanlStateChange
      Counter32,
   mscMpanlSigMpanlRemoteBusy
      Counter32,
   mscMpanlSigMpanlReceiveRejectFrame
      Counter32,
   mscMpanlSigMpanlAckTimeout
      Counter32,
   mscMpanlSigMpanlIFramesTransmitted
      Counter32,
   mscMpanlSigMpanlIFramesTxDiscarded
      Counter32,
   mscMpanlSigMpanlIFramesReceived
      Counter32,
   mscMpanlSigMpanlIFramesRcvdDiscarded
      Counter32 }

mscMpanlSigMpanlStateChange OBJECT-TYPE
   SYNTAX     Counter32 
   ACCESS     read-only
   STATUS     mandatory
   DESCRIPTION
     "This attribute counts the number of times the SVC data link layer 
      interface has changed state. Frequent state changes may indicate a 
      problem with the line quality. While the data link layer is in 
      informationTransfer state, this counter will increment on each 
      expiry of idleProbeTimer as its state goes from 
      informationTransfer to waitingAck and back. When this count 
      reaches maximum, it wraps to zero."
::= { mscMpanlSigMpanlLapfStatsEntry 1 }

mscMpanlSigMpanlRemoteBusy OBJECT-TYPE
   SYNTAX     Counter32 
   ACCESS     read-only
   STATUS     mandatory
   DESCRIPTION
     "This attribute counts the number of times transmission of an I-frame 
      was unsuccessful due to a perceived remote busy condition 
      (window closed or remote busy). When this count reaches 
      maximum, it wraps to zero."
::= { mscMpanlSigMpanlLapfStatsEntry 2 }

mscMpanlSigMpanlReceiveRejectFrame OBJECT-TYPE
   SYNTAX     Counter32 
   ACCESS     read-only
   STATUS     mandatory
   DESCRIPTION
     "This attribute counts the number of REJ frames received by the 
      interface. When this count reaches maximum, it wraps to zero."
::= { mscMpanlSigMpanlLapfStatsEntry 3 }

mscMpanlSigMpanlAckTimeout OBJECT-TYPE
   SYNTAX     Counter32 
   ACCESS     read-only
   STATUS     mandatory
   DESCRIPTION
     "This attribute counts the number of times the ackTimer has expired. 
      Frequent increments of this counter indicate a problem at the link or 
      improper values have been chosen for ackTimer and ackDelayTimer 
      between the local and remote sides. When this count reaches 
      maximum, it wraps to zero."
::= { mscMpanlSigMpanlLapfStatsEntry 4 }

mscMpanlSigMpanlIFramesTransmitted OBJECT-TYPE
   SYNTAX     Counter32 
   ACCESS     read-only
   STATUS     mandatory
   DESCRIPTION
     "This attribute counts the number of SVC I-frames transmitted to the 
      interface on DLCI 0. An I-frame may be counted more than once if 
      there are retransmissions at the SVC data link layer. When this 
      count reaches maximum, it wraps to zero."
::= { mscMpanlSigMpanlLapfStatsEntry 5 }

mscMpanlSigMpanlIFramesTxDiscarded OBJECT-TYPE
   SYNTAX     Counter32 
   ACCESS     read-only
   STATUS     mandatory
   DESCRIPTION
     "This attribute counts the number of SVC I-frames that are bound for 
      the link but have been discarded. Discard reasons may be one of the 
      following:
      1.	the frame length is beyond allow limit.
      2.	the SVC data link layer is in disconnected state.
      3. 	the transmit queue has been purged because the queue length 
      has reached the reset threshold.
      4.	the transmit queue or the queue waiting for acknowledgment
      has been 			purged because the link cannot be re-established.
      
      When this count reaches maximum, it wraps to zero."
::= { mscMpanlSigMpanlLapfStatsEntry 6 }

mscMpanlSigMpanlIFramesReceived OBJECT-TYPE
   SYNTAX     Counter32 
   ACCESS     read-only
   STATUS     mandatory
   DESCRIPTION
     "This attribute counts the number of SVC I-frames received from the 
      interface. When this count reaches maximum, it wraps to zero."
::= { mscMpanlSigMpanlLapfStatsEntry 7 }

mscMpanlSigMpanlIFramesRcvdDiscarded OBJECT-TYPE
   SYNTAX     Counter32 
   ACCESS     read-only
   STATUS     mandatory
   DESCRIPTION
     "This attribute counts the number of SVC I-frames received but have 
      been discarded. The discard reasons are:
      1.	 incorrect frame size
      2. frame is out of sequence
      3. frame received while the network side of the SVC data link
      layer is not in the informationTransfer or waitingAck state.
      
      When this count reaches maximum, it wraps to zero."
::= { mscMpanlSigMpanlLapfStatsEntry 8 }


-- Mpanl/n Lmi
-- This component defines the parameters for implementing the Local 
-- Management Interface protocol.

mscMpanlLmi OBJECT IDENTIFIER ::= { mscMpanl 8 }



mscMpanlLmiRowStatusTable OBJECT-TYPE
   SYNTAX     SEQUENCE OF MscMpanlLmiRowStatusEntry
   ACCESS     not-accessible
   STATUS     mandatory
   DESCRIPTION
     "This entry controls the addition and deletion of 
      mscMpanlLmi components."
::= { mscMpanlLmi 1 }

mscMpanlLmiRowStatusEntry OBJECT-TYPE
   SYNTAX     MscMpanlLmiRowStatusEntry
   ACCESS     not-accessible
   STATUS     mandatory
   DESCRIPTION
     "A single entry in the table represents a single 
      mscMpanlLmi component."
   INDEX {
      mscMpanlIndex,
      mscMpanlLmiIndex }
::= { mscMpanlLmiRowStatusTable 1 }

MscMpanlLmiRowStatusEntry ::= SEQUENCE {
   mscMpanlLmiRowStatus
      RowStatus,
   mscMpanlLmiComponentName
      DisplayString,
   mscMpanlLmiStorageType
      StorageType,
   mscMpanlLmiIndex
      NonReplicated }

mscMpanlLmiRowStatus OBJECT-TYPE
   SYNTAX     RowStatus 
   ACCESS     read-only
   STATUS     mandatory
   DESCRIPTION
     "This variable is used as the basis for SNMP naming of
      mscMpanlLmi components.
      These components cannot be added nor deleted."
::= { mscMpanlLmiRowStatusEntry 1 }

mscMpanlLmiComponentName OBJECT-TYPE
   SYNTAX     DisplayString 
   ACCESS     read-only
   STATUS     mandatory
   DESCRIPTION
     "This variable provides the component's string name for
      use with the ASCII Console Interface"
::= { mscMpanlLmiRowStatusEntry 2 }

mscMpanlLmiStorageType OBJECT-TYPE
   SYNTAX     StorageType 
   ACCESS     read-only
   STATUS     mandatory
   DESCRIPTION
     "This variable represents the storage type value for the
      mscMpanlLmi tables."
::= { mscMpanlLmiRowStatusEntry 4 }

mscMpanlLmiIndex OBJECT-TYPE
   SYNTAX     NonReplicated 
   ACCESS     not-accessible
   STATUS     mandatory
   DESCRIPTION
     "This variable represents the index for the mscMpanlLmi tables."
::= { mscMpanlLmiRowStatusEntry 10 }

mscMpanlLmiParmsTable OBJECT-TYPE
   SYNTAX     SEQUENCE OF MscMpanlLmiParmsEntry
   ACCESS     not-accessible
   STATUS     mandatory
   DESCRIPTION
     "This group contains the provisionable attributes of the Local 
      Management Interface component."
::= { mscMpanlLmi 10 }

mscMpanlLmiParmsEntry OBJECT-TYPE
   SYNTAX     MscMpanlLmiParmsEntry
   ACCESS     not-accessible
   STATUS     mandatory
   DESCRIPTION
     "An entry in the mscMpanlLmiParmsTable."
   INDEX {
      mscMpanlIndex,
      mscMpanlLmiIndex }
::= { mscMpanlLmiParmsTable 1 }

MscMpanlLmiParmsEntry ::= SEQUENCE {
   mscMpanlLmiProcedures
      INTEGER }

mscMpanlLmiProcedures OBJECT-TYPE
   SYNTAX     INTEGER  {
                 none(0),
                 vendorForum(1),
                 ansi(2),
                 ccitt(3) }
   ACCESS     read-only
   STATUS     mandatory
   DESCRIPTION
     "This attribute selects the procedures to be used for the Local 
      Management Interface. For the MPANL service this attribute is 
      always set to none.
      
      none	:	 no Local Management Interface procedures are running on 
      this interface. This accomodates MPANL user equipment that have 
      not implemented any LMI procedures. The remaining attributes of 
      this group will be ignored.
      
      vendorForum	:	Local Management Interface procedures from the 
      Vendor Forum specification are supported on this interface. DLCI 
      1023 is used for the LMI protocol.
      
      ansi: 	Local Management Interface procedures from the ANSI 
      specification are supported. DLCI 0 is used for the LMI protocol.
      
      ccitt: Local Management Interface procedures from the CCITT 
      specification are supported. DLCI 0 is used for the LMI protocol."
   DEFVAL     { none }
::= { mscMpanlLmiParmsEntry 1 }

mscMpanlLmiStateTable OBJECT-TYPE
   SYNTAX     SEQUENCE OF MscMpanlLmiStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscMpanlLmi 12 }

mscMpanlLmiStateEntry OBJECT-TYPE
   SYNTAX     MscMpanlLmiStateEntry
   ACCESS     not-accessible
   STATUS     mandatory
   DESCRIPTION
     "An entry in the mscMpanlLmiStateTable."
   INDEX {
      mscMpanlIndex,
      mscMpanlLmiIndex }
::= { mscMpanlLmiStateTable 1 }

MscMpanlLmiStateEntry ::= SEQUENCE {
   mscMpanlLmiAdminState
      INTEGER,
   mscMpanlLmiOperationalState
      INTEGER,
   mscMpanlLmiUsageState
      INTEGER }

mscMpanlLmiAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscMpanlLmiStateEntry 1 }

mscMpanlLmiOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscMpanlLmiStateEntry 2 }

mscMpanlLmiUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscMpanlLmiStateEntry 3 }


-- Mpanl/n VoiceOverFrameRelay
-- This component, when provisioned, provides VoFr link layer 
-- framing capability to the containing Mpanl instance.

mscMpanlVoFr OBJECT IDENTIFIER ::= { mscMpanl 18 }



mscMpanlVoFrRowStatusTable OBJECT-TYPE
   SYNTAX     SEQUENCE OF MscMpanlVoFrRowStatusEntry
   ACCESS     not-accessible
   STATUS     mandatory
   DESCRIPTION
     "This entry controls the addition and deletion of 
      mscMpanlVoFr components."
::= { mscMpanlVoFr 1 }

mscMpanlVoFrRowStatusEntry OBJECT-TYPE
   SYNTAX     MscMpanlVoFrRowStatusEntry
   ACCESS     not-accessible
   STATUS     mandatory
   DESCRIPTION
     "A single entry in the table represents a single 
      mscMpanlVoFr component."
   INDEX {
      mscMpanlIndex,
      mscMpanlVoFrIndex }
::= { mscMpanlVoFrRowStatusTable 1 }

MscMpanlVoFrRowStatusEntry ::= SEQUENCE {
   mscMpanlVoFrRowStatus
      RowStatus,
   mscMpanlVoFrComponentName
      DisplayString,
   mscMpanlVoFrStorageType
      StorageType,
   mscMpanlVoFrIndex
      NonReplicated }

mscMpanlVoFrRowStatus OBJECT-TYPE
   SYNTAX     RowStatus 
   ACCESS     read-only
   STATUS     mandatory
   DESCRIPTION
     "This variable is used as the basis for SNMP naming of
      mscMpanlVoFr components.
      These components cannot be added nor deleted."
::= { mscMpanlVoFrRowStatusEntry 1 }

mscMpanlVoFrComponentName OBJECT-TYPE
   SYNTAX     DisplayString 
   ACCESS     read-only
   STATUS     mandatory
   DESCRIPTION
     "This variable provides the component's string name for
      use with the ASCII Console Interface"
::= { mscMpanlVoFrRowStatusEntry 2 }

mscMpanlVoFrStorageType OBJECT-TYPE
   SYNTAX     StorageType 
   ACCESS     read-only
   STATUS     mandatory
   DESCRIPTION
     "This variable represents the storage type value for the
      mscMpanlVoFr tables."
::= { mscMpanlVoFrRowStatusEntry 4 }

mscMpanlVoFrIndex OBJECT-TYPE
   SYNTAX     NonReplicated 
   ACCESS     not-accessible
   STATUS     mandatory
   DESCRIPTION
     "This variable represents the index for the mscMpanlVoFr tables."
::= { mscMpanlVoFrRowStatusEntry 10 }

mscMpanlVoFrOperTable OBJECT-TYPE
   SYNTAX     SEQUENCE OF MscMpanlVoFrOperEntry
   ACCESS     not-accessible
   STATUS     mandatory
   DESCRIPTION
     "This group contains operational attributes of the VoFr component."
::= { mscMpanlVoFr 10 }

mscMpanlVoFrOperEntry OBJECT-TYPE
   SYNTAX     MscMpanlVoFrOperEntry
   ACCESS     not-accessible
   STATUS     mandatory
   DESCRIPTION
     "An entry in the mscMpanlVoFrOperTable."
   INDEX {
      mscMpanlIndex,
      mscMpanlVoFrIndex }
::= { mscMpanlVoFrOperTable 1 }

MscMpanlVoFrOperEntry ::= SEQUENCE {
   mscMpanlVoFrMaximumFrameSize
      Counter32,
   mscMpanlVoFrTransmitInformationRate
      Counter32 }

mscMpanlVoFrMaximumFrameSize OBJECT-TYPE
   SYNTAX     Counter32 
   ACCESS     read-only
   STATUS     mandatory
   DESCRIPTION
     "This attribute indicates the maximum size of VoFr frames 
      transmitted to MPA. The size excludes HDLC flags and CRC octets. 
      MPA signals the required value as part of the MPANL initial 
      staging, which is then used to set the value of this attribute. Default 
      value is used before MPANL staging is completed."
::= { mscMpanlVoFrOperEntry 1 }

mscMpanlVoFrTransmitInformationRate OBJECT-TYPE
   SYNTAX     Counter32 
   ACCESS     read-only
   STATUS     mandatory
   DESCRIPTION
     "This attribute indicates the maximum information rate towards 
      MPA. Value may change over time, as signalled by MPA. Default 
      value is used before MPANL staging is completed."
::= { mscMpanlVoFrOperEntry 2 }

mscMpanlVoFrStatsTable OBJECT-TYPE
   SYNTAX     SEQUENCE OF MscMpanlVoFrStatsEntry
   ACCESS     not-accessible
   STATUS     mandatory
   DESCRIPTION
     "This group contains statistics attributes of the VoFr component."
::= { mscMpanlVoFr 11 }

mscMpanlVoFrStatsEntry OBJECT-TYPE
   SYNTAX     MscMpanlVoFrStatsEntry
   ACCESS     not-accessible
   STATUS     mandatory
   DESCRIPTION
     "An entry in the mscMpanlVoFrStatsTable."
   INDEX {
      mscMpanlIndex,
      mscMpanlVoFrIndex }
::= { mscMpanlVoFrStatsTable 1 }

MscMpanlVoFrStatsEntry ::= SEQUENCE {
   mscMpanlVoFrFragmentedHighestPriorityFrames
      Counter32,
   mscMpanlVoFrLostFragmentsFromIf
      Counter32,
   mscMpanlVoFrProtocolViolationsFromIf
      Counter32 }

mscMpanlVoFrFragmentedHighestPriorityFrames OBJECT-TYPE
   SYNTAX     Counter32 
   ACCESS     read-only
   STATUS     mandatory
   DESCRIPTION
     "This attribute counts egress frames with the highest priority, which 
      had to be fragmented because they were larger than 
      maximumFrameSize. This could happen when a data call is setup to 
      use the highest emission priority, or MPA is provisioned with too 
      low maximum frame size. When the maximum is reached the count 
      wraps to zero."
::= { mscMpanlVoFrStatsEntry 1 }

mscMpanlVoFrLostFragmentsFromIf OBJECT-TYPE
   SYNTAX     Counter32 
   ACCESS     read-only
   STATUS     mandatory
   DESCRIPTION
     "This attribute counts lost VoFr fragments from the interface. 
      Presence of lost fragments indicates a link problem. Note that lost 
      whole frames cannot be detected. When the maximum is reached 
      the count wraps to zero."
::= { mscMpanlVoFrStatsEntry 5 }

mscMpanlVoFrProtocolViolationsFromIf OBJECT-TYPE
   SYNTAX     Counter32 
   ACCESS     read-only
   STATUS     mandatory
   DESCRIPTION
     "This attribute counts VoFr protocol violations detected in the data 
      from the interface. When the maximum is reached the count wraps 
      to zero."
::= { mscMpanlVoFrStatsEntry 6 }


-- Mpanl/n FrMuxSetup
-- This component contains operational attributes for egress traffic 
-- shaping as well as the component name of the FrMux Dlci to which 
-- this Mpanl/n is associated.

mscMpanlFrMuxSetup OBJECT IDENTIFIER ::= { mscMpanl 19 }



mscMpanlFrMuxSetupRowStatusTable OBJECT-TYPE
   SYNTAX     SEQUENCE OF MscMpanlFrMuxSetupRowStatusEntry
   ACCESS     not-accessible
   STATUS     mandatory
   DESCRIPTION
     "This entry controls the addition and deletion of 
      mscMpanlFrMuxSetup components."
::= { mscMpanlFrMuxSetup 1 }

mscMpanlFrMuxSetupRowStatusEntry OBJECT-TYPE
   SYNTAX     MscMpanlFrMuxSetupRowStatusEntry
   ACCESS     not-accessible
   STATUS     mandatory
   DESCRIPTION
     "A single entry in the table represents a single 
      mscMpanlFrMuxSetup component."
   INDEX {
      mscMpanlIndex,
      mscMpanlFrMuxSetupIndex }
::= { mscMpanlFrMuxSetupRowStatusTable 1 }

MscMpanlFrMuxSetupRowStatusEntry ::= SEQUENCE {
   mscMpanlFrMuxSetupRowStatus
      RowStatus,
   mscMpanlFrMuxSetupComponentName
      DisplayString,
   mscMpanlFrMuxSetupStorageType
      StorageType,
   mscMpanlFrMuxSetupIndex
      NonReplicated }

mscMpanlFrMuxSetupRowStatus OBJECT-TYPE
   SYNTAX     RowStatus 
   ACCESS     read-write
   STATUS     mandatory
   DESCRIPTION
     "This variable is used as the basis for SNMP naming of
      mscMpanlFrMuxSetup components.
      These components can be added and deleted."
::= { mscMpanlFrMuxSetupRowStatusEntry 1 }

mscMpanlFrMuxSetupComponentName OBJECT-TYPE
   SYNTAX     DisplayString 
   ACCESS     read-only
   STATUS     mandatory
   DESCRIPTION
     "This variable provides the component's string name for
      use with the ASCII Console Interface"
::= { mscMpanlFrMuxSetupRowStatusEntry 2 }

mscMpanlFrMuxSetupStorageType OBJECT-TYPE
   SYNTAX     StorageType 
   ACCESS     read-only
   STATUS     mandatory
   DESCRIPTION
     "This variable represents the storage type value for the
      mscMpanlFrMuxSetup tables."
::= { mscMpanlFrMuxSetupRowStatusEntry 4 }

mscMpanlFrMuxSetupIndex OBJECT-TYPE
   SYNTAX     NonReplicated 
   ACCESS     not-accessible
   STATUS     mandatory
   DESCRIPTION
     "This variable represents the index for the mscMpanlFrMuxSetup tables."
::= { mscMpanlFrMuxSetupRowStatusEntry 10 }

mscMpanlFrMuxSetupOpTable OBJECT-TYPE
   SYNTAX     SEQUENCE OF MscMpanlFrMuxSetupOpEntry
   ACCESS     not-accessible
   STATUS     mandatory
   DESCRIPTION
     "This group contains the following operational parameters: 
      committedInformationRate of the PVC connection used for 
      tunnelling the MPANL traffic, and the component name of the Dlci 
      which carries the traffic for this MPANL."
::= { mscMpanlFrMuxSetup 11 }

mscMpanlFrMuxSetupOpEntry OBJECT-TYPE
   SYNTAX     MscMpanlFrMuxSetupOpEntry
   ACCESS     not-accessible
   STATUS     mandatory
   DESCRIPTION
     "An entry in the mscMpanlFrMuxSetupOpTable."
   INDEX {
      mscMpanlIndex,
      mscMpanlFrMuxSetupIndex }
::= { mscMpanlFrMuxSetupOpTable 1 }

MscMpanlFrMuxSetupOpEntry ::= SEQUENCE {
   mscMpanlFrMuxSetupCommittedInformationRate
      Unsigned32,
   mscMpanlFrMuxSetupDlciCompName
      RowPointer }

mscMpanlFrMuxSetupCommittedInformationRate OBJECT-TYPE
   SYNTAX     Unsigned32 (16000..4294967295)
   ACCESS     read-only
   STATUS     mandatory
   DESCRIPTION
     "This attribute specifies, in bit/s, the committed information rate 
      (CIR) to which the traffic transmitted towards the interface is 
      shaped."
   DEFVAL     { 16000 }
::= { mscMpanlFrMuxSetupOpEntry 1 }

mscMpanlFrMuxSetupDlciCompName OBJECT-TYPE
   SYNTAX     RowPointer 
   ACCESS     read-only
   STATUS     mandatory
   DESCRIPTION
     "This attribute specifies the component name of the Dlci with which 
      the application using this FrMuxSetup component is associated. The 
      name is a string FrMux/n Dlci/m. For a PVC this is the same 
      component name as provisioned under the subcomponent 
      FrMuxPvcSetup."
::= { mscMpanlFrMuxSetupOpEntry 2 }


-- Mpanl/n FrMuxSetup PvcSetup
-- This component contains provisionable attributes for setting up a 
-- Dlci associated with the application using this component. The Dlci 
-- is of a PVC type. 

mscMpanlFrMuxSetupPvcSetup OBJECT IDENTIFIER ::= { mscMpanlFrMuxSetup 2 }



mscMpanlFrMuxSetupPvcSetupRowStatusTable OBJECT-TYPE
   SYNTAX     SEQUENCE OF MscMpanlFrMuxSetupPvcSetupRowStatusEntry
   ACCESS     not-accessible
   STATUS     mandatory
   DESCRIPTION
     "This entry controls the addition and deletion of 
      mscMpanlFrMuxSetupPvcSetup components."
::= { mscMpanlFrMuxSetupPvcSetup 1 }

mscMpanlFrMuxSetupPvcSetupRowStatusEntry OBJECT-TYPE
   SYNTAX     MscMpanlFrMuxSetupPvcSetupRowStatusEntry
   ACCESS     not-accessible
   STATUS     mandatory
   DESCRIPTION
     "A single entry in the table represents a single 
      mscMpanlFrMuxSetupPvcSetup component."
   INDEX {
      mscMpanlIndex,
      mscMpanlFrMuxSetupIndex,
      mscMpanlFrMuxSetupPvcSetupIndex }
::= { mscMpanlFrMuxSetupPvcSetupRowStatusTable 1 }

MscMpanlFrMuxSetupPvcSetupRowStatusEntry ::= SEQUENCE {
   mscMpanlFrMuxSetupPvcSetupRowStatus
      RowStatus,
   mscMpanlFrMuxSetupPvcSetupComponentName
      DisplayString,
   mscMpanlFrMuxSetupPvcSetupStorageType
      StorageType,
   mscMpanlFrMuxSetupPvcSetupIndex
      NonReplicated }

mscMpanlFrMuxSetupPvcSetupRowStatus OBJECT-TYPE
   SYNTAX     RowStatus 
   ACCESS     read-only
   STATUS     mandatory
   DESCRIPTION
     "This variable is used as the basis for SNMP naming of
      mscMpanlFrMuxSetupPvcSetup components.
      These components cannot be added nor deleted."
::= { mscMpanlFrMuxSetupPvcSetupRowStatusEntry 1 }

mscMpanlFrMuxSetupPvcSetupComponentName OBJECT-TYPE
   SYNTAX     DisplayString 
   ACCESS     read-only
   STATUS     mandatory
   DESCRIPTION
     "This variable provides the component's string name for
      use with the ASCII Console Interface"
::= { mscMpanlFrMuxSetupPvcSetupRowStatusEntry 2 }

mscMpanlFrMuxSetupPvcSetupStorageType OBJECT-TYPE
   SYNTAX     StorageType 
   ACCESS     read-only
   STATUS     mandatory
   DESCRIPTION
     "This variable represents the storage type value for the
      mscMpanlFrMuxSetupPvcSetup tables."
::= { mscMpanlFrMuxSetupPvcSetupRowStatusEntry 4 }

mscMpanlFrMuxSetupPvcSetupIndex OBJECT-TYPE
   SYNTAX     NonReplicated 
   ACCESS     not-accessible
   STATUS     mandatory
   DESCRIPTION
     "This variable represents the index for the mscMpanlFrMuxSetupPvcSetup tables."
::= { mscMpanlFrMuxSetupPvcSetupRowStatusEntry 10 }

mscMpanlFrMuxSetupPvcSetupProvTable OBJECT-TYPE
   SYNTAX     SEQUENCE OF MscMpanlFrMuxSetupPvcSetupProvEntry
   ACCESS     not-accessible
   STATUS     mandatory
   DESCRIPTION
     "This group contains provisionable attributes for setting up a Dlci 
      associated with the application using the FrMuxSetup component. 
      The Dlci is of the PVC type."
::= { mscMpanlFrMuxSetupPvcSetup 10 }

mscMpanlFrMuxSetupPvcSetupProvEntry OBJECT-TYPE
   SYNTAX     MscMpanlFrMuxSetupPvcSetupProvEntry
   ACCESS     not-accessible
   STATUS     mandatory
   DESCRIPTION
     "An entry in the mscMpanlFrMuxSetupPvcSetupProvTable."
   INDEX {
      mscMpanlIndex,
      mscMpanlFrMuxSetupIndex,
      mscMpanlFrMuxSetupPvcSetupIndex }
::= { mscMpanlFrMuxSetupPvcSetupProvTable 1 }

MscMpanlFrMuxSetupPvcSetupProvEntry ::= SEQUENCE {
   mscMpanlFrMuxSetupPvcSetupDlciName
      Link }

mscMpanlFrMuxSetupPvcSetupDlciName OBJECT-TYPE
   SYNTAX     Link 
   ACCESS     read-write
   STATUS     mandatory
   DESCRIPTION
     "This attribute is the link to the Dlci which is associated with the 
      application using the FrMuxSetup component."
::= { mscMpanlFrMuxSetupPvcSetupProvEntry 1 }


-- Mpanl/n Isdn
-- This component defines the parameters associated with the ISDN B-
-- Channel interface. Adding this component makes the Mpanl
-- behave as an ISDN access to the MPA.

mscMpanlIsdn OBJECT IDENTIFIER ::= { mscMpanl 22 }



mscMpanlIsdnRowStatusTable OBJECT-TYPE
   SYNTAX     SEQUENCE OF MscMpanlIsdnRowStatusEntry
   ACCESS     not-accessible
   STATUS     mandatory
   DESCRIPTION
     "This entry controls the addition and deletion of 
      mscMpanlIsdn components."
::= { mscMpanlIsdn 1 }

mscMpanlIsdnRowStatusEntry OBJECT-TYPE
   SYNTAX     MscMpanlIsdnRowStatusEntry
   ACCESS     not-accessible
   STATUS     mandatory
   DESCRIPTION
     "A single entry in the table represents a single 
      mscMpanlIsdn component."
   INDEX {
      mscMpanlIndex,
      mscMpanlIsdnIndex }
::= { mscMpanlIsdnRowStatusTable 1 }

MscMpanlIsdnRowStatusEntry ::= SEQUENCE {
   mscMpanlIsdnRowStatus
      RowStatus,
   mscMpanlIsdnComponentName
      DisplayString,
   mscMpanlIsdnStorageType
      StorageType,
   mscMpanlIsdnIndex
      NonReplicated }

mscMpanlIsdnRowStatus OBJECT-TYPE
   SYNTAX     RowStatus 
   ACCESS     read-write
   STATUS     mandatory
   DESCRIPTION
     "This variable is used as the basis for SNMP naming of
      mscMpanlIsdn components.
      These components can be added and deleted."
::= { mscMpanlIsdnRowStatusEntry 1 }

mscMpanlIsdnComponentName OBJECT-TYPE
   SYNTAX     DisplayString 
   ACCESS     read-only
   STATUS     mandatory
   DESCRIPTION
     "This variable provides the component's string name for
      use with the ASCII Console Interface"
::= { mscMpanlIsdnRowStatusEntry 2 }

mscMpanlIsdnStorageType OBJECT-TYPE
   SYNTAX     StorageType 
   ACCESS     read-only
   STATUS     mandatory
   DESCRIPTION
     "This variable represents the storage type value for the
      mscMpanlIsdn tables."
::= { mscMpanlIsdnRowStatusEntry 4 }

mscMpanlIsdnIndex OBJECT-TYPE
   SYNTAX     NonReplicated 
   ACCESS     not-accessible
   STATUS     mandatory
   DESCRIPTION
     "This variable represents the index for the mscMpanlIsdn tables."
::= { mscMpanlIsdnRowStatusEntry 10 }

mscMpanlIsdnProvTable OBJECT-TYPE
   SYNTAX     SEQUENCE OF MscMpanlIsdnProvEntry
   ACCESS     not-accessible
   STATUS     mandatory
   DESCRIPTION
     "This group contains the provisionable attributes of the Isdn 
      component."
::= { mscMpanlIsdn 11 }

mscMpanlIsdnProvEntry OBJECT-TYPE
   SYNTAX     MscMpanlIsdnProvEntry
   ACCESS     not-accessible
   STATUS     mandatory
   DESCRIPTION
     "An entry in the mscMpanlIsdnProvTable."
   INDEX {
      mscMpanlIndex,
      mscMpanlIsdnIndex }
::= { mscMpanlIsdnProvTable 1 }

MscMpanlIsdnProvEntry ::= SEQUENCE {
   mscMpanlIsdnT320
      Unsigned32,
   mscMpanlIsdnAddressSignalling
      INTEGER }

mscMpanlIsdnT320 OBJECT-TYPE
   SYNTAX     Unsigned32 (0..255)
   ACCESS     read-write
   STATUS     mandatory
   DESCRIPTION
     "This attribute specifies the waiting time for a silent 
      B-Channel (no active VCs associated with the Mpanl) to be 
      disconnected and made available. Default is 60 seconds. 0 means 
      t320 will never timeout."
   DEFVAL     { 60 }
::= { mscMpanlIsdnProvEntry 1 }

mscMpanlIsdnAddressSignalling OBJECT-TYPE
   SYNTAX     INTEGER  {
                 isdnDna(0),
                 normalBehavior(1) }
   ACCESS     read-write
   STATUS     mandatory
   DESCRIPTION
     "This attribute defines whether the ISDN Calling Party Number is to 
      be signalled to the remote DTE during an SVC call establishment. 
      Otherwise, no changes to the current behavior of SVC call 
      establishement (i.e., Passport Dna is used in the calling party 
      number information element)."
   DEFVAL     { normalBehavior }
::= { mscMpanlIsdnProvEntry 2 }

mscMpanlIsdnOperTable OBJECT-TYPE
   SYNTAX     SEQUENCE OF MscMpanlIsdnOperEntry
   ACCESS     not-accessible
   STATUS     mandatory
   DESCRIPTION
     "This group contains the operational attributes of the Isdn 
      component."
::= { mscMpanlIsdn 12 }

mscMpanlIsdnOperEntry OBJECT-TYPE
   SYNTAX     MscMpanlIsdnOperEntry
   ACCESS     not-accessible
   STATUS     mandatory
   DESCRIPTION
     "An entry in the mscMpanlIsdnOperTable."
   INDEX {
      mscMpanlIndex,
      mscMpanlIsdnIndex }
::= { mscMpanlIsdnOperTable 1 }

MscMpanlIsdnOperEntry ::= SEQUENCE {
   mscMpanlIsdnDataSigChan
      INTEGER,
   mscMpanlIsdnBChannelState
      INTEGER,
   mscMpanlIsdnLastUsedCgpn
      DigitString,
   mscMpanlIsdnBChanIntState
      INTEGER,
   mscMpanlIsdnActiveVirtualCircuitsCount
      Counter32 }

mscMpanlIsdnDataSigChan OBJECT-TYPE
   SYNTAX     INTEGER (1..255)
   ACCESS     read-only
   STATUS     mandatory
   DESCRIPTION
     "This attribute indicates the instance number of the dataSigChan 
      component controlling the allocation of this Mpanl Isdn component."
::= { mscMpanlIsdnOperEntry 1 }

mscMpanlIsdnBChannelState OBJECT-TYPE
   SYNTAX     INTEGER  {
                 idle(0),
                 busy(1),
                 disabled(2) }
   ACCESS     read-only
   STATUS     mandatory
   DESCRIPTION
     "This attribute indicates the state of the B-Channel. If the value is 
      idle it means that no VCs are connected and this B-Channel is 
      available. If the value is busy it means this B-Channel has been 
      allocated and is not available. If the value is disabled it means the 
      application interface or the port is locked or disabled."
::= { mscMpanlIsdnOperEntry 2 }

mscMpanlIsdnLastUsedCgpn OBJECT-TYPE
   SYNTAX     DigitString (SIZE (0..15))
   ACCESS     read-only
   STATUS     mandatory
   DESCRIPTION
     "This attribute indicates the calling party number currently using
      the B-Channel. When the B-Channel is free, the null string is 
      displayed."
::= { mscMpanlIsdnOperEntry 3 }

mscMpanlIsdnBChanIntState OBJECT-TYPE
   SYNTAX     INTEGER  {
                 isdnInit(0),
                 waitAccEnable(1),
                 waitLnsResponse(2),
                 waitFramerData(3),
                 enabling(4),
                 waitAccRegAck(5),
                 up(6),
                 down(7),
                 releasing(8) }
   ACCESS     read-only
   STATUS     mandatory
   DESCRIPTION
     "Debug information"
::= { mscMpanlIsdnOperEntry 4 }

mscMpanlIsdnActiveVirtualCircuitsCount OBJECT-TYPE
   SYNTAX     Counter32 
   ACCESS     read-only
   STATUS     mandatory
   DESCRIPTION
     "Current number of virtual circuits (switched and permanent) in data 
      transfer."
::= { mscMpanlIsdnOperEntry 5 }




-- 
-- Version and Compliance statements
-- 



-- Object-Group Statement:
-- A list of all current accessible leaf objects.

-- OBJECTS { mscMpanlSigMpanlSapXCommandsRx,
--           mscMpanlFramerInterfaceName,
--           mscMpanlDlciDiscExcessFromIfBytes,
--           mscMpanlDlciVcSegmentSize,
--           mscMpanlDlciLoopbackState,
--           mscMpanlUnknownDlciFramesFromIf,
--           mscMpanlSigLastCauseInStatusMsgReceived,
--           mscMpanlFramerOperationalState,
--           mscMpanlSigMpanlLastStateChangeReason,
--           mscMpanlLmiAdminState,
--           mscMpanlDnaDefaultTransferPriority,
--           mscMpanlFramerFrmModeErrors,
--           mscMpanlDlciVcComponentName,
--           mscMpanlDlciLCoRequiredCustomerParameter,
--           mscMpanlSigMpanlStorageType,
--           mscMpanlSigMpanlAckTimeout,
--           mscMpanlVoFrComponentName,
--           mscMpanlIsdnComponentName,
--           mscMpanlOctetToIf,
--           mscMpanlDlciDiscDeCongestedToIf,
--           mscMpanlFramerLrcErrors,
--           mscMpanlDlciVcCallingNpi,
--           mscMpanlIsdnDataSigChan,
--           mscMpanlDnaStorageType,
--           mscMpanlDlciStartTime,
--           mscMpanlLmiRowStatus,
--           mscMpanlDlciJvcCurrentState,
--           mscMpanlFramerAborts,
--           mscMpanlDlciABitStatusToIf,
--           mscMpanlDlciEmissionPriorityToIf,
--           mscMpanlDlciLbStorageType,
--           mscMpanlSigMpanlSap0CommandsTx,
--           mscMpanlVoFrTransmitInformationRate,
--           mscMpanlSigMpanlSapXCommandsTx,
--           mscMpanlVoFrProtocolViolationsFromIf,
--           mscMpanlDlciVcMaxSubnetPktSize,
--           mscMpanlDlciAccounting,
--           mscMpanlSigReceiveRejectFrame,
--           mscMpanlDlciUnknownStatus,
--           mscMpanlLmiUsageState,
--           mscMpanlDlciTotalEgressSegFrm,
--           mscMpanlDnaEgressAccounting,
--           mscMpanlAlarmStatus,
--           mscMpanlDlciVcState,
--           mscMpanlIsdnActiveVirtualCircuitsCount,
--           mscMpanlDlciVcEmissionPriorityFromNetwork,
--           mscMpanlDlciDiscFrameAbit,
--           mscMpanlLmiStorageType,
--           mscMpanlDlciBciToSubnet,
--           mscMpanlDlciDeBytesToIf,
--           mscMpanlDlciLbLocalDeFrm,
--           mscMpanlDlciDiscCongestedToIf,
--           mscMpanlSigRemoteBusy,
--           mscMpanlDlciDeFrmToIf,
--           mscMpanlDlciLCoOptimization,
--           mscMpanlDlciLbRemoteDeBytes,
--           mscMpanlDlciVcEmissionPriorityToNetwork,
--           mscMpanlDlciLCoElapsedTimeTillNow,
--           mscMpanlDlciVcPeakOoSeqByteCount,
--           mscMpanlDlciABitReasonToIf,
--           mscMpanlDlciLbRemoteDeFrm,
--           mscMpanlDlciDiscDeCongestedFromIfBytes,
--           mscMpanlDlciDiscByteAbit,
--           mscMpanlSigMpanlIFramesTxDiscarded,
--           mscMpanlDlciTotalIngressBytes,
--           mscMpanlSigInCalls,
--           mscMpanlDlciProceduralStatus,
--           mscMpanlFrMuxSetupRowStatus,
--           mscMpanlSigNetworkType,
--           mscMpanlFramerAdminState,
--           mscMpanlSigMpanlRemoteBusy,
--           mscMpanlFramerFrameCrcType,
--           mscMpanlDlciLCoRetryCount,
--           mscMpanlDlciLCoEmissionPriority,
--           mscMpanlSigMpanlReceiveRejectFrame,
--           mscMpanlDlciOperationalState,
--           mscMpanlDlciVcCalledNpi,
--           mscMpanlDlciLCoRequiredSecurity,
--           mscMpanlSigMpanlDteCustomerId,
--           mscMpanlDlciTotalEgressBytes,
--           mscMpanlDlciBytesToIf,
--           mscMpanlSigLastDlciWithMsgBlockCongestion,
--           mscMpanlDlciVcNotDataXferToSubnet,
--           mscMpanlDlciVcPeakOoSeqPktCount,
--           mscMpanlDlciFrmToIf,
--           mscMpanlDlciVcCallReferenceNumberDecimal,
--           mscMpanlFrMuxSetupPvcSetupRowStatus,
--           mscMpanlDlciLCoCallingDna,
--           mscMpanlVoFrMaximumFrameSize,
--           mscMpanlDlciVcRowStatus,
--           mscMpanlDlciLCoDiscardPriority,
--           mscMpanlSigDisconnectTimer,
--           mscMpanlDlciDiscCongestedFromIfBytes,
--           mscMpanlSigStateChange,
--           mscMpanlCustomerIdentifier,
--           mscMpanlComponentName,
--           mscMpanlDlciVcRcosToNetwork,
--           mscMpanlDlciEirIngressBytes,
--           mscMpanlSigMpanlHighestDlci,
--           mscMpanlDlciJvcRowStatus,
--           mscMpanlDlciLCoCallReferenceNumber,
--           mscMpanlSigMpanlDteComponentName,
--           mscMpanlSigMpanlCurrentState,
--           mscMpanlDlciTransferPriFromNwk,
--           mscMpanlPrefixDnaComponentName,
--           mscMpanlIsdnAddressSignalling,
--           mscMpanlSigMpanlDteNodeId,
--           mscMpanlDlciLCoPktsToNetwork,
--           mscMpanlDlciJvcComponentName,
--           mscMpanlDlciVcCombErrorsFromSubnet,
--           mscMpanlSigMpanlStateChange,
--           mscMpanlSigUsageState,
--           mscMpanlDlciEirEgressBytes,
--           mscMpanlInvalidHeaderFramesFromIf,
--           mscMpanlDlciLbLocalFecnFrm,
--           mscMpanlDlciFecnFrmFromIf,
--           mscMpanlDlciVcSegmentsRx,
--           mscMpanlSigMpanlProtocolErrors,
--           mscMpanlFramerFrmFromIf64,
--           mscMpanlFrMuxSetupStorageType,
--           mscMpanlVoFrLostFragmentsFromIf,
--           mscMpanlDlciVcCalledLcn,
--           mscMpanlIsdnT320,
--           mscMpanlDlciLCoRequiredTxBandwidth,
--           mscMpanlSigLastTimeMsgBlockCongested,
--           mscMpanlDlciJvcCalledAddress,
--           mscMpanlDlciLCoCostMetric,
--           mscMpanlDlciStandbyStatus,
--           mscMpanlSigIdleProbeTimer,
--           mscMpanlDlciLCoBytesFromNetwork,
--           mscMpanlSigMpanlIFramesReceived,
--           mscMpanlSigIFramesTxDiscarded,
--           mscMpanlDlciStorageType,
--           mscMpanlDlciVcDmepValue,
--           mscMpanlIfIndex,
--           mscMpanlFramerNormPrioLinkUtilToIf,
--           mscMpanlDlciJvcCallingAddress,
--           mscMpanlSigOutCalls,
--           mscMpanlFramerStorageType,
--           mscMpanlVoFrStorageType,
--           mscMpanlDlciErrorShortFrmFromIf,
--           mscMpanlFrmFromIf,
--           mscMpanlDlciCommittedBurstSize,
--           mscMpanlFramerCrcErrors,
--           mscMpanlDlciVcStartTime,
--           mscMpanlDlciLCoReasonForNoRoute,
--           mscMpanlDlciAdminState,
--           mscMpanlSigMpanlUsageState,
--           mscMpanlDlciVcDiagnosticCode,
--           mscMpanlDlciLCoRequiredRxBandwidth,
--           mscMpanlSigIFramesRcvdDiscarded,
--           mscMpanlSigInCallsRefused,
--           mscMpanlDnaComponentName,
--           mscMpanlDlciVcCallingLcn,
--           mscMpanlDnaAccountClass,
--           mscMpanlDlciVcSendSequenceNumber,
--           mscMpanlDlciLbLocalTotalBytes,
--           mscMpanlControlStatus,
--           mscMpanlFramerLargeFrmErrors,
--           mscMpanlLmiOperationalState,
--           mscMpanlFrmToIfByQueueValue,
--           mscMpanlDlciLbLocalTotalFrm,
--           mscMpanlDlciDiscardedSegFrm,
--           mscMpanlSigMpanlOperationalState,
--           mscMpanlDlciLCoDelayMetric,
--           mscMpanlDlciLbLocalBecnFrm,
--           mscMpanlDlciVcType,
--           mscMpanlRowStatus,
--           mscMpanlDlciJvcCalledLcn,
--           mscMpanlDlciVcAccountingEnabled,
--           mscMpanlSigStorageType,
--           mscMpanlDlciVcFrmLossTimeouts,
--           mscMpanlDlciAvailabilityStatus,
--           mscMpanlSigMpanlIFramesRcvdDiscarded,
--           mscMpanlFramerNonOctetErrors,
--           mscMpanlDlciLCoComponentName,
--           mscMpanlDlciVcPreviousState,
--           mscMpanlPrefixDnaRowStatus,
--           mscMpanlDlciVcOoSeqPktCntExceeded,
--           mscMpanlDlciLbComponentName,
--           mscMpanlSigCallSetupTimer,
--           mscMpanlUsageState,
--           mscMpanlDlciLCoCallingNpi,
--           mscMpanlDlciLCoHoldingPriority,
--           mscMpanlDlciLbRemoteTotalBytes,
--           mscMpanlIsdnBChanIntState,
--           mscMpanlSigIFramesTransmitted,
--           mscMpanlDlciDiscExcessFromIf,
--           mscMpanlDlciExcessBurstSize,
--           mscMpanlSigOutCallsFailed,
--           mscMpanlOperationalState,
--           mscMpanlDlciLCoPathValue,
--           mscMpanlSigLastQ933StateReceivedStatus,
--           mscMpanlSigRetransmitLimit,
--           mscMpanlDlciDiscDeCongestedToIfBytes,
--           mscMpanlDnaAccountCollection,
--           mscMpanlSigMpanlIFramesTransmitted,
--           mscMpanlDlciJvcPacketsDiscarded,
--           mscMpanlDlciLCoState,
--           mscMpanlSigMpanlAdminState,
--           mscMpanlDnaServiceExchange,
--           mscMpanlDlciJvcPacketsFromSubnet,
--           mscMpanlFrMuxSetupPvcSetupStorageType,
--           mscMpanlFramerRowStatus,
--           mscMpanlDlciAlarmStatus,
--           mscMpanlDlciVcPriority,
--           mscMpanlDlciVcPathReliability,
--           mscMpanlDlciVcCannotForwardToSubnet,
--           mscMpanlDlciMaximumFrameSize,
--           mscMpanlSigMpanlFrmrReceive,
--           mscMpanlPrefixDnaStorageType,
--           mscMpanlAvailabilityStatus,
--           mscMpanlFramerOctetFromIf64,
--           mscMpanlDlciLbRemoteFecnFrm,
--           mscMpanlDlciFciFromSubnet,
--           mscMpanlSigAckDelayTimer,
--           mscMpanlSigCurrentState,
--           mscMpanlRoundTripDelay,
--           mscMpanlDlciElapsedDifference,
--           mscMpanlDnaRowStatus,
--           mscMpanlFramerDataInversion,
--           mscMpanlSigOperationalState,
--           mscMpanlSigCallProceedingTimer,
--           mscMpanlSigMpanlRowStatus,
--           mscMpanlDlciDeBytesFromIf,
--           mscMpanlFramerFlagsBetweenFrames,
--           mscMpanlDlciLCoRequiredTrafficType,
--           mscMpanlDlciLbRowStatus,
--           mscMpanlDlciLCoCalledNpi,
--           mscMpanlDlciTransferPriToNwk,
--           mscMpanlSigMpanlSap0CommandsRx,
--           mscMpanlSigFrmrReceive,
--           mscMpanlOctetFromIf,
--           mscMpanlDlciDiscDeCongestedFromIf,
--           mscMpanlDlciVcStorageType,
--           mscMpanlDlciLCoRowStatus,
--           mscMpanlIsdnLastUsedCgpn,
--           mscMpanlDlciEirEgressSegFrm,
--           mscMpanlIsdnStorageType,
--           mscMpanlDlciFecnFrmToIf,
--           mscMpanlSigDefaultAccounting,
--           mscMpanlDlciLCoPathUpDateTime,
--           mscMpanlFramerFrmToIf64,
--           mscMpanlDlciABitStatusFromIf,
--           mscMpanlDlciJvcCallingLcn,
--           mscMpanlDlciVcAccountingEnd,
--           mscMpanlSigLastStateInStatusMsgReceived,
--           mscMpanlDlciDiscardedBytes,
--           mscMpanlDlciVcElapsedTimeTillNow,
--           mscMpanlDlciComponentName,
--           mscMpanlProceduralStatus,
--           mscMpanlDlciBecnFrmSetByService,
--           mscMpanlIsdnRowStatus,
--           mscMpanlFrMuxSetupPvcSetupDlciName,
--           mscMpanlOctetToIfByQueueValue,
--           mscMpanlDlciJvcPreviousState,
--           mscMpanlDlciABitReasonFromIf,
--           mscMpanlFrMuxSetupCommittedInformationRate,
--           mscMpanlFramerComponentName,
--           mscMpanlDlciLCoPermittedTrunkTypes,
--           mscMpanlSigLastDlciReceivedStatus,
--           mscMpanlDlciLbLocalDeBytes,
--           mscMpanlStorageType,
--           mscMpanlDlciBciFromSubnet,
--           mscMpanlDlciLCoSetupPriority,
--           mscMpanlDlciLCoStorageType,
--           mscMpanlFramerUnderruns,
--           mscMpanlDlciDeFrmFromIf,
--           mscMpanlDlciVcPreviousDiagnosticCode,
--           mscMpanlFrmToIf,
--           mscMpanlDlciVcDataPath,
--           mscMpanlSigCurrentQueueSize,
--           mscMpanlSigProtocolErrors,
--           mscMpanlDlciLCoLastTearDownReason,
--           mscMpanlSigQualityOfServiceNotAvailable,
--           mscMpanlDlciVcPeakRetryQueueSize,
--           mscMpanlDlciLCoPathFailureCount,
--           mscMpanlDlciVcCallingDna,
--           mscMpanlDlciDiscCongestedFromIf,
--           mscMpanlDlciLCoBytesToNetwork,
--           mscMpanlDlciExcessBytesFromIf,
--           mscMpanlDlciVcPeakOoSeqFrmForwarded,
--           mscMpanlFrMuxSetupDlciCompName,
--           mscMpanlDlciVcFrmCongestedToSubnet,
--           mscMpanlDlciExcessFrmFromIf,
--           mscMpanlSigMpanlCurrentQueueSize,
--           mscMpanlDlciLCoPathFailureAction,
--           mscMpanlDlciJvcCallingNpi,
--           mscMpanlSigComponentName,
--           mscMpanlFramerOverruns,
--           mscMpanlDlciVcFastSelectCall,
--           mscMpanlDlciBytesFromIf,
--           mscMpanlDlciBecnFrmToIf,
--           mscMpanlDlciLCoRoundTripDelay,
--           mscMpanlDlciVcNotDataXferFromSubnet,
--           mscMpanlDlciLbRemoteTotalFrm,
--           mscMpanlDlciFrmFromIf,
--           mscMpanlSnmpOperStatus,
--           mscMpanlDlciLbRemoteBecnFrm,
--           mscMpanlCommentText,
--           mscMpanlSigIFramesReceived,
--           mscMpanlDlciCallReferenceNumber,
--           mscMpanlDlciLCoEnd,
--           mscMpanlNumberOfEmissionQs,
--           mscMpanlSigSetupTimeout,
--           mscMpanlLastUnknownDlci,
--           mscMpanlSigReleaseTimer,
--           mscMpanlDlciVcRcosFromNetwork,
--           mscMpanlSigMpanlComponentName,
--           mscMpanlUnknownStatus,
--           mscMpanlStandbyStatus,
--           mscMpanlLmiProcedures,
--           mscMpanlLmiComponentName,
--           mscMpanlDlciVcDuplicatesFromSubnet,
--           mscMpanlDlciQ933CallReference,
--           mscMpanlSigRowStatus,
--           mscMpanlDlciControlStatus,
--           mscMpanlSigLastStateChangeReason,
--           mscMpanlDlciLCoCalledDna,
--           mscMpanlDlciLCoPktsFromNetwork,
--           mscMpanlDlciTotalIngressSegFrm,
--           mscMpanlDlciLCoBumpPreference,
--           mscMpanlDlciQ933CallState,
--           mscMpanlSigAckTimeout,
--           mscMpanlDlciRowStatus,
--           mscMpanlFrMuxSetupComponentName,
--           mscMpanlDlciVcOoSeqByteCntExceeded,
--           mscMpanlFrMuxSetupPvcSetupComponentName,
--           mscMpanlDlciJvcStorageType,
--           mscMpanlVoFrRowStatus,
--           mscMpanlDlciErrorLongBytesFromIf,
--           mscMpanlSigAckTimer,
--           mscMpanlAdminState,
--           mscMpanlDlciDiscCongestedToIfBytes,
--           mscMpanlDlciVcPktRetryTimeouts,
--           mscMpanlDlciVcOutOfRangeFrmFromSubnet,
--           mscMpanlDlciErrorLongFrmFromIf,
--           mscMpanlVoFrFragmentedHighestPriorityFrames,
--           mscMpanlDlciJvcProtocolErrors,
--           mscMpanlDlciVcCalledDna,
--           mscMpanlDlciUsageState,
--           mscMpanlIfAdminStatus,
--           mscMpanlDlciVcSegmentsSent,
--           mscMpanlSigCurrentNumberOfSvcCalls,
--           mscMpanlDlciJvcCalledNpi,
--           mscMpanlSigAdminState,
--           mscMpanlDlciBecnFrmFromIf,
--           mscMpanlFramerUsageState,
--           mscMpanlDlciVcSubnetRecoveries,
--           mscMpanlFramerNormPrioLinkUtilFromIf,
--           mscMpanlDlciJvcPacketsToSubnet,
--           mscMpanlSigWindowSize,
--           mscMpanlDlciEirIngressSegFrm,
--           mscMpanlIsdnBChannelState }
-- STATUS  mandatory
-- DESCRIPTION
--   "A list of all current accessible leaf objects."

mpaNetworkLinkGroup OBJECT IDENTIFIER ::= { mpaNetworkLinkMIB 1 }
mpaNetworkLinkGroupCA OBJECT IDENTIFIER ::= { mpaNetworkLinkGroup 1 }
mpaNetworkLinkGroupCA02 OBJECT IDENTIFIER ::= { mpaNetworkLinkGroupCA 3 }
mpaNetworkLinkGroupCA02A OBJECT IDENTIFIER ::= { mpaNetworkLinkGroupCA02 2 }



-- Agent-Capabilities Statement:

-- PRODUCT-RELEASE "MscPassport Release 1.2 MpaNetworkLink."
-- STATUS          mandatory
-- DESCRIPTION     "Carrier Passport MpaNetworkLink MIB: MIB Version CA02A,
--                  Software Version CA02S9C."
-- SUPPORTS        Nortel-MsCarrier-MscPassport-MpaNetworkLinkMIB
--    INCLUDES     { mpaNetworkLinkGroupCA02A }

mpaNetworkLinkCapabilities OBJECT IDENTIFIER ::= { mpaNetworkLinkMIB 3 }
mpaNetworkLinkCapabilitiesCA OBJECT IDENTIFIER ::= { mpaNetworkLinkCapabilities 1 }
mpaNetworkLinkCapabilitiesCA02 OBJECT IDENTIFIER ::= { mpaNetworkLinkCapabilitiesCA 3 }
mpaNetworkLinkCapabilitiesCA02A OBJECT IDENTIFIER ::= { mpaNetworkLinkCapabilitiesCA02 2 }





END
