Nortel-MsCarrier-MscPassport-PppMIB
DEFINITIONS ::= BEGIN



IMPORTS

      OBJECT-TYPE
   FROM RFC-1212

      mscPassportMIBs,
      mscComponents
   FROM Nortel-MsCarrier-MscPassport-UsefulDefinitionsMIB

      Counter32,
      DisplayString,
      StorageType,
      RowStatus,
      InterfaceIndex,
      Gauge32,
      Integer32,
      Unsigned32
   FROM Nortel-MsCarrier-MscPassport-StandardTextualConventionsMIB

      NonReplicated,
      Link
   FROM Nortel-MsCarrier-MscPassport-TextualConventionsMIB;




-- LAST-UPDATED   "9909010000Z"
-- ORGANIZATION   "Nortel Networks"
-- CONTACT-INFO   "
--         Nortel Carrier Data Network Management
--         
--         Postal:       P.O. Box 3511, Station C 
--                       Ottawa, Ontario 
--                       Canada  K1Y 4H7
--         
--         via the WEB:  http://www.nortelnetworks.com  
--                       select 'Contact Us' from the menu
--          
--         via phone:    1-800-4NORTEL"
-- DESCRIPTION
--    "The module describing the Nortel MsCarrier MscPassport
--     Ppp Enterprise MIB."

pppMIB OBJECT IDENTIFIER ::= { mscPassportMIBs 33 }










-- PointToPointProtocol/n
-- This component defines an instance of the Ppp link level protocol. The 
-- component instance value is a unique number.

mscPpp OBJECT IDENTIFIER ::= { mscComponents 102 }



mscPppRowStatusTable OBJECT-TYPE
   SYNTAX     SEQUENCE OF MscPppRowStatusEntry
   ACCESS     not-accessible
   STATUS     mandatory
   DESCRIPTION
     "This entry controls the addition and deletion of 
      mscPpp components."
::= { mscPpp 1 }

mscPppRowStatusEntry OBJECT-TYPE
   SYNTAX     MscPppRowStatusEntry
   ACCESS     not-accessible
   STATUS     mandatory
   DESCRIPTION
     "A single entry in the table represents a single 
      mscPpp component."
   INDEX {
      mscPppIndex }
::= { mscPppRowStatusTable 1 }

MscPppRowStatusEntry ::= SEQUENCE {
   mscPppRowStatus
      RowStatus,
   mscPppComponentName
      DisplayString,
   mscPppStorageType
      StorageType,
   mscPppIndex
      Integer32 }

mscPppRowStatus OBJECT-TYPE
   SYNTAX     RowStatus 
   ACCESS     read-write
   STATUS     mandatory
   DESCRIPTION
     "This variable is used as the basis for SNMP naming of
      mscPpp components.
      These components can be added and deleted."
::= { mscPppRowStatusEntry 1 }

mscPppComponentName OBJECT-TYPE
   SYNTAX     DisplayString 
   ACCESS     read-only
   STATUS     mandatory
   DESCRIPTION
     "This variable provides the component's string name for
      use with the ASCII Console Interface"
::= { mscPppRowStatusEntry 2 }

mscPppStorageType OBJECT-TYPE
   SYNTAX     StorageType 
   ACCESS     read-only
   STATUS     mandatory
   DESCRIPTION
     "This variable represents the storage type value for the
      mscPpp tables."
::= { mscPppRowStatusEntry 4 }

mscPppIndex OBJECT-TYPE
   SYNTAX     Integer32 (1..65535)
   ACCESS     not-accessible
   STATUS     mandatory
   DESCRIPTION
     "This variable represents the index for the mscPpp tables."
::= { mscPppRowStatusEntry 10 }

mscPppCidDataTable OBJECT-TYPE
   SYNTAX     SEQUENCE OF MscPppCidDataEntry
   ACCESS     not-accessible
   STATUS     mandatory
   DESCRIPTION
     "This group contains the attribute for a component's Customer 
      Identifier (CID). Refer to the attribute description for a detailed 
      explanation of CIDs."
::= { mscPpp 20 }

mscPppCidDataEntry OBJECT-TYPE
   SYNTAX     MscPppCidDataEntry
   ACCESS     not-accessible
   STATUS     mandatory
   DESCRIPTION
     "An entry in the mscPppCidDataTable."
   INDEX {
      mscPppIndex }
::= { mscPppCidDataTable 1 }

MscPppCidDataEntry ::= SEQUENCE {
   mscPppCustomerIdentifier
      Unsigned32 }

mscPppCustomerIdentifier OBJECT-TYPE
   SYNTAX     Unsigned32 (0 | 1..8191)
   ACCESS     read-write
   STATUS     mandatory
   DESCRIPTION
     "This attribute holds the Customer Identifier (CID).
      
      Every component has a CID. If a component has a cid attribute, the 
      component's CID is the provisioned value of that attribute; 
      otherwise the component inherits the CID of its parent. The top-
      level component has a CID of 0.
      
      Every operator session also has a CID, which is the CID 
      provisioned for the operator's user ID. An operator will see only the 
      stream data for components having a matching CID. Also, the 
      operator will be allowed to issue commands for only those 
      components which have a matching CID.
      
      An operator CID of 0 is used to identify the Network Manager 
      (referred to as 'NetMan' in DPN). This CID matches the CID of 
      any component. Values 1 to 8191 inclusive (equivalent to 'basic 
      CIDs' in DPN) may be assigned to specific customers."
   DEFVAL     { 0 }
::= { mscPppCidDataEntry 1 }

mscPppIfEntryTable OBJECT-TYPE
   SYNTAX     SEQUENCE OF MscPppIfEntryEntry
   ACCESS     not-accessible
   STATUS     mandatory
   DESCRIPTION
     "This group contains the provisionable attributes for the ifEntry."
::= { mscPpp 21 }

mscPppIfEntryEntry OBJECT-TYPE
   SYNTAX     MscPppIfEntryEntry
   ACCESS     not-accessible
   STATUS     mandatory
   DESCRIPTION
     "An entry in the mscPppIfEntryTable."
   INDEX {
      mscPppIndex }
::= { mscPppIfEntryTable 1 }

MscPppIfEntryEntry ::= SEQUENCE {
   mscPppIfAdminStatus
      INTEGER,
   mscPppIfIndex
      InterfaceIndex }

mscPppIfAdminStatus OBJECT-TYPE
   SYNTAX     INTEGER  {
                 up(1),
                 down(2),
                 testing(3) }
   ACCESS     read-write
   STATUS     mandatory
   DESCRIPTION
     "The desired state of the interface. The up state indicates the 
      interface is operational. The down state indicates the interface is not 
      operational. The testing state indicates that no operational packets 
      can be passed."
   DEFVAL     { up }
::= { mscPppIfEntryEntry 1 }

mscPppIfIndex OBJECT-TYPE
   SYNTAX     InterfaceIndex (1..65535)
   ACCESS     read-only
   STATUS     mandatory
   DESCRIPTION
     "This is the index for the IfEntry. Its value is automatically initialized 
      during the provisioning process."
::= { mscPppIfEntryEntry 2 }

mscPppMpTable OBJECT-TYPE
   SYNTAX     SEQUENCE OF MscPppMpEntry
   ACCESS     not-accessible
   STATUS     mandatory
   DESCRIPTION
     "This group contains the base provisioning data for the Media 
      Application component."
::= { mscPpp 22 }

mscPppMpEntry OBJECT-TYPE
   SYNTAX     MscPppMpEntry
   ACCESS     not-accessible
   STATUS     mandatory
   DESCRIPTION
     "An entry in the mscPppMpTable."
   INDEX {
      mscPppIndex }
::= { mscPppMpTable 1 }

MscPppMpEntry ::= SEQUENCE {
   mscPppLinkToProtocolPort
      Link }

mscPppLinkToProtocolPort OBJECT-TYPE
   SYNTAX     Link 
   ACCESS     read-write
   STATUS     mandatory
   DESCRIPTION
     "This attribute contains a protocol port component name. The attribute 
      associates the application with a protocol port."
::= { mscPppMpEntry 1 }

mscPppStateTable OBJECT-TYPE
   SYNTAX     SEQUENCE OF MscPppStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscPpp 23 }

mscPppStateEntry OBJECT-TYPE
   SYNTAX     MscPppStateEntry
   ACCESS     not-accessible
   STATUS     mandatory
   DESCRIPTION
     "An entry in the mscPppStateTable."
   INDEX {
      mscPppIndex }
::= { mscPppStateTable 1 }

MscPppStateEntry ::= SEQUENCE {
   mscPppAdminState
      INTEGER,
   mscPppOperationalState
      INTEGER,
   mscPppUsageState
      INTEGER }

mscPppAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscPppStateEntry 1 }

mscPppOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscPppStateEntry 2 }

mscPppUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscPppStateEntry 3 }

mscPppOperStatusTable OBJECT-TYPE
   SYNTAX     SEQUENCE OF MscPppOperStatusEntry
   ACCESS     not-accessible
   STATUS     mandatory
   DESCRIPTION
     "This group includes the Operational Status attribute. This attribute 
      defines the current operational state of this component."
::= { mscPpp 24 }

mscPppOperStatusEntry OBJECT-TYPE
   SYNTAX     MscPppOperStatusEntry
   ACCESS     not-accessible
   STATUS     mandatory
   DESCRIPTION
     "An entry in the mscPppOperStatusTable."
   INDEX {
      mscPppIndex }
::= { mscPppOperStatusTable 1 }

MscPppOperStatusEntry ::= SEQUENCE {
   mscPppSnmpOperStatus
      INTEGER }

mscPppSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { mscPppOperStatusEntry 1 }


-- Ppp/n Link
-- This component is used to contain all the attributes related to the Ppp 
-- link. This is a mandatory subcomponent of Ppp and does not need to be 
-- added.

mscPppLnk OBJECT IDENTIFIER ::= { mscPpp 2 }



mscPppLnkRowStatusTable OBJECT-TYPE
   SYNTAX     SEQUENCE OF MscPppLnkRowStatusEntry
   ACCESS     not-accessible
   STATUS     mandatory
   DESCRIPTION
     "This entry controls the addition and deletion of 
      mscPppLnk components."
::= { mscPppLnk 1 }

mscPppLnkRowStatusEntry OBJECT-TYPE
   SYNTAX     MscPppLnkRowStatusEntry
   ACCESS     not-accessible
   STATUS     mandatory
   DESCRIPTION
     "A single entry in the table represents a single 
      mscPppLnk component."
   INDEX {
      mscPppIndex,
      mscPppLnkIndex }
::= { mscPppLnkRowStatusTable 1 }

MscPppLnkRowStatusEntry ::= SEQUENCE {
   mscPppLnkRowStatus
      RowStatus,
   mscPppLnkComponentName
      DisplayString,
   mscPppLnkStorageType
      StorageType,
   mscPppLnkIndex
      NonReplicated }

mscPppLnkRowStatus OBJECT-TYPE
   SYNTAX     RowStatus 
   ACCESS     read-only
   STATUS     mandatory
   DESCRIPTION
     "This variable is used as the basis for SNMP naming of
      mscPppLnk components.
      These components cannot be added nor deleted."
::= { mscPppLnkRowStatusEntry 1 }

mscPppLnkComponentName OBJECT-TYPE
   SYNTAX     DisplayString 
   ACCESS     read-only
   STATUS     mandatory
   DESCRIPTION
     "This variable provides the component's string name for
      use with the ASCII Console Interface"
::= { mscPppLnkRowStatusEntry 2 }

mscPppLnkStorageType OBJECT-TYPE
   SYNTAX     StorageType 
   ACCESS     read-only
   STATUS     mandatory
   DESCRIPTION
     "This variable represents the storage type value for the
      mscPppLnk tables."
::= { mscPppLnkRowStatusEntry 4 }

mscPppLnkIndex OBJECT-TYPE
   SYNTAX     NonReplicated 
   ACCESS     not-accessible
   STATUS     mandatory
   DESCRIPTION
     "This variable represents the index for the mscPppLnk tables."
::= { mscPppLnkRowStatusEntry 10 }

mscPppLnkProvTable OBJECT-TYPE
   SYNTAX     SEQUENCE OF MscPppLnkProvEntry
   ACCESS     not-accessible
   STATUS     mandatory
   DESCRIPTION
     "This group contains the provisioned attributes for the Ppp Link 
      component."
::= { mscPppLnk 10 }

mscPppLnkProvEntry OBJECT-TYPE
   SYNTAX     MscPppLnkProvEntry
   ACCESS     not-accessible
   STATUS     mandatory
   DESCRIPTION
     "An entry in the mscPppLnkProvTable."
   INDEX {
      mscPppIndex,
      mscPppLnkIndex }
::= { mscPppLnkProvTable 1 }

MscPppLnkProvEntry ::= SEQUENCE {
   mscPppLnkConfigInitialMru
      Unsigned32,
   mscPppLnkConfigMagicNumber
      INTEGER,
   mscPppLnkRestartTimer
      Unsigned32,
   mscPppLnkContinuityMonitor
      INTEGER,
   mscPppLnkNegativeAckTries
      Unsigned32,
   mscPppLnkQualityThreshold
      Unsigned32,
   mscPppLnkQualityWindow
      Unsigned32,
   mscPppLnkTerminateRequestTries
      Unsigned32,
   mscPppLnkConfigureRequestTries
      Unsigned32 }

mscPppLnkConfigInitialMru OBJECT-TYPE
   SYNTAX     Unsigned32 (68..18000)
   ACCESS     read-write
   STATUS     mandatory
   DESCRIPTION
     "This is the initial Maximum Receive Unit (Mru) that the local Ppp entity 
      will advertise to the remote entity. A change to this attribute will not 
      take effect until Ppp is restarted (lock/unlock)."
   DEFVAL     { 18000 }
::= { mscPppLnkProvEntry 1 }

mscPppLnkConfigMagicNumber OBJECT-TYPE
   SYNTAX     INTEGER  {
                 disabled(1),
                 enabled(2) }
   ACCESS     read-write
   STATUS     mandatory
   DESCRIPTION
     "If enabled then the local node will attempt to perform Magic Number 
      negotiation with the remote node. If disabled then this negotiation is not 
      performed. In any event, the local node will comply with any magic 
      number negotiations attempted by the remote node, per the Ppp 
      specification. A change to this attribute will not take effect until Ppp is 
      restarted (lock/unlock)."
   DEFVAL     { enabled }
::= { mscPppLnkProvEntry 4 }

mscPppLnkRestartTimer OBJECT-TYPE
   SYNTAX     Unsigned32 (1000..10000)
   ACCESS     read-write
   STATUS     mandatory
   DESCRIPTION
     "This is the time, in milliseconds, that Ppp will wait for a response to a 
      configure request or a terminate request before retrying."
   DEFVAL     { 3000 }
::= { mscPppLnkProvEntry 6 }

mscPppLnkContinuityMonitor OBJECT-TYPE
   SYNTAX     INTEGER  {
                 enabled(1),
                 disabled(2) }
   ACCESS     read-write
   STATUS     mandatory
   DESCRIPTION
     "This 					attribute turns on/off (enabled/disabled) the Link Continuity 
      Monitor. If set to enabled, periodic keep alive echo packet will be sent 
      over the Ppp link. If set to disabled, no keep alive packets will be sent. 
      A change to this attribute will not take effect until Ppp is restarted (lock/
      unlock)."
   DEFVAL     { enabled }
::= { mscPppLnkProvEntry 7 }

mscPppLnkNegativeAckTries OBJECT-TYPE
   SYNTAX     Unsigned32 (0..4294967295)
   ACCESS     read-write
   STATUS     mandatory
   DESCRIPTION
     "This attribute specifies the maximum negative acknowledgments sent to 
      the remote Ppp entity during negotiation before defaulting it's 
      configuration parameters."
   DEFVAL     { 10 }
::= { mscPppLnkProvEntry 8 }

mscPppLnkQualityThreshold OBJECT-TYPE
   SYNTAX     Unsigned32 (10..99)
   ACCESS     read-write
   STATUS     mandatory
   DESCRIPTION
     "This attribute specifies the minimum allowed line quality before the line 
      is considered too poor to continue operation. The value for this attribute 
      is a percentage measure of the line quality given in integers (10 to 99). 
      The higher the value, the more stringent the line requirements."
   DEFVAL     { 90 }
::= { mscPppLnkProvEntry 9 }

mscPppLnkQualityWindow OBJECT-TYPE
   SYNTAX     Unsigned32 (10..400)
   ACCESS     read-write
   STATUS     mandatory
   DESCRIPTION
     "This attribute specifies the number of seconds used for sampling line 
      quality. If line quality drops below the level set with the 
      qualityThreshold attribute during this window, this instance of Ppp will 
      be marked down until line quality recovers."
   DEFVAL     { 30 }
::= { mscPppLnkProvEntry 10 }

mscPppLnkTerminateRequestTries OBJECT-TYPE
   SYNTAX     Unsigned32 (0..4294967295)
   ACCESS     read-write
   STATUS     mandatory
   DESCRIPTION
     "This attribute specifies the maximum terminate requests to be sent, when 
      closing the connection, and not answered before this instance of Ppp 
      enters a closing state."
   DEFVAL     { 10 }
::= { mscPppLnkProvEntry 11 }

mscPppLnkConfigureRequestTries OBJECT-TYPE
   SYNTAX     Unsigned32 (0..4294967295)
   ACCESS     read-write
   STATUS     mandatory
   DESCRIPTION
     "This attribute specifies the number of configuration requests that will be 
      sent out and not answered before this instance of Ppp enters a listening 
      state. If both sides enter the listening state then the link will not come 
      up. To eliminate this possibility, this attribute should be set to 
      1000000000. This will ensure that this end of the Ppp link will 
      continue to try until the link is good."
   DEFVAL     { 1000000000 }
::= { mscPppLnkProvEntry 12 }

mscPppLnkOperTable OBJECT-TYPE
   SYNTAX     SEQUENCE OF MscPppLnkOperEntry
   ACCESS     not-accessible
   STATUS     mandatory
   DESCRIPTION
     "This group contains the Ppp Link Operational attributes."
::= { mscPppLnk 11 }

mscPppLnkOperEntry OBJECT-TYPE
   SYNTAX     MscPppLnkOperEntry
   ACCESS     not-accessible
   STATUS     mandatory
   DESCRIPTION
     "An entry in the mscPppLnkOperTable."
   INDEX {
      mscPppIndex,
      mscPppLnkIndex }
::= { mscPppLnkOperTable 1 }

MscPppLnkOperEntry ::= SEQUENCE {
   mscPppLnkOperState
      INTEGER,
   mscPppLnkLineCondition
      INTEGER,
   mscPppLnkBadAddresses
      Counter32,
   mscPppLnkBadControls
      Counter32,
   mscPppLnkPacketTooLongs
      Counter32,
   mscPppLnkBadFcss
      Counter32,
   mscPppLnkLocalMru
      Unsigned32,
   mscPppLnkRemoteMru
      Unsigned32,
   mscPppLnkTransmitFcsSize
      Unsigned32,
   mscPppLnkReceiveFcsSize
      Unsigned32 }

mscPppLnkOperState OBJECT-TYPE
   SYNTAX     INTEGER  {
                 initial(0),
                 starting(1),
                 closed(2),
                 stopped(3),
                 closing(4),
                 stopping(5),
                 reqsent(6),
                 ackrcvd(7),
                 acksent(8),
                 opened(9) }
   ACCESS     read-only
   STATUS     mandatory
   DESCRIPTION
     "This is the operational state of the Link Control Protocol. For more 
      information as to the definition of each state see RFC1331 section 5.3."
   DEFVAL     { initial }
::= { mscPppLnkOperEntry 1 }

mscPppLnkLineCondition OBJECT-TYPE
   SYNTAX     INTEGER  {
                 ok(0),
                 looped(1),
                 noClock(3),
                 badLineCondition(4) }
   ACCESS     read-only
   STATUS     mandatory
   DESCRIPTION
     "This attribute describes the condition of the physical line that Ppp is 
      running over.
      ok: The condition of the line is good.
      looped: The line is looped back on itself, probably at the remote end.
      noClock: There is a hardware problem with the line. The cable may not 
      be plugged in correctly.
      badLineCondition: The quality of the line is below the 
      qualityThreshold."
   DEFVAL     { ok }
::= { mscPppLnkOperEntry 2 }

mscPppLnkBadAddresses OBJECT-TYPE
   SYNTAX     Counter32 
   ACCESS     read-only
   STATUS     mandatory
   DESCRIPTION
     "This attribute counts the number of packets received with an incorrect 
      Address Field. If this count is going up quickly, it could indicate that 
      there is a line quality problem or that the remote end is transmitting a 
      protocol other than Ppp. This counter will wrap around to 0 when it 
      exceeds its maximum count."
::= { mscPppLnkOperEntry 4 }

mscPppLnkBadControls OBJECT-TYPE
   SYNTAX     Counter32 
   ACCESS     read-only
   STATUS     mandatory
   DESCRIPTION
     "This attribute counts the number of packets received on this link with an 
      incorrect Control Field. If this count is going up quickly, it could 
      indicate that there is a line quality problem or that the remote end is 
      transmitting a protocol other than Ppp. This counter will wrap around to 
      0 when it exceeds its maximum count."
::= { mscPppLnkOperEntry 5 }

mscPppLnkPacketTooLongs OBJECT-TYPE
   SYNTAX     Counter32 
   ACCESS     read-only
   STATUS     mandatory
   DESCRIPTION
     "This attribute counts the number of packets received that have been 
      discarded because their length exceeded the Maximum Receive Unit 
      (Mru). This counter will wrap around to 0 when it exceeds its maximum 
      count."
::= { mscPppLnkOperEntry 6 }

mscPppLnkBadFcss OBJECT-TYPE
   SYNTAX     Counter32 
   ACCESS     read-only
   STATUS     mandatory
   DESCRIPTION
     "This attribute counts the number of packets received that have been 
      discarded due to having an incorrect Frame Check Sequence (Fcs). This 
      counter will wrap around to 0 when it exceeds its maximum count."
::= { mscPppLnkOperEntry 7 }

mscPppLnkLocalMru OBJECT-TYPE
   SYNTAX     Unsigned32 (1..2147483648)
   ACCESS     read-only
   STATUS     mandatory
   DESCRIPTION
     "This is the current value of the Maximum Receive Unit (Mru) for the 
      local Ppp Entity. This value is the Mru that the remote entity is using 
      when sending packets to the local Ppp entity."
   DEFVAL     { 1 }
::= { mscPppLnkOperEntry 8 }

mscPppLnkRemoteMru OBJECT-TYPE
   SYNTAX     Unsigned32 (1..2147483648)
   ACCESS     read-only
   STATUS     mandatory
   DESCRIPTION
     "This is the current value of the Maximum Receive Unit (Mru) for the 
      remote Ppp entity. This value is the Mru that the local entity is using 
      when sending packets to the remote Ppp entity."
::= { mscPppLnkOperEntry 9 }

mscPppLnkTransmitFcsSize OBJECT-TYPE
   SYNTAX     Unsigned32 (0..128)
   ACCESS     read-only
   STATUS     mandatory
   DESCRIPTION
     "This is the size of the Frame Check Sequence (Fcs) in bits that the local 
      node will generate when sending packets to the remote node."
   DEFVAL     { 0 }
::= { mscPppLnkOperEntry 16 }

mscPppLnkReceiveFcsSize OBJECT-TYPE
   SYNTAX     Unsigned32 (0..128)
   ACCESS     read-only
   STATUS     mandatory
   DESCRIPTION
     "This is the size of the Frame Check Sequence (Fcs) in bits that the 
      remote node will generate when sending packets to the local node."
   DEFVAL     { 0 }
::= { mscPppLnkOperEntry 17 }


-- Ppp/n LinkQualityMonitor
-- This component is used to contain all the operational attributes for the 
-- Ppp Link Quality Monitor. This is a mandatory subcomponent of Ppp 
-- and does not need to be manually added.

mscPppLqm OBJECT IDENTIFIER ::= { mscPpp 3 }



mscPppLqmRowStatusTable OBJECT-TYPE
   SYNTAX     SEQUENCE OF MscPppLqmRowStatusEntry
   ACCESS     not-accessible
   STATUS     mandatory
   DESCRIPTION
     "This entry controls the addition and deletion of 
      mscPppLqm components."
::= { mscPppLqm 1 }

mscPppLqmRowStatusEntry OBJECT-TYPE
   SYNTAX     MscPppLqmRowStatusEntry
   ACCESS     not-accessible
   STATUS     mandatory
   DESCRIPTION
     "A single entry in the table represents a single 
      mscPppLqm component."
   INDEX {
      mscPppIndex,
      mscPppLqmIndex }
::= { mscPppLqmRowStatusTable 1 }

MscPppLqmRowStatusEntry ::= SEQUENCE {
   mscPppLqmRowStatus
      RowStatus,
   mscPppLqmComponentName
      DisplayString,
   mscPppLqmStorageType
      StorageType,
   mscPppLqmIndex
      NonReplicated }

mscPppLqmRowStatus OBJECT-TYPE
   SYNTAX     RowStatus 
   ACCESS     read-only
   STATUS     mandatory
   DESCRIPTION
     "This variable is used as the basis for SNMP naming of
      mscPppLqm components.
      These components cannot be added nor deleted."
::= { mscPppLqmRowStatusEntry 1 }

mscPppLqmComponentName OBJECT-TYPE
   SYNTAX     DisplayString 
   ACCESS     read-only
   STATUS     mandatory
   DESCRIPTION
     "This variable provides the component's string name for
      use with the ASCII Console Interface"
::= { mscPppLqmRowStatusEntry 2 }

mscPppLqmStorageType OBJECT-TYPE
   SYNTAX     StorageType 
   ACCESS     read-only
   STATUS     mandatory
   DESCRIPTION
     "This variable represents the storage type value for the
      mscPppLqm tables."
::= { mscPppLqmRowStatusEntry 4 }

mscPppLqmIndex OBJECT-TYPE
   SYNTAX     NonReplicated 
   ACCESS     not-accessible
   STATUS     mandatory
   DESCRIPTION
     "This variable represents the index for the mscPppLqm tables."
::= { mscPppLqmRowStatusEntry 10 }

mscPppLqmProvTable OBJECT-TYPE
   SYNTAX     SEQUENCE OF MscPppLqmProvEntry
   ACCESS     not-accessible
   STATUS     mandatory
   DESCRIPTION
     "This group contains the provisioned attributes for the Ppp Link Quality 
      Monitor component."
::= { mscPppLqm 10 }

mscPppLqmProvEntry OBJECT-TYPE
   SYNTAX     MscPppLqmProvEntry
   ACCESS     not-accessible
   STATUS     mandatory
   DESCRIPTION
     "An entry in the mscPppLqmProvTable."
   INDEX {
      mscPppIndex,
      mscPppLqmIndex }
::= { mscPppLqmProvTable 1 }

MscPppLqmProvEntry ::= SEQUENCE {
   mscPppLqmConfigPeriod
      Unsigned32,
   mscPppLqmConfigStatus
      INTEGER }

mscPppLqmConfigPeriod OBJECT-TYPE
   SYNTAX     Unsigned32 (0..2147483647)
   ACCESS     read-write
   STATUS     mandatory
   DESCRIPTION
     "This is the Lqm reporting period that the local Ppp entity will attempt to 
      negotiate with the remote entity, in units of hundredths of a second. A 
      value of '0' will allow the remote Ppp entity to determine the reporting 
      period. A value greater than 180,000 (1/2 hour) will allow the period to 
      be determined dynamically as a function of the transmit data rate. A 
      value from 1-9 will be rounded up to 10 during negotiation. A change to 
      this attribute will not take effect until Ppp is restarted (lock/unlock)."
   DEFVAL     { 0 }
::= { mscPppLqmProvEntry 1 }

mscPppLqmConfigStatus OBJECT-TYPE
   SYNTAX     INTEGER  {
                 disabled(1),
                 enabled(2) }
   ACCESS     read-write
   STATUS     mandatory
   DESCRIPTION
     "If this attribute is enabled, the local node will attempt to perform Lqm 
      negotiation with the remote node. If it is disabled then this negotiation is 
      not performed. A change to this attribute will not take effect until Ppp is 
      restarted (lock/unlock)."
   DEFVAL     { disabled }
::= { mscPppLqmProvEntry 2 }

mscPppLqmOperTable OBJECT-TYPE
   SYNTAX     SEQUENCE OF MscPppLqmOperEntry
   ACCESS     not-accessible
   STATUS     mandatory
   DESCRIPTION
     "This group contains the operational attributes for the Ppp Link Quality 
      Monitor component."
::= { mscPppLqm 11 }

mscPppLqmOperEntry OBJECT-TYPE
   SYNTAX     MscPppLqmOperEntry
   ACCESS     not-accessible
   STATUS     mandatory
   DESCRIPTION
     "An entry in the mscPppLqmOperTable."
   INDEX {
      mscPppIndex,
      mscPppLqmIndex }
::= { mscPppLqmOperTable 1 }

MscPppLqmOperEntry ::= SEQUENCE {
   mscPppLqmQuality
      INTEGER,
   mscPppLqmInGoodOctets
      Counter32,
   mscPppLqmLocalPeriod
      Unsigned32,
   mscPppLqmRemotePeriod
      Unsigned32,
   mscPppLqmOutLqrs
      Counter32,
   mscPppLqmInLqrs
      Counter32 }

mscPppLqmQuality OBJECT-TYPE
   SYNTAX     INTEGER  {
                 good(1),
                 bad(2),
                 notDetermined(3) }
   ACCESS     read-only
   STATUS     mandatory
   DESCRIPTION
     "This is the current quality of the link as declared by the local Ppp 
      entity's Link-Quality Management modules. A value of good indicates 
      that LinkQualityMonitor configStatus is enabled and Link quality is 
      above Link qualityThreshold. A value of bad indicates that 
      LinkQualityMonitor configStatus is enabled and Link quality is not 
      above Link qualityThreshold. A value of notDetermined indicates that 
      LinkQualityMonitor configStatus is enabled and the quality of the link 
      has not been calculated yet or LinkQualityMonitor configStatus is 
      disabled."
   DEFVAL     { notDetermined }
::= { mscPppLqmOperEntry 1 }

mscPppLqmInGoodOctets OBJECT-TYPE
   SYNTAX     Counter32 
   ACCESS     read-only
   STATUS     mandatory
   DESCRIPTION
     "This attribute counts the number of good octets received. This counter 
      will wrap around to 0 when it exceeds its maximum count."
::= { mscPppLqmOperEntry 2 }

mscPppLqmLocalPeriod OBJECT-TYPE
   SYNTAX     Unsigned32 (1..4294967295)
   ACCESS     read-only
   STATUS     mandatory
   DESCRIPTION
     "This is the Lqm reporting period, in hundredths of a second that is in 
      effect for the local Ppp entity."
   DEFVAL     { 1 }
::= { mscPppLqmOperEntry 3 }

mscPppLqmRemotePeriod OBJECT-TYPE
   SYNTAX     Unsigned32 (1..4294967295)
   ACCESS     read-only
   STATUS     mandatory
   DESCRIPTION
     "This is the Lqm reporting period, in hundredths of a second, that is in 
      effect for the remote Ppp entity."
   DEFVAL     { 1 }
::= { mscPppLqmOperEntry 4 }

mscPppLqmOutLqrs OBJECT-TYPE
   SYNTAX     Counter32 
   ACCESS     read-only
   STATUS     mandatory
   DESCRIPTION
     "This attribute counts the number of link quality reports sent out. This 
      counter will wrap around to 0 when it exceeds its maximum count."
::= { mscPppLqmOperEntry 5 }

mscPppLqmInLqrs OBJECT-TYPE
   SYNTAX     Counter32 
   ACCESS     read-only
   STATUS     mandatory
   DESCRIPTION
     "This attribute counts the number of link quality reports received. This 
      counter will wrap around to 0 when it exceeds its maximum count."
::= { mscPppLqmOperEntry 6 }


-- Ppp/n NetworkControlProtocol
-- This component is used to contain all the operational attributes for the 
-- Ppp Network Control Protocols (Ncp). This is a mandatory 
-- subcomponent of Ppp and does not need to be manually added.

mscPppNcp OBJECT IDENTIFIER ::= { mscPpp 4 }



mscPppNcpRowStatusTable OBJECT-TYPE
   SYNTAX     SEQUENCE OF MscPppNcpRowStatusEntry
   ACCESS     not-accessible
   STATUS     mandatory
   DESCRIPTION
     "This entry controls the addition and deletion of 
      mscPppNcp components."
::= { mscPppNcp 1 }

mscPppNcpRowStatusEntry OBJECT-TYPE
   SYNTAX     MscPppNcpRowStatusEntry
   ACCESS     not-accessible
   STATUS     mandatory
   DESCRIPTION
     "A single entry in the table represents a single 
      mscPppNcp component."
   INDEX {
      mscPppIndex,
      mscPppNcpIndex }
::= { mscPppNcpRowStatusTable 1 }

MscPppNcpRowStatusEntry ::= SEQUENCE {
   mscPppNcpRowStatus
      RowStatus,
   mscPppNcpComponentName
      DisplayString,
   mscPppNcpStorageType
      StorageType,
   mscPppNcpIndex
      NonReplicated }

mscPppNcpRowStatus OBJECT-TYPE
   SYNTAX     RowStatus 
   ACCESS     read-only
   STATUS     mandatory
   DESCRIPTION
     "This variable is used as the basis for SNMP naming of
      mscPppNcp components.
      These components cannot be added nor deleted."
::= { mscPppNcpRowStatusEntry 1 }

mscPppNcpComponentName OBJECT-TYPE
   SYNTAX     DisplayString 
   ACCESS     read-only
   STATUS     mandatory
   DESCRIPTION
     "This variable provides the component's string name for
      use with the ASCII Console Interface"
::= { mscPppNcpRowStatusEntry 2 }

mscPppNcpStorageType OBJECT-TYPE
   SYNTAX     StorageType 
   ACCESS     read-only
   STATUS     mandatory
   DESCRIPTION
     "This variable represents the storage type value for the
      mscPppNcp tables."
::= { mscPppNcpRowStatusEntry 4 }

mscPppNcpIndex OBJECT-TYPE
   SYNTAX     NonReplicated 
   ACCESS     not-accessible
   STATUS     mandatory
   DESCRIPTION
     "This variable represents the index for the mscPppNcp tables."
::= { mscPppNcpRowStatusEntry 10 }

mscPppNcpBprovTable OBJECT-TYPE
   SYNTAX     SEQUENCE OF MscPppNcpBprovEntry
   ACCESS     not-accessible
   STATUS     mandatory
   DESCRIPTION
     "This group contains the provisioned attributes for the Bridge Network 
      Control Protocol."
::= { mscPppNcp 11 }

mscPppNcpBprovEntry OBJECT-TYPE
   SYNTAX     MscPppNcpBprovEntry
   ACCESS     not-accessible
   STATUS     mandatory
   DESCRIPTION
     "An entry in the mscPppNcpBprovTable."
   INDEX {
      mscPppIndex,
      mscPppNcpIndex }
::= { mscPppNcpBprovTable 1 }

MscPppNcpBprovEntry ::= SEQUENCE {
   mscPppNcpBConfigTinygram
      INTEGER,
   mscPppNcpBConfigLanId
      INTEGER }

mscPppNcpBConfigTinygram OBJECT-TYPE
   SYNTAX     INTEGER  {
                 disabled(1),
                 enabled(2) }
   ACCESS     read-write
   STATUS     mandatory
   DESCRIPTION
     "If this attribute is set to disabled then the local Bridge Network Control 
      Protocol (Bncp) entity will not initiate the tinygram compression option 
      negotiation. If it is enabled then the local Bncp entity will initiate 
      negotiation of this option. A change to this attribute will not take effect 
      until Ppp is restarted (lock/unlock)."
   DEFVAL     { enabled }
::= { mscPppNcpBprovEntry 1 }

mscPppNcpBConfigLanId OBJECT-TYPE
   SYNTAX     INTEGER  {
                 disabled(1),
                 enabled(2) }
   ACCESS     read-write
   STATUS     mandatory
   DESCRIPTION
     "If this attribute is set to disabled then the local Bncp entity will not 
      initiate the lan identification option negotiation. If it is enabled then the 
      local Bncp entity will initiate negotiation of the option. A change to this 
      attribute will not take effect until Ppp is restarted (lock/unlock)."
   DEFVAL     { enabled }
::= { mscPppNcpBprovEntry 4 }

mscPppNcpIpOperTable OBJECT-TYPE
   SYNTAX     SEQUENCE OF MscPppNcpIpOperEntry
   ACCESS     not-accessible
   STATUS     mandatory
   DESCRIPTION
     "This group contains the Ip Network Control Protocol operational 
      attributes."
::= { mscPppNcp 12 }

mscPppNcpIpOperEntry OBJECT-TYPE
   SYNTAX     MscPppNcpIpOperEntry
   ACCESS     not-accessible
   STATUS     mandatory
   DESCRIPTION
     "An entry in the mscPppNcpIpOperTable."
   INDEX {
      mscPppIndex,
      mscPppNcpIndex }
::= { mscPppNcpIpOperTable 1 }

MscPppNcpIpOperEntry ::= SEQUENCE {
   mscPppNcpIpOperState
      INTEGER }

mscPppNcpIpOperState OBJECT-TYPE
   SYNTAX     INTEGER  {
                 initial(0),
                 starting(1),
                 closed(2),
                 stopped(3),
                 closing(4),
                 stopping(5),
                 reqsent(6),
                 ackrcvd(7),
                 acksent(8),
                 opened(9) }
   ACCESS     read-only
   STATUS     mandatory
   DESCRIPTION
     "This is the operational state of the Ip network protocol. For more 
      information as to the definition of each state see RFC1331 section 5.3."
   DEFVAL     { initial }
::= { mscPppNcpIpOperEntry 1 }

mscPppNcpBoperTable OBJECT-TYPE
   SYNTAX     SEQUENCE OF MscPppNcpBoperEntry
   ACCESS     not-accessible
   STATUS     mandatory
   DESCRIPTION
     "This group contains the Bridge Network Control Protocol operational 
      attributes."
::= { mscPppNcp 14 }

mscPppNcpBoperEntry OBJECT-TYPE
   SYNTAX     MscPppNcpBoperEntry
   ACCESS     not-accessible
   STATUS     mandatory
   DESCRIPTION
     "An entry in the mscPppNcpBoperTable."
   INDEX {
      mscPppIndex,
      mscPppNcpIndex }
::= { mscPppNcpBoperTable 1 }

MscPppNcpBoperEntry ::= SEQUENCE {
   mscPppNcpBOperState
      INTEGER,
   mscPppNcpBLocalToRemoteTinygramComp
      INTEGER,
   mscPppNcpBRemoteToLocalTinygramComp
      INTEGER,
   mscPppNcpBLocalToRemoteLanId
      INTEGER,
   mscPppNcpBRemoteToLocalLanId
      INTEGER }

mscPppNcpBOperState OBJECT-TYPE
   SYNTAX     INTEGER  {
                 initial(0),
                 starting(1),
                 closed(2),
                 stopped(3),
                 closing(4),
                 stopping(5),
                 reqsent(6),
                 ackrcvd(7),
                 acksent(8),
                 opened(9) }
   ACCESS     read-only
   STATUS     mandatory
   DESCRIPTION
     "This is the operational status of the bridge network protocol. For more 
      information as to the definition of each state see RFC1331 section 5.3."
   DEFVAL     { initial }
::= { mscPppNcpBoperEntry 1 }

mscPppNcpBLocalToRemoteTinygramComp OBJECT-TYPE
   SYNTAX     INTEGER  {
                 disabled(1),
                 enabled(2) }
   ACCESS     read-only
   STATUS     mandatory
   DESCRIPTION
     "This attribute indicates whether the local node will perform tinygram 
      compression when sending packets to the remote entity. If it is disabled 
      then the local entity will not perform tinygram compression. If it is 
      enabled then the local entity will perform tinygram compression."
   DEFVAL     { disabled }
::= { mscPppNcpBoperEntry 3 }

mscPppNcpBRemoteToLocalTinygramComp OBJECT-TYPE
   SYNTAX     INTEGER  {
                 disabled(1),
                 enabled(2) }
   ACCESS     read-only
   STATUS     mandatory
   DESCRIPTION
     "If this attribute is disabled then the remote entity is not expected to 
      perform tinygram compression. If it is enabled then the remote entity is 
      expected to perform tinygram compression."
   DEFVAL     { disabled }
::= { mscPppNcpBoperEntry 4 }

mscPppNcpBLocalToRemoteLanId OBJECT-TYPE
   SYNTAX     INTEGER  {
                 disabled(1),
                 enabled(2) }
   ACCESS     read-only
   STATUS     mandatory
   DESCRIPTION
     "This attribute indicates whether the local node will include the lan 
      identification field in transmitted packets or not. If it is disabled then the 
      local node will not transmit this field, enabled means that the field will 
      be transmitted."
   DEFVAL     { disabled }
::= { mscPppNcpBoperEntry 5 }

mscPppNcpBRemoteToLocalLanId OBJECT-TYPE
   SYNTAX     INTEGER  {
                 disabled(1),
                 enabled(2) }
   ACCESS     read-only
   STATUS     mandatory
   DESCRIPTION
     "This attribute indicates whether the remote node has indicated that it 
      will include the lan identification field in transmitted packets or not. If it 
      is disabled then the field will not be transmitted, if enabled then the field 
      will be transmitted."
   DEFVAL     { disabled }
::= { mscPppNcpBoperEntry 6 }

mscPppNcpOperTable OBJECT-TYPE
   SYNTAX     SEQUENCE OF MscPppNcpOperEntry
   ACCESS     not-accessible
   STATUS     mandatory
   DESCRIPTION
     "This group contains the operational attributes for any Network Control 
      Protocols other than Ip and Bridge."
::= { mscPppNcp 16 }

mscPppNcpOperEntry OBJECT-TYPE
   SYNTAX     MscPppNcpOperEntry
   ACCESS     not-accessible
   STATUS     mandatory
   DESCRIPTION
     "An entry in the mscPppNcpOperTable."
   INDEX {
      mscPppIndex,
      mscPppNcpIndex }
::= { mscPppNcpOperTable 1 }

MscPppNcpOperEntry ::= SEQUENCE {
   mscPppNcpAppletalkOperState
      INTEGER,
   mscPppNcpIpxOperState
      INTEGER,
   mscPppNcpXnsOperState
      INTEGER,
   mscPppNcpDecnetOperState
      INTEGER }

mscPppNcpAppletalkOperState OBJECT-TYPE
   SYNTAX     INTEGER  {
                 initial(0),
                 starting(1),
                 closed(2),
                 stopped(3),
                 closing(4),
                 stopping(5),
                 reqsent(6),
                 ackrcvd(7),
                 acksent(8),
                 opened(9) }
   ACCESS     read-only
   STATUS     mandatory
   DESCRIPTION
     "This is the operational state of the AppleTalk network protocol. For 
      more information as to the definition of each state see RFC1331 section 
      5.3."
   DEFVAL     { initial }
::= { mscPppNcpOperEntry 1 }

mscPppNcpIpxOperState OBJECT-TYPE
   SYNTAX     INTEGER  {
                 initial(0),
                 starting(1),
                 closed(2),
                 stopped(3),
                 closing(4),
                 stopping(5),
                 reqsent(6),
                 ackrcvd(7),
                 acksent(8),
                 opened(9) }
   ACCESS     read-only
   STATUS     mandatory
   DESCRIPTION
     "This is the operational state of the Ipx network protocol. For more 
      information as to the definition of each state see RFC1331 section 5.3."
   DEFVAL     { initial }
::= { mscPppNcpOperEntry 2 }

mscPppNcpXnsOperState OBJECT-TYPE
   SYNTAX     INTEGER  {
                 initial(0),
                 starting(1),
                 closed(2),
                 stopped(3),
                 closing(4),
                 stopping(5),
                 reqsent(6),
                 ackrcvd(7),
                 acksent(8),
                 opened(9) }
   ACCESS     read-only
   STATUS     mandatory
   DESCRIPTION
     "This is the operational state of the Xns network protocol. For more 
      information as to the definition of each state see RFC1331 section 5.3."
   DEFVAL     { initial }
::= { mscPppNcpOperEntry 3 }

mscPppNcpDecnetOperState OBJECT-TYPE
   SYNTAX     INTEGER  {
                 initial(0),
                 starting(1),
                 closed(2),
                 stopped(3),
                 closing(4),
                 stopping(5),
                 reqsent(6),
                 ackrcvd(7),
                 acksent(8),
                 opened(9) }
   ACCESS     read-only
   STATUS     mandatory
   DESCRIPTION
     "This is the operational state of the DecNet network protocol. For more 
      information as to the definition of each state see RFC1331 section 5.3."
   DEFVAL     { initial }
::= { mscPppNcpOperEntry 4 }


-- Ppp/n Ncp BridgeMediaConfigEntry/n
-- This component is one entry in the BridgeMediaConfigEntry table. 
-- There are four of these components automatically added to create the 
-- table. The instances of this component are the mac types for which the 
-- data in this table entry pertains to.
-- 1) ethernet - IEEE 802.3/Ethernet
-- 2) tokenBus - IEEE 802.4/Token Bus
-- 3) tokenRing - IEEE 802.5/Token Ring
-- 4) fddi - Fddi

mscPppNcpBmcEntry OBJECT IDENTIFIER ::= { mscPppNcp 2 }



mscPppNcpBmcEntryRowStatusTable OBJECT-TYPE
   SYNTAX     SEQUENCE OF MscPppNcpBmcEntryRowStatusEntry
   ACCESS     not-accessible
   STATUS     mandatory
   DESCRIPTION
     "This entry controls the addition and deletion of 
      mscPppNcpBmcEntry components."
::= { mscPppNcpBmcEntry 1 }

mscPppNcpBmcEntryRowStatusEntry OBJECT-TYPE
   SYNTAX     MscPppNcpBmcEntryRowStatusEntry
   ACCESS     not-accessible
   STATUS     mandatory
   DESCRIPTION
     "A single entry in the table represents a single 
      mscPppNcpBmcEntry component."
   INDEX {
      mscPppIndex,
      mscPppNcpIndex,
      mscPppNcpBmcEntryMacTypeIndex }
::= { mscPppNcpBmcEntryRowStatusTable 1 }

MscPppNcpBmcEntryRowStatusEntry ::= SEQUENCE {
   mscPppNcpBmcEntryRowStatus
      RowStatus,
   mscPppNcpBmcEntryComponentName
      DisplayString,
   mscPppNcpBmcEntryStorageType
      StorageType,
   mscPppNcpBmcEntryMacTypeIndex
      INTEGER }

mscPppNcpBmcEntryRowStatus OBJECT-TYPE
   SYNTAX     RowStatus 
   ACCESS     read-write
   STATUS     mandatory
   DESCRIPTION
     "This variable is used as the basis for SNMP naming of
      mscPppNcpBmcEntry components.
      These components can be added."
::= { mscPppNcpBmcEntryRowStatusEntry 1 }

mscPppNcpBmcEntryComponentName OBJECT-TYPE
   SYNTAX     DisplayString 
   ACCESS     read-only
   STATUS     mandatory
   DESCRIPTION
     "This variable provides the component's string name for
      use with the ASCII Console Interface"
::= { mscPppNcpBmcEntryRowStatusEntry 2 }

mscPppNcpBmcEntryStorageType OBJECT-TYPE
   SYNTAX     StorageType 
   ACCESS     read-only
   STATUS     mandatory
   DESCRIPTION
     "This variable represents the storage type value for the
      mscPppNcpBmcEntry tables."
::= { mscPppNcpBmcEntryRowStatusEntry 4 }

mscPppNcpBmcEntryMacTypeIndex OBJECT-TYPE
   SYNTAX     INTEGER  {
                 ethernet(1),
                 tokenBus(2),
                 tokenRing(3),
                 fddi(4) }
   ACCESS     not-accessible
   STATUS     mandatory
   DESCRIPTION
     "This variable represents the index for the mscPppNcpBmcEntry tables."
::= { mscPppNcpBmcEntryRowStatusEntry 10 }

mscPppNcpBmcEntryProvTable OBJECT-TYPE
   SYNTAX     SEQUENCE OF MscPppNcpBmcEntryProvEntry
   ACCESS     not-accessible
   STATUS     mandatory
   DESCRIPTION
     "This group contains the attributes for one entry in the 
      BridgeMediaConfigEntry table."
::= { mscPppNcpBmcEntry 10 }

mscPppNcpBmcEntryProvEntry OBJECT-TYPE
   SYNTAX     MscPppNcpBmcEntryProvEntry
   ACCESS     not-accessible
   STATUS     mandatory
   DESCRIPTION
     "An entry in the mscPppNcpBmcEntryProvTable."
   INDEX {
      mscPppIndex,
      mscPppNcpIndex,
      mscPppNcpBmcEntryMacTypeIndex }
::= { mscPppNcpBmcEntryProvTable 1 }

MscPppNcpBmcEntryProvEntry ::= SEQUENCE {
   mscPppNcpBmcEntryLocalStatus
      INTEGER }

mscPppNcpBmcEntryLocalStatus OBJECT-TYPE
   SYNTAX     INTEGER  {
                 accept(1) }
   ACCESS     read-write
   STATUS     mandatory
   DESCRIPTION
     "This attribute indicates whether the local Ppp bridging entity should 
      accept packets of the protocol type identified by the instance value of 
      this component. Setting this attribute to accept allows packets of this 
      protocol type to be accepted. A change to this attribute will not take 
      effect until Ppp is restarted (lock/unlock)."
   DEFVAL     { accept }
::= { mscPppNcpBmcEntryProvEntry 1 }

-- 
-- *** THIS SUBTREE CURRENTLY NOT IMPLEMENTED ***
-- 

-- Ppp/n Ncp BridgeMediaEntry/n
-- This component is one entry in the BridgeMediaEntry table. There will 
-- be four of these components created automatically to create the table. 
-- The instances of this component are the mac types for which the data in 
-- this table entry pertains to.
-- 1) ethernet - IEEE 802.3/Ethernet
-- 2) tokenBus - IEEE 802.4/Token Bus
-- 3) tokenRing - IEEE 802.5/Token Ring
-- 4) fddi - Fddi

mscPppNcpBmEntry OBJECT IDENTIFIER ::= { mscPppNcp 3 }



mscPppNcpBmEntryRowStatusTable OBJECT-TYPE
   SYNTAX     SEQUENCE OF MscPppNcpBmEntryRowStatusEntry
   ACCESS     not-accessible
   STATUS     mandatory
   DESCRIPTION
     "*** THIS TABLE CURRENTLY NOT IMPLEMENTED ***

      This entry controls the addition and deletion of 
      mscPppNcpBmEntry components."
::= { mscPppNcpBmEntry 1 }

mscPppNcpBmEntryRowStatusEntry OBJECT-TYPE
   SYNTAX     MscPppNcpBmEntryRowStatusEntry
   ACCESS     not-accessible
   STATUS     mandatory
   DESCRIPTION
     "A single entry in the table represents a single 
      mscPppNcpBmEntry component."
   INDEX {
      mscPppIndex,
      mscPppNcpIndex,
      mscPppNcpBmEntryMacTypeIndex }
::= { mscPppNcpBmEntryRowStatusTable 1 }

MscPppNcpBmEntryRowStatusEntry ::= SEQUENCE {
   mscPppNcpBmEntryRowStatus
      RowStatus,
   mscPppNcpBmEntryComponentName
      DisplayString,
   mscPppNcpBmEntryStorageType
      StorageType,
   mscPppNcpBmEntryMacTypeIndex
      INTEGER }

mscPppNcpBmEntryRowStatus OBJECT-TYPE
   SYNTAX     RowStatus 
   ACCESS     read-only
   STATUS     mandatory
   DESCRIPTION
     "This variable is used as the basis for SNMP naming of
      mscPppNcpBmEntry components.
      These components cannot be added nor deleted."
::= { mscPppNcpBmEntryRowStatusEntry 1 }

mscPppNcpBmEntryComponentName OBJECT-TYPE
   SYNTAX     DisplayString 
   ACCESS     read-only
   STATUS     mandatory
   DESCRIPTION
     "This variable provides the component's string name for
      use with the ASCII Console Interface"
::= { mscPppNcpBmEntryRowStatusEntry 2 }

mscPppNcpBmEntryStorageType OBJECT-TYPE
   SYNTAX     StorageType 
   ACCESS     read-only
   STATUS     mandatory
   DESCRIPTION
     "This variable represents the storage type value for the
      mscPppNcpBmEntry tables."
::= { mscPppNcpBmEntryRowStatusEntry 4 }

mscPppNcpBmEntryMacTypeIndex OBJECT-TYPE
   SYNTAX     INTEGER  {
                 ethernet(1),
                 tokenBus(2),
                 tokenRing(3),
                 fddi(4) }
   ACCESS     not-accessible
   STATUS     mandatory
   DESCRIPTION
     "This variable represents the index for the mscPppNcpBmEntry tables."
::= { mscPppNcpBmEntryRowStatusEntry 10 }

mscPppNcpBmEntryOperTable OBJECT-TYPE
   SYNTAX     SEQUENCE OF MscPppNcpBmEntryOperEntry
   ACCESS     not-accessible
   STATUS     mandatory
   DESCRIPTION
     "*** THIS TABLE CURRENTLY NOT IMPLEMENTED ***

      This group contains the attributes for one entry in the BridgeMediaEntry 
      table."
::= { mscPppNcpBmEntry 10 }

mscPppNcpBmEntryOperEntry OBJECT-TYPE
   SYNTAX     MscPppNcpBmEntryOperEntry
   ACCESS     not-accessible
   STATUS     mandatory
   DESCRIPTION
     "An entry in the mscPppNcpBmEntryOperTable."
   INDEX {
      mscPppIndex,
      mscPppNcpIndex,
      mscPppNcpBmEntryMacTypeIndex }
::= { mscPppNcpBmEntryOperTable 1 }

MscPppNcpBmEntryOperEntry ::= SEQUENCE {
   mscPppNcpBmEntryLocalStatus
      INTEGER,
   mscPppNcpBmEntryRemoteStatus
      INTEGER }

mscPppNcpBmEntryLocalStatus OBJECT-TYPE
   SYNTAX     INTEGER  {
                 accept(1),
                 dontAccept(2) }
   ACCESS     read-only
   STATUS     mandatory
   DESCRIPTION
     "This attribute indicates whether the local Ppp bridging entity will accept 
      packets of the protocol type identified by the instance value of this 
      component. A value of accept indicates that packets of this protocol type 
      will be accepted. A value of dontAccept indicates that packets of this 
      type will not be accepted."
::= { mscPppNcpBmEntryOperEntry 2 }

mscPppNcpBmEntryRemoteStatus OBJECT-TYPE
   SYNTAX     INTEGER  {
                 accept(1),
                 dontAccept(2) }
   ACCESS     read-only
   STATUS     mandatory
   DESCRIPTION
     "This attribute indicates whether the remote Ppp bridging entity will 
      accept packets of the protocol type identified by the instance value of 
      this component. A value of accept indicates that packets of this protocol 
      type will be accepted. A value of dontAccept indicates that packets of 
      this type will not be accepted."
::= { mscPppNcpBmEntryOperEntry 3 }


-- 
-- Ppp/n Framer
-- 
-- The Framer component controls link layer framing for application 
-- components sending and receiving data on a link interface. It is also 
-- through Framer, that an application component is associated with a 
-- specific hardware link interface.
-- 
-- The Framer component provides provisionable attributes related to 
-- datapath aspects of the hardware interface (such as crc and frame length) 
-- rather than interface specific attributes (such as modem leads and 
-- clocking) which are associated with specific hardware components (such 
-- as V35/n or DS1/n). The Framer component also provides a 
-- provisionable attribute which binds the application component to a 
-- specific hardware component.
-- 
-- The Framer component contains operational attributes for link interface 
-- datapath statistics (such as frame counts and aborts).
-- 

mscPppFramer OBJECT IDENTIFIER ::= { mscPpp 5 }



mscPppFramerRowStatusTable OBJECT-TYPE
   SYNTAX     SEQUENCE OF MscPppFramerRowStatusEntry
   ACCESS     not-accessible
   STATUS     mandatory
   DESCRIPTION
     "This entry controls the addition and deletion of 
      mscPppFramer components."
::= { mscPppFramer 1 }

mscPppFramerRowStatusEntry OBJECT-TYPE
   SYNTAX     MscPppFramerRowStatusEntry
   ACCESS     not-accessible
   STATUS     mandatory
   DESCRIPTION
     "A single entry in the table represents a single 
      mscPppFramer component."
   INDEX {
      mscPppIndex,
      mscPppFramerIndex }
::= { mscPppFramerRowStatusTable 1 }

MscPppFramerRowStatusEntry ::= SEQUENCE {
   mscPppFramerRowStatus
      RowStatus,
   mscPppFramerComponentName
      DisplayString,
   mscPppFramerStorageType
      StorageType,
   mscPppFramerIndex
      NonReplicated }

mscPppFramerRowStatus OBJECT-TYPE
   SYNTAX     RowStatus 
   ACCESS     read-only
   STATUS     mandatory
   DESCRIPTION
     "This variable is used as the basis for SNMP naming of
      mscPppFramer components.
      These components cannot be added nor deleted."
::= { mscPppFramerRowStatusEntry 1 }

mscPppFramerComponentName OBJECT-TYPE
   SYNTAX     DisplayString 
   ACCESS     read-only
   STATUS     mandatory
   DESCRIPTION
     "This variable provides the component's string name for
      use with the ASCII Console Interface"
::= { mscPppFramerRowStatusEntry 2 }

mscPppFramerStorageType OBJECT-TYPE
   SYNTAX     StorageType 
   ACCESS     read-only
   STATUS     mandatory
   DESCRIPTION
     "This variable represents the storage type value for the
      mscPppFramer tables."
::= { mscPppFramerRowStatusEntry 4 }

mscPppFramerIndex OBJECT-TYPE
   SYNTAX     NonReplicated 
   ACCESS     not-accessible
   STATUS     mandatory
   DESCRIPTION
     "This variable represents the index for the mscPppFramer tables."
::= { mscPppFramerRowStatusEntry 10 }

mscPppFramerProvTable OBJECT-TYPE
   SYNTAX     SEQUENCE OF MscPppFramerProvEntry
   ACCESS     not-accessible
   STATUS     mandatory
   DESCRIPTION
     "This group contains the base provisioning data for the Framer 
      component. Application or hardware interface specific provisioning data 
      is contained in other provisionable Framer groups."
::= { mscPppFramer 10 }

mscPppFramerProvEntry OBJECT-TYPE
   SYNTAX     MscPppFramerProvEntry
   ACCESS     not-accessible
   STATUS     mandatory
   DESCRIPTION
     "An entry in the mscPppFramerProvTable."
   INDEX {
      mscPppIndex,
      mscPppFramerIndex }
::= { mscPppFramerProvTable 1 }

MscPppFramerProvEntry ::= SEQUENCE {
   mscPppFramerInterfaceName
      Link }

mscPppFramerInterfaceName OBJECT-TYPE
   SYNTAX     Link 
   ACCESS     read-write
   STATUS     mandatory
   DESCRIPTION
     "This attribute contains a hardware component name.
      
      The attribute associates the application with a specific link. This defines 
      the logical processor on which Framer's parent component (as well as 
      Framer itself) will run."
::= { mscPppFramerProvEntry 1 }

mscPppFramerStateTable OBJECT-TYPE
   SYNTAX     SEQUENCE OF MscPppFramerStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscPppFramer 12 }

mscPppFramerStateEntry OBJECT-TYPE
   SYNTAX     MscPppFramerStateEntry
   ACCESS     not-accessible
   STATUS     mandatory
   DESCRIPTION
     "An entry in the mscPppFramerStateTable."
   INDEX {
      mscPppIndex,
      mscPppFramerIndex }
::= { mscPppFramerStateTable 1 }

MscPppFramerStateEntry ::= SEQUENCE {
   mscPppFramerAdminState
      INTEGER,
   mscPppFramerOperationalState
      INTEGER,
   mscPppFramerUsageState
      INTEGER }

mscPppFramerAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscPppFramerStateEntry 1 }

mscPppFramerOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscPppFramerStateEntry 2 }

mscPppFramerUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscPppFramerStateEntry 3 }

mscPppFramerStatsTable OBJECT-TYPE
   SYNTAX     SEQUENCE OF MscPppFramerStatsEntry
   ACCESS     not-accessible
   STATUS     mandatory
   DESCRIPTION
     "This group contains the operational statistics data for a Framer 
      component."
::= { mscPppFramer 13 }

mscPppFramerStatsEntry OBJECT-TYPE
   SYNTAX     MscPppFramerStatsEntry
   ACCESS     not-accessible
   STATUS     mandatory
   DESCRIPTION
     "An entry in the mscPppFramerStatsTable."
   INDEX {
      mscPppIndex,
      mscPppFramerIndex }
::= { mscPppFramerStatsTable 1 }

MscPppFramerStatsEntry ::= SEQUENCE {
   mscPppFramerFrmToIf
      Counter32,
   mscPppFramerFrmFromIf
      Counter32,
   mscPppFramerAborts
      Counter32,
   mscPppFramerCrcErrors
      Counter32,
   mscPppFramerLrcErrors
      Counter32,
   mscPppFramerNonOctetErrors
      Counter32,
   mscPppFramerOverruns
      Counter32,
   mscPppFramerUnderruns
      Counter32,
   mscPppFramerLargeFrmErrors
      Counter32 }

mscPppFramerFrmToIf OBJECT-TYPE
   SYNTAX     Counter32 
   ACCESS     read-only
   STATUS     mandatory
   DESCRIPTION
     "This attribute counts the number of frames transmitted to the link 
      interface by Framer.
      
      Note: This does not include the number of frames transmitted directly to 
      the hardware queue, thus bypassing the Framer component."
::= { mscPppFramerStatsEntry 1 }

mscPppFramerFrmFromIf OBJECT-TYPE
   SYNTAX     Counter32 
   ACCESS     read-only
   STATUS     mandatory
   DESCRIPTION
     "This attribute counts the number of frames received from the link 
      interface by Framer."
::= { mscPppFramerStatsEntry 2 }

mscPppFramerAborts OBJECT-TYPE
   SYNTAX     Counter32 
   ACCESS     read-only
   STATUS     mandatory
   DESCRIPTION
     "This attribute counts the total number of aborts received."
::= { mscPppFramerStatsEntry 3 }

mscPppFramerCrcErrors OBJECT-TYPE
   SYNTAX     Counter32 
   ACCESS     read-only
   STATUS     mandatory
   DESCRIPTION
     "This attribute counts the total number of frames with CRC errors."
::= { mscPppFramerStatsEntry 4 }

mscPppFramerLrcErrors OBJECT-TYPE
   SYNTAX     Counter32 
   ACCESS     read-only
   STATUS     mandatory
   DESCRIPTION
     "This attribute counts the total number of frames with LRC errors."
::= { mscPppFramerStatsEntry 5 }

mscPppFramerNonOctetErrors OBJECT-TYPE
   SYNTAX     Counter32 
   ACCESS     read-only
   STATUS     mandatory
   DESCRIPTION
     "This attribute counts the total number of frames that were non octet 
      aligned."
::= { mscPppFramerStatsEntry 6 }

mscPppFramerOverruns OBJECT-TYPE
   SYNTAX     Counter32 
   ACCESS     read-only
   STATUS     mandatory
   DESCRIPTION
     "This attribute counts the total number of frames received from the link 
      for which overruns occurred."
::= { mscPppFramerStatsEntry 7 }

mscPppFramerUnderruns OBJECT-TYPE
   SYNTAX     Counter32 
   ACCESS     read-only
   STATUS     mandatory
   DESCRIPTION
     "This attribute counts the total number of frames transmitted to the link 
      for which underruns occurred."
::= { mscPppFramerStatsEntry 8 }

mscPppFramerLargeFrmErrors OBJECT-TYPE
   SYNTAX     Counter32 
   ACCESS     read-only
   STATUS     mandatory
   DESCRIPTION
     "This attribute counts the total number of frames received which were too 
      large. The frame execeeded the maximumFrameLengthLimit provisioned 
      attribute or it contained more than the 255 block hardware limit."
::= { mscPppFramerStatsEntry 9 }

mscPppFramerUtilTable OBJECT-TYPE
   SYNTAX     SEQUENCE OF MscPppFramerUtilEntry
   ACCESS     not-accessible
   STATUS     mandatory
   DESCRIPTION
     "This group contains the link utilizaiton operational data for a Framer 
      component."
::= { mscPppFramer 14 }

mscPppFramerUtilEntry OBJECT-TYPE
   SYNTAX     MscPppFramerUtilEntry
   ACCESS     not-accessible
   STATUS     mandatory
   DESCRIPTION
     "An entry in the mscPppFramerUtilTable."
   INDEX {
      mscPppIndex,
      mscPppFramerIndex }
::= { mscPppFramerUtilTable 1 }

MscPppFramerUtilEntry ::= SEQUENCE {
   mscPppFramerNormPrioLinkUtilToIf
      Gauge32,
   mscPppFramerNormPrioLinkUtilFromIf
      Gauge32 }

mscPppFramerNormPrioLinkUtilToIf OBJECT-TYPE
   SYNTAX     Gauge32 (0..100)
   ACCESS     read-only
   STATUS     mandatory
   DESCRIPTION
     "This attribute is the utilization of the normal priority data sent to the link 
      as a percentage of the available bandwidth on the link. The utilization is 
      the average for the last minute."
   DEFVAL     { 0 }
::= { mscPppFramerUtilEntry 1 }

mscPppFramerNormPrioLinkUtilFromIf OBJECT-TYPE
   SYNTAX     Gauge32 (0..100)
   ACCESS     read-only
   STATUS     mandatory
   DESCRIPTION
     "This attribute is the utilization of the normal priority data received from 
      the link as a percentage of the available bandwidth on the link. The 
      utilization is the average for the last minute."
   DEFVAL     { 0 }
::= { mscPppFramerUtilEntry 3 }


-- Ppp/n LinkEmissionQueue
-- This component provides a means of statistics gathering and packet 
-- discard.

mscPppLeq OBJECT IDENTIFIER ::= { mscPpp 6 }



mscPppLeqRowStatusTable OBJECT-TYPE
   SYNTAX     SEQUENCE OF MscPppLeqRowStatusEntry
   ACCESS     not-accessible
   STATUS     mandatory
   DESCRIPTION
     "This entry controls the addition and deletion of 
      mscPppLeq components."
::= { mscPppLeq 1 }

mscPppLeqRowStatusEntry OBJECT-TYPE
   SYNTAX     MscPppLeqRowStatusEntry
   ACCESS     not-accessible
   STATUS     mandatory
   DESCRIPTION
     "A single entry in the table represents a single 
      mscPppLeq component."
   INDEX {
      mscPppIndex,
      mscPppLeqIndex }
::= { mscPppLeqRowStatusTable 1 }

MscPppLeqRowStatusEntry ::= SEQUENCE {
   mscPppLeqRowStatus
      RowStatus,
   mscPppLeqComponentName
      DisplayString,
   mscPppLeqStorageType
      StorageType,
   mscPppLeqIndex
      NonReplicated }

mscPppLeqRowStatus OBJECT-TYPE
   SYNTAX     RowStatus 
   ACCESS     read-write
   STATUS     mandatory
   DESCRIPTION
     "This variable is used as the basis for SNMP naming of
      mscPppLeq components.
      These components can be added and deleted."
::= { mscPppLeqRowStatusEntry 1 }

mscPppLeqComponentName OBJECT-TYPE
   SYNTAX     DisplayString 
   ACCESS     read-only
   STATUS     mandatory
   DESCRIPTION
     "This variable provides the component's string name for
      use with the ASCII Console Interface"
::= { mscPppLeqRowStatusEntry 2 }

mscPppLeqStorageType OBJECT-TYPE
   SYNTAX     StorageType 
   ACCESS     read-only
   STATUS     mandatory
   DESCRIPTION
     "This variable represents the storage type value for the
      mscPppLeq tables."
::= { mscPppLeqRowStatusEntry 4 }

mscPppLeqIndex OBJECT-TYPE
   SYNTAX     NonReplicated 
   ACCESS     not-accessible
   STATUS     mandatory
   DESCRIPTION
     "This variable represents the index for the mscPppLeq tables."
::= { mscPppLeqRowStatusEntry 10 }

mscPppLeqProvTable OBJECT-TYPE
   SYNTAX     SEQUENCE OF MscPppLeqProvEntry
   ACCESS     not-accessible
   STATUS     mandatory
   DESCRIPTION
     "This group contains the provisioned attributes for the 
      LinkEmissionQueue component."
::= { mscPppLeq 10 }

mscPppLeqProvEntry OBJECT-TYPE
   SYNTAX     MscPppLeqProvEntry
   ACCESS     not-accessible
   STATUS     mandatory
   DESCRIPTION
     "An entry in the mscPppLeqProvTable."
   INDEX {
      mscPppIndex,
      mscPppLeqIndex }
::= { mscPppLeqProvTable 1 }

MscPppLeqProvEntry ::= SEQUENCE {
   mscPppLeqMaxPackets
      Unsigned32,
   mscPppLeqMaxMsecData
      Unsigned32,
   mscPppLeqMaxPercentMulticast
      Unsigned32,
   mscPppLeqTimeToLive
      Unsigned32 }

mscPppLeqMaxPackets OBJECT-TYPE
   SYNTAX     Unsigned32 (0..2048)
   ACCESS     read-write
   STATUS     mandatory
   DESCRIPTION
     "This attribute specifies the maximum number of packets allowed in the 
      Leq before being discarded. If this attribute is set to zero then the 
      maximum number of packets is calculated from the transmit data rate. 
      This calculated value is placed in queuePktThreshold."
   DEFVAL     { 0 }
::= { mscPppLeqProvEntry 1 }

mscPppLeqMaxMsecData OBJECT-TYPE
   SYNTAX     Unsigned32 (100..60000)
   ACCESS     read-write
   STATUS     mandatory
   DESCRIPTION
     "This attribute specifies the maximum number of 'Milliseconds worth of 
      data' allowed in the Leq before packets are discarded. The 
      queueByteThreshold will be calculated from this attribute, based on the 
      transmit data rate."
   DEFVAL     { 10000 }
::= { mscPppLeqProvEntry 2 }

mscPppLeqMaxPercentMulticast OBJECT-TYPE
   SYNTAX     Unsigned32 (1..100)
   ACCESS     read-write
   STATUS     mandatory
   DESCRIPTION
     "This attribute specifies the maximum percentage of multicast packets 
      allowed in the Leq, based on queuePktThreshold, before being 
      discarded. The calculated value will be placed in 
      queueMulticastThreshold."
   DEFVAL     { 50 }
::= { mscPppLeqProvEntry 3 }

mscPppLeqTimeToLive OBJECT-TYPE
   SYNTAX     Unsigned32 (100..60000)
   ACCESS     read-write
   STATUS     mandatory
   DESCRIPTION
     "This attribute specifies the 'Milliseconds Time To Live' of packets in 
      the Leq. If the timeToLive of a packet expires, it will be discarded."
   DEFVAL     { 10000 }
::= { mscPppLeqProvEntry 4 }

mscPppLeqStatsTable OBJECT-TYPE
   SYNTAX     SEQUENCE OF MscPppLeqStatsEntry
   ACCESS     not-accessible
   STATUS     mandatory
   DESCRIPTION
     "This group contains Link Emission Queue general statistics."
::= { mscPppLeq 11 }

mscPppLeqStatsEntry OBJECT-TYPE
   SYNTAX     MscPppLeqStatsEntry
   ACCESS     not-accessible
   STATUS     mandatory
   DESCRIPTION
     "An entry in the mscPppLeqStatsTable."
   INDEX {
      mscPppIndex,
      mscPppLeqIndex }
::= { mscPppLeqStatsTable 1 }

MscPppLeqStatsEntry ::= SEQUENCE {
   mscPppLeqTimedOutPkt
      Counter32,
   mscPppLeqHardwareForcedPkt
      Counter32,
   mscPppLeqForcedPktDiscards
      Counter32,
   mscPppLeqQueuePurgeDiscards
      Counter32 }

mscPppLeqTimedOutPkt OBJECT-TYPE
   SYNTAX     Counter32 
   ACCESS     read-only
   STATUS     mandatory
   DESCRIPTION
     "This attribute counts the number of packets that have been discarded due 
      to exceeding the timeToLive. This counter will wrap around to 0 when it 
      exceeds its maximum count."
::= { mscPppLeqStatsEntry 1 }

mscPppLeqHardwareForcedPkt OBJECT-TYPE
   SYNTAX     Counter32 
   ACCESS     read-only
   STATUS     mandatory
   DESCRIPTION
     "This attribute counts the number of hardware forced packets on this 
      instance of Ppp. This counter will wrap around to 0 when it exceeds its 
      maximum count."
::= { mscPppLeqStatsEntry 2 }

mscPppLeqForcedPktDiscards OBJECT-TYPE
   SYNTAX     Counter32 
   ACCESS     read-only
   STATUS     mandatory
   DESCRIPTION
     "This attribute counts the total number of hardware forced packets that 
      had to be discarded due to link failure. This counter will wrap around to 
      0 when it exceeds its maximum count."
::= { mscPppLeqStatsEntry 4 }

mscPppLeqQueuePurgeDiscards OBJECT-TYPE
   SYNTAX     Counter32 
   ACCESS     read-only
   STATUS     mandatory
   DESCRIPTION
     "This attribute counts the total number of packets discarded by a queue 
      purge (i.e. a discarding of all packets on the queue). This counter will 
      wrap around to 0 when it exceeds its maximum count."
::= { mscPppLeqStatsEntry 5 }

mscPppLeqTStatsTable OBJECT-TYPE
   SYNTAX     SEQUENCE OF MscPppLeqTStatsEntry
   ACCESS     not-accessible
   STATUS     mandatory
   DESCRIPTION
     "This group contains Link Emission Queue total statistics."
::= { mscPppLeq 12 }

mscPppLeqTStatsEntry OBJECT-TYPE
   SYNTAX     MscPppLeqTStatsEntry
   ACCESS     not-accessible
   STATUS     mandatory
   DESCRIPTION
     "An entry in the mscPppLeqTStatsTable."
   INDEX {
      mscPppIndex,
      mscPppLeqIndex }
::= { mscPppLeqTStatsTable 1 }

MscPppLeqTStatsEntry ::= SEQUENCE {
   mscPppLeqTotalPktHandled
      Counter32,
   mscPppLeqTotalPktForwarded
      Counter32,
   mscPppLeqTotalPktQueued
      Counter32,
   mscPppLeqTotalMulticastPkt
      Counter32,
   mscPppLeqTotalPktDiscards
      Counter32 }

mscPppLeqTotalPktHandled OBJECT-TYPE
   SYNTAX     Counter32 
   ACCESS     read-only
   STATUS     mandatory
   DESCRIPTION
     "This attribute counts the total number of packets handled by the Leq. 
      This counter will wrap around to 0 when it exceeds its maximum count."
::= { mscPppLeqTStatsEntry 1 }

mscPppLeqTotalPktForwarded OBJECT-TYPE
   SYNTAX     Counter32 
   ACCESS     read-only
   STATUS     mandatory
   DESCRIPTION
     "This attribute counts the total number of packets forwarded by the Leq. 
      This counter will wrap around to 0 when it exceeds its maximum count."
::= { mscPppLeqTStatsEntry 2 }

mscPppLeqTotalPktQueued OBJECT-TYPE
   SYNTAX     Counter32 
   ACCESS     read-only
   STATUS     mandatory
   DESCRIPTION
     "This attribute counts the total number of packets that required queuing 
      by the Leq due to transmit congestion. This counter will wrap around to 
      0 when it exceeds its maximum count."
::= { mscPppLeqTStatsEntry 3 }

mscPppLeqTotalMulticastPkt OBJECT-TYPE
   SYNTAX     Counter32 
   ACCESS     read-only
   STATUS     mandatory
   DESCRIPTION
     "This attribute counts the total number of multicast packets handled by 
      this instance of Ppp. This counter will wrap around to 0 when it exceeds 
      its maximum count."
::= { mscPppLeqTStatsEntry 4 }

mscPppLeqTotalPktDiscards OBJECT-TYPE
   SYNTAX     Counter32 
   ACCESS     read-only
   STATUS     mandatory
   DESCRIPTION
     "This attribute counts the total number of packets that were discarded for 
      this instance of Ppp. This is the sum of timedOutPkt, forcedPktDiscards, 
      queuePurgeDiscards, pktThresholdExceeded, byteThresholdExceeded, 
      mulThresholdExceeded, and memThresholdExceeded. This counter will 
      wrap around to 0 when it exceeds its maximum count."
::= { mscPppLeqTStatsEntry 8 }

mscPppLeqCStatsTable OBJECT-TYPE
   SYNTAX     SEQUENCE OF MscPppLeqCStatsEntry
   ACCESS     not-accessible
   STATUS     mandatory
   DESCRIPTION
     "This group contains Link Emission Queue current statistics."
::= { mscPppLeq 13 }

mscPppLeqCStatsEntry OBJECT-TYPE
   SYNTAX     MscPppLeqCStatsEntry
   ACCESS     not-accessible
   STATUS     mandatory
   DESCRIPTION
     "An entry in the mscPppLeqCStatsTable."
   INDEX {
      mscPppIndex,
      mscPppLeqIndex }
::= { mscPppLeqCStatsTable 1 }

MscPppLeqCStatsEntry ::= SEQUENCE {
   mscPppLeqCurrentPktQueued
      Gauge32,
   mscPppLeqCurrentBytesQueued
      Gauge32,
   mscPppLeqCurrentMulticastQueued
      Gauge32 }

mscPppLeqCurrentPktQueued OBJECT-TYPE
   SYNTAX     Gauge32 (0..4294967295)
   ACCESS     read-only
   STATUS     mandatory
   DESCRIPTION
     "This attribute counts the current number of packets queued."
   DEFVAL     { 0 }
::= { mscPppLeqCStatsEntry 1 }

mscPppLeqCurrentBytesQueued OBJECT-TYPE
   SYNTAX     Gauge32 (0..4294967295)
   ACCESS     read-only
   STATUS     mandatory
   DESCRIPTION
     "This attribute counts the current number of bytes queued."
   DEFVAL     { 0 }
::= { mscPppLeqCStatsEntry 2 }

mscPppLeqCurrentMulticastQueued OBJECT-TYPE
   SYNTAX     Gauge32 (0..4294967295)
   ACCESS     read-only
   STATUS     mandatory
   DESCRIPTION
     "This attribute counts the current number of multicast packets in the 
      queue."
   DEFVAL     { 0 }
::= { mscPppLeqCStatsEntry 3 }

mscPppLeqThrStatsTable OBJECT-TYPE
   SYNTAX     SEQUENCE OF MscPppLeqThrStatsEntry
   ACCESS     not-accessible
   STATUS     mandatory
   DESCRIPTION
     "This group contains Link Emission Queue threshold statistics."
::= { mscPppLeq 14 }

mscPppLeqThrStatsEntry OBJECT-TYPE
   SYNTAX     MscPppLeqThrStatsEntry
   ACCESS     not-accessible
   STATUS     mandatory
   DESCRIPTION
     "An entry in the mscPppLeqThrStatsTable."
   INDEX {
      mscPppIndex,
      mscPppLeqIndex }
::= { mscPppLeqThrStatsTable 1 }

MscPppLeqThrStatsEntry ::= SEQUENCE {
   mscPppLeqQueuePktThreshold
      Unsigned32,
   mscPppLeqPktThresholdExceeded
      Counter32,
   mscPppLeqQueueByteThreshold
      Unsigned32,
   mscPppLeqByteThresholdExceeded
      Counter32,
   mscPppLeqQueueMulticastThreshold
      Unsigned32,
   mscPppLeqMulThresholdExceeded
      Counter32,
   mscPppLeqMemThresholdExceeded
      Counter32 }

mscPppLeqQueuePktThreshold OBJECT-TYPE
   SYNTAX     Unsigned32 (0..4294967295)
   ACCESS     read-only
   STATUS     mandatory
   DESCRIPTION
     "This attribute is the maximum number of packets that can be contained 
      in the queue before being discarded. If maxPackets was set to 0 then this 
      attribute will contain the value that has been calculated based on the 
      transmit data rate. If maxPackets was set to one or more than this 
      attribute will contain that number."
   DEFVAL     { 0 }
::= { mscPppLeqThrStatsEntry 1 }

mscPppLeqPktThresholdExceeded OBJECT-TYPE
   SYNTAX     Counter32 
   ACCESS     read-only
   STATUS     mandatory
   DESCRIPTION
     "This attribute counts the number of packets discarded due to the 
      queuePktThreshold being exceeded. This counter will wrap around to 0 
      when it exceeds its maximum count."
::= { mscPppLeqThrStatsEntry 2 }

mscPppLeqQueueByteThreshold OBJECT-TYPE
   SYNTAX     Unsigned32 (0..4294967295)
   ACCESS     read-only
   STATUS     mandatory
   DESCRIPTION
     "This attribute is the maximum number of bytes allowed in the queue 
      based on maxMsecData and the transmit data rate."
   DEFVAL     { 0 }
::= { mscPppLeqThrStatsEntry 3 }

mscPppLeqByteThresholdExceeded OBJECT-TYPE
   SYNTAX     Counter32 
   ACCESS     read-only
   STATUS     mandatory
   DESCRIPTION
     "This attribute counts the number of packets discarded due to the 
      queueByteThreshold being exceeded. This counter will wrap around to 0 
      when it exceeds its maximum count."
::= { mscPppLeqThrStatsEntry 4 }

mscPppLeqQueueMulticastThreshold OBJECT-TYPE
   SYNTAX     Unsigned32 (0..4294967295)
   ACCESS     read-only
   STATUS     mandatory
   DESCRIPTION
     "This attribute is the number of multicast packets allowed in the queue 
      based on maxPercentMulticast and maxPackets."
   DEFVAL     { 0 }
::= { mscPppLeqThrStatsEntry 5 }

mscPppLeqMulThresholdExceeded OBJECT-TYPE
   SYNTAX     Counter32 
   ACCESS     read-only
   STATUS     mandatory
   DESCRIPTION
     "This attribute counts the number of packets discarded due to the 
      queueMulticastThreshold being exceeded. This counter will wrap 
      around to 0 when it exceeds its maximum count."
::= { mscPppLeqThrStatsEntry 6 }

mscPppLeqMemThresholdExceeded OBJECT-TYPE
   SYNTAX     Counter32 
   ACCESS     read-only
   STATUS     mandatory
   DESCRIPTION
     "This attribute counts the number of packets discarded due to exceeding 
      the memory usage threshold for Leq. The memory usage threshold is 
      determined by the Leq software, guaranteeing that the Leq does not 
      consume all of the memory. This counter will wrap around to 0 when it 
      exceeds its maximum count."
::= { mscPppLeqThrStatsEntry 7 }




-- 
-- Version and Compliance statements
-- 



-- Object-Group Statement:
-- A list of all current accessible leaf objects.

-- OBJECTS { mscPppLnkPacketTooLongs,
--           mscPppIfAdminStatus,
--           mscPppLnkRowStatus,
--           mscPppLnkRestartTimer,
--           mscPppCustomerIdentifier,
--           mscPppFramerNonOctetErrors,
--           mscPppFramerUsageState,
--           mscPppFramerNormPrioLinkUtilFromIf,
--           mscPppNcpBRemoteToLocalLanId,
--           mscPppUsageState,
--           mscPppLnkBadFcss,
--           mscPppLnkRemoteMru,
--           mscPppFramerInterfaceName,
--           mscPppLeqStorageType,
--           mscPppLeqTotalPktQueued,
--           mscPppLeqQueuePktThreshold,
--           mscPppNcpBmEntryRemoteStatus,
--           mscPppNcpBLocalToRemoteTinygramComp,
--           mscPppFramerOperationalState,
--           mscPppNcpBOperState,
--           mscPppOperationalState,
--           mscPppNcpIpxOperState,
--           mscPppLnkTransmitFcsSize,
--           mscPppLeqPktThresholdExceeded,
--           mscPppNcpStorageType,
--           mscPppLeqQueueByteThreshold,
--           mscPppFramerLrcErrors,
--           mscPppLeqTotalPktHandled,
--           mscPppLqmComponentName,
--           mscPppFramerComponentName,
--           mscPppLeqRowStatus,
--           mscPppFramerAborts,
--           mscPppLeqMulThresholdExceeded,
--           mscPppLnkConfigureRequestTries,
--           mscPppLnkQualityWindow,
--           mscPppLinkToProtocolPort,
--           mscPppLnkLocalMru,
--           mscPppLeqTotalPktForwarded,
--           mscPppFramerFrmFromIf,
--           mscPppLeqCurrentPktQueued,
--           mscPppLeqTotalPktDiscards,
--           mscPppNcpBConfigTinygram,
--           mscPppNcpBmEntryLocalStatus,
--           mscPppNcpAppletalkOperState,
--           mscPppLeqQueueMulticastThreshold,
--           mscPppLeqMemThresholdExceeded,
--           mscPppNcpBmcEntryLocalStatus,
--           mscPppLqmRemotePeriod,
--           mscPppLeqForcedPktDiscards,
--           mscPppLnkReceiveFcsSize,
--           mscPppLeqTimeToLive,
--           mscPppFramerFrmToIf,
--           mscPppLeqQueuePurgeDiscards,
--           mscPppNcpBmEntryComponentName,
--           mscPppLnkQualityThreshold,
--           mscPppNcpBmcEntryRowStatus,
--           mscPppNcpBmcEntryComponentName,
--           mscPppFramerOverruns,
--           mscPppLeqTotalMulticastPkt,
--           mscPppLnkConfigInitialMru,
--           mscPppLqmConfigStatus,
--           mscPppLqmLocalPeriod,
--           mscPppNcpXnsOperState,
--           mscPppLeqMaxMsecData,
--           mscPppComponentName,
--           mscPppLnkComponentName,
--           mscPppFramerUnderruns,
--           mscPppLeqCurrentBytesQueued,
--           mscPppLqmRowStatus,
--           mscPppLqmStorageType,
--           mscPppLqmOutLqrs,
--           mscPppLeqMaxPackets,
--           mscPppAdminState,
--           mscPppNcpIpOperState,
--           mscPppLnkConfigMagicNumber,
--           mscPppNcpRowStatus,
--           mscPppLeqMaxPercentMulticast,
--           mscPppNcpBmEntryStorageType,
--           mscPppLnkTerminateRequestTries,
--           mscPppLnkContinuityMonitor,
--           mscPppLeqHardwareForcedPkt,
--           mscPppLnkOperState,
--           mscPppNcpDecnetOperState,
--           mscPppLeqByteThresholdExceeded,
--           mscPppLnkBadControls,
--           mscPppLnkNegativeAckTries,
--           mscPppSnmpOperStatus,
--           mscPppIfIndex,
--           mscPppFramerNormPrioLinkUtilToIf,
--           mscPppLeqComponentName,
--           mscPppLeqTimedOutPkt,
--           mscPppNcpBLocalToRemoteLanId,
--           mscPppLnkBadAddresses,
--           mscPppFramerStorageType,
--           mscPppRowStatus,
--           mscPppNcpBmEntryRowStatus,
--           mscPppLqmInLqrs,
--           mscPppFramerCrcErrors,
--           mscPppStorageType,
--           mscPppLnkStorageType,
--           mscPppNcpBmcEntryStorageType,
--           mscPppNcpBRemoteToLocalTinygramComp,
--           mscPppNcpComponentName,
--           mscPppLeqCurrentMulticastQueued,
--           mscPppLqmQuality,
--           mscPppFramerAdminState,
--           mscPppNcpBConfigLanId,
--           mscPppFramerLargeFrmErrors,
--           mscPppLnkLineCondition,
--           mscPppFramerRowStatus,
--           mscPppLqmConfigPeriod,
--           mscPppLqmInGoodOctets }
-- STATUS  mandatory
-- DESCRIPTION
--   "A list of all current accessible leaf objects."

pppGroup OBJECT IDENTIFIER ::= { pppMIB 1 }
pppGroupCA OBJECT IDENTIFIER ::= { pppGroup 1 }
pppGroupCA02 OBJECT IDENTIFIER ::= { pppGroupCA 3 }
pppGroupCA02A OBJECT IDENTIFIER ::= { pppGroupCA02 2 }



-- Agent-Capabilities Statement:

-- PRODUCT-RELEASE "MscPassport Release 1.2 Ppp."
-- STATUS          mandatory
-- DESCRIPTION     "Carrier Passport Ppp MIB: MIB Version CA02A,
--                  Software Version CA02S9C."
-- SUPPORTS        Nortel-MsCarrier-MscPassport-PppMIB
--    INCLUDES     { pppGroupCA02A }
--        rfc1471 (Link Control Protocol of the Point-to-Point Protocol)
-- 
-- SUPPORTS RFC1471-MIB
--    INCLUDES	{ pppLinkStatusTable, pppLinkConfigTable, pppLqrTable, 
--       	  pppLqrConfigTable }  
--    			   pppLqrExtnsTable, pppEchoTest, and
--       		   pppDiscardTest are not supported.
-- 
--       variations for pppLinkConfigTable
-- 
--    VARIATION		pppLinkConfigInitialMRU
--       SYNTAX		INTEGER (68..18000)
--       DEFVAL		{ 18000 }
--       DESCRIPTION	"Packets smaller than 68 bytes or larger than 18000
--          		bytes can not be supported.  This implementation
--         		will default the pppLinkConfigInitialMRU to 18000."
-- 
--    VARIATION		pppLinkConfigReceiveACCMap
--       DEFVAL		{ '00000000'h }
--       DESCRIPTION	"ACC map is not supported by this implementation."
-- 
-- 
--    VARIATION		pppLinkConfigTransmitACCMap
--       DEFVAL		{ '00000000'h }
--       DESCRIPTION	"ACC map is not supported by this implementation."
-- 
--    VARIATION		pppLinkConfigMagicNumber
--       DEFVAL		{ true }
--       DESCRIPTION	"This implementation will default
--          		 pppLinkConfigMagicNumber to true."
-- 
--    VARIATION		pppLinkConfigFcsSize
--       SYNTAX    	INTEGER (16)
--       DESCRIPTION	"Only 16 bit crc is supported by this implementation."
-- 
--       variations for pppLqrConfigTable
-- 
--    VARIATION		pppLqrConfigStatus
--       DEFVAL		{ disabled }
--       DESCRIPTION	"This implementation will default pppLqrConfigStatus 
--       		to disabled."
-- 
--  
--       rfc1472 (Security Protocols of the Point-to-Point Protocol are
--                not supported)
-- 
--       rfc1473 (IP Network Control Protocol of the Point-to-Point Protocol)
-- 
--    SUPPORTS RFC1473-MIB
--       INCLUDES	{ pppIpTable, pppIpConfigTable }
-- 
--       variations for pppIpConfigTable
-- 
--    VARIATION		pppIpConfigCompression
--       WRITE-SYNTAX	INTEGER { none(1) }
--       DESCRIPTION	"No IP compression is supported by this implementation."
-- 
-- 
-- 
--       rfc1474 (Bridge Network Control Protocol of the Point-to-Point Protocol)
-- 
--    SUPPORTS RFC1474-MIB
--       INCLUDES	{ pppBridgeTable, pppBridgeConfigTable,
--       		  pppBridgeMediaTable, pppBridgeMediaConfigTable }
-- 
--       variations for pppBridgeConfigTable
-- 
--    VARIATION		pppBridgeConfigRingId
--       WRITE-SYNTAX	INTEGER { false(1) }
--       DESCRIPTION	"Remote Ring Identification Option negotiation is not
--       		supported by this implementation."
-- 
--    VARIATION		pppBridgeConfigLineId
--       WRITE-SYNTAX	INTEGER { false(1) }
--       DESCRIPTION	"Line Identification Option negotiation is not 
--                         supported by this implementation."
-- 
--    VARIATION		pppBridgeConfigLanId
--       DEFVAL		{ true }
--       DESCRIPTION	"This implementation will initiate negotiation of this
--       		        option by default."
-- 
--       variations for pppBridgeMediaConfigTable
-- 
--    VARIATION		pppBridgeMediaConfigMacType
--       ACCESS		read-only
--       DESCRIPTION	"This implementation does not allow writes to the 
--       	        	pppBridgeMediaConfigMacType."
-- 
--    VARIATION		pppBridgeMediaConfigLocalStatus
--       WRITE-SYNTAX	INTEGER { accept(1) }
--       DESCRIPTION	"This implementation does not allow packets to be
--         		selectively accepted based on Mac type."
-- 

pppCapabilities OBJECT IDENTIFIER ::= { pppMIB 3 }
pppCapabilitiesCA OBJECT IDENTIFIER ::= { pppCapabilities 1 }
pppCapabilitiesCA02 OBJECT IDENTIFIER ::= { pppCapabilitiesCA 3 }
pppCapabilitiesCA02A OBJECT IDENTIFIER ::= { pppCapabilitiesCA02 2 }





END
