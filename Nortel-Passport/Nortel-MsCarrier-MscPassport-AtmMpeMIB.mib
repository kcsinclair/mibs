Nortel-MsCarrier-MscPassport-AtmMpeMIB
DEFINITIONS ::= BEGIN



IMPORTS

      OBJECT-TYPE
   FROM RFC-1212

      mscPassportMIBs,
      mscComponents
   FROM Nortel-MsCarrier-MscPassport-UsefulDefinitionsMIB

      Counter32,
      DisplayString,
      StorageType,
      RowStatus,
      InterfaceIndex,
      Integer32,
      Unsigned32
   FROM Nortel-MsCarrier-MscPassport-StandardTextualConventionsMIB

      Link
   FROM Nortel-MsCarrier-MscPassport-TextualConventionsMIB;




-- LAST-UPDATED   "9909010000Z"
-- ORGANIZATION   "Nortel Networks"
-- CONTACT-INFO   "
--         Nortel Carrier Data Network Management
--         
--         Postal:       P.O. Box 3511, Station C 
--                       Ottawa, Ontario 
--                       Canada  K1Y 4H7
--         
--         via the WEB:  http://www.nortelnetworks.com  
--                       select 'Contact Us' from the menu
--          
--         via phone:    1-800-4NORTEL"
-- DESCRIPTION
--    "The module describing the Nortel MsCarrier MscPassport
--     AtmMpe Enterprise MIB."

atmMpeMIB OBJECT IDENTIFIER ::= { mscPassportMIBs 65 }










-- AtmMpe/n
-- This component represents a logical interface between the Virtual 
-- Router and an ATM media (AtmIf). Multiprotocol Encapsulation as 
-- specified in RFC1483 is used to transfer higher-layer protocol data 
-- across virtual channels in an ATM network. AtmMpes provide a 
-- means to associate multiple ATM virtual channel connections with a 
-- single VirtualRouter ProtocolPort. The AtmMpe component is 
-- associated with a ProtocolPort via a linkage attribute and virtual 
-- channel connections via a linkage attribute in each AtmConnection 
-- subcomponent.

mscAtmMpe OBJECT IDENTIFIER ::= { mscComponents 118 }



mscAtmMpeRowStatusTable OBJECT-TYPE
   SYNTAX     SEQUENCE OF MscAtmMpeRowStatusEntry
   ACCESS     not-accessible
   STATUS     mandatory
   DESCRIPTION
     "This entry controls the addition and deletion of 
      mscAtmMpe components."
::= { mscAtmMpe 1 }

mscAtmMpeRowStatusEntry OBJECT-TYPE
   SYNTAX     MscAtmMpeRowStatusEntry
   ACCESS     not-accessible
   STATUS     mandatory
   DESCRIPTION
     "A single entry in the table represents a single 
      mscAtmMpe component."
   INDEX {
      mscAtmMpeIndex }
::= { mscAtmMpeRowStatusTable 1 }

MscAtmMpeRowStatusEntry ::= SEQUENCE {
   mscAtmMpeRowStatus
      RowStatus,
   mscAtmMpeComponentName
      DisplayString,
   mscAtmMpeStorageType
      StorageType,
   mscAtmMpeIndex
      Integer32 }

mscAtmMpeRowStatus OBJECT-TYPE
   SYNTAX     RowStatus 
   ACCESS     read-write
   STATUS     mandatory
   DESCRIPTION
     "This variable is used as the basis for SNMP naming of
      mscAtmMpe components.
      These components can be added and deleted."
::= { mscAtmMpeRowStatusEntry 1 }

mscAtmMpeComponentName OBJECT-TYPE
   SYNTAX     DisplayString 
   ACCESS     read-only
   STATUS     mandatory
   DESCRIPTION
     "This variable provides the component's string name for
      use with the ASCII Console Interface"
::= { mscAtmMpeRowStatusEntry 2 }

mscAtmMpeStorageType OBJECT-TYPE
   SYNTAX     StorageType 
   ACCESS     read-only
   STATUS     mandatory
   DESCRIPTION
     "This variable represents the storage type value for the
      mscAtmMpe tables."
::= { mscAtmMpeRowStatusEntry 4 }

mscAtmMpeIndex OBJECT-TYPE
   SYNTAX     Integer32 (0..255)
   ACCESS     not-accessible
   STATUS     mandatory
   DESCRIPTION
     "This variable represents the index for the mscAtmMpe tables."
::= { mscAtmMpeRowStatusEntry 10 }

mscAtmMpeCidDataTable OBJECT-TYPE
   SYNTAX     SEQUENCE OF MscAtmMpeCidDataEntry
   ACCESS     not-accessible
   STATUS     mandatory
   DESCRIPTION
     "This group contains the attribute for a component's Customer 
      Identifier (CID). Refer to the attribute description for a detailed 
      explanation of CIDs."
::= { mscAtmMpe 10 }

mscAtmMpeCidDataEntry OBJECT-TYPE
   SYNTAX     MscAtmMpeCidDataEntry
   ACCESS     not-accessible
   STATUS     mandatory
   DESCRIPTION
     "An entry in the mscAtmMpeCidDataTable."
   INDEX {
      mscAtmMpeIndex }
::= { mscAtmMpeCidDataTable 1 }

MscAtmMpeCidDataEntry ::= SEQUENCE {
   mscAtmMpeCustomerIdentifier
      Unsigned32 }

mscAtmMpeCustomerIdentifier OBJECT-TYPE
   SYNTAX     Unsigned32 (0 | 1..8191)
   ACCESS     read-write
   STATUS     mandatory
   DESCRIPTION
     "This attribute holds the Customer Identifier (CID).
      
      Every component has a CID. If a component has a cid attribute, the 
      component's CID is the provisioned value of that attribute; 
      otherwise the component inherits the CID of its parent. The top-
      level component has a CID of 0.
      
      Every operator session also has a CID, which is the CID 
      provisioned for the operator's user ID. An operator will see only the 
      stream data for components having a matching CID. Also, the 
      operator will be allowed to issue commands for only those 
      components which have a matching CID.
      
      An operator CID of 0 is used to identify the Network Manager 
      (referred to as 'NetMan' in DPN). This CID matches the CID of 
      any component. Values 1 to 8191 inclusive (equivalent to 'basic 
      CIDs' in DPN) may be assigned to specific customers."
   DEFVAL     { 0 }
::= { mscAtmMpeCidDataEntry 1 }

mscAtmMpeIfEntryTable OBJECT-TYPE
   SYNTAX     SEQUENCE OF MscAtmMpeIfEntryEntry
   ACCESS     not-accessible
   STATUS     mandatory
   DESCRIPTION
     "This group contains the provisionable attributes for the ifEntry."
::= { mscAtmMpe 11 }

mscAtmMpeIfEntryEntry OBJECT-TYPE
   SYNTAX     MscAtmMpeIfEntryEntry
   ACCESS     not-accessible
   STATUS     mandatory
   DESCRIPTION
     "An entry in the mscAtmMpeIfEntryTable."
   INDEX {
      mscAtmMpeIndex }
::= { mscAtmMpeIfEntryTable 1 }

MscAtmMpeIfEntryEntry ::= SEQUENCE {
   mscAtmMpeIfAdminStatus
      INTEGER,
   mscAtmMpeIfIndex
      InterfaceIndex }

mscAtmMpeIfAdminStatus OBJECT-TYPE
   SYNTAX     INTEGER  {
                 up(1),
                 down(2),
                 testing(3) }
   ACCESS     read-write
   STATUS     mandatory
   DESCRIPTION
     "The desired state of the interface. The up state indicates the 
      interface is operational. The down state indicates the interface is not 
      operational. The testing state indicates that no operational packets 
      can be passed."
   DEFVAL     { up }
::= { mscAtmMpeIfEntryEntry 1 }

mscAtmMpeIfIndex OBJECT-TYPE
   SYNTAX     InterfaceIndex (1..65535)
   ACCESS     read-only
   STATUS     mandatory
   DESCRIPTION
     "This is the index for the IfEntry. Its value is automatically initialized 
      during the provisioning process."
::= { mscAtmMpeIfEntryEntry 2 }

mscAtmMpeProvTable OBJECT-TYPE
   SYNTAX     SEQUENCE OF MscAtmMpeProvEntry
   ACCESS     not-accessible
   STATUS     mandatory
   DESCRIPTION
     "This group contains the provisioned attributes for the AtmMpe 
      component."
::= { mscAtmMpe 12 }

mscAtmMpeProvEntry OBJECT-TYPE
   SYNTAX     MscAtmMpeProvEntry
   ACCESS     not-accessible
   STATUS     mandatory
   DESCRIPTION
     "An entry in the mscAtmMpeProvTable."
   INDEX {
      mscAtmMpeIndex }
::= { mscAtmMpeProvTable 1 }

MscAtmMpeProvEntry ::= SEQUENCE {
   mscAtmMpeMaxTransmissionUnit
      Unsigned32,
   mscAtmMpeEncapType
      INTEGER,
   mscAtmMpeIlsForwarder
      Link }

mscAtmMpeMaxTransmissionUnit OBJECT-TYPE
   SYNTAX     Unsigned32 (256..9188)
   ACCESS     read-write
   STATUS     mandatory
   DESCRIPTION
     "This attribute sets the size of the largest datagram which can be sent 
      on the interface. This includes the size of the Logical Link Control 
      header (if applicable) as well as the protocol data unit."
   DEFVAL     { 9188 }
::= { mscAtmMpeProvEntry 1 }

mscAtmMpeEncapType OBJECT-TYPE
   SYNTAX     INTEGER  {
                 llcEncap(1),
                 ipVcEncap(2),
                 ipxVcEncap(3) }
   ACCESS     read-write
   STATUS     mandatory
   DESCRIPTION
     "This attribute specifies the rfc1483 encapsulation type to be used for 
      the AtmConnections under this AtmMpe. Specifying llcEncap 
      allows multiplexing of multiple protocols over the VCCs. The 
      protocol of the carried PDU will be identified by an IEEE 802.2 
      Logical Link Control header. If Bridging or Inverse ARP is to be 
      carried over a VCC, llcEncap must be used. Specifying ipVcEncap 
      or ipxVcEncap indicates that all the VCCs (i.e. AtmConnections) 
      under an AtmMpe component will use VC based multiplexing and 
      will carry IP or IPX PDUs only. Thus an IpxPort cannot be 
      provisioned under a protocol port linked to an AtmMpe component 
      with encapsulation type of ipVcEncap. Similarly, an IpPort cannot 
      be provisioned under a protocol port linked to an AtmMpe 
      component with encapsulation type of ipxVcEncap."
   DEFVAL     { llcEncap }
::= { mscAtmMpeProvEntry 2 }

mscAtmMpeIlsForwarder OBJECT-TYPE
   SYNTAX     Link 
   ACCESS     read-write
   STATUS     mandatory
   DESCRIPTION
     "This attribute specifies the IlsForwarder component this AtmMpe 
      component is using."
::= { mscAtmMpeProvEntry 3 }

mscAtmMpeMediaProvTable OBJECT-TYPE
   SYNTAX     SEQUENCE OF MscAtmMpeMediaProvEntry
   ACCESS     not-accessible
   STATUS     mandatory
   DESCRIPTION
     "This group contains the base provisioning data for the Atm Mpe 
      component."
::= { mscAtmMpe 13 }

mscAtmMpeMediaProvEntry OBJECT-TYPE
   SYNTAX     MscAtmMpeMediaProvEntry
   ACCESS     not-accessible
   STATUS     mandatory
   DESCRIPTION
     "An entry in the mscAtmMpeMediaProvTable."
   INDEX {
      mscAtmMpeIndex }
::= { mscAtmMpeMediaProvTable 1 }

MscAtmMpeMediaProvEntry ::= SEQUENCE {
   mscAtmMpeLinkToProtocolPort
      Link }

mscAtmMpeLinkToProtocolPort OBJECT-TYPE
   SYNTAX     Link 
   ACCESS     read-write
   STATUS     mandatory
   DESCRIPTION
     "This attribute contains a protocol port component name. The 
      attribute associates an AtmMpe application with a protocol port."
::= { mscAtmMpeMediaProvEntry 1 }

mscAtmMpeStateTable OBJECT-TYPE
   SYNTAX     SEQUENCE OF MscAtmMpeStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscAtmMpe 14 }

mscAtmMpeStateEntry OBJECT-TYPE
   SYNTAX     MscAtmMpeStateEntry
   ACCESS     not-accessible
   STATUS     mandatory
   DESCRIPTION
     "An entry in the mscAtmMpeStateTable."
   INDEX {
      mscAtmMpeIndex }
::= { mscAtmMpeStateTable 1 }

MscAtmMpeStateEntry ::= SEQUENCE {
   mscAtmMpeAdminState
      INTEGER,
   mscAtmMpeOperationalState
      INTEGER,
   mscAtmMpeUsageState
      INTEGER }

mscAtmMpeAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscAtmMpeStateEntry 1 }

mscAtmMpeOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscAtmMpeStateEntry 2 }

mscAtmMpeUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscAtmMpeStateEntry 3 }

mscAtmMpeOperStatusTable OBJECT-TYPE
   SYNTAX     SEQUENCE OF MscAtmMpeOperStatusEntry
   ACCESS     not-accessible
   STATUS     mandatory
   DESCRIPTION
     "This group includes the Operational Status attribute. This attribute 
      defines the current operational state of this component."
::= { mscAtmMpe 15 }

mscAtmMpeOperStatusEntry OBJECT-TYPE
   SYNTAX     MscAtmMpeOperStatusEntry
   ACCESS     not-accessible
   STATUS     mandatory
   DESCRIPTION
     "An entry in the mscAtmMpeOperStatusTable."
   INDEX {
      mscAtmMpeIndex }
::= { mscAtmMpeOperStatusTable 1 }

MscAtmMpeOperStatusEntry ::= SEQUENCE {
   mscAtmMpeSnmpOperStatus
      INTEGER }

mscAtmMpeSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { mscAtmMpeOperStatusEntry 1 }


-- AtmMpe/n Ac/n
-- This component represents a virtual channel through which 
-- internetworking frames will be transported using rfc1483 
-- encapsulation. The AtmConnection component contains OSI state 
-- information, frame based statistics, and the linkage to an ATM 
-- virtual channel connection. This component's instance value is used 
-- by higher-layer protocols when referring to a specific ATM 
-- connection.

mscAtmMpeAc OBJECT IDENTIFIER ::= { mscAtmMpe 2 }



mscAtmMpeAcRowStatusTable OBJECT-TYPE
   SYNTAX     SEQUENCE OF MscAtmMpeAcRowStatusEntry
   ACCESS     not-accessible
   STATUS     mandatory
   DESCRIPTION
     "This entry controls the addition and deletion of 
      mscAtmMpeAc components."
::= { mscAtmMpeAc 1 }

mscAtmMpeAcRowStatusEntry OBJECT-TYPE
   SYNTAX     MscAtmMpeAcRowStatusEntry
   ACCESS     not-accessible
   STATUS     mandatory
   DESCRIPTION
     "A single entry in the table represents a single 
      mscAtmMpeAc component."
   INDEX {
      mscAtmMpeIndex,
      mscAtmMpeAcIndex }
::= { mscAtmMpeAcRowStatusTable 1 }

MscAtmMpeAcRowStatusEntry ::= SEQUENCE {
   mscAtmMpeAcRowStatus
      RowStatus,
   mscAtmMpeAcComponentName
      DisplayString,
   mscAtmMpeAcStorageType
      StorageType,
   mscAtmMpeAcIndex
      Integer32 }

mscAtmMpeAcRowStatus OBJECT-TYPE
   SYNTAX     RowStatus 
   ACCESS     read-write
   STATUS     mandatory
   DESCRIPTION
     "This variable is used as the basis for SNMP naming of
      mscAtmMpeAc components.
      These components can be added and deleted."
::= { mscAtmMpeAcRowStatusEntry 1 }

mscAtmMpeAcComponentName OBJECT-TYPE
   SYNTAX     DisplayString 
   ACCESS     read-only
   STATUS     mandatory
   DESCRIPTION
     "This variable provides the component's string name for
      use with the ASCII Console Interface"
::= { mscAtmMpeAcRowStatusEntry 2 }

mscAtmMpeAcStorageType OBJECT-TYPE
   SYNTAX     StorageType 
   ACCESS     read-only
   STATUS     mandatory
   DESCRIPTION
     "This variable represents the storage type value for the
      mscAtmMpeAc tables."
::= { mscAtmMpeAcRowStatusEntry 4 }

mscAtmMpeAcIndex OBJECT-TYPE
   SYNTAX     Integer32 (1..255)
   ACCESS     not-accessible
   STATUS     mandatory
   DESCRIPTION
     "This variable represents the index for the mscAtmMpeAc tables."
::= { mscAtmMpeAcRowStatusEntry 10 }

mscAtmMpeAcProvTable OBJECT-TYPE
   SYNTAX     SEQUENCE OF MscAtmMpeAcProvEntry
   ACCESS     not-accessible
   STATUS     mandatory
   DESCRIPTION
     "This group contains the provisioned attributes for the 
      AtmConnection component."
::= { mscAtmMpeAc 10 }

mscAtmMpeAcProvEntry OBJECT-TYPE
   SYNTAX     MscAtmMpeAcProvEntry
   ACCESS     not-accessible
   STATUS     mandatory
   DESCRIPTION
     "An entry in the mscAtmMpeAcProvTable."
   INDEX {
      mscAtmMpeIndex,
      mscAtmMpeAcIndex }
::= { mscAtmMpeAcProvTable 1 }

MscAtmMpeAcProvEntry ::= SEQUENCE {
   mscAtmMpeAcAtmConnection
      Link,
   mscAtmMpeAcIpCoS
      Unsigned32 }

mscAtmMpeAcAtmConnection OBJECT-TYPE
   SYNTAX     Link 
   ACCESS     read-write
   STATUS     mandatory
   DESCRIPTION
     "This attribute specifies the Atm nailed up endpoint, AtmIf/n Vcc/
      vpi.vci Nep, that this connection is associated with."
::= { mscAtmMpeAcProvEntry 1 }

mscAtmMpeAcIpCoS OBJECT-TYPE
   SYNTAX     Unsigned32 (0..3)
   ACCESS     read-write
   STATUS     mandatory
   DESCRIPTION
     "This attribute specifies the Class of Service (CoS) given to each 
      packet received on an ATM connection.
      
      The initial CoS given to a packet may be overridden when the 
      cosPolicyAssignment attribute is defined on either the IpPort 
      component of the ProtocolPort linked to the ATM MPE or the Ip 
      component of the protocol port's VirtualRouter.
      
      When a packet is to be transmitted on an ATM MPE protocol port 
      where multiple connections are available for the packet's next hop, 
      the packet is forwarded on the connection where the ipCos value 
      matches the CoS of the packet. When the packets' CoS does not 
      match the ipCos value of any of the available connections, the 
      packet is forwarded using next lowest CoS; failing this, the packet 
      is forwarded using the next highest CoS."
   DEFVAL     { 0 }
::= { mscAtmMpeAcProvEntry 2 }

mscAtmMpeAcStateTable OBJECT-TYPE
   SYNTAX     SEQUENCE OF MscAtmMpeAcStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscAtmMpeAc 11 }

mscAtmMpeAcStateEntry OBJECT-TYPE
   SYNTAX     MscAtmMpeAcStateEntry
   ACCESS     not-accessible
   STATUS     mandatory
   DESCRIPTION
     "An entry in the mscAtmMpeAcStateTable."
   INDEX {
      mscAtmMpeIndex,
      mscAtmMpeAcIndex }
::= { mscAtmMpeAcStateTable 1 }

MscAtmMpeAcStateEntry ::= SEQUENCE {
   mscAtmMpeAcAdminState
      INTEGER,
   mscAtmMpeAcOperationalState
      INTEGER,
   mscAtmMpeAcUsageState
      INTEGER }

mscAtmMpeAcAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscAtmMpeAcStateEntry 1 }

mscAtmMpeAcOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscAtmMpeAcStateEntry 2 }

mscAtmMpeAcUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscAtmMpeAcStateEntry 3 }

mscAtmMpeAcOperTable OBJECT-TYPE
   SYNTAX     SEQUENCE OF MscAtmMpeAcOperEntry
   ACCESS     not-accessible
   STATUS     mandatory
   DESCRIPTION
     "This group contains the operational attributes for the 
      AtmConnection component."
::= { mscAtmMpeAc 12 }

mscAtmMpeAcOperEntry OBJECT-TYPE
   SYNTAX     MscAtmMpeAcOperEntry
   ACCESS     not-accessible
   STATUS     mandatory
   DESCRIPTION
     "An entry in the mscAtmMpeAcOperTable."
   INDEX {
      mscAtmMpeIndex,
      mscAtmMpeAcIndex }
::= { mscAtmMpeAcOperTable 1 }

MscAtmMpeAcOperEntry ::= SEQUENCE {
   mscAtmMpeAcSpeed
      Counter32 }

mscAtmMpeAcSpeed OBJECT-TYPE
   SYNTAX     Counter32 
   ACCESS     read-only
   STATUS     mandatory
   DESCRIPTION
     "This attribute indicates the approximate bit rate for the connection. 
      The bit rate is determined from the cell rate provisioned for the Vcc 
      linked to this connection. The cell rate is multiplied by 53 bytes per 
      cell and 8 bits per byte to obtain the bit rate. The ifSpeed of the 
      entry in the ifTable corresponding to the AtmMpe component is the 
      lowest speed of all the connections associated with the AtmMpe 
      component."
::= { mscAtmMpeAcOperEntry 1 }

mscAtmMpeAcStatsTable OBJECT-TYPE
   SYNTAX     SEQUENCE OF MscAtmMpeAcStatsEntry
   ACCESS     not-accessible
   STATUS     mandatory
   DESCRIPTION
     "This group contains the frame based statistics maintained for the 
      AtmConnection component. For cell based statistics, see the Vcc 
      component."
::= { mscAtmMpeAc 13 }

mscAtmMpeAcStatsEntry OBJECT-TYPE
   SYNTAX     MscAtmMpeAcStatsEntry
   ACCESS     not-accessible
   STATUS     mandatory
   DESCRIPTION
     "An entry in the mscAtmMpeAcStatsTable."
   INDEX {
      mscAtmMpeIndex,
      mscAtmMpeAcIndex }
::= { mscAtmMpeAcStatsTable 1 }

MscAtmMpeAcStatsEntry ::= SEQUENCE {
   mscAtmMpeAcOutPackets
      Counter32,
   mscAtmMpeAcOutOctets
      Counter32,
   mscAtmMpeAcOutDiscards
      Counter32,
   mscAtmMpeAcInPackets
      Counter32,
   mscAtmMpeAcInOctets
      Counter32,
   mscAtmMpeAcInUnknownProtos
      Counter32,
   mscAtmMpeAcInErrors
      Counter32 }

mscAtmMpeAcOutPackets OBJECT-TYPE
   SYNTAX     Counter32 
   ACCESS     read-only
   STATUS     mandatory
   DESCRIPTION
     "This attribute counts the total number of packets sent on this 
      connection. This counter will wrap around to 0 when it exceeds its 
      maximum count."
::= { mscAtmMpeAcStatsEntry 1 }

mscAtmMpeAcOutOctets OBJECT-TYPE
   SYNTAX     Counter32 
   ACCESS     read-only
   STATUS     mandatory
   DESCRIPTION
     "This attribute counts the total number of octets sent on this 
      connection. This counter will wrap around to 0 when it exceeds its 
      maximum count.
      DESCRIPTION"
::= { mscAtmMpeAcStatsEntry 2 }

mscAtmMpeAcOutDiscards OBJECT-TYPE
   SYNTAX     Counter32 
   ACCESS     read-only
   STATUS     mandatory
   DESCRIPTION
     "This attribute counts the total number of packets which were 
      supposed to be sent on this connection but were discarded due to 
      congestion or the connection being down. This counter will wrap 
      around to 0 when it exceeds its maximum count.
      DESCRIPTION"
::= { mscAtmMpeAcStatsEntry 3 }

mscAtmMpeAcInPackets OBJECT-TYPE
   SYNTAX     Counter32 
   ACCESS     read-only
   STATUS     mandatory
   DESCRIPTION
     "This attribute counts the total number of packets received on this 
      connection. This counter will wrap around to 0 when it exceeds its 
      maximum count.
      DESCRIPTION"
::= { mscAtmMpeAcStatsEntry 4 }

mscAtmMpeAcInOctets OBJECT-TYPE
   SYNTAX     Counter32 
   ACCESS     read-only
   STATUS     mandatory
   DESCRIPTION
     "The attribute counts the total number of octets received on this 
      connection. This counter will wrap around to 0 when it exceeds its 
      maximum count.
      DESCRIPTION"
::= { mscAtmMpeAcStatsEntry 5 }

mscAtmMpeAcInUnknownProtos OBJECT-TYPE
   SYNTAX     Counter32 
   ACCESS     read-only
   STATUS     mandatory
   DESCRIPTION
     "This attribute counts the total number of packets received on this 
      connection which were discarded because they contained an 
      unknown or unsupported protocol (includes packets received for 
      protocols not currently bound to the associated ProtocolPort 
      component). This counter will wrap around to 0 when it exceeds its 
      maximum count.
      DESCRIPTION"
::= { mscAtmMpeAcStatsEntry 6 }

mscAtmMpeAcInErrors OBJECT-TYPE
   SYNTAX     Counter32 
   ACCESS     read-only
   STATUS     mandatory
   DESCRIPTION
     "This attribute counts the total number of packets received on the 
      connection which contained errors preventing them from being 
      delivered to a higher-layer protocol (includes short frames). This 
      counter will wrap around to 0 when it exceeds its maximum count.
      DESCRIPTION"
::= { mscAtmMpeAcStatsEntry 7 }




-- 
-- Version and Compliance statements
-- 



-- Object-Group Statement:
-- A list of all current accessible leaf objects.

-- OBJECTS { mscAtmMpeComponentName,
--           mscAtmMpeLinkToProtocolPort,
--           mscAtmMpeAcInOctets,
--           mscAtmMpeIfAdminStatus,
--           mscAtmMpeAcInPackets,
--           mscAtmMpeCustomerIdentifier,
--           mscAtmMpeAcUsageState,
--           mscAtmMpeEncapType,
--           mscAtmMpeAcOutOctets,
--           mscAtmMpeSnmpOperStatus,
--           mscAtmMpeAcOutPackets,
--           mscAtmMpeUsageState,
--           mscAtmMpeAcStorageType,
--           mscAtmMpeIfIndex,
--           mscAtmMpeIlsForwarder,
--           mscAtmMpeAcOperationalState,
--           mscAtmMpeAcInUnknownProtos,
--           mscAtmMpeStorageType,
--           mscAtmMpeRowStatus,
--           mscAtmMpeMaxTransmissionUnit,
--           mscAtmMpeAcSpeed,
--           mscAtmMpeOperationalState,
--           mscAtmMpeAcOutDiscards,
--           mscAtmMpeAcAdminState,
--           mscAtmMpeAcComponentName,
--           mscAtmMpeAcInErrors,
--           mscAtmMpeAcIpCoS,
--           mscAtmMpeAcAtmConnection,
--           mscAtmMpeAcRowStatus,
--           mscAtmMpeAdminState }
-- STATUS  mandatory
-- DESCRIPTION
--   "A list of all current accessible leaf objects."

atmMpeGroup OBJECT IDENTIFIER ::= { atmMpeMIB 1 }
atmMpeGroupCA OBJECT IDENTIFIER ::= { atmMpeGroup 1 }
atmMpeGroupCA02 OBJECT IDENTIFIER ::= { atmMpeGroupCA 3 }
atmMpeGroupCA02A OBJECT IDENTIFIER ::= { atmMpeGroupCA02 2 }



-- Agent-Capabilities Statement:

-- PRODUCT-RELEASE "MscPassport Release 1.2 AtmMpe."
-- STATUS          mandatory
-- DESCRIPTION     "Carrier Passport AtmMpe MIB: MIB Version CA02A,
--                  Software Version CA02S9C."
-- SUPPORTS        Nortel-MsCarrier-MscPassport-AtmMpeMIB
--    INCLUDES     { atmMpeGroupCA02A }

atmMpeCapabilities OBJECT IDENTIFIER ::= { atmMpeMIB 3 }
atmMpeCapabilitiesCA OBJECT IDENTIFIER ::= { atmMpeCapabilities 1 }
atmMpeCapabilitiesCA02 OBJECT IDENTIFIER ::= { atmMpeCapabilitiesCA 3 }
atmMpeCapabilitiesCA02A OBJECT IDENTIFIER ::= { atmMpeCapabilitiesCA02 2 }





END
