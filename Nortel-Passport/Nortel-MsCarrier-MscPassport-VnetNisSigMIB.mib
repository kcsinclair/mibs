Nortel-MsCarrier-MscPassport-VnetNisSigMIB
DEFINITIONS ::= BEGIN



IMPORTS

      OBJECT-TYPE
   FROM RFC-1212

      mscPassportMIBs
   FROM Nortel-MsCarrier-MscPassport-UsefulDefinitionsMIB

      DisplayString,
      StorageType,
      RowStatus,
      Unsigned32
   FROM Nortel-MsCarrier-MscPassport-StandardTextualConventionsMIB

      NonReplicated,
      Link
   FROM Nortel-MsCarrier-MscPassport-TextualConventionsMIB

      mscSigChan,
      mscSigChanIndex
   FROM Nortel-MsCarrier-MscPassport-VoiceNetworkingMIB;




-- LAST-UPDATED   "9909010000Z"
-- ORGANIZATION   "Nortel Networks"
-- CONTACT-INFO   "
--         Nortel Carrier Data Network Management
--         
--         Postal:       P.O. Box 3511, Station C 
--                       Ottawa, Ontario 
--                       Canada  K1Y 4H7
--         
--         via the WEB:  http://www.nortelnetworks.com  
--                       select 'Contact Us' from the menu
--          
--         via phone:    1-800-4NORTEL"
-- DESCRIPTION
--    "The module describing the Nortel MsCarrier MscPassport
--     VnetNisSig Enterprise MIB."

vnetNisSigMIB OBJECT IDENTIFIER ::= { mscPassportMIBs 112 }










-- SigChan/n NisSig
-- The NisSig component defines the operational characteristics of the 
-- signalling channel's connection to the external equipment.

mscSigChanNis OBJECT IDENTIFIER ::= { mscSigChan 8 }



mscSigChanNisRowStatusTable OBJECT-TYPE
   SYNTAX     SEQUENCE OF MscSigChanNisRowStatusEntry
   ACCESS     not-accessible
   STATUS     mandatory
   DESCRIPTION
     "This entry controls the addition and deletion of 
      mscSigChanNis components."
::= { mscSigChanNis 1 }

mscSigChanNisRowStatusEntry OBJECT-TYPE
   SYNTAX     MscSigChanNisRowStatusEntry
   ACCESS     not-accessible
   STATUS     mandatory
   DESCRIPTION
     "A single entry in the table represents a single 
      mscSigChanNis component."
   INDEX {
      mscSigChanIndex,
      mscSigChanNisIndex }
::= { mscSigChanNisRowStatusTable 1 }

MscSigChanNisRowStatusEntry ::= SEQUENCE {
   mscSigChanNisRowStatus
      RowStatus,
   mscSigChanNisComponentName
      DisplayString,
   mscSigChanNisStorageType
      StorageType,
   mscSigChanNisIndex
      NonReplicated }

mscSigChanNisRowStatus OBJECT-TYPE
   SYNTAX     RowStatus 
   ACCESS     read-write
   STATUS     mandatory
   DESCRIPTION
     "This variable is used as the basis for SNMP naming of
      mscSigChanNis components.
      These components can be added and deleted."
::= { mscSigChanNisRowStatusEntry 1 }

mscSigChanNisComponentName OBJECT-TYPE
   SYNTAX     DisplayString 
   ACCESS     read-only
   STATUS     mandatory
   DESCRIPTION
     "This variable provides the component's string name for
      use with the ASCII Console Interface"
::= { mscSigChanNisRowStatusEntry 2 }

mscSigChanNisStorageType OBJECT-TYPE
   SYNTAX     StorageType 
   ACCESS     read-only
   STATUS     mandatory
   DESCRIPTION
     "This variable represents the storage type value for the
      mscSigChanNis tables."
::= { mscSigChanNisRowStatusEntry 4 }

mscSigChanNisIndex OBJECT-TYPE
   SYNTAX     NonReplicated 
   ACCESS     not-accessible
   STATUS     mandatory
   DESCRIPTION
     "This variable represents the index for the mscSigChanNis tables."
::= { mscSigChanNisRowStatusEntry 10 }

mscSigChanNisL2Table OBJECT-TYPE
   SYNTAX     SEQUENCE OF MscSigChanNisL2Entry
   ACCESS     not-accessible
   STATUS     mandatory
   DESCRIPTION
     "This group specifies the provisionable layer 2 attributes of the 
      Q.931 ITU-T protocol."
::= { mscSigChanNis 11 }

mscSigChanNisL2Entry OBJECT-TYPE
   SYNTAX     MscSigChanNisL2Entry
   ACCESS     not-accessible
   STATUS     mandatory
   DESCRIPTION
     "An entry in the mscSigChanNisL2Table."
   INDEX {
      mscSigChanIndex,
      mscSigChanNisIndex }
::= { mscSigChanNisL2Table 1 }

MscSigChanNisL2Entry ::= SEQUENCE {
   mscSigChanNisT23
      Unsigned32,
   mscSigChanNisT200
      Unsigned32,
   mscSigChanNisN200
      Unsigned32,
   mscSigChanNisT203
      Unsigned32,
   mscSigChanNisCircuitSwitchedK
      Unsigned32 }

mscSigChanNisT23 OBJECT-TYPE
   SYNTAX     Unsigned32 (1..15)
   ACCESS     read-write
   STATUS     mandatory
   DESCRIPTION
     "This attribute specifies the layer 2 enable request timer."
   DEFVAL     { 10 }
::= { mscSigChanNisL2Entry 1 }

mscSigChanNisT200 OBJECT-TYPE
   SYNTAX     Unsigned32 (1..20)
   ACCESS     read-write
   STATUS     mandatory
   DESCRIPTION
     "This attribute specifies the maximum time between a layer 2 frame 
      and its acknowledgment."
   DEFVAL     { 1 }
::= { mscSigChanNisL2Entry 2 }

mscSigChanNisN200 OBJECT-TYPE
   SYNTAX     Unsigned32 (1..8)
   ACCESS     read-write
   STATUS     mandatory
   DESCRIPTION
     "This attribute specifies the maximum number of re-transmissions of 
      a layer 2 frame."
   DEFVAL     { 3 }
::= { mscSigChanNisL2Entry 3 }

mscSigChanNisT203 OBJECT-TYPE
   SYNTAX     Unsigned32 (2..40)
   ACCESS     read-write
   STATUS     mandatory
   DESCRIPTION
     "This attribute specifies the maximum time for which layer 2 frames 
      may be absent. Expiry triggers a check on whether the far end is 
      alive."
   DEFVAL     { 10 }
::= { mscSigChanNisL2Entry 4 }

mscSigChanNisCircuitSwitchedK OBJECT-TYPE
   SYNTAX     Unsigned32 (1..127)
   ACCESS     read-write
   STATUS     mandatory
   DESCRIPTION
     "This attribute specifies the maximum number of sequentially 
      numbered I frames (that is, window size (k)) that may be 
      unacknowledged at any given time for a SAP supporting primary 
      rate (64kbit/sec) signalling."
   DEFVAL     { 7 }
::= { mscSigChanNisL2Entry 6 }

mscSigChanNisL3Table OBJECT-TYPE
   SYNTAX     SEQUENCE OF MscSigChanNisL3Entry
   ACCESS     not-accessible
   STATUS     mandatory
   DESCRIPTION
     "This group represents the provisionable Layer 3 timer attributes of a 
      the Nis signalling protocol."
::= { mscSigChanNis 12 }

mscSigChanNisL3Entry OBJECT-TYPE
   SYNTAX     MscSigChanNisL3Entry
   ACCESS     not-accessible
   STATUS     mandatory
   DESCRIPTION
     "An entry in the mscSigChanNisL3Table."
   INDEX {
      mscSigChanIndex,
      mscSigChanNisIndex }
::= { mscSigChanNisL3Table 1 }

MscSigChanNisL3Entry ::= SEQUENCE {
   mscSigChanNisT309
      Unsigned32,
   mscSigChanNisT310
      Unsigned32 }

mscSigChanNisT309 OBJECT-TYPE
   SYNTAX     Unsigned32 (15..120)
   ACCESS     read-write
   STATUS     mandatory
   DESCRIPTION
     "This attribute specifies the data link failure timer; used to ride out 
      temporary failures."
   DEFVAL     { 90 }
::= { mscSigChanNisL3Entry 3 }

mscSigChanNisT310 OBJECT-TYPE
   SYNTAX     Unsigned32 (10..120)
   ACCESS     read-write
   STATUS     mandatory
   DESCRIPTION
     "This attribute specifies the call proceeding state timer."
   DEFVAL     { 10 }
::= { mscSigChanNisL3Entry 4 }

mscSigChanNisProvTable OBJECT-TYPE
   SYNTAX     SEQUENCE OF MscSigChanNisProvEntry
   ACCESS     not-accessible
   STATUS     mandatory
   DESCRIPTION
     "This group defines the general options of the D-channel signalling 
      link."
::= { mscSigChanNis 13 }

mscSigChanNisProvEntry OBJECT-TYPE
   SYNTAX     MscSigChanNisProvEntry
   ACCESS     not-accessible
   STATUS     mandatory
   DESCRIPTION
     "An entry in the mscSigChanNisProvTable."
   INDEX {
      mscSigChanIndex,
      mscSigChanNisIndex }
::= { mscSigChanNisProvTable 1 }

MscSigChanNisProvEntry ::= SEQUENCE {
   mscSigChanNisSide
      INTEGER,
   mscSigChanNisMaxNonCallConcurrent
      Unsigned32 }

mscSigChanNisSide OBJECT-TYPE
   SYNTAX     INTEGER  {
                 network(1),
                 user(2) }
   ACCESS     read-write
   STATUS     mandatory
   DESCRIPTION
     "This attribute specifies whether the interface is the network or user 
      side of the connection. The parameter applies to both the layer 2 
      and layer 3 of the interface. If this attribute is set to network, then 
      the interface is master during channel negotiation. If this attribute is 
      set to user, then the interface is slave during channel negotiation."
   DEFVAL     { network }
::= { mscSigChanNisProvEntry 1 }

mscSigChanNisMaxNonCallConcurrent OBJECT-TYPE
   SYNTAX     Unsigned32 (1..30)
   ACCESS     read-write
   STATUS     mandatory
   DESCRIPTION
     "This attribute specifies the maximum number of simultaneous active 
      non-call messages that are allowed."
   DEFVAL     { 30 }
::= { mscSigChanNisProvEntry 2 }

mscSigChanNisStateTable OBJECT-TYPE
   SYNTAX     SEQUENCE OF MscSigChanNisStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscSigChanNis 14 }

mscSigChanNisStateEntry OBJECT-TYPE
   SYNTAX     MscSigChanNisStateEntry
   ACCESS     not-accessible
   STATUS     mandatory
   DESCRIPTION
     "An entry in the mscSigChanNisStateTable."
   INDEX {
      mscSigChanIndex,
      mscSigChanNisIndex }
::= { mscSigChanNisStateTable 1 }

MscSigChanNisStateEntry ::= SEQUENCE {
   mscSigChanNisAdminState
      INTEGER,
   mscSigChanNisOperationalState
      INTEGER,
   mscSigChanNisUsageState
      INTEGER }

mscSigChanNisAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscSigChanNisStateEntry 1 }

mscSigChanNisOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscSigChanNisStateEntry 2 }

mscSigChanNisUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscSigChanNisStateEntry 3 }

mscSigChanNisStatsTable OBJECT-TYPE
   SYNTAX     SEQUENCE OF MscSigChanNisStatsEntry
   ACCESS     not-accessible
   STATUS     mandatory
   DESCRIPTION
     "This group provides the operational components for the NisSig 
      component."
::= { mscSigChanNis 15 }

mscSigChanNisStatsEntry OBJECT-TYPE
   SYNTAX     MscSigChanNisStatsEntry
   ACCESS     not-accessible
   STATUS     mandatory
   DESCRIPTION
     "An entry in the mscSigChanNisStatsTable."
   INDEX {
      mscSigChanIndex,
      mscSigChanNisIndex }
::= { mscSigChanNisStatsTable 1 }

MscSigChanNisStatsEntry ::= SEQUENCE {
   mscSigChanNisTotalCallsToIf
      Unsigned32,
   mscSigChanNisTotalCallsFromIf
      Unsigned32,
   mscSigChanNisNonCallAssocSessionsToIf
      Unsigned32,
   mscSigChanNisNonCallAssocSessionsFromIf
      Unsigned32 }

mscSigChanNisTotalCallsToIf OBJECT-TYPE
   SYNTAX     Unsigned32 (0..4294967295)
   ACCESS     read-only
   STATUS     mandatory
   DESCRIPTION
     "This attribute counts the total number of calls that have been made 
      to the interface. The value wraps when it reaches its maximum."
   DEFVAL     { 0 }
::= { mscSigChanNisStatsEntry 2 }

mscSigChanNisTotalCallsFromIf OBJECT-TYPE
   SYNTAX     Unsigned32 (0..4294967295)
   ACCESS     read-only
   STATUS     mandatory
   DESCRIPTION
     "This attribute counts the total number of calls from the interface. 
      The value wraps when it reaches its maximum."
   DEFVAL     { 0 }
::= { mscSigChanNisStatsEntry 3 }

mscSigChanNisNonCallAssocSessionsToIf OBJECT-TYPE
   SYNTAX     Unsigned32 (0..4294967295)
   ACCESS     read-only
   STATUS     mandatory
   DESCRIPTION
     "This attribute counts the total number of non-call associated 
      sessions to the interface. The value wraps when it reaches its 
      maximum."
   DEFVAL     { 0 }
::= { mscSigChanNisStatsEntry 4 }

mscSigChanNisNonCallAssocSessionsFromIf OBJECT-TYPE
   SYNTAX     Unsigned32 (0..4294967295)
   ACCESS     read-only
   STATUS     mandatory
   DESCRIPTION
     "This attribute counts the total number of non-call associated 
      sessions from the interface. The value wraps when it reaches its 
      maximum."
   DEFVAL     { 0 }
::= { mscSigChanNisStatsEntry 5 }

mscSigChanNisOperTable OBJECT-TYPE
   SYNTAX     SEQUENCE OF MscSigChanNisOperEntry
   ACCESS     not-accessible
   STATUS     mandatory
   DESCRIPTION
     "This group provides the operational attributes for the NisSig 
      protocol."
::= { mscSigChanNis 16 }

mscSigChanNisOperEntry OBJECT-TYPE
   SYNTAX     MscSigChanNisOperEntry
   ACCESS     not-accessible
   STATUS     mandatory
   DESCRIPTION
     "An entry in the mscSigChanNisOperTable."
   INDEX {
      mscSigChanIndex,
      mscSigChanNisIndex }
::= { mscSigChanNisOperTable 1 }

MscSigChanNisOperEntry ::= SEQUENCE {
   mscSigChanNisActiveChannels
      Unsigned32,
   mscSigChanNisActiveVoiceChannels
      Unsigned32,
   mscSigChanNisActiveDataChannels
      Unsigned32,
   mscSigChanNisPeakActiveChannels
      Unsigned32,
   mscSigChanNisPeakActiveVoiceChannels
      Unsigned32,
   mscSigChanNisPeakActiveDataChannels
      Unsigned32,
   mscSigChanNisDChanStatus
      INTEGER }

mscSigChanNisActiveChannels OBJECT-TYPE
   SYNTAX     Unsigned32 (0..128)
   ACCESS     read-only
   STATUS     mandatory
   DESCRIPTION
     "This attribute indicates the number of currently active channels. 
      This includes data and voice channels."
   DEFVAL     { 0 }
::= { mscSigChanNisOperEntry 1 }

mscSigChanNisActiveVoiceChannels OBJECT-TYPE
   SYNTAX     Unsigned32 (0..128)
   ACCESS     read-only
   STATUS     mandatory
   DESCRIPTION
     "This attribute indicates the number of channels that are currently 
      carrying voice."
   DEFVAL     { 0 }
::= { mscSigChanNisOperEntry 2 }

mscSigChanNisActiveDataChannels OBJECT-TYPE
   SYNTAX     Unsigned32 (0..128)
   ACCESS     read-only
   STATUS     mandatory
   DESCRIPTION
     "This attribute indicates the number of channels that are currently 
      carrying data. This does not include modem data."
   DEFVAL     { 0 }
::= { mscSigChanNisOperEntry 3 }

mscSigChanNisPeakActiveChannels OBJECT-TYPE
   SYNTAX     Unsigned32 (0..128)
   ACCESS     read-only
   STATUS     mandatory
   DESCRIPTION
     "This attribute indicates the maximum number of channels that have 
      been active on this signalling channel during the last polling period."
   DEFVAL     { 0 }
::= { mscSigChanNisOperEntry 4 }

mscSigChanNisPeakActiveVoiceChannels OBJECT-TYPE
   SYNTAX     Unsigned32 (0..128)
   ACCESS     read-only
   STATUS     mandatory
   DESCRIPTION
     "This attribute indicates the maximum number of voice channels that 
      have been active on this signalling channel during the last polling 
      period."
   DEFVAL     { 0 }
::= { mscSigChanNisOperEntry 5 }

mscSigChanNisPeakActiveDataChannels OBJECT-TYPE
   SYNTAX     Unsigned32 (0..128)
   ACCESS     read-only
   STATUS     mandatory
   DESCRIPTION
     "This attribute indicates the maximum number of data channels that 
      have been active on this signalling channel during the last polling 
      period."
   DEFVAL     { 0 }
::= { mscSigChanNisOperEntry 6 }

mscSigChanNisDChanStatus OBJECT-TYPE
   SYNTAX     INTEGER  {
                 outOfService(0),
                 establishing(1),
                 established(2),
                 enabling(3),
                 inService(4),
                 restarting(5) }
   ACCESS     read-only
   STATUS     mandatory
   DESCRIPTION
     "This attribute indicates the state of the D-channel. 
      outOfService means that there is no layer 2 or layer 3 connectivity 
      to the PBX.
      establishing means that the signalling channel is attempting to stage 
      the layer 2.
      established means that the layer 2 is enabled. If the signalling 
      channel stays in the established state, then it is waiting for a restart 
      from the PBX.
      enabling means that the resources for processing calls are being 
      initialized. If the signalling channel stays in the enabling state then 
      it is waiting for a restart acknowledgement from the PBX. 
      inService means that the resources for processing calls are 
      available. 
      restarting means that the resources for call processing are being 
      rei-initialized."
::= { mscSigChanNisOperEntry 7 }

mscSigChanNisToolsTable OBJECT-TYPE
   SYNTAX     SEQUENCE OF MscSigChanNisToolsEntry
   ACCESS     not-accessible
   STATUS     mandatory
   DESCRIPTION
     "This contains a series of operational attributes which turn on and off 
      several kinds of tracing."
::= { mscSigChanNis 17 }

mscSigChanNisToolsEntry OBJECT-TYPE
   SYNTAX     MscSigChanNisToolsEntry
   ACCESS     not-accessible
   STATUS     mandatory
   DESCRIPTION
     "An entry in the mscSigChanNisToolsTable."
   INDEX {
      mscSigChanIndex,
      mscSigChanNisIndex }
::= { mscSigChanNisToolsTable 1 }

MscSigChanNisToolsEntry ::= SEQUENCE {
   mscSigChanNisTracing
      OCTET STRING }

mscSigChanNisTracing OBJECT-TYPE
   SYNTAX     OCTET STRING (SIZE (1))
   ACCESS     read-write
   STATUS     mandatory
   DESCRIPTION
     "This attribute defines which types of tracing are active for this 
      signalling channel.  The tracing messages are sent to the debug 
      stream. To see the messages the agentQueue attribute in Col/debug 
      must be greater than 0 and a Telnet NMIS session must list the 
      debug stream in in its data streams (ex. set nmis telnet session/1 
      dataStreams debug). Different types of tracing can be enabled 
      simultaneously.  
      Note that tracing consumes additional CPU resources and will slow 
      down call processing on a heavily loaded card.  If there is message 
      block exhaustion tracing will be suspended for a period and then 
      automatically reenabled.  An alarm is generated on tracing 
      suspension and resumption.  This mechanism protects the function 
      processor against excessive numbers of tracing messages.
      
      Types of tracing include: 
      protocolErrors - get details of any protocol errors which are 
      occuring. Protocol errors are also reported in summary form as 
      alarms. 
      q931Summary - Summary of the Q.931 messages on the signalling 
      link, including certain call details (calling number, called number, 
      release codes). 
      q931Hex - Q.931 messages displayed in hex format.  Useful to 
      determine protocol compliance in case of errors reported on local or 
      remote ends.
      q931Symbolic - Q.931 messages parsed to give maximum detail.  
      Useful for understanding content of messages flowing on the link.
      portHex - Messages in hex format being sent and received on the 
      link.

      Description of bits:
      protocolErrors(0)
      q931Summary(1)
      q931Hex(2)
      q931Symbolic(3)
      portHex(4)"
::= { mscSigChanNisToolsEntry 1 }

mscSigChanNisNisSpecificProvTable OBJECT-TYPE
   SYNTAX     SEQUENCE OF MscSigChanNisNisSpecificProvEntry
   ACCESS     not-accessible
   STATUS     mandatory
   DESCRIPTION
     "This group provides NIS protocol specific provisioning."
::= { mscSigChanNis 18 }

mscSigChanNisNisSpecificProvEntry OBJECT-TYPE
   SYNTAX     MscSigChanNisNisSpecificProvEntry
   ACCESS     not-accessible
   STATUS     mandatory
   DESCRIPTION
     "An entry in the mscSigChanNisNisSpecificProvTable."
   INDEX {
      mscSigChanIndex,
      mscSigChanNisIndex }
::= { mscSigChanNisNisSpecificProvTable 1 }

MscSigChanNisNisSpecificProvEntry ::= SEQUENCE {
   mscSigChanNisChanMaintenanceHandling
      INTEGER }

mscSigChanNisChanMaintenanceHandling OBJECT-TYPE
   SYNTAX     INTEGER  {
                 globalOnStartup(0),
                 serviceMessage(1),
                 restartMessage(2) }
   ACCESS     read-write
   STATUS     mandatory
   DESCRIPTION
     "This attribute specifies how channel maintenance events should be 
      handled upon startup. Channel maintenance events include locking 
      and unlocking a channel or channel registration. The decision is 
      either to send individual channel RESTART messages, SERVICE 
      messages, or nothing. Note that channel registration only occurs 
      after the global interface restart at startup.
      
      Setting this attribute to enable SERVICE messages ensures that 
      SERVICE messages occur at startup and whenever a channel goes 
      into or out of service. If this attribute is not set to enable SERVICE 
      messaging, a RESTART is always sent on unlocking a channel.
      
      globalOnStartup provides the minimum required functionality at 
      startup, without any individual channel confirmation. Note that 
      when this is set, channel RESTART is still used for channel unlock. 
      globalOnStartup applies to SigChan startup only.
      
      serviceMessage enables sending and receiving SERVICE messages. 
      If this attribute is set to serviceMessage, SERVICE messages are 
      used for channel maintenance on channel lock, channel unlock, and 
      startup.
      
      restartMessage specifies that individual channel RESTARTs when 
      the SigChan starts up. If this attribute is set to restartMessage, a 
      RESTART message is used to send at startup and channel unlock."
   DEFVAL     { restartMessage }
::= { mscSigChanNisNisSpecificProvEntry 1 }


-- SigChan/n Nis Framer
-- 
-- The Framer component controls link layer framing for application 
-- components sending and receiving data on a link interface. It is also 
-- through Framer, that an application component is associated with a 
-- specific hardware link interface.
-- 
-- The Framer component provides provisionable attributes related to 
-- data path aspects of the hardware interface (such as crc and frame 
-- length). The Framer component also provides a provisionable 
-- attribute which binds the application component to a specific 
-- hardware component.
-- 
-- The Framer component contains operational attributes for link 
-- interface data path statistics (such as frame counts and aborts).
-- 

mscSigChanNisFramer OBJECT IDENTIFIER ::= { mscSigChanNis 2 }



mscSigChanNisFramerRowStatusTable OBJECT-TYPE
   SYNTAX     SEQUENCE OF MscSigChanNisFramerRowStatusEntry
   ACCESS     not-accessible
   STATUS     mandatory
   DESCRIPTION
     "This entry controls the addition and deletion of 
      mscSigChanNisFramer components."
::= { mscSigChanNisFramer 1 }

mscSigChanNisFramerRowStatusEntry OBJECT-TYPE
   SYNTAX     MscSigChanNisFramerRowStatusEntry
   ACCESS     not-accessible
   STATUS     mandatory
   DESCRIPTION
     "A single entry in the table represents a single 
      mscSigChanNisFramer component."
   INDEX {
      mscSigChanIndex,
      mscSigChanNisIndex,
      mscSigChanNisFramerIndex }
::= { mscSigChanNisFramerRowStatusTable 1 }

MscSigChanNisFramerRowStatusEntry ::= SEQUENCE {
   mscSigChanNisFramerRowStatus
      RowStatus,
   mscSigChanNisFramerComponentName
      DisplayString,
   mscSigChanNisFramerStorageType
      StorageType,
   mscSigChanNisFramerIndex
      NonReplicated }

mscSigChanNisFramerRowStatus OBJECT-TYPE
   SYNTAX     RowStatus 
   ACCESS     read-only
   STATUS     mandatory
   DESCRIPTION
     "This variable is used as the basis for SNMP naming of
      mscSigChanNisFramer components.
      These components cannot be added nor deleted."
::= { mscSigChanNisFramerRowStatusEntry 1 }

mscSigChanNisFramerComponentName OBJECT-TYPE
   SYNTAX     DisplayString 
   ACCESS     read-only
   STATUS     mandatory
   DESCRIPTION
     "This variable provides the component's string name for
      use with the ASCII Console Interface"
::= { mscSigChanNisFramerRowStatusEntry 2 }

mscSigChanNisFramerStorageType OBJECT-TYPE
   SYNTAX     StorageType 
   ACCESS     read-only
   STATUS     mandatory
   DESCRIPTION
     "This variable represents the storage type value for the
      mscSigChanNisFramer tables."
::= { mscSigChanNisFramerRowStatusEntry 4 }

mscSigChanNisFramerIndex OBJECT-TYPE
   SYNTAX     NonReplicated 
   ACCESS     not-accessible
   STATUS     mandatory
   DESCRIPTION
     "This variable represents the index for the mscSigChanNisFramer tables."
::= { mscSigChanNisFramerRowStatusEntry 10 }

mscSigChanNisFramerProvTable OBJECT-TYPE
   SYNTAX     SEQUENCE OF MscSigChanNisFramerProvEntry
   ACCESS     not-accessible
   STATUS     mandatory
   DESCRIPTION
     "This group contains the base provisioning data for the Framer 
      component. Application or hardware interface specific provisioning 
      data is contained in other provisionable Framer groups."
::= { mscSigChanNisFramer 10 }

mscSigChanNisFramerProvEntry OBJECT-TYPE
   SYNTAX     MscSigChanNisFramerProvEntry
   ACCESS     not-accessible
   STATUS     mandatory
   DESCRIPTION
     "An entry in the mscSigChanNisFramerProvTable."
   INDEX {
      mscSigChanIndex,
      mscSigChanNisIndex,
      mscSigChanNisFramerIndex }
::= { mscSigChanNisFramerProvTable 1 }

MscSigChanNisFramerProvEntry ::= SEQUENCE {
   mscSigChanNisFramerInterfaceName
      Link }

mscSigChanNisFramerInterfaceName OBJECT-TYPE
   SYNTAX     Link 
   ACCESS     read-write
   STATUS     mandatory
   DESCRIPTION
     "This attribute contains a hardware component name.
      
      The attribute associates the application with a specific link. This 
      defines the module processor on which Framer's parent component 
      (as well as Framer itself) will run."
::= { mscSigChanNisFramerProvEntry 1 }

mscSigChanNisFramerStateTable OBJECT-TYPE
   SYNTAX     SEQUENCE OF MscSigChanNisFramerStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscSigChanNisFramer 12 }

mscSigChanNisFramerStateEntry OBJECT-TYPE
   SYNTAX     MscSigChanNisFramerStateEntry
   ACCESS     not-accessible
   STATUS     mandatory
   DESCRIPTION
     "An entry in the mscSigChanNisFramerStateTable."
   INDEX {
      mscSigChanIndex,
      mscSigChanNisIndex,
      mscSigChanNisFramerIndex }
::= { mscSigChanNisFramerStateTable 1 }

MscSigChanNisFramerStateEntry ::= SEQUENCE {
   mscSigChanNisFramerAdminState
      INTEGER,
   mscSigChanNisFramerOperationalState
      INTEGER,
   mscSigChanNisFramerUsageState
      INTEGER }

mscSigChanNisFramerAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscSigChanNisFramerStateEntry 1 }

mscSigChanNisFramerOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscSigChanNisFramerStateEntry 2 }

mscSigChanNisFramerUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscSigChanNisFramerStateEntry 3 }

mscSigChanNisFramerStatsTable OBJECT-TYPE
   SYNTAX     SEQUENCE OF MscSigChanNisFramerStatsEntry
   ACCESS     not-accessible
   STATUS     mandatory
   DESCRIPTION
     "This group contains the operational statistics data for a Framer 
      component."
::= { mscSigChanNisFramer 13 }

mscSigChanNisFramerStatsEntry OBJECT-TYPE
   SYNTAX     MscSigChanNisFramerStatsEntry
   ACCESS     not-accessible
   STATUS     mandatory
   DESCRIPTION
     "An entry in the mscSigChanNisFramerStatsTable."
   INDEX {
      mscSigChanIndex,
      mscSigChanNisIndex,
      mscSigChanNisFramerIndex }
::= { mscSigChanNisFramerStatsTable 1 }

MscSigChanNisFramerStatsEntry ::= SEQUENCE {
   mscSigChanNisFramerFrmToIf
      Unsigned32,
   mscSigChanNisFramerFrmFromIf
      Unsigned32,
   mscSigChanNisFramerOctetFromIf
      Unsigned32,
   mscSigChanNisFramerAborts
      Unsigned32,
   mscSigChanNisFramerCrcErrors
      Unsigned32,
   mscSigChanNisFramerLrcErrors
      Unsigned32,
   mscSigChanNisFramerNonOctetErrors
      Unsigned32,
   mscSigChanNisFramerOverruns
      Unsigned32,
   mscSigChanNisFramerUnderruns
      Unsigned32,
   mscSigChanNisFramerLargeFrmErrors
      Unsigned32 }

mscSigChanNisFramerFrmToIf OBJECT-TYPE
   SYNTAX     Unsigned32 (0..4294967295)
   ACCESS     read-only
   STATUS     mandatory
   DESCRIPTION
     "This attribute counts the number of frames transmitted to the link 
      interface by Framer.
      This count wraps to zero after reaching its maximum value."
   DEFVAL     { 0 }
::= { mscSigChanNisFramerStatsEntry 1 }

mscSigChanNisFramerFrmFromIf OBJECT-TYPE
   SYNTAX     Unsigned32 (0..4294967295)
   ACCESS     read-only
   STATUS     mandatory
   DESCRIPTION
     "This attribute counts the number of frames received from the link 
      interface by Framer.
      This count wraps to zero after reaching its maximum value."
   DEFVAL     { 0 }
::= { mscSigChanNisFramerStatsEntry 2 }

mscSigChanNisFramerOctetFromIf OBJECT-TYPE
   SYNTAX     Unsigned32 (0..4294967295)
   ACCESS     read-only
   STATUS     mandatory
   DESCRIPTION
     "The number of bytes received from the link interface by Framer."
   DEFVAL     { 0 }
::= { mscSigChanNisFramerStatsEntry 3 }

mscSigChanNisFramerAborts OBJECT-TYPE
   SYNTAX     Unsigned32 (0..4294967295)
   ACCESS     read-only
   STATUS     mandatory
   DESCRIPTION
     "This attribute counts the total number of aborts received.
      This count wraps to zero after reaching its maximum value."
   DEFVAL     { 0 }
::= { mscSigChanNisFramerStatsEntry 4 }

mscSigChanNisFramerCrcErrors OBJECT-TYPE
   SYNTAX     Unsigned32 (0..4294967295)
   ACCESS     read-only
   STATUS     mandatory
   DESCRIPTION
     "This attribute counts the total number of frames with CRC errors.
      This count wraps to zero after reaching its maximum value."
   DEFVAL     { 0 }
::= { mscSigChanNisFramerStatsEntry 5 }

mscSigChanNisFramerLrcErrors OBJECT-TYPE
   SYNTAX     Unsigned32 (0..4294967295)
   ACCESS     read-only
   STATUS     mandatory
   DESCRIPTION
     "This attribute counts the total number of frames with LRC errors.
      This count wraps to zero after reaching its maximum value."
   DEFVAL     { 0 }
::= { mscSigChanNisFramerStatsEntry 6 }

mscSigChanNisFramerNonOctetErrors OBJECT-TYPE
   SYNTAX     Unsigned32 (0..4294967295)
   ACCESS     read-only
   STATUS     mandatory
   DESCRIPTION
     "This attribute counts the total number of frames that were non octet 
      aligned.
      This count wraps to zero after reaching its maximum value."
   DEFVAL     { 0 }
::= { mscSigChanNisFramerStatsEntry 7 }

mscSigChanNisFramerOverruns OBJECT-TYPE
   SYNTAX     Unsigned32 (0..4294967295)
   ACCESS     read-only
   STATUS     mandatory
   DESCRIPTION
     "This attribute counts the total number of frames received from the 
      link for which overruns occurred.
      This count wraps to zero after reaching its maximum value."
   DEFVAL     { 0 }
::= { mscSigChanNisFramerStatsEntry 8 }

mscSigChanNisFramerUnderruns OBJECT-TYPE
   SYNTAX     Unsigned32 (0..4294967295)
   ACCESS     read-only
   STATUS     mandatory
   DESCRIPTION
     "This attribute counts the total number of frames transmitted to the 
      link for which underruns occurred.
      This count wraps to zero after reaching its maximum value."
   DEFVAL     { 0 }
::= { mscSigChanNisFramerStatsEntry 9 }

mscSigChanNisFramerLargeFrmErrors OBJECT-TYPE
   SYNTAX     Unsigned32 (0..4294967295)
   ACCESS     read-only
   STATUS     mandatory
   DESCRIPTION
     "This attribute counts the total number of frames received which 
      were too large (longer than 500 bytes).
      This count wraps to zero after reaching its maximum value."
   DEFVAL     { 0 }
::= { mscSigChanNisFramerStatsEntry 10 }




-- 
-- Version and Compliance statements
-- 



-- Object-Group Statement:
-- A list of all current accessible leaf objects.

-- OBJECTS { mscSigChanNisUsageState,
--           mscSigChanNisN200,
--           mscSigChanNisSide,
--           mscSigChanNisFramerAborts,
--           mscSigChanNisTotalCallsFromIf,
--           mscSigChanNisComponentName,
--           mscSigChanNisT23,
--           mscSigChanNisFramerStorageType,
--           mscSigChanNisPeakActiveDataChannels,
--           mscSigChanNisFramerOctetFromIf,
--           mscSigChanNisFramerFrmToIf,
--           mscSigChanNisStorageType,
--           mscSigChanNisCircuitSwitchedK,
--           mscSigChanNisT200,
--           mscSigChanNisT309,
--           mscSigChanNisFramerUnderruns,
--           mscSigChanNisOperationalState,
--           mscSigChanNisT203,
--           mscSigChanNisFramerOperationalState,
--           mscSigChanNisDChanStatus,
--           mscSigChanNisFramerAdminState,
--           mscSigChanNisTotalCallsToIf,
--           mscSigChanNisFramerCrcErrors,
--           mscSigChanNisPeakActiveChannels,
--           mscSigChanNisFramerLrcErrors,
--           mscSigChanNisAdminState,
--           mscSigChanNisTracing,
--           mscSigChanNisFramerLargeFrmErrors,
--           mscSigChanNisFramerRowStatus,
--           mscSigChanNisActiveVoiceChannels,
--           mscSigChanNisT310,
--           mscSigChanNisChanMaintenanceHandling,
--           mscSigChanNisRowStatus,
--           mscSigChanNisFramerOverruns,
--           mscSigChanNisFramerFrmFromIf,
--           mscSigChanNisMaxNonCallConcurrent,
--           mscSigChanNisNonCallAssocSessionsFromIf,
--           mscSigChanNisPeakActiveVoiceChannels,
--           mscSigChanNisFramerNonOctetErrors,
--           mscSigChanNisNonCallAssocSessionsToIf,
--           mscSigChanNisFramerInterfaceName,
--           mscSigChanNisActiveDataChannels,
--           mscSigChanNisActiveChannels,
--           mscSigChanNisFramerUsageState,
--           mscSigChanNisFramerComponentName }
-- STATUS  mandatory
-- DESCRIPTION
--   "A list of all current accessible leaf objects."

vnetNisSigGroup OBJECT IDENTIFIER ::= { vnetNisSigMIB 1 }
vnetNisSigGroupCA OBJECT IDENTIFIER ::= { vnetNisSigGroup 1 }
vnetNisSigGroupCA02 OBJECT IDENTIFIER ::= { vnetNisSigGroupCA 3 }
vnetNisSigGroupCA02A OBJECT IDENTIFIER ::= { vnetNisSigGroupCA02 2 }



-- Agent-Capabilities Statement:

-- PRODUCT-RELEASE "MscPassport Release 1.2 VnetNisSig."
-- STATUS          mandatory
-- DESCRIPTION     "Carrier Passport VnetNisSig MIB: MIB Version CA02A,
--                  Software Version CA02S9C."
-- SUPPORTS        Nortel-MsCarrier-MscPassport-VnetNisSigMIB
--    INCLUDES     { vnetNisSigGroupCA02A }

vnetNisSigCapabilities OBJECT IDENTIFIER ::= { vnetNisSigMIB 3 }
vnetNisSigCapabilitiesCA OBJECT IDENTIFIER ::= { vnetNisSigCapabilities 1 }
vnetNisSigCapabilitiesCA02 OBJECT IDENTIFIER ::= { vnetNisSigCapabilitiesCA 3 }
vnetNisSigCapabilitiesCA02A OBJECT IDENTIFIER ::= { vnetNisSigCapabilitiesCA02 2 }





END
