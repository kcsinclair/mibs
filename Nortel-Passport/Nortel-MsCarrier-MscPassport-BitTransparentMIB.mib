Nortel-MsCarrier-MscPassport-BitTransparentMIB
DEFINITIONS ::= BEGIN



IMPORTS

      OBJECT-TYPE
   FROM RFC-1212

      mscPassportMIBs,
      mscComponents
   FROM Nortel-MsCarrier-MscPassport-UsefulDefinitionsMIB

      Counter32,
      DisplayString,
      StorageType,
      RowStatus,
      InterfaceIndex,
      Gauge32,
      Integer32,
      Unsigned32
   FROM Nortel-MsCarrier-MscPassport-StandardTextualConventionsMIB

      AsciiString,
      Hex,
      NonReplicated,
      EnterpriseDateAndTime,
      PassportCounter64,
      Link
   FROM Nortel-MsCarrier-MscPassport-TextualConventionsMIB;




-- LAST-UPDATED   "9909010000Z"
-- ORGANIZATION   "Nortel Networks"
-- CONTACT-INFO   "
--         Nortel Carrier Data Network Management
--         
--         Postal:       P.O. Box 3511, Station C 
--                       Ottawa, Ontario 
--                       Canada  K1Y 4H7
--         
--         via the WEB:  http://www.nortelnetworks.com  
--                       select 'Contact Us' from the menu
--          
--         via phone:    1-800-4NORTEL"
-- DESCRIPTION
--    "The module describing the Nortel MsCarrier MscPassport
--     BitTransparent Enterprise MIB."

bitTransparentMIB OBJECT IDENTIFIER ::= { mscPassportMIBs 46 }










-- BitTransparentDataService/n
-- The Bit Transparent Data Service (BTDS) component defines an 
-- instance of the Bit transparent data service offered by Magellan 
-- Passport. 
-- One instance of this component is required by each DS1, E1, V35 
-- or V11 channel which is offering bit transparent traffic.
-- The instance number is arbitrary.

mscBtds OBJECT IDENTIFIER ::= { mscComponents 81 }



mscBtdsRowStatusTable OBJECT-TYPE
   SYNTAX     SEQUENCE OF MscBtdsRowStatusEntry
   ACCESS     not-accessible
   STATUS     mandatory
   DESCRIPTION
     "This entry controls the addition and deletion of 
      mscBtds components."
::= { mscBtds 1 }

mscBtdsRowStatusEntry OBJECT-TYPE
   SYNTAX     MscBtdsRowStatusEntry
   ACCESS     not-accessible
   STATUS     mandatory
   DESCRIPTION
     "A single entry in the table represents a single 
      mscBtds component."
   INDEX {
      mscBtdsIndex }
::= { mscBtdsRowStatusTable 1 }

MscBtdsRowStatusEntry ::= SEQUENCE {
   mscBtdsRowStatus
      RowStatus,
   mscBtdsComponentName
      DisplayString,
   mscBtdsStorageType
      StorageType,
   mscBtdsIndex
      Integer32 }

mscBtdsRowStatus OBJECT-TYPE
   SYNTAX     RowStatus 
   ACCESS     read-write
   STATUS     mandatory
   DESCRIPTION
     "This variable is used as the basis for SNMP naming of
      mscBtds components.
      These components can be added and deleted."
::= { mscBtdsRowStatusEntry 1 }

mscBtdsComponentName OBJECT-TYPE
   SYNTAX     DisplayString 
   ACCESS     read-only
   STATUS     mandatory
   DESCRIPTION
     "This variable provides the component's string name for
      use with the ASCII Console Interface"
::= { mscBtdsRowStatusEntry 2 }

mscBtdsStorageType OBJECT-TYPE
   SYNTAX     StorageType 
   ACCESS     read-only
   STATUS     mandatory
   DESCRIPTION
     "This variable represents the storage type value for the
      mscBtds tables."
::= { mscBtdsRowStatusEntry 4 }

mscBtdsIndex OBJECT-TYPE
   SYNTAX     Integer32 (1..65535)
   ACCESS     not-accessible
   STATUS     mandatory
   DESCRIPTION
     "This variable represents the index for the mscBtds tables."
::= { mscBtdsRowStatusEntry 10 }

mscBtdsCidDataTable OBJECT-TYPE
   SYNTAX     SEQUENCE OF MscBtdsCidDataEntry
   ACCESS     not-accessible
   STATUS     mandatory
   DESCRIPTION
     "This group contains the attribute for a component's Customer 
      Identifier (CID). Refer to the attribute description for a detailed 
      explanation of CIDs."
::= { mscBtds 100 }

mscBtdsCidDataEntry OBJECT-TYPE
   SYNTAX     MscBtdsCidDataEntry
   ACCESS     not-accessible
   STATUS     mandatory
   DESCRIPTION
     "An entry in the mscBtdsCidDataTable."
   INDEX {
      mscBtdsIndex }
::= { mscBtdsCidDataTable 1 }

MscBtdsCidDataEntry ::= SEQUENCE {
   mscBtdsCustomerIdentifier
      Unsigned32 }

mscBtdsCustomerIdentifier OBJECT-TYPE
   SYNTAX     Unsigned32 (0 | 1..8191)
   ACCESS     read-write
   STATUS     mandatory
   DESCRIPTION
     "This attribute holds the Customer Identifier (CID).
      
      Every component has a CID. If a component has a cid attribute, the 
      component's CID is the provisioned value of that attribute; 
      otherwise the component inherits the CID of its parent. The top-
      level component has a CID of 0.
      
      Every operator session also has a CID, which is the CID 
      provisioned for the operator's user ID. An operator will see only the 
      stream data for components having a matching CID. Also, the 
      operator will be allowed to issue commands for only those 
      components which have a matching CID.
      
      An operator CID of 0 is used to identify the Network Manager 
      (referred to as 'NetMan' in DPN). This CID matches the CID of 
      any component. Values 1 to 8191 inclusive (equivalent to 'basic 
      CIDs' in DPN) may be assigned to specific customers."
   DEFVAL     { 0 }
::= { mscBtdsCidDataEntry 1 }

mscBtdsIfEntryTable OBJECT-TYPE
   SYNTAX     SEQUENCE OF MscBtdsIfEntryEntry
   ACCESS     not-accessible
   STATUS     mandatory
   DESCRIPTION
     "This group contains the provisionable attributes for the ifEntry."
::= { mscBtds 101 }

mscBtdsIfEntryEntry OBJECT-TYPE
   SYNTAX     MscBtdsIfEntryEntry
   ACCESS     not-accessible
   STATUS     mandatory
   DESCRIPTION
     "An entry in the mscBtdsIfEntryTable."
   INDEX {
      mscBtdsIndex }
::= { mscBtdsIfEntryTable 1 }

MscBtdsIfEntryEntry ::= SEQUENCE {
   mscBtdsIfAdminStatus
      INTEGER,
   mscBtdsIfIndex
      InterfaceIndex }

mscBtdsIfAdminStatus OBJECT-TYPE
   SYNTAX     INTEGER  {
                 up(1),
                 down(2),
                 testing(3) }
   ACCESS     read-write
   STATUS     mandatory
   DESCRIPTION
     "The desired state of the interface. The up state indicates the 
      interface is operational. The down state indicates the interface is not 
      operational. The testing state indicates that no operational packets 
      can be passed."
   DEFVAL     { up }
::= { mscBtdsIfEntryEntry 1 }

mscBtdsIfIndex OBJECT-TYPE
   SYNTAX     InterfaceIndex (1..65535)
   ACCESS     read-only
   STATUS     mandatory
   DESCRIPTION
     "This is the index for the IfEntry. Its value is automatically initialized 
      during the provisioning process."
::= { mscBtdsIfEntryEntry 2 }

mscBtdsOperStatusTable OBJECT-TYPE
   SYNTAX     SEQUENCE OF MscBtdsOperStatusEntry
   ACCESS     not-accessible
   STATUS     mandatory
   DESCRIPTION
     "This group includes the Operational Status attribute. This attribute 
      defines the current operational state of this component."
::= { mscBtds 102 }

mscBtdsOperStatusEntry OBJECT-TYPE
   SYNTAX     MscBtdsOperStatusEntry
   ACCESS     not-accessible
   STATUS     mandatory
   DESCRIPTION
     "An entry in the mscBtdsOperStatusTable."
   INDEX {
      mscBtdsIndex }
::= { mscBtdsOperStatusTable 1 }

MscBtdsOperStatusEntry ::= SEQUENCE {
   mscBtdsSnmpOperStatus
      INTEGER }

mscBtdsSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { mscBtdsOperStatusEntry 1 }

mscBtdsStateTable OBJECT-TYPE
   SYNTAX     SEQUENCE OF MscBtdsStateEntry
   ACCESS     not-accessible
   STATUS     mandatory
   DESCRIPTION
     "This group contains the three OSI State attributes and the six OSI 
      Status attributes. The descriptions generically indicate what each 
      attribute implies about the component. Note that not all the values 
      and state combinations described here are supported by every 
      component which uses this group. For component-specific 
      information and the valid state combinations, refer to NTP 241-
      7001-150, Passport Operations and Maintenance Guide."
::= { mscBtds 103 }

mscBtdsStateEntry OBJECT-TYPE
   SYNTAX     MscBtdsStateEntry
   ACCESS     not-accessible
   STATUS     mandatory
   DESCRIPTION
     "An entry in the mscBtdsStateTable."
   INDEX {
      mscBtdsIndex }
::= { mscBtdsStateTable 1 }

MscBtdsStateEntry ::= SEQUENCE {
   mscBtdsAdminState
      INTEGER,
   mscBtdsOperationalState
      INTEGER,
   mscBtdsUsageState
      INTEGER,
   mscBtdsAvailabilityStatus
      OCTET STRING,
   mscBtdsProceduralStatus
      OCTET STRING,
   mscBtdsControlStatus
      OCTET STRING,
   mscBtdsAlarmStatus
      OCTET STRING,
   mscBtdsStandbyStatus
      INTEGER,
   mscBtdsUnknownStatus
      INTEGER }

mscBtdsAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component.
      
      The OSI Status attributes, if supported by the component, may 
      provide more details, qualifying the state of the component."
   DEFVAL     { unlocked }
::= { mscBtdsStateEntry 1 }

mscBtdsOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle.
      
      The OSI Status attributes, if supported by the component, may 
      provide more details, qualifying the state of the component."
   DEFVAL     { disabled }
::= { mscBtdsStateEntry 2 }

mscBtdsUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time.
      
      The OSI Status attributes, if supported by the component, may 
      provide more details, qualifying the state of the component."
   DEFVAL     { idle }
::= { mscBtdsStateEntry 3 }

mscBtdsAvailabilityStatus OBJECT-TYPE
   SYNTAX     OCTET STRING (SIZE (2))
   ACCESS     read-only
   STATUS     mandatory
   DESCRIPTION
     "If supported by the component, this attribute indicates the OSI 
      Availability status of the component. Note that, even though it is 
      defined as a multi-valued set, at most one value is shown to the user.
      
      When no values are in the set, this indicates that either the attribute 
      is not supported or that none of the status conditions described 
      below are present.
      
      The value inTest indicates that the resource is undergoing a test 
      procedure. If adminState is locked or shuttingDown, the normal 
      users are precluded from using the resource and controlStatus is 
      reservedForTest. Tests that do not exclude additional users can be 
      present in any operational or administrative state but the 
      reservedForTest condition should not be present.
      
      The value failed indicates that the component has an internal fault 
      that prevents it from operating. The operationalState is disabled.
      
      The value dependency indicates that the component cannot operate 
      because some other resource on which it depends is unavailable. 
      The operationalState is disabled.
      
      The value powerOff indicates the resource requires power to be 
      applied and it is not powered on. The operationalState is disabled.
      
      The value offLine indicates the resource requires a routine 
      operation (either manual, automatic, or both) to be performed to 
      place it on-line and make it available for use. The operationalState 
      is disabled.
      
      The value offDuty indicates the resource is inactive in accordance 
      with a predetermined time schedule. In the absence of other 
      disabling conditions, the operationalState is enabled or disabled.
      
      The value degraded indicates the service provided by the 
      component is degraded in some way, such as in speed or operating 
      capacity. However, the resource remains available for service. The 
      operationalState is enabled.
      
      The value notInstalled indicates the resource is not present. The 
      operationalState is disabled.
      
      The value logFull is not used.

      Description of bits:
      inTest(0)
      failed(1)
      powerOff(2)
      offLine(3)
      offDuty(4)
      dependency(5)
      degraded(6)
      notInstalled(7)
      logFull(8)"
::= { mscBtdsStateEntry 4 }

mscBtdsProceduralStatus OBJECT-TYPE
   SYNTAX     OCTET STRING (SIZE (1))
   ACCESS     read-only
   STATUS     mandatory
   DESCRIPTION
     "If supported by the component, this attribute indicates the OSI 
      Procedural status of the component. Note that, even though it is 
      defined as a multi-valued set, at most one value is shown to the user.
      
      When no values are in the set, this indicates that either the attribute 
      is not supported or that none of the status conditions described 
      below are present.
      
      The value initializationRequired indicates (for a resource which 
      doesn't initialize autonomously) that initialization is required before 
      it can perform its normal functions, and this procedure has not been 
      initiated. The operationalState is disabled.
      
      The value notInitialized indicates (for a resource which does 
      initialize autonomously) that initialization is required before it can 
      perform its normal functions, and this procedure has not been 
      initiated. The operationalState may be enabled or disabled.
      
      The value initializing indicates that initialization has been initiated 
      but is not yet complete. The operationalState may be enabled or 
      disabled.
      
      The value reporting indicates the resource has completed some 
      processing operation and is notifying the results. The 
      operationalState is enabled.
      
      The value terminating indicates the component is in a termination 
      phase. If the resource doesn't reinitialize autonomously, 
      operationalState is disabled; otherwise it is enabled or disabled.

      Description of bits:
      initializationRequired(0)
      notInitialized(1)
      initializing(2)
      reporting(3)
      terminating(4)"
::= { mscBtdsStateEntry 5 }

mscBtdsControlStatus OBJECT-TYPE
   SYNTAX     OCTET STRING (SIZE (1))
   ACCESS     read-only
   STATUS     mandatory
   DESCRIPTION
     "If supported by the component, this attribute indicates the OSI 
      Control status of the component. Note that, even though it is defined 
      as a multi-valued set, at most one value is shown to the user.
      
      When no values are in the set, this indicates that either the attribute 
      is not supported or that none of the status conditions described 
      below are present.
      
      The value subjectToTest indicates the resource is available but tests 
      may be conducted simultaneously at unpredictable times, which 
      may cause it to exhibit unusual characteristics.
      
      The value partOfServicesLocked indicates that part of the service is 
      restricted from users of a resource. The adminState is unlocked.
      
      The value reservedForTest indicates that the component is 
      administratively unavailable because it is undergoing a test 
      procedure. The adminState is locked.
      
      The value suspended indicates that the service has been 
      administratively suspended.

      Description of bits:
      subjectToTest(0)
      partOfServicesLocked(1)
      reservedForTest(2)
      suspended(3)"
::= { mscBtdsStateEntry 6 }

mscBtdsAlarmStatus OBJECT-TYPE
   SYNTAX     OCTET STRING (SIZE (1))
   ACCESS     read-only
   STATUS     mandatory
   DESCRIPTION
     "If supported by the component, this attribute indicates the OSI 
      Alarm status of the component. Note that, even though it is defined 
      as a multi-valued set, at most one value is shown to the user.
      
      When no values are in the set, this indicates that either the attribute 
      is not supported or that none of the status conditions described 
      below are present.
      
      The value underRepair indicates the component is currently being 
      repaired. The operationalState is enabled or disabled.
      
      The value critical indicates one or more critical alarms are 
      outstanding against the component. Other, less severe, alarms may 
      also be outstanding. The operationalState is enabled or disabled.
      
      The value major indicates one or more major alarms are 
      outstanding against the component. Other, less severe, alarms may 
      also be outstanding. The operationalState is enabled or disabled.
      
      The value minor indicates one or more minor alarms are 
      outstanding against the component. Other, less severe, alarms may 
      also be outstanding. The operationalState is enabled or disabled.
      
      The value alarmOutstanding generically indicates that an alarm of 
      some severity is outstanding against the component.

      Description of bits:
      underRepair(0)
      critical(1)
      major(2)
      minor(3)
      alarmOutstanding(4)"
::= { mscBtdsStateEntry 7 }

mscBtdsStandbyStatus OBJECT-TYPE
   SYNTAX     INTEGER  {
                 hotStandby(0),
                 coldStandby(1),
                 providingService(2),
                 notSet(15) }
   ACCESS     read-only
   STATUS     mandatory
   DESCRIPTION
     "If supported by the component, this attribute indicates the OSI 
      Standby status of the component.
      
      The value notSet indicates that either the attribute is not supported 
      or that none of the status conditions described below are present. 
      Note that this is a non-standard value, used because the original 
      specification indicated this attribute was set-valued and thus, did not 
      provide a value to indicate that none of the other three are 
      applicable.
      
      The value hotStandby indicates that the resource is not providing 
      service but will be immediately able to take over the role of the 
      resource to be backed up, without initialization activity, and 
      containing the same information as the resource to be backed up.
      
      The value coldStandby indicates the resource is a backup for 
      another resource but will not be immediately able to take over the 
      role of the backed up resource and will require some initialization 
      activity.
      
      The value providingService indicates that this component, as a 
      backup resource, is currently backing up another resource."
   DEFVAL     { notSet }
::= { mscBtdsStateEntry 8 }

mscBtdsUnknownStatus OBJECT-TYPE
   SYNTAX     INTEGER  {
                 false(0),
                 true(1) }
   ACCESS     read-only
   STATUS     mandatory
   DESCRIPTION
     "This attribute indicates the OSI Unknown status of the component.
      
      The value false indicates that all of the other OSI State and Status 
      attribute values can be considered accurate.
      
      The value true indicates that the actual state of the component is not 
      known for sure."
   DEFVAL     { false }
::= { mscBtdsStateEntry 9 }

mscBtdsOperationalTable OBJECT-TYPE
   SYNTAX     SEQUENCE OF MscBtdsOperationalEntry
   ACCESS     not-accessible
   STATUS     mandatory
   DESCRIPTION
     "This group contains operational attributes related to a Btds."
::= { mscBtds 105 }

mscBtdsOperationalEntry OBJECT-TYPE
   SYNTAX     MscBtdsOperationalEntry
   ACCESS     not-accessible
   STATUS     mandatory
   DESCRIPTION
     "An entry in the mscBtdsOperationalTable."
   INDEX {
      mscBtdsIndex }
::= { mscBtdsOperationalTable 1 }

MscBtdsOperationalEntry ::= SEQUENCE {
   mscBtdsServiceFailureReason
      OCTET STRING }

mscBtdsServiceFailureReason OBJECT-TYPE
   SYNTAX     OCTET STRING (SIZE (2))
   ACCESS     read-only
   STATUS     mandatory
   DESCRIPTION
     "This attribute indicates the result of end to end negotiation with the 
      remote end across the subnet.
      
      If serviceFailureReason is undetermined, this Btds has not 
      performed end to end negotiation with the remote end, and may or 
      may not be up. serviceFailureReason is undetermined if this Btds 
      just became enabled, if there is not enough available bandwidth to 
      perform negotiation or if the remote end cannot perform negotiation 
      with this Btds.
      If serviceFailureReason is none, end to end negotiation passed.
      If serviceFailureReason is mismatchedService, end to end 
      negotiation failed because the remote end service is not a Btds.
      If serviceFailureReason is mismatchedTimeSlotAlignment, end to 
      end negotiation failed because the local Btds Framer 
      timeSlotAlignment does not match the remote Btds Framer 
      timeSlotAlignment.
      If serviceFailureReason is mismatchedCallDiscriminator, the local 
      Btds call discrimination subcomponents (Btds Mcdn and Btds 
      Dpnss1) do not match the remote Btds call discrimination 
      subcomponents.
      If serviceFailureReason is compDecodeFailed, end to end 
      negotiation failed because the information received from the remote 
      end was not recognized as valid data.

      Description of bits:
      none(0)
      undetermined(1)
      logicalConnection(2)
      mismatchedService(3)
      mismatchedTimeSlotAlignment(4)
      mismatchedCallDiscriminator(5)
      notused6(6)
      notused7(7)
      notused8(8)
      notused9(9)
      notused10(10)
      notused11(11)
      notused12(12)
      notused13(13)
      compDecodeFailed(14)"
::= { mscBtdsOperationalEntry 1 }


-- Btds/n Framer
-- The Framer component controls link layer framing for application 
-- components sending and receiving data on a link interface. It is also 
-- through Framer, that an application component is associated with a 
-- specific hardware link interface.
-- 
-- The Framer component provides provisionable attributes related to 
-- datapath aspects of the hardware interface rather than interface 
-- specific attributes which are associated with specific hardware 
-- components (such as V35/n or DS1/n). The Framer component also 
-- provides a provisionable attribute which binds the application 
-- component to a specific hardware component.
-- The Framer component contains operational attributes for link 
-- interface datapath statistics (such as frame counts).

mscBtdsFramer OBJECT IDENTIFIER ::= { mscBtds 2 }



mscBtdsFramerRowStatusTable OBJECT-TYPE
   SYNTAX     SEQUENCE OF MscBtdsFramerRowStatusEntry
   ACCESS     not-accessible
   STATUS     mandatory
   DESCRIPTION
     "This entry controls the addition and deletion of 
      mscBtdsFramer components."
::= { mscBtdsFramer 1 }

mscBtdsFramerRowStatusEntry OBJECT-TYPE
   SYNTAX     MscBtdsFramerRowStatusEntry
   ACCESS     not-accessible
   STATUS     mandatory
   DESCRIPTION
     "A single entry in the table represents a single 
      mscBtdsFramer component."
   INDEX {
      mscBtdsIndex,
      mscBtdsFramerIndex }
::= { mscBtdsFramerRowStatusTable 1 }

MscBtdsFramerRowStatusEntry ::= SEQUENCE {
   mscBtdsFramerRowStatus
      RowStatus,
   mscBtdsFramerComponentName
      DisplayString,
   mscBtdsFramerStorageType
      StorageType,
   mscBtdsFramerIndex
      NonReplicated }

mscBtdsFramerRowStatus OBJECT-TYPE
   SYNTAX     RowStatus 
   ACCESS     read-only
   STATUS     mandatory
   DESCRIPTION
     "This variable is used as the basis for SNMP naming of
      mscBtdsFramer components.
      These components cannot be added nor deleted."
::= { mscBtdsFramerRowStatusEntry 1 }

mscBtdsFramerComponentName OBJECT-TYPE
   SYNTAX     DisplayString 
   ACCESS     read-only
   STATUS     mandatory
   DESCRIPTION
     "This variable provides the component's string name for
      use with the ASCII Console Interface"
::= { mscBtdsFramerRowStatusEntry 2 }

mscBtdsFramerStorageType OBJECT-TYPE
   SYNTAX     StorageType 
   ACCESS     read-only
   STATUS     mandatory
   DESCRIPTION
     "This variable represents the storage type value for the
      mscBtdsFramer tables."
::= { mscBtdsFramerRowStatusEntry 4 }

mscBtdsFramerIndex OBJECT-TYPE
   SYNTAX     NonReplicated 
   ACCESS     not-accessible
   STATUS     mandatory
   DESCRIPTION
     "This variable represents the index for the mscBtdsFramer tables."
::= { mscBtdsFramerRowStatusEntry 10 }

mscBtdsFramerProvTable OBJECT-TYPE
   SYNTAX     SEQUENCE OF MscBtdsFramerProvEntry
   ACCESS     not-accessible
   STATUS     mandatory
   DESCRIPTION
     "This group contains the base provisioning data for the Framer 
      component. Application or hardware interface specific provisioning 
      data is contained in other provisionable Framer groups."
::= { mscBtdsFramer 10 }

mscBtdsFramerProvEntry OBJECT-TYPE
   SYNTAX     MscBtdsFramerProvEntry
   ACCESS     not-accessible
   STATUS     mandatory
   DESCRIPTION
     "An entry in the mscBtdsFramerProvTable."
   INDEX {
      mscBtdsIndex,
      mscBtdsFramerIndex }
::= { mscBtdsFramerProvTable 1 }

MscBtdsFramerProvEntry ::= SEQUENCE {
   mscBtdsFramerInterfaceName
      Link }

mscBtdsFramerInterfaceName OBJECT-TYPE
   SYNTAX     Link 
   ACCESS     read-write
   STATUS     mandatory
   DESCRIPTION
     "This attribute contains a hardware component name.
      
      The attribute associates the application with a specific link. This 
      defines the module processor on which Framer's parent component 
      (as well as Framer itself) will run."
::= { mscBtdsFramerProvEntry 1 }

mscBtdsFramerChannelTable OBJECT-TYPE
   SYNTAX     SEQUENCE OF MscBtdsFramerChannelEntry
   ACCESS     not-accessible
   STATUS     mandatory
   DESCRIPTION
     "This group contains attributes defining the framing of data on the 
      link interface or n*64kbps channel."
::= { mscBtdsFramer 11 }

mscBtdsFramerChannelEntry OBJECT-TYPE
   SYNTAX     MscBtdsFramerChannelEntry
   ACCESS     not-accessible
   STATUS     mandatory
   DESCRIPTION
     "An entry in the mscBtdsFramerChannelTable."
   INDEX {
      mscBtdsIndex,
      mscBtdsFramerIndex }
::= { mscBtdsFramerChannelTable 1 }

MscBtdsFramerChannelEntry ::= SEQUENCE {
   mscBtdsFramerProtocol
      INTEGER,
   mscBtdsFramerNumOfIdleBytesToMonitor
      Unsigned32,
   mscBtdsFramerIdlePattern
      Hex,
   mscBtdsFramerTimeSlotAlignment
      INTEGER,
   mscBtdsFramerInsertedOutputDelay
      Unsigned32,
   mscBtdsFramerBtdsCellSize
      INTEGER }

mscBtdsFramerProtocol OBJECT-TYPE
   SYNTAX     INTEGER  {
                 none(0),
                 hdlc(1),
                 nrziHdlc(2),
                 universal(3) }
   ACCESS     read-write
   STATUS     mandatory
   DESCRIPTION
     "This attribute specifies the ingress frames suppressed by this Btds.
      If protocol is none, this Btds does not suppress any ingress frames.
      If protocol is hdlc, this Btds suppresses ingress frames where each 
      byte is an identical non-inverted hdlc idle pattern, but only after two 
      or more consecutive frames meet this description.
      If protocol is nrziHdlc, this Btds suppresses ingress frames where 
      each byte is an identical NRZI encoded hdlc idle pattern, but only 
      after two or more consecutive frames meet this description.
      If protocol is universal, this Btds suppresses ingress frames where 
      each 16-bit word is identical, but only after a provisionable number 
      of consecutive frames meet this description. The number of 
      consecutive frames is determined by numOfIdleBytesToMonitor.
      Note that the number of idle bytes suppressed at the ingress side 
      does not necessarily equal the number of idle bytes generated at the 
      egress side.
      
      It is a semantic check warning if protocol is hdlc, nrziHdlc or 
      universal and this Btds is running on a 1pE1Mvp, 1pDS1Mvp or 
      1pTTC2mMvp card."
   DEFVAL     { none }
::= { mscBtdsFramerChannelEntry 7 }

mscBtdsFramerNumOfIdleBytesToMonitor OBJECT-TYPE
   SYNTAX     Unsigned32 (0..32000)
   ACCESS     read-write
   STATUS     mandatory
   DESCRIPTION
     "This attribute specifies the number of consecutive repeated ingress 
      16-bit words this Btds must encounter before suppressing universal 
      ingress idle frames. This attribute is only used if protocol is 
      universal.
      numOfIdleBytesToMonitor should be larger than the largest frame 
      size that can be sent into this Btds."
   DEFVAL     { 0 }
::= { mscBtdsFramerChannelEntry 8 }

mscBtdsFramerIdlePattern OBJECT-TYPE
   SYNTAX     Hex (0..255)
   ACCESS     read-write
   STATUS     mandatory
   DESCRIPTION
     "This attribute specifies how to fill a local egress frame when the 
      remote Btds suppressed an ingress frame."
   DEFVAL     { 255 }
::= { mscBtdsFramerChannelEntry 9 }

mscBtdsFramerTimeSlotAlignment OBJECT-TYPE
   SYNTAX     INTEGER  {
                 unaligned(0),
                 frameAligned(1) }
   ACCESS     read-write
   STATUS     mandatory
   DESCRIPTION
     "This attribute specifies the time slot alignment of this Btds. With 
      time slot alignment, data sent out on a particular time slot to a link 
      is received on the same time slot. A value of unaligned specifies the 
      regular Btds application. A value of frameAligned enables frame 
      aligned Btds. When framed aligned Btds is specified, only one 
      channel may be provisioned since only one fraction of N x 64 kbit/s 
      is presently available.
      
      timeSlotAlignment can not be set to frameAligned unless this Btds 
      is running on a DS1V, E1V, 1pDS1V or 1pE1V card
      timeSlotAlignment must have the same value at both ends of a Btds. 
      If timeSlotAlignment does not have the same value at both ends of a 
      Btds, the Btds will be out of service. In this case, Btds 
      serviceFailureReason is mismatchedTimeSlotAlignment."
   DEFVAL     { unaligned }
::= { mscBtdsFramerChannelEntry 10 }

mscBtdsFramerInsertedOutputDelay OBJECT-TYPE
   SYNTAX     Unsigned32 (0..50)
   ACCESS     read-write
   STATUS     mandatory
   DESCRIPTION
     "This attribute defines the amount of added output delay to 
      compensate for cross network delay variations. Cross network delay 
      variations is a function of the network topology. Settingthis attribute 
      will allow the Btds service to deal with cross network delay 
      variations.                                                                           This 
      attribute provides for delay in addition to the elastic buffer. Total 
      egress delay is approximately the insertedOutputDelayplus the 
      elastic buffer. The elastic buffer is the packetization timex5 cells in 
      the buffer. Packetization time per cell is calculated by taking the 
      inverse of [linespeed(kbits/sec) x (byte/8bits) x (1/cellsize (bytes))]. 
      This value is msec.The value for insertedOutputDelay should be 
      increased if the frmUnderRuns is increasing and frmLostInNetwork 
      is not increasing."
   DEFVAL     { 12 }
::= { mscBtdsFramerChannelEntry 11 }

mscBtdsFramerBtdsCellSize OBJECT-TYPE
   SYNTAX     INTEGER  {
                 n44(0),
                 n84(1) }
   ACCESS     read-write
   STATUS     mandatory
   DESCRIPTION
     "This attribute allows selection of larger BTDS cell sizes. Larger 
      BTDS cell sizes improve efficiency but increase the minimum 
      egress queue delay. If the associated channel is using less than 5 
      timeslots (320 kbits/sec), the default btdsCellSize will be used. 
      Setting btdsCellSize to 84 is only allowed on DS1 and E1 FPs."
   DEFVAL     { n44 }
::= { mscBtdsFramerChannelEntry 12 }

mscBtdsFramerStateTable OBJECT-TYPE
   SYNTAX     SEQUENCE OF MscBtdsFramerStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscBtdsFramer 12 }

mscBtdsFramerStateEntry OBJECT-TYPE
   SYNTAX     MscBtdsFramerStateEntry
   ACCESS     not-accessible
   STATUS     mandatory
   DESCRIPTION
     "An entry in the mscBtdsFramerStateTable."
   INDEX {
      mscBtdsIndex,
      mscBtdsFramerIndex }
::= { mscBtdsFramerStateTable 1 }

MscBtdsFramerStateEntry ::= SEQUENCE {
   mscBtdsFramerAdminState
      INTEGER,
   mscBtdsFramerOperationalState
      INTEGER,
   mscBtdsFramerUsageState
      INTEGER }

mscBtdsFramerAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscBtdsFramerStateEntry 1 }

mscBtdsFramerOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscBtdsFramerStateEntry 2 }

mscBtdsFramerUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscBtdsFramerStateEntry 3 }

mscBtdsFramerStatsTable OBJECT-TYPE
   SYNTAX     SEQUENCE OF MscBtdsFramerStatsEntry
   ACCESS     not-accessible
   STATUS     mandatory
   DESCRIPTION
     "This group contains the operational statistics data for a Framer 
      component."
::= { mscBtdsFramer 13 }

mscBtdsFramerStatsEntry OBJECT-TYPE
   SYNTAX     MscBtdsFramerStatsEntry
   ACCESS     not-accessible
   STATUS     mandatory
   DESCRIPTION
     "An entry in the mscBtdsFramerStatsTable."
   INDEX {
      mscBtdsIndex,
      mscBtdsFramerIndex }
::= { mscBtdsFramerStatsTable 1 }

MscBtdsFramerStatsEntry ::= SEQUENCE {
   mscBtdsFramerFrmFromIf
      Counter32,
   mscBtdsFramerSuppressedFrames
      Counter32,
   mscBtdsFramerFrmToIf
      Counter32,
   mscBtdsFramerLrcErrors
      Counter32,
   mscBtdsFramerFrmLostInNetwork
      Counter32,
   mscBtdsFramerFrmUnderRuns
      Counter32,
   mscBtdsFramerFrmDumped
      Counter32 }

mscBtdsFramerFrmFromIf OBJECT-TYPE
   SYNTAX     Counter32 
   ACCESS     read-only
   STATUS     mandatory
   DESCRIPTION
     "This attribute counts the number of frames received from the link 
      interface by Framer.
      This count wraps to zero after reaching its maximum value."
::= { mscBtdsFramerStatsEntry 1 }

mscBtdsFramerSuppressedFrames OBJECT-TYPE
   SYNTAX     Counter32 
   ACCESS     read-only
   STATUS     mandatory
   DESCRIPTION
     "This attribute counts the number of frames dropped at the interface 
      due to the idle pattern being detected.
      This count wraps to zero after reaching its maximum value."
::= { mscBtdsFramerStatsEntry 3 }

mscBtdsFramerFrmToIf OBJECT-TYPE
   SYNTAX     Counter32 
   ACCESS     read-only
   STATUS     mandatory
   DESCRIPTION
     "This attribute counts the number of frames transmitted to the link 
      interface by Framer.
      This count wraps to zero after reaching its maximum value."
::= { mscBtdsFramerStatsEntry 4 }

mscBtdsFramerLrcErrors OBJECT-TYPE
   SYNTAX     Counter32 
   ACCESS     read-only
   STATUS     mandatory
   DESCRIPTION
     "This attribute counts the number of frames received from the 
      network with LRC errors.
      This count wraps to zero after reaching its maximum value."
::= { mscBtdsFramerStatsEntry 5 }

mscBtdsFramerFrmLostInNetwork OBJECT-TYPE
   SYNTAX     Counter32 
   ACCESS     read-only
   STATUS     mandatory
   DESCRIPTION
     "This attribute counts the number of frames which the service knows 
      it did not receive from the network although they were sent in to the 
      network from the far end.
      This count wraps to zero after reaching its maximum value."
::= { mscBtdsFramerStatsEntry 6 }

mscBtdsFramerFrmUnderRuns OBJECT-TYPE
   SYNTAX     Counter32 
   ACCESS     read-only
   STATUS     mandatory
   DESCRIPTION
     "This attribute counts the number of times that a frame was needed 
      but was not available because it had been delayed too long in the 
      network.
      This error may occur repeatedly if the interface clocks at the two 
      access points to the network are operating at different rates.
      This count wraps to zero after reaching its maximum value."
::= { mscBtdsFramerStatsEntry 7 }

mscBtdsFramerFrmDumped OBJECT-TYPE
   SYNTAX     Counter32 
   ACCESS     read-only
   STATUS     mandatory
   DESCRIPTION
     "This attribute counts the number of frames which have been 
      dumped because the local interface output queue grew too large. 
      This can occur if the clock rate on the local interface is faster than 
      the clock rate on the remote interface and there are no silence 
      periods to absorb the difference.
      This count wraps to zero after reaching its maximum value."
::= { mscBtdsFramerStatsEntry 8 }


-- Btds/n PLC
-- This is the description of the PLC Component for the Btds service.. 

mscBtdsPlc OBJECT IDENTIFIER ::= { mscBtds 3 }



mscBtdsPlcRowStatusTable OBJECT-TYPE
   SYNTAX     SEQUENCE OF MscBtdsPlcRowStatusEntry
   ACCESS     not-accessible
   STATUS     mandatory
   DESCRIPTION
     "This entry controls the addition and deletion of 
      mscBtdsPlc components."
::= { mscBtdsPlc 1 }

mscBtdsPlcRowStatusEntry OBJECT-TYPE
   SYNTAX     MscBtdsPlcRowStatusEntry
   ACCESS     not-accessible
   STATUS     mandatory
   DESCRIPTION
     "A single entry in the table represents a single 
      mscBtdsPlc component."
   INDEX {
      mscBtdsIndex,
      mscBtdsPlcIndex }
::= { mscBtdsPlcRowStatusTable 1 }

MscBtdsPlcRowStatusEntry ::= SEQUENCE {
   mscBtdsPlcRowStatus
      RowStatus,
   mscBtdsPlcComponentName
      DisplayString,
   mscBtdsPlcStorageType
      StorageType,
   mscBtdsPlcIndex
      NonReplicated }

mscBtdsPlcRowStatus OBJECT-TYPE
   SYNTAX     RowStatus 
   ACCESS     read-only
   STATUS     mandatory
   DESCRIPTION
     "This variable is used as the basis for SNMP naming of
      mscBtdsPlc components.
      These components cannot be added nor deleted."
::= { mscBtdsPlcRowStatusEntry 1 }

mscBtdsPlcComponentName OBJECT-TYPE
   SYNTAX     DisplayString 
   ACCESS     read-only
   STATUS     mandatory
   DESCRIPTION
     "This variable provides the component's string name for
      use with the ASCII Console Interface"
::= { mscBtdsPlcRowStatusEntry 2 }

mscBtdsPlcStorageType OBJECT-TYPE
   SYNTAX     StorageType 
   ACCESS     read-only
   STATUS     mandatory
   DESCRIPTION
     "This variable represents the storage type value for the
      mscBtdsPlc tables."
::= { mscBtdsPlcRowStatusEntry 4 }

mscBtdsPlcIndex OBJECT-TYPE
   SYNTAX     NonReplicated 
   ACCESS     not-accessible
   STATUS     mandatory
   DESCRIPTION
     "This variable represents the index for the mscBtdsPlc tables."
::= { mscBtdsPlcRowStatusEntry 10 }

mscBtdsPlcProvTable OBJECT-TYPE
   SYNTAX     SEQUENCE OF MscBtdsPlcProvEntry
   ACCESS     not-accessible
   STATUS     mandatory
   DESCRIPTION
     "This group contains all provisionable attributes for a permanent 
      logical connection. Note that all of the attributes are valid and 
      provisionable on both ends of a connection. However with the 
      exception of remoteName, all operational attributes are derived 
      from the originating end provisioning, which may be either end 
      unless remoteName is not provisioned on one end."
::= { mscBtdsPlc 10 }

mscBtdsPlcProvEntry OBJECT-TYPE
   SYNTAX     MscBtdsPlcProvEntry
   ACCESS     not-accessible
   STATUS     mandatory
   DESCRIPTION
     "An entry in the mscBtdsPlcProvTable."
   INDEX {
      mscBtdsIndex,
      mscBtdsPlcIndex }
::= { mscBtdsPlcProvTable 1 }

MscBtdsPlcProvEntry ::= SEQUENCE {
   mscBtdsPlcRemoteName
      AsciiString,
   mscBtdsPlcSetupPriority
      Unsigned32,
   mscBtdsPlcHoldingPriority
      Unsigned32,
   mscBtdsPlcRequiredTxBandwidth
      Unsigned32,
   mscBtdsPlcRequiredRxBandwidth
      Unsigned32,
   mscBtdsPlcRequiredTrafficType
      INTEGER,
   mscBtdsPlcPermittedTrunkTypes
      OCTET STRING,
   mscBtdsPlcRequiredSecurity
      Unsigned32,
   mscBtdsPlcRequiredCustomerParm
      Unsigned32,
   mscBtdsPlcPathAttributeToMinimize
      INTEGER,
   mscBtdsPlcMaximumAcceptableCost
      Unsigned32,
   mscBtdsPlcMaximumAcceptableDelay
      Unsigned32,
   mscBtdsPlcEmissionPriority
      Unsigned32,
   mscBtdsPlcDiscardPriority
      Unsigned32,
   mscBtdsPlcPathType
      INTEGER,
   mscBtdsPlcPathFailureAction
      INTEGER,
   mscBtdsPlcBumpPreference
      INTEGER,
   mscBtdsPlcOptimization
      INTEGER,
   mscBtdsPlcAddressToCall
      AsciiString,
   mscBtdsPlcLocalAddress
      AsciiString,
   mscBtdsPlcMaximumAcceptableGatewayCost
      Unsigned32 }

mscBtdsPlcRemoteName OBJECT-TYPE
   SYNTAX     AsciiString (SIZE (0..40))
   ACCESS     read-write
   STATUS     mandatory
   DESCRIPTION
     "This attribute is the PLC's remote end point's address in the format 
      of a Passport component name. The syntax of a component is:
      'em/node type/instance'. For an alternative representation of end 
      point's addresses, see addressToCall and localAddress PLC 
      attributes. When using Passport component name representation, 
      end points are identified using a node name and a service name. As 
      an example, the end point component for a third Btds service on 
      node MoonBase is: 'EM/MoonBase BTDS/3'. If the remoteName is 
      provisioned, it must match the name of the remote end or the 
      connection will not be established even if the remote end is 
      provisioned correctly. If no remoteName is provisioned, then this 
      LC will accept connections from any other remote LC and it will 
      not originate calls. Connections establish faster and are unique if 
      both ends are provisioned with remoteName. 
      RemoteName should be used when the remote end of the connection 
      resides within the same topology region. If it resides in a different 
      topology region, then addressToCall and localAddress PLC 
      attributes should be used. When both remoteName and 
      addressToCall are provisioned, addressToCall takes precedence. 
      That is, connection will be established to the service specified by 
      addressToCall.
      These strings are case insensitive, but the complete component 
      name must be input."
   DEFVAL     { ''H }  -- ""
::= { mscBtdsPlcProvEntry 2 }

mscBtdsPlcSetupPriority OBJECT-TYPE
   SYNTAX     Unsigned32 (0..4)
   ACCESS     read-write
   STATUS     mandatory
   DESCRIPTION
     "This attribute gives the priority at which a path is established. Zero 
      is the highest priority and four is the lowest. When PORS 
      establishes a path through the network, it uses the setupPriority 
      attribute to determine its potential for bumping established paths to 
      acquire their bandwidth. The holdingPriority, a complementary 
      attribute of this attribute, indicates the priority a path maintains 
      once it is established. A new path can bump an existing path if the 
      new path's setupPriority is higher (numerically less) than the 
      existing path's holdingPriority."
   DEFVAL     { 2 }
::= { mscBtdsPlcProvEntry 3 }

mscBtdsPlcHoldingPriority OBJECT-TYPE
   SYNTAX     Unsigned32 (0..4)
   ACCESS     read-write
   STATUS     mandatory
   DESCRIPTION
     "This attribute gives the priority that a path holds once it is 
      established. Zero(0) is the highest priority and four(4) is the lowest. 
      A path's holdingPriority determines its likelihood of being bumped 
      by a new path to acquire its bandwidth. The setupPriority, a 
      complementary attribute, indicates the priority of a path at 
      establishment time. A new path can bump an existing path if the 
      new path's setupPriority is higher (numerically less) than the 
      existing path's holdingPriority."
   DEFVAL     { 2 }
::= { mscBtdsPlcProvEntry 4 }

mscBtdsPlcRequiredTxBandwidth OBJECT-TYPE
   SYNTAX     Unsigned32 (0..4294967295)
   ACCESS     read-write
   STATUS     mandatory
   DESCRIPTION
     "This attribute gives the bandwidth (in bits per second) reserved by a 
      path on each of the trunks of its route. This attribute represents the 
      bandwidth for traffic outgoing to the remote end point. This value 
      should be chosen to achieve the amount of statistical bandwidth 
      sharing that is desired by the network administration. This 
      reservation is not enforced and is used to determine how many paths 
      can be supported on a trunk. Both ends should be provisioned with 
      the correct values allowing for the fact that Transmit at this end 
      represents Receive at the remote end. Note that when the values do 
      not correspond the originating end of the connection determines the 
      value."
   DEFVAL     { 64000 }
::= { mscBtdsPlcProvEntry 5 }

mscBtdsPlcRequiredRxBandwidth OBJECT-TYPE
   SYNTAX     Unsigned32 (0..4294967295)
   ACCESS     read-write
   STATUS     mandatory
   DESCRIPTION
     "This attribute gives the bandwidth (in bits per second) reserved by a 
      path on each of trunks of its route. This attribute represents the 
      bandwidth for traffic incoming from the remote end point. This 
      value should be chosen to achieve the amount of statistical 
      bandwidth sharing that is desired by the network administration. 
      This reservation is not enforced and is used to determine how many 
      paths can be supported on a trunk. Both ends should be provisioned 
      with the correct values allowing for the fact that transmit at this end 
      represents receive at the remote end. Note that when the values do 
      not correspond, the originating end of the connection determines the 
      value."
   DEFVAL     { 64000 }
::= { mscBtdsPlcProvEntry 6 }

mscBtdsPlcRequiredTrafficType OBJECT-TYPE
   SYNTAX     INTEGER  {
                 voice(0),
                 data(1),
                 video(2),
                 trafficType1(3),
                 trafficType2(4),
                 trafficType3(5),
                 trafficType4(6),
                 trafficType5(7) }
   ACCESS     read-write
   STATUS     mandatory
   DESCRIPTION
     "This attribute indicates the type of traffic transmitted over the path. 
      There are eight(8) possible traffic types, and the path can transmit 
      only one of them. The originating end of the connection determines 
      the type. These are arbitrary designations for traffic type. The voice, 
      data and video traffic types are defined, and five(5) other arbitrary 
      traffic types can be defined by the network administration. This 
      attribute is used in the route selection process to restrict the route to 
      trunks that support this traffic type. The supportedTrafficType trunk 
      attribute lists all the types of traffic allowed on the trunk. For 
      example, if requiredTrafficType is specified as trafficType1, then 
      only trunks that include trafficType1 in supportedTrafficType, will 
      be candidates for this connection."
   DEFVAL     { video }
::= { mscBtdsPlcProvEntry 7 }

mscBtdsPlcPermittedTrunkTypes OBJECT-TYPE
   SYNTAX     OCTET STRING (SIZE (1))
   ACCESS     read-write
   STATUS     mandatory
   DESCRIPTION
     "This attribute lists up to eight(8) types of trunk that can be used on 
      the route. The terrestrial and satellite trunk types have been 
      defined, leaving six(6) remaining arbitrary types that can be defined 
      by the network administration. The trunk's type is indicated in the 
      trunkType attribute of the Trunk component. When selecting a 
      route, PORS only chooses trunks whose trunkType are in the 
      permittedTrunkTypes for the path.

      Description of bits:
      terrestrial(0)
      satellite(1)
      trunkType1(2)
      trunkType2(3)
      trunkType3(4)
      trunkType4(5)
      trunkType5(6)
      trunkType6(7)"
   DEFVAL     { 'f8'H }
::= { mscBtdsPlcProvEntry 8 }

mscBtdsPlcRequiredSecurity OBJECT-TYPE
   SYNTAX     Unsigned32 (0..7)
   ACCESS     read-write
   STATUS     mandatory
   DESCRIPTION
     "This attribute indicates the required minimum level of security of 
      the trunks on the route. Zero represents the most secure and seven 
      represents the least secure. The trunk's security is indicated by the 
      trunkSecurity attribute of the Trunk component, and has values 
      identical in range and meaning to the requiredSecurity attribute. 
      PORS ensures that any route selected does not contain a trunk 
      whose trunkSecurity attribute is numerically greater than the 
      requiredSecurity."
   DEFVAL     { 4 }
::= { mscBtdsPlcProvEntry 9 }

mscBtdsPlcRequiredCustomerParm OBJECT-TYPE
   SYNTAX     Unsigned32 (0..7)
   ACCESS     read-write
   STATUS     mandatory
   DESCRIPTION
     "This attribute indicates the allowed customer defined parameter of 
      the trunks on the route. Its value, a number from zero to seven, is 
      chosen by network administration to have a meaning specific to 
      their network, thus allowing them to customize the use of their 
      trunks. A complementary trunk attribute, customerParameter, also 
      has a value from zero to seven. The route selection process does not 
      consider trunks whose customerParameter is greater than the 
      requiredCustomerParameter of the path."
   DEFVAL     { 4 }
::= { mscBtdsPlcProvEntry 10 }

mscBtdsPlcPathAttributeToMinimize OBJECT-TYPE
   SYNTAX     INTEGER  {
                 cost(0),
                 delay(1) }
   ACCESS     read-write
   STATUS     mandatory
   DESCRIPTION
     "This attribute indicates whether a route is selected on the basis of 
      minimizing the cost or the delay. Each trunk has a cost and a delay 
      metric associated with it. The cost of a selected route is the sum of 
      the trunk cost metrics for all trunks included in the route. The delay 
      of a selected route is the sum of the trunk delay metric for all trunks 
      included in the route."
   DEFVAL     { cost }
::= { mscBtdsPlcProvEntry 11 }

mscBtdsPlcMaximumAcceptableCost OBJECT-TYPE
   SYNTAX     Unsigned32 (0..65535)
   ACCESS     read-write
   STATUS     mandatory
   DESCRIPTION
     "This attribute indicates an upper bound on the cost metric of a route, 
      which is the sum of the cost metrics of all trunks on the route. The 
      cost metric is the trunkCost attribute of the Trunk component. If for 
      any trunk the trunkCost is larger than the maximumAcceptableCost, 
      then that trunk is not considered during the route selection. While a 
      shortest route is being selected, the route cost is being compared 
      with the maximumAcceptableCost attribute, and this is done for any 
      minimization criterion. No route is selected if the cost metric of the 
      shortest route is larger than the maximumAcceptableCost."
   DEFVAL     { 1280 }
::= { mscBtdsPlcProvEntry 12 }

mscBtdsPlcMaximumAcceptableDelay OBJECT-TYPE
   SYNTAX     Unsigned32 (0..100000)
   ACCESS     read-write
   STATUS     mandatory
   DESCRIPTION
     "This attribute indicates an upper bound on the delay of a route, 
      which is the sum of the delay of all trunks on the route. It should be 
      provisioned with a reasonable maximum acceptable delay for the 
      end to end one way delay of a 512-byte packet. Remember, that the 
      trunk during its staging measures a measuredRoundTripDelay. This 
      delay is divided by two and truncated to an integer number of 
      milliseconds to provide a one way delay which is used to populate 
      the delay in this trunk object in the topological database. The value 
      includes emission, propagation, and queuing delays. A 512-byte 
      packet is used to perform the measurement. 
      If for any trunk the half of the trunk's measuredRoundTripDelay is 
      larger than the maximumAcceptableDelay, then that trunk is not 
      considered during the route selection.
      While a shortest route is being selected, the route delay is being 
      compared with the maximumAcceptableDelay attribute, and this is 
      done for any minimization criterion. No route is selected if the 
      delay metric of the shortest route is larger than the 
      maximumAcceptableDelay."
   DEFVAL     { 100000 }
::= { mscBtdsPlcProvEntry 13 }

mscBtdsPlcEmissionPriority OBJECT-TYPE
   SYNTAX     Unsigned32 (0..2)
   ACCESS     read-write
   STATUS     mandatory
   DESCRIPTION
     "This attribute indicates the urgency with which packets on the path 
      are emitted by the trunks on the route. EmissionPriority of Zero(0) 
      indicates the highest emission priority, while two (2) indicates the 
      lowest emission priority. Packets with a higher emissionPriority (or 
      numerically less) are serviced and sent out before the packets of 
      lower emissionPriority (or numerically higher)."
   DEFVAL     { 0 }
::= { mscBtdsPlcProvEntry 14 }

mscBtdsPlcDiscardPriority OBJECT-TYPE
   SYNTAX     Unsigned32 (1..3)
   ACCESS     read-write
   STATUS     mandatory
   DESCRIPTION
     "This attribute indicates the importance of the packets on the path. 
      One is used for paths carrying the most important traffic, and three 
      is used for paths carrying the least important traffic. Packets with 
      lower discardPriority(numerically lower) are discarded after 
      packets with a higher discardPriority(numerically higher)."
   DEFVAL     { 1 }
::= { mscBtdsPlcProvEntry 15 }

mscBtdsPlcPathType OBJECT-TYPE
   SYNTAX     INTEGER  {
                 normal(0),
                 manual(1),
                 forced(2) }
   ACCESS     read-write
   STATUS     mandatory
   DESCRIPTION
     "This attribute specifies if the path for this PLC is determined 
      automatically or by static provisioning. The default (normal) is to 
      automatically choose a route with Route Selection. Normal 
      pathTypes require less provisioning and can dynamically handle 
      path failures. The other pathTypes are both manual pathTypes 
      where the operator must specify, through provisioning, a static route 
      termed the manualPath. A manual pathType connection is nearly 
      identical to a normal path type connection with the exception that 
      the route is pre-provisioned. For a manual pathType, bandwidth 
      reservations are respected along the path exactly as in a normal 
      path. The last type, the forced pathType, is also a manual path but 
      regardless of the bandwidth available the route is granted provided 
      the trunks are operational and there are sufficient Logical Channels 
      (LChs).
      The forced pathType could result in over committing the reserved 
      bandwidth allowed on a trunk. A better way to achieve the effects of 
      a forced pathType is to use a manual pathType with setupPriority = 
      0 and holdingPriority = 0. In this manner the path will reserve 
      correct bandwidth and it will bump other paths if required while not 
      being bumped itself."
   DEFVAL     { normal }
::= { mscBtdsPlcProvEntry 16 }

mscBtdsPlcPathFailureAction OBJECT-TYPE
   SYNTAX     INTEGER  {
                 disconnectConnection(0),
                 reRoutePath(1) }
   ACCESS     read-write
   STATUS     mandatory
   DESCRIPTION
     "This attribute is used to specify whether the application can tolerate 
      momentary interruption of a path while a new path is selected. If 
      disconnectConnection is chosen, the application is informed as 
      soon as possible about a failure by disconnection. If the attribute is 
      set to reRoutePath, the path may attempt an immediate reroute, 
      provided the failure is a recoverable failure. If rerouting fails the 
      application is informed of the failure. 
      With this option set to reRoutePath the LCo may wait up to 30 
      seconds before informing the service of complete disconnection in 
      order to allow both ends to attempt to reconnect. Note that if PLC 
      components are different at both ends only the calling end is 
      allowed to reconnect.
      All pathTypes respect this attribute. Also on a manualPath with 
      both ends provisioned with independent paths (at least with respect 
      to the failure) this option will have the desired effect that the path is 
      rerouted without complete disconnection at both ends."
   DEFVAL     { reRoutePath }
::= { mscBtdsPlcProvEntry 17 }

mscBtdsPlcBumpPreference OBJECT-TYPE
   SYNTAX     INTEGER  {
                 bumpWhenNecessary(0),
                 bumpToObtainBestRoute(1) }
   ACCESS     read-write
   STATUS     mandatory
   DESCRIPTION
     "This attribute controls when bumping occurs in the route selection 
      process. A connection with higher (numerically less) setupPriority 
      may bump a connection with lower (numerically higher) 
      holdingPriority in order to acquire its bandwidth and be established. 
      By default, bumping occurs only when it is necessary. That is, a 
      connection will bump another connection only if there is no other 
      way for the connection to be established. A connection may be set 
      to always bump in order to find the best route it may have."
   DEFVAL     { bumpWhenNecessary }
::= { mscBtdsPlcProvEntry 18 }

mscBtdsPlcOptimization OBJECT-TYPE
   SYNTAX     INTEGER  {
                 disabled(0),
                 enabled(1) }
   ACCESS     read-write
   STATUS     mandatory
   DESCRIPTION
     "This attribute is used to specify whether this connection should 
      attempt to optimize its path when requested by the routing PORS 
      component. Every path is as optimal as it can be when it is 
      established, but as network traffic patterns and configurations 
      change this path may no longer be as optimal as it could be. The 
      PORS connection manager on a module requests circuits to 
      optimize at the optimization interval."
   DEFVAL     { enabled }
::= { mscBtdsPlcProvEntry 19 }

mscBtdsPlcAddressToCall OBJECT-TYPE
   SYNTAX     AsciiString (SIZE (0..40))
   ACCESS     read-write
   STATUS     mandatory
   DESCRIPTION
     "This attribute is the PLC's remote end point's address in the format 
      of a NSAP address. As such it must consist of a string of hex digits 
      although not all 40 digits must be specified. For an alternative 
      representation of end point's addresses, see romoteName attribute. 
      If the addressToCall is provisioned, it must match localAddress 
      provisioned on the remote end or the connection will not be 
      established. Connections establish faster and are unique if both ends 
      are provisioned with addressToCall. AddressToCall must be used 
      when the romote end of the connection resides in different topology 
      region. If it resides in the same topology region, then romoteName 
      may be used. When both remoteName and addressToCall are 
      provisioned, addressToCall takes precedence. That is, connection 
      will be established to the service specified by addressToCall."
   DEFVAL     { ''H }  -- ""
::= { mscBtdsPlcProvEntry 20 }

mscBtdsPlcLocalAddress OBJECT-TYPE
   SYNTAX     AsciiString (SIZE (0..40))
   ACCESS     read-write
   STATUS     mandatory
   DESCRIPTION
     "This attribute is the PLC's end point address in the format of an 
      NSAP address. As such it must consist of a string of hex digits 
      although not all 40 digits must be specified. LocalAddress must 
      share a prefix with MOD nodePrefix or one of MOD 
      alternatePorsPrefixes for this node, otherwise PORS will not be able 
      to route calls to this service. LocalAddress is used in conjunction 
      with addressToCall. That is, the end responsible for originating 
      calls must have addressToCall provisioned, while the end 
      responsible for terminationg calls must have localAddress 
      provisioned. In such a case, addressToCall on the originating end 
      must match exactly the localAddress of the terminating end. Note 
      that both ends may be originating and terminating at the same time. 
      That is, both ends may have addressToCall and localAddress 
      provisioned as long as addressToCall and localAddress on different 
      ends are identical."
   DEFVAL     { ''H }  -- ""
::= { mscBtdsPlcProvEntry 21 }

mscBtdsPlcMaximumAcceptableGatewayCost OBJECT-TYPE
   SYNTAX     Unsigned32 (0..65535)
   ACCESS     read-write
   STATUS     mandatory
   DESCRIPTION
     "This attribute indicates an upper bound on the gateway cost metric 
      of a route, which is the sum of the gateway cost metrics of all 
      gateway links on the route. It has the same semantics as the 
      maximumAcceptableCost except that gateway cost metrics are used 
      instead of trunk cost metrics. Gateway cost metrics are provisioned 
      under Trunk Address component of a gateway link specifying a 
      gateway costs of reaching an address through the link."
   DEFVAL     { 2048 }
::= { mscBtdsPlcProvEntry 22 }

mscBtdsPlcMpathTable OBJECT-TYPE
   SYNTAX     SEQUENCE OF MscBtdsPlcMpathEntry
   ACCESS     not-accessible
   STATUS     mandatory
   DESCRIPTION
     "This attribute is optional and specifies the sequence of trunks to be 
      used as the route for the path, thus bypassing PORS' automatic 
      route selection. If the path fails the validation, no other path can be 
      selected1. This attribute should only be used in special cases since 
      the route selection algorithm is able to find and maintain the best 
      routes. A related path attribute, the pathType, determines if this 
      route will be used as a manual or forced path type. 
      As an example, the trunk component name for the third trunk on 
      node MoonBase is 'EM/MoonBase Trk/3'. Note that only the first 
      end of the trunk that the packet would encounter is provisioned. 
      These strings are case insensitive but the complete component name 
      must be input. 
      
      Note 1: the trunk designation must be a 3-letter form, e.g., 'trk'. 
      Note 2: only the outbound trunks component names are used to 
      provision the manualPath.
      
      Note 3: It is recommended to have two independent routes specified 
      for a manual path by specifying a different manualPath 
      (non-symmetric) for each end. In this case, there is no way to select 
      which route will be used (first up wins) but if one path is torn down 
      due to a failure then the other manualPath may be used to reroute 
      the path."
::= { mscBtdsPlc 262 }

mscBtdsPlcMpathEntry OBJECT-TYPE
   SYNTAX     MscBtdsPlcMpathEntry
   ACCESS     not-accessible
   STATUS     mandatory
   DESCRIPTION
     "An entry in the mscBtdsPlcMpathTable."
   INDEX {
      mscBtdsIndex,
      mscBtdsPlcIndex,
      mscBtdsPlcMpathIndex }
::= { mscBtdsPlcMpathTable 1 }

MscBtdsPlcMpathEntry ::= SEQUENCE {
   mscBtdsPlcMpathIndex
      Integer32,
   mscBtdsPlcMpathValue
      AsciiString }

mscBtdsPlcMpathIndex OBJECT-TYPE
   SYNTAX     Integer32 (0..9)
   ACCESS     not-accessible
   STATUS     mandatory
   DESCRIPTION
     "This variable represents the mscBtdsPlcMpathTable
      specific index for the mscBtdsPlcMpathTable."
::= { mscBtdsPlcMpathEntry 1 }

mscBtdsPlcMpathValue OBJECT-TYPE
   SYNTAX     AsciiString (SIZE (0..40))
   ACCESS     read-write
   STATUS     mandatory
   DESCRIPTION
     "This variable represents an individual value for the
      mscBtdsPlcMpathTable."
::= { mscBtdsPlcMpathEntry 2 }


-- ...Lc
-- This component contains all of the operation attributes for a Path 
-- Oriented Logical Connection.

mscBtdsLCo OBJECT IDENTIFIER ::= { mscBtds 4 }



mscBtdsLCoRowStatusTable OBJECT-TYPE
   SYNTAX     SEQUENCE OF MscBtdsLCoRowStatusEntry
   ACCESS     not-accessible
   STATUS     mandatory
   DESCRIPTION
     "This entry controls the addition and deletion of 
      mscBtdsLCo components."
::= { mscBtdsLCo 1 }

mscBtdsLCoRowStatusEntry OBJECT-TYPE
   SYNTAX     MscBtdsLCoRowStatusEntry
   ACCESS     not-accessible
   STATUS     mandatory
   DESCRIPTION
     "A single entry in the table represents a single 
      mscBtdsLCo component."
   INDEX {
      mscBtdsIndex,
      mscBtdsLCoIndex }
::= { mscBtdsLCoRowStatusTable 1 }

MscBtdsLCoRowStatusEntry ::= SEQUENCE {
   mscBtdsLCoRowStatus
      RowStatus,
   mscBtdsLCoComponentName
      DisplayString,
   mscBtdsLCoStorageType
      StorageType,
   mscBtdsLCoIndex
      NonReplicated }

mscBtdsLCoRowStatus OBJECT-TYPE
   SYNTAX     RowStatus 
   ACCESS     read-only
   STATUS     mandatory
   DESCRIPTION
     "This variable is used as the basis for SNMP naming of
      mscBtdsLCo components.
      These components cannot be added nor deleted."
::= { mscBtdsLCoRowStatusEntry 1 }

mscBtdsLCoComponentName OBJECT-TYPE
   SYNTAX     DisplayString 
   ACCESS     read-only
   STATUS     mandatory
   DESCRIPTION
     "This variable provides the component's string name for
      use with the ASCII Console Interface"
::= { mscBtdsLCoRowStatusEntry 2 }

mscBtdsLCoStorageType OBJECT-TYPE
   SYNTAX     StorageType 
   ACCESS     read-only
   STATUS     mandatory
   DESCRIPTION
     "This variable represents the storage type value for the
      mscBtdsLCo tables."
::= { mscBtdsLCoRowStatusEntry 4 }

mscBtdsLCoIndex OBJECT-TYPE
   SYNTAX     NonReplicated 
   ACCESS     not-accessible
   STATUS     mandatory
   DESCRIPTION
     "This variable represents the index for the mscBtdsLCo tables."
::= { mscBtdsLCoRowStatusEntry 10 }

mscBtdsLCoPathDataTable OBJECT-TYPE
   SYNTAX     SEQUENCE OF MscBtdsLCoPathDataEntry
   ACCESS     not-accessible
   STATUS     mandatory
   DESCRIPTION
     "This group contains all operational attributes for the path oriented 
      LCo."
::= { mscBtdsLCo 10 }

mscBtdsLCoPathDataEntry OBJECT-TYPE
   SYNTAX     MscBtdsLCoPathDataEntry
   ACCESS     not-accessible
   STATUS     mandatory
   DESCRIPTION
     "An entry in the mscBtdsLCoPathDataTable."
   INDEX {
      mscBtdsIndex,
      mscBtdsLCoIndex }
::= { mscBtdsLCoPathDataTable 1 }

MscBtdsLCoPathDataEntry ::= SEQUENCE {
   mscBtdsLCoState
      INTEGER,
   mscBtdsLCoOverrideRemoteName
      AsciiString,
   mscBtdsLCoEnd
      INTEGER,
   mscBtdsLCoCostMetric
      Unsigned32,
   mscBtdsLCoDelayMetric
      Unsigned32,
   mscBtdsLCoRoundTripDelay
      Unsigned32,
   mscBtdsLCoSetupPriority
      Unsigned32,
   mscBtdsLCoHoldingPriority
      Unsigned32,
   mscBtdsLCoRequiredTxBandwidth
      Gauge32,
   mscBtdsLCoRequiredRxBandwidth
      Gauge32,
   mscBtdsLCoRequiredTrafficType
      INTEGER,
   mscBtdsLCoPermittedTrunkTypes
      OCTET STRING,
   mscBtdsLCoRequiredSecurity
      Unsigned32,
   mscBtdsLCoRequiredCustomerParameter
      Unsigned32,
   mscBtdsLCoEmissionPriority
      Unsigned32,
   mscBtdsLCoDiscardPriority
      Unsigned32,
   mscBtdsLCoPathType
      INTEGER,
   mscBtdsLCoRetryCount
      Unsigned32,
   mscBtdsLCoPathFailureCount
      Unsigned32,
   mscBtdsLCoReasonForNoRoute
      INTEGER,
   mscBtdsLCoLastTearDownReason
      INTEGER,
   mscBtdsLCoPathFailureAction
      INTEGER,
   mscBtdsLCoBumpPreference
      INTEGER,
   mscBtdsLCoOptimization
      INTEGER,
   mscBtdsLCoPathUpDateTime
      EnterpriseDateAndTime }

mscBtdsLCoState OBJECT-TYPE
   SYNTAX     INTEGER  {
                 pathDown(0),
                 selectingRoute(1),
                 connecting(2),
                 pathUp(3),
                 pathDownRetrying(4) }
   ACCESS     read-only
   STATUS     mandatory
   DESCRIPTION
     "This attribute reflects the current state of the connection. The 
      pathDown state indicates a connection that has no remote end 
      provisioned or the application has not yet signalled for a path. The 
      selectingRoute state occurs when a request has been sent to route 
      selector and it has not yet responded. The connectingState occurs 
      while a path is being established. The pathUp state is the normal 
      operational state of a path. The pathDownRetrying state indicates a 
      path that attempted route selection but received no route and is now 
      waiting to retry route selection again."
::= { mscBtdsLCoPathDataEntry 1 }

mscBtdsLCoOverrideRemoteName OBJECT-TYPE
   SYNTAX     AsciiString (SIZE (0..40))
   ACCESS     read-write
   STATUS     mandatory
   DESCRIPTION
     "If set and the current PLC remoteName is blank this remoteName 
      will override the blank PLC remoteName. Usually you would set 
      this attribute and then lock/unlock the service component which 
      will result in this new overrideRemoteName being used as if it had 
      been provisioned into the PLC remoteName. The advantage of this 
      attribute is that the connection's remoteName can be changed 
      immediately without having to 'activate prov' but the disadvantage 
      is that the overrideRemoteName is not permanent and if the card or 
      switch is reset the override will be lost."
::= { mscBtdsLCoPathDataEntry 2 }

mscBtdsLCoEnd OBJECT-TYPE
   SYNTAX     INTEGER  {
                 calling(0),
                 called(1) }
   ACCESS     read-only
   STATUS     mandatory
   DESCRIPTION
     "This attribute identifies whether this is the calling or called end of 
      the path."
::= { mscBtdsLCoPathDataEntry 3 }

mscBtdsLCoCostMetric OBJECT-TYPE
   SYNTAX     Unsigned32 (0..65535)
   ACCESS     read-only
   STATUS     mandatory
   DESCRIPTION
     "This attribute gives the route's total cost metric. It is calculated as 
      the sum of the cost metric of all trunks in the path at the time the 
      connection was established. The cost metric of a trunk is defined by 
      the trunkCost attribute of the Trunk component. The costMetric for 
      an LCo that is originated and terminated on the same module is 0."
::= { mscBtdsLCoPathDataEntry 4 }

mscBtdsLCoDelayMetric OBJECT-TYPE
   SYNTAX     Unsigned32 (0..100000)
   ACCESS     read-only
   STATUS     mandatory
   DESCRIPTION
     "This attribute gives the total delay of the route as the one way delay 
      for a 512 byte packet. It is calculated as the sum of the delays of all 
      trunks in the path stored in topology at the time the connection was 
      established. The delay for an LCo that is originated and terminated 
      on the same module is 0."
::= { mscBtdsLCoPathDataEntry 5 }

mscBtdsLCoRoundTripDelay OBJECT-TYPE
   SYNTAX     Unsigned32 (0..200000)
   ACCESS     read-only
   STATUS     mandatory
   DESCRIPTION
     "This attribute contains the time taken for a packet (cell) of 44 bytes 
      to be transmitted to the remote LCo and return to this LCo. The 
      number reported is given in milliseconds to the nearest millisecond. 
      A value of one millisecond is reported if the time is less than 1 
      millisecond even though the delay may be less than 1 Millisecond 
      when the LCo is originated and terminated on the same module."
::= { mscBtdsLCoPathDataEntry 6 }

mscBtdsLCoSetupPriority OBJECT-TYPE
   SYNTAX     Unsigned32 (0..4)
   ACCESS     read-only
   STATUS     mandatory
   DESCRIPTION
     "This attribute gives the priority at which the current path is 
      established. Zero is the highest priority and four is the lowest. The 
      holdingPriority, a complementary attribute of this component, 
      indicates the priority a path maintains once it is established."
::= { mscBtdsLCoPathDataEntry 7 }

mscBtdsLCoHoldingPriority OBJECT-TYPE
   SYNTAX     Unsigned32 (0..4)
   ACCESS     read-only
   STATUS     mandatory
   DESCRIPTION
     "This attribute gives the priority at which a path holds its current 
      path once the path is established. Zero is the highest priority and 
      four is the lowest. The setupPriority, a complementary attribute, 
      indicates the priority of a path at establishment time."
::= { mscBtdsLCoPathDataEntry 8 }

mscBtdsLCoRequiredTxBandwidth OBJECT-TYPE
   SYNTAX     Gauge32 (0..4294967295)
   ACCESS     read-only
   STATUS     mandatory
   DESCRIPTION
     "This attribute gives the actual bandwidth (in bits per second) 
      reserved by this path on each of the trunks of its route. This attribute 
      represents the bandwidth for traffic outgoing to the remote end 
      point. The originating end of the connection determines this value."
::= { mscBtdsLCoPathDataEntry 9 }

mscBtdsLCoRequiredRxBandwidth OBJECT-TYPE
   SYNTAX     Gauge32 (0..4294967295)
   ACCESS     read-only
   STATUS     mandatory
   DESCRIPTION
     "This attribute gives the actual bandwidth (in bits per second) 
      reserved by this path on each of trunks of its route. This attribute 
      represents the bandwidth for traffic incoming from the remote end 
      point. The originating end of the connection determines this value"
::= { mscBtdsLCoPathDataEntry 10 }

mscBtdsLCoRequiredTrafficType OBJECT-TYPE
   SYNTAX     INTEGER  {
                 voice(0),
                 data(1),
                 video(2),
                 trafficType1(3),
                 trafficType2(4),
                 trafficType3(5),
                 trafficType4(6),
                 trafficType5(7) }
   ACCESS     read-only
   STATUS     mandatory
   DESCRIPTION
     "This operational attribute indicates the type of traffic transmitted 
      over the path. There are eight possible traffic types, and the path can 
      transmit only one of them. The originating end of the connection 
      determines the type. These are arbitrary designations for traffic 
      type. The voice, data and video traffic types are defined, and five 
      other arbitrary traffic types can be defined by the network 
      administration. This attribute is used in the route selection process 
      to restrict the route to trunks that support this traffic type. The 
      supportedTrafficType trunk attribute lists all the types of traffic 
      allowed on the trunk. For example, if requiredTrafficType is 
      specified as trafficType1 then only trunks that include trafficType1 
      in supportedTrafficType, will be candidates for this connection."
::= { mscBtdsLCoPathDataEntry 11 }

mscBtdsLCoPermittedTrunkTypes OBJECT-TYPE
   SYNTAX     OCTET STRING (SIZE (1))
   ACCESS     read-only
   STATUS     mandatory
   DESCRIPTION
     "This operational attribute lists up to eight types of trunk that can be 
      used on the route. The originating end of the connection determines 
      the types. The terrestrial and satellite trunk types have been 
      defined, leaving six remaining arbitrary types that can be defined by 
      the network administration. The trunk's type is indicated in the 
      trunkType attribute of the Trunk component. When selecting a 
      route, PORS only chooses trunks whose trunkType are in the 
      permittedTrunkTypes for the path.

      Description of bits:
      terrestrial(0)
      satellite(1)
      trunkType1(2)
      trunkType2(3)
      trunkType3(4)
      trunkType4(5)
      trunkType5(6)
      trunkType6(7)"
::= { mscBtdsLCoPathDataEntry 12 }

mscBtdsLCoRequiredSecurity OBJECT-TYPE
   SYNTAX     Unsigned32 (0..7)
   ACCESS     read-only
   STATUS     mandatory
   DESCRIPTION
     "This attribute indicates the required minimum level of security of 
      the trunks on the route. Zero represents the most secure and seven 
      represents the least secure. The trunk's security is indicated by the 
      trunkSecurity attribute of the Trunk component, and has values 
      identical in range and meaning to the requiredSecurity attribute. 
      PORS ensures that any route selected does not contain a trunk 
      whose trunkSecurity attribute is numerically greater than the 
      requiredSecurity."
::= { mscBtdsLCoPathDataEntry 13 }

mscBtdsLCoRequiredCustomerParameter OBJECT-TYPE
   SYNTAX     Unsigned32 (0..7)
   ACCESS     read-only
   STATUS     mandatory
   DESCRIPTION
     "This attribute indicates the allowed customer defined parameter of 
      the trunks on the route.The originating end of the connection 
      determines the customer defined parameter. Its value, a number 
      from zero to seven, is chosen by a network administration to have a 
      meaning specific to their network, thus allowing them to customize 
      the use of their trunks. A complementary trunk attribute, 
      customerParameter, also has a value from zero to seven. The route 
      selection process does not consider trunks whose 
      customerParameter is greater than the requiredCustomerParameter 
      of the path."
::= { mscBtdsLCoPathDataEntry 14 }

mscBtdsLCoEmissionPriority OBJECT-TYPE
   SYNTAX     Unsigned32 (0..2)
   ACCESS     read-only
   STATUS     mandatory
   DESCRIPTION
     "This attribute indicates the urgency with which packets on the path 
      are emitted by the trunks on the route. The originating end of the 
      connection selects the emissionPriority. EmissionPriority of zero 
      indicates the highest emission priority, while two indicates the 
      lowest emission priority. Packets with a higher emissionPriority (or 
      numerically less) are serviced and sent out before the packets of 
      lower emissionPriority (or numerically higher)."
::= { mscBtdsLCoPathDataEntry 15 }

mscBtdsLCoDiscardPriority OBJECT-TYPE
   SYNTAX     Unsigned32 (1..3)
   ACCESS     read-only
   STATUS     mandatory
   DESCRIPTION
     "This attribute indicates the importance of the packets on the 
      path.The originating end of the connection sets discardPriority. One 
      is used for paths carrying the most important traffic, and three is 
      used for paths carrying the least important traffic. Packets with 
      lower discardPriority(numerically lower) are discarded after 
      packets with a higher discardPriority(numerically higher)."
::= { mscBtdsLCoPathDataEntry 16 }

mscBtdsLCoPathType OBJECT-TYPE
   SYNTAX     INTEGER  {
                 normal(0),
                 manual(1),
                 forced(2) }
   ACCESS     read-only
   STATUS     mandatory
   DESCRIPTION
     "This attribute indicates whether the path for this PLC was 
      determined automatically or by static provisioning. Normal 
      pathTypes are selected automatically by Route Selector.The other 
      pathTypes are both manual pathTypes where the operator must 
      specify, through provisioning, a static route termed the manualPath. 
      A manual pathType connection is nearly identical to a normal path 
      type connection with the exception that the route is pre-provisioned. 
      For a manual pathType, bandwidth reservations are respected along 
      the path exactly as in a normal path. The last type, the forced 
      pathType, is also a manual path but regardless of the bandwidth 
      available the route is granted provided the trunks are operational 
      and there are sufficient Logical Channels (LChs).
      
      The forced pathType could result in over committing the reserved 
      bandwidth allowed on a trunk. A better way to achieve the effects of 
      a forced pathType is to use a manual pathType with setupPriority = 
      0 and holdingPriority = 0. In this manner the path will reserve 
      correct bandwidth and it will bump other paths if required while not 
      being bumped itself."
::= { mscBtdsLCoPathDataEntry 17 }

mscBtdsLCoRetryCount OBJECT-TYPE
   SYNTAX     Unsigned32 (0..255)
   ACCESS     read-only
   STATUS     mandatory
   DESCRIPTION
     "This attribute is the count of the number of times the path chosen 
      during route selection could not be instantiated. This count should 
      be three or below if the network is performing adequately. A high 
      value indicates that the route selection is often performed using an 
      out-of-date view of available network bandwidth and/or topology.
      This attribute will only increase at the calling end of the connection.
      This attribute is reset each time a path reconnects and stops 
      counting when it reaches its maximum value."
::= { mscBtdsLCoPathDataEntry 18 }

mscBtdsLCoPathFailureCount OBJECT-TYPE
   SYNTAX     Unsigned32 (0..65535)
   ACCESS     read-only
   STATUS     mandatory
   DESCRIPTION
     "This attribute is the count of the number of times the path has 
      successfully connected. It is set to zero the first time the path is up. 
      If a path fails anytime after connecting this count will be 
      incremented when the path is up again. Failed route requests do not 
      count in this statistic. See retryCount above. This attribute stops 
      counting at its maximum value."
::= { mscBtdsLCoPathDataEntry 19 }

mscBtdsLCoReasonForNoRoute OBJECT-TYPE
   SYNTAX     INTEGER  {
                 none(0),
                 destinationNameTooLong(1),
                 destinationNotSpecified(2),
                 unknownDestinationName(3),
                 incorrectDestination(4),
                 incorrectDestinationEndPoint(5),
                 unknownSource(6),
                 unknownDestination(7),
                 sameNode(8),
                 routeCostTooMuch(9),
                 routesDelayTooLong(10),
                 attributesNotMet(11),
                 anError(12),
                 attributeProfileProblem(13),
                 manualPathIndexProblem(14) }
   ACCESS     read-only
   STATUS     mandatory
   DESCRIPTION
     "This attribute is the route selection's reasonForNoRoute and 
      provides a brief reason for which a route was not selected. The 
      reasons are essentially self-explanatory. Perhaps two reasons for no 
      route require some explanation. The reason 
      unknownRemoteNodeName is issued when the remote node name 
      is not in the topological database. The reason plcAttributesNotMet 
      is issued when there is no network connectivity at a level specified 
      by the PLC attributes. This reason is also issued when there is no 
      physical connectivity between two end nodes."
   DEFVAL     { none }
::= { mscBtdsLCoPathDataEntry 20 }

mscBtdsLCoLastTearDownReason OBJECT-TYPE
   SYNTAX     INTEGER  {
                 none(0),
                 normalShutDown(1),
                 insufficientTxLcOrBandwidth(2),
                 insufficientRxLcOrBandwidth(3),
                 trunkFailure(4),
                 trunkCardFailure(5),
                 operatorForced(6),
                 lostLcnClash(7),
                 networkCongestion(8),
                 trunkNotFound(9),
                 farEndNotFound(10),
                 wrongModuleReached(11),
                 farEndBusy(12),
                 callLoopedBack(13),
                 unknownReason(14),
                 farEndNotReady(15),
                 remoteNameMismatch(16),
                 serviceTypeMismatch(17),
                 reconnectFromFarEnd(18),
                 bumped(19),
                 accessCardFailure(20),
                 optimized(21),
                 overrideRemoteName(22),
                 trunkOrFarEndDidNotSupportMode(23) }
   ACCESS     read-only
   STATUS     mandatory
   DESCRIPTION
     "This attribute reflects the last tear down reason for a connection 
      (LCo). In many cases this displays the reason for a momentary 
      service interruption. This attribute applies to the last path failure 
      only. If a path is no longer up, this may give an indication to the 
      reason that the path has failed. In many cases an alarm will also be 
      generated with more specific information. The following is a brief 
      description of the reasons:
      none - This path has no information for the teardown this is typical 
      of a path provisioned with no remoteName that has not been up.
      normalShutDown - This path has gone down due to normal call 
      termination.
      insufficientTxLcOrBandwidth - At present there is either no 
      available bandwidth or logical channel numbers available on one or 
      more of the trunks for this path in the transmit direction.
      insufficientRxLcOrBandwidth - At present there is either no 
      available bandwidth or logical channel numbers available on one or 
      more of the trunks for this path in the receive direction.
      trunkFailure- A trunk on the path has failed or has gone down due 
      to a provisioning change of a critical attribute.
      trunkCardFailure- A trunk FP card has failed along the path.
      accessCardFailure- The FP on which the peer access service was 
      running has failed.
      operatorForced- The path has terminated due to the operator 
      locking a trunk along the path.
      lostLcnClash- The path has terminated because the PA's at both 
      ends of an intermediate trunk have allocated the same LC to 
      different calls. When this happens both calls must go down and then 
      try to come up again a fraction of a second later (effectively 
      ensuring that they will now be assigned different LC's). It is normal 
      to get the odd clash especially when the PA's usedLC is 
      approaching the PA's maxLC.
      networkCongestion - The path has failed due to control information 
      being lost and not recoverable.
      trunkNotFound - Occurs on a manual path usually. Check for 
      trunks not up or names provisioned incorrectly.
      farEndNotFound - The far end is not provisioned or is not up. 
      Check remote Name.
      wrongModuleReached - This may occur on a manual path. Check 
      provisioning for correct trunk and service names. For a normal 
      path, the network Topology may be changing check remoteName.
      farEndBusy - The far end has been reached but it is busy. Check 
      remoteName and remote end provisioning.
      callLoopedBack - This LCo is provisioned to call itself. Re-
      provision since this is invalid.
      unknownReason - The failure was not resolved.
      farEndNotReady - The remote end was reached but the connection 
      was refused due to the remote end not being enabled.
      remoteNameMismatch - The remote end has alarmed and rejected 
      this setup due to remoteName provisioning.
      serviceTypeMismatch - The remote Service Type does not match 
      this service type. Check provisioning.
      reconnectFromFarEnd - The remote end re-established this 
      connection. Check the remote end lastTearDownReason to 
      determine the real reason.
      bumped - Another call bumped this path from a trunk to get 
      bandwidth (or an LC) which it required to come up. This other path 
      had a higher setupPriority than this path's holdingPriority hence it 
      was allowed to steal the bandwidth (or LC) from this path.
      optimized - This call has been rerouted due to the optimization 
      feature. The call is still active this just indicates why the path 
      changed.
      trunkOrFarEndDidNotSupportMode - This call was unable to 
      complete because a mode required by the service was not supported 
      by one of the trunks the route went through or by the far end service 
      it connected to. Currently the only mode that this applies to is the 
      map/mux mode on TRUNK PA ATM component. Map mode was 
      required by the application (CES/FrAtm etc.) but was not available 
      on the TRUNK PA ATM component through which the call was 
      routed or the far end CES/FrAtm component did not specify the 
      same mode."
   DEFVAL     { none }
::= { mscBtdsLCoPathDataEntry 21 }

mscBtdsLCoPathFailureAction OBJECT-TYPE
   SYNTAX     INTEGER  {
                 disconnectConnection(0),
                 reRoutePath(1) }
   ACCESS     read-only
   STATUS     mandatory
   DESCRIPTION
     "This attribute displays whether the application is set to tolerate 
      momentary interruption of a path while a new path is selected. If 
      disconnectConnection is displayed, the application is informed as 
      soon as possible about a failure by disconnection. If the attribute 
      displays reRoutePath, the path may attempt an immediate reroute, 
      provided the failure is a recoverable failure. If rerouting fails the 
      application is informed of the failure. 
      With this option set to reRoutePath the LCo may wait up to 30 
      seconds before informing the service of complete disconnection in 
      order to allow both ends to attempt to reconnect. Note that if PLC 
      components are different at both ends only the calling end is 
      allowed to reconnect.
      
      All pathTypes respect this attribute. Also on a manualPath with 
      both ends provisioned with independent paths (at least with respect 
      to the failure) this option will have the desired effect that the path is 
      rerouted without complete disconnection at both ends"
::= { mscBtdsLCoPathDataEntry 22 }

mscBtdsLCoBumpPreference OBJECT-TYPE
   SYNTAX     INTEGER  {
                 bumpWhenNecessary(0),
                 bumpToObtainBestRoute(1) }
   ACCESS     read-only
   STATUS     mandatory
   DESCRIPTION
     "This attribute specifies when bumping will occur during route 
      selection process. Bumping may occur when necessary or always. It 
      will be necessary for a connection to bump if there is not enough 
      resources for the connection to be established and these resources 
      are occupied by a connection whose setupPriority is lower 
      (numerically higher) than the connection's setupPriority. A 
      connection may also always bump in order to obtain the best route."
::= { mscBtdsLCoPathDataEntry 23 }

mscBtdsLCoOptimization OBJECT-TYPE
   SYNTAX     INTEGER  {
                 disabled(0),
                 enabled(1) }
   ACCESS     read-only
   STATUS     mandatory
   DESCRIPTION
     "This attribute is used to specify whether this connection should 
      attempt to optimize its path when requested by the routing PORS 
      component. Every path is as optimal as it can be when it is 
      established, but as network traffic patterns and configurations 
      change this path may no longer be as optimal as it could be. The 
      PORS connection manager on a module requests circuits to 
      optimize at the optimization interval."
::= { mscBtdsLCoPathDataEntry 24 }

mscBtdsLCoPathUpDateTime OBJECT-TYPE
   SYNTAX     EnterpriseDateAndTime (SIZE (0 | 19))
   ACCESS     read-only
   STATUS     mandatory
   DESCRIPTION
     "This is the time stamp when the current path was established or 
      reestablished."
::= { mscBtdsLCoPathDataEntry 25 }

mscBtdsLCoStatsTable OBJECT-TYPE
   SYNTAX     SEQUENCE OF MscBtdsLCoStatsEntry
   ACCESS     not-accessible
   STATUS     mandatory
   DESCRIPTION
     "This group contains the operational statistics attributes for the path 
      oriented LCo."
::= { mscBtdsLCo 11 }

mscBtdsLCoStatsEntry OBJECT-TYPE
   SYNTAX     MscBtdsLCoStatsEntry
   ACCESS     not-accessible
   STATUS     mandatory
   DESCRIPTION
     "An entry in the mscBtdsLCoStatsTable."
   INDEX {
      mscBtdsIndex,
      mscBtdsLCoIndex }
::= { mscBtdsLCoStatsTable 1 }

MscBtdsLCoStatsEntry ::= SEQUENCE {
   mscBtdsLCoPktsToNetwork
      PassportCounter64,
   mscBtdsLCoBytesToNetwork
      PassportCounter64,
   mscBtdsLCoPktsFromNetwork
      PassportCounter64,
   mscBtdsLCoBytesFromNetwork
      PassportCounter64 }

mscBtdsLCoPktsToNetwork OBJECT-TYPE
   SYNTAX     PassportCounter64 
   ACCESS     read-only
   STATUS     mandatory
   DESCRIPTION
     "This attribute counts the number of packets transmitted to the 
      network over this Logical Connection."
::= { mscBtdsLCoStatsEntry 1 }

mscBtdsLCoBytesToNetwork OBJECT-TYPE
   SYNTAX     PassportCounter64 
   ACCESS     read-only
   STATUS     mandatory
   DESCRIPTION
     "This attribute counts the number of bytes sent to the network over 
      this Logical Connection."
::= { mscBtdsLCoStatsEntry 2 }

mscBtdsLCoPktsFromNetwork OBJECT-TYPE
   SYNTAX     PassportCounter64 
   ACCESS     read-only
   STATUS     mandatory
   DESCRIPTION
     "This attribute counts the number of packets received from the 
      remote LCo via the network."
::= { mscBtdsLCoStatsEntry 3 }

mscBtdsLCoBytesFromNetwork OBJECT-TYPE
   SYNTAX     PassportCounter64 
   ACCESS     read-only
   STATUS     mandatory
   DESCRIPTION
     "This attribute counts the number of bytes received from the remote 
      LCo via the network."
::= { mscBtdsLCoStatsEntry 4 }

mscBtdsLCoPathTable OBJECT-TYPE
   SYNTAX     SEQUENCE OF MscBtdsLCoPathEntry
   ACCESS     not-accessible
   STATUS     mandatory
   DESCRIPTION
     "This attribute contains the trunk component names over which the 
      path has been instantiated and the remote end point name 
      terminating the path."
::= { mscBtdsLCo 264 }

mscBtdsLCoPathEntry OBJECT-TYPE
   SYNTAX     MscBtdsLCoPathEntry
   ACCESS     not-accessible
   STATUS     mandatory
   DESCRIPTION
     "An entry in the mscBtdsLCoPathTable."
   INDEX {
      mscBtdsIndex,
      mscBtdsLCoIndex,
      mscBtdsLCoPathValue }
::= { mscBtdsLCoPathTable 1 }

MscBtdsLCoPathEntry ::= SEQUENCE {
   mscBtdsLCoPathValue
      AsciiString }

mscBtdsLCoPathValue OBJECT-TYPE
   SYNTAX     AsciiString (SIZE (0..40))
   ACCESS     read-only
   STATUS     mandatory
   DESCRIPTION
     "This variable represents both the value and the index for the
      mscBtdsLCoPathTable."
::= { mscBtdsLCoPathEntry 1 }


-- Btds/n Dpnss1
-- The Dpnss1 component handles Digital Private Network Signalling 
-- System No1 (DPNSS 1) messages for the purpose of voice/data call 
-- discrimination. Discrimination between a voice call and a data call 
-- causes adjustment of the VoiceService operational mode. 
-- A single instance of Dpnss1 component can be provisioned under a 
-- Btds/n component.
-- 
-- The operational mode of any VoiceService provisioned within one 
-- Primary Rate Interface (PRI) is controlled by the same Dpnss1 
-- component. 
-- 
-- To perform call discrimination, both ends of a Btds connection 
-- require the same call discrimination subcomponent (Mcdn or 
-- Dpnss1). Btds serviceFailureReason is 
-- mismatchedCallDiscriminator if the ends of a Btds connection 
-- have different call discrimination subcomponents.

mscBtdsDpnss1 OBJECT IDENTIFIER ::= { mscBtds 5 }



mscBtdsDpnss1RowStatusTable OBJECT-TYPE
   SYNTAX     SEQUENCE OF MscBtdsDpnss1RowStatusEntry
   ACCESS     not-accessible
   STATUS     mandatory
   DESCRIPTION
     "This entry controls the addition and deletion of 
      mscBtdsDpnss1 components."
::= { mscBtdsDpnss1 1 }

mscBtdsDpnss1RowStatusEntry OBJECT-TYPE
   SYNTAX     MscBtdsDpnss1RowStatusEntry
   ACCESS     not-accessible
   STATUS     mandatory
   DESCRIPTION
     "A single entry in the table represents a single 
      mscBtdsDpnss1 component."
   INDEX {
      mscBtdsIndex,
      mscBtdsDpnss1Index }
::= { mscBtdsDpnss1RowStatusTable 1 }

MscBtdsDpnss1RowStatusEntry ::= SEQUENCE {
   mscBtdsDpnss1RowStatus
      RowStatus,
   mscBtdsDpnss1ComponentName
      DisplayString,
   mscBtdsDpnss1StorageType
      StorageType,
   mscBtdsDpnss1Index
      NonReplicated }

mscBtdsDpnss1RowStatus OBJECT-TYPE
   SYNTAX     RowStatus 
   ACCESS     read-write
   STATUS     mandatory
   DESCRIPTION
     "This variable is used as the basis for SNMP naming of
      mscBtdsDpnss1 components.
      These components can be added and deleted."
::= { mscBtdsDpnss1RowStatusEntry 1 }

mscBtdsDpnss1ComponentName OBJECT-TYPE
   SYNTAX     DisplayString 
   ACCESS     read-only
   STATUS     mandatory
   DESCRIPTION
     "This variable provides the component's string name for
      use with the ASCII Console Interface"
::= { mscBtdsDpnss1RowStatusEntry 2 }

mscBtdsDpnss1StorageType OBJECT-TYPE
   SYNTAX     StorageType 
   ACCESS     read-only
   STATUS     mandatory
   DESCRIPTION
     "This variable represents the storage type value for the
      mscBtdsDpnss1 tables."
::= { mscBtdsDpnss1RowStatusEntry 4 }

mscBtdsDpnss1Index OBJECT-TYPE
   SYNTAX     NonReplicated 
   ACCESS     not-accessible
   STATUS     mandatory
   DESCRIPTION
     "This variable represents the index for the mscBtdsDpnss1 tables."
::= { mscBtdsDpnss1RowStatusEntry 10 }

mscBtdsDpnss1ProvTable OBJECT-TYPE
   SYNTAX     SEQUENCE OF MscBtdsDpnss1ProvEntry
   ACCESS     not-accessible
   STATUS     mandatory
   DESCRIPTION
     "This group contains the provisionable attribute for the Dpnss1 
      component to handle DPNSS 1 messages."
::= { mscBtdsDpnss1 10 }

mscBtdsDpnss1ProvEntry OBJECT-TYPE
   SYNTAX     MscBtdsDpnss1ProvEntry
   ACCESS     not-accessible
   STATUS     mandatory
   DESCRIPTION
     "An entry in the mscBtdsDpnss1ProvTable."
   INDEX {
      mscBtdsIndex,
      mscBtdsDpnss1Index }
::= { mscBtdsDpnss1ProvTable 1 }

MscBtdsDpnss1ProvEntry ::= SEQUENCE {
   mscBtdsDpnss1TimeslotsX
      OCTET STRING }

mscBtdsDpnss1TimeslotsX OBJECT-TYPE
   SYNTAX     OCTET STRING (SIZE (4))
   ACCESS     read-write
   STATUS     mandatory
   DESCRIPTION
     "This attribute contains the list of timeslots that are provisioned X 
      for call collision resolution. A timeslot not provisioned as X is 
      assumed to be Y.

      Description of bits:
      notused0(0)
      n1(1)
      n2(2)
      n3(3)
      n4(4)
      n5(5)
      n6(6)
      n7(7)
      n8(8)
      n9(9)
      n10(10)
      n11(11)
      n12(12)
      n13(13)
      n14(14)
      n15(15)
      n16(16)
      n17(17)
      n18(18)
      n19(19)
      n20(20)
      n21(21)
      n22(22)
      n23(23)
      n24(24)
      n25(25)
      n26(26)
      n27(27)
      n28(28)
      n29(29)
      n30(30)
      n31(31)"
::= { mscBtdsDpnss1ProvEntry 1 }

mscBtdsDpnss1VdcdTable OBJECT-TYPE
   SYNTAX     SEQUENCE OF MscBtdsDpnss1VdcdEntry
   ACCESS     not-accessible
   STATUS     mandatory
   DESCRIPTION
     "This group contains attributes which count the protocol messages 
      indicating changes to operational modes of VoiceServices."
::= { mscBtdsDpnss1 12 }

mscBtdsDpnss1VdcdEntry OBJECT-TYPE
   SYNTAX     MscBtdsDpnss1VdcdEntry
   ACCESS     not-accessible
   STATUS     mandatory
   DESCRIPTION
     "An entry in the mscBtdsDpnss1VdcdTable."
   INDEX {
      mscBtdsIndex,
      mscBtdsDpnss1Index }
::= { mscBtdsDpnss1VdcdTable 1 }

MscBtdsDpnss1VdcdEntry ::= SEQUENCE {
   mscBtdsDpnss1NewVoiceCalls
      Counter32,
   mscBtdsDpnss1NewDataCalls
      Counter32,
   mscBtdsDpnss1VoiceToData
      Counter32,
   mscBtdsDpnss1DataToVoice
      Counter32,
   mscBtdsDpnss1CallClears
      Counter32 }

mscBtdsDpnss1NewVoiceCalls OBJECT-TYPE
   SYNTAX     Counter32 
   ACCESS     read-only
   STATUS     mandatory
   DESCRIPTION
     "This attribute counts the number of messages indicating beginning 
      of establishment of a voice call. 
      This count wraps to zero after reaching its maximum value."
::= { mscBtdsDpnss1VdcdEntry 1 }

mscBtdsDpnss1NewDataCalls OBJECT-TYPE
   SYNTAX     Counter32 
   ACCESS     read-only
   STATUS     mandatory
   DESCRIPTION
     "This attribute counts the number of messages indicating beginning 
      of establishment of a data call. 
      This count wraps to zero after reaching its maximum value."
::= { mscBtdsDpnss1VdcdEntry 2 }

mscBtdsDpnss1VoiceToData OBJECT-TYPE
   SYNTAX     Counter32 
   ACCESS     read-only
   STATUS     mandatory
   DESCRIPTION
     "This attribute counts the number of messages indicating a change of 
      a call operational mode from voice transmission to data 
      transmission. 
      This count wraps to zero after reaching its maximum value."
::= { mscBtdsDpnss1VdcdEntry 3 }

mscBtdsDpnss1DataToVoice OBJECT-TYPE
   SYNTAX     Counter32 
   ACCESS     read-only
   STATUS     mandatory
   DESCRIPTION
     "This attribute counts the number of messages indicating a change of 
      a call operational mode from data transmission to voice 
      transmission. 
      This count wraps to zero after reaching its maximum value."
::= { mscBtdsDpnss1VdcdEntry 4 }

mscBtdsDpnss1CallClears OBJECT-TYPE
   SYNTAX     Counter32 
   ACCESS     read-only
   STATUS     mandatory
   DESCRIPTION
     "This attribute counts the number of CCS messages indicating the 
      end of a call. 
      This count wraps to zero after reaching its maximum value."
::= { mscBtdsDpnss1VdcdEntry 5 }

mscBtdsDpnss1FramesTable OBJECT-TYPE
   SYNTAX     SEQUENCE OF MscBtdsDpnss1FramesEntry
   ACCESS     not-accessible
   STATUS     mandatory
   DESCRIPTION
     "This group contains attributes which count layer 2 frames 
      potentially significant for voice/data call discrimination. See also 
      the description of HdlcStatistics group."
::= { mscBtdsDpnss1 13 }

mscBtdsDpnss1FramesEntry OBJECT-TYPE
   SYNTAX     MscBtdsDpnss1FramesEntry
   ACCESS     not-accessible
   STATUS     mandatory
   DESCRIPTION
     "An entry in the mscBtdsDpnss1FramesTable."
   INDEX {
      mscBtdsIndex,
      mscBtdsDpnss1Index }
::= { mscBtdsDpnss1FramesTable 1 }

MscBtdsDpnss1FramesEntry ::= SEQUENCE {
   mscBtdsDpnss1FrmProcessed
      Counter32,
   mscBtdsDpnss1FrmInvalid
      Counter32 }

mscBtdsDpnss1FrmProcessed OBJECT-TYPE
   SYNTAX     Counter32 
   ACCESS     read-only
   STATUS     mandatory
   DESCRIPTION
     "This attribute counts the number of valid layer 2 frames containing 
      an Information Field with a protocol message. Changes to 
      operational mode of a VoiceService are triggered only by a subset of 
      processed frames. Many frames refer to the call progress and are 
      ignored from the standpoint of voice/data call discrimination. 
      This count wraps to zero after reaching its maximum value."
::= { mscBtdsDpnss1FramesEntry 1 }

mscBtdsDpnss1FrmInvalid OBJECT-TYPE
   SYNTAX     Counter32 
   ACCESS     read-only
   STATUS     mandatory
   DESCRIPTION
     "This attribute counts the number of invalid layer 2 frames 
      For DPNSS 1, a frames is counted as invalid if 
      - it is shorter than 3 octets or longer than 48 octets (excluding two 
      octets of Cyclic Redundancy Check), or 
      - it has an invalid bit combination in the Address Field, or 
      - the Control Field is inconsistent with the Address Field, or 
      - the type of data is invalid, or 
      - it relates to time slot 0. 
      For MCDN, a frame is counted as invalid if 
      - it is shorter than 4 or longer than 264 octets (excluding two octets 
      of Cyclic Redundancy Check), or 
      - it has an invalid bit combination in the Address Field, or 
      - it has missing or incorrect mandatory information elements. 
      This count wraps to zero after reaching its maximum value."
::= { mscBtdsDpnss1FramesEntry 2 }

mscBtdsDpnss1HdlcTable OBJECT-TYPE
   SYNTAX     SEQUENCE OF MscBtdsDpnss1HdlcEntry
   ACCESS     not-accessible
   STATUS     mandatory
   DESCRIPTION
     "This group contains attributes which count the signalling frame 
      events."
::= { mscBtdsDpnss1 14 }

mscBtdsDpnss1HdlcEntry OBJECT-TYPE
   SYNTAX     MscBtdsDpnss1HdlcEntry
   ACCESS     not-accessible
   STATUS     mandatory
   DESCRIPTION
     "An entry in the mscBtdsDpnss1HdlcTable."
   INDEX {
      mscBtdsIndex,
      mscBtdsDpnss1Index }
::= { mscBtdsDpnss1HdlcTable 1 }

MscBtdsDpnss1HdlcEntry ::= SEQUENCE {
   mscBtdsDpnss1FrmFromIf
      Counter32,
   mscBtdsDpnss1Aborts
      Counter32,
   mscBtdsDpnss1CrcErrors
      Counter32,
   mscBtdsDpnss1NonOctetErrors
      Counter32,
   mscBtdsDpnss1Overruns
      Counter32,
   mscBtdsDpnss1LargeFrmErrors
      Counter32 }

mscBtdsDpnss1FrmFromIf OBJECT-TYPE
   SYNTAX     Counter32 
   ACCESS     read-only
   STATUS     mandatory
   DESCRIPTION
     "This attribute counts the number of all hdlc frames, correct or not, 
      received from the PRI. 
      This count wraps to zero after reaching its maximum value."
::= { mscBtdsDpnss1HdlcEntry 2 }

mscBtdsDpnss1Aborts OBJECT-TYPE
   SYNTAX     Counter32 
   ACCESS     read-only
   STATUS     mandatory
   DESCRIPTION
     "This attribute counts the number of frame receptions aborted before 
      completion, due to incoming frame format errors. 
      This count wraps to zero after reaching its maximum value."
::= { mscBtdsDpnss1HdlcEntry 3 }

mscBtdsDpnss1CrcErrors OBJECT-TYPE
   SYNTAX     Counter32 
   ACCESS     read-only
   STATUS     mandatory
   DESCRIPTION
     "This attribute counts the number of frames received with CRC 
      errors. 
      This count wraps to zero after reaching its maximum value."
::= { mscBtdsDpnss1HdlcEntry 4 }

mscBtdsDpnss1NonOctetErrors OBJECT-TYPE
   SYNTAX     Counter32 
   ACCESS     read-only
   STATUS     mandatory
   DESCRIPTION
     "This attribute counts the number of frames received that were non 
      octet aligned. 
      This count wraps to zero after reaching its maximum value."
::= { mscBtdsDpnss1HdlcEntry 5 }

mscBtdsDpnss1Overruns OBJECT-TYPE
   SYNTAX     Counter32 
   ACCESS     read-only
   STATUS     mandatory
   DESCRIPTION
     "This attribute counts the number of frames received for which 
      overruns occurred. 
      This count wraps to zero after reaching its maximum value."
::= { mscBtdsDpnss1HdlcEntry 6 }

mscBtdsDpnss1LargeFrmErrors OBJECT-TYPE
   SYNTAX     Counter32 
   ACCESS     read-only
   STATUS     mandatory
   DESCRIPTION
     "This attribute counts the number of received frames which were 
      longer than 1024 octets. 
      This count wraps to zero after reaching its maximum value."
::= { mscBtdsDpnss1HdlcEntry 8 }

mscBtdsDpnss1TSlotTable OBJECT-TYPE
   SYNTAX     SEQUENCE OF MscBtdsDpnss1TSlotEntry
   ACCESS     not-accessible
   STATUS     mandatory
   DESCRIPTION
     "This attribute displays the operational mode of every time slot 
      which is serviced by a voice service. 
      The value idle means that the time slot is not used to service a call, 
      hence the concerned voice service's bandwidth in the Passport 
      subnet is available for other uses. 
      The value voice means that a phone call is in progress. All 
      provisioned voice service's value added features have been activated 
      (features such as voice compression, silence suppression, echo 
      cancellation). 
      The value data means that a data call is in progress. All provisioned 
      voice service's value added features have been de-activated, so that 
      a clear 64 kbit/sec data connection is provided accross the Passport 
      subnet."
::= { mscBtdsDpnss1 286 }

mscBtdsDpnss1TSlotEntry OBJECT-TYPE
   SYNTAX     MscBtdsDpnss1TSlotEntry
   ACCESS     not-accessible
   STATUS     mandatory
   DESCRIPTION
     "An entry in the mscBtdsDpnss1TSlotTable."
   INDEX {
      mscBtdsIndex,
      mscBtdsDpnss1Index,
      mscBtdsDpnss1TSlotIndex }
::= { mscBtdsDpnss1TSlotTable 1 }

MscBtdsDpnss1TSlotEntry ::= SEQUENCE {
   mscBtdsDpnss1TSlotIndex
      Integer32,
   mscBtdsDpnss1TSlotValue
      INTEGER }

mscBtdsDpnss1TSlotIndex OBJECT-TYPE
   SYNTAX     Integer32 (1..31)
   ACCESS     not-accessible
   STATUS     mandatory
   DESCRIPTION
     "This variable represents the index for the mscBtdsDpnss1TSlotTable."
::= { mscBtdsDpnss1TSlotEntry 1 }

mscBtdsDpnss1TSlotValue OBJECT-TYPE
   SYNTAX     INTEGER  {
                 idle(0),
                 voice(1),
                 data(2) }
   ACCESS     read-only
   STATUS     mandatory
   DESCRIPTION
     "This variable represents an individual value for the
      mscBtdsDpnss1TSlotTable."
::= { mscBtdsDpnss1TSlotEntry 2 }


-- Btds/n Mcdn
-- The Mcdn component handles MCDN protocol, or Meridian 1 
-- ISDN Primary Rate Interface, messages for the purpose of 
-- voice/data call discrimination. Discrimination between a voice call 
-- and a data call causes adjustment of the VoiceService operational 
-- mode. 
-- A single instance of Mcdn component can be provisioned under a 
-- Btds/n component. 
-- The operational mode of any VoiceService provisioned within one 
-- Primary Rate Interface (PRI) is controlled by the same Mcdn 
-- component.
-- 
-- To perform call discrimination, both ends of a Btds connection 
-- require the same call discrimination subcomponent (Mcdn or 
-- Dpnss1). Btds serviceFailureReason is 
-- mismatchedCallDiscriminator if the ends of a Btds connection 
-- have different call discrimination subcomponents.

mscBtdsMcdn OBJECT IDENTIFIER ::= { mscBtds 6 }



mscBtdsMcdnRowStatusTable OBJECT-TYPE
   SYNTAX     SEQUENCE OF MscBtdsMcdnRowStatusEntry
   ACCESS     not-accessible
   STATUS     mandatory
   DESCRIPTION
     "This entry controls the addition and deletion of 
      mscBtdsMcdn components."
::= { mscBtdsMcdn 1 }

mscBtdsMcdnRowStatusEntry OBJECT-TYPE
   SYNTAX     MscBtdsMcdnRowStatusEntry
   ACCESS     not-accessible
   STATUS     mandatory
   DESCRIPTION
     "A single entry in the table represents a single 
      mscBtdsMcdn component."
   INDEX {
      mscBtdsIndex,
      mscBtdsMcdnIndex }
::= { mscBtdsMcdnRowStatusTable 1 }

MscBtdsMcdnRowStatusEntry ::= SEQUENCE {
   mscBtdsMcdnRowStatus
      RowStatus,
   mscBtdsMcdnComponentName
      DisplayString,
   mscBtdsMcdnStorageType
      StorageType,
   mscBtdsMcdnIndex
      NonReplicated }

mscBtdsMcdnRowStatus OBJECT-TYPE
   SYNTAX     RowStatus 
   ACCESS     read-write
   STATUS     mandatory
   DESCRIPTION
     "This variable is used as the basis for SNMP naming of
      mscBtdsMcdn components.
      These components can be added and deleted."
::= { mscBtdsMcdnRowStatusEntry 1 }

mscBtdsMcdnComponentName OBJECT-TYPE
   SYNTAX     DisplayString 
   ACCESS     read-only
   STATUS     mandatory
   DESCRIPTION
     "This variable provides the component's string name for
      use with the ASCII Console Interface"
::= { mscBtdsMcdnRowStatusEntry 2 }

mscBtdsMcdnStorageType OBJECT-TYPE
   SYNTAX     StorageType 
   ACCESS     read-only
   STATUS     mandatory
   DESCRIPTION
     "This variable represents the storage type value for the
      mscBtdsMcdn tables."
::= { mscBtdsMcdnRowStatusEntry 4 }

mscBtdsMcdnIndex OBJECT-TYPE
   SYNTAX     NonReplicated 
   ACCESS     not-accessible
   STATUS     mandatory
   DESCRIPTION
     "This variable represents the index for the mscBtdsMcdn tables."
::= { mscBtdsMcdnRowStatusEntry 10 }

mscBtdsMcdnProvTable OBJECT-TYPE
   SYNTAX     SEQUENCE OF MscBtdsMcdnProvEntry
   ACCESS     not-accessible
   STATUS     mandatory
   DESCRIPTION
     "This group contains the provisionable attribute for the Mcdn 
      component."
::= { mscBtdsMcdn 10 }

mscBtdsMcdnProvEntry OBJECT-TYPE
   SYNTAX     MscBtdsMcdnProvEntry
   ACCESS     not-accessible
   STATUS     mandatory
   DESCRIPTION
     "An entry in the mscBtdsMcdnProvTable."
   INDEX {
      mscBtdsIndex,
      mscBtdsMcdnIndex }
::= { mscBtdsMcdnProvTable 1 }

MscBtdsMcdnProvEntry ::= SEQUENCE {
   mscBtdsMcdnAdjPbxSide
      INTEGER }

mscBtdsMcdnAdjPbxSide OBJECT-TYPE
   SYNTAX     INTEGER  {
                 slave(0),
                 master(1) }
   ACCESS     read-write
   STATUS     mandatory
   DESCRIPTION
     "This attribute holds the provisioning related to call collision 
      resolution. Its value must be that same as in the adjacent PBX, at 
      the other end of the PRI. To provision the call collision resolution in 
      Nortel's SL1 and Meridian 1 PBXs, the network operator responds 
      to the prompt SIDE by entering either MAS or SLAV. So if the 
      SLAV was entered, then the adjPbxSide has to be provisioned slave."
   DEFVAL     { slave }
::= { mscBtdsMcdnProvEntry 1 }

mscBtdsMcdnVdcdTable OBJECT-TYPE
   SYNTAX     SEQUENCE OF MscBtdsMcdnVdcdEntry
   ACCESS     not-accessible
   STATUS     mandatory
   DESCRIPTION
     "This group contains attributes which count the protocol messages 
      indicating changes to operational modes of VoiceServices."
::= { mscBtdsMcdn 12 }

mscBtdsMcdnVdcdEntry OBJECT-TYPE
   SYNTAX     MscBtdsMcdnVdcdEntry
   ACCESS     not-accessible
   STATUS     mandatory
   DESCRIPTION
     "An entry in the mscBtdsMcdnVdcdTable."
   INDEX {
      mscBtdsIndex,
      mscBtdsMcdnIndex }
::= { mscBtdsMcdnVdcdTable 1 }

MscBtdsMcdnVdcdEntry ::= SEQUENCE {
   mscBtdsMcdnNewVoiceCalls
      Counter32,
   mscBtdsMcdnNewDataCalls
      Counter32,
   mscBtdsMcdnVoiceToData
      Counter32,
   mscBtdsMcdnDataToVoice
      Counter32,
   mscBtdsMcdnCallClears
      Counter32 }

mscBtdsMcdnNewVoiceCalls OBJECT-TYPE
   SYNTAX     Counter32 
   ACCESS     read-only
   STATUS     mandatory
   DESCRIPTION
     "This attribute counts the number of messages indicating beginning 
      of establishment of a voice call. 
      This count wraps to zero after reaching its maximum value."
::= { mscBtdsMcdnVdcdEntry 1 }

mscBtdsMcdnNewDataCalls OBJECT-TYPE
   SYNTAX     Counter32 
   ACCESS     read-only
   STATUS     mandatory
   DESCRIPTION
     "This attribute counts the number of messages indicating beginning 
      of establishment of a data call. 
      This count wraps to zero after reaching its maximum value."
::= { mscBtdsMcdnVdcdEntry 2 }

mscBtdsMcdnVoiceToData OBJECT-TYPE
   SYNTAX     Counter32 
   ACCESS     read-only
   STATUS     mandatory
   DESCRIPTION
     "This attribute counts the number of messages indicating a change of 
      a call operational mode from voice transmission to data 
      transmission. 
      This count wraps to zero after reaching its maximum value."
::= { mscBtdsMcdnVdcdEntry 3 }

mscBtdsMcdnDataToVoice OBJECT-TYPE
   SYNTAX     Counter32 
   ACCESS     read-only
   STATUS     mandatory
   DESCRIPTION
     "This attribute counts the number of messages indicating a change of 
      a call operational mode from data transmission to voice 
      transmission. 
      This count wraps to zero after reaching its maximum value."
::= { mscBtdsMcdnVdcdEntry 4 }

mscBtdsMcdnCallClears OBJECT-TYPE
   SYNTAX     Counter32 
   ACCESS     read-only
   STATUS     mandatory
   DESCRIPTION
     "This attribute counts the number of CCS messages indicating the 
      end of a call. 
      This count wraps to zero after reaching its maximum value."
::= { mscBtdsMcdnVdcdEntry 5 }

mscBtdsMcdnFramesTable OBJECT-TYPE
   SYNTAX     SEQUENCE OF MscBtdsMcdnFramesEntry
   ACCESS     not-accessible
   STATUS     mandatory
   DESCRIPTION
     "This group contains attributes which count layer 2 frames 
      potentially significant for voice/data call discrimination. See also 
      the description of HdlcStatistics group."
::= { mscBtdsMcdn 13 }

mscBtdsMcdnFramesEntry OBJECT-TYPE
   SYNTAX     MscBtdsMcdnFramesEntry
   ACCESS     not-accessible
   STATUS     mandatory
   DESCRIPTION
     "An entry in the mscBtdsMcdnFramesTable."
   INDEX {
      mscBtdsIndex,
      mscBtdsMcdnIndex }
::= { mscBtdsMcdnFramesTable 1 }

MscBtdsMcdnFramesEntry ::= SEQUENCE {
   mscBtdsMcdnFrmProcessed
      Counter32,
   mscBtdsMcdnFrmInvalid
      Counter32 }

mscBtdsMcdnFrmProcessed OBJECT-TYPE
   SYNTAX     Counter32 
   ACCESS     read-only
   STATUS     mandatory
   DESCRIPTION
     "This attribute counts the number of valid layer 2 frames containing 
      an Information Field with a protocol message. Changes to 
      operational mode of a VoiceService are triggered only by a subset of 
      processed frames. Many frames refer to the call progress and are 
      ignored from the standpoint of voice/data call discrimination. 
      This count wraps to zero after reaching its maximum value."
::= { mscBtdsMcdnFramesEntry 1 }

mscBtdsMcdnFrmInvalid OBJECT-TYPE
   SYNTAX     Counter32 
   ACCESS     read-only
   STATUS     mandatory
   DESCRIPTION
     "This attribute counts the number of invalid layer 2 frames 
      For DPNSS 1, a frames is counted as invalid if 
      - it is shorter than 3 octets or longer than 48 octets (excluding two 
      octets of Cyclic Redundancy Check), or 
      - it has an invalid bit combination in the Address Field, or 
      - the Control Field is inconsistent with the Address Field, or 
      - the type of data is invalid, or 
      - it relates to time slot 0. 
      For MCDN, a frame is counted as invalid if 
      - it is shorter than 4 or longer than 264 octets (excluding two octets 
      of Cyclic Redundancy Check), or 
      - it has an invalid bit combination in the Address Field, or 
      - it has missing or incorrect mandatory information elements. 
      This count wraps to zero after reaching its maximum value."
::= { mscBtdsMcdnFramesEntry 2 }

mscBtdsMcdnHdlcTable OBJECT-TYPE
   SYNTAX     SEQUENCE OF MscBtdsMcdnHdlcEntry
   ACCESS     not-accessible
   STATUS     mandatory
   DESCRIPTION
     "This group contains attributes which count the signalling frame 
      events."
::= { mscBtdsMcdn 14 }

mscBtdsMcdnHdlcEntry OBJECT-TYPE
   SYNTAX     MscBtdsMcdnHdlcEntry
   ACCESS     not-accessible
   STATUS     mandatory
   DESCRIPTION
     "An entry in the mscBtdsMcdnHdlcTable."
   INDEX {
      mscBtdsIndex,
      mscBtdsMcdnIndex }
::= { mscBtdsMcdnHdlcTable 1 }

MscBtdsMcdnHdlcEntry ::= SEQUENCE {
   mscBtdsMcdnFrmFromIf
      Counter32,
   mscBtdsMcdnAborts
      Counter32,
   mscBtdsMcdnCrcErrors
      Counter32,
   mscBtdsMcdnNonOctetErrors
      Counter32,
   mscBtdsMcdnOverruns
      Counter32,
   mscBtdsMcdnLargeFrmErrors
      Counter32 }

mscBtdsMcdnFrmFromIf OBJECT-TYPE
   SYNTAX     Counter32 
   ACCESS     read-only
   STATUS     mandatory
   DESCRIPTION
     "This attribute counts the number of all hdlc frames, correct or not, 
      received from the PRI. 
      This count wraps to zero after reaching its maximum value."
::= { mscBtdsMcdnHdlcEntry 2 }

mscBtdsMcdnAborts OBJECT-TYPE
   SYNTAX     Counter32 
   ACCESS     read-only
   STATUS     mandatory
   DESCRIPTION
     "This attribute counts the number of frame receptions aborted before 
      completion, due to incoming frame format errors. 
      This count wraps to zero after reaching its maximum value."
::= { mscBtdsMcdnHdlcEntry 3 }

mscBtdsMcdnCrcErrors OBJECT-TYPE
   SYNTAX     Counter32 
   ACCESS     read-only
   STATUS     mandatory
   DESCRIPTION
     "This attribute counts the number of frames received with CRC 
      errors. 
      This count wraps to zero after reaching its maximum value."
::= { mscBtdsMcdnHdlcEntry 4 }

mscBtdsMcdnNonOctetErrors OBJECT-TYPE
   SYNTAX     Counter32 
   ACCESS     read-only
   STATUS     mandatory
   DESCRIPTION
     "This attribute counts the number of frames received that were non 
      octet aligned. 
      This count wraps to zero after reaching its maximum value."
::= { mscBtdsMcdnHdlcEntry 5 }

mscBtdsMcdnOverruns OBJECT-TYPE
   SYNTAX     Counter32 
   ACCESS     read-only
   STATUS     mandatory
   DESCRIPTION
     "This attribute counts the number of frames received for which 
      overruns occurred. 
      This count wraps to zero after reaching its maximum value."
::= { mscBtdsMcdnHdlcEntry 6 }

mscBtdsMcdnLargeFrmErrors OBJECT-TYPE
   SYNTAX     Counter32 
   ACCESS     read-only
   STATUS     mandatory
   DESCRIPTION
     "This attribute counts the number of received frames which were 
      longer than 1024 octets. 
      This count wraps to zero after reaching its maximum value."
::= { mscBtdsMcdnHdlcEntry 8 }

mscBtdsMcdnTSlotTable OBJECT-TYPE
   SYNTAX     SEQUENCE OF MscBtdsMcdnTSlotEntry
   ACCESS     not-accessible
   STATUS     mandatory
   DESCRIPTION
     "This attribute displays the operational mode of every time slot 
      which is serviced by a voice service. 
      The value idle means that the time slot is not used to service a call, 
      hence the concerned voice service's bandwidth in the Passport 
      subnet is available for other uses. 
      The value voice means that a phone call is in progress. All 
      provisioned voice service's value added features have been activated 
      (features such as voice compression, silence suppression, echo 
      cancellation). 
      The value data means that a data call is in progress. All provisioned 
      voice service's value added features have been de-activated, so that 
      a clear 64 kbit/sec data connection is provided accross the Passport 
      subnet."
::= { mscBtdsMcdn 286 }

mscBtdsMcdnTSlotEntry OBJECT-TYPE
   SYNTAX     MscBtdsMcdnTSlotEntry
   ACCESS     not-accessible
   STATUS     mandatory
   DESCRIPTION
     "An entry in the mscBtdsMcdnTSlotTable."
   INDEX {
      mscBtdsIndex,
      mscBtdsMcdnIndex,
      mscBtdsMcdnTSlotIndex }
::= { mscBtdsMcdnTSlotTable 1 }

MscBtdsMcdnTSlotEntry ::= SEQUENCE {
   mscBtdsMcdnTSlotIndex
      Integer32,
   mscBtdsMcdnTSlotValue
      INTEGER }

mscBtdsMcdnTSlotIndex OBJECT-TYPE
   SYNTAX     Integer32 (1..31)
   ACCESS     not-accessible
   STATUS     mandatory
   DESCRIPTION
     "This variable represents the index for the mscBtdsMcdnTSlotTable."
::= { mscBtdsMcdnTSlotEntry 1 }

mscBtdsMcdnTSlotValue OBJECT-TYPE
   SYNTAX     INTEGER  {
                 idle(0),
                 voice(1),
                 data(2) }
   ACCESS     read-only
   STATUS     mandatory
   DESCRIPTION
     "This variable represents an individual value for the
      mscBtdsMcdnTSlotTable."
::= { mscBtdsMcdnTSlotEntry 2 }




-- 
-- Version and Compliance statements
-- 



-- Object-Group Statement:
-- A list of all current accessible leaf objects.

-- OBJECTS { mscBtdsDpnss1StorageType,
--           mscBtdsProceduralStatus,
--           mscBtdsLCoRowStatus,
--           mscBtdsMcdnNonOctetErrors,
--           mscBtdsPlcPathType,
--           mscBtdsLCoRetryCount,
--           mscBtdsPlcRequiredCustomerParm,
--           mscBtdsLCoEmissionPriority,
--           mscBtdsDpnss1TSlotValue,
--           mscBtdsFramerComponentName,
--           mscBtdsLCoPathUpDateTime,
--           mscBtdsPlcDiscardPriority,
--           mscBtdsDpnss1FrmProcessed,
--           mscBtdsMcdnComponentName,
--           mscBtdsFramerFrmToIf,
--           mscBtdsLCoReasonForNoRoute,
--           mscBtdsFramerFrmUnderRuns,
--           mscBtdsLCoRequiredRxBandwidth,
--           mscBtdsLCoBytesToNetwork,
--           mscBtdsLCoComponentName,
--           mscBtdsServiceFailureReason,
--           mscBtdsDpnss1LargeFrmErrors,
--           mscBtdsDpnss1RowStatus,
--           mscBtdsLCoDiscardPriority,
--           mscBtdsMcdnLargeFrmErrors,
--           mscBtdsPlcRequiredSecurity,
--           mscBtdsDpnss1VoiceToData,
--           mscBtdsDpnss1NonOctetErrors,
--           mscBtdsPlcPathAttributeToMinimize,
--           mscBtdsDpnss1NewVoiceCalls,
--           mscBtdsLCoLastTearDownReason,
--           mscBtdsLCoPktsToNetwork,
--           mscBtdsPlcPathFailureAction,
--           mscBtdsLCoRequiredSecurity,
--           mscBtdsLCoPathFailureCount,
--           mscBtdsPlcRequiredTrafficType,
--           mscBtdsPlcHoldingPriority,
--           mscBtdsPlcMaximumAcceptableDelay,
--           mscBtdsPlcMaximumAcceptableCost,
--           mscBtdsMcdnAdjPbxSide,
--           mscBtdsSnmpOperStatus,
--           mscBtdsIfIndex,
--           mscBtdsFramerFrmFromIf,
--           mscBtdsLCoPathFailureAction,
--           mscBtdsPlcPermittedTrunkTypes,
--           mscBtdsLCoRequiredTxBandwidth,
--           mscBtdsLCoHoldingPriority,
--           mscBtdsFramerProtocol,
--           mscBtdsLCoRoundTripDelay,
--           mscBtdsStandbyStatus,
--           mscBtdsLCoBytesFromNetwork,
--           mscBtdsFramerIdlePattern,
--           mscBtdsStorageType,
--           mscBtdsPlcBumpPreference,
--           mscBtdsPlcRequiredTxBandwidth,
--           mscBtdsLCoPermittedTrunkTypes,
--           mscBtdsDpnss1TimeslotsX,
--           mscBtdsPlcRequiredRxBandwidth,
--           mscBtdsDpnss1Aborts,
--           mscBtdsMcdnCallClears,
--           mscBtdsFramerAdminState,
--           mscBtdsMcdnDataToVoice,
--           mscBtdsControlStatus,
--           mscBtdsAdminState,
--           mscBtdsDpnss1NewDataCalls,
--           mscBtdsFramerRowStatus,
--           mscBtdsLCoPktsFromNetwork,
--           mscBtdsMcdnVoiceToData,
--           mscBtdsIfAdminStatus,
--           mscBtdsMcdnOverruns,
--           mscBtdsDpnss1CrcErrors,
--           mscBtdsCustomerIdentifier,
--           mscBtdsComponentName,
--           mscBtdsFramerUsageState,
--           mscBtdsPlcComponentName,
--           mscBtdsDpnss1CallClears,
--           mscBtdsLCoDelayMetric,
--           mscBtdsUsageState,
--           mscBtdsLCoCostMetric,
--           mscBtdsFramerFrmLostInNetwork,
--           mscBtdsFramerInterfaceName,
--           mscBtdsFramerTimeSlotAlignment,
--           mscBtdsFramerNumOfIdleBytesToMonitor,
--           mscBtdsFramerOperationalState,
--           mscBtdsFramerFrmDumped,
--           mscBtdsDpnss1Overruns,
--           mscBtdsLCoOverrideRemoteName,
--           mscBtdsOperationalState,
--           mscBtdsPlcAddressToCall,
--           mscBtdsFramerSuppressedFrames,
--           mscBtdsFramerLrcErrors,
--           mscBtdsPlcRemoteName,
--           mscBtdsFramerInsertedOutputDelay,
--           mscBtdsFramerBtdsCellSize,
--           mscBtdsDpnss1DataToVoice,
--           mscBtdsLCoEnd,
--           mscBtdsLCoPathValue,
--           mscBtdsDpnss1ComponentName,
--           mscBtdsLCoRequiredCustomerParameter,
--           mscBtdsMcdnNewDataCalls,
--           mscBtdsLCoState,
--           mscBtdsMcdnFrmInvalid,
--           mscBtdsUnknownStatus,
--           mscBtdsMcdnCrcErrors,
--           mscBtdsAlarmStatus,
--           mscBtdsPlcStorageType,
--           mscBtdsAvailabilityStatus,
--           mscBtdsMcdnFrmFromIf,
--           mscBtdsMcdnFrmProcessed,
--           mscBtdsMcdnStorageType,
--           mscBtdsMcdnAborts,
--           mscBtdsMcdnTSlotValue,
--           mscBtdsRowStatus,
--           mscBtdsPlcSetupPriority,
--           mscBtdsFramerStorageType,
--           mscBtdsPlcOptimization,
--           mscBtdsPlcLocalAddress,
--           mscBtdsLCoStorageType,
--           mscBtdsDpnss1FrmInvalid,
--           mscBtdsPlcMaximumAcceptableGatewayCost,
--           mscBtdsLCoBumpPreference,
--           mscBtdsPlcMpathValue,
--           mscBtdsPlcRowStatus,
--           mscBtdsLCoOptimization,
--           mscBtdsLCoSetupPriority,
--           mscBtdsLCoRequiredTrafficType,
--           mscBtdsMcdnRowStatus,
--           mscBtdsMcdnNewVoiceCalls,
--           mscBtdsPlcEmissionPriority,
--           mscBtdsDpnss1FrmFromIf,
--           mscBtdsLCoPathType }
-- STATUS  mandatory
-- DESCRIPTION
--   "A list of all current accessible leaf objects."

bitTransparentGroup OBJECT IDENTIFIER ::= { bitTransparentMIB 1 }
bitTransparentGroupCA OBJECT IDENTIFIER ::= { bitTransparentGroup 1 }
bitTransparentGroupCA02 OBJECT IDENTIFIER ::= { bitTransparentGroupCA 3 }
bitTransparentGroupCA02A OBJECT IDENTIFIER ::= { bitTransparentGroupCA02 2 }



-- Agent-Capabilities Statement:

-- PRODUCT-RELEASE "MscPassport Release 1.2 BitTransparent."
-- STATUS          mandatory
-- DESCRIPTION     "Carrier Passport BitTransparent MIB: MIB Version CA02A,
--                  Software Version CA02S9C."
-- SUPPORTS        Nortel-MsCarrier-MscPassport-BitTransparentMIB
--    INCLUDES     { bitTransparentGroupCA02A }

bitTransparentCapabilities OBJECT IDENTIFIER ::= { bitTransparentMIB 3 }
bitTransparentCapabilitiesCA OBJECT IDENTIFIER ::= { bitTransparentCapabilities 1 }
bitTransparentCapabilitiesCA02 OBJECT IDENTIFIER ::= { bitTransparentCapabilitiesCA 3 }
bitTransparentCapabilitiesCA02A OBJECT IDENTIFIER ::= { bitTransparentCapabilitiesCA02 2 }





END
