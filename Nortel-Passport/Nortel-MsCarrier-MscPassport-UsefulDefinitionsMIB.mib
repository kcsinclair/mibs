Nortel-MsCarrier-MscPassport-UsefulDefinitionsMIB
DEFINITIONS ::= BEGIN

IMPORTS

      enterprises
   FROM RFC1155-SMI;

--   LAST-UPDATED    "9907300000Z"
--   ORGANIZATION    "Nortel Networks"
--   CONTACT-INFO    "
--         Nortel Carrier Data Network Management
--
--         Postal:       P.O. Box 3511, Station C
--                       Ottawa, Ontario
--                       Canada  K1Y 4H7
--
--         via the WEB:  http://www.nortelnetworks.com
--                       select 'Contact Us' from the menu
--
--         via phone:    1-800-4NORTEL"

--   DESCRIPTION	
--    "The MIB module describing the top-level Nortel MsCarrier MscPassport
--    OBJECT IDENTIFIER tree structure. It also provides definitions for 
--    values of the variable sysOID for different Carrier Passport products."
-- 
--  usefulDefinitionsMIB	  OBJECT IDENTIFIER ::= { mscPassportMIBs 1 }


-- FYI:
-- enterprises OBJECT IDENTIFIER ::= { iso(1) org(3) dod(6)
--                                       internet(1) private(4) 1 }

-- arcs up to the enterprises:
nortel         OBJECT IDENTIFIER ::= { enterprises 562 }
msCarrier      OBJECT IDENTIFIER ::= { nortel 36 }
mscProducts    OBJECT IDENTIFIER ::= { msCarrier 1 }
mscPassport    OBJECT IDENTIFIER ::= { msCarrier 2 }

--
-- values for sysOID:
--

--   STATUS      current
--   DESCRIPTION
--      " Passport 7400 family of cell-based switches provide high
--      bandwidth, high performance networking for LAN interconnect
--      applications and network consolidation of data, voice, image and
--      video traffic. "

mscPassport7440  OBJECT IDENTIFIER ::= { mscProducts 1 }

--   STATUS      current
--   DESCRIPTION
--      " Passport 7400 family of cell-based switches provide high
--      bandwidth, high performance networking for LAN interconnect
--      applications and network consolidation of data, voice, image and 
--      video traffic. "

mscPassport7480 OBJECT IDENTIFIER ::= { mscProducts 2 }

--   STATUS      current
--   DESCRIPTION
--      " Passport Virtual Router is a subsystem within Passport which
--      provides internetworking capabilities. The Virtual Router
--      provides routing and packet forwarding functionality which
--      is similar to a real router."
 
mscPassportVirtualRouter  OBJECT IDENTIFIER ::= { mscProducts 3 }

--   STATUS      current
--   DESCRIPTION
--      " The Passport 15000 family of switches consists of multi-
--      service data switches providing high bandwidth, high 
--      performance networking consolidation of data, voice, image,
--      and video traffic. The Passport 15000 series is intended for
--      the carrier market with a higher capacity fabric-based
--      backplane and higher density functional processes."

mscPassport15000 OBJECT IDENTIFIER ::= { mscProducts 4 }

-- arcs immediately subordinate to Passport:
mscComponents              OBJECT IDENTIFIER ::= { mscPassport 1 }
                              -- all MIB variables are defined
                              -- in the subtree rooted at 'mscComponents'.
mscPassportMIBs            OBJECT IDENTIFIER ::= { mscPassport 2 }
                              -- all MIBs, OBJECT_GROUP and
                              -- AGENT-CAPABILITIES are defined
                              -- in the subtree rooted at 'mscPassportMIBs'.

-- see DESCRIPTION at the beginning of this module
usefulDefinitionsMIB	  OBJECT IDENTIFIER ::= { mscPassportMIBs 1 }

-- the following component is assigned here for convenience:
mscPassportTraps          OBJECT IDENTIFIER ::= { mscComponents 3 }
                              -- traps may be defined in a number
                              -- of different modules. Defining this
                              -- component here makes the IMPORT clauses
                              -- easier to understand.


--
-- Version and Compliance statements
--
 
 
-- Object-Group Statement:

--    OBJECTS   { }
--    STATUS    current
--    DESCRIPTION
--       "A list of all current accessible leaf objects."

usefulDefinitionsGroup OBJECT IDENTIFIER ::= { usefulDefinitionsMIB 1 }
usefulDefinitionsGroupCA OBJECT IDENTIFIER ::= { usefulDefinitionsGroup 1 }
usefulDefinitionsGroupCA01 OBJECT IDENTIFIER ::= { usefulDefinitionsGroupCA 2 }
usefulDefinitionsGroupCA01A OBJECT IDENTIFIER ::= { usefulDefinitionsGroupCA01 2 }


-- Agent-Capabilities Statement:

--    PRODUCT-RELEASE "Passport Carrier Release 1.1 Useful Definitions."
--    STATUS          current
--    DESCRIPTION
--       "Carrier Passport Useful Definitions MIB: MIB Version CA01A."
--    SUPPORTS        Nortel-MsCarrier-MscPassport-UsefuleDefinitionsMIB
--    INCLUDES        { usefulDefinitionsGroupCA01A }

usefulDefinitionsCapabilities OBJECT IDENTIFIER ::= { usefulDefinitionsMIB 3 }
usefulDefinitionsCapabilitiesCA OBJECT IDENTIFIER ::= { usefulDefinitionsCapabilities 1 }
usefulDefinitionsCapabilitiesCA01 OBJECT IDENTIFIER ::= { usefulDefinitionsCapabilitiesCA 2 }
usefulDefinitionsCapabilitiesCA01A OBJECT IDENTIFIER ::= { usefulDefinitionsCapabilitiesCA01 2 }


END
