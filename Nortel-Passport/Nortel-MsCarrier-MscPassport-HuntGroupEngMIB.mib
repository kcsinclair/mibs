Nortel-MsCarrier-MscPassport-HuntGroupEngMIB
DEFINITIONS ::= BEGIN



IMPORTS

      OBJECT-TYPE
   FROM RFC-1212

      mscPassportMIBs
   FROM Nortel-MsCarrier-MscPassport-UsefulDefinitionsMIB

      Counter32,
      DisplayString,
      StorageType,
      RowStatus,
      Unsigned32
   FROM Nortel-MsCarrier-MscPassport-StandardTextualConventionsMIB

      NonReplicated
   FROM Nortel-MsCarrier-MscPassport-TextualConventionsMIB

      mscLpEng,
      mscLpIndex,
      mscLpEngIndex
   FROM Nortel-MsCarrier-MscPassport-LogicalProcessorMIB;




-- LAST-UPDATED   "9909010000Z"
-- ORGANIZATION   "Nortel Networks"
-- CONTACT-INFO   "
--         Nortel Carrier Data Network Management
--         
--         Postal:       P.O. Box 3511, Station C 
--                       Ottawa, Ontario 
--                       Canada  K1Y 4H7
--         
--         via the WEB:  http://www.nortelnetworks.com  
--                       select 'Contact Us' from the menu
--          
--         via phone:    1-800-4NORTEL"
-- DESCRIPTION
--    "The module describing the Nortel MsCarrier MscPassport
--     HuntGroupEng Enterprise MIB."

huntGroupEngMIB OBJECT IDENTIFIER ::= { mscPassportMIBs 131 }










-- Lp Eng HuntGroupService
-- The HuntGroupService component contains engineering statistics 
-- for all hunt groups on the FP.

mscLpEngHgs OBJECT IDENTIFIER ::= { mscLpEng 4 }



mscLpEngHgsRowStatusTable OBJECT-TYPE
   SYNTAX     SEQUENCE OF MscLpEngHgsRowStatusEntry
   ACCESS     not-accessible
   STATUS     mandatory
   DESCRIPTION
     "This entry controls the addition and deletion of 
      mscLpEngHgs components."
::= { mscLpEngHgs 1 }

mscLpEngHgsRowStatusEntry OBJECT-TYPE
   SYNTAX     MscLpEngHgsRowStatusEntry
   ACCESS     not-accessible
   STATUS     mandatory
   DESCRIPTION
     "A single entry in the table represents a single 
      mscLpEngHgs component."
   INDEX {
      mscLpIndex,
      mscLpEngIndex,
      mscLpEngHgsIndex }
::= { mscLpEngHgsRowStatusTable 1 }

MscLpEngHgsRowStatusEntry ::= SEQUENCE {
   mscLpEngHgsRowStatus
      RowStatus,
   mscLpEngHgsComponentName
      DisplayString,
   mscLpEngHgsStorageType
      StorageType,
   mscLpEngHgsIndex
      NonReplicated }

mscLpEngHgsRowStatus OBJECT-TYPE
   SYNTAX     RowStatus 
   ACCESS     read-write
   STATUS     mandatory
   DESCRIPTION
     "This variable is used as the basis for SNMP naming of
      mscLpEngHgs components.
      These components can be added and deleted."
::= { mscLpEngHgsRowStatusEntry 1 }

mscLpEngHgsComponentName OBJECT-TYPE
   SYNTAX     DisplayString 
   ACCESS     read-only
   STATUS     mandatory
   DESCRIPTION
     "This variable provides the component's string name for
      use with the ASCII Console Interface"
::= { mscLpEngHgsRowStatusEntry 2 }

mscLpEngHgsStorageType OBJECT-TYPE
   SYNTAX     StorageType 
   ACCESS     read-only
   STATUS     mandatory
   DESCRIPTION
     "This variable represents the storage type value for the
      mscLpEngHgs tables."
::= { mscLpEngHgsRowStatusEntry 4 }

mscLpEngHgsIndex OBJECT-TYPE
   SYNTAX     NonReplicated 
   ACCESS     not-accessible
   STATUS     mandatory
   DESCRIPTION
     "This variable represents the index for the mscLpEngHgs tables."
::= { mscLpEngHgsRowStatusEntry 10 }

mscLpEngHgsOperationalTable OBJECT-TYPE
   SYNTAX     SEQUENCE OF MscLpEngHgsOperationalEntry
   ACCESS     not-accessible
   STATUS     mandatory
   DESCRIPTION
     "The Operational group contains attributes for all hunt groups on the 
      LP."
::= { mscLpEngHgs 10 }

mscLpEngHgsOperationalEntry OBJECT-TYPE
   SYNTAX     MscLpEngHgsOperationalEntry
   ACCESS     not-accessible
   STATUS     mandatory
   DESCRIPTION
     "An entry in the mscLpEngHgsOperationalTable."
   INDEX {
      mscLpIndex,
      mscLpEngIndex,
      mscLpEngHgsIndex }
::= { mscLpEngHgsOperationalTable 1 }

MscLpEngHgsOperationalEntry ::= SEQUENCE {
   mscLpEngHgsHuntGroups
      Unsigned32,
   mscLpEngHgsHuntAttempts
      Counter32 }

mscLpEngHgsHuntGroups OBJECT-TYPE
   SYNTAX     Unsigned32 (0..65535)
   ACCESS     read-only
   STATUS     mandatory
   DESCRIPTION
     "This attribute indicates the number of hunt groups provisioned on 
      the LP."
   DEFVAL     { 0 }
::= { mscLpEngHgsOperationalEntry 1 }

mscLpEngHgsHuntAttempts OBJECT-TYPE
   SYNTAX     Counter32 
   ACCESS     read-only
   STATUS     mandatory
   DESCRIPTION
     "This attribute counts the total number of hunt attempts made by all 
      hunt groups. The count includes both initial and subsequent hunt 
      attempts. Individual hunt groups maintain this counter within the 
      huntAttempts attribute of the Hg/n component. This counter wraps 
      to 0 when it exceeds its maximum value."
::= { mscLpEngHgsOperationalEntry 2 }




-- 
-- Version and Compliance statements
-- 



-- Object-Group Statement:
-- A list of all current accessible leaf objects.

-- OBJECTS { mscLpEngHgsComponentName,
--           mscLpEngHgsStorageType,
--           mscLpEngHgsRowStatus,
--           mscLpEngHgsHuntGroups,
--           mscLpEngHgsHuntAttempts }
-- STATUS  mandatory
-- DESCRIPTION
--   "A list of all current accessible leaf objects."

huntGroupEngGroup OBJECT IDENTIFIER ::= { huntGroupEngMIB 1 }
huntGroupEngGroupCA OBJECT IDENTIFIER ::= { huntGroupEngGroup 1 }
huntGroupEngGroupCA02 OBJECT IDENTIFIER ::= { huntGroupEngGroupCA 3 }
huntGroupEngGroupCA02A OBJECT IDENTIFIER ::= { huntGroupEngGroupCA02 2 }



-- Agent-Capabilities Statement:

-- PRODUCT-RELEASE "MscPassport Release 1.2 HuntGroupEng."
-- STATUS          mandatory
-- DESCRIPTION     "Carrier Passport HuntGroupEng MIB: MIB Version CA02A,
--                  Software Version CA02S9C."
-- SUPPORTS        Nortel-MsCarrier-MscPassport-HuntGroupEngMIB
--    INCLUDES     { huntGroupEngGroupCA02A }

huntGroupEngCapabilities OBJECT IDENTIFIER ::= { huntGroupEngMIB 3 }
huntGroupEngCapabilitiesCA OBJECT IDENTIFIER ::= { huntGroupEngCapabilities 1 }
huntGroupEngCapabilitiesCA02 OBJECT IDENTIFIER ::= { huntGroupEngCapabilitiesCA 3 }
huntGroupEngCapabilitiesCA02A OBJECT IDENTIFIER ::= { huntGroupEngCapabilitiesCA02 2 }





END
