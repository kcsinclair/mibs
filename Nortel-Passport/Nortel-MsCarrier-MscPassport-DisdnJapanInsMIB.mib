Nortel-MsCarrier-MscPassport-DisdnJapanInsMIB
DEFINITIONS ::= BEGIN



IMPORTS

      OBJECT-TYPE
   FROM RFC-1212

      mscPassportMIBs
   FROM Nortel-MsCarrier-MscPassport-UsefulDefinitionsMIB

      DisplayString,
      StorageType,
      RowStatus,
      Unsigned32
   FROM Nortel-MsCarrier-MscPassport-StandardTextualConventionsMIB

      NonReplicated,
      Link
   FROM Nortel-MsCarrier-MscPassport-TextualConventionsMIB

      mscDataSigChanIndex,
      mscDataSigChan
   FROM Nortel-MsCarrier-MscPassport-DataIsdnMIB;




-- LAST-UPDATED   "9909010000Z"
-- ORGANIZATION   "Nortel Networks"
-- CONTACT-INFO   "
--         Nortel Carrier Data Network Management
--         
--         Postal:       P.O. Box 3511, Station C 
--                       Ottawa, Ontario 
--                       Canada  K1Y 4H7
--         
--         via the WEB:  http://www.nortelnetworks.com  
--                       select 'Contact Us' from the menu
--          
--         via phone:    1-800-4NORTEL"
-- DESCRIPTION
--    "The module describing the Nortel MsCarrier MscPassport
--     DisdnJapanIns Enterprise MIB."

disdnJapanInsMIB OBJECT IDENTIFIER ::= { mscPassportMIBs 118 }










-- DataSigChan/n JapanIns
-- The JapanIns component defines the operational characteristics of 
-- the signalling channel's connection to the external equipment.

mscDataSigChanIns OBJECT IDENTIFIER ::= { mscDataSigChan 11 }



mscDataSigChanInsRowStatusTable OBJECT-TYPE
   SYNTAX     SEQUENCE OF MscDataSigChanInsRowStatusEntry
   ACCESS     not-accessible
   STATUS     mandatory
   DESCRIPTION
     "This entry controls the addition and deletion of 
      mscDataSigChanIns components."
::= { mscDataSigChanIns 1 }

mscDataSigChanInsRowStatusEntry OBJECT-TYPE
   SYNTAX     MscDataSigChanInsRowStatusEntry
   ACCESS     not-accessible
   STATUS     mandatory
   DESCRIPTION
     "A single entry in the table represents a single 
      mscDataSigChanIns component."
   INDEX {
      mscDataSigChanIndex,
      mscDataSigChanInsIndex }
::= { mscDataSigChanInsRowStatusTable 1 }

MscDataSigChanInsRowStatusEntry ::= SEQUENCE {
   mscDataSigChanInsRowStatus
      RowStatus,
   mscDataSigChanInsComponentName
      DisplayString,
   mscDataSigChanInsStorageType
      StorageType,
   mscDataSigChanInsIndex
      NonReplicated }

mscDataSigChanInsRowStatus OBJECT-TYPE
   SYNTAX     RowStatus 
   ACCESS     read-write
   STATUS     mandatory
   DESCRIPTION
     "This variable is used as the basis for SNMP naming of
      mscDataSigChanIns components.
      These components can be added and deleted."
::= { mscDataSigChanInsRowStatusEntry 1 }

mscDataSigChanInsComponentName OBJECT-TYPE
   SYNTAX     DisplayString 
   ACCESS     read-only
   STATUS     mandatory
   DESCRIPTION
     "This variable provides the component's string name for
      use with the ASCII Console Interface"
::= { mscDataSigChanInsRowStatusEntry 2 }

mscDataSigChanInsStorageType OBJECT-TYPE
   SYNTAX     StorageType 
   ACCESS     read-only
   STATUS     mandatory
   DESCRIPTION
     "This variable represents the storage type value for the
      mscDataSigChanIns tables."
::= { mscDataSigChanInsRowStatusEntry 4 }

mscDataSigChanInsIndex OBJECT-TYPE
   SYNTAX     NonReplicated 
   ACCESS     not-accessible
   STATUS     mandatory
   DESCRIPTION
     "This variable represents the index for the mscDataSigChanIns tables."
::= { mscDataSigChanInsRowStatusEntry 10 }

mscDataSigChanInsL2Table OBJECT-TYPE
   SYNTAX     SEQUENCE OF MscDataSigChanInsL2Entry
   ACCESS     not-accessible
   STATUS     mandatory
   DESCRIPTION
     "This group represents the provisionable Layer 2 attributes of the 
      Q931 CCITT protocol."
::= { mscDataSigChanIns 11 }

mscDataSigChanInsL2Entry OBJECT-TYPE
   SYNTAX     MscDataSigChanInsL2Entry
   ACCESS     not-accessible
   STATUS     mandatory
   DESCRIPTION
     "An entry in the mscDataSigChanInsL2Table."
   INDEX {
      mscDataSigChanIndex,
      mscDataSigChanInsIndex }
::= { mscDataSigChanInsL2Table 1 }

MscDataSigChanInsL2Entry ::= SEQUENCE {
   mscDataSigChanInsT23
      Unsigned32,
   mscDataSigChanInsT200
      Unsigned32,
   mscDataSigChanInsN200
      Unsigned32,
   mscDataSigChanInsT203
      Unsigned32,
   mscDataSigChanInsN201
      Unsigned32,
   mscDataSigChanInsCircuitSwitchedK
      Unsigned32 }

mscDataSigChanInsT23 OBJECT-TYPE
   SYNTAX     Unsigned32 (1..15)
   ACCESS     read-write
   STATUS     mandatory
   DESCRIPTION
     "This attribute specifies the layer2 enable request timer."
   DEFVAL     { 10 }
::= { mscDataSigChanInsL2Entry 1 }

mscDataSigChanInsT200 OBJECT-TYPE
   SYNTAX     Unsigned32 (1..20)
   ACCESS     read-write
   STATUS     mandatory
   DESCRIPTION
     "This attribute specifies the maximum time between a layer 2 frame 
      and its acknowledgement"
   DEFVAL     { 2 }
::= { mscDataSigChanInsL2Entry 2 }

mscDataSigChanInsN200 OBJECT-TYPE
   SYNTAX     Unsigned32 (1..8)
   ACCESS     read-write
   STATUS     mandatory
   DESCRIPTION
     "This attribute specifies the maximum number of re-transmissions of 
      a layer2 frame."
   DEFVAL     { 3 }
::= { mscDataSigChanInsL2Entry 3 }

mscDataSigChanInsT203 OBJECT-TYPE
   SYNTAX     Unsigned32 (2..40)
   ACCESS     read-write
   STATUS     mandatory
   DESCRIPTION
     "This attribute specifies the maximum time that a no layer 2 traffic 
      situation can last. Expiry triggers a check on whether the far end is 
      a live."
   DEFVAL     { 10 }
::= { mscDataSigChanInsL2Entry 4 }

mscDataSigChanInsN201 OBJECT-TYPE
   SYNTAX     Unsigned32 (4..260)
   ACCESS     read-write
   STATUS     mandatory
   DESCRIPTION
     "This attribute specifies the maximum number of octets in an 
      information field."
   DEFVAL     { 260 }
::= { mscDataSigChanInsL2Entry 5 }

mscDataSigChanInsCircuitSwitchedK OBJECT-TYPE
   SYNTAX     Unsigned32 (1..632)
   ACCESS     read-write
   STATUS     mandatory
   DESCRIPTION
     "This attribute specifies the maximum number of frames for B 
      channel use."
   DEFVAL     { 7 }
::= { mscDataSigChanInsL2Entry 6 }

mscDataSigChanInsProvTable OBJECT-TYPE
   SYNTAX     SEQUENCE OF MscDataSigChanInsProvEntry
   ACCESS     not-accessible
   STATUS     mandatory
   DESCRIPTION
     "This group defines the general options of the d-channel signalling 
      link."
::= { mscDataSigChanIns 13 }

mscDataSigChanInsProvEntry OBJECT-TYPE
   SYNTAX     MscDataSigChanInsProvEntry
   ACCESS     not-accessible
   STATUS     mandatory
   DESCRIPTION
     "An entry in the mscDataSigChanInsProvTable."
   INDEX {
      mscDataSigChanIndex,
      mscDataSigChanInsIndex }
::= { mscDataSigChanInsProvTable 1 }

MscDataSigChanInsProvEntry ::= SEQUENCE {
   mscDataSigChanInsSide
      INTEGER }

mscDataSigChanInsSide OBJECT-TYPE
   SYNTAX     INTEGER  {
                 network(1),
                 user(2) }
   ACCESS     read-write
   STATUS     mandatory
   DESCRIPTION
     "This attribute specifies whether the layer 2 HDLC interface is the 
      network or user side of the connection."
   DEFVAL     { user }
::= { mscDataSigChanInsProvEntry 1 }

mscDataSigChanInsOperTable OBJECT-TYPE
   SYNTAX     SEQUENCE OF MscDataSigChanInsOperEntry
   ACCESS     not-accessible
   STATUS     mandatory
   DESCRIPTION
     "This group provides the operational attributes for the signalling 
      protocol."
::= { mscDataSigChanIns 15 }

mscDataSigChanInsOperEntry OBJECT-TYPE
   SYNTAX     MscDataSigChanInsOperEntry
   ACCESS     not-accessible
   STATUS     mandatory
   DESCRIPTION
     "An entry in the mscDataSigChanInsOperTable."
   INDEX {
      mscDataSigChanIndex,
      mscDataSigChanInsIndex }
::= { mscDataSigChanInsOperTable 1 }

MscDataSigChanInsOperEntry ::= SEQUENCE {
   mscDataSigChanInsActiveChannels
      Unsigned32,
   mscDataSigChanInsPeakActiveChannels
      Unsigned32,
   mscDataSigChanInsDChanStatus
      INTEGER }

mscDataSigChanInsActiveChannels OBJECT-TYPE
   SYNTAX     Unsigned32 (0..128)
   ACCESS     read-only
   STATUS     mandatory
   DESCRIPTION
     "This attribute indicates the number of currently active channels. 
      This includes data and voice channels."
   DEFVAL     { 0 }
::= { mscDataSigChanInsOperEntry 1 }

mscDataSigChanInsPeakActiveChannels OBJECT-TYPE
   SYNTAX     Unsigned32 (0..128)
   ACCESS     read-only
   STATUS     mandatory
   DESCRIPTION
     "This attribute indicates the maximum number of channels that have 
      been active on this signalling channel during the last polling period."
   DEFVAL     { 0 }
::= { mscDataSigChanInsOperEntry 4 }

mscDataSigChanInsDChanStatus OBJECT-TYPE
   SYNTAX     INTEGER  {
                 outOfService(0),
                 establishing(1),
                 established(2),
                 enabling(3),
                 inService(4),
                 restarting(5) }
   ACCESS     read-only
   STATUS     mandatory
   DESCRIPTION
     "This attribute indicates the state of the D-channel. 
      outOfService means that there is no layer 2 or layer 3 connectivity 
      to the PBX.
      establishing means that the signalling channel is attempting to stage 
      the layer 2.
      established means that the layer 2 is enabled. If the signalling 
      channel stays in the established state, then it is waiting for a restart 
      from the PBX.
      enabling means that the resources for processing calls are being 
      initialized. If the signalling channel stays in the enabling state then 
      it is waiting for a restart acknowledgement from the PBX. 
      inService means that the resources for processing calls are 
      available. 
      restarting means that the resources for call processing are being rei-
      initialized."
::= { mscDataSigChanInsOperEntry 7 }

mscDataSigChanInsToolsTable OBJECT-TYPE
   SYNTAX     SEQUENCE OF MscDataSigChanInsToolsEntry
   ACCESS     not-accessible
   STATUS     mandatory
   DESCRIPTION
     "This group contains a series of operational attributes which turn on 
      and off several kinds of tracing."
::= { mscDataSigChanIns 16 }

mscDataSigChanInsToolsEntry OBJECT-TYPE
   SYNTAX     MscDataSigChanInsToolsEntry
   ACCESS     not-accessible
   STATUS     mandatory
   DESCRIPTION
     "An entry in the mscDataSigChanInsToolsTable."
   INDEX {
      mscDataSigChanIndex,
      mscDataSigChanInsIndex }
::= { mscDataSigChanInsToolsTable 1 }

MscDataSigChanInsToolsEntry ::= SEQUENCE {
   mscDataSigChanInsTracing
      OCTET STRING }

mscDataSigChanInsTracing OBJECT-TYPE
   SYNTAX     OCTET STRING (SIZE (1))
   ACCESS     read-write
   STATUS     mandatory
   DESCRIPTION
     "This attribute defines which types of tracing are active for this 
      signalling channel.  The tracing messages are sent to the debug 
      stream. To see the messages the agentQueue attribute in Col/debug 
      must be greater than 0 and a Telnet NMIS session must list the 
      debug stream in in its data streams (ex. set nmis telnet session/1 
      dataStreams debug). Different types of tracing can be enabled 
      simultaneously. 
      Note that tracing consumes additional CPU resources and will slow 
      down call processing on a heavily loaded card.  If there is message 
      block exhaustion tracing will be suspended for a period and then 
      automatically reenabled.  An alarm is generated on tracing 
      suspension and resumption.  This mechanism protects the function 
      processor against excessive numbers of tracing messages.
      
      Types of tracing include: 
      protocolErrors - get details of any protocol errors which are 
      occuring. Protocol errors are also reported in summary form as 
      alarms. 
      q931Summary - Summary of the Q.931 messages on the signalling 
      link, including certain call details (calling number, called number, 
      release codes). 
      q931Hex - Q.931 messages displayed in hex format.  Useful to 
      determine protocol compliance in case of errors reported on local or 
      remote ends.
      q931Symbolic - Q.931 messages parsed to give maximum detail.  
      Useful for understanding content of messages flowing on the link.
      portHex - Messages in hex format being sent and received on the 
      link.

      Description of bits:
      protocolErrors(0)
      q931Summary(1)
      q931Hex(2)
      q931Symbolic(3)
      portHex(4)"
::= { mscDataSigChanInsToolsEntry 1 }


-- 
-- DataSigChan/n ts014 Framer
-- 
-- The Framer component controls link layer framing for application 
-- components sending and receiving data on a link interface. It is also 
-- through Framer, that an application component is associated with a 
-- specific hardware link interface.
-- 
-- The Framer component provides provisionable attributes related to 
-- datapath aspects of the hardware interface (such as crc and frame 
-- length). The Framer component also provides a provisionable 
-- attribute which binds the application component to a specific 
-- hardware component.
-- 
-- The Framer component contains operational attributes for link 
-- interface datapath statistics (such as frame counts and aborts).
-- 

mscDataSigChanInsFramer OBJECT IDENTIFIER ::= { mscDataSigChanIns 2 }



mscDataSigChanInsFramerRowStatusTable OBJECT-TYPE
   SYNTAX     SEQUENCE OF MscDataSigChanInsFramerRowStatusEntry
   ACCESS     not-accessible
   STATUS     mandatory
   DESCRIPTION
     "This entry controls the addition and deletion of 
      mscDataSigChanInsFramer components."
::= { mscDataSigChanInsFramer 1 }

mscDataSigChanInsFramerRowStatusEntry OBJECT-TYPE
   SYNTAX     MscDataSigChanInsFramerRowStatusEntry
   ACCESS     not-accessible
   STATUS     mandatory
   DESCRIPTION
     "A single entry in the table represents a single 
      mscDataSigChanInsFramer component."
   INDEX {
      mscDataSigChanIndex,
      mscDataSigChanInsIndex,
      mscDataSigChanInsFramerIndex }
::= { mscDataSigChanInsFramerRowStatusTable 1 }

MscDataSigChanInsFramerRowStatusEntry ::= SEQUENCE {
   mscDataSigChanInsFramerRowStatus
      RowStatus,
   mscDataSigChanInsFramerComponentName
      DisplayString,
   mscDataSigChanInsFramerStorageType
      StorageType,
   mscDataSigChanInsFramerIndex
      NonReplicated }

mscDataSigChanInsFramerRowStatus OBJECT-TYPE
   SYNTAX     RowStatus 
   ACCESS     read-only
   STATUS     mandatory
   DESCRIPTION
     "This variable is used as the basis for SNMP naming of
      mscDataSigChanInsFramer components.
      These components cannot be added nor deleted."
::= { mscDataSigChanInsFramerRowStatusEntry 1 }

mscDataSigChanInsFramerComponentName OBJECT-TYPE
   SYNTAX     DisplayString 
   ACCESS     read-only
   STATUS     mandatory
   DESCRIPTION
     "This variable provides the component's string name for
      use with the ASCII Console Interface"
::= { mscDataSigChanInsFramerRowStatusEntry 2 }

mscDataSigChanInsFramerStorageType OBJECT-TYPE
   SYNTAX     StorageType 
   ACCESS     read-only
   STATUS     mandatory
   DESCRIPTION
     "This variable represents the storage type value for the
      mscDataSigChanInsFramer tables."
::= { mscDataSigChanInsFramerRowStatusEntry 4 }

mscDataSigChanInsFramerIndex OBJECT-TYPE
   SYNTAX     NonReplicated 
   ACCESS     not-accessible
   STATUS     mandatory
   DESCRIPTION
     "This variable represents the index for the mscDataSigChanInsFramer tables."
::= { mscDataSigChanInsFramerRowStatusEntry 10 }

mscDataSigChanInsFramerProvTable OBJECT-TYPE
   SYNTAX     SEQUENCE OF MscDataSigChanInsFramerProvEntry
   ACCESS     not-accessible
   STATUS     mandatory
   DESCRIPTION
     "This group contains the base provisioning data for the Framer 
      component. Application or hardware interface specific provisioning 
      data is contained in other provisionable Framer groups."
::= { mscDataSigChanInsFramer 10 }

mscDataSigChanInsFramerProvEntry OBJECT-TYPE
   SYNTAX     MscDataSigChanInsFramerProvEntry
   ACCESS     not-accessible
   STATUS     mandatory
   DESCRIPTION
     "An entry in the mscDataSigChanInsFramerProvTable."
   INDEX {
      mscDataSigChanIndex,
      mscDataSigChanInsIndex,
      mscDataSigChanInsFramerIndex }
::= { mscDataSigChanInsFramerProvTable 1 }

MscDataSigChanInsFramerProvEntry ::= SEQUENCE {
   mscDataSigChanInsFramerInterfaceName
      Link }

mscDataSigChanInsFramerInterfaceName OBJECT-TYPE
   SYNTAX     Link 
   ACCESS     read-write
   STATUS     mandatory
   DESCRIPTION
     "This attribute contains a hardware component name.
      
      The attribute associates the application with a specific link. This 
      defines the module processor on which Framer's parent component 
      (as well as Framer itself) will run."
::= { mscDataSigChanInsFramerProvEntry 1 }

mscDataSigChanInsFramerStateTable OBJECT-TYPE
   SYNTAX     SEQUENCE OF MscDataSigChanInsFramerStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscDataSigChanInsFramer 12 }

mscDataSigChanInsFramerStateEntry OBJECT-TYPE
   SYNTAX     MscDataSigChanInsFramerStateEntry
   ACCESS     not-accessible
   STATUS     mandatory
   DESCRIPTION
     "An entry in the mscDataSigChanInsFramerStateTable."
   INDEX {
      mscDataSigChanIndex,
      mscDataSigChanInsIndex,
      mscDataSigChanInsFramerIndex }
::= { mscDataSigChanInsFramerStateTable 1 }

MscDataSigChanInsFramerStateEntry ::= SEQUENCE {
   mscDataSigChanInsFramerAdminState
      INTEGER,
   mscDataSigChanInsFramerOperationalState
      INTEGER,
   mscDataSigChanInsFramerUsageState
      INTEGER }

mscDataSigChanInsFramerAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscDataSigChanInsFramerStateEntry 1 }

mscDataSigChanInsFramerOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscDataSigChanInsFramerStateEntry 2 }

mscDataSigChanInsFramerUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscDataSigChanInsFramerStateEntry 3 }

mscDataSigChanInsFramerStatsTable OBJECT-TYPE
   SYNTAX     SEQUENCE OF MscDataSigChanInsFramerStatsEntry
   ACCESS     not-accessible
   STATUS     mandatory
   DESCRIPTION
     "This group contains the operational statistics data for a Framer 
      component."
::= { mscDataSigChanInsFramer 13 }

mscDataSigChanInsFramerStatsEntry OBJECT-TYPE
   SYNTAX     MscDataSigChanInsFramerStatsEntry
   ACCESS     not-accessible
   STATUS     mandatory
   DESCRIPTION
     "An entry in the mscDataSigChanInsFramerStatsTable."
   INDEX {
      mscDataSigChanIndex,
      mscDataSigChanInsIndex,
      mscDataSigChanInsFramerIndex }
::= { mscDataSigChanInsFramerStatsTable 1 }

MscDataSigChanInsFramerStatsEntry ::= SEQUENCE {
   mscDataSigChanInsFramerFrmToIf
      Unsigned32,
   mscDataSigChanInsFramerFrmFromIf
      Unsigned32,
   mscDataSigChanInsFramerOctetFromIf
      Unsigned32,
   mscDataSigChanInsFramerAborts
      Unsigned32,
   mscDataSigChanInsFramerCrcErrors
      Unsigned32,
   mscDataSigChanInsFramerLrcErrors
      Unsigned32,
   mscDataSigChanInsFramerNonOctetErrors
      Unsigned32,
   mscDataSigChanInsFramerOverruns
      Unsigned32,
   mscDataSigChanInsFramerUnderruns
      Unsigned32,
   mscDataSigChanInsFramerLargeFrmErrors
      Unsigned32 }

mscDataSigChanInsFramerFrmToIf OBJECT-TYPE
   SYNTAX     Unsigned32 (0..4294967295)
   ACCESS     read-only
   STATUS     mandatory
   DESCRIPTION
     "This attribute counts the number of frames transmitted to the link 
      interface by Framer.
      This count wraps to zero after reaching its maximum value."
   DEFVAL     { 0 }
::= { mscDataSigChanInsFramerStatsEntry 1 }

mscDataSigChanInsFramerFrmFromIf OBJECT-TYPE
   SYNTAX     Unsigned32 (0..4294967295)
   ACCESS     read-only
   STATUS     mandatory
   DESCRIPTION
     "This attribute counts the number of frames received from the link 
      interface by Framer.
      This count wraps to zero after reaching its maximum value."
   DEFVAL     { 0 }
::= { mscDataSigChanInsFramerStatsEntry 2 }

mscDataSigChanInsFramerOctetFromIf OBJECT-TYPE
   SYNTAX     Unsigned32 (0..4294967295)
   ACCESS     read-only
   STATUS     mandatory
   DESCRIPTION
     "The number of bytes received from the link interface by Framer."
   DEFVAL     { 0 }
::= { mscDataSigChanInsFramerStatsEntry 3 }

mscDataSigChanInsFramerAborts OBJECT-TYPE
   SYNTAX     Unsigned32 (0..4294967295)
   ACCESS     read-only
   STATUS     mandatory
   DESCRIPTION
     "This attribute counts the total number of aborts received.
      This count wraps to zero after reaching its maximum value."
   DEFVAL     { 0 }
::= { mscDataSigChanInsFramerStatsEntry 4 }

mscDataSigChanInsFramerCrcErrors OBJECT-TYPE
   SYNTAX     Unsigned32 (0..4294967295)
   ACCESS     read-only
   STATUS     mandatory
   DESCRIPTION
     "This attribute counts the total number of frames with CRC errors.
      This count wraps to zero after reaching its maximum value."
   DEFVAL     { 0 }
::= { mscDataSigChanInsFramerStatsEntry 5 }

mscDataSigChanInsFramerLrcErrors OBJECT-TYPE
   SYNTAX     Unsigned32 (0..4294967295)
   ACCESS     read-only
   STATUS     mandatory
   DESCRIPTION
     "This attribute counts the total number of frames with LRC errors.
      This count wraps to zero after reaching its maximum value."
   DEFVAL     { 0 }
::= { mscDataSigChanInsFramerStatsEntry 6 }

mscDataSigChanInsFramerNonOctetErrors OBJECT-TYPE
   SYNTAX     Unsigned32 (0..4294967295)
   ACCESS     read-only
   STATUS     mandatory
   DESCRIPTION
     "This attribute counts the total number of frames that were non octet 
      aligned.
      This count wraps to zero after reaching its maximum value."
   DEFVAL     { 0 }
::= { mscDataSigChanInsFramerStatsEntry 7 }

mscDataSigChanInsFramerOverruns OBJECT-TYPE
   SYNTAX     Unsigned32 (0..4294967295)
   ACCESS     read-only
   STATUS     mandatory
   DESCRIPTION
     "This attribute counts the total number of frames received from the 
      link for which overruns occurred.
      This count wraps to zero after reaching its maximum value."
   DEFVAL     { 0 }
::= { mscDataSigChanInsFramerStatsEntry 8 }

mscDataSigChanInsFramerUnderruns OBJECT-TYPE
   SYNTAX     Unsigned32 (0..4294967295)
   ACCESS     read-only
   STATUS     mandatory
   DESCRIPTION
     "This attribute counts the total number of frames transmitted to the 
      link for which underruns occurred.
      This count wraps to zero after reaching its maximum value."
   DEFVAL     { 0 }
::= { mscDataSigChanInsFramerStatsEntry 9 }

mscDataSigChanInsFramerLargeFrmErrors OBJECT-TYPE
   SYNTAX     Unsigned32 (0..4294967295)
   ACCESS     read-only
   STATUS     mandatory
   DESCRIPTION
     "This attribute counts the total number of frames received which 
      were too large. The frame was longer than 500 bytes.
      This count wraps to zero after reaching its maximum value."
   DEFVAL     { 0 }
::= { mscDataSigChanInsFramerStatsEntry 10 }




-- 
-- Version and Compliance statements
-- 



-- Object-Group Statement:
-- A list of all current accessible leaf objects.

-- OBJECTS { mscDataSigChanInsRowStatus,
--           mscDataSigChanInsN201,
--           mscDataSigChanInsFramerFrmToIf,
--           mscDataSigChanInsFramerNonOctetErrors,
--           mscDataSigChanInsPeakActiveChannels,
--           mscDataSigChanInsFramerUsageState,
--           mscDataSigChanInsFramerComponentName,
--           mscDataSigChanInsN200,
--           mscDataSigChanInsSide,
--           mscDataSigChanInsFramerFrmFromIf,
--           mscDataSigChanInsFramerInterfaceName,
--           mscDataSigChanInsFramerStorageType,
--           mscDataSigChanInsCircuitSwitchedK,
--           mscDataSigChanInsFramerUnderruns,
--           mscDataSigChanInsComponentName,
--           mscDataSigChanInsFramerCrcErrors,
--           mscDataSigChanInsStorageType,
--           mscDataSigChanInsFramerOperationalState,
--           mscDataSigChanInsT200,
--           mscDataSigChanInsActiveChannels,
--           mscDataSigChanInsFramerOctetFromIf,
--           mscDataSigChanInsT203,
--           mscDataSigChanInsDChanStatus,
--           mscDataSigChanInsFramerAdminState,
--           mscDataSigChanInsT23,
--           mscDataSigChanInsFramerLrcErrors,
--           mscDataSigChanInsFramerLargeFrmErrors,
--           mscDataSigChanInsFramerOverruns,
--           mscDataSigChanInsFramerRowStatus,
--           mscDataSigChanInsTracing,
--           mscDataSigChanInsFramerAborts }
-- STATUS  mandatory
-- DESCRIPTION
--   "A list of all current accessible leaf objects."

disdnJapanInsGroup OBJECT IDENTIFIER ::= { disdnJapanInsMIB 1 }
disdnJapanInsGroupCA OBJECT IDENTIFIER ::= { disdnJapanInsGroup 1 }
disdnJapanInsGroupCA02 OBJECT IDENTIFIER ::= { disdnJapanInsGroupCA 3 }
disdnJapanInsGroupCA02A OBJECT IDENTIFIER ::= { disdnJapanInsGroupCA02 2 }



-- Agent-Capabilities Statement:

-- PRODUCT-RELEASE "MscPassport Release 1.2 DisdnJapanIns."
-- STATUS          mandatory
-- DESCRIPTION     "Carrier Passport DisdnJapanIns MIB: MIB Version CA02A,
--                  Software Version CA02S9C."
-- SUPPORTS        Nortel-MsCarrier-MscPassport-DisdnJapanInsMIB
--    INCLUDES     { disdnJapanInsGroupCA02A }

disdnJapanInsCapabilities OBJECT IDENTIFIER ::= { disdnJapanInsMIB 3 }
disdnJapanInsCapabilitiesCA OBJECT IDENTIFIER ::= { disdnJapanInsCapabilities 1 }
disdnJapanInsCapabilitiesCA02 OBJECT IDENTIFIER ::= { disdnJapanInsCapabilitiesCA 3 }
disdnJapanInsCapabilitiesCA02A OBJECT IDENTIFIER ::= { disdnJapanInsCapabilitiesCA02 2 }





END
