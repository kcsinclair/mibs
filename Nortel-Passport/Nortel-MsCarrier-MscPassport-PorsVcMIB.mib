Nortel-MsCarrier-MscPassport-PorsVcMIB
DEFINITIONS ::= BEGIN



IMPORTS

      OBJECT-TYPE
   FROM RFC-1212

      mscPassportMIBs
   FROM Nortel-MsCarrier-MscPassport-UsefulDefinitionsMIB

      RowPointer,
      DisplayString,
      StorageType,
      RowStatus,
      Integer32,
      Unsigned32
   FROM Nortel-MsCarrier-MscPassport-StandardTextualConventionsMIB

      AsciiString,
      NonReplicated,
      EnterpriseDateAndTime,
      Link
   FROM Nortel-MsCarrier-MscPassport-TextualConventionsMIB

      mscRtgIndex,
      mscRtg
   FROM Nortel-MsCarrier-MscPassport-BaseRoutingMIB;




-- LAST-UPDATED   "9909010000Z"
-- ORGANIZATION   "Nortel Networks"
-- CONTACT-INFO   "
--         Nortel Carrier Data Network Management
--         
--         Postal:       P.O. Box 3511, Station C 
--                       Ottawa, Ontario 
--                       Canada  K1Y 4H7
--         
--         via the WEB:  http://www.nortelnetworks.com  
--                       select 'Contact Us' from the menu
--          
--         via phone:    1-800-4NORTEL"
-- DESCRIPTION
--    "The module describing the Nortel MsCarrier MscPassport
--     PorsVc Enterprise MIB."

porsVcMIB OBJECT IDENTIFIER ::= { mscPassportMIBs 37 }










-- Routing RouteSelector
-- This component sits directly under the Routing component. It is 
-- dynamically created by Routing System and thus is always present 
-- when PORS software is loaded on a Passport node. RouteSelector is 
-- used by PORS services for the following purposes:
-- - Selecting a route to a destination through the current topology 
-- region. The route may be directly to the destination node or to a 
-- gateway node through which the destination can be reached.
-- - Returning a manual route stored as part of manual path profile.
-- 
-- RouteSelector is invoked with a route request data containing one of 
-- the following:
-- - Parameters which must be met by the selected route.
-- - Parameter profile reference where parameters which must be met 
-- by the selected route are stored.
-- - Manual path profile reference.
-- 
-- When the route request data contains a manual path profile 
-- reference then RouteSelector returns the manual path route 
-- associated with that reference. The manual path route is returned in 
-- the selected route description data. RouteSelector does not verify 
-- the manual path route. 
-- 
-- When the route request data contains parameter profile reference 
-- then RouteSelector obtains route request data parameters associated 
-- with that reference and then proceeds as though the parameters 
-- were contained in the route request data.
-- 
-- Using the route request data parameters, RouteSelector uses a route 
-- selection algorithm, based on Dijkstra's Shortest-Path-First 
-- algorithm, to select the best route to the destination. That route may 
-- be directly to the destination node or to a gateway node through 
-- which the destination can be reached. The selected route must 
-- satisfy all the route request data parameters. The route selection is 
-- done against the current view of the topological database 
-- maintained by Routing Topology System of the current topology 
-- region. Once the route is selected, selected route description data is 
-- returned by RouteSelector.
-- 
-- RouteSelector can be used in two modes: automatic and manual. 
-- 
-- In the automatic mode, a route request message containing the route 
-- request data is originated by a PORS VC and sent to RouteSelector. 
-- RouteSelector then selects a route or gets a manual route and returns 
-- its description in the selected route description data in the selected 
-- route message back to the PORS VC.
-- 
-- In the manual mode, RouteSelector allows the operator to modify 
-- the parameters in the route request data (except for the manual path 
-- profile reference), and to initiate route selection using that data. 
-- When RouteSelector selects the route it displays its description to 
-- the operator.

mscRtgRs OBJECT IDENTIFIER ::= { mscRtg 2 }



mscRtgRsRowStatusTable OBJECT-TYPE
   SYNTAX     SEQUENCE OF MscRtgRsRowStatusEntry
   ACCESS     not-accessible
   STATUS     mandatory
   DESCRIPTION
     "This entry controls the addition and deletion of 
      mscRtgRs components."
::= { mscRtgRs 1 }

mscRtgRsRowStatusEntry OBJECT-TYPE
   SYNTAX     MscRtgRsRowStatusEntry
   ACCESS     not-accessible
   STATUS     mandatory
   DESCRIPTION
     "A single entry in the table represents a single 
      mscRtgRs component."
   INDEX {
      mscRtgIndex,
      mscRtgRsIndex }
::= { mscRtgRsRowStatusTable 1 }

MscRtgRsRowStatusEntry ::= SEQUENCE {
   mscRtgRsRowStatus
      RowStatus,
   mscRtgRsComponentName
      DisplayString,
   mscRtgRsStorageType
      StorageType,
   mscRtgRsIndex
      NonReplicated }

mscRtgRsRowStatus OBJECT-TYPE
   SYNTAX     RowStatus 
   ACCESS     read-only
   STATUS     mandatory
   DESCRIPTION
     "This variable is used as the basis for SNMP naming of
      mscRtgRs components.
      These components cannot be added nor deleted."
::= { mscRtgRsRowStatusEntry 1 }

mscRtgRsComponentName OBJECT-TYPE
   SYNTAX     DisplayString 
   ACCESS     read-only
   STATUS     mandatory
   DESCRIPTION
     "This variable provides the component's string name for
      use with the ASCII Console Interface"
::= { mscRtgRsRowStatusEntry 2 }

mscRtgRsStorageType OBJECT-TYPE
   SYNTAX     StorageType 
   ACCESS     read-only
   STATUS     mandatory
   DESCRIPTION
     "This variable represents the storage type value for the
      mscRtgRs tables."
::= { mscRtgRsRowStatusEntry 4 }

mscRtgRsIndex OBJECT-TYPE
   SYNTAX     NonReplicated 
   ACCESS     not-accessible
   STATUS     mandatory
   DESCRIPTION
     "This variable represents the index for the mscRtgRs tables."
::= { mscRtgRsRowStatusEntry 10 }

mscRtgRsSelectedRouteTable OBJECT-TYPE
   SYNTAX     SEQUENCE OF MscRtgRsSelectedRouteEntry
   ACCESS     not-accessible
   STATUS     mandatory
   DESCRIPTION
     "This group contains operational attributes describing the last 
      selected or manual route returned by RouteSelector. These attributes 
      form selected route description data."
::= { mscRtgRs 10 }

mscRtgRsSelectedRouteEntry OBJECT-TYPE
   SYNTAX     MscRtgRsSelectedRouteEntry
   ACCESS     not-accessible
   STATUS     mandatory
   DESCRIPTION
     "An entry in the mscRtgRsSelectedRouteTable."
   INDEX {
      mscRtgIndex,
      mscRtgRsIndex }
::= { mscRtgRsSelectedRouteTable 1 }

MscRtgRsSelectedRouteEntry ::= SEQUENCE {
   mscRtgRsRouteCostMetric
      Unsigned32,
   mscRtgRsRouteDelayMetric
      Unsigned32,
   mscRtgRsBumpingPriority
      Unsigned32,
   mscRtgRsReasonForNoRoute
      INTEGER,
   mscRtgRsAttributeNotMet
      INTEGER,
   mscRtgRsRouteGatewayCostMetric
      Unsigned32,
   mscRtgRsRouteType
      INTEGER }

mscRtgRsRouteCostMetric OBJECT-TYPE
   SYNTAX     Unsigned32 (0..999999)
   ACCESS     read-only
   STATUS     mandatory
   DESCRIPTION
     "This attribute indicates the sum of cost metrics of trunks that make 
      up the selected route returned by RouteSelector. If the cost metrics 
      at both ends of a trunk differ, the larger metric is used for that trunk. 
      If a route could not be selected for whatever reason then the 
      routeCostMetric is set to a value 999999 intended to symbolize 
      unknown cost. For manual routes the value of routeCostMetric is 
      also 999999. This is because RouteSelector does not verify manual 
      routes thus routeCostMetric is unknown."
   DEFVAL     { 999999 }
::= { mscRtgRsSelectedRouteEntry 1 }

mscRtgRsRouteDelayMetric OBJECT-TYPE
   SYNTAX     Unsigned32 (0..999999)
   ACCESS     read-only
   STATUS     mandatory
   DESCRIPTION
     "This attribute indicates the sum of delay metrics of trunks that make 
      up the selected route returned by RouteSelector. The delay metric of 
      a trunk is equal to half the measuredRoundTripDelay operational 
      attribute of the trunk. If the delay metrics at both ends of a trunk 
      differ, the larger metric is used for that trunk. If a route could not be 
      selected for whatever reason then the routeDelayMetric is set to a 
      value 999999 intended to symbolize unknown delay. For manual 
      routes the value of routeDelayMetric is also 999999. This is 
      because RouteSelector does not verify manual routes, thus 
      routeDelayMetric is unknown."
   DEFVAL     { 999999 }
::= { mscRtgRsSelectedRouteEntry 2 }

mscRtgRsBumpingPriority OBJECT-TYPE
   SYNTAX     Unsigned32 (0..4)
   ACCESS     read-only
   STATUS     mandatory
   DESCRIPTION
     "This attribute indicates the priority at which a route has been 
      selected, or a value of 4 for manual routes since no route selection 
      was made. Since RouteSelector does not verify manual routes the 
      value of 4 for routeBumpingPriority symbolizes an unknown value 
      for manual routes. The remainder of the description is not 
      applicable to manual routes.
      
      The bumping priority of a route specifies a priority at which a path 
      along that route can be established. The lowest bumping priority is 
      4, the highest bumping priority is equal to a setup priority contained 
      in the route request data. If a route is selected at bumping priority 4, 
      then no paths will be bumped since there appears to be enough free 
      bandwidth on selected trunks, and also since this bumping priority 
      is not better than the lowest holding priority (4) of any path. 
      
      If a route cannot be selected at bumping priority 4 and a setup 
      priority is 3 or better, then a route may be selected at bumping 
      priority 3. This means that paths at holding priority 4 may be 
      bumped if currently there is not enough free bandwidth on selected 
      trunks to establish the new path with setup priority 3. 
      
      If a route cannot be selected at bumping priority 3 and a setup 
      priority is 2 or better, then a route may be selected at bumping 
      priority 2. In this case paths with holding priority 4 and 3 may be 
      bumped if there is not enough free bandwidth on selected trunks to 
      establish the new path with setup priority 2. 
      
      If a route cannot be selected at bumping priority 2 and a setup 
      priority is 1 or better, then a route may be selected at bumping 
      priority 1. In this case paths with holding priority 4, 3, and 2 may be 
      bumped if there is not enough free bandwidth on selected trunks to 
      establish the new path with setup priority 1.
      
      If a route cannot be selected at bumping priority 1 and a setup 
      priority is 0, then a route may be selected at bumping priority 0. In 
      this case paths with holding priority 4, 3, 2, and 1 may be bumped if 
      there is not enough free bandwidth on selected trunks to establish 
      the new path with setup priority 0."
::= { mscRtgRsSelectedRouteEntry 3 }

mscRtgRsReasonForNoRoute OBJECT-TYPE
   SYNTAX     INTEGER  {
                 none(0),
                 destinationNameTooLong(1),
                 destinationNotSpecified(2),
                 unknownDestinationName(3),
                 incorrectDestination(4),
                 incorrectDestinationEndPoint(5),
                 unknownSource(6),
                 unknownDestination(7),
                 sameNode(8),
                 routeCostTooMuch(9),
                 routeDelayTooLong(10),
                 attributesNotMet(11),
                 internalReason(12),
                 attributeProfileProblem(13),
                 manualPathIndexProblem(14) }
   ACCESS     read-only
   STATUS     mandatory
   DESCRIPTION
     "This attribute indicates the reason for which a route was not 
      selected by RouteSelector. 
      
      If the route was selected then reasonForNoRoute has a value of 
      none.
      
      If the destination in the form of ASCII name was specified (see 
      destination) and the name of node is too long (more than 12 
      characters) then reasonForNoRoute has a value of 
      destinationNameTooLong. Check and correct node name in the 
      destination attribute.
      
      If the destination was not specified, that is destination is blank, then 
      reasonForNoRoute has a value of destinationNotSpecified. 
      Destination attribute should not be blank.
      
      If the destination in the form of ASCII name was specified (see 
      destination) and the name of node cannot be found in topological 
      database then reasonForNoRoute has a value of 
      unknownDestinationName. Check and correct node name in the 
      destination attribute. If it is correct then this node does not appear in 
      local topological database as this node may lie across the topology 
      region or cluster boundary.
      
      If the destination cannot be found in the topological database or 
      cannot be reached through any gateway node then 
      reasonForNoRoute has a value of unknownDestination. Ensure the 
      destination specified in destination attribute resides in the topology 
      region, or can be reached through a Routing Gateway. That is, at 
      least one reachable address provisioned under a Trunk Address 
      component representing a gateway link can reach the destination 
      NSAP address.
      
      If the destination was specified using an incorrect format (see 
      destination) then reasonForNoRoute has a value of 
      incorrectDestination. Use the correct format for destination 
      attribute.
      
      If there is no physical connectivity to the destination or gateway 
      node, or number of hops to such node exceeds a limit of 20 hops, or 
      a route to such node cannot satisfy all the parameters in the route 
      request data then reasonForNoRoute has a value of 
      attributeNotMet. Set operationMode to manual and issue d rtg rs 
      command and inspect attributeNotMet to determine which attribute 
      could not be satisfied.
      
      If the route to the destination could not be selected for some internal 
      reason then reasonForNoRoute has a value of internalReason. A 
      Software Alarm generated in association with this situation should 
      be reported to Nortel Networks technical support.
      
      If the route to the destination could not be selected because of 
      profile reference problem then reasonForNoRoute has a value of 
      attributeProfileProblem.
      
      If the route to the destination could not be selected because of 
      manual path reference problem then reasonForNoRoute has a value 
      of manualPathIndexProblem. 
      
      The following values of reasonForNoRoute are no longer 
      generated: routeCostTooMuch, routeDelayTooMuch, 
      incorrectDestinationEndPoint, and sameNode."
   DEFVAL     { none }
::= { mscRtgRsSelectedRouteEntry 4 }

mscRtgRsAttributeNotMet OBJECT-TYPE
   SYNTAX     INTEGER  {
                 unknownAttributeNotMet(0),
                 allAttributesMet(1),
                 requiredRxBandwidth(2),
                 requiredTxBandwidth(3),
                 requiredTrunkModes(4),
                 maximumAcceptableCost(5),
                 maximumAcceptableDelay(6),
                 requiredTrafficType(7),
                 permittedTrunkTypes(8),
                 requiredSecurity(9),
                 requiredCustomerParm(10),
                 maximumTransmissionUnit(11),
                 maximumAcceptableGatewayCost(12),
                 maximumGatewayHops(13) }
   ACCESS     read-only
   STATUS     mandatory
   DESCRIPTION
     "This attribute indicates the name of a possible route request data 
      parameter which prevents RouteSelector from selecting the route. 
      This attribute always has a value of allAttributesMet for manual 
      routes since RouteSelector does not verify manual routes. This 
      attribute has a meaningful value if reasonForNoRoute attribute has 
      a value of attributesNotMet. The value of attributeNotMet is only 
      computed when RouteSelector operates in manual mode. That is, 
      when route selection has been initiated by the operator in which 
      case operationMode has a value of manual. 
      
      RouteSelector determines which of the attributes: 
      requiredRxBandwidth, requiredTxBandwidth, requiredTrunkModes, 
      maximumAcceptableCost, maximumAcceptableDelay, 
      maximumAcceptableGatewaCost, requiredTrafficType, 
      permittedTrunkTypes, requiredSecurity, 
      requiredCustomerParameter, and maximumTransmissionUnit 
      prevents successful route selection by dropping the constraints 
      associated with that attribute and reselecting the route. If that route 
      can be successfully selected then the attribute for which the 
      constraints were dropped is the attribute preventing successful route 
      selection. 
      
      For example, RouteSelector drops bandwidth constraints by 
      selecting a route with requiredRxBandwidth or 
      requiredTxBandwidth of 0. If the route can be selected then 
      bandwidth is preventing successful route selection.
      
      A value of unknownAttributeNotMet indicates that RouteSelector 
      cannot determine why route cannot be selected. Constraints for all 
      attributes are dropped yet successful route cannot be computed. 
      This usually indicates a lack physical connectivity to the destination 
      or gateway node. Alternatively, this may indicate that destination or 
      gateway node is more than 20 hops away where 20 hops is the 
      maximum number of hops in the route."
   DEFVAL     { allAttributesMet }
::= { mscRtgRsSelectedRouteEntry 5 }

mscRtgRsRouteGatewayCostMetric OBJECT-TYPE
   SYNTAX     Unsigned32 (0..999999)
   ACCESS     read-only
   STATUS     mandatory
   DESCRIPTION
     "This attribute indicates the cost metric associated with reaching the 
      destination indirectly through a gateway node or gateway link that 
      is part of the selected route If the selected route leads directly to the 
      destination node then the routeGatewayCostMetric is set to a value 
      0. If a route could not be selected for whatever reason then the 
      routeGatewayCostMetric is set to a value 999999 intended to 
      symbolize unknown cost. For manual routes the value of 
      routeGatewayCostMetric is also 999999. This is because 
      RouteSelector does not verify manual routes thus 
      routeGatewayCostMetric is unknown."
   DEFVAL     { 0 }
::= { mscRtgRsSelectedRouteEntry 6 }

mscRtgRsRouteType OBJECT-TYPE
   SYNTAX     INTEGER  {
                 noRoute(3),
                 sameNode(4),
                 destinationNode(5),
                 destinationNodeLegacy(6),
                 gatewayNode(7),
                 gatewayLink(8),
                 routingGateway(9),
                 manual(10) }
   ACCESS     read-only
   STATUS     mandatory
   DESCRIPTION
     "This attribute indicates the type of route that was selected by 
      RouteSelector. 
      
      If no route was selected then routeType has a value of noRoute. 
      
      If the destination resides on the current node then routeType has a 
      value of sameNode. 
      
      If the destination resides on a different node and can be reached 
      directly as opposed to indirectly through a gateway node then 
      routeType has a value of destinationNode or 
      destinationNodeLegacy with the latter only possible when legacy 
      gateway selection algorithm was used (see 
      gatewaySelectionAlgorithm).
      
      If the destination can be reached indirectly through a gateway node 
      with the gateway node being different from the current node then 
      routeType has a value of gatewayNode or gatewayLink depending 
      on whether or not the route consists of a single gateway link. A 
      route consists of a single gateway link only when the route 
      requestor (see routeRequestor) is a Routing Gateway (in inbound or 
      outbound direction) and the route leads immediately across 
      topology region or cluster boundary.
      
      If the destination can be reached indirectly through a gateway node 
      with the gateway node being the current node and the route 
      requestor (see routeRequestor) is an application service as opposed 
      to a Routing Gateway then routeType has a value of 
      routingGateway.
      
      If selected route is a manual route then routeType has a value of 
      manual.
      
      Note that the type of route, except for manual route, depends on 
      who is the route requestor (application service, Routing Gateway 
      serving as inbound or outbound gateway), where it resides (gateway 
      or non-gateway node), how the destination can be reached (directly 
      or indirectly through a gateway node), and what is the gateway 
      selection algorithm (cost-based, random or legacy)."
   DEFVAL     { noRoute }
::= { mscRtgRsSelectedRouteEntry 8 }

mscRtgRsControlsTable OBJECT-TYPE
   SYNTAX     SEQUENCE OF MscRtgRsControlsEntry
   ACCESS     not-accessible
   STATUS     mandatory
   DESCRIPTION
     "This group contains attributes used to control RouteSelector."
::= { mscRtgRs 11 }

mscRtgRsControlsEntry OBJECT-TYPE
   SYNTAX     MscRtgRsControlsEntry
   ACCESS     not-accessible
   STATUS     mandatory
   DESCRIPTION
     "An entry in the mscRtgRsControlsTable."
   INDEX {
      mscRtgIndex,
      mscRtgRsIndex }
::= { mscRtgRsControlsTable 1 }

MscRtgRsControlsEntry ::= SEQUENCE {
   mscRtgRsRouteSelectionAttributes
      INTEGER,
   mscRtgRsOperationMode
      INTEGER,
   mscRtgRsLastRouteSelectionTime
      EnterpriseDateAndTime }

mscRtgRsRouteSelectionAttributes OBJECT-TYPE
   SYNTAX     INTEGER  {
                 fromOperator(0),
                 fromLastRouteRequest(1) }
   ACCESS     read-write
   STATUS     obsolete
   DESCRIPTION
     "This attribute acts as a 2-position switch, allowing an operator to 
      specify whether the route selection attributes kept by the 
      RouteSelector should be as he/she set them: 
      routeSelectionAttributes = fromOperator, 
      or the route selection attributes could be updated automatically to 
      contain the route selection attributes of the last automatic route 
      request: 
      routeSelectionAttributes = fromLastRouteRequest."
   DEFVAL     { fromLastRouteRequest }
::= { mscRtgRsControlsEntry 1 }

mscRtgRsOperationMode OBJECT-TYPE
   SYNTAX     INTEGER  {
                 automatic(0),
                 manual(1) }
   ACCESS     read-write
   STATUS     mandatory
   DESCRIPTION
     "This attribute indicates the mode in which the RouteSelector is 
      currently operating. The two possible modes are automatic and 
      manual. 
      
      In the automatic mode, a route request message containing the route 
      request data is originated by a PORS VC and sent to the 
      RouteSelector. RouteSelector then selects a route or gets a manual 
      route and returns its description in the selected route description 
      data in the selected route message back to the PORS VC.
      
      In the manual mode, the RouteSelector allows the operator to 
      modify the parameters in the route request data (except for the 
      manual path profile reference), and to initiate route selection using 
      that data. When RouteSelector selects the route it displays its 
      description to the operator.
      
      Note that even when operationMode is set to manual, 
      RouteSelector handles route request messages originated by 
      services' VCs in the same way as it does when operationMode is 
      set to automatic."
   DEFVAL     { automatic }
::= { mscRtgRsControlsEntry 2 }

mscRtgRsLastRouteSelectionTime OBJECT-TYPE
   SYNTAX     EnterpriseDateAndTime (SIZE (0 | 19))
   ACCESS     read-only
   STATUS     mandatory
   DESCRIPTION
     "This attribute indicates the time when RouteSelector last handled a 
      route request message."
::= { mscRtgRsControlsEntry 3 }

mscRtgRsPathAttributesTable OBJECT-TYPE
   SYNTAX     SEQUENCE OF MscRtgRsPathAttributesEntry
   ACCESS     not-accessible
   STATUS     mandatory
   DESCRIPTION
     "This group contains parameters in route request data that govern the 
      route selection. Values of these parameters are obtained either from 
      an operator or from the last route request message from a PORS VC 
      that contained such parameters or a reference to such parameters 
      (parameter profile reference) as part of the route request data. Route 
      request messages from a PORS VC that ask for a manual route do 
      not contain such parameters or reference to such parameters. All 
      other route request messages either explicitly contain route request 
      data parameters or a reference to a profile containing such 
      parameters.
      
      This group of attributes is therefore not applicable to manual routes."
::= { mscRtgRs 12 }

mscRtgRsPathAttributesEntry OBJECT-TYPE
   SYNTAX     MscRtgRsPathAttributesEntry
   ACCESS     not-accessible
   STATUS     mandatory
   DESCRIPTION
     "An entry in the mscRtgRsPathAttributesTable."
   INDEX {
      mscRtgIndex,
      mscRtgRsIndex }
::= { mscRtgRsPathAttributesTable 1 }

MscRtgRsPathAttributesEntry ::= SEQUENCE {
   mscRtgRsSourceId
      Unsigned32,
   mscRtgRsRemoteName
      AsciiString,
   mscRtgRsSetupPriority
      Unsigned32,
   mscRtgRsRequiredTxBandwidth
      Unsigned32,
   mscRtgRsRequiredRxBandwidth
      Unsigned32,
   mscRtgRsMaximumTransmissionUnit
      Unsigned32,
   mscRtgRsSecurity
      Unsigned32,
   mscRtgRsTrafficType
      INTEGER,
   mscRtgRsPermittedTrunkTypes
      OCTET STRING,
   mscRtgRsCustomerParameter
      Unsigned32,
   mscRtgRsPathAttributeToMinimize
      INTEGER,
   mscRtgRsMaximumAcceptableCost
      Unsigned32,
   mscRtgRsMaximumAcceptableDelay
      Unsigned32,
   mscRtgRsBumpPreference
      INTEGER,
   mscRtgRsRequiredTrunkModes
      INTEGER,
   mscRtgRsMaximumAcceptableGatewayCost
      Unsigned32,
   mscRtgRsRouteRequestor
      INTEGER,
   mscRtgRsGatewaySelectionAlg
      INTEGER,
   mscRtgRsDestination
      AsciiString }

mscRtgRsSourceId OBJECT-TYPE
   SYNTAX     Unsigned32 (1..16777215)
   ACCESS     read-write
   STATUS     mandatory
   DESCRIPTION
     "This attribute indicates the node ID of the source node from which a 
      route to the destination is to be found. It is typically the current 
      node. The term 'source' is used in relation to the route selection 
      process and not the node where RouteSelector resides, that is the 
      current node. That is, the source node need not be the current node 
      although the selected route will be based on the topological 
      database of the current node."
   DEFVAL     { 1 }
::= { mscRtgRsPathAttributesEntry 1 }

mscRtgRsRemoteName OBJECT-TYPE
   SYNTAX     AsciiString (SIZE (6..40))
   ACCESS     read-write
   STATUS     obsolete
   DESCRIPTION
     "This attribute is the remote end point's description. The term 
      'remote' means the other end point, usually distant from the source 
      node. End points are identified using a node name and a service 
      name. The syntax is 'EM/NodeName <service name>/<instance>'. 
      As an example, the end point component name for the third voice 
      service on node MoonBase is 'EM/MoonBase VS/3'."
::= { mscRtgRsPathAttributesEntry 2 }

mscRtgRsSetupPriority OBJECT-TYPE
   SYNTAX     Unsigned32 (0..4)
   ACCESS     read-write
   STATUS     mandatory
   DESCRIPTION
     "This attribute indicates the required priority for path establishment 
      along the selected. Zero is the highest priority and four is the 
      lowest. This attribute is closely related to bumpingPriority attribute."
   DEFVAL     { 2 }
::= { mscRtgRsPathAttributesEntry 3 }

mscRtgRsRequiredTxBandwidth OBJECT-TYPE
   SYNTAX     Unsigned32 (0..4294967295)
   ACCESS     read-write
   STATUS     mandatory
   DESCRIPTION
     "This attribute indicates the required transmit bandwidth in bits per 
      second to send data to the destination."
   DEFVAL     { 64000 }
::= { mscRtgRsPathAttributesEntry 4 }

mscRtgRsRequiredRxBandwidth OBJECT-TYPE
   SYNTAX     Unsigned32 (0..4294967295)
   ACCESS     read-write
   STATUS     mandatory
   DESCRIPTION
     "This attribute indicates the required receive bandwidth in bits per 
      second to receive data from the destination."
   DEFVAL     { 64000 }
::= { mscRtgRsPathAttributesEntry 5 }

mscRtgRsMaximumTransmissionUnit OBJECT-TYPE
   SYNTAX     Unsigned32 (0..8192)
   ACCESS     read-write
   STATUS     mandatory
   DESCRIPTION
     "This attribute indicates the size of the largest packet that can be 
      transported along the selected route. It is used by RouteSelector to 
      select a route which avoids trunks whose maximum transmission 
      unit is less than maximumTransmissionUnit and as a result would 
      be unable to transport packets of this size. The default value of 0 
      permits all trunks to be eligible with respect to this attribute."
   DEFVAL     { 0 }
::= { mscRtgRsPathAttributesEntry 6 }

mscRtgRsSecurity OBJECT-TYPE
   SYNTAX     Unsigned32 (0..7)
   ACCESS     read-write
   STATUS     mandatory
   DESCRIPTION
     "This attribute indicates the required minimum level of security of 
      the trunks along the selected route. Zero represents the most secure 
      and seven represents the least secure. The trunk's security is 
      indicated by the trunkSecurity attribute of the Trunk 
      PathAdministrator (Trk Pa) component. RouteSelector ensures that 
      any route selected does not contain a trunk whose trunkSecurity 
      attribute is numerically greater than the requiredSecurity."
   DEFVAL     { 4 }
::= { mscRtgRsPathAttributesEntry 7 }

mscRtgRsTrafficType OBJECT-TYPE
   SYNTAX     INTEGER  {
                 voice(0),
                 data(1),
                 video(2),
                 trafficType1(3),
                 trafficType2(4),
                 trafficType3(5),
                 trafficType4(6),
                 trafficType5(7) }
   ACCESS     read-write
   STATUS     mandatory
   DESCRIPTION
     "This attribute indicates the required type of traffic that can be 
      transported along the selected route. There are eight possible traffic 
      types, and only one type can be transported. The voice, data, and 
      video traffic types are already defined, and five other traffic types 
      can be defined by the network administrator. The 
      supportedTrafficType attribute of the Trunk PathAdministrator (Trk 
      Pa) component lists all the types of traffic allowed on the trunk. 
      When selecting a route, RouteSelector only chooses trunks whose 
      supportedTrafficType contains the requiredTrafficType."
   DEFVAL     { voice }
::= { mscRtgRsPathAttributesEntry 8 }

mscRtgRsPermittedTrunkTypes OBJECT-TYPE
   SYNTAX     OCTET STRING (SIZE (1))
   ACCESS     read-write
   STATUS     mandatory
   DESCRIPTION
     "This attribute indicates a maximum of eight types of trunks that can 
      be part of the selected route. The terrestrial and satellite trunk types 
      have been defined already, leaving six remaining types that can be 
      defined by the network administrator. The trunkType attribute of the 
      Trunk PathAdministrator (Trk Pa) component specifies the type of 
      the trunk. When selecting a route, RouteSelector only chooses 
      trunks whose trunkType is one of the permittedTrunkTypes.

      Description of bits:
      terrestrial(0)
      satellite(1)
      trunkType1(2)
      trunkType2(3)
      trunkType3(4)
      trunkType4(5)
      trunkType5(6)
      trunkType6(7)"
   DEFVAL     { 'f8'H }
::= { mscRtgRsPathAttributesEntry 9 }

mscRtgRsCustomerParameter OBJECT-TYPE
   SYNTAX     Unsigned32 (0..7)
   ACCESS     read-write
   STATUS     mandatory
   DESCRIPTION
     "This attribute indicates the mechanism to customize the usage of 
      trunks. Any trunk, whose customerParameter attribute under the 
      Trunk PathAdministrator (Trk Pa) component is larger than the 
      requiredCustomerParameter is not eligible to become part of the 
      selected route."
   DEFVAL     { 4 }
::= { mscRtgRsPathAttributesEntry 10 }

mscRtgRsPathAttributeToMinimize OBJECT-TYPE
   SYNTAX     INTEGER  {
                 cost(0),
                 delay(1) }
   ACCESS     read-write
   STATUS     mandatory
   DESCRIPTION
     "This attribute indicates whether a route should be selected on the 
      basis of minimizing the route cost or the route delay. Each trunk has 
      a cost and a delay metric associated with it. The cost of a route is 
      the sum of the trunk cost metrics for all trunks included in the route. 
      The delay of a route is the sum of the trunk delay metrics for all 
      trunks included in the route. The delay metric of a trunk is equal to 
      half the measuredRoundTripDelay operational attribute of the 
      trunk."
   DEFVAL     { cost }
::= { mscRtgRsPathAttributesEntry 11 }

mscRtgRsMaximumAcceptableCost OBJECT-TYPE
   SYNTAX     Unsigned32 (0..65535)
   ACCESS     read-write
   STATUS     mandatory
   DESCRIPTION
     "This attribute indicates the upper bound on the cost metric of the 
      selected route, which is the sum of the cost metrics of all trunks on 
      the route. RouteSelector ensures the cost metric of the selected route 
      does not exceed the maximumAcceptableCost."
   DEFVAL     { 1280 }
::= { mscRtgRsPathAttributesEntry 12 }

mscRtgRsMaximumAcceptableDelay OBJECT-TYPE
   SYNTAX     Unsigned32 (0..100000)
   ACCESS     read-write
   STATUS     mandatory
   DESCRIPTION
     "This attribute indicates the upper bound on the delay metric of the 
      selected route, which is the sum of the delay metrics of all trunks on 
      the route. RouteSelector ensures the delay metric of the selected 
      route does not exceed the maximumAcceptableDelay. The delay 
      metric of a trunk is equal to half the measuredRoundTripDelay 
      operational attribute of the trunk."
   DEFVAL     { 100000 }
::= { mscRtgRsPathAttributesEntry 13 }

mscRtgRsBumpPreference OBJECT-TYPE
   SYNTAX     INTEGER  {
                 bumpWhenNecessary(0),
                 bumpToObtainBestRoute(1) }
   ACCESS     read-write
   STATUS     mandatory
   DESCRIPTION
     "This attribute indicates whether bumping may be considered when 
      selecting a route. By default, bumping may be considered only 
      when it is necessary. That is, only when no other route to the 
      destination or gateway node can be found An indication to always 
      bump in order to find the best route may be set. In this case an 
      absolutely best route to the destination or gateway node is found 
      even if other paths along that route would need bumping."
   DEFVAL     { bumpWhenNecessary }
::= { mscRtgRsPathAttributesEntry 14 }

mscRtgRsRequiredTrunkModes OBJECT-TYPE
   SYNTAX     INTEGER  {
                 any(0),
                 mapping(1) }
   ACCESS     read-write
   STATUS     mandatory
   DESCRIPTION
     "This attribute indicates which trunk modes to consider during route 
      selection. The operational mode attribute of the Trunk 
      PathAdministrator (Trk Pa) component specifies the mode of the 
      trunk. When selecting a route, RouteSelector can either consider 
      trunks with any mode, or only trunks with mode set to mapping. 
      That is, the selected route may contain trunks with any mode, or all 
      trunks with mode set to mapping."
   DEFVAL     { any }
::= { mscRtgRsPathAttributesEntry 15 }

mscRtgRsMaximumAcceptableGatewayCost OBJECT-TYPE
   SYNTAX     Unsigned32 (0..65535)
   ACCESS     read-write
   STATUS     mandatory
   DESCRIPTION
     "This attribute indicates the upper bound on the cost metric 
      associated with reaching the destination along the selected route and 
      through a gateway node. Such cost metrics are provisioned under 
      Trunk Address component on a gateway node specifying costs of 
      reaching an address through the gateway node and more accurately 
      through the gateway link represented by the Trunk component."
   DEFVAL     { 2048 }
::= { mscRtgRsPathAttributesEntry 16 }

mscRtgRsRouteRequestor OBJECT-TYPE
   SYNTAX     INTEGER  {
                 applicationService(0),
                 inboundRGty(1),
                 outboundRGty(2) }
   ACCESS     read-write
   STATUS     mandatory
   DESCRIPTION
     "This attribute indicates the type of entity that makes a request for a 
      route (route requestor). Three types of entities can make route 
      requests: application service, Routing Gateway serving as inbound 
      gateway at a gateway node, or Routing Gateway serving as 
      outbound gateway at a gateway node."
   DEFVAL     { applicationService }
::= { mscRtgRsPathAttributesEntry 17 }

mscRtgRsGatewaySelectionAlg OBJECT-TYPE
   SYNTAX     INTEGER  {
                 costBased(1),
                 random(2),
                 legacy(4) }
   ACCESS     read-write
   STATUS     mandatory
   DESCRIPTION
     "This attribute indicates the type of algorithm to use when a route to 
      the destination has to be selected indirectly through a gateway node. 
      The following types of algorithms are available: cost based, 
      random, and legacy. 
      
      For cost based algorithm, RouteSelector selects gateway node that 
      advertised it can reach the destination at the smallest cost. 
      
      For random algorithm, RouteSelector selects randomly any gateway 
      node that advertised it can reach the destination.
      
      For legacy algorithm, RouteSelector selects a complete route to the 
      destination without attempting to route through gateway nodes. This 
      is only possible during single to multi topology region migration, or 
      cluster migration but before such migration is complete. During 
      such migrations routing to the destination is initially attempted 
      through gateway nodes, but if such routing fails then legacy routing 
      is attempted."
   DEFVAL     { costBased }
::= { mscRtgRsPathAttributesEntry 18 }

mscRtgRsDestination OBJECT-TYPE
   SYNTAX     AsciiString (SIZE (0..45))
   ACCESS     read-write
   STATUS     mandatory
   DESCRIPTION
     "This attribute indicates either the ASCII name, node ID, or NSAP 
      address of the destination node to which a route needs to be found. 
      The format for destination is either 
      1. 'EM/nodeName serviceName/instance', for ASCII name, for 
      example 'EM/MoonBase VS/3', or
      2. 'NID/nodeId', for node ID, for example 'NID/1226', or
      3. 'NSAP/nsapAddress', for NSAP address, for example 
      'NSAP/12234001'.
      
      For NSAP address formats a full ATM End System Address, node 
      summary, or reachable address can be specified, as well as a node 
      prefix."
::= { mscRtgRsPathAttributesEntry 20 }

mscRtgRsSrdTable OBJECT-TYPE
   SYNTAX     SEQUENCE OF MscRtgRsSrdEntry
   ACCESS     not-accessible
   STATUS     mandatory
   DESCRIPTION
     "This attribute indicates a vector of strings describing the selected or 
      manual route returned by RouteSelector. Each entry in the vector 
      describes one hop of the route. The hops are identified using a node 
      name and either 
      - a TRM allocated trunk identification or exit number (TRM uses a 
      component 'link', or 'Lk' in short form, to refer to trunks), or
      - a trunk name,
      which is local to that node. TRM allocated exit number is used for 
      routes selected by RouteSelector. Trunk name is used for manual 
      routes. 
      
      For example, a hop out of node StarBase using exit number 99 is 
      described as 'EM/STARBASE Trm Lk/99' for the selected route. A 
      hop out of node StarBase using trunk name 123 is described as 
      'EM/STARBASE TRK/123' for the manual route. A command 
      display Trm Lk/99 on node StarBase can be used to find out the 
      trunk name corresponding to exit number 99."
::= { mscRtgRs 224 }

mscRtgRsSrdEntry OBJECT-TYPE
   SYNTAX     MscRtgRsSrdEntry
   ACCESS     not-accessible
   STATUS     mandatory
   DESCRIPTION
     "An entry in the mscRtgRsSrdTable."
   INDEX {
      mscRtgIndex,
      mscRtgRsIndex,
      mscRtgRsSrdIndex }
::= { mscRtgRsSrdTable 1 }

MscRtgRsSrdEntry ::= SEQUENCE {
   mscRtgRsSrdIndex
      Integer32,
   mscRtgRsSrdValue
      AsciiString }

mscRtgRsSrdIndex OBJECT-TYPE
   SYNTAX     Integer32 (1..20)
   ACCESS     not-accessible
   STATUS     mandatory
   DESCRIPTION
     "This variable represents the mscRtgRsSrdTable
      specific index for the mscRtgRsSrdTable."
::= { mscRtgRsSrdEntry 1 }

mscRtgRsSrdValue OBJECT-TYPE
   SYNTAX     AsciiString (SIZE (0..40))
   ACCESS     read-only
   STATUS     mandatory
   DESCRIPTION
     "This variable represents an individual value for the
      mscRtgRsSrdTable."
::= { mscRtgRsSrdEntry 2 }

mscRtgRsRouteStatisticsTable OBJECT-TYPE
   SYNTAX     SEQUENCE OF MscRtgRsRouteStatisticsEntry
   ACCESS     not-accessible
   STATUS     mandatory
   DESCRIPTION
     "This attribute indicates a table (or an array) of the number of route 
      requests and the number of routes selected. There are six rows and 
      five columns in the table. The first row contains a number of route 
      requests in a column. Each column corresponds to a value of 
      setupPriority (= 0,1,2,3,4). An element in the first row gives a 
      number of route request per given setupPriority. The five 
      subsequent rows provide numbers of routes selected at 
      bumpingPriority 0,1,2,3,4. The second row provides numbers of 
      route selections at bumpingPriority 0. Only route requests of 
      setupPriority 0 could be given routes of the bumpingPriority 0. By 
      virtue of the property of bumpingPriority that it cannot be better 
      than the setupPriority the rows two to six form a lower triangular 
      matrix. Route selections performed upon operator request (manual 
      route requests) are not counted."
::= { mscRtgRs 225 }

mscRtgRsRouteStatisticsEntry OBJECT-TYPE
   SYNTAX     MscRtgRsRouteStatisticsEntry
   ACCESS     not-accessible
   STATUS     mandatory
   DESCRIPTION
     "An entry in the mscRtgRsRouteStatisticsTable."
   INDEX {
      mscRtgIndex,
      mscRtgRsIndex,
      mscRtgRsRouteStatisticsSetupPriorityIndex,
      mscRtgRsRouteStatisticsStatisticsTableIndex }
::= { mscRtgRsRouteStatisticsTable 1 }

MscRtgRsRouteStatisticsEntry ::= SEQUENCE {
   mscRtgRsRouteStatisticsSetupPriorityIndex
      INTEGER,
   mscRtgRsRouteStatisticsStatisticsTableIndex
      Integer32,
   mscRtgRsRouteStatisticsValue
      Unsigned32 }

mscRtgRsRouteStatisticsSetupPriorityIndex OBJECT-TYPE
   SYNTAX     INTEGER  {
                 routesRequested(0),
                 routesSelectedAtBp0(1),
                 routesSelectedAtBp1(2),
                 routesSelectedAtBp2(3),
                 routesSelectedAtBp3(4),
                 routesSelectedAtBp4(5) }
   ACCESS     not-accessible
   STATUS     mandatory
   DESCRIPTION
     "This variable represents the next to last index for the 
      mscRtgRsRouteStatisticsTable."
::= { mscRtgRsRouteStatisticsEntry 1 }

mscRtgRsRouteStatisticsStatisticsTableIndex OBJECT-TYPE
   SYNTAX     Integer32 (0..4)
   ACCESS     not-accessible
   STATUS     mandatory
   DESCRIPTION
     "This variable represents the final index for the 
      mscRtgRsRouteStatisticsTable."
::= { mscRtgRsRouteStatisticsEntry 2 }

mscRtgRsRouteStatisticsValue OBJECT-TYPE
   SYNTAX     Unsigned32 (0..4294967295)
   ACCESS     read-only
   STATUS     mandatory
   DESCRIPTION
     "This variable represents an individual value for the
      mscRtgRsRouteStatisticsTable."
::= { mscRtgRsRouteStatisticsEntry 3 }

mscRtgRsDgnTable OBJECT-TYPE
   SYNTAX     SEQUENCE OF MscRtgRsDgnEntry
   ACCESS     not-accessible
   STATUS     mandatory
   DESCRIPTION
     "This attribute indicates a set of node IDs of destination or gateway 
      nodes which directly or indirectly support the destination and to 
      which RouteSelector attempted to find a route. Node to which the 
      RouteSelector selected the route is also included in 
      destinationOrGatewayNodes."
::= { mscRtgRs 650 }

mscRtgRsDgnEntry OBJECT-TYPE
   SYNTAX     MscRtgRsDgnEntry
   ACCESS     not-accessible
   STATUS     mandatory
   DESCRIPTION
     "An entry in the mscRtgRsDgnTable."
   INDEX {
      mscRtgIndex,
      mscRtgRsIndex,
      mscRtgRsDgnValue }
::= { mscRtgRsDgnTable 1 }

MscRtgRsDgnEntry ::= SEQUENCE {
   mscRtgRsDgnValue
      Integer32 }

mscRtgRsDgnValue OBJECT-TYPE
   SYNTAX     Integer32 (0..4095)
   ACCESS     read-only
   STATUS     mandatory
   DESCRIPTION
     "This variable represents both the value and the index for the
      mscRtgRsDgnTable."
::= { mscRtgRsDgnEntry 1 }


-- This is the Routing PathOrientedRoutingSystem Component. It is 
-- used to display attributes of the PORS connections on a module and 
-- attributes for setting optimization timing for PORS connections. 
-- The PathOrientedRoutingSystem component also optimizes PORS 
-- connections on this module. 

mscRtgPors OBJECT IDENTIFIER ::= { mscRtg 6 }



mscRtgPorsRowStatusTable OBJECT-TYPE
   SYNTAX     SEQUENCE OF MscRtgPorsRowStatusEntry
   ACCESS     not-accessible
   STATUS     mandatory
   DESCRIPTION
     "This entry controls the addition and deletion of 
      mscRtgPors components."
::= { mscRtgPors 1 }

mscRtgPorsRowStatusEntry OBJECT-TYPE
   SYNTAX     MscRtgPorsRowStatusEntry
   ACCESS     not-accessible
   STATUS     mandatory
   DESCRIPTION
     "A single entry in the table represents a single 
      mscRtgPors component."
   INDEX {
      mscRtgIndex,
      mscRtgPorsIndex }
::= { mscRtgPorsRowStatusTable 1 }

MscRtgPorsRowStatusEntry ::= SEQUENCE {
   mscRtgPorsRowStatus
      RowStatus,
   mscRtgPorsComponentName
      DisplayString,
   mscRtgPorsStorageType
      StorageType,
   mscRtgPorsIndex
      NonReplicated }

mscRtgPorsRowStatus OBJECT-TYPE
   SYNTAX     RowStatus 
   ACCESS     read-write
   STATUS     mandatory
   DESCRIPTION
     "This variable is used as the basis for SNMP naming of
      mscRtgPors components.
      These components can be added and deleted."
::= { mscRtgPorsRowStatusEntry 1 }

mscRtgPorsComponentName OBJECT-TYPE
   SYNTAX     DisplayString 
   ACCESS     read-only
   STATUS     mandatory
   DESCRIPTION
     "This variable provides the component's string name for
      use with the ASCII Console Interface"
::= { mscRtgPorsRowStatusEntry 2 }

mscRtgPorsStorageType OBJECT-TYPE
   SYNTAX     StorageType 
   ACCESS     read-only
   STATUS     mandatory
   DESCRIPTION
     "This variable represents the storage type value for the
      mscRtgPors tables."
::= { mscRtgPorsRowStatusEntry 4 }

mscRtgPorsIndex OBJECT-TYPE
   SYNTAX     NonReplicated 
   ACCESS     not-accessible
   STATUS     mandatory
   DESCRIPTION
     "This variable represents the index for the mscRtgPors tables."
::= { mscRtgPorsRowStatusEntry 10 }

mscRtgPorsProvTable OBJECT-TYPE
   SYNTAX     SEQUENCE OF MscRtgPorsProvEntry
   ACCESS     not-accessible
   STATUS     mandatory
   DESCRIPTION
     "This group contains all provisionable attributes for the Routing 
      PathOrientedRoutingSystem component."
::= { mscRtgPors 10 }

mscRtgPorsProvEntry OBJECT-TYPE
   SYNTAX     MscRtgPorsProvEntry
   ACCESS     not-accessible
   STATUS     mandatory
   DESCRIPTION
     "An entry in the mscRtgPorsProvTable."
   INDEX {
      mscRtgIndex,
      mscRtgPorsIndex }
::= { mscRtgPorsProvTable 1 }

MscRtgPorsProvEntry ::= SEQUENCE {
   mscRtgPorsOptimizationInterval
      Unsigned32 }

mscRtgPorsOptimizationInterval OBJECT-TYPE
   SYNTAX     Unsigned32 (0 | 1..1440)
   ACCESS     read-write
   STATUS     mandatory
   DESCRIPTION
     "This attribute defines the interval at which the optimization process 
      will be triggered. The time is defined from the end of one 
      optimization pass until the start of another optimization pass.
      
      If an interval of zero is specified periodic optimization is disabled 
      on this module."
   DEFVAL     { 30 }
::= { mscRtgPorsProvEntry 1 }

mscRtgPorsInfoTable OBJECT-TYPE
   SYNTAX     SEQUENCE OF MscRtgPorsInfoEntry
   ACCESS     not-accessible
   STATUS     mandatory
   DESCRIPTION
     "This group contains operational information for the 
      PathOrientedRoutingSystem component."
::= { mscRtgPors 11 }

mscRtgPorsInfoEntry OBJECT-TYPE
   SYNTAX     MscRtgPorsInfoEntry
   ACCESS     not-accessible
   STATUS     mandatory
   DESCRIPTION
     "An entry in the mscRtgPorsInfoTable."
   INDEX {
      mscRtgIndex,
      mscRtgPorsIndex }
::= { mscRtgPorsInfoTable 1 }

MscRtgPorsInfoEntry ::= SEQUENCE {
   mscRtgPorsActiveConnections
      Unsigned32,
   mscRtgPorsOptimizationState
      INTEGER,
   mscRtgPorsLastOptimizationTime
      EnterpriseDateAndTime,
   mscRtgPorsNextOptimizationTime
      EnterpriseDateAndTime,
   mscRtgPorsOptimizationPasses
      Unsigned32,
   mscRtgPorsOptimizationProgress
      Unsigned32,
   mscRtgPorsPathsOptimized
      Unsigned32,
   mscRtgPorsTotalPathsOptimized
      Unsigned32 }

mscRtgPorsActiveConnections OBJECT-TYPE
   SYNTAX     Unsigned32 (0..65535)
   ACCESS     read-only
   STATUS     mandatory
   DESCRIPTION
     "This attribute is the current number of active PORS connections on 
      this module. Active connections are connections that are in the 
      Logical Connection component pathUp state.
      
      This value is updated when requested and represents the current 
      number of active PORS connections. During PORS optimization 
      this number represents all the connections that receive optimization 
      requests."
::= { mscRtgPorsInfoEntry 1 }

mscRtgPorsOptimizationState OBJECT-TYPE
   SYNTAX     INTEGER  {
                 disabled(0),
                 scheduled(1),
                 optimizing(2) }
   ACCESS     read-only
   STATUS     mandatory
   DESCRIPTION
     "This attribute is the current state of the PORS optimization. The 
      disabled state means that the optimizationInterval has been set to 
      zero. The scheduled state means that the optimization will be 
      started at the nextOptimizationTime. The optimizing state means 
      that PORS is currently attempting to optimize all connections on the 
      module."
::= { mscRtgPorsInfoEntry 2 }

mscRtgPorsLastOptimizationTime OBJECT-TYPE
   SYNTAX     EnterpriseDateAndTime (SIZE (0 | 19))
   ACCESS     read-only
   STATUS     mandatory
   DESCRIPTION
     "This attribute specifies the time that the last optimization started."
::= { mscRtgPorsInfoEntry 3 }

mscRtgPorsNextOptimizationTime OBJECT-TYPE
   SYNTAX     EnterpriseDateAndTime (SIZE (0 | 19))
   ACCESS     read-only
   STATUS     mandatory
   DESCRIPTION
     "This attribute specifies the time the next optimization process will 
      begin. 
      
      In the event that optimizationInterval is set to zero this value is also 
      set to 0."
::= { mscRtgPorsInfoEntry 4 }

mscRtgPorsOptimizationPasses OBJECT-TYPE
   SYNTAX     Unsigned32 (0..4294967295)
   ACCESS     read-only
   STATUS     mandatory
   DESCRIPTION
     "This is the number of optimization passes for the PORS connection 
      manager. An optimization pass consists of a notification to each 
      active PORS connection to attempt to optimize.
      All types of optimization passes are included in this statistic."
::= { mscRtgPorsInfoEntry 5 }

mscRtgPorsOptimizationProgress OBJECT-TYPE
   SYNTAX     Unsigned32 (0..100)
   ACCESS     read-only
   STATUS     mandatory
   DESCRIPTION
     "This attribute is the percentage of active connections that have been 
      sent an optimization request. A message is sent to each PORS 
      component LC requesting it to optimize its route.
      
      This value is cleared at the beginning of each optimization pass."
::= { mscRtgPorsInfoEntry 6 }

mscRtgPorsPathsOptimized OBJECT-TYPE
   SYNTAX     Unsigned32 (0..65535)
   ACCESS     read-only
   STATUS     mandatory
   DESCRIPTION
     "This attribute is the number of successfully optimized paths for the 
      latest optimization pass. Successfully optimized paths are paths that 
      switched to a better route.
      
      This value is cleared at the beginning of each optimization pass."
::= { mscRtgPorsInfoEntry 7 }

mscRtgPorsTotalPathsOptimized OBJECT-TYPE
   SYNTAX     Unsigned32 (0..4294967295)
   ACCESS     read-only
   STATUS     mandatory
   DESCRIPTION
     "This attribute is the number of successfully optimized paths on this 
      module since the CP became active."
::= { mscRtgPorsInfoEntry 8 }


-- Rtg Pors Prof/n
-- This component includes all attributes which may generically apply 
-- to a set of LogicalConnections. It is basically identical to the 
-- PermanentLogicalConnection except it does not include a 
-- remoteName or manualPath attribute. The specification of emission 
-- and discard priority is also a bit different in that they may be left 
-- unspecified in which case the emission and discard priority of the 
-- connection will be selected by the application.

mscRtgPorsProf OBJECT IDENTIFIER ::= { mscRtgPors 7 }



mscRtgPorsProfRowStatusTable OBJECT-TYPE
   SYNTAX     SEQUENCE OF MscRtgPorsProfRowStatusEntry
   ACCESS     not-accessible
   STATUS     mandatory
   DESCRIPTION
     "This entry controls the addition and deletion of 
      mscRtgPorsProf components."
::= { mscRtgPorsProf 1 }

mscRtgPorsProfRowStatusEntry OBJECT-TYPE
   SYNTAX     MscRtgPorsProfRowStatusEntry
   ACCESS     not-accessible
   STATUS     mandatory
   DESCRIPTION
     "A single entry in the table represents a single 
      mscRtgPorsProf component."
   INDEX {
      mscRtgIndex,
      mscRtgPorsIndex,
      mscRtgPorsProfIndex }
::= { mscRtgPorsProfRowStatusTable 1 }

MscRtgPorsProfRowStatusEntry ::= SEQUENCE {
   mscRtgPorsProfRowStatus
      RowStatus,
   mscRtgPorsProfComponentName
      DisplayString,
   mscRtgPorsProfStorageType
      StorageType,
   mscRtgPorsProfIndex
      Integer32 }

mscRtgPorsProfRowStatus OBJECT-TYPE
   SYNTAX     RowStatus 
   ACCESS     read-write
   STATUS     mandatory
   DESCRIPTION
     "This variable is used as the basis for SNMP naming of
      mscRtgPorsProf components.
      These components can be added and deleted."
::= { mscRtgPorsProfRowStatusEntry 1 }

mscRtgPorsProfComponentName OBJECT-TYPE
   SYNTAX     DisplayString 
   ACCESS     read-only
   STATUS     mandatory
   DESCRIPTION
     "This variable provides the component's string name for
      use with the ASCII Console Interface"
::= { mscRtgPorsProfRowStatusEntry 2 }

mscRtgPorsProfStorageType OBJECT-TYPE
   SYNTAX     StorageType 
   ACCESS     read-only
   STATUS     mandatory
   DESCRIPTION
     "This variable represents the storage type value for the
      mscRtgPorsProf tables."
::= { mscRtgPorsProfRowStatusEntry 4 }

mscRtgPorsProfIndex OBJECT-TYPE
   SYNTAX     Integer32 (1..255)
   ACCESS     not-accessible
   STATUS     mandatory
   DESCRIPTION
     "This variable represents the index for the mscRtgPorsProf tables."
::= { mscRtgPorsProfRowStatusEntry 10 }

mscRtgPorsProfProvTable OBJECT-TYPE
   SYNTAX     SEQUENCE OF MscRtgPorsProfProvEntry
   ACCESS     not-accessible
   STATUS     mandatory
   DESCRIPTION
     "This group contains all provisionable attributes for a PORS profile.."
::= { mscRtgPorsProf 11 }

mscRtgPorsProfProvEntry OBJECT-TYPE
   SYNTAX     MscRtgPorsProfProvEntry
   ACCESS     not-accessible
   STATUS     mandatory
   DESCRIPTION
     "An entry in the mscRtgPorsProfProvTable."
   INDEX {
      mscRtgIndex,
      mscRtgPorsIndex,
      mscRtgPorsProfIndex }
::= { mscRtgPorsProfProvTable 1 }

MscRtgPorsProfProvEntry ::= SEQUENCE {
   mscRtgPorsProfSetupPriority
      Unsigned32,
   mscRtgPorsProfHoldingPriority
      Unsigned32,
   mscRtgPorsProfRequiredTxBandwidth
      Unsigned32,
   mscRtgPorsProfRequiredRxBandwidth
      Unsigned32,
   mscRtgPorsProfRequiredTrafficType
      INTEGER,
   mscRtgPorsProfPermittedTrunkTypes
      OCTET STRING,
   mscRtgPorsProfRequiredSecurity
      Unsigned32,
   mscRtgPorsProfRequiredCustomerParm
      Unsigned32,
   mscRtgPorsProfPathAttributeToMinimize
      INTEGER,
   mscRtgPorsProfMaximumAcceptableCost
      Unsigned32,
   mscRtgPorsProfMaximumAcceptableDelay
      Unsigned32,
   mscRtgPorsProfEmissionPriority
      INTEGER,
   mscRtgPorsProfDiscardPriority
      INTEGER,
   mscRtgPorsProfPathFailureAction
      INTEGER,
   mscRtgPorsProfBumpPreference
      INTEGER,
   mscRtgPorsProfOptimization
      INTEGER }

mscRtgPorsProfSetupPriority OBJECT-TYPE
   SYNTAX     Unsigned32 (0..4)
   ACCESS     read-write
   STATUS     mandatory
   DESCRIPTION
     "This attribute specifies the priority at which a path is established. 
      Zero is the highest priority and four is the lowest. When PORS 
      establishes a path through the network, it uses the setupPriority 
      attribute to determine its potential for bumping established paths to 
      acquire their bandwidth. The holdingPriority, a complementary 
      attribute of this attribute, specifies the priority a path maintains once 
      it is established. A new path can bump an existing path if the new 
      path's setupPriority is higher (numerically less) than the existing 
      path's holdingPriority."
   DEFVAL     { 2 }
::= { mscRtgPorsProfProvEntry 3 }

mscRtgPorsProfHoldingPriority OBJECT-TYPE
   SYNTAX     Unsigned32 (0..4)
   ACCESS     read-write
   STATUS     mandatory
   DESCRIPTION
     "This attribute specifies the priority that a path holds once it is 
      established. Zero is the highest priority and four is the lowest. A 
      path's holdingPriority determines this path's likelihood of being 
      bumped by a new path to acquire its bandwidth. The setupPriority, a 
      complementary attribute, indicates the priority of a path at 
      establishment time. A new path can bump an existing path if the 
      new path's setupPriority is higher (numerically less) than the 
      existing path's holdingPriority."
   DEFVAL     { 2 }
::= { mscRtgPorsProfProvEntry 4 }

mscRtgPorsProfRequiredTxBandwidth OBJECT-TYPE
   SYNTAX     Unsigned32 (0..155520000)
   ACCESS     read-write
   STATUS     mandatory
   DESCRIPTION
     "This attribute specifies the bandwidth (in bits per second) reserved 
      by a path on each of the trunks of its route.This attribute represents 
      the bandwidth for traffic outgoing to the remote end point. This 
      value should be chosen to achieve the amount of statistical 
      bandwidth sharing that is desired by the network administration. 
      This reservation is not enforced but is used to determine how many 
      paths can be supported on a trunk. Both ends should be provisioned 
      with the correct values allowing for the fact that transmit at this end 
      represents receive at the remote end. Note that when the values do 
      not correspond, the originating end of the connection determines the 
      value. A value of 0 (the default) means that the bandwidth will be 
      the Peak Cell Rate for CLP0+1 as chosen by the user. A non zero 
      value overrides this reservation."
   DEFVAL     { 0 }
::= { mscRtgPorsProfProvEntry 5 }

mscRtgPorsProfRequiredRxBandwidth OBJECT-TYPE
   SYNTAX     Unsigned32 (0..155520000)
   ACCESS     read-write
   STATUS     mandatory
   DESCRIPTION
     "This attribute specifies the bandwidth (in bits per second) reserved 
      by a path on each of trunks of its route. This attribute represents the 
      bandwidth for traffic incoming from the remote end point. This 
      value should be chosen to achieve the amount of statistical 
      bandwidth sharing that is desired by the network administration. 
      This reservation is not enforced but is used to determine how many 
      paths can be supported on a trunk. Both ends should be provisioned 
      with the correct values allowing for the fact that transmit at this end 
      represents receive at the remote end. Note that when the values do 
      not correspond, the originating end of the connection determines the 
      value. A value of 0 (the default) means that the bandwidth will be 
      the Peak Cell Rate for CLP0+1 as chosen by the user. A non zero 
      value overrides this reservation."
   DEFVAL     { 0 }
::= { mscRtgPorsProfProvEntry 6 }

mscRtgPorsProfRequiredTrafficType OBJECT-TYPE
   SYNTAX     INTEGER  {
                 voice(0),
                 data(1),
                 video(2),
                 trafficType1(3),
                 trafficType2(4),
                 trafficType3(5),
                 trafficType4(6),
                 trafficType5(7) }
   ACCESS     read-write
   STATUS     mandatory
   DESCRIPTION
     "This attribute specifies the type of traffic transmitted over the path. 
      There are eight possible traffic types, and the path can transmit only 
      one of them. The originating end of the connection determines the 
      type. The voice, data and video traffic types are defined, and five 
      other arbitrary traffic types can be defined by the network 
      administration. This attribute is used in the route selection process 
      to restrict the route to trunks that support this traffic type. The 
      supportedTrafficType trunk attribute lists all the types of traffic 
      allowed on the trunk. For example, if requiredTrafficType is 
      specified as trafficType1, then only trunks that include trafficType1 
      in supportedTrafficType will be candidates for this connection."
   DEFVAL     { data }
::= { mscRtgPorsProfProvEntry 7 }

mscRtgPorsProfPermittedTrunkTypes OBJECT-TYPE
   SYNTAX     OCTET STRING (SIZE (1))
   ACCESS     read-write
   STATUS     mandatory
   DESCRIPTION
     "This attribute specifies up to eight types of trunk that can be used on 
      the route. The terrestrial and satellite trunk types have been 
      defined, leaving six remaining arbitrary types that can be defined by 
      the network administration. The trunk's type is indicated in the 
      trunkType attribute of the Trunk component. When selecting a 
      route, PORS only chooses trunks whose trunkType are in the 
      permittedTrunkTypes for the path.

      Description of bits:
      terrestrial(0)
      satellite(1)
      trunkType1(2)
      trunkType2(3)
      trunkType3(4)
      trunkType4(5)
      trunkType5(6)
      trunkType6(7)"
   DEFVAL     { 'f8'H }
::= { mscRtgPorsProfProvEntry 8 }

mscRtgPorsProfRequiredSecurity OBJECT-TYPE
   SYNTAX     Unsigned32 (0..7)
   ACCESS     read-write
   STATUS     mandatory
   DESCRIPTION
     "This attribute specifies the required minimum level of security of 
      the trunks on the route. A value of zero represents the most secure 
      while seven represents the least secure. The trunk's security is 
      indicated by the trunkSecurity attribute of the Trunk component, 
      and has values identical in range and meaning to the 
      requiredSecurity attribute. PORS ensures that any route selected 
      does not contain a trunk whose trunkSecurity attribute is 
      numerically greater than the requiredSecurity."
   DEFVAL     { 4 }
::= { mscRtgPorsProfProvEntry 9 }

mscRtgPorsProfRequiredCustomerParm OBJECT-TYPE
   SYNTAX     Unsigned32 (0..7)
   ACCESS     read-write
   STATUS     mandatory
   DESCRIPTION
     "This attribute specifies the allowed customer defined parameter of 
      the trunks on the route. Its value, a number from zero to seven, is 
      chosen by network administration to have a meaning specific to 
      their network, thus allowing them to customize the use of their 
      trunks. A complementary trunk attribute, customerParameter, also 
      has a value from zero to seven. The route selection process does not 
      consider trunks whose customerParameter is greater than the 
      requiredCustomerParameter of the path."
   DEFVAL     { 4 }
::= { mscRtgPorsProfProvEntry 10 }

mscRtgPorsProfPathAttributeToMinimize OBJECT-TYPE
   SYNTAX     INTEGER  {
                 cost(0),
                 delay(1) }
   ACCESS     read-write
   STATUS     mandatory
   DESCRIPTION
     "This attribute specifies whether a route is selected on the basis of 
      minimizing the cost or the delay. Each trunk has a cost and a delay 
      metric associated with it. The cost of a selected route is the sum of 
      the trunk cost metrics for all trunks included in the route. The delay 
      of a selected route is the sum of the trunk delay metric for all trunks 
      included in the route."
   DEFVAL     { cost }
::= { mscRtgPorsProfProvEntry 11 }

mscRtgPorsProfMaximumAcceptableCost OBJECT-TYPE
   SYNTAX     Unsigned32 (0..65535)
   ACCESS     read-write
   STATUS     mandatory
   DESCRIPTION
     "This attribute specifies an upper bound on the cost metric of a route, 
      which is the sum of the cost metrics of all trunks on the route. The 
      cost metric is the trunkCost attribute of the Trunk component. If for 
      any trunk the trunkCost is larger than the maximumAcceptableCost, 
      then that trunk is not considered during the route selection. While a 
      shortest route is being selected, the route cost is being compared 
      with the maximumAcceptableCost attribute, and this is done 
      regardless ofthe value of pathAttributeToMinimize. No route is 
      selected if the cost metric of the shortest route is larger than the 
      maximumAcceptableCost."
   DEFVAL     { 1280 }
::= { mscRtgPorsProfProvEntry 12 }

mscRtgPorsProfMaximumAcceptableDelay OBJECT-TYPE
   SYNTAX     Unsigned32 (0..100000)
   ACCESS     read-write
   STATUS     mandatory
   DESCRIPTION
     "This attribute specifies an upper bound on the delay of a route, 
      which is the sum of the delay of all trunks on the route. It should be 
      provisioned with a reasonable maximum acceptable delay for the 
      end to end one way delay of a 512 byte packet. Remember, that 
      during its staging, the trunk measures a measuredRoundTripDelay. 
      This delay is divided by two and truncated to an integer number of 
      milliseconds to provide a one way delay which is used to populate 
      the delay in this trunk object in the topological database. The value 
      includes emission, propagation, and queuing delays. A 512 byte 
      data packet is used to perform the measurement. 
      If for any trunk, half of the trunk's measuredRoundTripDelay is 
      larger than the maximumAcceptableDelay, then that trunk is not 
      considered during the route selection.
      While a shortest route is being selected, the route delay is being 
      compared with the maximumAcceptableDelay attribute, and this is 
      done for any minimization criterion. No route is selected if the 
      delay metric of the shortest route is larger than the 
      maximumAcceptableDelay."
   DEFVAL     { 100000 }
::= { mscRtgPorsProfProvEntry 13 }

mscRtgPorsProfEmissionPriority OBJECT-TYPE
   SYNTAX     INTEGER  {
                 ep0(0),
                 ep1(1),
                 ep2(2),
                 sameAsApplication(3) }
   ACCESS     read-write
   STATUS     mandatory
   DESCRIPTION
     "This attribute specifies the urgency with which packets on the path 
      are emitted by the trunks on the route. An EmissionPriority of zero 
      indicates the highest emission priority, while two indicates the 
      lowest emission priority. Packets with a higher emissionPriority (or 
      numerically less) are serviced and sent out before the packets of 
      lower emissionPriority (or numerically higher). The default value 
      for this attribute (sameAsApplication) will cause the connection's 
      emissionPriority to be inherited from the user of the profile. In other 
      words, setting this attribute to anything other than the default acts as 
      an override to the priority normally used by the application linked 
      to this profile."
   DEFVAL     { sameAsApplication }
::= { mscRtgPorsProfProvEntry 14 }

mscRtgPorsProfDiscardPriority OBJECT-TYPE
   SYNTAX     INTEGER  {
                 sameAsApplication(0),
                 dp1(1),
                 dp2(2),
                 dp3(3) }
   ACCESS     read-write
   STATUS     mandatory
   DESCRIPTION
     "This attribute specifies the importance of the packets on the path. 
      One is used for paths carrying the most important traffic, and three 
      is used for paths carrying the least important traffic. Packets with 
      lower discardPriority (numerically lower) are discarded after 
      packets with a higher discardPriority (numerically higher). The 
      default value for this attribute (sameAsApplication) will cause the 
      connection's discardPriority to be inherited from the user of the 
      profile. In other words, setting this attribute to anything other than 
      the default acts as an override to the priority normally used by the 
      application linked to this profile."
   DEFVAL     { sameAsApplication }
::= { mscRtgPorsProfProvEntry 15 }

mscRtgPorsProfPathFailureAction OBJECT-TYPE
   SYNTAX     INTEGER  {
                 disconnectConnection(0),
                 reRoutePath(1) }
   ACCESS     read-write
   STATUS     mandatory
   DESCRIPTION
     "This attribute specifies whether the application can tolerate 
      momentary interruption of a path while a new path is selected. If 
      disconnectConnection is chosen, the application is informed as 
      soon as possible about a failure by disconnection. If the attribute is 
      set to reRoutePath, the path may attempt an immediate reroute, 
      provided the failure is a recoverable failure. If rerouting fails the 
      application is informed of the failure. 
      With this option set to reRoutePath the LCo may wait up to 30 
      seconds before informing the service of complete disconnection in 
      order to allow both ends to attempt to reconnect. Note that if PLC 
      components are different at both ends only the calling end is 
      allowed to reconnect."
   DEFVAL     { reRoutePath }
::= { mscRtgPorsProfProvEntry 17 }

mscRtgPorsProfBumpPreference OBJECT-TYPE
   SYNTAX     INTEGER  {
                 bumpWhenNecessary(0),
                 bumpToObtainBestRoute(1) }
   ACCESS     read-write
   STATUS     mandatory
   DESCRIPTION
     "This attribute specifies when bumping may be triggered as a result 
      of this call being routed/rerouted or optimized. There are two 
      possibilities:
      bumpWhenNecessary: means that this call will only trigger the 
      bumping of another call (subject to setup/holding priority 
      restrictions) when there is no other way to establish a route for this 
      call.
      bumpToObtainBestRoute: means that this call may trigger the 
      bumping of other calls (subject to setup/holding priority 
      restrictions) if doing so would result in this call obtaining a better 
      (lower cost/delay) route.
      Since bumping to obtain the best route can be somewhat intrusive 
      the default is only to bump when there is no other way to route the 
      call."
   DEFVAL     { bumpWhenNecessary }
::= { mscRtgPorsProfProvEntry 18 }

mscRtgPorsProfOptimization OBJECT-TYPE
   SYNTAX     INTEGER  {
                 disabled(0),
                 enabled(1) }
   ACCESS     read-write
   STATUS     mandatory
   DESCRIPTION
     "If this attribute is enabled, this connection will be optimized 
      periodically as specified by the Rtg Pors attribute 
      optimizationInterval. If this attribute is disabled, the connection will 
      use the route it was given for the life of the connection or until a 
      failure or lock results in the call being rerouted."
   DEFVAL     { enabled }
::= { mscRtgPorsProfProvEntry 19 }

mscRtgPorsProfUsrTable OBJECT-TYPE
   SYNTAX     SEQUENCE OF MscRtgPorsProfUsrEntry
   ACCESS     not-accessible
   STATUS     mandatory
   DESCRIPTION
     "This attribute specifies all of the components which are associated 
      with this Profile. Users of this profile will select and instantiate 
      routes based on the attributes of this profile when PORS is used to 
      choose and instantiate the route. If IISP or PNNI are used to choose 
      and instantiate the route these attributes are ignored since they have 
      no counterparts in IISP or PNNI routing."
::= { mscRtgPorsProf 400 }

mscRtgPorsProfUsrEntry OBJECT-TYPE
   SYNTAX     MscRtgPorsProfUsrEntry
   ACCESS     not-accessible
   STATUS     mandatory
   DESCRIPTION
     "An entry in the mscRtgPorsProfUsrTable."
   INDEX {
      mscRtgIndex,
      mscRtgPorsIndex,
      mscRtgPorsProfIndex,
      mscRtgPorsProfUsrValue }
::= { mscRtgPorsProfUsrTable 1 }

MscRtgPorsProfUsrEntry ::= SEQUENCE {
   mscRtgPorsProfUsrValue
      Link }

mscRtgPorsProfUsrValue OBJECT-TYPE
   SYNTAX     Link 
   ACCESS     read-only
   STATUS     mandatory
   DESCRIPTION
     "This variable represents both the value and the index for the
      mscRtgPorsProfUsrTable."
::= { mscRtgPorsProfUsrEntry 1 }


-- Rtg Pors ManualPath/n
-- This component specifies the sequence of Trunks used by a service 
-- as the route between source and destination nodes. Services with a 
-- link to this component bypass PORS automatic route selection in 
-- favor of the route specified in the route attribute. This component, 
-- along with the Rtg Pors Profile/n component and the signaled 
-- called party NSAP address, determine the end to end path. An 
-- instance of this component should be provisioned for every unique 
-- list of Trunks used as a route by a service bypassing PORS 
-- automatic routing.

mscRtgPorsMpath OBJECT IDENTIFIER ::= { mscRtgPors 8 }



mscRtgPorsMpathRowStatusTable OBJECT-TYPE
   SYNTAX     SEQUENCE OF MscRtgPorsMpathRowStatusEntry
   ACCESS     not-accessible
   STATUS     mandatory
   DESCRIPTION
     "This entry controls the addition and deletion of 
      mscRtgPorsMpath components."
::= { mscRtgPorsMpath 1 }

mscRtgPorsMpathRowStatusEntry OBJECT-TYPE
   SYNTAX     MscRtgPorsMpathRowStatusEntry
   ACCESS     not-accessible
   STATUS     mandatory
   DESCRIPTION
     "A single entry in the table represents a single 
      mscRtgPorsMpath component."
   INDEX {
      mscRtgIndex,
      mscRtgPorsIndex,
      mscRtgPorsMpathIndex }
::= { mscRtgPorsMpathRowStatusTable 1 }

MscRtgPorsMpathRowStatusEntry ::= SEQUENCE {
   mscRtgPorsMpathRowStatus
      RowStatus,
   mscRtgPorsMpathComponentName
      DisplayString,
   mscRtgPorsMpathStorageType
      StorageType,
   mscRtgPorsMpathIndex
      Integer32 }

mscRtgPorsMpathRowStatus OBJECT-TYPE
   SYNTAX     RowStatus 
   ACCESS     read-write
   STATUS     mandatory
   DESCRIPTION
     "This variable is used as the basis for SNMP naming of
      mscRtgPorsMpath components.
      These components can be added and deleted."
::= { mscRtgPorsMpathRowStatusEntry 1 }

mscRtgPorsMpathComponentName OBJECT-TYPE
   SYNTAX     DisplayString 
   ACCESS     read-only
   STATUS     mandatory
   DESCRIPTION
     "This variable provides the component's string name for
      use with the ASCII Console Interface"
::= { mscRtgPorsMpathRowStatusEntry 2 }

mscRtgPorsMpathStorageType OBJECT-TYPE
   SYNTAX     StorageType 
   ACCESS     read-only
   STATUS     mandatory
   DESCRIPTION
     "This variable represents the storage type value for the
      mscRtgPorsMpath tables."
::= { mscRtgPorsMpathRowStatusEntry 4 }

mscRtgPorsMpathIndex OBJECT-TYPE
   SYNTAX     Integer32 (1..255)
   ACCESS     not-accessible
   STATUS     mandatory
   DESCRIPTION
     "This variable represents the index for the mscRtgPorsMpath tables."
::= { mscRtgPorsMpathRowStatusEntry 10 }

mscRtgPorsMpathOperTable OBJECT-TYPE
   SYNTAX     SEQUENCE OF MscRtgPorsMpathOperEntry
   ACCESS     not-accessible
   STATUS     mandatory
   DESCRIPTION
     "This group contains operational information for the Rtg Pors 
      ManualPath/n component."
::= { mscRtgPorsMpath 12 }

mscRtgPorsMpathOperEntry OBJECT-TYPE
   SYNTAX     MscRtgPorsMpathOperEntry
   ACCESS     not-accessible
   STATUS     mandatory
   DESCRIPTION
     "An entry in the mscRtgPorsMpathOperTable."
   INDEX {
      mscRtgIndex,
      mscRtgPorsIndex,
      mscRtgPorsMpathIndex }
::= { mscRtgPorsMpathOperTable 1 }

MscRtgPorsMpathOperEntry ::= SEQUENCE {
   mscRtgPorsMpathLastSetupFailureReason
      INTEGER,
   mscRtgPorsMpathLastSetupFailurePoint
      AsciiString,
   mscRtgPorsMpathLastSetupFailedUser
      RowPointer }

mscRtgPorsMpathLastSetupFailureReason OBJECT-TYPE
   SYNTAX     INTEGER  {
                 none(0),
                 insufficientTxLcOrBandwidth(2),
                 insufficientRxLcOrBandwidth(3),
                 trunkFailure(4),
                 trunkCardFailure(5),
                 operatorForced(6),
                 lostLcnClash(7),
                 networkCongestion(8),
                 trunkNotFound(9),
                 farEndNotFound(10),
                 farEndBusy(12),
                 unknownReason(14),
                 farEndNotReady(15),
                 serviceTypeMismatch(17),
                 bumped(19),
                 accessCardFailure(20),
                 trunkOrFarEndDidNotSupportMode(23) }
   ACCESS     read-only
   STATUS     mandatory
   DESCRIPTION
     "This attribute indicates the reason for the most recent failure for an 
      attempted connection using this ManualPath's route. The following 
      is a brief description of the reasons:
      none - This path has no information for the teardown.
      insufficientTxLcOrBandwidth - At present there is either no 
      available bandwidth or logical channel numbers available on one or 
      more of the Trunks for this path in the transmit direction. If a trunk 
      in the route attribute was previously locked, or has a Trk PA 
      subcomponent that is not in the up state , that Trunk is considered 
      as having no available bandwidth. If the Trunk PA is in mapped 
      mode, the inability to allocate an Atmif Vcc also results in this 
      failure reason. 
      insufficientRxLcOrBandwidth - At present there is either no 
      available bandwidth or logical channel numbers available on one or 
      more of the Trunks for this path in the receive direction. If a trunk 
      in the route attribute was previously locked, or has a Trk PA 
      subcomponent that is not in the up state , that Trunk is considered 
      as having no available bandwidth.
      trunkFailure- A Trunk on the path has failed or has gone down, 
      due to a provisioning change of a critical attribute, as the path was 
      being established.
      trunkCardFailure- A Trunk FP card has failed along the path as the 
      path was being established.
      accessCardFailure- The FP on which the peer access service was 
      running has failed as the path was being established.
      operatorForced- The path has terminated due to the operator 
      locking a Trunk along the path as the path was being established.
      lostLcnClash- The path has terminated because the Trk PA's at both 
      ends of an intermediate trunk have allocated the same Trk LC to 
      different calls. When this happens both calls must go down and then 
      try to come up again a fraction of a second later (effectively 
      ensuring that they will now be assigned different Trk LC's). It is 
      normal to get the odd clash especially when the Trk PA usedLC is 
      approaching the Trk PA maxLC. An LCN clash results in the path 
      failing to instantiate only if the application disabled rerouting. By 
      default rerouting is enabled for all applications. Applications can 
      disable rerouting by using a Rtg Pors Prof/n component with 
      pathFailureAction set to disconnectConnection.
      networkCongestion - The path has failed to establish due to control 
      information being lost and not being recoverable.
      trunkNotFound - Check for Trunks not up or names provisioned 
      incorrectly in route attribute . 
      farEndNotFound - The far end is not provisioned or is not up. The 
      called NSAP address cannot be reached through the last node in the 
      Rtg Pors ManualPath path.
      farEndBusy - The far end has been reached but it is busy. Check 
      remote end provisioning.
      unknownReason - The failure was not resolved.
      farEndNotReady - The remote end was reached but the connection 
      was refused due to the remote end not being enabled.
      serviceTypeMismatch - The remote service type does not match 
      this service type. Check provisioning.
      bumped - Another call bumped this path, as it was being 
      established, from a trunk to get bandwidth (or an LC) which it 
      required to come up. This other path had a higher setupPriority than 
      this path's holdingPriority hence it was allowed to steal the 
      bandwidth (or LC) from this path. A manual path that is bumped 
      fails to instantiate if it cannot bump another path along the same 
      route, or if it has pathFailureAction set to disconnectConnection.
      trunkOrFarEndDidNotSupportMode - This call was unable to 
      complete because a mode required by the service was not supported 
      by one of the Trunks the route went through or by the far end 
      service it connected to. Currently the only mode that this applies to 
      is the map/mux mode on Trk Pa Atm component."
   DEFVAL     { none }
::= { mscRtgPorsMpathOperEntry 1 }

mscRtgPorsMpathLastSetupFailurePoint OBJECT-TYPE
   SYNTAX     AsciiString (SIZE (0..40))
   ACCESS     read-only
   STATUS     mandatory
   DESCRIPTION
     "This attribute indicates the point in the route at which the path 
      failed to establish. A failure at either end of a trunk will result in the 
      display of the name of the trunk nearer the calling end."
::= { mscRtgPorsMpathOperEntry 2 }

mscRtgPorsMpathLastSetupFailedUser OBJECT-TYPE
   SYNTAX     RowPointer 
   ACCESS     read-only
   STATUS     mandatory
   DESCRIPTION
     "This attribute indicates the component in the users attribute that last 
      failed to instantiate a path based on the route."
::= { mscRtgPorsMpathOperEntry 3 }

mscRtgPorsMpathRouteTable OBJECT-TYPE
   SYNTAX     SEQUENCE OF MscRtgPorsMpathRouteEntry
   ACCESS     not-accessible
   STATUS     mandatory
   DESCRIPTION
     "This attribute specifies the sequence of trunks used as the route for a 
      path. If any trunk in the sequence does not meet the requirements 
      (bandwidth, permittedTrunkType, security, customerParm, etc.) for 
      a component listed in users, path validation fails and no path is 
      instantiated for that user.
      Changing this attribute will cause active connections of users of this 
      ManualPath to move to the new route only if the users have 
      optimization enabled and Rtg Pors optimizationInterval > 0. 
      Otherwise, changing this attribute will cause the users' current 
      connections to stay on the old route with all new calls instantiating 
      their paths with the new route. Optimization can be disabled by 
      having the application use a Rtg Pors Prof/n component with 
      optimization disabled or by setting Rtg Pors optimizationInterval 0.
      As an example, the trunk component name for the trunk instance 10 
      on node MoonBase is EM/MoonBase Trk/10. These strings are case 
      insensitive but the complete component name must be input.
      Note 1: the trunk designation must be in the 3-letter form 'trk'.
      Note 2: only the outbound trunk component names are used to 
      provision the route."
::= { mscRtgPorsMpath 408 }

mscRtgPorsMpathRouteEntry OBJECT-TYPE
   SYNTAX     MscRtgPorsMpathRouteEntry
   ACCESS     not-accessible
   STATUS     mandatory
   DESCRIPTION
     "An entry in the mscRtgPorsMpathRouteTable."
   INDEX {
      mscRtgIndex,
      mscRtgPorsIndex,
      mscRtgPorsMpathIndex,
      mscRtgPorsMpathRouteIndex }
::= { mscRtgPorsMpathRouteTable 1 }

MscRtgPorsMpathRouteEntry ::= SEQUENCE {
   mscRtgPorsMpathRouteIndex
      Integer32,
   mscRtgPorsMpathRouteValue
      AsciiString }

mscRtgPorsMpathRouteIndex OBJECT-TYPE
   SYNTAX     Integer32 (0..19)
   ACCESS     not-accessible
   STATUS     mandatory
   DESCRIPTION
     "This variable represents the mscRtgPorsMpathRouteTable
      specific index for the mscRtgPorsMpathRouteTable."
::= { mscRtgPorsMpathRouteEntry 1 }

mscRtgPorsMpathRouteValue OBJECT-TYPE
   SYNTAX     AsciiString (SIZE (0..40))
   ACCESS     read-write
   STATUS     mandatory
   DESCRIPTION
     "This variable represents an individual value for the
      mscRtgPorsMpathRouteTable."
::= { mscRtgPorsMpathRouteEntry 2 }

mscRtgPorsMpathUsrTable OBJECT-TYPE
   SYNTAX     SEQUENCE OF MscRtgPorsMpathUsrEntry
   ACCESS     not-accessible
   STATUS     mandatory
   DESCRIPTION
     "This attribute specifies all of the components that will use this 
      ManualPath to instantiate a path. Users of this component have 
      paths that follow the sequence of Trunks specified in the route 
      attribute of this component when PORS is used to choose and 
      instantiate the route."
::= { mscRtgPorsMpath 409 }

mscRtgPorsMpathUsrEntry OBJECT-TYPE
   SYNTAX     MscRtgPorsMpathUsrEntry
   ACCESS     not-accessible
   STATUS     mandatory
   DESCRIPTION
     "An entry in the mscRtgPorsMpathUsrTable."
   INDEX {
      mscRtgIndex,
      mscRtgPorsIndex,
      mscRtgPorsMpathIndex,
      mscRtgPorsMpathUsrValue }
::= { mscRtgPorsMpathUsrTable 1 }

MscRtgPorsMpathUsrEntry ::= SEQUENCE {
   mscRtgPorsMpathUsrValue
      Link }

mscRtgPorsMpathUsrValue OBJECT-TYPE
   SYNTAX     Link 
   ACCESS     read-only
   STATUS     mandatory
   DESCRIPTION
     "This variable represents both the value and the index for the
      mscRtgPorsMpathUsrTable."
::= { mscRtgPorsMpathUsrEntry 1 }




-- 
-- Version and Compliance statements
-- 



-- Object-Group Statement:
-- A list of all current accessible leaf objects.

-- OBJECTS { mscRtgRsAttributeNotMet,
--           mscRtgPorsProfEmissionPriority,
--           mscRtgRsComponentName,
--           mscRtgPorsProfSetupPriority,
--           mscRtgRsCustomerParameter,
--           mscRtgPorsProfRequiredRxBandwidth,
--           mscRtgRsLastRouteSelectionTime,
--           mscRtgPorsProfOptimization,
--           mscRtgPorsOptimizationState,
--           mscRtgPorsStorageType,
--           mscRtgRsReasonForNoRoute,
--           mscRtgPorsMpathRouteValue,
--           mscRtgPorsPathsOptimized,
--           mscRtgRsRouteGatewayCostMetric,
--           mscRtgPorsProfUsrValue,
--           mscRtgPorsProfRowStatus,
--           mscRtgRsRouteStatisticsValue,
--           mscRtgPorsMpathLastSetupFailurePoint,
--           mscRtgPorsMpathRowStatus,
--           mscRtgPorsOptimizationInterval,
--           mscRtgPorsMpathUsrValue,
--           mscRtgRsPathAttributeToMinimize,
--           mscRtgRsMaximumAcceptableGatewayCost,
--           mscRtgPorsMpathStorageType,
--           mscRtgPorsRowStatus,
--           mscRtgPorsProfComponentName,
--           mscRtgRsRouteRequestor,
--           mscRtgRsMaximumTransmissionUnit,
--           mscRtgRsRequiredTrunkModes,
--           mscRtgRsTrafficType,
--           mscRtgPorsProfDiscardPriority,
--           mscRtgPorsProfRequiredCustomerParm,
--           mscRtgRsSrdValue,
--           mscRtgPorsOptimizationPasses,
--           mscRtgPorsProfBumpPreference,
--           mscRtgPorsLastOptimizationTime,
--           mscRtgPorsComponentName,
--           mscRtgPorsTotalPathsOptimized,
--           mscRtgPorsActiveConnections,
--           mscRtgRsRequiredTxBandwidth,
--           mscRtgRsMaximumAcceptableDelay,
--           mscRtgRsMaximumAcceptableCost,
--           mscRtgRsPermittedTrunkTypes,
--           mscRtgPorsProfRequiredSecurity,
--           mscRtgRsBumpingPriority,
--           mscRtgRsSourceId,
--           mscRtgPorsProfRequiredTrafficType,
--           mscRtgRsStorageType,
--           mscRtgPorsProfPathAttributeToMinimize,
--           mscRtgRsOperationMode,
--           mscRtgRsRouteType,
--           mscRtgRsSetupPriority,
--           mscRtgPorsProfRequiredTxBandwidth,
--           mscRtgPorsProfPathFailureAction,
--           mscRtgPorsMpathLastSetupFailureReason,
--           mscRtgRsBumpPreference,
--           mscRtgRsSecurity,
--           mscRtgPorsProfHoldingPriority,
--           mscRtgRsDestination,
--           mscRtgPorsProfMaximumAcceptableDelay,
--           mscRtgRsGatewaySelectionAlg,
--           mscRtgPorsProfMaximumAcceptableCost,
--           mscRtgRsDgnValue,
--           mscRtgPorsOptimizationProgress,
--           mscRtgRsRequiredRxBandwidth,
--           mscRtgPorsNextOptimizationTime,
--           mscRtgRsRouteCostMetric,
--           mscRtgPorsMpathComponentName,
--           mscRtgPorsProfStorageType,
--           mscRtgPorsProfPermittedTrunkTypes,
--           mscRtgRsRowStatus,
--           mscRtgRsRouteDelayMetric,
--           mscRtgPorsMpathLastSetupFailedUser }
-- STATUS  mandatory
-- DESCRIPTION
--   "A list of all current accessible leaf objects."

porsVcGroup OBJECT IDENTIFIER ::= { porsVcMIB 1 }
porsVcGroupCA OBJECT IDENTIFIER ::= { porsVcGroup 1 }
porsVcGroupCA02 OBJECT IDENTIFIER ::= { porsVcGroupCA 3 }
porsVcGroupCA02A OBJECT IDENTIFIER ::= { porsVcGroupCA02 2 }



-- Agent-Capabilities Statement:

-- PRODUCT-RELEASE "MscPassport Release 1.2 PorsVc."
-- STATUS          mandatory
-- DESCRIPTION     "Carrier Passport PorsVc MIB: MIB Version CA02A,
--                  Software Version CA02S9C."
-- SUPPORTS        Nortel-MsCarrier-MscPassport-PorsVcMIB
--    INCLUDES     { porsVcGroupCA02A }

porsVcCapabilities OBJECT IDENTIFIER ::= { porsVcMIB 3 }
porsVcCapabilitiesCA OBJECT IDENTIFIER ::= { porsVcCapabilities 1 }
porsVcCapabilitiesCA02 OBJECT IDENTIFIER ::= { porsVcCapabilitiesCA 3 }
porsVcCapabilitiesCA02A OBJECT IDENTIFIER ::= { porsVcCapabilitiesCA02 2 }





END
