Nortel-MsCarrier-MscPassport-LogicalProcessorMIB
DEFINITIONS ::= BEGIN



IMPORTS

      OBJECT-TYPE
   FROM RFC-1212

      mscPassportMIBs,
      mscComponents
   FROM Nortel-MsCarrier-MscPassport-UsefulDefinitionsMIB

      Counter32,
      RowPointer,
      DisplayString,
      StorageType,
      RowStatus,
      InterfaceIndex,
      Gauge32,
      Integer32,
      Unsigned32
   FROM Nortel-MsCarrier-MscPassport-StandardTextualConventionsMIB

      AsciiString,
      Hex,
      NonReplicated,
      EnterpriseDateAndTime,
      PassportCounter64,
      Link
   FROM Nortel-MsCarrier-MscPassport-TextualConventionsMIB;




-- LAST-UPDATED   "9909010000Z"
-- ORGANIZATION   "Nortel Networks"
-- CONTACT-INFO   "
--         Nortel Carrier Data Network Management
--         
--         Postal:       P.O. Box 3511, Station C 
--                       Ottawa, Ontario 
--                       Canada  K1Y 4H7
--         
--         via the WEB:  http://www.nortelnetworks.com  
--                       select 'Contact Us' from the menu
--          
--         via phone:    1-800-4NORTEL"
-- DESCRIPTION
--    "The module describing the Nortel MsCarrier MscPassport
--     LogicalProcessor Enterprise MIB."

logicalProcessorMIB OBJECT IDENTIFIER ::= { mscPassportMIBs 11 }










-- LogicalProcessor/n
-- The LogicalProcessor (Lp) component is a root component. One Lp 
-- component is created for each Logical Processor. An Lp may be 
-- configured to run on up to two cards; one as the main card, and the 
-- other as the spare card. When two cards are configured, the Lp runs 
-- on one card, and waits for that card to fail before starting to run on 
-- the other card.

mscLp OBJECT IDENTIFIER ::= { mscComponents 12 }



mscLpRowStatusTable OBJECT-TYPE
   SYNTAX     SEQUENCE OF MscLpRowStatusEntry
   ACCESS     not-accessible
   STATUS     mandatory
   DESCRIPTION
     "This entry controls the addition and deletion of 
      mscLp components."
::= { mscLp 1 }

mscLpRowStatusEntry OBJECT-TYPE
   SYNTAX     MscLpRowStatusEntry
   ACCESS     not-accessible
   STATUS     mandatory
   DESCRIPTION
     "A single entry in the table represents a single 
      mscLp component."
   INDEX {
      mscLpIndex }
::= { mscLpRowStatusTable 1 }

MscLpRowStatusEntry ::= SEQUENCE {
   mscLpRowStatus
      RowStatus,
   mscLpComponentName
      DisplayString,
   mscLpStorageType
      StorageType,
   mscLpIndex
      Integer32 }

mscLpRowStatus OBJECT-TYPE
   SYNTAX     RowStatus 
   ACCESS     read-write
   STATUS     mandatory
   DESCRIPTION
     "This variable is used as the basis for SNMP naming of
      mscLp components.
      These components can be added and deleted."
::= { mscLpRowStatusEntry 1 }

mscLpComponentName OBJECT-TYPE
   SYNTAX     DisplayString 
   ACCESS     read-only
   STATUS     mandatory
   DESCRIPTION
     "This variable provides the component's string name for
      use with the ASCII Console Interface"
::= { mscLpRowStatusEntry 2 }

mscLpStorageType OBJECT-TYPE
   SYNTAX     StorageType 
   ACCESS     read-only
   STATUS     mandatory
   DESCRIPTION
     "This variable represents the storage type value for the
      mscLp tables."
::= { mscLpRowStatusEntry 4 }

mscLpIndex OBJECT-TYPE
   SYNTAX     Integer32 (0..15)
   ACCESS     not-accessible
   STATUS     mandatory
   DESCRIPTION
     "This variable represents the index for the mscLp tables."
::= { mscLpRowStatusEntry 10 }

mscLpProvTable OBJECT-TYPE
   SYNTAX     SEQUENCE OF MscLpProvEntry
   ACCESS     not-accessible
   STATUS     mandatory
   DESCRIPTION
     "This Group contains the provisionable attributes for the LP 
      component."
::= { mscLp 100 }

mscLpProvEntry OBJECT-TYPE
   SYNTAX     MscLpProvEntry
   ACCESS     not-accessible
   STATUS     mandatory
   DESCRIPTION
     "An entry in the mscLpProvTable."
   INDEX {
      mscLpIndex }
::= { mscLpProvTable 1 }

MscLpProvEntry ::= SEQUENCE {
   mscLpMainCard
      Link,
   mscLpSpareCard
      Link,
   mscLpLogicalProcessorType
      Link }

mscLpMainCard OBJECT-TYPE
   SYNTAX     Link 
   ACCESS     read-write
   STATUS     mandatory
   DESCRIPTION
     "This is the preferred processor card on which this LP should be 
      assigned."
::= { mscLpProvEntry 1 }

mscLpSpareCard OBJECT-TYPE
   SYNTAX     Link 
   ACCESS     read-write
   STATUS     mandatory
   DESCRIPTION
     "This is the spare processor card on which this LP should be 
      assigned."
::= { mscLpProvEntry 2 }

mscLpLogicalProcessorType OBJECT-TYPE
   SYNTAX     Link 
   ACCESS     read-write
   STATUS     mandatory
   DESCRIPTION
     "This is the Logical Processor Type (LPT) that determines which 
      software this LP will run."
::= { mscLpProvEntry 3 }

mscLpCidDataTable OBJECT-TYPE
   SYNTAX     SEQUENCE OF MscLpCidDataEntry
   ACCESS     not-accessible
   STATUS     mandatory
   DESCRIPTION
     "This group contains the attribute for a component's Customer 
      Identifier (CID). Refer to the attribute description for a detailed 
      explanation of CIDs."
::= { mscLp 101 }

mscLpCidDataEntry OBJECT-TYPE
   SYNTAX     MscLpCidDataEntry
   ACCESS     not-accessible
   STATUS     mandatory
   DESCRIPTION
     "An entry in the mscLpCidDataTable."
   INDEX {
      mscLpIndex }
::= { mscLpCidDataTable 1 }

MscLpCidDataEntry ::= SEQUENCE {
   mscLpCustomerIdentifier
      Unsigned32 }

mscLpCustomerIdentifier OBJECT-TYPE
   SYNTAX     Unsigned32 (0 | 1..8191)
   ACCESS     read-write
   STATUS     mandatory
   DESCRIPTION
     "This attribute holds the Customer Identifier (CID).
      
      Every component has a CID. If a component has a cid attribute, the 
      component's CID is the provisioned value of that attribute; 
      otherwise the component inherits the CID of its parent. The top-
      level component has a CID of 0.
      
      Every operator session also has a CID, which is the CID 
      provisioned for the operator's user ID. An operator will see only the 
      stream data for components having a matching CID. Also, the 
      operator will be allowed to issue commands for only those 
      components which have a matching CID.
      
      An operator CID of 0 is used to identify the Network Manager 
      (referred to as 'NetMan' in DPN). This CID matches the CID of 
      any component. Values 1 to 8191 inclusive (equivalent to 'basic 
      CIDs' in DPN) may be assigned to specific customers."
   DEFVAL     { 0 }
::= { mscLpCidDataEntry 1 }

mscLpStateTable OBJECT-TYPE
   SYNTAX     SEQUENCE OF MscLpStateEntry
   ACCESS     not-accessible
   STATUS     mandatory
   DESCRIPTION
     "This group contains the three OSI State attributes and the six OSI 
      Status attributes. The descriptions generically indicate what each 
      attribute implies about the component. Note that not all the values 
      and state combinations described here are supported by every 
      component which uses this group. For component-specific 
      information and the valid state combinations, refer to NTP 241-
      7001-150, Passport Operations and Maintenance Guide."
::= { mscLp 102 }

mscLpStateEntry OBJECT-TYPE
   SYNTAX     MscLpStateEntry
   ACCESS     not-accessible
   STATUS     mandatory
   DESCRIPTION
     "An entry in the mscLpStateTable."
   INDEX {
      mscLpIndex }
::= { mscLpStateTable 1 }

MscLpStateEntry ::= SEQUENCE {
   mscLpAdminState
      INTEGER,
   mscLpOperationalState
      INTEGER,
   mscLpUsageState
      INTEGER,
   mscLpAvailabilityStatus
      OCTET STRING,
   mscLpProceduralStatus
      OCTET STRING,
   mscLpControlStatus
      OCTET STRING,
   mscLpAlarmStatus
      OCTET STRING,
   mscLpStandbyStatus
      INTEGER,
   mscLpUnknownStatus
      INTEGER }

mscLpAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component.
      
      The OSI Status attributes, if supported by the component, may 
      provide more details, qualifying the state of the component."
   DEFVAL     { unlocked }
::= { mscLpStateEntry 1 }

mscLpOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle.
      
      The OSI Status attributes, if supported by the component, may 
      provide more details, qualifying the state of the component."
   DEFVAL     { disabled }
::= { mscLpStateEntry 2 }

mscLpUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time.
      
      The OSI Status attributes, if supported by the component, may 
      provide more details, qualifying the state of the component."
   DEFVAL     { idle }
::= { mscLpStateEntry 3 }

mscLpAvailabilityStatus OBJECT-TYPE
   SYNTAX     OCTET STRING (SIZE (2))
   ACCESS     read-only
   STATUS     mandatory
   DESCRIPTION
     "If supported by the component, this attribute indicates the OSI 
      Availability status of the component. Note that, even though it is 
      defined as a multi-valued set, at most one value is shown to the user.
      
      When no values are in the set, this indicates that either the attribute 
      is not supported or that none of the status conditions described 
      below are present.
      
      The value inTest indicates that the resource is undergoing a test 
      procedure. If adminState is locked or shuttingDown, the normal 
      users are precluded from using the resource and controlStatus is 
      reservedForTest. Tests that do not exclude additional users can be 
      present in any operational or administrative state but the 
      reservedForTest condition should not be present.
      
      The value failed indicates that the component has an internal fault 
      that prevents it from operating. The operationalState is disabled.
      
      The value dependency indicates that the component cannot operate 
      because some other resource on which it depends is unavailable. 
      The operationalState is disabled.
      
      The value powerOff indicates the resource requires power to be 
      applied and it is not powered on. The operationalState is disabled.
      
      The value offLine indicates the resource requires a routine 
      operation (either manual, automatic, or both) to be performed to 
      place it on-line and make it available for use. The operationalState 
      is disabled.
      
      The value offDuty indicates the resource is inactive in accordance 
      with a predetermined time schedule. In the absence of other 
      disabling conditions, the operationalState is enabled or disabled.
      
      The value degraded indicates the service provided by the 
      component is degraded in some way, such as in speed or operating 
      capacity. However, the resource remains available for service. The 
      operationalState is enabled.
      
      The value notInstalled indicates the resource is not present. The 
      operationalState is disabled.
      
      The value logFull is not used.

      Description of bits:
      inTest(0)
      failed(1)
      powerOff(2)
      offLine(3)
      offDuty(4)
      dependency(5)
      degraded(6)
      notInstalled(7)
      logFull(8)"
::= { mscLpStateEntry 4 }

mscLpProceduralStatus OBJECT-TYPE
   SYNTAX     OCTET STRING (SIZE (1))
   ACCESS     read-only
   STATUS     mandatory
   DESCRIPTION
     "If supported by the component, this attribute indicates the OSI 
      Procedural status of the component. Note that, even though it is 
      defined as a multi-valued set, at most one value is shown to the user.
      
      When no values are in the set, this indicates that either the attribute 
      is not supported or that none of the status conditions described 
      below are present.
      
      The value initializationRequired indicates (for a resource which 
      doesn't initialize autonomously) that initialization is required before 
      it can perform its normal functions, and this procedure has not been 
      initiated. The operationalState is disabled.
      
      The value notInitialized indicates (for a resource which does 
      initialize autonomously) that initialization is required before it can 
      perform its normal functions, and this procedure has not been 
      initiated. The operationalState may be enabled or disabled.
      
      The value initializing indicates that initialization has been initiated 
      but is not yet complete. The operationalState may be enabled or 
      disabled.
      
      The value reporting indicates the resource has completed some 
      processing operation and is notifying the results. The 
      operationalState is enabled.
      
      The value terminating indicates the component is in a termination 
      phase. If the resource doesn't reinitialize autonomously, 
      operationalState is disabled; otherwise it is enabled or disabled.

      Description of bits:
      initializationRequired(0)
      notInitialized(1)
      initializing(2)
      reporting(3)
      terminating(4)"
::= { mscLpStateEntry 5 }

mscLpControlStatus OBJECT-TYPE
   SYNTAX     OCTET STRING (SIZE (1))
   ACCESS     read-only
   STATUS     mandatory
   DESCRIPTION
     "If supported by the component, this attribute indicates the OSI 
      Control status of the component. Note that, even though it is defined 
      as a multi-valued set, at most one value is shown to the user.
      
      When no values are in the set, this indicates that either the attribute 
      is not supported or that none of the status conditions described 
      below are present.
      
      The value subjectToTest indicates the resource is available but tests 
      may be conducted simultaneously at unpredictable times, which 
      may cause it to exhibit unusual characteristics.
      
      The value partOfServicesLocked indicates that part of the service is 
      restricted from users of a resource. The adminState is unlocked.
      
      The value reservedForTest indicates that the component is 
      administratively unavailable because it is undergoing a test 
      procedure. The adminState is locked.
      
      The value suspended indicates that the service has been 
      administratively suspended.

      Description of bits:
      subjectToTest(0)
      partOfServicesLocked(1)
      reservedForTest(2)
      suspended(3)"
::= { mscLpStateEntry 6 }

mscLpAlarmStatus OBJECT-TYPE
   SYNTAX     OCTET STRING (SIZE (1))
   ACCESS     read-only
   STATUS     mandatory
   DESCRIPTION
     "If supported by the component, this attribute indicates the OSI 
      Alarm status of the component. Note that, even though it is defined 
      as a multi-valued set, at most one value is shown to the user.
      
      When no values are in the set, this indicates that either the attribute 
      is not supported or that none of the status conditions described 
      below are present.
      
      The value underRepair indicates the component is currently being 
      repaired. The operationalState is enabled or disabled.
      
      The value critical indicates one or more critical alarms are 
      outstanding against the component. Other, less severe, alarms may 
      also be outstanding. The operationalState is enabled or disabled.
      
      The value major indicates one or more major alarms are 
      outstanding against the component. Other, less severe, alarms may 
      also be outstanding. The operationalState is enabled or disabled.
      
      The value minor indicates one or more minor alarms are 
      outstanding against the component. Other, less severe, alarms may 
      also be outstanding. The operationalState is enabled or disabled.
      
      The value alarmOutstanding generically indicates that an alarm of 
      some severity is outstanding against the component.

      Description of bits:
      underRepair(0)
      critical(1)
      major(2)
      minor(3)
      alarmOutstanding(4)"
::= { mscLpStateEntry 7 }

mscLpStandbyStatus OBJECT-TYPE
   SYNTAX     INTEGER  {
                 hotStandby(0),
                 coldStandby(1),
                 providingService(2),
                 notSet(15) }
   ACCESS     read-only
   STATUS     mandatory
   DESCRIPTION
     "If supported by the component, this attribute indicates the OSI 
      Standby status of the component.
      
      The value notSet indicates that either the attribute is not supported 
      or that none of the status conditions described below are present. 
      Note that this is a non-standard value, used because the original 
      specification indicated this attribute was set-valued and thus, did not 
      provide a value to indicate that none of the other three are 
      applicable.
      
      The value hotStandby indicates that the resource is not providing 
      service but will be immediately able to take over the role of the 
      resource to be backed up, without initialization activity, and 
      containing the same information as the resource to be backed up.
      
      The value coldStandby indicates the resource is a backup for 
      another resource but will not be immediately able to take over the 
      role of the backed up resource and will require some initialization 
      activity.
      
      The value providingService indicates that this component, as a 
      backup resource, is currently backing up another resource."
   DEFVAL     { notSet }
::= { mscLpStateEntry 8 }

mscLpUnknownStatus OBJECT-TYPE
   SYNTAX     INTEGER  {
                 false(0),
                 true(1) }
   ACCESS     read-only
   STATUS     mandatory
   DESCRIPTION
     "This attribute indicates the OSI Unknown status of the component.
      
      The value false indicates that all of the other OSI State and Status 
      attribute values can be considered accurate.
      
      The value true indicates that the actual state of the component is not 
      known for sure."
   DEFVAL     { false }
::= { mscLpStateEntry 9 }

mscLpOperTable OBJECT-TYPE
   SYNTAX     SEQUENCE OF MscLpOperEntry
   ACCESS     not-accessible
   STATUS     mandatory
   DESCRIPTION
     "This Group contains the operational attributes for the LP 
      component."
::= { mscLp 103 }

mscLpOperEntry OBJECT-TYPE
   SYNTAX     MscLpOperEntry
   ACCESS     not-accessible
   STATUS     mandatory
   DESCRIPTION
     "An entry in the mscLpOperTable."
   INDEX {
      mscLpIndex }
::= { mscLpOperTable 1 }

MscLpOperEntry ::= SEQUENCE {
   mscLpActiveCard
      RowPointer,
   mscLpMainCardStatus
      INTEGER,
   mscLpSpareCardStatus
      INTEGER,
   mscLpRestartOnCpSwitch
      INTEGER,
   mscLpScheduledSwitchover
      EnterpriseDateAndTime }

mscLpActiveCard OBJECT-TYPE
   SYNTAX     RowPointer 
   ACCESS     read-only
   STATUS     mandatory
   DESCRIPTION
     "This attribute indicates on which card this LP is currently running 
      (if any)."
::= { mscLpOperEntry 1 }

mscLpMainCardStatus OBJECT-TYPE
   SYNTAX     INTEGER  {
                 notProvisioned(0),
                 notAvailable(1),
                 available(3),
                 active(4) }
   ACCESS     read-only
   STATUS     mandatory
   DESCRIPTION
     "This attribute specifies the status of this LP's main card. The 
      following values have been defined:
      notProvisioned		 No main card has been provisioned.
      notAvailable		 The main card is not available.
      available		 The main card is available (running as standby).
      active		 The main card is running as active."
::= { mscLpOperEntry 2 }

mscLpSpareCardStatus OBJECT-TYPE
   SYNTAX     INTEGER  {
                 notProvisioned(0),
                 notAvailable(1),
                 alreadyInUse(2),
                 available(3),
                 active(4) }
   ACCESS     read-only
   STATUS     mandatory
   DESCRIPTION
     "This attribute specifies the status of this LP's spare card. The 
      following values have been defined:
      notProvisioned		 No spare card has been provisioned.
      notAvailable		 The spare card is not available.
      alreadyInUse		 The spare card is already in use by another LP.
      available		 The spare card is available (running as standby).
      active		 The spare card is running as active."
::= { mscLpOperEntry 3 }

mscLpRestartOnCpSwitch OBJECT-TYPE
   SYNTAX     INTEGER  {
                 false(0),
                 true(1) }
   ACCESS     read-only
   STATUS     mandatory
   DESCRIPTION
     "This attribute indicates whether the Lp always restarts upon a CP 
      switchover. The value is true  if the featureList of the associated Sw 
      Lpt component contains a feature that does not support hitless CP 
      switchover. The value is also  true  when the feature 
      noHitlessCpSwitch is provisioned on  the CP. A  value of false does 
      not guarantee 'no restart'; dynamic conditions may still result in an 
      FP restart when a CP switchover occurs."
::= { mscLpOperEntry 4 }

mscLpScheduledSwitchover OBJECT-TYPE
   SYNTAX     EnterpriseDateAndTime (SIZE (0 | 16))
   ACCESS     read-only
   STATUS     mandatory
   DESCRIPTION
     "This attribute indicates the execution time of the scheduled 
      switchover. When there is no switchover scheduled the time is 
      equals to 0 (0000-00-00 00:00)."
::= { mscLpOperEntry 5 }

mscLpUtilTable OBJECT-TYPE
   SYNTAX     SEQUENCE OF MscLpUtilEntry
   ACCESS     not-accessible
   STATUS     mandatory
   DESCRIPTION
     "This group contains the operational attributes that specify the 
      processor's utilization levels. When this group exists for an LP 
      component, the attributes are representative of the active card."
::= { mscLp 104 }

mscLpUtilEntry OBJECT-TYPE
   SYNTAX     MscLpUtilEntry
   ACCESS     not-accessible
   STATUS     mandatory
   DESCRIPTION
     "An entry in the mscLpUtilTable."
   INDEX {
      mscLpIndex }
::= { mscLpUtilTable 1 }

MscLpUtilEntry ::= SEQUENCE {
   mscLpTimeInterval
      Unsigned32,
   mscLpCpuUtil
      Gauge32,
   mscLpCpuUtilAvg
      Gauge32,
   mscLpCpuUtilAvgMin
      Gauge32,
   mscLpCpuUtilAvgMax
      Gauge32,
   mscLpMsgBlockUsage
      Gauge32,
   mscLpMsgBlockUsageAvg
      Gauge32,
   mscLpMsgBlockUsageAvgMin
      Gauge32,
   mscLpMsgBlockUsageAvgMax
      Gauge32,
   mscLpLocalMsgBlockUsage
      Gauge32,
   mscLpLocalMsgBlockUsageAvg
      Gauge32,
   mscLpLocalMsgBlockUsageMin
      Gauge32,
   mscLpLocalMsgBlockUsageMax
      Gauge32 }

mscLpTimeInterval OBJECT-TYPE
   SYNTAX     Unsigned32 (0..15)
   ACCESS     read-only
   STATUS     mandatory
   DESCRIPTION
     "This attribute indicates the time period (in minutes) for which the 
      average, minimum and maximum utilization values are calculated.  
      This attribute is reset to 0 every 15 minutes."
::= { mscLpUtilEntry 1 }

mscLpCpuUtil OBJECT-TYPE
   SYNTAX     Gauge32 (0..100)
   ACCESS     read-only
   STATUS     mandatory
   DESCRIPTION
     "This attribute indicates an approximation of the current processor 
      utilization level (expressed as a percentage)."
::= { mscLpUtilEntry 2 }

mscLpCpuUtilAvg OBJECT-TYPE
   SYNTAX     Gauge32 (0..100)
   ACCESS     read-only
   STATUS     mandatory
   DESCRIPTION
     "This attribute indicates an average processor utilization level over 
      the specified time period, timeInterval. This average is calculated 
      based on one minute CPU utilization averages."
::= { mscLpUtilEntry 3 }

mscLpCpuUtilAvgMin OBJECT-TYPE
   SYNTAX     Gauge32 (0..100)
   ACCESS     read-only
   STATUS     mandatory
   DESCRIPTION
     "This attribute indicates the minimum processor utilization level over 
      a specified time period, timeInterval. This is based on one minute 
      CPU utilization averages."
::= { mscLpUtilEntry 4 }

mscLpCpuUtilAvgMax OBJECT-TYPE
   SYNTAX     Gauge32 (0..100)
   ACCESS     read-only
   STATUS     mandatory
   DESCRIPTION
     "This attribute indicates the maximum processor utilization level 
      over a specified time period, timeInterval. This is based on one 
      minute CPU utilization averages."
::= { mscLpUtilEntry 5 }

mscLpMsgBlockUsage OBJECT-TYPE
   SYNTAX     Gauge32 (0..2147483647)
   ACCESS     read-only
   STATUS     mandatory
   DESCRIPTION
     "This attribute indicates the processor's current shared message 
      block memory utilization.
      If there is no shared memory on the card, this attribute indicates 0."
::= { mscLpUtilEntry 6 }

mscLpMsgBlockUsageAvg OBJECT-TYPE
   SYNTAX     Gauge32 (0..2147483647)
   ACCESS     read-only
   STATUS     mandatory
   DESCRIPTION
     "This attribute indicates the processor's average memory utilization 
      of shared message blocks, calculated over a specified time period, 
      timeInterval.  This utilization value is calculated using 15 second 
      samples.  At the start of each timeInterval, this average memory 
      utilization is reset to the current usage, sharedMsgBlockUsage.
      If there is no shared memory on the card, this attribute indicates 0."
::= { mscLpUtilEntry 7 }

mscLpMsgBlockUsageAvgMin OBJECT-TYPE
   SYNTAX     Gauge32 (0..2147483647)
   ACCESS     read-only
   STATUS     mandatory
   DESCRIPTION
     "This attribute indicates the processor's minimum memory 
      utilization  of shared message blocks, calculated over a specified 
      time period, timeInterval.  This utilization value is calculated using 
      15 second samples.  At the start of each timeInterval, this minimum 
      memory utilization is reset to the current usage, 
      sharedMsgBlockUsage.
      If there is no shared memory on the card, this attribute indicates 0."
::= { mscLpUtilEntry 8 }

mscLpMsgBlockUsageAvgMax OBJECT-TYPE
   SYNTAX     Gauge32 (0..2147483647)
   ACCESS     read-only
   STATUS     mandatory
   DESCRIPTION
     "This attribute indicates the processor's maximum memory 
      utilization of shared message blocks, calculated over a specified 
      time period, timeInterval.  This utilization value is calculated using 
      15 second samples.  At the start of each timeInterval, this maximum 
      memory utilization is reset to the current usage, 
      sharedMsgBlockUsage.
      If there is no shared memory on the card, this attribute indicates 0."
::= { mscLpUtilEntry 9 }

mscLpLocalMsgBlockUsage OBJECT-TYPE
   SYNTAX     Gauge32 (0..2147483647)
   ACCESS     read-only
   STATUS     mandatory
   DESCRIPTION
     "This attribute indicates the processor's current memory utilization 
      of message blocks which are used for local messaging on the card."
::= { mscLpUtilEntry 10 }

mscLpLocalMsgBlockUsageAvg OBJECT-TYPE
   SYNTAX     Gauge32 (0..2147483647)
   ACCESS     read-only
   STATUS     mandatory
   DESCRIPTION
     "This attribute indicates the processor's average memory utilization 
      of message blocks used for local messaging on the card, calculated 
      over a specified time period, timeInterval.  This utilization value is 
      calculated using 15 second samples.  At the start of each 
      timeInterval, this average memory utilization is reset to the current 
      usage, localMsgBlockUsage."
::= { mscLpUtilEntry 11 }

mscLpLocalMsgBlockUsageMin OBJECT-TYPE
   SYNTAX     Gauge32 (0..2147483647)
   ACCESS     read-only
   STATUS     mandatory
   DESCRIPTION
     "This attribute indicates the processor's minimum memory 
      utilization of message blocks used for local messaging on the card, 
      calculated over a specified time period, timeInterval.  This 
      utilization value is updated at 15 second intervals.  At the start of 
      each timeInterval, this minimum memory utilization is reset to the 
      current usage, localMsgBlockUsage."
::= { mscLpUtilEntry 12 }

mscLpLocalMsgBlockUsageMax OBJECT-TYPE
   SYNTAX     Gauge32 (0..2147483647)
   ACCESS     read-only
   STATUS     mandatory
   DESCRIPTION
     "This attribute indicates the processor's maximum memory 
      utilization of message blocks used for local messaging on the card, 
      calculated over a specified time period, timeInterval.  This 
      utilization value is updated at 15 second intervals.  At the start of 
      each timeInterval, this maximum memory utilization is reset to the 
      current usage, localMsgBlockUsage."
::= { mscLpUtilEntry 13 }

mscLpCapTable OBJECT-TYPE
   SYNTAX     SEQUENCE OF MscLpCapEntry
   ACCESS     not-accessible
   STATUS     mandatory
   DESCRIPTION
     "This group contains the operational attributes that specify the 
      processor's capacity levels. When this group exists for an LP 
      component, the attributes are representative of the active Card."
::= { mscLp 105 }

mscLpCapEntry OBJECT-TYPE
   SYNTAX     MscLpCapEntry
   ACCESS     not-accessible
   STATUS     mandatory
   DESCRIPTION
     "An entry in the mscLpCapTable."
   INDEX {
      mscLpIndex }
::= { mscLpCapTable 1 }

MscLpCapEntry ::= SEQUENCE {
   mscLpMsgBlockCapacity
      Unsigned32,
   mscLpLocalMsgBlockCapacity
      Unsigned32 }

mscLpMsgBlockCapacity OBJECT-TYPE
   SYNTAX     Unsigned32 (0..2147483647)
   ACCESS     read-only
   STATUS     mandatory
   DESCRIPTION
     "This attribute indicates the processor card's shared message block 
      memory capacity."
::= { mscLpCapEntry 1 }

mscLpLocalMsgBlockCapacity OBJECT-TYPE
   SYNTAX     Unsigned32 (0..2147483647)
   ACCESS     read-only
   STATUS     mandatory
   DESCRIPTION
     "This attribute indicates the processor card's local message block 
      memory capacity.  These message blocks are used for local 
      messaging on the card."
::= { mscLpCapEntry 2 }

mscLpLinkToApplicationsTable OBJECT-TYPE
   SYNTAX     SEQUENCE OF MscLpLinkToApplicationsEntry
   ACCESS     not-accessible
   STATUS     mandatory
   DESCRIPTION
     "This attribute allows applications to link themselves directly to the 
      LP component."
::= { mscLp 242 }

mscLpLinkToApplicationsEntry OBJECT-TYPE
   SYNTAX     MscLpLinkToApplicationsEntry
   ACCESS     not-accessible
   STATUS     mandatory
   DESCRIPTION
     "An entry in the mscLpLinkToApplicationsTable."
   INDEX {
      mscLpIndex,
      mscLpLinkToApplicationsValue }
::= { mscLpLinkToApplicationsTable 1 }

MscLpLinkToApplicationsEntry ::= SEQUENCE {
   mscLpLinkToApplicationsValue
      Link }

mscLpLinkToApplicationsValue OBJECT-TYPE
   SYNTAX     Link 
   ACCESS     read-only
   STATUS     mandatory
   DESCRIPTION
     "This variable represents both the value and the index for the
      mscLpLinkToApplicationsTable."
::= { mscLpLinkToApplicationsEntry 1 }

mscLpMemoryCapacityTable OBJECT-TYPE
   SYNTAX     SEQUENCE OF MscLpMemoryCapacityEntry
   ACCESS     not-accessible
   STATUS     mandatory
   DESCRIPTION
     "This attribute indicates the processor card's memory capacity for 
      each type of memory."
::= { mscLp 244 }

mscLpMemoryCapacityEntry OBJECT-TYPE
   SYNTAX     MscLpMemoryCapacityEntry
   ACCESS     not-accessible
   STATUS     mandatory
   DESCRIPTION
     "An entry in the mscLpMemoryCapacityTable."
   INDEX {
      mscLpIndex,
      mscLpMemoryCapacityIndex }
::= { mscLpMemoryCapacityTable 1 }

MscLpMemoryCapacityEntry ::= SEQUENCE {
   mscLpMemoryCapacityIndex
      INTEGER,
   mscLpMemoryCapacityValue
      Unsigned32 }

mscLpMemoryCapacityIndex OBJECT-TYPE
   SYNTAX     INTEGER  {
                 fastRam(0),
                 normalRam(1),
                 sharedRam(2) }
   ACCESS     not-accessible
   STATUS     mandatory
   DESCRIPTION
     "This variable represents the mscLpMemoryCapacityTable
      specific index for the mscLpMemoryCapacityTable."
::= { mscLpMemoryCapacityEntry 1 }

mscLpMemoryCapacityValue OBJECT-TYPE
   SYNTAX     Unsigned32 (0..2147483647)
   ACCESS     read-only
   STATUS     mandatory
   DESCRIPTION
     "This variable represents an individual value for the
      mscLpMemoryCapacityTable."
::= { mscLpMemoryCapacityEntry 2 }

mscLpMemoryUsageTable OBJECT-TYPE
   SYNTAX     SEQUENCE OF MscLpMemoryUsageEntry
   ACCESS     not-accessible
   STATUS     mandatory
   DESCRIPTION
     "This attribute indicates the processor's current memory utilization 
      for each type of memory."
::= { mscLp 245 }

mscLpMemoryUsageEntry OBJECT-TYPE
   SYNTAX     MscLpMemoryUsageEntry
   ACCESS     not-accessible
   STATUS     mandatory
   DESCRIPTION
     "An entry in the mscLpMemoryUsageTable."
   INDEX {
      mscLpIndex,
      mscLpMemoryUsageIndex }
::= { mscLpMemoryUsageTable 1 }

MscLpMemoryUsageEntry ::= SEQUENCE {
   mscLpMemoryUsageIndex
      INTEGER,
   mscLpMemoryUsageValue
      Gauge32 }

mscLpMemoryUsageIndex OBJECT-TYPE
   SYNTAX     INTEGER  {
                 fastRam(0),
                 normalRam(1),
                 sharedRam(2) }
   ACCESS     not-accessible
   STATUS     mandatory
   DESCRIPTION
     "This variable represents the mscLpMemoryUsageTable
      specific index for the mscLpMemoryUsageTable."
::= { mscLpMemoryUsageEntry 1 }

mscLpMemoryUsageValue OBJECT-TYPE
   SYNTAX     Gauge32 (0..2147483647)
   ACCESS     read-only
   STATUS     mandatory
   DESCRIPTION
     "This variable represents an individual value for the
      mscLpMemoryUsageTable."
::= { mscLpMemoryUsageEntry 2 }

mscLpMemoryUsageAvgTable OBJECT-TYPE
   SYNTAX     SEQUENCE OF MscLpMemoryUsageAvgEntry
   ACCESS     not-accessible
   STATUS     mandatory
   DESCRIPTION
     "This attribute indicates the processor's average memory utilization 
      for each type of memory in the specified time period, timeInterval. 
      This value is calculated using 15 second samples."
::= { mscLp 276 }

mscLpMemoryUsageAvgEntry OBJECT-TYPE
   SYNTAX     MscLpMemoryUsageAvgEntry
   ACCESS     not-accessible
   STATUS     mandatory
   DESCRIPTION
     "An entry in the mscLpMemoryUsageAvgTable."
   INDEX {
      mscLpIndex,
      mscLpMemoryUsageAvgIndex }
::= { mscLpMemoryUsageAvgTable 1 }

MscLpMemoryUsageAvgEntry ::= SEQUENCE {
   mscLpMemoryUsageAvgIndex
      INTEGER,
   mscLpMemoryUsageAvgValue
      Gauge32 }

mscLpMemoryUsageAvgIndex OBJECT-TYPE
   SYNTAX     INTEGER  {
                 fastRam(0),
                 normalRam(1),
                 sharedRam(2) }
   ACCESS     not-accessible
   STATUS     mandatory
   DESCRIPTION
     "This variable represents the mscLpMemoryUsageAvgTable
      specific index for the mscLpMemoryUsageAvgTable."
::= { mscLpMemoryUsageAvgEntry 1 }

mscLpMemoryUsageAvgValue OBJECT-TYPE
   SYNTAX     Gauge32 (0..2147483647)
   ACCESS     read-only
   STATUS     mandatory
   DESCRIPTION
     "This variable represents an individual value for the
      mscLpMemoryUsageAvgTable."
::= { mscLpMemoryUsageAvgEntry 2 }

mscLpMemoryUsageAvgMinTable OBJECT-TYPE
   SYNTAX     SEQUENCE OF MscLpMemoryUsageAvgMinEntry
   ACCESS     not-accessible
   STATUS     mandatory
   DESCRIPTION
     "This attribute indicates the processor's minimum memory 
      utilization for each type of memory in the specified time period, 
      timeInterval. This value is calculated using 15 second samples."
::= { mscLp 277 }

mscLpMemoryUsageAvgMinEntry OBJECT-TYPE
   SYNTAX     MscLpMemoryUsageAvgMinEntry
   ACCESS     not-accessible
   STATUS     mandatory
   DESCRIPTION
     "An entry in the mscLpMemoryUsageAvgMinTable."
   INDEX {
      mscLpIndex,
      mscLpMemoryUsageAvgMinIndex }
::= { mscLpMemoryUsageAvgMinTable 1 }

MscLpMemoryUsageAvgMinEntry ::= SEQUENCE {
   mscLpMemoryUsageAvgMinIndex
      INTEGER,
   mscLpMemoryUsageAvgMinValue
      Gauge32 }

mscLpMemoryUsageAvgMinIndex OBJECT-TYPE
   SYNTAX     INTEGER  {
                 fastRam(0),
                 normalRam(1),
                 sharedRam(2) }
   ACCESS     not-accessible
   STATUS     mandatory
   DESCRIPTION
     "This variable represents the mscLpMemoryUsageAvgMinTable
      specific index for the mscLpMemoryUsageAvgMinTable."
::= { mscLpMemoryUsageAvgMinEntry 1 }

mscLpMemoryUsageAvgMinValue OBJECT-TYPE
   SYNTAX     Gauge32 (0..2147483647)
   ACCESS     read-only
   STATUS     mandatory
   DESCRIPTION
     "This variable represents an individual value for the
      mscLpMemoryUsageAvgMinTable."
::= { mscLpMemoryUsageAvgMinEntry 2 }

mscLpMemoryUsageAvgMaxTable OBJECT-TYPE
   SYNTAX     SEQUENCE OF MscLpMemoryUsageAvgMaxEntry
   ACCESS     not-accessible
   STATUS     mandatory
   DESCRIPTION
     "This attribute indicates the processor's maximum memory 
      utilization for each type of memory in the specified time period, 
      timeInterval. This value is calculated using 15 second samples."
::= { mscLp 278 }

mscLpMemoryUsageAvgMaxEntry OBJECT-TYPE
   SYNTAX     MscLpMemoryUsageAvgMaxEntry
   ACCESS     not-accessible
   STATUS     mandatory
   DESCRIPTION
     "An entry in the mscLpMemoryUsageAvgMaxTable."
   INDEX {
      mscLpIndex,
      mscLpMemoryUsageAvgMaxIndex }
::= { mscLpMemoryUsageAvgMaxTable 1 }

MscLpMemoryUsageAvgMaxEntry ::= SEQUENCE {
   mscLpMemoryUsageAvgMaxIndex
      INTEGER,
   mscLpMemoryUsageAvgMaxValue
      Gauge32 }

mscLpMemoryUsageAvgMaxIndex OBJECT-TYPE
   SYNTAX     INTEGER  {
                 fastRam(0),
                 normalRam(1),
                 sharedRam(2) }
   ACCESS     not-accessible
   STATUS     mandatory
   DESCRIPTION
     "This variable represents the mscLpMemoryUsageAvgMaxTable
      specific index for the mscLpMemoryUsageAvgMaxTable."
::= { mscLpMemoryUsageAvgMaxEntry 1 }

mscLpMemoryUsageAvgMaxValue OBJECT-TYPE
   SYNTAX     Gauge32 (0..2147483647)
   ACCESS     read-only
   STATUS     mandatory
   DESCRIPTION
     "This variable represents an individual value for the
      mscLpMemoryUsageAvgMaxTable."
::= { mscLpMemoryUsageAvgMaxEntry 2 }


-- Lp/n DS3/n
-- The DS3 component controls a DS3 port on a DS3 Function 
-- Processor. Non-zero Instance numbers for the DS3 are only allowed 
-- on cell-based boards.

mscLpDS3 OBJECT IDENTIFIER ::= { mscLp 5 }



mscLpDS3RowStatusTable OBJECT-TYPE
   SYNTAX     SEQUENCE OF MscLpDS3RowStatusEntry
   ACCESS     not-accessible
   STATUS     mandatory
   DESCRIPTION
     "This entry controls the addition and deletion of 
      mscLpDS3 components."
::= { mscLpDS3 1 }

mscLpDS3RowStatusEntry OBJECT-TYPE
   SYNTAX     MscLpDS3RowStatusEntry
   ACCESS     not-accessible
   STATUS     mandatory
   DESCRIPTION
     "A single entry in the table represents a single 
      mscLpDS3 component."
   INDEX {
      mscLpIndex,
      mscLpDS3Index }
::= { mscLpDS3RowStatusTable 1 }

MscLpDS3RowStatusEntry ::= SEQUENCE {
   mscLpDS3RowStatus
      RowStatus,
   mscLpDS3ComponentName
      DisplayString,
   mscLpDS3StorageType
      StorageType,
   mscLpDS3Index
      Integer32 }

mscLpDS3RowStatus OBJECT-TYPE
   SYNTAX     RowStatus 
   ACCESS     read-write
   STATUS     mandatory
   DESCRIPTION
     "This variable is used as the basis for SNMP naming of
      mscLpDS3 components.
      These components can be added and deleted."
::= { mscLpDS3RowStatusEntry 1 }

mscLpDS3ComponentName OBJECT-TYPE
   SYNTAX     DisplayString 
   ACCESS     read-only
   STATUS     mandatory
   DESCRIPTION
     "This variable provides the component's string name for
      use with the ASCII Console Interface"
::= { mscLpDS3RowStatusEntry 2 }

mscLpDS3StorageType OBJECT-TYPE
   SYNTAX     StorageType 
   ACCESS     read-only
   STATUS     mandatory
   DESCRIPTION
     "This variable represents the storage type value for the
      mscLpDS3 tables."
::= { mscLpDS3RowStatusEntry 4 }

mscLpDS3Index OBJECT-TYPE
   SYNTAX     Integer32 (0..11)
   ACCESS     not-accessible
   STATUS     mandatory
   DESCRIPTION
     "This variable represents the index for the mscLpDS3 tables."
::= { mscLpDS3RowStatusEntry 10 }

mscLpDS3ProvTable OBJECT-TYPE
   SYNTAX     SEQUENCE OF MscLpDS3ProvEntry
   ACCESS     not-accessible
   STATUS     mandatory
   DESCRIPTION
     "This group contains all of the provisioning data for a DS3 
      component."
::= { mscLpDS3 10 }

mscLpDS3ProvEntry OBJECT-TYPE
   SYNTAX     MscLpDS3ProvEntry
   ACCESS     not-accessible
   STATUS     mandatory
   DESCRIPTION
     "An entry in the mscLpDS3ProvTable."
   INDEX {
      mscLpIndex,
      mscLpDS3Index }
::= { mscLpDS3ProvTable 1 }

MscLpDS3ProvEntry ::= SEQUENCE {
   mscLpDS3CbitParity
      INTEGER,
   mscLpDS3LineLength
      Unsigned32,
   mscLpDS3ClockingSource
      INTEGER,
   mscLpDS3ApplicationFramerName
      Link,
   mscLpDS3Mapping
      INTEGER }

mscLpDS3CbitParity OBJECT-TYPE
   SYNTAX     INTEGER  {
                 off(0),
                 on(1) }
   ACCESS     read-write
   STATUS     mandatory
   DESCRIPTION
     "This attribute indicates if C-Bit parity has been turned ON or OFF. 
      The CBIT component will appear under the DS3 component when 
      the cbitParity attribute is set to on."
   DEFVAL     { on }
::= { mscLpDS3ProvEntry 1 }

mscLpDS3LineLength OBJECT-TYPE
   SYNTAX     Unsigned32 (0..450)
   ACCESS     read-write
   STATUS     mandatory
   DESCRIPTION
     "This attribute defines the line length for equalization calculations 
      for the DS3 line. The range is between 0 and 450 feet (1 metre = 
      3.28 feet). 
      Note: There are currently only two ranges as far as the equalization 
      calculation performed on the FP is concerned: 0 to 224ft and 225 to 
      450ft."
   DEFVAL     { 1 }
::= { mscLpDS3ProvEntry 2 }

mscLpDS3ClockingSource OBJECT-TYPE
   SYNTAX     INTEGER  {
                 local(0),
                 line(1),
                 module(2),
                 otherPort(4) }
   ACCESS     read-write
   STATUS     mandatory
   DESCRIPTION
     "This attribute defines the type of clocking source used for 
      synchronizing the DS3 transmit clock: local means direct use of the 
      local clock oscillator at its centre frequency; line means use of a 
      signal phase-locked to the incoming DS3 line rate; module means 
      the use of a signal phase-locked to the CP reference clock.
      Note that the multiport cell-based cards have one common clock 
      source for all ports. For this reason, the following rules apply for the 
      value of clockingSource across the board's three ports: 
      All three clockingSource values must be 'local' OR
      All three clockingSource values must be 'module' OR
      One clockingSource value must be 'line' and the other two must be 
      'otherPort'.
      If there is no NS component provisioned, the default value for this 
      attribute will be local. If the NS component has been provisioned, 
      the default value is module, except for the 1pDS3C cards.
      For the 1pDS3C cards, the default and only valid value for this 
      attribute is local. The clockingSource of the DS1 sub-component 
      becomes the effective clocking source for this attribute. All the DS1 
      sub-components have the same clocking source."
::= { mscLpDS3ProvEntry 3 }

mscLpDS3ApplicationFramerName OBJECT-TYPE
   SYNTAX     Link 
   ACCESS     read-write
   STATUS     mandatory
   DESCRIPTION
     "This attribute defines the link to the software stack. It defines which 
      application is running on top of the DS3 component."
::= { mscLpDS3ProvEntry 4 }

mscLpDS3Mapping OBJECT-TYPE
   SYNTAX     INTEGER  {
                 direct(0),
                 plcp(1) }
   ACCESS     read-write
   STATUS     mandatory
   DESCRIPTION
     "This attribute indicates if ATM cells will be mapped directly into 
      the DS3 payload, or whether PLCP mapping will be used. The 
      PLCP component will appear under the DS3 component when this 
      attribute is set to plcp. This attribute will be ignored when set on 
      frame-based cards."
   DEFVAL     { direct }
::= { mscLpDS3ProvEntry 5 }

mscLpDS3CidDataTable OBJECT-TYPE
   SYNTAX     SEQUENCE OF MscLpDS3CidDataEntry
   ACCESS     not-accessible
   STATUS     mandatory
   DESCRIPTION
     "This group contains the attribute for a component's Customer 
      Identifier (CID). Refer to the attribute description for a detailed 
      explanation of CIDs."
::= { mscLpDS3 11 }

mscLpDS3CidDataEntry OBJECT-TYPE
   SYNTAX     MscLpDS3CidDataEntry
   ACCESS     not-accessible
   STATUS     mandatory
   DESCRIPTION
     "An entry in the mscLpDS3CidDataTable."
   INDEX {
      mscLpIndex,
      mscLpDS3Index }
::= { mscLpDS3CidDataTable 1 }

MscLpDS3CidDataEntry ::= SEQUENCE {
   mscLpDS3CustomerIdentifier
      Unsigned32 }

mscLpDS3CustomerIdentifier OBJECT-TYPE
   SYNTAX     Unsigned32 (0 | 1..8191)
   ACCESS     read-write
   STATUS     mandatory
   DESCRIPTION
     "This attribute holds the Customer Identifier (CID).
      
      Every component has a CID. If a component has a cid attribute, the 
      component's CID is the provisioned value of that attribute; 
      otherwise the component inherits the CID of its parent. The top-
      level component has a CID of 0.
      
      Every operator session also has a CID, which is the CID 
      provisioned for the operator's user ID. An operator will see only the 
      stream data for components having a matching CID. Also, the 
      operator will be allowed to issue commands for only those 
      components which have a matching CID.
      
      An operator CID of 0 is used to identify the Network Manager 
      (referred to as 'NetMan' in DPN). This CID matches the CID of 
      any component. Values 1 to 8191 inclusive (equivalent to 'basic 
      CIDs' in DPN) may be assigned to specific customers."
   DEFVAL     { 0 }
::= { mscLpDS3CidDataEntry 1 }

mscLpDS3AdminInfoTable OBJECT-TYPE
   SYNTAX     SEQUENCE OF MscLpDS3AdminInfoEntry
   ACCESS     not-accessible
   STATUS     mandatory
   DESCRIPTION
     "This group contains the attributes pertaining to the vendor of the 
      equipment."
::= { mscLpDS3 12 }

mscLpDS3AdminInfoEntry OBJECT-TYPE
   SYNTAX     MscLpDS3AdminInfoEntry
   ACCESS     not-accessible
   STATUS     mandatory
   DESCRIPTION
     "An entry in the mscLpDS3AdminInfoTable."
   INDEX {
      mscLpIndex,
      mscLpDS3Index }
::= { mscLpDS3AdminInfoTable 1 }

MscLpDS3AdminInfoEntry ::= SEQUENCE {
   mscLpDS3Vendor
      AsciiString,
   mscLpDS3CommentText
      AsciiString }

mscLpDS3Vendor OBJECT-TYPE
   SYNTAX     AsciiString (SIZE (0..20))
   ACCESS     read-write
   STATUS     mandatory
   DESCRIPTION
     "This is the name of the vendor supplying the facility."
::= { mscLpDS3AdminInfoEntry 1 }

mscLpDS3CommentText OBJECT-TYPE
   SYNTAX     AsciiString (SIZE (0..60))
   ACCESS     read-write
   STATUS     mandatory
   DESCRIPTION
     "Any miscellaneous text about the facility."
::= { mscLpDS3AdminInfoEntry 2 }

mscLpDS3IfEntryTable OBJECT-TYPE
   SYNTAX     SEQUENCE OF MscLpDS3IfEntryEntry
   ACCESS     not-accessible
   STATUS     mandatory
   DESCRIPTION
     "This group contains the provisionable attributes for the ifEntry."
::= { mscLpDS3 13 }

mscLpDS3IfEntryEntry OBJECT-TYPE
   SYNTAX     MscLpDS3IfEntryEntry
   ACCESS     not-accessible
   STATUS     mandatory
   DESCRIPTION
     "An entry in the mscLpDS3IfEntryTable."
   INDEX {
      mscLpIndex,
      mscLpDS3Index }
::= { mscLpDS3IfEntryTable 1 }

MscLpDS3IfEntryEntry ::= SEQUENCE {
   mscLpDS3IfAdminStatus
      INTEGER,
   mscLpDS3IfIndex
      InterfaceIndex }

mscLpDS3IfAdminStatus OBJECT-TYPE
   SYNTAX     INTEGER  {
                 up(1),
                 down(2),
                 testing(3) }
   ACCESS     read-write
   STATUS     mandatory
   DESCRIPTION
     "The desired state of the interface. The up state indicates the 
      interface is operational. The down state indicates the interface is not 
      operational. The testing state indicates that no operational packets 
      can be passed."
   DEFVAL     { up }
::= { mscLpDS3IfEntryEntry 1 }

mscLpDS3IfIndex OBJECT-TYPE
   SYNTAX     InterfaceIndex (1..65535)
   ACCESS     read-only
   STATUS     mandatory
   DESCRIPTION
     "This is the index for the IfEntry. Its value is automatically initialized 
      during the provisioning process."
::= { mscLpDS3IfEntryEntry 2 }

mscLpDS3OperStatusTable OBJECT-TYPE
   SYNTAX     SEQUENCE OF MscLpDS3OperStatusEntry
   ACCESS     not-accessible
   STATUS     mandatory
   DESCRIPTION
     "This group includes the Operational Status attribute. This attribute 
      defines the current operational state of this component."
::= { mscLpDS3 14 }

mscLpDS3OperStatusEntry OBJECT-TYPE
   SYNTAX     MscLpDS3OperStatusEntry
   ACCESS     not-accessible
   STATUS     mandatory
   DESCRIPTION
     "An entry in the mscLpDS3OperStatusTable."
   INDEX {
      mscLpIndex,
      mscLpDS3Index }
::= { mscLpDS3OperStatusTable 1 }

MscLpDS3OperStatusEntry ::= SEQUENCE {
   mscLpDS3SnmpOperStatus
      INTEGER }

mscLpDS3SnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { mscLpDS3OperStatusEntry 1 }

mscLpDS3StateTable OBJECT-TYPE
   SYNTAX     SEQUENCE OF MscLpDS3StateEntry
   ACCESS     not-accessible
   STATUS     mandatory
   DESCRIPTION
     "This group contains the three OSI State attributes and the six OSI 
      Status attributes. The descriptions generically indicate what each 
      attribute implies about the component. Note that not all the values 
      and state combinations described here are supported by every 
      component which uses this group. For component-specific 
      information and the valid state combinations, refer to NTP 241-
      7001-150, Passport Operations and Maintenance Guide."
::= { mscLpDS3 15 }

mscLpDS3StateEntry OBJECT-TYPE
   SYNTAX     MscLpDS3StateEntry
   ACCESS     not-accessible
   STATUS     mandatory
   DESCRIPTION
     "An entry in the mscLpDS3StateTable."
   INDEX {
      mscLpIndex,
      mscLpDS3Index }
::= { mscLpDS3StateTable 1 }

MscLpDS3StateEntry ::= SEQUENCE {
   mscLpDS3AdminState
      INTEGER,
   mscLpDS3OperationalState
      INTEGER,
   mscLpDS3UsageState
      INTEGER,
   mscLpDS3AvailabilityStatus
      OCTET STRING,
   mscLpDS3ProceduralStatus
      OCTET STRING,
   mscLpDS3ControlStatus
      OCTET STRING,
   mscLpDS3AlarmStatus
      OCTET STRING,
   mscLpDS3StandbyStatus
      INTEGER,
   mscLpDS3UnknownStatus
      INTEGER }

mscLpDS3AdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component.
      
      The OSI Status attributes, if supported by the component, may 
      provide more details, qualifying the state of the component."
   DEFVAL     { unlocked }
::= { mscLpDS3StateEntry 1 }

mscLpDS3OperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle.
      
      The OSI Status attributes, if supported by the component, may 
      provide more details, qualifying the state of the component."
   DEFVAL     { disabled }
::= { mscLpDS3StateEntry 2 }

mscLpDS3UsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time.
      
      The OSI Status attributes, if supported by the component, may 
      provide more details, qualifying the state of the component."
   DEFVAL     { idle }
::= { mscLpDS3StateEntry 3 }

mscLpDS3AvailabilityStatus OBJECT-TYPE
   SYNTAX     OCTET STRING (SIZE (2))
   ACCESS     read-only
   STATUS     mandatory
   DESCRIPTION
     "If supported by the component, this attribute indicates the OSI 
      Availability status of the component. Note that, even though it is 
      defined as a multi-valued set, at most one value is shown to the user.
      
      When no values are in the set, this indicates that either the attribute 
      is not supported or that none of the status conditions described 
      below are present.
      
      The value inTest indicates that the resource is undergoing a test 
      procedure. If adminState is locked or shuttingDown, the normal 
      users are precluded from using the resource and controlStatus is 
      reservedForTest. Tests that do not exclude additional users can be 
      present in any operational or administrative state but the 
      reservedForTest condition should not be present.
      
      The value failed indicates that the component has an internal fault 
      that prevents it from operating. The operationalState is disabled.
      
      The value dependency indicates that the component cannot operate 
      because some other resource on which it depends is unavailable. 
      The operationalState is disabled.
      
      The value powerOff indicates the resource requires power to be 
      applied and it is not powered on. The operationalState is disabled.
      
      The value offLine indicates the resource requires a routine 
      operation (either manual, automatic, or both) to be performed to 
      place it on-line and make it available for use. The operationalState 
      is disabled.
      
      The value offDuty indicates the resource is inactive in accordance 
      with a predetermined time schedule. In the absence of other 
      disabling conditions, the operationalState is enabled or disabled.
      
      The value degraded indicates the service provided by the 
      component is degraded in some way, such as in speed or operating 
      capacity. However, the resource remains available for service. The 
      operationalState is enabled.
      
      The value notInstalled indicates the resource is not present. The 
      operationalState is disabled.
      
      The value logFull is not used.

      Description of bits:
      inTest(0)
      failed(1)
      powerOff(2)
      offLine(3)
      offDuty(4)
      dependency(5)
      degraded(6)
      notInstalled(7)
      logFull(8)"
::= { mscLpDS3StateEntry 4 }

mscLpDS3ProceduralStatus OBJECT-TYPE
   SYNTAX     OCTET STRING (SIZE (1))
   ACCESS     read-only
   STATUS     mandatory
   DESCRIPTION
     "If supported by the component, this attribute indicates the OSI 
      Procedural status of the component. Note that, even though it is 
      defined as a multi-valued set, at most one value is shown to the user.
      
      When no values are in the set, this indicates that either the attribute 
      is not supported or that none of the status conditions described 
      below are present.
      
      The value initializationRequired indicates (for a resource which 
      doesn't initialize autonomously) that initialization is required before 
      it can perform its normal functions, and this procedure has not been 
      initiated. The operationalState is disabled.
      
      The value notInitialized indicates (for a resource which does 
      initialize autonomously) that initialization is required before it can 
      perform its normal functions, and this procedure has not been 
      initiated. The operationalState may be enabled or disabled.
      
      The value initializing indicates that initialization has been initiated 
      but is not yet complete. The operationalState may be enabled or 
      disabled.
      
      The value reporting indicates the resource has completed some 
      processing operation and is notifying the results. The 
      operationalState is enabled.
      
      The value terminating indicates the component is in a termination 
      phase. If the resource doesn't reinitialize autonomously, 
      operationalState is disabled; otherwise it is enabled or disabled.

      Description of bits:
      initializationRequired(0)
      notInitialized(1)
      initializing(2)
      reporting(3)
      terminating(4)"
::= { mscLpDS3StateEntry 5 }

mscLpDS3ControlStatus OBJECT-TYPE
   SYNTAX     OCTET STRING (SIZE (1))
   ACCESS     read-only
   STATUS     mandatory
   DESCRIPTION
     "If supported by the component, this attribute indicates the OSI 
      Control status of the component. Note that, even though it is defined 
      as a multi-valued set, at most one value is shown to the user.
      
      When no values are in the set, this indicates that either the attribute 
      is not supported or that none of the status conditions described 
      below are present.
      
      The value subjectToTest indicates the resource is available but tests 
      may be conducted simultaneously at unpredictable times, which 
      may cause it to exhibit unusual characteristics.
      
      The value partOfServicesLocked indicates that part of the service is 
      restricted from users of a resource. The adminState is unlocked.
      
      The value reservedForTest indicates that the component is 
      administratively unavailable because it is undergoing a test 
      procedure. The adminState is locked.
      
      The value suspended indicates that the service has been 
      administratively suspended.

      Description of bits:
      subjectToTest(0)
      partOfServicesLocked(1)
      reservedForTest(2)
      suspended(3)"
::= { mscLpDS3StateEntry 6 }

mscLpDS3AlarmStatus OBJECT-TYPE
   SYNTAX     OCTET STRING (SIZE (1))
   ACCESS     read-only
   STATUS     mandatory
   DESCRIPTION
     "If supported by the component, this attribute indicates the OSI 
      Alarm status of the component. Note that, even though it is defined 
      as a multi-valued set, at most one value is shown to the user.
      
      When no values are in the set, this indicates that either the attribute 
      is not supported or that none of the status conditions described 
      below are present.
      
      The value underRepair indicates the component is currently being 
      repaired. The operationalState is enabled or disabled.
      
      The value critical indicates one or more critical alarms are 
      outstanding against the component. Other, less severe, alarms may 
      also be outstanding. The operationalState is enabled or disabled.
      
      The value major indicates one or more major alarms are 
      outstanding against the component. Other, less severe, alarms may 
      also be outstanding. The operationalState is enabled or disabled.
      
      The value minor indicates one or more minor alarms are 
      outstanding against the component. Other, less severe, alarms may 
      also be outstanding. The operationalState is enabled or disabled.
      
      The value alarmOutstanding generically indicates that an alarm of 
      some severity is outstanding against the component.

      Description of bits:
      underRepair(0)
      critical(1)
      major(2)
      minor(3)
      alarmOutstanding(4)"
::= { mscLpDS3StateEntry 7 }

mscLpDS3StandbyStatus OBJECT-TYPE
   SYNTAX     INTEGER  {
                 hotStandby(0),
                 coldStandby(1),
                 providingService(2),
                 notSet(15) }
   ACCESS     read-only
   STATUS     mandatory
   DESCRIPTION
     "If supported by the component, this attribute indicates the OSI 
      Standby status of the component.
      
      The value notSet indicates that either the attribute is not supported 
      or that none of the status conditions described below are present. 
      Note that this is a non-standard value, used because the original 
      specification indicated this attribute was set-valued and thus, did not 
      provide a value to indicate that none of the other three are 
      applicable.
      
      The value hotStandby indicates that the resource is not providing 
      service but will be immediately able to take over the role of the 
      resource to be backed up, without initialization activity, and 
      containing the same information as the resource to be backed up.
      
      The value coldStandby indicates the resource is a backup for 
      another resource but will not be immediately able to take over the 
      role of the backed up resource and will require some initialization 
      activity.
      
      The value providingService indicates that this component, as a 
      backup resource, is currently backing up another resource."
   DEFVAL     { notSet }
::= { mscLpDS3StateEntry 8 }

mscLpDS3UnknownStatus OBJECT-TYPE
   SYNTAX     INTEGER  {
                 false(0),
                 true(1) }
   ACCESS     read-only
   STATUS     mandatory
   DESCRIPTION
     "This attribute indicates the OSI Unknown status of the component.
      
      The value false indicates that all of the other OSI State and Status 
      attribute values can be considered accurate.
      
      The value true indicates that the actual state of the component is not 
      known for sure."
   DEFVAL     { false }
::= { mscLpDS3StateEntry 9 }

mscLpDS3OperTable OBJECT-TYPE
   SYNTAX     SEQUENCE OF MscLpDS3OperEntry
   ACCESS     not-accessible
   STATUS     mandatory
   DESCRIPTION
     "This group contains the common operational data for DS3 
      component."
::= { mscLpDS3 16 }

mscLpDS3OperEntry OBJECT-TYPE
   SYNTAX     MscLpDS3OperEntry
   ACCESS     not-accessible
   STATUS     mandatory
   DESCRIPTION
     "An entry in the mscLpDS3OperTable."
   INDEX {
      mscLpIndex,
      mscLpDS3Index }
::= { mscLpDS3OperTable 1 }

MscLpDS3OperEntry ::= SEQUENCE {
   mscLpDS3LosAlarm
      INTEGER,
   mscLpDS3LofAlarm
      INTEGER,
   mscLpDS3RxAisAlarm
      INTEGER,
   mscLpDS3RxRaiAlarm
      INTEGER,
   mscLpDS3RxIdle
      INTEGER,
   mscLpDS3TxAis
      INTEGER,
   mscLpDS3TxRai
      INTEGER,
   mscLpDS3TxIdle
      INTEGER }

mscLpDS3LosAlarm OBJECT-TYPE
   SYNTAX     INTEGER  {
                 on(0),
                 off(1) }
   ACCESS     read-only
   STATUS     mandatory
   DESCRIPTION
     "This attribute displays whether a Loss Of Signal (LOS) alarm state 
      has been entered. An LOS alarm state is entered when LOS defects 
      have been observed and accumulated for a period of 2.5 seconds +/- 
      0.5 seconds. An LOS defect is detected at the DS3 line interface 
      upon observing 175 +/- 75 continuous pulse positions with no 
      pulses of either positive or negative polarity. If the LOS defects are 
      intermittently occurring, the LOS defect accumulator is 
      decremented at a rate of 1/10 of the incrementing rate (alarm 
      integration ratio of 1/10), with all measurements based on a 200 ms 
      polling cycle.
      The DS3 component goes into an operational state of disabled until 
      the LOS alarm condition is cleared. The LOS alarm state is cleared 
      after LOS defects have been absent for a period of 10 seconds +/- 
      0.5 seconds.
      The losAlarm attribute is always set to off when the component has 
      been locked and left offline."
   DEFVAL     { off }
::= { mscLpDS3OperEntry 1 }

mscLpDS3LofAlarm OBJECT-TYPE
   SYNTAX     INTEGER  {
                 on(0),
                 off(1) }
   ACCESS     read-only
   STATUS     mandatory
   DESCRIPTION
     "This attribute displays whether a Loss Of Frame (LOF) alarm state 
      has been entered. An LOF alarm state is entered when Severely 
      Errored Frame (SEF) defects have been observed and accumulated 
      for a period of 2.5 seconds +/- 0.5 seconds. A SEF defect is 
      detected when 3 (or more) out of 16 (or fewer) F-bits are in error, or 
      one (or more) M-bits in two (or more) out of four (or fewer) 
      consecutive M-frames are in error. If the LOF defects are 
      intermittently occurring, the LOF defect accumulator is 
      decremented at a rate of 1/10 of the incrementing rate (alarm 
      integration ratio of 1/10), with all measurements based on a 200 ms 
      polling cycle.
      The DS3 component goes into an operational state of disabled until 
      the LOF alarm condition is cleared. The condition is cleared when 
      framing has been achieved for a period of 10 seconds +/- 0.5 
      seconds. As long as SEF defects are detected, the node also 
      transmits the far-end SEF/AIS defect indicator over the outgoing 
      line. When not running in C-Bit Parity mode, the txRai attribute is 
      also set to on when transmitting the far-end SEF/AIS defect 
      indicator on the outgoing line.
      The lofAlarm attribute is always set to off when the component has 
      been locked and left offline."
   DEFVAL     { off }
::= { mscLpDS3OperEntry 2 }

mscLpDS3RxAisAlarm OBJECT-TYPE
   SYNTAX     INTEGER  {
                 on(0),
                 off(1) }
   ACCESS     read-only
   STATUS     mandatory
   DESCRIPTION
     "This attribute displays whether an Alarm Indication Signal (AIS) 
      alarm state has been entered. An AIS alarm state is entered when 
      AIS defects have been observed and accumulated for 2.5 seconds +/
      - 0.5 seconds. An AIS defect is the occurrence of AIS (valid DS3 
      frame with payload containing the 1010...sequence and with C-Bits 
      set to zero) in contiguous M-frames for a time greater than 100 
      milliseconds. If the AIS defects are intermittently occurring, the 
      AIS defect accumulator is decremented at a rate of 1/10 of the 
      incrementing rate (alarm integration ratio of 1/10), with all 
      measurements based on a 200 ms polling cycle.
      The DS3 component goes into an operational state of disabled until 
      the AIS alarm condition is cleared (after AIS has been no longer 
      detected for a period of 10 seconds +/- 0.5 seconds). As long as AIS 
      is detected, the node also transmits the far-end SEF/AIS defect 
      indicator over the outgoing line. When not running in C-Bit Parity 
      mode, the txRai attribute is also set to on when transmitting the far-
      end SEF/AIS defect indicator on the outgoing line.
      The rxAisAlarm attribute is always set to off when the component 
      has been locked and left offline."
   DEFVAL     { off }
::= { mscLpDS3OperEntry 3 }

mscLpDS3RxRaiAlarm OBJECT-TYPE
   SYNTAX     INTEGER  {
                 on(0),
                 off(1) }
   ACCESS     read-only
   STATUS     mandatory
   DESCRIPTION
     "This attribute displays whether a Remote Alarm Indication (RAI) 
      alarm state has been entered. 
      When not running the C-Bit Parity mode, the RAI alarm state is 
      entered when the far-end SEF/AIS defect indicator has been 
      observed and accumulated for a period of 2.5 seconds +/- 0.5 
      seconds on the incoming DS3 line. If the RAI defects are 
      intermittently occurring, the RAI defect accumulator is 
      decremented at a rate of 1/10 of the incrementing rate (alarm 
      integration ratio of 1/10), with all measurements based on a 200 ms 
      polling cycle. The DS3 component goes into an operational state of 
      disabled until the RAI alarm condition is cleared. The condition is 
      cleared when the far-end SEF/AIS defect indicator has not been 
      detected for 10 seconds +/- 0.5 seconds. 
      When running the C-Bit Parity mode, the RAI alarm state is entered 
      upon detection of a far-end alarm over the Far-End Alarm and 
      Control (FEAC) channel. The RAI alarm state is exited as soon as 
      no more far-end alarm is detected on the FEAC channel. The far-
      end alarms that can be detected on the FEAC channel and that cause 
      the RAI alarm state to be entered are: equipment failure alarm 
      (service affecting), LOS alarm, LOF alarm, idle and AIS alarm.
      The rxRaiAlarm attribute is always set to off when the component 
      has been locked and left offline."
   DEFVAL     { off }
::= { mscLpDS3OperEntry 4 }

mscLpDS3RxIdle OBJECT-TYPE
   SYNTAX     INTEGER  {
                 on(0),
                 off(1) }
   ACCESS     read-only
   STATUS     mandatory
   DESCRIPTION
     "This attribute displays whether an Idle failure condition has been 
      reported on the DS3 port. An Idle condition is reported when DS3 
      Idle defects have been observed and accumulated for a period of 2.5 
      seconds +/- 0.5 seconds. The DS3 Idle defect is the occurrence of a 
      valid DS3 frame with the information bits set to a 11001100.. 
      sequence. If the DS3 Idle defects are intermittently occurring, the 
      DS3 Idle defect accumulator is decremented at a rate of 1/10 of the 
      incrementing rate (alarm integration ratio of 1/10), with all 
      measurements based on a 200 ms polling cycle.
      The DS3 component goes into an operational state of disabled until 
      the Idle failure condition is cleared. The failure condition is cleared 
      when the DS3 idle pattern has not been detected for at least 10 
      seconds +/- 0.5 seconds.
      The rxIdle attribute is always set to off when the component has 
      been locked and left offline.
      The idle pattern indicates that the far-end is physically connected 
      but not put in service. For instance, DS3 idle is transmitted on the 
      outgoing line when the DS3 component is locked and not used for 
      operational testing."
   DEFVAL     { off }
::= { mscLpDS3OperEntry 5 }

mscLpDS3TxAis OBJECT-TYPE
   SYNTAX     INTEGER  {
                 on(0),
                 off(1) }
   ACCESS     read-only
   STATUS     mandatory
   DESCRIPTION
     "This attribute displays whether an Alarm Indication Signal (AIS) 
      alarm is being transmitted on the DS3 line. Currently, AIS is never 
      transmitted by a Passport DS3 node."
   DEFVAL     { off }
::= { mscLpDS3OperEntry 6 }

mscLpDS3TxRai OBJECT-TYPE
   SYNTAX     INTEGER  {
                 on(0),
                 off(1) }
   ACCESS     read-only
   STATUS     mandatory
   DESCRIPTION
     "When not running C-Bit Parity mode, this attribute displays whether 
      the far-end SEF/AIS defect indicator is transmitted over the 
      outgoing line when the DS3 component has been unlocked or used 
      in operational testing. When running in C-Bit Parity mode, this 
      attribute displays whether a far-end alarm is sent over the Far-End 
      Alarm and Control (FEAC) channel when the DS3 component has 
      been unlocked or used in operational testing. When the DS3 
      component is locked and not used in operational testing, this 
      attribute is always set to off."
   DEFVAL     { off }
::= { mscLpDS3OperEntry 7 }

mscLpDS3TxIdle OBJECT-TYPE
   SYNTAX     INTEGER  {
                 on(0),
                 off(1) }
   ACCESS     read-only
   STATUS     mandatory
   DESCRIPTION
     "This attribute displays whether the DS3 Idle signal is transmitted 
      over the outgoing line. DS3 Idle is sent when the DS3 component 
      has been locked and not used in operational testing."
   DEFVAL     { off }
::= { mscLpDS3OperEntry 8 }

mscLpDS3StatsTable OBJECT-TYPE
   SYNTAX     SEQUENCE OF MscLpDS3StatsEntry
   ACCESS     not-accessible
   STATUS     mandatory
   DESCRIPTION
     "This group contains the specific DS3 common operational data for a 
      DS3 component. Each attribute type is a non-negative integer which 
      monotonically increases until it reaches a maximum value, at which 
      point it wraps around and starts increasing again from zero."
::= { mscLpDS3 17 }

mscLpDS3StatsEntry OBJECT-TYPE
   SYNTAX     MscLpDS3StatsEntry
   ACCESS     not-accessible
   STATUS     mandatory
   DESCRIPTION
     "An entry in the mscLpDS3StatsTable."
   INDEX {
      mscLpIndex,
      mscLpDS3Index }
::= { mscLpDS3StatsTable 1 }

MscLpDS3StatsEntry ::= SEQUENCE {
   mscLpDS3RunningTime
      Counter32,
   mscLpDS3ErrorFreeSec
      Counter32,
   mscLpDS3LineCodeViolations
      Counter32,
   mscLpDS3LineErroredSec
      Counter32,
   mscLpDS3LineSevErroredSec
      Counter32,
   mscLpDS3LineLosSec
      Counter32,
   mscLpDS3LineFailures
      Counter32,
   mscLpDS3PathCodeViolations
      Counter32,
   mscLpDS3PathErroredSec
      Counter32,
   mscLpDS3PathSevErroredSec
      Counter32,
   mscLpDS3PathSefAisSec
      Counter32,
   mscLpDS3PathUnavailSec
      Counter32,
   mscLpDS3PathFailures
      Counter32 }

mscLpDS3RunningTime OBJECT-TYPE
   SYNTAX     Counter32 
   ACCESS     read-only
   STATUS     mandatory
   DESCRIPTION
     "This attribute indicates the total number of seconds since the DS3 
      component has been activated and been in unlocked state or used 
      for operational testing. All the other error counts that follow as well 
      as each DS3 subcomponent's error counts can be updated when this 
      count is active."
::= { mscLpDS3StatsEntry 1 }

mscLpDS3ErrorFreeSec OBJECT-TYPE
   SYNTAX     Counter32 
   ACCESS     read-only
   STATUS     mandatory
   DESCRIPTION
     "This attribute indicates the number of seconds that the DS3 port has 
      been in an error free state."
::= { mscLpDS3StatsEntry 2 }

mscLpDS3LineCodeViolations OBJECT-TYPE
   SYNTAX     Counter32 
   ACCESS     read-only
   STATUS     mandatory
   DESCRIPTION
     "This attribute indicates the total number of Line Code Violations 
      (LCV) detected. A DS3 Line Code Violation is a B3Zs error. LCV 
      counting is inhibited for second intervals where Line Severely 
      Errored Second (LSES) is counted.
      This attribute is a non-negative integer which monotonically 
      increases until it reaches a maximum value, at which point it wraps 
      around and starts increasing again from zero."
::= { mscLpDS3StatsEntry 3 }

mscLpDS3LineErroredSec OBJECT-TYPE
   SYNTAX     Counter32 
   ACCESS     read-only
   STATUS     mandatory
   DESCRIPTION
     "This attribute indicates the total number of Line Errored Seconds 
      (LES) that have been counted. A LES is declared for second 
      intervals containing one or more LCV or one or more Loss Of 
      Signal (LOS) defects."
::= { mscLpDS3StatsEntry 4 }

mscLpDS3LineSevErroredSec OBJECT-TYPE
   SYNTAX     Counter32 
   ACCESS     read-only
   STATUS     mandatory
   DESCRIPTION
     "This attribute indicates the total number of Line Severely Errored 
      Seconds (LSES) that have been counted. A LSES is declared for 
      second intervals containing more than 44 LCVs or one or more 
      LOS defects."
::= { mscLpDS3StatsEntry 5 }

mscLpDS3LineLosSec OBJECT-TYPE
   SYNTAX     Counter32 
   ACCESS     read-only
   STATUS     mandatory
   DESCRIPTION
     "This attribute indicates the total number of Line LOS Seconds 
      (LOSS) that have been counted. A LOSS is declared for second 
      intervals containing one or more LOS defects."
::= { mscLpDS3StatsEntry 6 }

mscLpDS3LineFailures OBJECT-TYPE
   SYNTAX     Counter32 
   ACCESS     read-only
   STATUS     mandatory
   DESCRIPTION
     "This attribute indicates the total number of times that a line failure 
      (LOS failure) has been declared.
      This attribute is a non-negative integer which monotonically 
      increases until it reaches a maximum value, at which point it wraps 
      around and starts increasing again from zero."
::= { mscLpDS3StatsEntry 7 }

mscLpDS3PathCodeViolations OBJECT-TYPE
   SYNTAX     Counter32 
   ACCESS     read-only
   STATUS     mandatory
   DESCRIPTION
     "This attribute indicates the total number of Path Code Violations 
      (PCVs) detected. Each PCV corresponds to a P-bit parity error, or 
      possibly a frame error or a disagreement between P-bits or X-bits. 
      PCV counting is inhibited over second intervals where a Path 
      Severely Errored Second (PSES) is counted. Counting of PCVs is 
      also inhibited over second intervals where a Path Unavailable 
      Second (PUAS) is counted. 
      This attribute is a non-negative integer which monotonically 
      increases until it reaches a maximum value, at which point it wraps 
      around and starts increasing again from zero."
::= { mscLpDS3StatsEntry 8 }

mscLpDS3PathErroredSec OBJECT-TYPE
   SYNTAX     Counter32 
   ACCESS     read-only
   STATUS     mandatory
   DESCRIPTION
     "This attribute indicates the total number of Path Errored Seconds 
      (PESs) that have been counted. A PES is declared for second 
      intervals containing one or more Path Code Violations (PCV) or one 
      or more Severely Errored Frame (SEF) or Alarm Indication Signal 
      (AIS) defects. Counting of Path Errored Seconds is inhibited when 
      Path Unavailable Seconds (PUAS) is counted over the monitored 
      second."
::= { mscLpDS3StatsEntry 9 }

mscLpDS3PathSevErroredSec OBJECT-TYPE
   SYNTAX     Counter32 
   ACCESS     read-only
   STATUS     mandatory
   DESCRIPTION
     "This attribute indicates the total number of Path Severely Errored 
      Seconds (PSESs) that have been counted. A PSES is declared for 
      second intervals containing more than 44 PCVs or one or more SEF 
      or AIS defects. Counting of PSESs is inhibited when Path 
      Unavailable Seconds (PUAS) is counted over the monitored second."
::= { mscLpDS3StatsEntry 10 }

mscLpDS3PathSefAisSec OBJECT-TYPE
   SYNTAX     Counter32 
   ACCESS     read-only
   STATUS     mandatory
   DESCRIPTION
     "This attribute indicates the total number of SEF/AIS Seconds 
      (PSASs). A PSAS is declared for second intervals containing one or 
      more Severely Errored Frame (SEF) or Alarm Indication Signal 
      (AIS) defects. Counting of PSAS is inhibited when Path 
      Unavailable Seconds (PUAS) is counted over the monitored second."
::= { mscLpDS3StatsEntry 11 }

mscLpDS3PathUnavailSec OBJECT-TYPE
   SYNTAX     Counter32 
   ACCESS     read-only
   STATUS     mandatory
   DESCRIPTION
     "This attribute indicates the total number of one second intervals for 
      which the DS3 path is unavailable. The DS3 path becomes 
      unavailable at the onset of 10 consecutive Path Severely Errored 
      Seconds (PSES). The 10 PSESs are included in the unavailable 
      time. Once unavailable, the DS3 path becomes available at the onset 
      of 10 contiguous seconds with no PSES. The 10 seconds with no 
      PSES are excluded from the unavailable time. For second intervals 
      where PUAS is counted, counting of Path Coding Violations (PCV), 
      Path Errored Seconds (PES), Path Severely Errored Seconds (PSES) 
      and Path Sef/Ais Seconds (PSAS) is inhibited."
::= { mscLpDS3StatsEntry 12 }

mscLpDS3PathFailures OBJECT-TYPE
   SYNTAX     Counter32 
   ACCESS     read-only
   STATUS     mandatory
   DESCRIPTION
     "This attribute indicates the total number of times that a path failure 
      (LOF/AIS failure) has been declared.
      This attribute is a non-negative integer which monotonically 
      increases until it reaches a maximum value, at which point it wraps 
      around and starts increasing again from zero."
::= { mscLpDS3StatsEntry 13 }


-- 
-- The Test component is configured to control a hardware facility test 
-- on a physical (V35, X21, DS1, E1, DS3, E3 etc.) or a logical port.

mscLpDS3Test OBJECT IDENTIFIER ::= { mscLpDS3 2 }



mscLpDS3TestRowStatusTable OBJECT-TYPE
   SYNTAX     SEQUENCE OF MscLpDS3TestRowStatusEntry
   ACCESS     not-accessible
   STATUS     mandatory
   DESCRIPTION
     "This entry controls the addition and deletion of 
      mscLpDS3Test components."
::= { mscLpDS3Test 1 }

mscLpDS3TestRowStatusEntry OBJECT-TYPE
   SYNTAX     MscLpDS3TestRowStatusEntry
   ACCESS     not-accessible
   STATUS     mandatory
   DESCRIPTION
     "A single entry in the table represents a single 
      mscLpDS3Test component."
   INDEX {
      mscLpIndex,
      mscLpDS3Index,
      mscLpDS3TestIndex }
::= { mscLpDS3TestRowStatusTable 1 }

MscLpDS3TestRowStatusEntry ::= SEQUENCE {
   mscLpDS3TestRowStatus
      RowStatus,
   mscLpDS3TestComponentName
      DisplayString,
   mscLpDS3TestStorageType
      StorageType,
   mscLpDS3TestIndex
      NonReplicated }

mscLpDS3TestRowStatus OBJECT-TYPE
   SYNTAX     RowStatus 
   ACCESS     read-only
   STATUS     mandatory
   DESCRIPTION
     "This variable is used as the basis for SNMP naming of
      mscLpDS3Test components.
      These components cannot be added nor deleted."
::= { mscLpDS3TestRowStatusEntry 1 }

mscLpDS3TestComponentName OBJECT-TYPE
   SYNTAX     DisplayString 
   ACCESS     read-only
   STATUS     mandatory
   DESCRIPTION
     "This variable provides the component's string name for
      use with the ASCII Console Interface"
::= { mscLpDS3TestRowStatusEntry 2 }

mscLpDS3TestStorageType OBJECT-TYPE
   SYNTAX     StorageType 
   ACCESS     read-only
   STATUS     mandatory
   DESCRIPTION
     "This variable represents the storage type value for the
      mscLpDS3Test tables."
::= { mscLpDS3TestRowStatusEntry 4 }

mscLpDS3TestIndex OBJECT-TYPE
   SYNTAX     NonReplicated 
   ACCESS     not-accessible
   STATUS     mandatory
   DESCRIPTION
     "This variable represents the index for the mscLpDS3Test tables."
::= { mscLpDS3TestRowStatusEntry 10 }

mscLpDS3TestStateTable OBJECT-TYPE
   SYNTAX     SEQUENCE OF MscLpDS3TestStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscLpDS3Test 10 }

mscLpDS3TestStateEntry OBJECT-TYPE
   SYNTAX     MscLpDS3TestStateEntry
   ACCESS     not-accessible
   STATUS     mandatory
   DESCRIPTION
     "An entry in the mscLpDS3TestStateTable."
   INDEX {
      mscLpIndex,
      mscLpDS3Index,
      mscLpDS3TestIndex }
::= { mscLpDS3TestStateTable 1 }

MscLpDS3TestStateEntry ::= SEQUENCE {
   mscLpDS3TestAdminState
      INTEGER,
   mscLpDS3TestOperationalState
      INTEGER,
   mscLpDS3TestUsageState
      INTEGER }

mscLpDS3TestAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscLpDS3TestStateEntry 1 }

mscLpDS3TestOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscLpDS3TestStateEntry 2 }

mscLpDS3TestUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscLpDS3TestStateEntry 3 }

mscLpDS3TestSetupTable OBJECT-TYPE
   SYNTAX     SEQUENCE OF MscLpDS3TestSetupEntry
   ACCESS     not-accessible
   STATUS     mandatory
   DESCRIPTION
     "This group contains all of the operational data for a Test 
      component."
::= { mscLpDS3Test 11 }

mscLpDS3TestSetupEntry OBJECT-TYPE
   SYNTAX     MscLpDS3TestSetupEntry
   ACCESS     not-accessible
   STATUS     mandatory
   DESCRIPTION
     "An entry in the mscLpDS3TestSetupTable."
   INDEX {
      mscLpIndex,
      mscLpDS3Index,
      mscLpDS3TestIndex }
::= { mscLpDS3TestSetupTable 1 }

MscLpDS3TestSetupEntry ::= SEQUENCE {
   mscLpDS3TestPurpose
      AsciiString,
   mscLpDS3TestType
      INTEGER,
   mscLpDS3TestFrmSize
      Unsigned32,
   mscLpDS3TestFrmPatternType
      INTEGER,
   mscLpDS3TestCustomizedPattern
      Hex,
   mscLpDS3TestDataStartDelay
      Unsigned32,
   mscLpDS3TestDisplayInterval
      Unsigned32,
   mscLpDS3TestDuration
      Unsigned32 }

mscLpDS3TestPurpose OBJECT-TYPE
   SYNTAX     AsciiString (SIZE (0..40))
   ACCESS     read-write
   STATUS     mandatory
   DESCRIPTION
     "This attribute records the purpose of the test so that the test results 
      can be associated and properly analyzed."
::= { mscLpDS3TestSetupEntry 1 }

mscLpDS3TestType OBJECT-TYPE
   SYNTAX     INTEGER  {
                 card(0),
                 manual(1),
                 localLoop(2),
                 remoteLoop(3),
                 externalLoop(4),
                 payloadLoop(5),
                 remoteLoopThisTrib(6),
                 v54RemoteLoop(7),
                 pn127RemoteLoop(8) }
   ACCESS     read-write
   STATUS     mandatory
   DESCRIPTION
     "This attribute is the type of test to be run. The available test types 
      include the following:
      card test sets up an internal loop on the board and runs a bit error 
      rate test.
      manual test assumes the line is looped back externally and a bit 
      error rate test is performed.
      localLoop test loops back the local modem and performs a bit error 
      rate test.
      remoteLoop test loops back the remote modem (or CSU) and 
      performs a bit error rate test.
      externalLoop test loops back the line to the far end.
      payloadLoop test only loops back the payload data received from 
      the incoming line.
      remoteLoopThisTrib loops this particular tributary back at the far 
      end, using services provided by the parent.
      v54RemoteLoop initiates a V.54 Remote Loopback test.
      pn127RemoteLoop initiates a PN127 Remote Loopback test.
      Note that not all test types are not supported by all function 
      processors."
   DEFVAL     { card }
::= { mscLpDS3TestSetupEntry 2 }

mscLpDS3TestFrmSize OBJECT-TYPE
   SYNTAX     Unsigned32 (4..4096)
   ACCESS     read-write
   STATUS     mandatory
   DESCRIPTION
     "This attribute defines the size of the test data frames in number of 
      bytes."
   DEFVAL     { 1024 }
::= { mscLpDS3TestSetupEntry 3 }

mscLpDS3TestFrmPatternType OBJECT-TYPE
   SYNTAX     INTEGER  {
                 ccitt32kBitPattern(0),
                 ccitt8MBitPattern(1),
                 customizedPattern(2) }
   ACCESS     read-write
   STATUS     mandatory
   DESCRIPTION
     "This attribute defines the type of data pattern generation to use. The 
      following lists the available pattern types:
      ccitt32kBitPattern is a pseudo-random sequence of 32 kbit.
      ccitt8MBitPattern is a pseudo-random sequence of 8Mbit.
      customizedPattern is the pattern defined in the customizedPattern 
      attribute."
   DEFVAL     { ccitt32kBitPattern }
::= { mscLpDS3TestSetupEntry 4 }

mscLpDS3TestCustomizedPattern OBJECT-TYPE
   SYNTAX     Hex (0..4294967295)
   ACCESS     read-write
   STATUS     mandatory
   DESCRIPTION
     "This attribute allows a customized 32 bit pattern to be defined for 
      use in the test data frames. This attribute is used when the attribute 
      frmPatternType is set to CustomizedPattern. Note that a 55 hex 
      pattern is an alternating 1 and 0 pattern."
   DEFVAL     { 1431655765 }
::= { mscLpDS3TestSetupEntry 5 }

mscLpDS3TestDataStartDelay OBJECT-TYPE
   SYNTAX     Unsigned32 (0..1814400)
   ACCESS     read-write
   STATUS     mandatory
   DESCRIPTION
     "This attribute specifies the time delay (in seconds) between when 
      the test expects the loop to have been set up, to when the test data 
      actually starts to be transmitted. This attribute is to accommodate 
      some non-standard equipment that requires extra time for setting up 
      a requested loop.
      This attribute is ignored when the test type is set to externalLoop."
   DEFVAL     { 0 }
::= { mscLpDS3TestSetupEntry 6 }

mscLpDS3TestDisplayInterval OBJECT-TYPE
   SYNTAX     Unsigned32 (0..30240)
   ACCESS     read-write
   STATUS     mandatory
   DESCRIPTION
     "This attribute defines the interval (in minutes) between which 
      interim test results are to be displayed. Results are displayed at the 
      operator console at which the test was started. When the test type is 
      set to externalLoop, this attribute is ignored. There will be no 
      display of results if displayInterval is set to 0. This attribute can be 
      changed anytime."
   DEFVAL     { 5 }
::= { mscLpDS3TestSetupEntry 7 }

mscLpDS3TestDuration OBJECT-TYPE
   SYNTAX     Unsigned32 (1..30240)
   ACCESS     read-write
   STATUS     mandatory
   DESCRIPTION
     "This attribute is the duration (in minutes) that test data will be 
      transmitted. In the case of an externalLoop, this is the time that the 
      loop is in effect. Note that dataStartDelay does not apply to the 
      externalLoop."
   DEFVAL     { 1 }
::= { mscLpDS3TestSetupEntry 8 }

mscLpDS3TestResultsTable OBJECT-TYPE
   SYNTAX     SEQUENCE OF MscLpDS3TestResultsEntry
   ACCESS     not-accessible
   STATUS     mandatory
   DESCRIPTION
     "This group contains all the statistics related attributes of the Test 
      component."
::= { mscLpDS3Test 12 }

mscLpDS3TestResultsEntry OBJECT-TYPE
   SYNTAX     MscLpDS3TestResultsEntry
   ACCESS     not-accessible
   STATUS     mandatory
   DESCRIPTION
     "An entry in the mscLpDS3TestResultsTable."
   INDEX {
      mscLpIndex,
      mscLpDS3Index,
      mscLpDS3TestIndex }
::= { mscLpDS3TestResultsTable 1 }

MscLpDS3TestResultsEntry ::= SEQUENCE {
   mscLpDS3TestElapsedTime
      Counter32,
   mscLpDS3TestTimeRemaining
      Unsigned32,
   mscLpDS3TestCauseOfTermination
      INTEGER,
   mscLpDS3TestBitsTx
      PassportCounter64,
   mscLpDS3TestBytesTx
      PassportCounter64,
   mscLpDS3TestFrmTx
      PassportCounter64,
   mscLpDS3TestBitsRx
      PassportCounter64,
   mscLpDS3TestBytesRx
      PassportCounter64,
   mscLpDS3TestFrmRx
      PassportCounter64,
   mscLpDS3TestErroredFrmRx
      PassportCounter64,
   mscLpDS3TestBitErrorRate
      AsciiString }

mscLpDS3TestElapsedTime OBJECT-TYPE
   SYNTAX     Counter32 
   ACCESS     read-only
   STATUS     mandatory
   DESCRIPTION
     "This attribute is the number of minutes elapsed since the test started 
      for an externalLoop test. For a data test, this is the time since test 
      data was first transmitted."
::= { mscLpDS3TestResultsEntry 1 }

mscLpDS3TestTimeRemaining OBJECT-TYPE
   SYNTAX     Unsigned32 (0..4294967295)
   ACCESS     read-only
   STATUS     mandatory
   DESCRIPTION
     "This attribute is the number of minutes remaining before the test is 
      to be stopped according to the duration attribute."
   DEFVAL     { 0 }
::= { mscLpDS3TestResultsEntry 2 }

mscLpDS3TestCauseOfTermination OBJECT-TYPE
   SYNTAX     INTEGER  {
                 testTimeExpired(0),
                 stoppedByOperator(1),
                 unknown(2),
                 neverStarted(3),
                 testRunning(4),
                 hardwareReconfigured(5),
                 loopCodeSyncFailed(6),
                 patternSyncFailed(7),
                 patternSyncLost(8) }
   ACCESS     read-only
   STATUS     mandatory
   DESCRIPTION
     "This attribute indicates either the status of the test or the cause of 
      the test's termination:
      
      neverStarted indicates that the test has not yet been started.
      
      testRunning indicates that the test has been started.
      
      stoppedByOperator indicates that the operator issued a stop 
      command on a test that was running.
      
      testTimeExpired indicates that the test ran for the time specified by 
      the test's duration.
      
      loopCodeSyncFailed indicates that the local end failed to 
      synchronize to the loopCode pattern. The local end transmits the 
      loopCode pattern to cause the remote end to apply a loopback, after 
      which the local end should receive the loopCode pattern. The exact 
      pattern used to request loopCode depends on the test type. This 
      failure indicates a high rate of transmission errors, or that the 
      remote end has failed to apply the loopback.
      
      patternSyncFailed indicates that the local end failed to synchronize 
      to the frmPatternType test pattern, that should have been looped 
      back at the remote end. This failure indicates a high rate of 
      transmission errors or the absence of a loopback.
      
      patternSyncLost indicates that the local end gained and then lost 
      synchronization to the returned frmPatternType test pattern. This 
      failure indicates a sudden increase in transmission errors, frame 
      slippage, or the removal of an existing loopback.
      
      unknown is set when a reason to terminate other than those listed 
      here is encountered.
      
      Note: Only MSA cards support recognition of the failures 
      loopCodeSyncFailed, patternSyncFailed and patternSyncLost. 
      Other cards will not terminate the test under the conditions 
      described by these values."
   DEFVAL     { neverStarted }
::= { mscLpDS3TestResultsEntry 3 }

mscLpDS3TestBitsTx OBJECT-TYPE
   SYNTAX     PassportCounter64 
   ACCESS     read-only
   STATUS     mandatory
   DESCRIPTION
     "This attribute is the total number of bits sent during the test period. 
      As long as the line speed of the hardware interface is less than 
      70 Mbit/s, this counter is not expected to reach the maximum value."
::= { mscLpDS3TestResultsEntry 4 }

mscLpDS3TestBytesTx OBJECT-TYPE
   SYNTAX     PassportCounter64 
   ACCESS     read-only
   STATUS     mandatory
   DESCRIPTION
     "This attribute is the total number of bytes sent during the test 
      period. This counter is not expected to reach its maximum value."
::= { mscLpDS3TestResultsEntry 5 }

mscLpDS3TestFrmTx OBJECT-TYPE
   SYNTAX     PassportCounter64 
   ACCESS     read-only
   STATUS     mandatory
   DESCRIPTION
     "This attribute is the total number of frames sent during the test 
      period. This counter is not expected to reach its maximum value."
::= { mscLpDS3TestResultsEntry 6 }

mscLpDS3TestBitsRx OBJECT-TYPE
   SYNTAX     PassportCounter64 
   ACCESS     read-only
   STATUS     mandatory
   DESCRIPTION
     "This attribute is the total number of bits received during the test 
      period. This counter is not expected to reach its maximum value. 
      The counter will wrap around to 0 if it does reach the maximum 
      value."
::= { mscLpDS3TestResultsEntry 7 }

mscLpDS3TestBytesRx OBJECT-TYPE
   SYNTAX     PassportCounter64 
   ACCESS     read-only
   STATUS     mandatory
   DESCRIPTION
     "This attribute is the total number of bytes received during the test 
      period. This counter is not expected to reach its maximum value. 
      The counter will wrap around to 0 if it does reach its maximum 
      value."
::= { mscLpDS3TestResultsEntry 8 }

mscLpDS3TestFrmRx OBJECT-TYPE
   SYNTAX     PassportCounter64 
   ACCESS     read-only
   STATUS     mandatory
   DESCRIPTION
     "This attribute is the total number of frames received during the test 
      period. This counter is not expected to reach its maximum value. 
      The counter will wrap around to 0 if it does reach its maximum 
      value."
::= { mscLpDS3TestResultsEntry 9 }

mscLpDS3TestErroredFrmRx OBJECT-TYPE
   SYNTAX     PassportCounter64 
   ACCESS     read-only
   STATUS     mandatory
   DESCRIPTION
     "This attribute is not displayed for ATM cards because the physical 
      layer drops all errored frames at the controller interface. 
      
      For all other card types, this attribute is the total number of errored 
      frames received during the test period. This counter is not expected 
      to reach its maximum value. The counter will wrap around to 0 if it 
      does reach its maximum value."
::= { mscLpDS3TestResultsEntry 10 }

mscLpDS3TestBitErrorRate OBJECT-TYPE
   SYNTAX     AsciiString (SIZE (5))
   ACCESS     read-only
   STATUS     mandatory
   DESCRIPTION
     "This attribute is not displayed for ATM cards because the physical 
      layer drops all errored frames at the controller interface. 
      
      For all other card types, this attribute is the calculated bit error rate 
      on the link. Test data are generated and sent in frames of a preset 
      size (frameSize). The Test component will try to estimate the 
      number of bit errors in any errored frame which is identifiable. The 
      statistics will be updated accordingly. A lost frame (may be due to 
      an error on the flag sequence) will be discarded for the bit error rate 
      calculation. The result is presented in the form of xEsyy, where x is 
      the mantissa, syy is the exponent, for example 0E+00, 2E-09.
      Note that the bitErrorRate is an estimate only. For more reliable test 
      results, the test should be done over a long period. Multiple tests 
      would also improve the confidence level of the test results."
::= { mscLpDS3TestResultsEntry 11 }


-- Lp/n DS3/n CBIT
-- The CBIT component is configured to display all DS3 C-Bit parity 
-- related operational and statistical data. It will appear under the DS3 
-- component when the DS3 cbitParity attribute is set to on.

mscLpDS3CBit OBJECT IDENTIFIER ::= { mscLpDS3 3 }



mscLpDS3CBitRowStatusTable OBJECT-TYPE
   SYNTAX     SEQUENCE OF MscLpDS3CBitRowStatusEntry
   ACCESS     not-accessible
   STATUS     mandatory
   DESCRIPTION
     "This entry controls the addition and deletion of 
      mscLpDS3CBit components."
::= { mscLpDS3CBit 1 }

mscLpDS3CBitRowStatusEntry OBJECT-TYPE
   SYNTAX     MscLpDS3CBitRowStatusEntry
   ACCESS     not-accessible
   STATUS     mandatory
   DESCRIPTION
     "A single entry in the table represents a single 
      mscLpDS3CBit component."
   INDEX {
      mscLpIndex,
      mscLpDS3Index,
      mscLpDS3CBitIndex }
::= { mscLpDS3CBitRowStatusTable 1 }

MscLpDS3CBitRowStatusEntry ::= SEQUENCE {
   mscLpDS3CBitRowStatus
      RowStatus,
   mscLpDS3CBitComponentName
      DisplayString,
   mscLpDS3CBitStorageType
      StorageType,
   mscLpDS3CBitIndex
      NonReplicated }

mscLpDS3CBitRowStatus OBJECT-TYPE
   SYNTAX     RowStatus 
   ACCESS     read-only
   STATUS     mandatory
   DESCRIPTION
     "This variable is used as the basis for SNMP naming of
      mscLpDS3CBit components.
      These components cannot be added nor deleted."
::= { mscLpDS3CBitRowStatusEntry 1 }

mscLpDS3CBitComponentName OBJECT-TYPE
   SYNTAX     DisplayString 
   ACCESS     read-only
   STATUS     mandatory
   DESCRIPTION
     "This variable provides the component's string name for
      use with the ASCII Console Interface"
::= { mscLpDS3CBitRowStatusEntry 2 }

mscLpDS3CBitStorageType OBJECT-TYPE
   SYNTAX     StorageType 
   ACCESS     read-only
   STATUS     mandatory
   DESCRIPTION
     "This variable represents the storage type value for the
      mscLpDS3CBit tables."
::= { mscLpDS3CBitRowStatusEntry 4 }

mscLpDS3CBitIndex OBJECT-TYPE
   SYNTAX     NonReplicated 
   ACCESS     not-accessible
   STATUS     mandatory
   DESCRIPTION
     "This variable represents the index for the mscLpDS3CBit tables."
::= { mscLpDS3CBitRowStatusEntry 10 }

mscLpDS3CBitOperationalTable OBJECT-TYPE
   SYNTAX     SEQUENCE OF MscLpDS3CBitOperationalEntry
   ACCESS     not-accessible
   STATUS     mandatory
   DESCRIPTION
     "This group contains the DS3 C-Bit Parity operational data for the 
      CBIT component."
::= { mscLpDS3CBit 10 }

mscLpDS3CBitOperationalEntry OBJECT-TYPE
   SYNTAX     MscLpDS3CBitOperationalEntry
   ACCESS     not-accessible
   STATUS     mandatory
   DESCRIPTION
     "An entry in the mscLpDS3CBitOperationalTable."
   INDEX {
      mscLpIndex,
      mscLpDS3Index,
      mscLpDS3CBitIndex }
::= { mscLpDS3CBitOperationalTable 1 }

MscLpDS3CBitOperationalEntry ::= SEQUENCE {
   mscLpDS3CBitFarEndAlarm
      INTEGER,
   mscLpDS3CBitLoopedbackToFarEnd
      OCTET STRING,
   mscLpDS3CBitLoopbackAtFarEndRequested
      OCTET STRING }

mscLpDS3CBitFarEndAlarm OBJECT-TYPE
   SYNTAX     INTEGER  {
                 equipmentFailure(0),
                 los(1),
                 sef(2),
                 ais(3),
                 idle(4),
                 none(5) }
   ACCESS     read-only
   STATUS     mandatory
   DESCRIPTION
     "This attribute indicates the Far-End alarm signal that is currently 
      received at the DS3 interface. This signal is carried over the Far-
      End Alarm and Control (FEAC) bits of DS3 frames. Five far-end 
      alarm signals can be received: far-end equipment failure that is 
      received when the far-end terminal has detected a local equipment 
      failure; far-end Loss Of Signal (LOS) that is received when the far-
      end DS3 terminal has declared a LOS failure condition; far-end 
      Loss of Frame (LOF) when the far-end DS3 terminal has declared a 
      Loss Of Frame (LOF) failure condition; far-end Alarm Indication 
      Signal (AIS) when the far-end has declared an AIS failure 
      condition; far-end Idle when the far-end has declared an Idle signal 
      condition."
   DEFVAL     { none }
::= { mscLpDS3CBitOperationalEntry 1 }

mscLpDS3CBitLoopedbackToFarEnd OBJECT-TYPE
   SYNTAX     OCTET STRING (SIZE (4))
   ACCESS     read-only
   STATUS     mandatory
   DESCRIPTION
     "This indicates whether or not the DS3 component is currently 
      looping back the incoming DS3 signal or one of its DS1 tributaries 
      to the far-end DS3 terminal. This is activated when the far-end DS3 
      equipment has ordered the local terminal to do so.

      Description of bits:
      notused0(0)
      n1(1)
      n2(2)
      n3(3)
      n4(4)
      n5(5)
      n6(6)
      n7(7)
      n8(8)
      n9(9)
      n10(10)
      n11(11)
      n12(12)
      n13(13)
      n14(14)
      n15(15)
      n16(16)
      n17(17)
      n18(18)
      n19(19)
      n20(20)
      n21(21)
      n22(22)
      n23(23)
      n24(24)
      n25(25)
      n26(26)
      n27(27)
      n28(28)
      notused29(29)
      notused30(30)
      ds3Line(31)"
::= { mscLpDS3CBitOperationalEntry 2 }

mscLpDS3CBitLoopbackAtFarEndRequested OBJECT-TYPE
   SYNTAX     OCTET STRING (SIZE (4))
   ACCESS     read-only
   STATUS     mandatory
   DESCRIPTION
     "This attribute indicates which DS1 tributaries are being looped 
      back, or if the DS3 line is being looped back. Each value listed 
      indicates a loopback request has been made. When a loopback 
      deactivation command has been sent to the far end, the 
      corresponding value will be removed from the list.

      Description of bits:
      notused0(0)
      n1(1)
      n2(2)
      n3(3)
      n4(4)
      n5(5)
      n6(6)
      n7(7)
      n8(8)
      n9(9)
      n10(10)
      n11(11)
      n12(12)
      n13(13)
      n14(14)
      n15(15)
      n16(16)
      n17(17)
      n18(18)
      n19(19)
      n20(20)
      n21(21)
      n22(22)
      n23(23)
      n24(24)
      n25(25)
      n26(26)
      n27(27)
      n28(28)
      notused29(29)
      notused30(30)
      ds3Line(31)"
::= { mscLpDS3CBitOperationalEntry 3 }

mscLpDS3CBitStatsTable OBJECT-TYPE
   SYNTAX     SEQUENCE OF MscLpDS3CBitStatsEntry
   ACCESS     not-accessible
   STATUS     mandatory
   DESCRIPTION
     "This group contains the DS3 C-Bit Parity statistical data for the 
      CBIT component. Each attribute type is a non-negative integer 
      which monotonically increases until it reaches a maximum value, at 
      which point it wraps around and starts increasing again from zero."
::= { mscLpDS3CBit 11 }

mscLpDS3CBitStatsEntry OBJECT-TYPE
   SYNTAX     MscLpDS3CBitStatsEntry
   ACCESS     not-accessible
   STATUS     mandatory
   DESCRIPTION
     "An entry in the mscLpDS3CBitStatsTable."
   INDEX {
      mscLpIndex,
      mscLpDS3Index,
      mscLpDS3CBitIndex }
::= { mscLpDS3CBitStatsTable 1 }

MscLpDS3CBitStatsEntry ::= SEQUENCE {
   mscLpDS3CBitCbitErrorFreeSec
      Counter32,
   mscLpDS3CBitCbitCodeViolations
      Counter32,
   mscLpDS3CBitCbitErroredSec
      Counter32,
   mscLpDS3CBitCbitSevErroredSec
      Counter32,
   mscLpDS3CBitCbitUnavailSec
      Counter32,
   mscLpDS3CBitFarEndErrorFreeSec
      Counter32,
   mscLpDS3CBitFarEndCodeViolations
      Counter32,
   mscLpDS3CBitFarEndErroredSec
      Counter32,
   mscLpDS3CBitFarEndSevErroredSec
      Counter32,
   mscLpDS3CBitFarEndSefAisSec
      Counter32,
   mscLpDS3CBitFarEndUnavailSec
      Counter32,
   mscLpDS3CBitFarEndFailures
      Counter32 }

mscLpDS3CBitCbitErrorFreeSec OBJECT-TYPE
   SYNTAX     Counter32 
   ACCESS     read-only
   STATUS     mandatory
   DESCRIPTION
     "This attribute indicates the number of seconds that the DS3 port has 
      not suffered any C-Bit errors."
::= { mscLpDS3CBitStatsEntry 1 }

mscLpDS3CBitCbitCodeViolations OBJECT-TYPE
   SYNTAX     Counter32 
   ACCESS     read-only
   STATUS     mandatory
   DESCRIPTION
     "This attribute indicates the total count of C-Bit Parity Code 
      Violations (CCV). A CCV is obtained when the parity calculated 
      over the previous DS3 frame and the value of the CP-bits appearing 
      in the current DS3 frame differ. The value of this attribute will wrap 
      around to 0 if it does reach its maximum value. CCV counting is 
      inhibited for second intervals where C-Bit Parity Severely Errored 
      Seconds (CSES) are counted. It is also inhibited for second intervals 
      where C-Bit Unavailable Seconds (CUAS) are counted.
      This attribute is a non-negative integer which monotonically 
      increases until it reaches a maximum value, at which point it wraps 
      around and starts increasing again from zero."
::= { mscLpDS3CBitStatsEntry 2 }

mscLpDS3CBitCbitErroredSec OBJECT-TYPE
   SYNTAX     Counter32 
   ACCESS     read-only
   STATUS     mandatory
   DESCRIPTION
     "This attribute indicates the total number of C-Bit Parity Errored 
      Seconds (CES). A CES second is declared for second intervals 
      containing one or more CCVs or when one or more SEF (Severely 
      Errored Frame) or AIS (Alarm Indication Signal) defects.
      CES counting is inhibited for second intervals where C-Bit 
      Unavailable Seconds (CUAS) are counted."
::= { mscLpDS3CBitStatsEntry 3 }

mscLpDS3CBitCbitSevErroredSec OBJECT-TYPE
   SYNTAX     Counter32 
   ACCESS     read-only
   STATUS     mandatory
   DESCRIPTION
     "This attribute indicates the total number of C-Bit Parity Severely 
      Errored Seconds (CSES). A CSES is declared for second intervals 
      containing more than 44 CCVs or one or more SEF or AIS defects. 
      The occurrence of CSES in a one second interval causes the 
      inhibition of CCV counting during that second interval. CSES 
      counting is also inhibited for second intervals where C-Bit 
      Unavailable Seconds (CUAS) are counted."
::= { mscLpDS3CBitStatsEntry 4 }

mscLpDS3CBitCbitUnavailSec OBJECT-TYPE
   SYNTAX     Counter32 
   ACCESS     read-only
   STATUS     mandatory
   DESCRIPTION
     "This attribute indicates the total number of one second intervals for 
      which the DS3 path is unavailable. The DS3 path becomes 
      unavailable at the onset of 10 consecutive C-Bit Severely Errored 
      Seconds (CSES). The 10 CSESs are included in the unavailable 
      time. Once unavailable, the DS3 path becomes available at the onset 
      of 10 contiguous seconds with no CSES. The 10 seconds with no 
      CSES are excluded from the unavailable time. For second intervals 
      where CUAS is counted, counting of C-Bit Coding Violations 
      (CCV), C-Bit Errored Seconds (CES) and C-Bit Severely Errored 
      Seconds (CSES) is inhibited."
::= { mscLpDS3CBitStatsEntry 5 }

mscLpDS3CBitFarEndErrorFreeSec OBJECT-TYPE
   SYNTAX     Counter32 
   ACCESS     read-only
   STATUS     mandatory
   DESCRIPTION
     "This attribute indicates the number of seconds that the DS3 port has 
      not suffered of any far-end errors."
::= { mscLpDS3CBitStatsEntry 6 }

mscLpDS3CBitFarEndCodeViolations OBJECT-TYPE
   SYNTAX     Counter32 
   ACCESS     read-only
   STATUS     mandatory
   DESCRIPTION
     "This attribute indicates the total count of DS3 frames containing a 
      Coding Violation on the Far-End (FECV), also known as a Far-End 
      Block Error (FEBE). Each FEBE is reported over the FEBE bits 
      each time the far-end DS3 terminal detects a C-BIT Parity error 
      over a received DS3 frame. For second intervals where Far-End 
      Unavailable Seconds (FEAUS) or Far-End Severely Errored 
      Seconds (FESES) are counted, counting of FECVs is inhibited.
      This attribute is a non-negative integer which monotonically 
      increases until it reaches a maximum value, at which point it wraps 
      around and starts increasing again from zero."
::= { mscLpDS3CBitStatsEntry 7 }

mscLpDS3CBitFarEndErroredSec OBJECT-TYPE
   SYNTAX     Counter32 
   ACCESS     read-only
   STATUS     mandatory
   DESCRIPTION
     "This attribute indicates the total number of Far-End Errored 
      Seconds (FEES). A FEES is declared for second intervals 
      containing with one or more FECVs or one or more far-end SEF/
      AIS defects. A far-end SEF/AIS defect occurs when the X-Bits of 
      the DS3 frame are received as being set to zero. For second 
      intervals where Far-End Unavailable Seconds (FEUAS) are 
      counted, counting of FEESs is inhibited."
::= { mscLpDS3CBitStatsEntry 8 }

mscLpDS3CBitFarEndSevErroredSec OBJECT-TYPE
   SYNTAX     Counter32 
   ACCESS     read-only
   STATUS     mandatory
   DESCRIPTION
     "This attribute indicates the total number of Far-End Severely 
      Errored Seconds (FESES). A FESES is declared for second 
      intervals containing more than 44 FECVs or one or more far-end 
      SEF/AIS defects. For second intervals where a FESES is counted, 
      counting of FECVs is inhibited. For second intervals where Far-End 
      Unavailable Seconds (FEUAS) are counted, counting of FESESs is 
      inhibited."
::= { mscLpDS3CBitStatsEntry 9 }

mscLpDS3CBitFarEndSefAisSec OBJECT-TYPE
   SYNTAX     Counter32 
   ACCESS     read-only
   STATUS     mandatory
   DESCRIPTION
     "This attribute indicates the total number of Far-End SEF/AIS 
      Seconds (FESAS). A FESAS is declared for second intervals 
      containing one or more far-end SEF/AIS defects.For second 
      intervals where Far-End Unavailable Seconds (FEUAS) are 
      counted, counting of FESASs is inhibited."
::= { mscLpDS3CBitStatsEntry 10 }

mscLpDS3CBitFarEndUnavailSec OBJECT-TYPE
   SYNTAX     Counter32 
   ACCESS     read-only
   STATUS     mandatory
   DESCRIPTION
     "This attribute indicates the total number of one second intervals for 
      which the DS3 far-end path is unavailable. The DS3 far-end path 
      becomes unavailable at the onset of 10 consecutive Far-End 
      Severely Errored Seconds (FESES). The 10 FESESs are included in 
      the unavailable time. Once unavailable, the DS3 far-end path 
      becomes available at the onset of 10 contiguous seconds with no 
      FESES. The 10 seconds with no FESES are excluded from the 
      unavailable time. For second intervals where FEUAS is counted, 
      counting of Far-End Coding Violations (FECV), Far-End Errored 
      Seconds (FEES), Far-End Severely Errored Seconds (FESES) and 
      Far-End Sef/Ais Seconds (FESAS) is inhibited."
::= { mscLpDS3CBitStatsEntry 11 }

mscLpDS3CBitFarEndFailures OBJECT-TYPE
   SYNTAX     Counter32 
   ACCESS     read-only
   STATUS     mandatory
   DESCRIPTION
     "This attribute indicates the total number of times that a far-end path 
      failure (i.e. a Far-End SEF/AIS defect) has been declared.
      This attribute is a non-negative integer which monotonically 
      increases until it reaches a maximum value, at which point it wraps 
      around and starts increasing again from zero."
::= { mscLpDS3CBitStatsEntry 12 }


-- LP/n DS3/n PLCP
-- LP/n E3/n PLCP
-- The PLCP component is configured to display all DS3/E3 PLCP 
-- related operational and statistical data. It will appear under the DS3 
-- or E3 components when the mapping attribute is set to plcp.

mscLpDS3Plcp OBJECT IDENTIFIER ::= { mscLpDS3 4 }



mscLpDS3PlcpRowStatusTable OBJECT-TYPE
   SYNTAX     SEQUENCE OF MscLpDS3PlcpRowStatusEntry
   ACCESS     not-accessible
   STATUS     mandatory
   DESCRIPTION
     "This entry controls the addition and deletion of 
      mscLpDS3Plcp components."
::= { mscLpDS3Plcp 1 }

mscLpDS3PlcpRowStatusEntry OBJECT-TYPE
   SYNTAX     MscLpDS3PlcpRowStatusEntry
   ACCESS     not-accessible
   STATUS     mandatory
   DESCRIPTION
     "A single entry in the table represents a single 
      mscLpDS3Plcp component."
   INDEX {
      mscLpIndex,
      mscLpDS3Index,
      mscLpDS3PlcpIndex }
::= { mscLpDS3PlcpRowStatusTable 1 }

MscLpDS3PlcpRowStatusEntry ::= SEQUENCE {
   mscLpDS3PlcpRowStatus
      RowStatus,
   mscLpDS3PlcpComponentName
      DisplayString,
   mscLpDS3PlcpStorageType
      StorageType,
   mscLpDS3PlcpIndex
      NonReplicated }

mscLpDS3PlcpRowStatus OBJECT-TYPE
   SYNTAX     RowStatus 
   ACCESS     read-only
   STATUS     mandatory
   DESCRIPTION
     "This variable is used as the basis for SNMP naming of
      mscLpDS3Plcp components.
      These components cannot be added nor deleted."
::= { mscLpDS3PlcpRowStatusEntry 1 }

mscLpDS3PlcpComponentName OBJECT-TYPE
   SYNTAX     DisplayString 
   ACCESS     read-only
   STATUS     mandatory
   DESCRIPTION
     "This variable provides the component's string name for
      use with the ASCII Console Interface"
::= { mscLpDS3PlcpRowStatusEntry 2 }

mscLpDS3PlcpStorageType OBJECT-TYPE
   SYNTAX     StorageType 
   ACCESS     read-only
   STATUS     mandatory
   DESCRIPTION
     "This variable represents the storage type value for the
      mscLpDS3Plcp tables."
::= { mscLpDS3PlcpRowStatusEntry 4 }

mscLpDS3PlcpIndex OBJECT-TYPE
   SYNTAX     NonReplicated 
   ACCESS     not-accessible
   STATUS     mandatory
   DESCRIPTION
     "This variable represents the index for the mscLpDS3Plcp tables."
::= { mscLpDS3PlcpRowStatusEntry 10 }

mscLpDS3PlcpOperationalTable OBJECT-TYPE
   SYNTAX     SEQUENCE OF MscLpDS3PlcpOperationalEntry
   ACCESS     not-accessible
   STATUS     mandatory
   DESCRIPTION
     "This group contains the operational data for the PLCP component."
::= { mscLpDS3Plcp 10 }

mscLpDS3PlcpOperationalEntry OBJECT-TYPE
   SYNTAX     MscLpDS3PlcpOperationalEntry
   ACCESS     not-accessible
   STATUS     mandatory
   DESCRIPTION
     "An entry in the mscLpDS3PlcpOperationalTable."
   INDEX {
      mscLpIndex,
      mscLpDS3Index,
      mscLpDS3PlcpIndex }
::= { mscLpDS3PlcpOperationalTable 1 }

MscLpDS3PlcpOperationalEntry ::= SEQUENCE {
   mscLpDS3PlcpLofAlarm
      INTEGER,
   mscLpDS3PlcpRxRaiAlarm
      INTEGER }

mscLpDS3PlcpLofAlarm OBJECT-TYPE
   SYNTAX     INTEGER  {
                 on(0),
                 off(1) }
   ACCESS     read-only
   STATUS     mandatory
   DESCRIPTION
     "This attribute displays whether a PLCP Loss Of Frame (LOF) 
      failure alarm state has been entered. An LOF failure is declared 
      when a PLCP LOF defect persists for 2.5 s +/- 0.5 s. An LOF defect 
      occurs when an OOF (Out of Frame) state persists for more than 1 
      ms. If the OOF events are intermittent, the LOF defect counter is 
      decremented at a rate of 1/12 (for DS3 PLCP) or 1/9 (for G.751 E3 
      PLCP) of the incrementing rate, with all measurements based on a 
      200 ms polling cycle. An OOF event (also known as a PLCP SEF 
      event) is declared when an error is detected in both the A1 and A2 
      octets, or when two consecutive POHIDs are found in error.
      OOF is removed when two valid sets of framing octets and two 
      valid and sequential POHID octets have been found. The LOF 
      defect is removed when the defect counter reaches zero, i.e. when 
      OOF events are absent for more than 12 ms (DS3 PLCP) or 9 ms 
      (G.751 E3 PLCP). LOF failure alarm is cleared when LOF defect is 
      absent for 10.0 s +/- 0.5 s
      The DS3 or E3 component goes into an operational state of disabled 
      until the LOF failure alarm is cleared. The terminal declaring the 
      LOF failure alarm will transmit a PLCP RAI signal to the far-end 
      for the duration of the alarm.
      The lofAlarm attribute is always set to off when the DS3 or E3 
      component has been locked and left offline."
   DEFVAL     { off }
::= { mscLpDS3PlcpOperationalEntry 1 }

mscLpDS3PlcpRxRaiAlarm OBJECT-TYPE
   SYNTAX     INTEGER  {
                 on(0),
                 off(1) }
   ACCESS     read-only
   STATUS     mandatory
   DESCRIPTION
     "This attribute displays whether a PLCP Remote Alarm Indication 
      (RAI) failure alarm state has been entered. An RAI failure alarm 
      occurs when ten consecutive PLCP RAI bits (bit 5 in the G1 byte) 
      are high on the incoming line. An RAI failure alarm is cleared when 
      ten consecutive RAI bits are set to 0.
      Note: Some standards call this alarm RFI.
      The rxRaiAlarm attribute is always set to off when the DS3 or E3 
      component has been locked and left offline."
   DEFVAL     { off }
::= { mscLpDS3PlcpOperationalEntry 2 }

mscLpDS3PlcpStatsTable OBJECT-TYPE
   SYNTAX     SEQUENCE OF MscLpDS3PlcpStatsEntry
   ACCESS     not-accessible
   STATUS     mandatory
   DESCRIPTION
     "This group contains the statistical data for the PLCP component. 
      Each attribute type is a non-negative integer which monotonically 
      increases until it reaches a maximum value, at which point it wraps 
      around and starts increasing again from zero."
::= { mscLpDS3Plcp 11 }

mscLpDS3PlcpStatsEntry OBJECT-TYPE
   SYNTAX     MscLpDS3PlcpStatsEntry
   ACCESS     not-accessible
   STATUS     mandatory
   DESCRIPTION
     "An entry in the mscLpDS3PlcpStatsTable."
   INDEX {
      mscLpIndex,
      mscLpDS3Index,
      mscLpDS3PlcpIndex }
::= { mscLpDS3PlcpStatsTable 1 }

MscLpDS3PlcpStatsEntry ::= SEQUENCE {
   mscLpDS3PlcpErrorFreeSec
      Counter32,
   mscLpDS3PlcpCodingViolations
      Counter32,
   mscLpDS3PlcpErroredSec
      Counter32,
   mscLpDS3PlcpSevErroredSec
      Counter32,
   mscLpDS3PlcpSevErroredFramingSec
      Counter32,
   mscLpDS3PlcpUnavailSec
      Counter32,
   mscLpDS3PlcpFarEndErrorFreeSec
      Counter32,
   mscLpDS3PlcpFarEndCodingViolations
      Counter32,
   mscLpDS3PlcpFarEndErroredSec
      Counter32,
   mscLpDS3PlcpFarEndSevErroredSec
      Counter32,
   mscLpDS3PlcpFarEndUnavailableSec
      Counter32 }

mscLpDS3PlcpErrorFreeSec OBJECT-TYPE
   SYNTAX     Counter32 
   ACCESS     read-only
   STATUS     mandatory
   DESCRIPTION
     "This attribute indicates the number of seconds during which the 
      near-end PLCP path layer had no errors."
::= { mscLpDS3PlcpStatsEntry 1 }

mscLpDS3PlcpCodingViolations OBJECT-TYPE
   SYNTAX     Counter32 
   ACCESS     read-only
   STATUS     mandatory
   DESCRIPTION
     "This attribute indicates the total number of BIP-8 Errors, framing 
      pattern octet errors, and path overhead identification errors detected 
      in received PLCP frames. 
      Counting of PLCP CV is inhibited for second intervals where PLCP 
      Severely Errored Framing Seconds (SEFS) or PLCP Unavailable 
      Seconds (UAS) are counted.
      This attribute is a non-negative integer which monotonically 
      increases until it reaches a maximum value, at which point it wraps 
      around and starts increasing again from zero."
::= { mscLpDS3PlcpStatsEntry 2 }

mscLpDS3PlcpErroredSec OBJECT-TYPE
   SYNTAX     Counter32 
   ACCESS     read-only
   STATUS     mandatory
   DESCRIPTION
     "This attribute indicates the number of seconds containing one or 
      more PLCP Coding Violations (CV) or in which a PLCP Severely 
      Errored Framing Second (SEFS) was counted. 
      Counting of PLCP ES is inhibited during second intervals where 
      PLCP Unavailable Seconds (UAS) are counted."
::= { mscLpDS3PlcpStatsEntry 3 }

mscLpDS3PlcpSevErroredSec OBJECT-TYPE
   SYNTAX     Counter32 
   ACCESS     read-only
   STATUS     mandatory
   DESCRIPTION
     "This attribute indicates the number of seconds containing 5 or more 
      PLCPCVs or in which a PLCPSEFS was counted (i.e. a PLCP OOF 
      event occurred). 
      Counting of PLCP SES is inhibited during second intervals where 
      PLCP Unavailable Seconds (UAS) are counted."
::= { mscLpDS3PlcpStatsEntry 4 }

mscLpDS3PlcpSevErroredFramingSec OBJECT-TYPE
   SYNTAX     Counter32 
   ACCESS     read-only
   STATUS     mandatory
   DESCRIPTION
     "This attribute indicates the number of seconds containing one or 
      more PLCP Severely Errored Frame (SEF) events. An SEF event is 
      equivalent to a PLCP OOF (Out of Frame) event.
      Counting of PLCPP SEFSs is inhibited for second intervals where 
      PLCP Unavailable Seconds (UAS) are counted."
::= { mscLpDS3PlcpStatsEntry 5 }

mscLpDS3PlcpUnavailSec OBJECT-TYPE
   SYNTAX     Counter32 
   ACCESS     read-only
   STATUS     mandatory
   DESCRIPTION
     "This attribute indicates the number of seconds when the near-end 
      PLCP layer is unavailable. The PLCP Path Layer becomes 
      unavailable at the declaration of PLCP LOF (Loss of Frame) failure 
      alarm state. The PLCP Path Layer becomes available again only 
      after clearing this condition.
      For second intervals where PLCP UAS are counted, counting of 
      PLCP Severely Errored Framing Seconds (SEFS), PLCP Coding 
      Violations (CV), PLCP Errored Seconds (ES), PLCP Severely 
      Errored Seconds (SES) and PLCP Far-End Severely Errored 
      Seconds (FESES) is inhibited."
::= { mscLpDS3PlcpStatsEntry 6 }

mscLpDS3PlcpFarEndErrorFreeSec OBJECT-TYPE
   SYNTAX     Counter32 
   ACCESS     read-only
   STATUS     mandatory
   DESCRIPTION
     "This attribute indicates the number of seconds during which the far-
      end PLCP path layer had no errors."
::= { mscLpDS3PlcpStatsEntry 7 }

mscLpDS3PlcpFarEndCodingViolations OBJECT-TYPE
   SYNTAX     Counter32 
   ACCESS     read-only
   STATUS     mandatory
   DESCRIPTION
     "This attribute indicates the total number of PLCP Far-End Block 
      Errors (FEBE) reported by the far-end terminal. 
      Counting of FEBEs is inhibited for second intervals where PLCP 
      Far-End Unavailable Seconds (FEUAS) are counted.
      This attribute is a non-negative integer which monotonically 
      increases until it reaches a maximum value, at which point it wraps 
      around and starts increasing again from zero."
::= { mscLpDS3PlcpStatsEntry 8 }

mscLpDS3PlcpFarEndErroredSec OBJECT-TYPE
   SYNTAX     Counter32 
   ACCESS     read-only
   STATUS     mandatory
   DESCRIPTION
     "This attribute indicates the number of seconds containing one or 
      more PLCP Far-End Coding Violations (FECV).
      Counting of PLCP FEES is inhibited during second intervals where 
      PLCP Far-End Unavailable Seconds (FEUAS) are counted."
::= { mscLpDS3PlcpStatsEntry 9 }

mscLpDS3PlcpFarEndSevErroredSec OBJECT-TYPE
   SYNTAX     Counter32 
   ACCESS     read-only
   STATUS     mandatory
   DESCRIPTION
     "This attribute indicates the number of seconds containing 5 or more 
      PLCP Far-End Coding Violations (FECV). 
      Counting of PLCP FESES is inhibited for second intervals where 
      PLCP Far-End Unavailable Seconds (FEUAS) are counted."
::= { mscLpDS3PlcpStatsEntry 10 }

mscLpDS3PlcpFarEndUnavailableSec OBJECT-TYPE
   SYNTAX     Counter32 
   ACCESS     read-only
   STATUS     mandatory
   DESCRIPTION
     "This attribute indicates the number of seconds during which the 
      PLCP far end is unavailable. The PLCP Path Layer becomes 
      unavailable at the declaration of PLCP RAI (Remote Alarm 
      Indication). Service becomes available again after this condition is 
      cleared. For second intervals where PLCP FEUAS are counted, 
      counting of PLCP Far-End Coding Violations (FECV), PLCP Far-
      End Errored Seconds (FEES), and PLCP Far-End Severely Errored 
      Seconds (FESES) is inhibited."
::= { mscLpDS3PlcpStatsEntry 11 }


-- 
-- The AtmCell is a component that contains provisioning and 
-- operational attributes. The provisioning attributes are used to set the 
-- Loss of Cell Deliniation (LCD) alarm activation delay and to turn 
-- cell payload scrambling on or off. The operational attributes are 
-- used to report about the quality of the ATM cells received by the 
-- interface and the cell capacity utilization. The AtmCell component 
-- appears under all port components running on ATM cards.

mscLpDS3Cell OBJECT IDENTIFIER ::= { mscLpDS3 5 }



mscLpDS3CellRowStatusTable OBJECT-TYPE
   SYNTAX     SEQUENCE OF MscLpDS3CellRowStatusEntry
   ACCESS     not-accessible
   STATUS     mandatory
   DESCRIPTION
     "This entry controls the addition and deletion of 
      mscLpDS3Cell components."
::= { mscLpDS3Cell 1 }

mscLpDS3CellRowStatusEntry OBJECT-TYPE
   SYNTAX     MscLpDS3CellRowStatusEntry
   ACCESS     not-accessible
   STATUS     mandatory
   DESCRIPTION
     "A single entry in the table represents a single 
      mscLpDS3Cell component."
   INDEX {
      mscLpIndex,
      mscLpDS3Index,
      mscLpDS3CellIndex }
::= { mscLpDS3CellRowStatusTable 1 }

MscLpDS3CellRowStatusEntry ::= SEQUENCE {
   mscLpDS3CellRowStatus
      RowStatus,
   mscLpDS3CellComponentName
      DisplayString,
   mscLpDS3CellStorageType
      StorageType,
   mscLpDS3CellIndex
      NonReplicated }

mscLpDS3CellRowStatus OBJECT-TYPE
   SYNTAX     RowStatus 
   ACCESS     read-write
   STATUS     mandatory
   DESCRIPTION
     "This variable is used as the basis for SNMP naming of
      mscLpDS3Cell components.
      These components can be added and deleted."
::= { mscLpDS3CellRowStatusEntry 1 }

mscLpDS3CellComponentName OBJECT-TYPE
   SYNTAX     DisplayString 
   ACCESS     read-only
   STATUS     mandatory
   DESCRIPTION
     "This variable provides the component's string name for
      use with the ASCII Console Interface"
::= { mscLpDS3CellRowStatusEntry 2 }

mscLpDS3CellStorageType OBJECT-TYPE
   SYNTAX     StorageType 
   ACCESS     read-only
   STATUS     mandatory
   DESCRIPTION
     "This variable represents the storage type value for the
      mscLpDS3Cell tables."
::= { mscLpDS3CellRowStatusEntry 4 }

mscLpDS3CellIndex OBJECT-TYPE
   SYNTAX     NonReplicated 
   ACCESS     not-accessible
   STATUS     mandatory
   DESCRIPTION
     "This variable represents the index for the mscLpDS3Cell tables."
::= { mscLpDS3CellRowStatusEntry 10 }

mscLpDS3CellProvTable OBJECT-TYPE
   SYNTAX     SEQUENCE OF MscLpDS3CellProvEntry
   ACCESS     not-accessible
   STATUS     mandatory
   DESCRIPTION
     "This group contains the provisioning attributes for the AtmCell 
      component."
::= { mscLpDS3Cell 10 }

mscLpDS3CellProvEntry OBJECT-TYPE
   SYNTAX     MscLpDS3CellProvEntry
   ACCESS     not-accessible
   STATUS     mandatory
   DESCRIPTION
     "An entry in the mscLpDS3CellProvTable."
   INDEX {
      mscLpIndex,
      mscLpDS3Index,
      mscLpDS3CellIndex }
::= { mscLpDS3CellProvTable 1 }

MscLpDS3CellProvEntry ::= SEQUENCE {
   mscLpDS3CellAlarmActDelay
      Unsigned32,
   mscLpDS3CellScrambleCellPayload
      INTEGER,
   mscLpDS3CellCorrectSingleBitHeaderErrors
      INTEGER }

mscLpDS3CellAlarmActDelay OBJECT-TYPE
   SYNTAX     Unsigned32 (0..2000)
   ACCESS     read-write
   STATUS     mandatory
   DESCRIPTION
     "This attribute defines the time during which a Loss of Cell 
      Delineation (LCD) defect should be observed before declaring an 
      LCD alarm (alarm 70115501). The time is specified in milliseconds."
   DEFVAL     { 500 }
::= { mscLpDS3CellProvEntry 1 }

mscLpDS3CellScrambleCellPayload OBJECT-TYPE
   SYNTAX     INTEGER  {
                 off(0),
                 on(1) }
   ACCESS     read-write
   STATUS     mandatory
   DESCRIPTION
     "Cell scrambling, as defined by  ITU-T Recommendation I.432., can 
      provide a solution to the problem of transmission equipment which 
      is sensitive to certain bit patterns in the ATM cell payload. This 
      attribute controls whether or not the cell payload is scrambled.
      It defaults to off for DS1 interfaces, and on for all other interfaces.
      Note that this setting must be the same at both ends of the link."
::= { mscLpDS3CellProvEntry 2 }

mscLpDS3CellCorrectSingleBitHeaderErrors OBJECT-TYPE
   SYNTAX     INTEGER  {
                 off(0),
                 on(1) }
   ACCESS     read-write
   STATUS     mandatory
   DESCRIPTION
     "This attribute specifies whether the port corrects single bit errors 
      detected in the headers of received cells. If single bit errors are 
      corrected, the affected cells are passed up to the ATM layer 
      according to normal operation. If single bit errors are not corrected, 
      these errored cells are discarded by the physical layer. Note that 
      cells containing multiple bit errors in their headers are always 
      discarded.
      
      Single bit HEC error correction must remain off for the following 
      card types: 3pDS1Atm, 8pDS1Atm, 3pE1Atm, 8pE1Atm, 
      2pJ6MAtm, 3pDS3Atm, and 3pE3Atm."
   DEFVAL     { off }
::= { mscLpDS3CellProvEntry 3 }

mscLpDS3CellOperTable OBJECT-TYPE
   SYNTAX     SEQUENCE OF MscLpDS3CellOperEntry
   ACCESS     not-accessible
   STATUS     mandatory
   DESCRIPTION
     "This group contains the common operational attributes for the 
      AtmCell component."
::= { mscLpDS3Cell 11 }

mscLpDS3CellOperEntry OBJECT-TYPE
   SYNTAX     MscLpDS3CellOperEntry
   ACCESS     not-accessible
   STATUS     mandatory
   DESCRIPTION
     "An entry in the mscLpDS3CellOperTable."
   INDEX {
      mscLpIndex,
      mscLpDS3Index,
      mscLpDS3CellIndex }
::= { mscLpDS3CellOperTable 1 }

MscLpDS3CellOperEntry ::= SEQUENCE {
   mscLpDS3CellLcdAlarm
      INTEGER }

mscLpDS3CellLcdAlarm OBJECT-TYPE
   SYNTAX     INTEGER  {
                 on(0),
                 off(1) }
   ACCESS     read-only
   STATUS     mandatory
   DESCRIPTION
     "This attribute displays whether the Loss of Cell Delineation (LCD) 
      failure alarm state has been entered. This state is entered when LCD 
      defects have been observed and accumulated for a period of time 
      specified through the alarmActDelay attribute.
      In ATM cell direct mapping mode, an LCD defect occurs when Out 
      of Cell Delineation (OCD) anomaly persists for x milliseconds, and 
      disappears when the Out of Cell Delineation (OCD) is absent for x 
      msec. An OCD anomaly occurs when 7 consecutive incorrect HECs 
      have been detected. An OCD anomaly terminates when 6 
      consecutive correct HECs have been detected.
      For an AtmCell component located under a DS3 or E3 component 
      with mapping = PLCP, the LCD defect is directly derived from the 
      PLCP LOF defect.
      If LCD defects are intermittently occurring, the LCD defect 
      accumulator is decremented at a rate of 1/10 of the incrementing 
      rate (alarm integration ratio of 1/10), with all measurements based 
      on a 200 ms polling cycle
      The component under which is located the AtmCell component goes 
      into an operational state of disabled until the LCD alarm condition 
      is cleared. The condition is cleared after the LCD defect has not 
      been reported for a period of 10 seconds +/- 0.5 seconds.
      The lcdAlarm attribute is always set to off when the parent of the 
      AtmCell component has been locked and left offline. This can also 
      happen when the Path or Channel component has been suspended 
      since its parent has been locked."
   DEFVAL     { off }
::= { mscLpDS3CellOperEntry 1 }

mscLpDS3CellStatsTable OBJECT-TYPE
   SYNTAX     SEQUENCE OF MscLpDS3CellStatsEntry
   ACCESS     not-accessible
   STATUS     mandatory
   DESCRIPTION
     "This group contains the Statistics attribute for the AtmCell 
      component. Each attribute type is a non-negative integer which 
      monotonically increases until it reaches a maximum value, at which 
      point it wraps around and starts increasing again from zero."
::= { mscLpDS3Cell 12 }

mscLpDS3CellStatsEntry OBJECT-TYPE
   SYNTAX     MscLpDS3CellStatsEntry
   ACCESS     not-accessible
   STATUS     mandatory
   DESCRIPTION
     "An entry in the mscLpDS3CellStatsTable."
   INDEX {
      mscLpIndex,
      mscLpDS3Index,
      mscLpDS3CellIndex }
::= { mscLpDS3CellStatsTable 1 }

MscLpDS3CellStatsEntry ::= SEQUENCE {
   mscLpDS3CellUncorrectableHecErrors
      Counter32,
   mscLpDS3CellSevErroredSec
      Counter32,
   mscLpDS3CellReceiveCellUtilization
      Gauge32,
   mscLpDS3CellTransmitCellUtilization
      Gauge32,
   mscLpDS3CellCorrectableHeaderErrors
      Counter32 }

mscLpDS3CellUncorrectableHecErrors OBJECT-TYPE
   SYNTAX     Counter32 
   ACCESS     read-only
   STATUS     mandatory
   DESCRIPTION
     "This attribute indicates the number of uncorrectable ATM cell 
      header errors that have been detected. Counting of 
      uncorrectableHeaderErrors is inhibited when an Out of Cell 
      Delineation (OCD) defect is present. An OCD defect occurs when 
      seven consecutive incorrect HECs have been detected. An OCD 
      defect terminates when six consecutive correct HECs have been 
      detected."
::= { mscLpDS3CellStatsEntry 1 }

mscLpDS3CellSevErroredSec OBJECT-TYPE
   SYNTAX     Counter32 
   ACCESS     read-only
   STATUS     mandatory
   DESCRIPTION
     "This attribute indicates the total number of ATM Cell Severely 
      Errored Seconds (SESs) that have been counted. 
      
      In direct mapping mode, an ATM Cell SES is declared for second 
      intervals containing one or more Out of Cell Delineation (OCD) 
      defects. An OCD defect occurs when seven consecutive incorrect 
      HECs have been detected. An OCD defect terminates when six 
      consecutive correct HECs have been detected.
      
      In PLCP mapping mode, an ATM Cell SES is declared for second 
      intervals containing one or more PLCP LOF defects.
      
      Counting of uncorrectableHeaderErrors (ucErr) and 
      correctableHeaderErrors (cErr) is inhibited when the OCD defect 
      is present."
::= { mscLpDS3CellStatsEntry 2 }

mscLpDS3CellReceiveCellUtilization OBJECT-TYPE
   SYNTAX     Gauge32 (0..100)
   ACCESS     read-only
   STATUS     mandatory
   DESCRIPTION
     "This attribute is the ratio of the number of valid, assigned cells 
      received on the link to the nominal link capacity. The utilization is 
      calculated over a period of one minute.
      This attribute is always set to 0 when the parent of the AtmCell 
      component has been locked and left offline. This can also happen 
      when the Path or Channel component has been suspended since its 
      parent has been locked."
   DEFVAL     { 0 }
::= { mscLpDS3CellStatsEntry 3 }

mscLpDS3CellTransmitCellUtilization OBJECT-TYPE
   SYNTAX     Gauge32 (0..100)
   ACCESS     read-only
   STATUS     mandatory
   DESCRIPTION
     "This attribute is the ratio of the number of valid, assigned cells 
      transmitted on the link to the nominal link capacity. The utilization 
      is calculated over a period of one minute.
      This attribute is always set to 0 when the parent of the AtmCell 
      component has been locked and left offline. This can also happen 
      when the Path or Channel component has been suspended since its 
      parent has been locked."
   DEFVAL     { 0 }
::= { mscLpDS3CellStatsEntry 4 }

mscLpDS3CellCorrectableHeaderErrors OBJECT-TYPE
   SYNTAX     Counter32 
   ACCESS     read-only
   STATUS     mandatory
   DESCRIPTION
     "This attribute indicates the number of correctable ATM cell header 
      errors that have been detected and corrected. Counting of 
      correctableHeaderErrors is inhibited when an Out of Cell 
      Delineation (OCD) defect is present. An OCD defect occurs when 
      seven consecutive incorrect HECs have been detected. An OCD 
      defect terminates when six consecutive correct HECs have been 
      detected"
::= { mscLpDS3CellStatsEntry 5 }


-- Lp/n DS3/n DS1/n
-- The DS1 component controls and monitors a DS1 tributary of a 
-- channelized DS3 port on a Function Processor that supports 
-- channelization of a DS3.

mscLpDS3DS1 OBJECT IDENTIFIER ::= { mscLpDS3 6 }



mscLpDS3DS1RowStatusTable OBJECT-TYPE
   SYNTAX     SEQUENCE OF MscLpDS3DS1RowStatusEntry
   ACCESS     not-accessible
   STATUS     mandatory
   DESCRIPTION
     "This entry controls the addition and deletion of 
      mscLpDS3DS1 components."
::= { mscLpDS3DS1 1 }

mscLpDS3DS1RowStatusEntry OBJECT-TYPE
   SYNTAX     MscLpDS3DS1RowStatusEntry
   ACCESS     not-accessible
   STATUS     mandatory
   DESCRIPTION
     "A single entry in the table represents a single 
      mscLpDS3DS1 component."
   INDEX {
      mscLpIndex,
      mscLpDS3Index,
      mscLpDS3DS1Index }
::= { mscLpDS3DS1RowStatusTable 1 }

MscLpDS3DS1RowStatusEntry ::= SEQUENCE {
   mscLpDS3DS1RowStatus
      RowStatus,
   mscLpDS3DS1ComponentName
      DisplayString,
   mscLpDS3DS1StorageType
      StorageType,
   mscLpDS3DS1Index
      Integer32 }

mscLpDS3DS1RowStatus OBJECT-TYPE
   SYNTAX     RowStatus 
   ACCESS     read-write
   STATUS     mandatory
   DESCRIPTION
     "This variable is used as the basis for SNMP naming of
      mscLpDS3DS1 components.
      These components can be added and deleted."
::= { mscLpDS3DS1RowStatusEntry 1 }

mscLpDS3DS1ComponentName OBJECT-TYPE
   SYNTAX     DisplayString 
   ACCESS     read-only
   STATUS     mandatory
   DESCRIPTION
     "This variable provides the component's string name for
      use with the ASCII Console Interface"
::= { mscLpDS3DS1RowStatusEntry 2 }

mscLpDS3DS1StorageType OBJECT-TYPE
   SYNTAX     StorageType 
   ACCESS     read-only
   STATUS     mandatory
   DESCRIPTION
     "This variable represents the storage type value for the
      mscLpDS3DS1 tables."
::= { mscLpDS3DS1RowStatusEntry 4 }

mscLpDS3DS1Index OBJECT-TYPE
   SYNTAX     Integer32 (1..28)
   ACCESS     not-accessible
   STATUS     mandatory
   DESCRIPTION
     "This variable represents the index for the mscLpDS3DS1 tables."
::= { mscLpDS3DS1RowStatusEntry 10 }

mscLpDS3DS1ProvTable OBJECT-TYPE
   SYNTAX     SEQUENCE OF MscLpDS3DS1ProvEntry
   ACCESS     not-accessible
   STATUS     mandatory
   DESCRIPTION
     "This group contains all of the provisioning data for a DS1 
      component."
::= { mscLpDS3DS1 10 }

mscLpDS3DS1ProvEntry OBJECT-TYPE
   SYNTAX     MscLpDS3DS1ProvEntry
   ACCESS     not-accessible
   STATUS     mandatory
   DESCRIPTION
     "An entry in the mscLpDS3DS1ProvTable."
   INDEX {
      mscLpIndex,
      mscLpDS3Index,
      mscLpDS3DS1Index }
::= { mscLpDS3DS1ProvTable 1 }

MscLpDS3DS1ProvEntry ::= SEQUENCE {
   mscLpDS3DS1LineType
      INTEGER,
   mscLpDS3DS1ZeroCoding
      INTEGER,
   mscLpDS3DS1ClockingSource
      INTEGER }

mscLpDS3DS1LineType OBJECT-TYPE
   SYNTAX     INTEGER  {
                 d4(0),
                 esf(1),
                 d4Cas(4),
                 esfCas(5) }
   ACCESS     read-write
   STATUS     mandatory
   DESCRIPTION
     "This attribute defines the framing of the DS1 tributary.
      d4 defines a framing pattern of 12 frames per multiframe.
      esf defines a framing pattern of 24 frames per multiframe.
      d4Cas defines a framing pattern of 12 frames per multiframe with 
      channel associated signalling.
      esfCas defines a framing pattern of 24 frames per multiframe with 
      channel associated signalling.
      
      For the 4pDS3ChAtm card, only d4 and esf framing patterns are 
      permitted."
   DEFVAL     { esf }
::= { mscLpDS3DS1ProvEntry 1 }

mscLpDS3DS1ZeroCoding OBJECT-TYPE
   SYNTAX     INTEGER  {
                 bit7Stuffing(0),
                 none(3) }
   ACCESS     read-write
   STATUS     mandatory
   DESCRIPTION
     "This attribute defines the zero encoding on the DS1 tributary.
      bit7Stuffing sets bit 7 of every timeslot to a one to guarantee ones's 
      density. This reduces the available bandwidth of the channel by 1/8.
      none does no zero encoding."
   DEFVAL     { none }
::= { mscLpDS3DS1ProvEntry 2 }

mscLpDS3DS1ClockingSource OBJECT-TYPE
   SYNTAX     INTEGER  {
                 local(0),
                 line(1),
                 module(2) }
   ACCESS     read-write
   STATUS     mandatory
   DESCRIPTION
     "This attribute defines the source of the transmit clock for the DS1 
      tributary.
      When the clocking source is selected from local, the crystal on the 
      port generates the clocking for the DS1 tributary.
      When the clocking source is selected from line, the port 
      synchronizes to the clock from the DS1 tributary.
      When the clocking source is selected from module, the ports clock 
      synchronizes to the clock provided by the oscillator on the active 
      CP.
      On a 1pDS3C card, if the NetworkSynchronization (NS) component 
      is present the default value of this attribute will be module otherwise 
      it will be line.
      On a 2pDS3cAal or 4pDS3ChAtm card, the only valid values are 
      local and module. If the NS component is present the default value 
      of this attribute will be module otherwise it will be local.
      On a 4pDS3ChAtm card the clocking source for all DS1 and all 
      DS3 components on card must be the same, except when a DS1 is 
      using line as a clocking source."
::= { mscLpDS3DS1ProvEntry 3 }

mscLpDS3DS1CidDataTable OBJECT-TYPE
   SYNTAX     SEQUENCE OF MscLpDS3DS1CidDataEntry
   ACCESS     not-accessible
   STATUS     mandatory
   DESCRIPTION
     "This group contains the attribute for a component's Customer 
      Identifier (CID). Refer to the attribute description for a detailed 
      explanation of CIDs."
::= { mscLpDS3DS1 11 }

mscLpDS3DS1CidDataEntry OBJECT-TYPE
   SYNTAX     MscLpDS3DS1CidDataEntry
   ACCESS     not-accessible
   STATUS     mandatory
   DESCRIPTION
     "An entry in the mscLpDS3DS1CidDataTable."
   INDEX {
      mscLpIndex,
      mscLpDS3Index,
      mscLpDS3DS1Index }
::= { mscLpDS3DS1CidDataTable 1 }

MscLpDS3DS1CidDataEntry ::= SEQUENCE {
   mscLpDS3DS1CustomerIdentifier
      Unsigned32 }

mscLpDS3DS1CustomerIdentifier OBJECT-TYPE
   SYNTAX     Unsigned32 (0 | 1..8191)
   ACCESS     read-write
   STATUS     mandatory
   DESCRIPTION
     "This attribute holds the Customer Identifier (CID).
      
      Every component has a CID. If a component has a cid attribute, the 
      component's CID is the provisioned value of that attribute; 
      otherwise the component inherits the CID of its parent. The top-
      level component has a CID of 0.
      
      Every operator session also has a CID, which is the CID 
      provisioned for the operator's user ID. An operator will see only the 
      stream data for components having a matching CID. Also, the 
      operator will be allowed to issue commands for only those 
      components which have a matching CID.
      
      An operator CID of 0 is used to identify the Network Manager 
      (referred to as 'NetMan' in DPN). This CID matches the CID of 
      any component. Values 1 to 8191 inclusive (equivalent to 'basic 
      CIDs' in DPN) may be assigned to specific customers."
   DEFVAL     { 0 }
::= { mscLpDS3DS1CidDataEntry 1 }

mscLpDS3DS1AdminInfoTable OBJECT-TYPE
   SYNTAX     SEQUENCE OF MscLpDS3DS1AdminInfoEntry
   ACCESS     not-accessible
   STATUS     mandatory
   DESCRIPTION
     "This group contains the attributes pertaining to the vendor of the 
      equipment."
::= { mscLpDS3DS1 12 }

mscLpDS3DS1AdminInfoEntry OBJECT-TYPE
   SYNTAX     MscLpDS3DS1AdminInfoEntry
   ACCESS     not-accessible
   STATUS     mandatory
   DESCRIPTION
     "An entry in the mscLpDS3DS1AdminInfoTable."
   INDEX {
      mscLpIndex,
      mscLpDS3Index,
      mscLpDS3DS1Index }
::= { mscLpDS3DS1AdminInfoTable 1 }

MscLpDS3DS1AdminInfoEntry ::= SEQUENCE {
   mscLpDS3DS1Vendor
      AsciiString,
   mscLpDS3DS1CommentText
      AsciiString }

mscLpDS3DS1Vendor OBJECT-TYPE
   SYNTAX     AsciiString (SIZE (0..20))
   ACCESS     read-write
   STATUS     mandatory
   DESCRIPTION
     "This is the name of the vendor supplying the facility."
::= { mscLpDS3DS1AdminInfoEntry 1 }

mscLpDS3DS1CommentText OBJECT-TYPE
   SYNTAX     AsciiString (SIZE (0..60))
   ACCESS     read-write
   STATUS     mandatory
   DESCRIPTION
     "Any miscellaneous text about the facility."
::= { mscLpDS3DS1AdminInfoEntry 2 }

mscLpDS3DS1IfEntryTable OBJECT-TYPE
   SYNTAX     SEQUENCE OF MscLpDS3DS1IfEntryEntry
   ACCESS     not-accessible
   STATUS     mandatory
   DESCRIPTION
     "This group contains the provisionable attributes for the ifEntry."
::= { mscLpDS3DS1 13 }

mscLpDS3DS1IfEntryEntry OBJECT-TYPE
   SYNTAX     MscLpDS3DS1IfEntryEntry
   ACCESS     not-accessible
   STATUS     mandatory
   DESCRIPTION
     "An entry in the mscLpDS3DS1IfEntryTable."
   INDEX {
      mscLpIndex,
      mscLpDS3Index,
      mscLpDS3DS1Index }
::= { mscLpDS3DS1IfEntryTable 1 }

MscLpDS3DS1IfEntryEntry ::= SEQUENCE {
   mscLpDS3DS1IfAdminStatus
      INTEGER,
   mscLpDS3DS1IfIndex
      InterfaceIndex }

mscLpDS3DS1IfAdminStatus OBJECT-TYPE
   SYNTAX     INTEGER  {
                 up(1),
                 down(2),
                 testing(3) }
   ACCESS     read-write
   STATUS     mandatory
   DESCRIPTION
     "The desired state of the interface. The up state indicates the 
      interface is operational. The down state indicates the interface is not 
      operational. The testing state indicates that no operational packets 
      can be passed."
   DEFVAL     { up }
::= { mscLpDS3DS1IfEntryEntry 1 }

mscLpDS3DS1IfIndex OBJECT-TYPE
   SYNTAX     InterfaceIndex (1..65535)
   ACCESS     read-only
   STATUS     mandatory
   DESCRIPTION
     "This is the index for the IfEntry. Its value is automatically initialized 
      during the provisioning process."
::= { mscLpDS3DS1IfEntryEntry 2 }

mscLpDS3DS1OperStatusTable OBJECT-TYPE
   SYNTAX     SEQUENCE OF MscLpDS3DS1OperStatusEntry
   ACCESS     not-accessible
   STATUS     mandatory
   DESCRIPTION
     "This group includes the Operational Status attribute. This attribute 
      defines the current operational state of this component."
::= { mscLpDS3DS1 14 }

mscLpDS3DS1OperStatusEntry OBJECT-TYPE
   SYNTAX     MscLpDS3DS1OperStatusEntry
   ACCESS     not-accessible
   STATUS     mandatory
   DESCRIPTION
     "An entry in the mscLpDS3DS1OperStatusTable."
   INDEX {
      mscLpIndex,
      mscLpDS3Index,
      mscLpDS3DS1Index }
::= { mscLpDS3DS1OperStatusTable 1 }

MscLpDS3DS1OperStatusEntry ::= SEQUENCE {
   mscLpDS3DS1SnmpOperStatus
      INTEGER }

mscLpDS3DS1SnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { mscLpDS3DS1OperStatusEntry 1 }

mscLpDS3DS1StateTable OBJECT-TYPE
   SYNTAX     SEQUENCE OF MscLpDS3DS1StateEntry
   ACCESS     not-accessible
   STATUS     mandatory
   DESCRIPTION
     "This group contains the three OSI State attributes and the six OSI 
      Status attributes. The descriptions generically indicate what each 
      attribute implies about the component. Note that not all the values 
      and state combinations described here are supported by every 
      component which uses this group. For component-specific 
      information and the valid state combinations, refer to NTP 241-
      7001-150, Passport Operations and Maintenance Guide."
::= { mscLpDS3DS1 15 }

mscLpDS3DS1StateEntry OBJECT-TYPE
   SYNTAX     MscLpDS3DS1StateEntry
   ACCESS     not-accessible
   STATUS     mandatory
   DESCRIPTION
     "An entry in the mscLpDS3DS1StateTable."
   INDEX {
      mscLpIndex,
      mscLpDS3Index,
      mscLpDS3DS1Index }
::= { mscLpDS3DS1StateTable 1 }

MscLpDS3DS1StateEntry ::= SEQUENCE {
   mscLpDS3DS1AdminState
      INTEGER,
   mscLpDS3DS1OperationalState
      INTEGER,
   mscLpDS3DS1UsageState
      INTEGER,
   mscLpDS3DS1AvailabilityStatus
      OCTET STRING,
   mscLpDS3DS1ProceduralStatus
      OCTET STRING,
   mscLpDS3DS1ControlStatus
      OCTET STRING,
   mscLpDS3DS1AlarmStatus
      OCTET STRING,
   mscLpDS3DS1StandbyStatus
      INTEGER,
   mscLpDS3DS1UnknownStatus
      INTEGER }

mscLpDS3DS1AdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component.
      
      The OSI Status attributes, if supported by the component, may 
      provide more details, qualifying the state of the component."
   DEFVAL     { unlocked }
::= { mscLpDS3DS1StateEntry 1 }

mscLpDS3DS1OperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle.
      
      The OSI Status attributes, if supported by the component, may 
      provide more details, qualifying the state of the component."
   DEFVAL     { disabled }
::= { mscLpDS3DS1StateEntry 2 }

mscLpDS3DS1UsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time.
      
      The OSI Status attributes, if supported by the component, may 
      provide more details, qualifying the state of the component."
   DEFVAL     { idle }
::= { mscLpDS3DS1StateEntry 3 }

mscLpDS3DS1AvailabilityStatus OBJECT-TYPE
   SYNTAX     OCTET STRING (SIZE (2))
   ACCESS     read-only
   STATUS     mandatory
   DESCRIPTION
     "If supported by the component, this attribute indicates the OSI 
      Availability status of the component. Note that, even though it is 
      defined as a multi-valued set, at most one value is shown to the user.
      
      When no values are in the set, this indicates that either the attribute 
      is not supported or that none of the status conditions described 
      below are present.
      
      The value inTest indicates that the resource is undergoing a test 
      procedure. If adminState is locked or shuttingDown, the normal 
      users are precluded from using the resource and controlStatus is 
      reservedForTest. Tests that do not exclude additional users can be 
      present in any operational or administrative state but the 
      reservedForTest condition should not be present.
      
      The value failed indicates that the component has an internal fault 
      that prevents it from operating. The operationalState is disabled.
      
      The value dependency indicates that the component cannot operate 
      because some other resource on which it depends is unavailable. 
      The operationalState is disabled.
      
      The value powerOff indicates the resource requires power to be 
      applied and it is not powered on. The operationalState is disabled.
      
      The value offLine indicates the resource requires a routine 
      operation (either manual, automatic, or both) to be performed to 
      place it on-line and make it available for use. The operationalState 
      is disabled.
      
      The value offDuty indicates the resource is inactive in accordance 
      with a predetermined time schedule. In the absence of other 
      disabling conditions, the operationalState is enabled or disabled.
      
      The value degraded indicates the service provided by the 
      component is degraded in some way, such as in speed or operating 
      capacity. However, the resource remains available for service. The 
      operationalState is enabled.
      
      The value notInstalled indicates the resource is not present. The 
      operationalState is disabled.
      
      The value logFull is not used.

      Description of bits:
      inTest(0)
      failed(1)
      powerOff(2)
      offLine(3)
      offDuty(4)
      dependency(5)
      degraded(6)
      notInstalled(7)
      logFull(8)"
::= { mscLpDS3DS1StateEntry 4 }

mscLpDS3DS1ProceduralStatus OBJECT-TYPE
   SYNTAX     OCTET STRING (SIZE (1))
   ACCESS     read-only
   STATUS     mandatory
   DESCRIPTION
     "If supported by the component, this attribute indicates the OSI 
      Procedural status of the component. Note that, even though it is 
      defined as a multi-valued set, at most one value is shown to the user.
      
      When no values are in the set, this indicates that either the attribute 
      is not supported or that none of the status conditions described 
      below are present.
      
      The value initializationRequired indicates (for a resource which 
      doesn't initialize autonomously) that initialization is required before 
      it can perform its normal functions, and this procedure has not been 
      initiated. The operationalState is disabled.
      
      The value notInitialized indicates (for a resource which does 
      initialize autonomously) that initialization is required before it can 
      perform its normal functions, and this procedure has not been 
      initiated. The operationalState may be enabled or disabled.
      
      The value initializing indicates that initialization has been initiated 
      but is not yet complete. The operationalState may be enabled or 
      disabled.
      
      The value reporting indicates the resource has completed some 
      processing operation and is notifying the results. The 
      operationalState is enabled.
      
      The value terminating indicates the component is in a termination 
      phase. If the resource doesn't reinitialize autonomously, 
      operationalState is disabled; otherwise it is enabled or disabled.

      Description of bits:
      initializationRequired(0)
      notInitialized(1)
      initializing(2)
      reporting(3)
      terminating(4)"
::= { mscLpDS3DS1StateEntry 5 }

mscLpDS3DS1ControlStatus OBJECT-TYPE
   SYNTAX     OCTET STRING (SIZE (1))
   ACCESS     read-only
   STATUS     mandatory
   DESCRIPTION
     "If supported by the component, this attribute indicates the OSI 
      Control status of the component. Note that, even though it is defined 
      as a multi-valued set, at most one value is shown to the user.
      
      When no values are in the set, this indicates that either the attribute 
      is not supported or that none of the status conditions described 
      below are present.
      
      The value subjectToTest indicates the resource is available but tests 
      may be conducted simultaneously at unpredictable times, which 
      may cause it to exhibit unusual characteristics.
      
      The value partOfServicesLocked indicates that part of the service is 
      restricted from users of a resource. The adminState is unlocked.
      
      The value reservedForTest indicates that the component is 
      administratively unavailable because it is undergoing a test 
      procedure. The adminState is locked.
      
      The value suspended indicates that the service has been 
      administratively suspended.

      Description of bits:
      subjectToTest(0)
      partOfServicesLocked(1)
      reservedForTest(2)
      suspended(3)"
::= { mscLpDS3DS1StateEntry 6 }

mscLpDS3DS1AlarmStatus OBJECT-TYPE
   SYNTAX     OCTET STRING (SIZE (1))
   ACCESS     read-only
   STATUS     mandatory
   DESCRIPTION
     "If supported by the component, this attribute indicates the OSI 
      Alarm status of the component. Note that, even though it is defined 
      as a multi-valued set, at most one value is shown to the user.
      
      When no values are in the set, this indicates that either the attribute 
      is not supported or that none of the status conditions described 
      below are present.
      
      The value underRepair indicates the component is currently being 
      repaired. The operationalState is enabled or disabled.
      
      The value critical indicates one or more critical alarms are 
      outstanding against the component. Other, less severe, alarms may 
      also be outstanding. The operationalState is enabled or disabled.
      
      The value major indicates one or more major alarms are 
      outstanding against the component. Other, less severe, alarms may 
      also be outstanding. The operationalState is enabled or disabled.
      
      The value minor indicates one or more minor alarms are 
      outstanding against the component. Other, less severe, alarms may 
      also be outstanding. The operationalState is enabled or disabled.
      
      The value alarmOutstanding generically indicates that an alarm of 
      some severity is outstanding against the component.

      Description of bits:
      underRepair(0)
      critical(1)
      major(2)
      minor(3)
      alarmOutstanding(4)"
::= { mscLpDS3DS1StateEntry 7 }

mscLpDS3DS1StandbyStatus OBJECT-TYPE
   SYNTAX     INTEGER  {
                 hotStandby(0),
                 coldStandby(1),
                 providingService(2),
                 notSet(15) }
   ACCESS     read-only
   STATUS     mandatory
   DESCRIPTION
     "If supported by the component, this attribute indicates the OSI 
      Standby status of the component.
      
      The value notSet indicates that either the attribute is not supported 
      or that none of the status conditions described below are present. 
      Note that this is a non-standard value, used because the original 
      specification indicated this attribute was set-valued and thus, did not 
      provide a value to indicate that none of the other three are 
      applicable.
      
      The value hotStandby indicates that the resource is not providing 
      service but will be immediately able to take over the role of the 
      resource to be backed up, without initialization activity, and 
      containing the same information as the resource to be backed up.
      
      The value coldStandby indicates the resource is a backup for 
      another resource but will not be immediately able to take over the 
      role of the backed up resource and will require some initialization 
      activity.
      
      The value providingService indicates that this component, as a 
      backup resource, is currently backing up another resource."
   DEFVAL     { notSet }
::= { mscLpDS3DS1StateEntry 8 }

mscLpDS3DS1UnknownStatus OBJECT-TYPE
   SYNTAX     INTEGER  {
                 false(0),
                 true(1) }
   ACCESS     read-only
   STATUS     mandatory
   DESCRIPTION
     "This attribute indicates the OSI Unknown status of the component.
      
      The value false indicates that all of the other OSI State and Status 
      attribute values can be considered accurate.
      
      The value true indicates that the actual state of the component is not 
      known for sure."
   DEFVAL     { false }
::= { mscLpDS3DS1StateEntry 9 }

mscLpDS3DS1OperTable OBJECT-TYPE
   SYNTAX     SEQUENCE OF MscLpDS3DS1OperEntry
   ACCESS     not-accessible
   STATUS     mandatory
   DESCRIPTION
     "This group contains the common operational data for a component 
      in a digital hierarchy interface."
::= { mscLpDS3DS1 16 }

mscLpDS3DS1OperEntry OBJECT-TYPE
   SYNTAX     MscLpDS3DS1OperEntry
   ACCESS     not-accessible
   STATUS     mandatory
   DESCRIPTION
     "An entry in the mscLpDS3DS1OperTable."
   INDEX {
      mscLpIndex,
      mscLpDS3Index,
      mscLpDS3DS1Index }
::= { mscLpDS3DS1OperTable 1 }

MscLpDS3DS1OperEntry ::= SEQUENCE {
   mscLpDS3DS1RxAisAlarm
      INTEGER,
   mscLpDS3DS1LofAlarm
      INTEGER,
   mscLpDS3DS1RxRaiAlarm
      INTEGER,
   mscLpDS3DS1TxAisAlarm
      INTEGER,
   mscLpDS3DS1TxRaiAlarm
      INTEGER }

mscLpDS3DS1RxAisAlarm OBJECT-TYPE
   SYNTAX     INTEGER  {
                 on(0),
                 off(1) }
   ACCESS     read-only
   STATUS     mandatory
   DESCRIPTION
     "This attribute indicates whether an AIS (Alarm Indication Signal) 
      alarm state has been entered. The AIS Alarm state is entered when 
      AIS defects have been observed and accumulated for 2.5 seconds 
      +/- 0.5 seconds. An AIS defect is detected after having received less 
      than 3 zeros in a 2048 bit period. If the AIS defects are 
      intermittently occurring, the AIS defect accumulator is decremented 
      at a rate of 1/10 of the incrementing rate (alarm integration ratio of 
      1/10), with all measurements based on a 200 ms polling cycle. This 
      tributary goes into an operationalState of disabled for the duration 
      of an AIS alarm state.
      The AIS alarm state is cleared when AIS defects are absent for 10 
      seconds +/- 0.5 seconds."
   DEFVAL     { off }
::= { mscLpDS3DS1OperEntry 1 }

mscLpDS3DS1LofAlarm OBJECT-TYPE
   SYNTAX     INTEGER  {
                 on(0),
                 off(1) }
   ACCESS     read-only
   STATUS     mandatory
   DESCRIPTION
     "This attribute indicates whether a LOF (Loss of Frame) alarm state 
      has been entered. The LOF alarm state is entered when LOF defects 
      (2 out of 5 framing bits in error ) have been detected for 3 seconds 
      +/- 0.5 seconds. If the LOF defects are intermittently occurring, the 
      LOF defect accumulator is decremented at a rate of 1/10 of the 
      incrementing rate (alarm integration ratio of 1/10), with all 
      measurements based on a 200 ms polling cycle. This tributary goes 
      into an operationalState of disabled until the LOF alarm state is 
      cleared. Also, an RAI alarm is transmitted to the far end for the 
      duration of the LOF alarm state 
      The condition is cleared when framing has been achieved for 10 
      seconds +/- 0.5 seconds."
   DEFVAL     { off }
::= { mscLpDS3DS1OperEntry 2 }

mscLpDS3DS1RxRaiAlarm OBJECT-TYPE
   SYNTAX     INTEGER  {
                 on(0),
                 off(1) }
   ACCESS     read-only
   STATUS     mandatory
   DESCRIPTION
     "This attribute indicates whether an RAI (Remote Alarm Indication) 
      alarm state has been entered. An RAI alarm state is entered when 
      the RAI defect indicator has been observed and accumulated for 3.5 
      seconds +/- 0.5 seconds. If the RAI defects are intermittently 
      occurring, the RAI defect accumulator is decremented at a rate of 1/
      10 of the incrementing rate (alarm integration ratio of 1/10), with all 
      measurements based on a 200 ms polling cycle. 
      The RAI alarm state is cleared when the RAI defect indicator has 
      been absent for 10 seconds +/- 0.5 seconds. The RAI alarm is 
      usually an indication that the far end facility is unable to gain 
      synchronization."
   DEFVAL     { off }
::= { mscLpDS3DS1OperEntry 3 }

mscLpDS3DS1TxAisAlarm OBJECT-TYPE
   SYNTAX     INTEGER  {
                 on(0),
                 off(1) }
   ACCESS     read-only
   STATUS     mandatory
   DESCRIPTION
     "This attribute indicates whether an AIS (Alarm Indication Signal) 
      alarm is being transmitted on the line. An AIS alarm is transmitted 
      when the tributary is in a locked state."
   DEFVAL     { off }
::= { mscLpDS3DS1OperEntry 4 }

mscLpDS3DS1TxRaiAlarm OBJECT-TYPE
   SYNTAX     INTEGER  {
                 on(0),
                 off(1) }
   ACCESS     read-only
   STATUS     mandatory
   DESCRIPTION
     "This attribute indicates whether a RAI signal is being sent on the 
      outgoing line. The RAI signal is transmitted when the tributary 
      detects a LOF alarm condition."
   DEFVAL     { off }
::= { mscLpDS3DS1OperEntry 5 }

mscLpDS3DS1StatsTable OBJECT-TYPE
   SYNTAX     SEQUENCE OF MscLpDS3DS1StatsEntry
   ACCESS     not-accessible
   STATUS     mandatory
   DESCRIPTION
     "This group contains the common statistical data for a component in 
      a digital hierarchy interface."
::= { mscLpDS3DS1 17 }

mscLpDS3DS1StatsEntry OBJECT-TYPE
   SYNTAX     MscLpDS3DS1StatsEntry
   ACCESS     not-accessible
   STATUS     mandatory
   DESCRIPTION
     "An entry in the mscLpDS3DS1StatsTable."
   INDEX {
      mscLpIndex,
      mscLpDS3Index,
      mscLpDS3DS1Index }
::= { mscLpDS3DS1StatsTable 1 }

MscLpDS3DS1StatsEntry ::= SEQUENCE {
   mscLpDS3DS1RunningTime
      Counter32,
   mscLpDS3DS1ErrorFreeSec
      Counter32,
   mscLpDS3DS1ErroredSec
      Counter32,
   mscLpDS3DS1SevErroredSec
      Counter32,
   mscLpDS3DS1SevErroredFrmSec
      Counter32,
   mscLpDS3DS1UnavailSec
      Counter32,
   mscLpDS3DS1CrcErrors
      Counter32,
   mscLpDS3DS1FrmErrors
      Counter32,
   mscLpDS3DS1SlipErrors
      Counter32 }

mscLpDS3DS1RunningTime OBJECT-TYPE
   SYNTAX     Counter32 
   ACCESS     read-only
   STATUS     mandatory
   DESCRIPTION
     "This attribute counts the number of seconds since the tributary was 
      activated."
::= { mscLpDS3DS1StatsEntry 1 }

mscLpDS3DS1ErrorFreeSec OBJECT-TYPE
   SYNTAX     Counter32 
   ACCESS     read-only
   STATUS     mandatory
   DESCRIPTION
     "This attribute counts the number of seconds that the tributary has 
      been in an error free state."
::= { mscLpDS3DS1StatsEntry 2 }

mscLpDS3DS1ErroredSec OBJECT-TYPE
   SYNTAX     Counter32 
   ACCESS     read-only
   STATUS     mandatory
   DESCRIPTION
     "This attribute counts the number of errored seconds the tributary has 
      counted since it was activated. An errored second is declared when 
      a second with one or more Code Violation Error events, or one or 
      more Out Of Frame events occurs. A code violation error may be a 
      CRC error or a BPV error. An Out Of Frame event occurs when 2 
      out of 5 framing bits are in error."
::= { mscLpDS3DS1StatsEntry 3 }

mscLpDS3DS1SevErroredSec OBJECT-TYPE
   SYNTAX     Counter32 
   ACCESS     read-only
   STATUS     mandatory
   DESCRIPTION
     "This attribute counts the number of severely errored seconds the 
      tributary has counted since it was activated. A severely errored 
      second occurs when a second with 320 or more Code Violation 
      Error events or one or more Out Of Frame events occurs."
::= { mscLpDS3DS1StatsEntry 4 }

mscLpDS3DS1SevErroredFrmSec OBJECT-TYPE
   SYNTAX     Counter32 
   ACCESS     read-only
   STATUS     mandatory
   DESCRIPTION
     "This attribute counts the number of severely errored framing 
      seconds the tributary has counted since it was activated A severely 
      errored framing second occurs when a second with one or more Out 
      Of Frame events occurs."
::= { mscLpDS3DS1StatsEntry 5 }

mscLpDS3DS1UnavailSec OBJECT-TYPE
   SYNTAX     Counter32 
   ACCESS     read-only
   STATUS     mandatory
   DESCRIPTION
     "This attribute counts the total number of seconds that the tributary 
      has been in an unavailable signal state. An unavailable signal state 
      occurs at the onset of 10 consecutive Severely Errored Seconds. The 
      state is cleared at the onset of 10 seconds with no Severely Errored 
      Seconds."
::= { mscLpDS3DS1StatsEntry 6 }

mscLpDS3DS1CrcErrors OBJECT-TYPE
   SYNTAX     Counter32 
   ACCESS     read-only
   STATUS     mandatory
   DESCRIPTION
     "This attribute counts the total number of CRC-6 errors. These will 
      only be counted when the lineType is esf."
::= { mscLpDS3DS1StatsEntry 7 }

mscLpDS3DS1FrmErrors OBJECT-TYPE
   SYNTAX     Counter32 
   ACCESS     read-only
   STATUS     mandatory
   DESCRIPTION
     "This attribute counts the total number of frame errors. A frame error 
      is an error in the framing bits."
::= { mscLpDS3DS1StatsEntry 8 }

mscLpDS3DS1SlipErrors OBJECT-TYPE
   SYNTAX     Counter32 
   ACCESS     read-only
   STATUS     mandatory
   DESCRIPTION
     "The total number of times that the line experienced a controlled 
      frame slip."
::= { mscLpDS3DS1StatsEntry 9 }


-- Channel
-- The Channel component is configured to control a group of 
-- timeslots that form a fractional group on a DS1 or E1 port. 
-- Cell-based cards allow only one channel per port, and this is 
-- automatically provisioned with all available timeslots. Similarly, the 
-- 1pDS3C card type only allows one channel per port, and this is 
-- automatically provisioned with all available timeslots.

mscLpDS3DS1Chan OBJECT IDENTIFIER ::= { mscLpDS3DS1 2 }



mscLpDS3DS1ChanRowStatusTable OBJECT-TYPE
   SYNTAX     SEQUENCE OF MscLpDS3DS1ChanRowStatusEntry
   ACCESS     not-accessible
   STATUS     mandatory
   DESCRIPTION
     "This entry controls the addition and deletion of 
      mscLpDS3DS1Chan components."
::= { mscLpDS3DS1Chan 1 }

mscLpDS3DS1ChanRowStatusEntry OBJECT-TYPE
   SYNTAX     MscLpDS3DS1ChanRowStatusEntry
   ACCESS     not-accessible
   STATUS     mandatory
   DESCRIPTION
     "A single entry in the table represents a single 
      mscLpDS3DS1Chan component."
   INDEX {
      mscLpIndex,
      mscLpDS3Index,
      mscLpDS3DS1Index,
      mscLpDS3DS1ChanIndex }
::= { mscLpDS3DS1ChanRowStatusTable 1 }

MscLpDS3DS1ChanRowStatusEntry ::= SEQUENCE {
   mscLpDS3DS1ChanRowStatus
      RowStatus,
   mscLpDS3DS1ChanComponentName
      DisplayString,
   mscLpDS3DS1ChanStorageType
      StorageType,
   mscLpDS3DS1ChanIndex
      Integer32 }

mscLpDS3DS1ChanRowStatus OBJECT-TYPE
   SYNTAX     RowStatus 
   ACCESS     read-write
   STATUS     mandatory
   DESCRIPTION
     "This variable is used as the basis for SNMP naming of
      mscLpDS3DS1Chan components.
      These components can be added and deleted."
::= { mscLpDS3DS1ChanRowStatusEntry 1 }

mscLpDS3DS1ChanComponentName OBJECT-TYPE
   SYNTAX     DisplayString 
   ACCESS     read-only
   STATUS     mandatory
   DESCRIPTION
     "This variable provides the component's string name for
      use with the ASCII Console Interface"
::= { mscLpDS3DS1ChanRowStatusEntry 2 }

mscLpDS3DS1ChanStorageType OBJECT-TYPE
   SYNTAX     StorageType 
   ACCESS     read-only
   STATUS     mandatory
   DESCRIPTION
     "This variable represents the storage type value for the
      mscLpDS3DS1Chan tables."
::= { mscLpDS3DS1ChanRowStatusEntry 4 }

mscLpDS3DS1ChanIndex OBJECT-TYPE
   SYNTAX     Integer32 (0)
   ACCESS     not-accessible
   STATUS     mandatory
   DESCRIPTION
     "This variable represents the index for the mscLpDS3DS1Chan tables."
::= { mscLpDS3DS1ChanRowStatusEntry 10 }

mscLpDS3DS1ChanProvTable OBJECT-TYPE
   SYNTAX     SEQUENCE OF MscLpDS3DS1ChanProvEntry
   ACCESS     not-accessible
   STATUS     mandatory
   DESCRIPTION
     "This group contains all of the provisional data for a Channel 
      component."
::= { mscLpDS3DS1Chan 10 }

mscLpDS3DS1ChanProvEntry OBJECT-TYPE
   SYNTAX     MscLpDS3DS1ChanProvEntry
   ACCESS     not-accessible
   STATUS     mandatory
   DESCRIPTION
     "An entry in the mscLpDS3DS1ChanProvTable."
   INDEX {
      mscLpIndex,
      mscLpDS3Index,
      mscLpDS3DS1Index,
      mscLpDS3DS1ChanIndex }
::= { mscLpDS3DS1ChanProvTable 1 }

MscLpDS3DS1ChanProvEntry ::= SEQUENCE {
   mscLpDS3DS1ChanTimeslots
      OCTET STRING,
   mscLpDS3DS1ChanTimeslotDataRate
      INTEGER,
   mscLpDS3DS1ChanApplicationFramerName
      Link }

mscLpDS3DS1ChanTimeslots OBJECT-TYPE
   SYNTAX     OCTET STRING (SIZE (4))
   ACCESS     read-write
   STATUS     mandatory
   DESCRIPTION
     "This attribute contains the list of timeslots that are used by the 
      Channel component. Valid numbers are 1-24 for a Channel used by 
      a DS1 component, and 1-31 for a Channel used by an E1 
      component.

      Description of bits:
      notused0(0)
      n1(1)
      n2(2)
      n3(3)
      n4(4)
      n5(5)
      n6(6)
      n7(7)
      n8(8)
      n9(9)
      n10(10)
      n11(11)
      n12(12)
      n13(13)
      n14(14)
      n15(15)
      n16(16)
      n17(17)
      n18(18)
      n19(19)
      n20(20)
      n21(21)
      n22(22)
      n23(23)
      n24(24)
      n25(25)
      n26(26)
      n27(27)
      n28(28)
      n29(29)
      n30(30)
      n31(31)"
::= { mscLpDS3DS1ChanProvEntry 1 }

mscLpDS3DS1ChanTimeslotDataRate OBJECT-TYPE
   SYNTAX     INTEGER  {
                 n56k(0),
                 doNotOverride(1) }
   ACCESS     read-write
   STATUS     mandatory
   DESCRIPTION
     "This attribute selects the data rate of the timeslots in a channel of a 
      DS1 component. For E1, the data rate of the timeslots will always 
      be 64kbit/s regardless of this attribute.
      When doNotOverride is selected for a channel on a DS1, the data 
      rate of the channel's timeslots are dependant on the zeroCoding 
      selection of the DS1 component. If the zeroCoding is B8ZS (where 
      supported on the FP) or none, the timeslot's data rate will be 64kbit/
      s. If the zeroCoding option is bit7Stuffing, the data rate of a timeslot 
      will be 56kbit/s.
      When 56k is selected for a channel on a DS1, the least significant 
      bit of each timeslot of this Channel will always be set to 1 and not 
      used for data. The data rate for the timeslots of this channel is 
      therefore restricted to 56kbit/s.
      One application of this attribute is to allow a DS1 line to support 
      mixing channels that originate from lines that use different 
      zeroCoding schemes."
   DEFVAL     { doNotOverride }
::= { mscLpDS3DS1ChanProvEntry 2 }

mscLpDS3DS1ChanApplicationFramerName OBJECT-TYPE
   SYNTAX     Link 
   ACCESS     read-write
   STATUS     mandatory
   DESCRIPTION
     "This attribute defines the link to the software stack. It defines which 
      application is running on top of this hardware component."
::= { mscLpDS3DS1ChanProvEntry 3 }

mscLpDS3DS1ChanCidDataTable OBJECT-TYPE
   SYNTAX     SEQUENCE OF MscLpDS3DS1ChanCidDataEntry
   ACCESS     not-accessible
   STATUS     mandatory
   DESCRIPTION
     "This group contains the attribute for a component's Customer 
      Identifier (CID). Refer to the attribute description for a detailed 
      explanation of CIDs."
::= { mscLpDS3DS1Chan 11 }

mscLpDS3DS1ChanCidDataEntry OBJECT-TYPE
   SYNTAX     MscLpDS3DS1ChanCidDataEntry
   ACCESS     not-accessible
   STATUS     mandatory
   DESCRIPTION
     "An entry in the mscLpDS3DS1ChanCidDataTable."
   INDEX {
      mscLpIndex,
      mscLpDS3Index,
      mscLpDS3DS1Index,
      mscLpDS3DS1ChanIndex }
::= { mscLpDS3DS1ChanCidDataTable 1 }

MscLpDS3DS1ChanCidDataEntry ::= SEQUENCE {
   mscLpDS3DS1ChanCustomerIdentifier
      Unsigned32 }

mscLpDS3DS1ChanCustomerIdentifier OBJECT-TYPE
   SYNTAX     Unsigned32 (0 | 1..8191)
   ACCESS     read-write
   STATUS     mandatory
   DESCRIPTION
     "This attribute holds the Customer Identifier (CID).
      
      Every component has a CID. If a component has a cid attribute, the 
      component's CID is the provisioned value of that attribute; 
      otherwise the component inherits the CID of its parent. The top-
      level component has a CID of 0.
      
      Every operator session also has a CID, which is the CID 
      provisioned for the operator's user ID. An operator will see only the 
      stream data for components having a matching CID. Also, the 
      operator will be allowed to issue commands for only those 
      components which have a matching CID.
      
      An operator CID of 0 is used to identify the Network Manager 
      (referred to as 'NetMan' in DPN). This CID matches the CID of 
      any component. Values 1 to 8191 inclusive (equivalent to 'basic 
      CIDs' in DPN) may be assigned to specific customers."
   DEFVAL     { 0 }
::= { mscLpDS3DS1ChanCidDataEntry 1 }

mscLpDS3DS1ChanIfEntryTable OBJECT-TYPE
   SYNTAX     SEQUENCE OF MscLpDS3DS1ChanIfEntryEntry
   ACCESS     not-accessible
   STATUS     mandatory
   DESCRIPTION
     "This group contains the provisionable attributes for the ifEntry."
::= { mscLpDS3DS1Chan 12 }

mscLpDS3DS1ChanIfEntryEntry OBJECT-TYPE
   SYNTAX     MscLpDS3DS1ChanIfEntryEntry
   ACCESS     not-accessible
   STATUS     mandatory
   DESCRIPTION
     "An entry in the mscLpDS3DS1ChanIfEntryTable."
   INDEX {
      mscLpIndex,
      mscLpDS3Index,
      mscLpDS3DS1Index,
      mscLpDS3DS1ChanIndex }
::= { mscLpDS3DS1ChanIfEntryTable 1 }

MscLpDS3DS1ChanIfEntryEntry ::= SEQUENCE {
   mscLpDS3DS1ChanIfAdminStatus
      INTEGER,
   mscLpDS3DS1ChanIfIndex
      InterfaceIndex }

mscLpDS3DS1ChanIfAdminStatus OBJECT-TYPE
   SYNTAX     INTEGER  {
                 up(1),
                 down(2),
                 testing(3) }
   ACCESS     read-write
   STATUS     mandatory
   DESCRIPTION
     "The desired state of the interface. The up state indicates the 
      interface is operational. The down state indicates the interface is not 
      operational. The testing state indicates that no operational packets 
      can be passed."
   DEFVAL     { up }
::= { mscLpDS3DS1ChanIfEntryEntry 1 }

mscLpDS3DS1ChanIfIndex OBJECT-TYPE
   SYNTAX     InterfaceIndex (1..65535)
   ACCESS     read-only
   STATUS     mandatory
   DESCRIPTION
     "This is the index for the IfEntry. Its value is automatically initialized 
      during the provisioning process."
::= { mscLpDS3DS1ChanIfEntryEntry 2 }

mscLpDS3DS1ChanOperStatusTable OBJECT-TYPE
   SYNTAX     SEQUENCE OF MscLpDS3DS1ChanOperStatusEntry
   ACCESS     not-accessible
   STATUS     mandatory
   DESCRIPTION
     "This group includes the Operational Status attribute. This attribute 
      defines the current operational state of this component."
::= { mscLpDS3DS1Chan 13 }

mscLpDS3DS1ChanOperStatusEntry OBJECT-TYPE
   SYNTAX     MscLpDS3DS1ChanOperStatusEntry
   ACCESS     not-accessible
   STATUS     mandatory
   DESCRIPTION
     "An entry in the mscLpDS3DS1ChanOperStatusTable."
   INDEX {
      mscLpIndex,
      mscLpDS3Index,
      mscLpDS3DS1Index,
      mscLpDS3DS1ChanIndex }
::= { mscLpDS3DS1ChanOperStatusTable 1 }

MscLpDS3DS1ChanOperStatusEntry ::= SEQUENCE {
   mscLpDS3DS1ChanSnmpOperStatus
      INTEGER }

mscLpDS3DS1ChanSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { mscLpDS3DS1ChanOperStatusEntry 1 }

mscLpDS3DS1ChanStateTable OBJECT-TYPE
   SYNTAX     SEQUENCE OF MscLpDS3DS1ChanStateEntry
   ACCESS     not-accessible
   STATUS     mandatory
   DESCRIPTION
     "This group contains the three OSI State attributes and the six OSI 
      Status attributes. The descriptions generically indicate what each 
      attribute implies about the component. Note that not all the values 
      and state combinations described here are supported by every 
      component which uses this group. For component-specific 
      information and the valid state combinations, refer to NTP 241-
      7001-150, Passport Operations and Maintenance Guide."
::= { mscLpDS3DS1Chan 14 }

mscLpDS3DS1ChanStateEntry OBJECT-TYPE
   SYNTAX     MscLpDS3DS1ChanStateEntry
   ACCESS     not-accessible
   STATUS     mandatory
   DESCRIPTION
     "An entry in the mscLpDS3DS1ChanStateTable."
   INDEX {
      mscLpIndex,
      mscLpDS3Index,
      mscLpDS3DS1Index,
      mscLpDS3DS1ChanIndex }
::= { mscLpDS3DS1ChanStateTable 1 }

MscLpDS3DS1ChanStateEntry ::= SEQUENCE {
   mscLpDS3DS1ChanAdminState
      INTEGER,
   mscLpDS3DS1ChanOperationalState
      INTEGER,
   mscLpDS3DS1ChanUsageState
      INTEGER,
   mscLpDS3DS1ChanAvailabilityStatus
      OCTET STRING,
   mscLpDS3DS1ChanProceduralStatus
      OCTET STRING,
   mscLpDS3DS1ChanControlStatus
      OCTET STRING,
   mscLpDS3DS1ChanAlarmStatus
      OCTET STRING,
   mscLpDS3DS1ChanStandbyStatus
      INTEGER,
   mscLpDS3DS1ChanUnknownStatus
      INTEGER }

mscLpDS3DS1ChanAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component.
      
      The OSI Status attributes, if supported by the component, may 
      provide more details, qualifying the state of the component."
   DEFVAL     { unlocked }
::= { mscLpDS3DS1ChanStateEntry 1 }

mscLpDS3DS1ChanOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle.
      
      The OSI Status attributes, if supported by the component, may 
      provide more details, qualifying the state of the component."
   DEFVAL     { disabled }
::= { mscLpDS3DS1ChanStateEntry 2 }

mscLpDS3DS1ChanUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time.
      
      The OSI Status attributes, if supported by the component, may 
      provide more details, qualifying the state of the component."
   DEFVAL     { idle }
::= { mscLpDS3DS1ChanStateEntry 3 }

mscLpDS3DS1ChanAvailabilityStatus OBJECT-TYPE
   SYNTAX     OCTET STRING (SIZE (2))
   ACCESS     read-only
   STATUS     mandatory
   DESCRIPTION
     "If supported by the component, this attribute indicates the OSI 
      Availability status of the component. Note that, even though it is 
      defined as a multi-valued set, at most one value is shown to the user.
      
      When no values are in the set, this indicates that either the attribute 
      is not supported or that none of the status conditions described 
      below are present.
      
      The value inTest indicates that the resource is undergoing a test 
      procedure. If adminState is locked or shuttingDown, the normal 
      users are precluded from using the resource and controlStatus is 
      reservedForTest. Tests that do not exclude additional users can be 
      present in any operational or administrative state but the 
      reservedForTest condition should not be present.
      
      The value failed indicates that the component has an internal fault 
      that prevents it from operating. The operationalState is disabled.
      
      The value dependency indicates that the component cannot operate 
      because some other resource on which it depends is unavailable. 
      The operationalState is disabled.
      
      The value powerOff indicates the resource requires power to be 
      applied and it is not powered on. The operationalState is disabled.
      
      The value offLine indicates the resource requires a routine 
      operation (either manual, automatic, or both) to be performed to 
      place it on-line and make it available for use. The operationalState 
      is disabled.
      
      The value offDuty indicates the resource is inactive in accordance 
      with a predetermined time schedule. In the absence of other 
      disabling conditions, the operationalState is enabled or disabled.
      
      The value degraded indicates the service provided by the 
      component is degraded in some way, such as in speed or operating 
      capacity. However, the resource remains available for service. The 
      operationalState is enabled.
      
      The value notInstalled indicates the resource is not present. The 
      operationalState is disabled.
      
      The value logFull is not used.

      Description of bits:
      inTest(0)
      failed(1)
      powerOff(2)
      offLine(3)
      offDuty(4)
      dependency(5)
      degraded(6)
      notInstalled(7)
      logFull(8)"
::= { mscLpDS3DS1ChanStateEntry 4 }

mscLpDS3DS1ChanProceduralStatus OBJECT-TYPE
   SYNTAX     OCTET STRING (SIZE (1))
   ACCESS     read-only
   STATUS     mandatory
   DESCRIPTION
     "If supported by the component, this attribute indicates the OSI 
      Procedural status of the component. Note that, even though it is 
      defined as a multi-valued set, at most one value is shown to the user.
      
      When no values are in the set, this indicates that either the attribute 
      is not supported or that none of the status conditions described 
      below are present.
      
      The value initializationRequired indicates (for a resource which 
      doesn't initialize autonomously) that initialization is required before 
      it can perform its normal functions, and this procedure has not been 
      initiated. The operationalState is disabled.
      
      The value notInitialized indicates (for a resource which does 
      initialize autonomously) that initialization is required before it can 
      perform its normal functions, and this procedure has not been 
      initiated. The operationalState may be enabled or disabled.
      
      The value initializing indicates that initialization has been initiated 
      but is not yet complete. The operationalState may be enabled or 
      disabled.
      
      The value reporting indicates the resource has completed some 
      processing operation and is notifying the results. The 
      operationalState is enabled.
      
      The value terminating indicates the component is in a termination 
      phase. If the resource doesn't reinitialize autonomously, 
      operationalState is disabled; otherwise it is enabled or disabled.

      Description of bits:
      initializationRequired(0)
      notInitialized(1)
      initializing(2)
      reporting(3)
      terminating(4)"
::= { mscLpDS3DS1ChanStateEntry 5 }

mscLpDS3DS1ChanControlStatus OBJECT-TYPE
   SYNTAX     OCTET STRING (SIZE (1))
   ACCESS     read-only
   STATUS     mandatory
   DESCRIPTION
     "If supported by the component, this attribute indicates the OSI 
      Control status of the component. Note that, even though it is defined 
      as a multi-valued set, at most one value is shown to the user.
      
      When no values are in the set, this indicates that either the attribute 
      is not supported or that none of the status conditions described 
      below are present.
      
      The value subjectToTest indicates the resource is available but tests 
      may be conducted simultaneously at unpredictable times, which 
      may cause it to exhibit unusual characteristics.
      
      The value partOfServicesLocked indicates that part of the service is 
      restricted from users of a resource. The adminState is unlocked.
      
      The value reservedForTest indicates that the component is 
      administratively unavailable because it is undergoing a test 
      procedure. The adminState is locked.
      
      The value suspended indicates that the service has been 
      administratively suspended.

      Description of bits:
      subjectToTest(0)
      partOfServicesLocked(1)
      reservedForTest(2)
      suspended(3)"
::= { mscLpDS3DS1ChanStateEntry 6 }

mscLpDS3DS1ChanAlarmStatus OBJECT-TYPE
   SYNTAX     OCTET STRING (SIZE (1))
   ACCESS     read-only
   STATUS     mandatory
   DESCRIPTION
     "If supported by the component, this attribute indicates the OSI 
      Alarm status of the component. Note that, even though it is defined 
      as a multi-valued set, at most one value is shown to the user.
      
      When no values are in the set, this indicates that either the attribute 
      is not supported or that none of the status conditions described 
      below are present.
      
      The value underRepair indicates the component is currently being 
      repaired. The operationalState is enabled or disabled.
      
      The value critical indicates one or more critical alarms are 
      outstanding against the component. Other, less severe, alarms may 
      also be outstanding. The operationalState is enabled or disabled.
      
      The value major indicates one or more major alarms are 
      outstanding against the component. Other, less severe, alarms may 
      also be outstanding. The operationalState is enabled or disabled.
      
      The value minor indicates one or more minor alarms are 
      outstanding against the component. Other, less severe, alarms may 
      also be outstanding. The operationalState is enabled or disabled.
      
      The value alarmOutstanding generically indicates that an alarm of 
      some severity is outstanding against the component.

      Description of bits:
      underRepair(0)
      critical(1)
      major(2)
      minor(3)
      alarmOutstanding(4)"
::= { mscLpDS3DS1ChanStateEntry 7 }

mscLpDS3DS1ChanStandbyStatus OBJECT-TYPE
   SYNTAX     INTEGER  {
                 hotStandby(0),
                 coldStandby(1),
                 providingService(2),
                 notSet(15) }
   ACCESS     read-only
   STATUS     mandatory
   DESCRIPTION
     "If supported by the component, this attribute indicates the OSI 
      Standby status of the component.
      
      The value notSet indicates that either the attribute is not supported 
      or that none of the status conditions described below are present. 
      Note that this is a non-standard value, used because the original 
      specification indicated this attribute was set-valued and thus, did not 
      provide a value to indicate that none of the other three are 
      applicable.
      
      The value hotStandby indicates that the resource is not providing 
      service but will be immediately able to take over the role of the 
      resource to be backed up, without initialization activity, and 
      containing the same information as the resource to be backed up.
      
      The value coldStandby indicates the resource is a backup for 
      another resource but will not be immediately able to take over the 
      role of the backed up resource and will require some initialization 
      activity.
      
      The value providingService indicates that this component, as a 
      backup resource, is currently backing up another resource."
   DEFVAL     { notSet }
::= { mscLpDS3DS1ChanStateEntry 8 }

mscLpDS3DS1ChanUnknownStatus OBJECT-TYPE
   SYNTAX     INTEGER  {
                 false(0),
                 true(1) }
   ACCESS     read-only
   STATUS     mandatory
   DESCRIPTION
     "This attribute indicates the OSI Unknown status of the component.
      
      The value false indicates that all of the other OSI State and Status 
      attribute values can be considered accurate.
      
      The value true indicates that the actual state of the component is not 
      known for sure."
   DEFVAL     { false }
::= { mscLpDS3DS1ChanStateEntry 9 }

mscLpDS3DS1ChanOperTable OBJECT-TYPE
   SYNTAX     SEQUENCE OF MscLpDS3DS1ChanOperEntry
   ACCESS     not-accessible
   STATUS     mandatory
   DESCRIPTION
     "This group contains all of the operational data for a Channel 
      component."
::= { mscLpDS3DS1Chan 15 }

mscLpDS3DS1ChanOperEntry OBJECT-TYPE
   SYNTAX     MscLpDS3DS1ChanOperEntry
   ACCESS     not-accessible
   STATUS     mandatory
   DESCRIPTION
     "An entry in the mscLpDS3DS1ChanOperTable."
   INDEX {
      mscLpIndex,
      mscLpDS3Index,
      mscLpDS3DS1Index,
      mscLpDS3DS1ChanIndex }
::= { mscLpDS3DS1ChanOperTable 1 }

MscLpDS3DS1ChanOperEntry ::= SEQUENCE {
   mscLpDS3DS1ChanActualChannelSpeed
      Gauge32 }

mscLpDS3DS1ChanActualChannelSpeed OBJECT-TYPE
   SYNTAX     Gauge32 (0..4294967295)
   ACCESS     read-only
   STATUS     mandatory
   DESCRIPTION
     "This attribute displays the measured link speed of the Channel 
      component."
   DEFVAL     { 0 }
::= { mscLpDS3DS1ChanOperEntry 1 }

mscLpDS3DS1ChanAdminInfoTable OBJECT-TYPE
   SYNTAX     SEQUENCE OF MscLpDS3DS1ChanAdminInfoEntry
   ACCESS     not-accessible
   STATUS     mandatory
   DESCRIPTION
     "This group contains the attributes pertaining to the vendor of the 
      equipment."
::= { mscLpDS3DS1Chan 16 }

mscLpDS3DS1ChanAdminInfoEntry OBJECT-TYPE
   SYNTAX     MscLpDS3DS1ChanAdminInfoEntry
   ACCESS     not-accessible
   STATUS     mandatory
   DESCRIPTION
     "An entry in the mscLpDS3DS1ChanAdminInfoTable."
   INDEX {
      mscLpIndex,
      mscLpDS3Index,
      mscLpDS3DS1Index,
      mscLpDS3DS1ChanIndex }
::= { mscLpDS3DS1ChanAdminInfoTable 1 }

MscLpDS3DS1ChanAdminInfoEntry ::= SEQUENCE {
   mscLpDS3DS1ChanVendor
      AsciiString,
   mscLpDS3DS1ChanCommentText
      AsciiString }

mscLpDS3DS1ChanVendor OBJECT-TYPE
   SYNTAX     AsciiString (SIZE (0..20))
   ACCESS     read-write
   STATUS     mandatory
   DESCRIPTION
     "This is the name of the vendor supplying the facility."
::= { mscLpDS3DS1ChanAdminInfoEntry 1 }

mscLpDS3DS1ChanCommentText OBJECT-TYPE
   SYNTAX     AsciiString (SIZE (0..60))
   ACCESS     read-write
   STATUS     mandatory
   DESCRIPTION
     "Any miscellaneous text about the facility."
::= { mscLpDS3DS1ChanAdminInfoEntry 2 }


-- 
-- The Test component is configured to control a hardware facility test 
-- on a physical (V35, X21, DS1, E1, DS3, E3 etc.) or a logical port.

mscLpDS3DS1ChanTest OBJECT IDENTIFIER ::= { mscLpDS3DS1Chan 2 }



mscLpDS3DS1ChanTestRowStatusTable OBJECT-TYPE
   SYNTAX     SEQUENCE OF MscLpDS3DS1ChanTestRowStatusEntry
   ACCESS     not-accessible
   STATUS     mandatory
   DESCRIPTION
     "This entry controls the addition and deletion of 
      mscLpDS3DS1ChanTest components."
::= { mscLpDS3DS1ChanTest 1 }

mscLpDS3DS1ChanTestRowStatusEntry OBJECT-TYPE
   SYNTAX     MscLpDS3DS1ChanTestRowStatusEntry
   ACCESS     not-accessible
   STATUS     mandatory
   DESCRIPTION
     "A single entry in the table represents a single 
      mscLpDS3DS1ChanTest component."
   INDEX {
      mscLpIndex,
      mscLpDS3Index,
      mscLpDS3DS1Index,
      mscLpDS3DS1ChanIndex,
      mscLpDS3DS1ChanTestIndex }
::= { mscLpDS3DS1ChanTestRowStatusTable 1 }

MscLpDS3DS1ChanTestRowStatusEntry ::= SEQUENCE {
   mscLpDS3DS1ChanTestRowStatus
      RowStatus,
   mscLpDS3DS1ChanTestComponentName
      DisplayString,
   mscLpDS3DS1ChanTestStorageType
      StorageType,
   mscLpDS3DS1ChanTestIndex
      NonReplicated }

mscLpDS3DS1ChanTestRowStatus OBJECT-TYPE
   SYNTAX     RowStatus 
   ACCESS     read-only
   STATUS     mandatory
   DESCRIPTION
     "This variable is used as the basis for SNMP naming of
      mscLpDS3DS1ChanTest components.
      These components cannot be added nor deleted."
::= { mscLpDS3DS1ChanTestRowStatusEntry 1 }

mscLpDS3DS1ChanTestComponentName OBJECT-TYPE
   SYNTAX     DisplayString 
   ACCESS     read-only
   STATUS     mandatory
   DESCRIPTION
     "This variable provides the component's string name for
      use with the ASCII Console Interface"
::= { mscLpDS3DS1ChanTestRowStatusEntry 2 }

mscLpDS3DS1ChanTestStorageType OBJECT-TYPE
   SYNTAX     StorageType 
   ACCESS     read-only
   STATUS     mandatory
   DESCRIPTION
     "This variable represents the storage type value for the
      mscLpDS3DS1ChanTest tables."
::= { mscLpDS3DS1ChanTestRowStatusEntry 4 }

mscLpDS3DS1ChanTestIndex OBJECT-TYPE
   SYNTAX     NonReplicated 
   ACCESS     not-accessible
   STATUS     mandatory
   DESCRIPTION
     "This variable represents the index for the mscLpDS3DS1ChanTest tables."
::= { mscLpDS3DS1ChanTestRowStatusEntry 10 }

mscLpDS3DS1ChanTestStateTable OBJECT-TYPE
   SYNTAX     SEQUENCE OF MscLpDS3DS1ChanTestStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscLpDS3DS1ChanTest 10 }

mscLpDS3DS1ChanTestStateEntry OBJECT-TYPE
   SYNTAX     MscLpDS3DS1ChanTestStateEntry
   ACCESS     not-accessible
   STATUS     mandatory
   DESCRIPTION
     "An entry in the mscLpDS3DS1ChanTestStateTable."
   INDEX {
      mscLpIndex,
      mscLpDS3Index,
      mscLpDS3DS1Index,
      mscLpDS3DS1ChanIndex,
      mscLpDS3DS1ChanTestIndex }
::= { mscLpDS3DS1ChanTestStateTable 1 }

MscLpDS3DS1ChanTestStateEntry ::= SEQUENCE {
   mscLpDS3DS1ChanTestAdminState
      INTEGER,
   mscLpDS3DS1ChanTestOperationalState
      INTEGER,
   mscLpDS3DS1ChanTestUsageState
      INTEGER }

mscLpDS3DS1ChanTestAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscLpDS3DS1ChanTestStateEntry 1 }

mscLpDS3DS1ChanTestOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscLpDS3DS1ChanTestStateEntry 2 }

mscLpDS3DS1ChanTestUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscLpDS3DS1ChanTestStateEntry 3 }

mscLpDS3DS1ChanTestSetupTable OBJECT-TYPE
   SYNTAX     SEQUENCE OF MscLpDS3DS1ChanTestSetupEntry
   ACCESS     not-accessible
   STATUS     mandatory
   DESCRIPTION
     "This group contains all of the operational data for a Test 
      component."
::= { mscLpDS3DS1ChanTest 11 }

mscLpDS3DS1ChanTestSetupEntry OBJECT-TYPE
   SYNTAX     MscLpDS3DS1ChanTestSetupEntry
   ACCESS     not-accessible
   STATUS     mandatory
   DESCRIPTION
     "An entry in the mscLpDS3DS1ChanTestSetupTable."
   INDEX {
      mscLpIndex,
      mscLpDS3Index,
      mscLpDS3DS1Index,
      mscLpDS3DS1ChanIndex,
      mscLpDS3DS1ChanTestIndex }
::= { mscLpDS3DS1ChanTestSetupTable 1 }

MscLpDS3DS1ChanTestSetupEntry ::= SEQUENCE {
   mscLpDS3DS1ChanTestPurpose
      AsciiString,
   mscLpDS3DS1ChanTestType
      INTEGER,
   mscLpDS3DS1ChanTestFrmSize
      Unsigned32,
   mscLpDS3DS1ChanTestFrmPatternType
      INTEGER,
   mscLpDS3DS1ChanTestCustomizedPattern
      Hex,
   mscLpDS3DS1ChanTestDataStartDelay
      Unsigned32,
   mscLpDS3DS1ChanTestDisplayInterval
      Unsigned32,
   mscLpDS3DS1ChanTestDuration
      Unsigned32 }

mscLpDS3DS1ChanTestPurpose OBJECT-TYPE
   SYNTAX     AsciiString (SIZE (0..40))
   ACCESS     read-write
   STATUS     mandatory
   DESCRIPTION
     "This attribute records the purpose of the test so that the test results 
      can be associated and properly analyzed."
::= { mscLpDS3DS1ChanTestSetupEntry 1 }

mscLpDS3DS1ChanTestType OBJECT-TYPE
   SYNTAX     INTEGER  {
                 card(0),
                 manual(1),
                 localLoop(2),
                 remoteLoop(3),
                 externalLoop(4),
                 payloadLoop(5),
                 remoteLoopThisTrib(6),
                 v54RemoteLoop(7),
                 pn127RemoteLoop(8) }
   ACCESS     read-write
   STATUS     mandatory
   DESCRIPTION
     "This attribute is the type of test to be run. The available test types 
      include the following:
      card test sets up an internal loop on the board and runs a bit error 
      rate test.
      manual test assumes the line is looped back externally and a bit 
      error rate test is performed.
      localLoop test loops back the local modem and performs a bit error 
      rate test.
      remoteLoop test loops back the remote modem (or CSU) and 
      performs a bit error rate test.
      externalLoop test loops back the line to the far end.
      payloadLoop test only loops back the payload data received from 
      the incoming line.
      remoteLoopThisTrib loops this particular tributary back at the far 
      end, using services provided by the parent.
      v54RemoteLoop initiates a V.54 Remote Loopback test.
      pn127RemoteLoop initiates a PN127 Remote Loopback test.
      Note that not all test types are not supported by all function 
      processors."
   DEFVAL     { card }
::= { mscLpDS3DS1ChanTestSetupEntry 2 }

mscLpDS3DS1ChanTestFrmSize OBJECT-TYPE
   SYNTAX     Unsigned32 (4..4096)
   ACCESS     read-write
   STATUS     mandatory
   DESCRIPTION
     "This attribute defines the size of the test data frames in number of 
      bytes."
   DEFVAL     { 1024 }
::= { mscLpDS3DS1ChanTestSetupEntry 3 }

mscLpDS3DS1ChanTestFrmPatternType OBJECT-TYPE
   SYNTAX     INTEGER  {
                 ccitt32kBitPattern(0),
                 ccitt8MBitPattern(1),
                 customizedPattern(2) }
   ACCESS     read-write
   STATUS     mandatory
   DESCRIPTION
     "This attribute defines the type of data pattern generation to use. The 
      following lists the available pattern types:
      ccitt32kBitPattern is a pseudo-random sequence of 32 kbit.
      ccitt8MBitPattern is a pseudo-random sequence of 8Mbit.
      customizedPattern is the pattern defined in the customizedPattern 
      attribute."
   DEFVAL     { ccitt32kBitPattern }
::= { mscLpDS3DS1ChanTestSetupEntry 4 }

mscLpDS3DS1ChanTestCustomizedPattern OBJECT-TYPE
   SYNTAX     Hex (0..4294967295)
   ACCESS     read-write
   STATUS     mandatory
   DESCRIPTION
     "This attribute allows a customized 32 bit pattern to be defined for 
      use in the test data frames. This attribute is used when the attribute 
      frmPatternType is set to CustomizedPattern. Note that a 55 hex 
      pattern is an alternating 1 and 0 pattern."
   DEFVAL     { 1431655765 }
::= { mscLpDS3DS1ChanTestSetupEntry 5 }

mscLpDS3DS1ChanTestDataStartDelay OBJECT-TYPE
   SYNTAX     Unsigned32 (0..1814400)
   ACCESS     read-write
   STATUS     mandatory
   DESCRIPTION
     "This attribute specifies the time delay (in seconds) between when 
      the test expects the loop to have been set up, to when the test data 
      actually starts to be transmitted. This attribute is to accommodate 
      some non-standard equipment that requires extra time for setting up 
      a requested loop.
      This attribute is ignored when the test type is set to externalLoop."
   DEFVAL     { 0 }
::= { mscLpDS3DS1ChanTestSetupEntry 6 }

mscLpDS3DS1ChanTestDisplayInterval OBJECT-TYPE
   SYNTAX     Unsigned32 (0..30240)
   ACCESS     read-write
   STATUS     mandatory
   DESCRIPTION
     "This attribute defines the interval (in minutes) between which 
      interim test results are to be displayed. Results are displayed at the 
      operator console at which the test was started. When the test type is 
      set to externalLoop, this attribute is ignored. There will be no 
      display of results if displayInterval is set to 0. This attribute can be 
      changed anytime."
   DEFVAL     { 5 }
::= { mscLpDS3DS1ChanTestSetupEntry 7 }

mscLpDS3DS1ChanTestDuration OBJECT-TYPE
   SYNTAX     Unsigned32 (1..30240)
   ACCESS     read-write
   STATUS     mandatory
   DESCRIPTION
     "This attribute is the duration (in minutes) that test data will be 
      transmitted. In the case of an externalLoop, this is the time that the 
      loop is in effect. Note that dataStartDelay does not apply to the 
      externalLoop."
   DEFVAL     { 1 }
::= { mscLpDS3DS1ChanTestSetupEntry 8 }

mscLpDS3DS1ChanTestResultsTable OBJECT-TYPE
   SYNTAX     SEQUENCE OF MscLpDS3DS1ChanTestResultsEntry
   ACCESS     not-accessible
   STATUS     mandatory
   DESCRIPTION
     "This group contains all the statistics related attributes of the Test 
      component."
::= { mscLpDS3DS1ChanTest 12 }

mscLpDS3DS1ChanTestResultsEntry OBJECT-TYPE
   SYNTAX     MscLpDS3DS1ChanTestResultsEntry
   ACCESS     not-accessible
   STATUS     mandatory
   DESCRIPTION
     "An entry in the mscLpDS3DS1ChanTestResultsTable."
   INDEX {
      mscLpIndex,
      mscLpDS3Index,
      mscLpDS3DS1Index,
      mscLpDS3DS1ChanIndex,
      mscLpDS3DS1ChanTestIndex }
::= { mscLpDS3DS1ChanTestResultsTable 1 }

MscLpDS3DS1ChanTestResultsEntry ::= SEQUENCE {
   mscLpDS3DS1ChanTestElapsedTime
      Counter32,
   mscLpDS3DS1ChanTestTimeRemaining
      Unsigned32,
   mscLpDS3DS1ChanTestCauseOfTermination
      INTEGER,
   mscLpDS3DS1ChanTestBitsTx
      PassportCounter64,
   mscLpDS3DS1ChanTestBytesTx
      PassportCounter64,
   mscLpDS3DS1ChanTestFrmTx
      PassportCounter64,
   mscLpDS3DS1ChanTestBitsRx
      PassportCounter64,
   mscLpDS3DS1ChanTestBytesRx
      PassportCounter64,
   mscLpDS3DS1ChanTestFrmRx
      PassportCounter64,
   mscLpDS3DS1ChanTestErroredFrmRx
      PassportCounter64,
   mscLpDS3DS1ChanTestBitErrorRate
      AsciiString }

mscLpDS3DS1ChanTestElapsedTime OBJECT-TYPE
   SYNTAX     Counter32 
   ACCESS     read-only
   STATUS     mandatory
   DESCRIPTION
     "This attribute is the number of minutes elapsed since the test started 
      for an externalLoop test. For a data test, this is the time since test 
      data was first transmitted."
::= { mscLpDS3DS1ChanTestResultsEntry 1 }

mscLpDS3DS1ChanTestTimeRemaining OBJECT-TYPE
   SYNTAX     Unsigned32 (0..4294967295)
   ACCESS     read-only
   STATUS     mandatory
   DESCRIPTION
     "This attribute is the number of minutes remaining before the test is 
      to be stopped according to the duration attribute."
   DEFVAL     { 0 }
::= { mscLpDS3DS1ChanTestResultsEntry 2 }

mscLpDS3DS1ChanTestCauseOfTermination OBJECT-TYPE
   SYNTAX     INTEGER  {
                 testTimeExpired(0),
                 stoppedByOperator(1),
                 unknown(2),
                 neverStarted(3),
                 testRunning(4),
                 hardwareReconfigured(5),
                 loopCodeSyncFailed(6),
                 patternSyncFailed(7),
                 patternSyncLost(8) }
   ACCESS     read-only
   STATUS     mandatory
   DESCRIPTION
     "This attribute indicates either the status of the test or the cause of 
      the test's termination:
      
      neverStarted indicates that the test has not yet been started.
      
      testRunning indicates that the test has been started.
      
      stoppedByOperator indicates that the operator issued a stop 
      command on a test that was running.
      
      testTimeExpired indicates that the test ran for the time specified by 
      the test's duration.
      
      loopCodeSyncFailed indicates that the local end failed to 
      synchronize to the loopCode pattern. The local end transmits the 
      loopCode pattern to cause the remote end to apply a loopback, after 
      which the local end should receive the loopCode pattern. The exact 
      pattern used to request loopCode depends on the test type. This 
      failure indicates a high rate of transmission errors, or that the 
      remote end has failed to apply the loopback.
      
      patternSyncFailed indicates that the local end failed to synchronize 
      to the frmPatternType test pattern, that should have been looped 
      back at the remote end. This failure indicates a high rate of 
      transmission errors or the absence of a loopback.
      
      patternSyncLost indicates that the local end gained and then lost 
      synchronization to the returned frmPatternType test pattern. This 
      failure indicates a sudden increase in transmission errors, frame 
      slippage, or the removal of an existing loopback.
      
      unknown is set when a reason to terminate other than those listed 
      here is encountered.
      
      Note: Only MSA cards support recognition of the failures 
      loopCodeSyncFailed, patternSyncFailed and patternSyncLost. 
      Other cards will not terminate the test under the conditions 
      described by these values."
   DEFVAL     { neverStarted }
::= { mscLpDS3DS1ChanTestResultsEntry 3 }

mscLpDS3DS1ChanTestBitsTx OBJECT-TYPE
   SYNTAX     PassportCounter64 
   ACCESS     read-only
   STATUS     mandatory
   DESCRIPTION
     "This attribute is the total number of bits sent during the test period. 
      As long as the line speed of the hardware interface is less than 
      70 Mbit/s, this counter is not expected to reach the maximum value."
::= { mscLpDS3DS1ChanTestResultsEntry 4 }

mscLpDS3DS1ChanTestBytesTx OBJECT-TYPE
   SYNTAX     PassportCounter64 
   ACCESS     read-only
   STATUS     mandatory
   DESCRIPTION
     "This attribute is the total number of bytes sent during the test 
      period. This counter is not expected to reach its maximum value."
::= { mscLpDS3DS1ChanTestResultsEntry 5 }

mscLpDS3DS1ChanTestFrmTx OBJECT-TYPE
   SYNTAX     PassportCounter64 
   ACCESS     read-only
   STATUS     mandatory
   DESCRIPTION
     "This attribute is the total number of frames sent during the test 
      period. This counter is not expected to reach its maximum value."
::= { mscLpDS3DS1ChanTestResultsEntry 6 }

mscLpDS3DS1ChanTestBitsRx OBJECT-TYPE
   SYNTAX     PassportCounter64 
   ACCESS     read-only
   STATUS     mandatory
   DESCRIPTION
     "This attribute is the total number of bits received during the test 
      period. This counter is not expected to reach its maximum value. 
      The counter will wrap around to 0 if it does reach the maximum 
      value."
::= { mscLpDS3DS1ChanTestResultsEntry 7 }

mscLpDS3DS1ChanTestBytesRx OBJECT-TYPE
   SYNTAX     PassportCounter64 
   ACCESS     read-only
   STATUS     mandatory
   DESCRIPTION
     "This attribute is the total number of bytes received during the test 
      period. This counter is not expected to reach its maximum value. 
      The counter will wrap around to 0 if it does reach its maximum 
      value."
::= { mscLpDS3DS1ChanTestResultsEntry 8 }

mscLpDS3DS1ChanTestFrmRx OBJECT-TYPE
   SYNTAX     PassportCounter64 
   ACCESS     read-only
   STATUS     mandatory
   DESCRIPTION
     "This attribute is the total number of frames received during the test 
      period. This counter is not expected to reach its maximum value. 
      The counter will wrap around to 0 if it does reach its maximum 
      value."
::= { mscLpDS3DS1ChanTestResultsEntry 9 }

mscLpDS3DS1ChanTestErroredFrmRx OBJECT-TYPE
   SYNTAX     PassportCounter64 
   ACCESS     read-only
   STATUS     mandatory
   DESCRIPTION
     "This attribute is not displayed for ATM cards because the physical 
      layer drops all errored frames at the controller interface. 
      
      For all other card types, this attribute is the total number of errored 
      frames received during the test period. This counter is not expected 
      to reach its maximum value. The counter will wrap around to 0 if it 
      does reach its maximum value."
::= { mscLpDS3DS1ChanTestResultsEntry 10 }

mscLpDS3DS1ChanTestBitErrorRate OBJECT-TYPE
   SYNTAX     AsciiString (SIZE (5))
   ACCESS     read-only
   STATUS     mandatory
   DESCRIPTION
     "This attribute is not displayed for ATM cards because the physical 
      layer drops all errored frames at the controller interface. 
      
      For all other card types, this attribute is the calculated bit error rate 
      on the link. Test data are generated and sent in frames of a preset 
      size (frameSize). The Test component will try to estimate the 
      number of bit errors in any errored frame which is identifiable. The 
      statistics will be updated accordingly. A lost frame (may be due to 
      an error on the flag sequence) will be discarded for the bit error rate 
      calculation. The result is presented in the form of xEsyy, where x is 
      the mantissa, syy is the exponent, for example 0E+00, 2E-09.
      Note that the bitErrorRate is an estimate only. For more reliable test 
      results, the test should be done over a long period. Multiple tests 
      would also improve the confidence level of the test results."
::= { mscLpDS3DS1ChanTestResultsEntry 11 }


-- 
-- The AtmCell is a component that contains provisioning and 
-- operational attributes. The provisioning attributes are used to set the 
-- Loss of Cell Deliniation (LCD) alarm activation delay and to turn 
-- cell payload scrambling on or off. The operational attributes are 
-- used to report about the quality of the ATM cells received by the 
-- interface and the cell capacity utilization. The AtmCell component 
-- appears under all port components running on ATM cards.

mscLpDS3DS1ChanCell OBJECT IDENTIFIER ::= { mscLpDS3DS1Chan 3 }



mscLpDS3DS1ChanCellRowStatusTable OBJECT-TYPE
   SYNTAX     SEQUENCE OF MscLpDS3DS1ChanCellRowStatusEntry
   ACCESS     not-accessible
   STATUS     mandatory
   DESCRIPTION
     "This entry controls the addition and deletion of 
      mscLpDS3DS1ChanCell components."
::= { mscLpDS3DS1ChanCell 1 }

mscLpDS3DS1ChanCellRowStatusEntry OBJECT-TYPE
   SYNTAX     MscLpDS3DS1ChanCellRowStatusEntry
   ACCESS     not-accessible
   STATUS     mandatory
   DESCRIPTION
     "A single entry in the table represents a single 
      mscLpDS3DS1ChanCell component."
   INDEX {
      mscLpIndex,
      mscLpDS3Index,
      mscLpDS3DS1Index,
      mscLpDS3DS1ChanIndex,
      mscLpDS3DS1ChanCellIndex }
::= { mscLpDS3DS1ChanCellRowStatusTable 1 }

MscLpDS3DS1ChanCellRowStatusEntry ::= SEQUENCE {
   mscLpDS3DS1ChanCellRowStatus
      RowStatus,
   mscLpDS3DS1ChanCellComponentName
      DisplayString,
   mscLpDS3DS1ChanCellStorageType
      StorageType,
   mscLpDS3DS1ChanCellIndex
      NonReplicated }

mscLpDS3DS1ChanCellRowStatus OBJECT-TYPE
   SYNTAX     RowStatus 
   ACCESS     read-write
   STATUS     mandatory
   DESCRIPTION
     "This variable is used as the basis for SNMP naming of
      mscLpDS3DS1ChanCell components.
      These components can be added and deleted."
::= { mscLpDS3DS1ChanCellRowStatusEntry 1 }

mscLpDS3DS1ChanCellComponentName OBJECT-TYPE
   SYNTAX     DisplayString 
   ACCESS     read-only
   STATUS     mandatory
   DESCRIPTION
     "This variable provides the component's string name for
      use with the ASCII Console Interface"
::= { mscLpDS3DS1ChanCellRowStatusEntry 2 }

mscLpDS3DS1ChanCellStorageType OBJECT-TYPE
   SYNTAX     StorageType 
   ACCESS     read-only
   STATUS     mandatory
   DESCRIPTION
     "This variable represents the storage type value for the
      mscLpDS3DS1ChanCell tables."
::= { mscLpDS3DS1ChanCellRowStatusEntry 4 }

mscLpDS3DS1ChanCellIndex OBJECT-TYPE
   SYNTAX     NonReplicated 
   ACCESS     not-accessible
   STATUS     mandatory
   DESCRIPTION
     "This variable represents the index for the mscLpDS3DS1ChanCell tables."
::= { mscLpDS3DS1ChanCellRowStatusEntry 10 }

mscLpDS3DS1ChanCellProvTable OBJECT-TYPE
   SYNTAX     SEQUENCE OF MscLpDS3DS1ChanCellProvEntry
   ACCESS     not-accessible
   STATUS     mandatory
   DESCRIPTION
     "This group contains the provisioning attributes for the AtmCell 
      component."
::= { mscLpDS3DS1ChanCell 10 }

mscLpDS3DS1ChanCellProvEntry OBJECT-TYPE
   SYNTAX     MscLpDS3DS1ChanCellProvEntry
   ACCESS     not-accessible
   STATUS     mandatory
   DESCRIPTION
     "An entry in the mscLpDS3DS1ChanCellProvTable."
   INDEX {
      mscLpIndex,
      mscLpDS3Index,
      mscLpDS3DS1Index,
      mscLpDS3DS1ChanIndex,
      mscLpDS3DS1ChanCellIndex }
::= { mscLpDS3DS1ChanCellProvTable 1 }

MscLpDS3DS1ChanCellProvEntry ::= SEQUENCE {
   mscLpDS3DS1ChanCellAlarmActDelay
      Unsigned32,
   mscLpDS3DS1ChanCellScrambleCellPayload
      INTEGER,
   mscLpDS3DS1ChanCellCorrectSingleBitHeaderErrors
      INTEGER }

mscLpDS3DS1ChanCellAlarmActDelay OBJECT-TYPE
   SYNTAX     Unsigned32 (0..2000)
   ACCESS     read-write
   STATUS     mandatory
   DESCRIPTION
     "This attribute defines the time during which a Loss of Cell 
      Delineation (LCD) defect should be observed before declaring an 
      LCD alarm (alarm 70115501). The time is specified in milliseconds."
   DEFVAL     { 500 }
::= { mscLpDS3DS1ChanCellProvEntry 1 }

mscLpDS3DS1ChanCellScrambleCellPayload OBJECT-TYPE
   SYNTAX     INTEGER  {
                 off(0),
                 on(1) }
   ACCESS     read-write
   STATUS     mandatory
   DESCRIPTION
     "Cell scrambling, as defined by  ITU-T Recommendation I.432., can 
      provide a solution to the problem of transmission equipment which 
      is sensitive to certain bit patterns in the ATM cell payload. This 
      attribute controls whether or not the cell payload is scrambled.
      It defaults to off for DS1 interfaces, and on for all other interfaces.
      Note that this setting must be the same at both ends of the link."
::= { mscLpDS3DS1ChanCellProvEntry 2 }

mscLpDS3DS1ChanCellCorrectSingleBitHeaderErrors OBJECT-TYPE
   SYNTAX     INTEGER  {
                 off(0),
                 on(1) }
   ACCESS     read-write
   STATUS     mandatory
   DESCRIPTION
     "This attribute specifies whether the port corrects single bit errors 
      detected in the headers of received cells. If single bit errors are 
      corrected, the affected cells are passed up to the ATM layer 
      according to normal operation. If single bit errors are not corrected, 
      these errored cells are discarded by the physical layer. Note that 
      cells containing multiple bit errors in their headers are always 
      discarded.
      
      Single bit HEC error correction must remain off for the following 
      card types: 3pDS1Atm, 8pDS1Atm, 3pE1Atm, 8pE1Atm, 
      2pJ6MAtm, 3pDS3Atm, and 3pE3Atm."
   DEFVAL     { off }
::= { mscLpDS3DS1ChanCellProvEntry 3 }

mscLpDS3DS1ChanCellOperTable OBJECT-TYPE
   SYNTAX     SEQUENCE OF MscLpDS3DS1ChanCellOperEntry
   ACCESS     not-accessible
   STATUS     mandatory
   DESCRIPTION
     "This group contains the common operational attributes for the 
      AtmCell component."
::= { mscLpDS3DS1ChanCell 11 }

mscLpDS3DS1ChanCellOperEntry OBJECT-TYPE
   SYNTAX     MscLpDS3DS1ChanCellOperEntry
   ACCESS     not-accessible
   STATUS     mandatory
   DESCRIPTION
     "An entry in the mscLpDS3DS1ChanCellOperTable."
   INDEX {
      mscLpIndex,
      mscLpDS3Index,
      mscLpDS3DS1Index,
      mscLpDS3DS1ChanIndex,
      mscLpDS3DS1ChanCellIndex }
::= { mscLpDS3DS1ChanCellOperTable 1 }

MscLpDS3DS1ChanCellOperEntry ::= SEQUENCE {
   mscLpDS3DS1ChanCellLcdAlarm
      INTEGER }

mscLpDS3DS1ChanCellLcdAlarm OBJECT-TYPE
   SYNTAX     INTEGER  {
                 on(0),
                 off(1) }
   ACCESS     read-only
   STATUS     mandatory
   DESCRIPTION
     "This attribute displays whether the Loss of Cell Delineation (LCD) 
      failure alarm state has been entered. This state is entered when LCD 
      defects have been observed and accumulated for a period of time 
      specified through the alarmActDelay attribute.
      In ATM cell direct mapping mode, an LCD defect occurs when Out 
      of Cell Delineation (OCD) anomaly persists for x milliseconds, and 
      disappears when the Out of Cell Delineation (OCD) is absent for x 
      msec. An OCD anomaly occurs when 7 consecutive incorrect HECs 
      have been detected. An OCD anomaly terminates when 6 
      consecutive correct HECs have been detected.
      For an AtmCell component located under a DS3 or E3 component 
      with mapping = PLCP, the LCD defect is directly derived from the 
      PLCP LOF defect.
      If LCD defects are intermittently occurring, the LCD defect 
      accumulator is decremented at a rate of 1/10 of the incrementing 
      rate (alarm integration ratio of 1/10), with all measurements based 
      on a 200 ms polling cycle
      The component under which is located the AtmCell component goes 
      into an operational state of disabled until the LCD alarm condition 
      is cleared. The condition is cleared after the LCD defect has not 
      been reported for a period of 10 seconds +/- 0.5 seconds.
      The lcdAlarm attribute is always set to off when the parent of the 
      AtmCell component has been locked and left offline. This can also 
      happen when the Path or Channel component has been suspended 
      since its parent has been locked."
   DEFVAL     { off }
::= { mscLpDS3DS1ChanCellOperEntry 1 }

mscLpDS3DS1ChanCellStatsTable OBJECT-TYPE
   SYNTAX     SEQUENCE OF MscLpDS3DS1ChanCellStatsEntry
   ACCESS     not-accessible
   STATUS     mandatory
   DESCRIPTION
     "This group contains the Statistics attribute for the AtmCell 
      component. Each attribute type is a non-negative integer which 
      monotonically increases until it reaches a maximum value, at which 
      point it wraps around and starts increasing again from zero."
::= { mscLpDS3DS1ChanCell 12 }

mscLpDS3DS1ChanCellStatsEntry OBJECT-TYPE
   SYNTAX     MscLpDS3DS1ChanCellStatsEntry
   ACCESS     not-accessible
   STATUS     mandatory
   DESCRIPTION
     "An entry in the mscLpDS3DS1ChanCellStatsTable."
   INDEX {
      mscLpIndex,
      mscLpDS3Index,
      mscLpDS3DS1Index,
      mscLpDS3DS1ChanIndex,
      mscLpDS3DS1ChanCellIndex }
::= { mscLpDS3DS1ChanCellStatsTable 1 }

MscLpDS3DS1ChanCellStatsEntry ::= SEQUENCE {
   mscLpDS3DS1ChanCellUncorrectableHecErrors
      Counter32,
   mscLpDS3DS1ChanCellSevErroredSec
      Counter32,
   mscLpDS3DS1ChanCellReceiveCellUtilization
      Gauge32,
   mscLpDS3DS1ChanCellTransmitCellUtilization
      Gauge32,
   mscLpDS3DS1ChanCellCorrectableHeaderErrors
      Counter32 }

mscLpDS3DS1ChanCellUncorrectableHecErrors OBJECT-TYPE
   SYNTAX     Counter32 
   ACCESS     read-only
   STATUS     mandatory
   DESCRIPTION
     "This attribute indicates the number of uncorrectable ATM cell 
      header errors that have been detected. Counting of 
      uncorrectableHeaderErrors is inhibited when an Out of Cell 
      Delineation (OCD) defect is present. An OCD defect occurs when 
      seven consecutive incorrect HECs have been detected. An OCD 
      defect terminates when six consecutive correct HECs have been 
      detected."
::= { mscLpDS3DS1ChanCellStatsEntry 1 }

mscLpDS3DS1ChanCellSevErroredSec OBJECT-TYPE
   SYNTAX     Counter32 
   ACCESS     read-only
   STATUS     mandatory
   DESCRIPTION
     "This attribute indicates the total number of ATM Cell Severely 
      Errored Seconds (SESs) that have been counted. 
      
      In direct mapping mode, an ATM Cell SES is declared for second 
      intervals containing one or more Out of Cell Delineation (OCD) 
      defects. An OCD defect occurs when seven consecutive incorrect 
      HECs have been detected. An OCD defect terminates when six 
      consecutive correct HECs have been detected.
      
      In PLCP mapping mode, an ATM Cell SES is declared for second 
      intervals containing one or more PLCP LOF defects.
      
      Counting of uncorrectableHeaderErrors (ucErr) and 
      correctableHeaderErrors (cErr) is inhibited when the OCD defect 
      is present."
::= { mscLpDS3DS1ChanCellStatsEntry 2 }

mscLpDS3DS1ChanCellReceiveCellUtilization OBJECT-TYPE
   SYNTAX     Gauge32 (0..100)
   ACCESS     read-only
   STATUS     mandatory
   DESCRIPTION
     "This attribute is the ratio of the number of valid, assigned cells 
      received on the link to the nominal link capacity. The utilization is 
      calculated over a period of one minute.
      This attribute is always set to 0 when the parent of the AtmCell 
      component has been locked and left offline. This can also happen 
      when the Path or Channel component has been suspended since its 
      parent has been locked."
   DEFVAL     { 0 }
::= { mscLpDS3DS1ChanCellStatsEntry 3 }

mscLpDS3DS1ChanCellTransmitCellUtilization OBJECT-TYPE
   SYNTAX     Gauge32 (0..100)
   ACCESS     read-only
   STATUS     mandatory
   DESCRIPTION
     "This attribute is the ratio of the number of valid, assigned cells 
      transmitted on the link to the nominal link capacity. The utilization 
      is calculated over a period of one minute.
      This attribute is always set to 0 when the parent of the AtmCell 
      component has been locked and left offline. This can also happen 
      when the Path or Channel component has been suspended since its 
      parent has been locked."
   DEFVAL     { 0 }
::= { mscLpDS3DS1ChanCellStatsEntry 4 }

mscLpDS3DS1ChanCellCorrectableHeaderErrors OBJECT-TYPE
   SYNTAX     Counter32 
   ACCESS     read-only
   STATUS     mandatory
   DESCRIPTION
     "This attribute indicates the number of correctable ATM cell header 
      errors that have been detected and corrected. Counting of 
      correctableHeaderErrors is inhibited when an Out of Cell 
      Delineation (OCD) defect is present. An OCD defect occurs when 
      seven consecutive incorrect HECs have been detected. An OCD 
      defect terminates when six consecutive correct HECs have been 
      detected"
::= { mscLpDS3DS1ChanCellStatsEntry 5 }


-- Lp/x Ds1/y Chan/z Tc
-- Lp/x E1/y Chan/z Tc
-- 
-- The Tc component is used to provision and monitor trunk 
-- conditioning options. A separate instance of this component is 
-- required for each Chan on a Port which is offering a structured 
-- constant bit rate service.
-- 
-- Under certain failure alarm conditions, trunk conditioning 
-- replacementData is substituted into the timeslots as defined by the 
-- Chan component. Trunk conditioning signaling is also substituted 
-- into the appropriate Channel Associated Signaling (CAS) bits when 
-- a lineType that uses CAS has been defined.
-- 
-- When used with AAL1 Circuit Emulation Service, trunk 
-- conditioning is transmitted towards the ATM network under the 
-- following conditions:
-- lossOfSignal (LOS)
-- lossOfFrame (LOF)
-- remoteAlarmIndication (RAI)
-- alarmIndicationSignal (AIS)
-- bufferUnderflow (BU)
-- and in addition for E1:
-- lossOfMultiframe (LOMF)
-- receiveMultiframeRemoteAlarmIndication (RMRAI)
-- 
-- When used with AAL1 Circuit Emulation Service, trunk 
-- conditioning is transmitted towards the PDH network under the 
-- following conditions:
-- bufferUnderflow (BU)
-- AAL1 protocol errors.
-- 

mscLpDS3DS1ChanTc OBJECT IDENTIFIER ::= { mscLpDS3DS1Chan 4 }



mscLpDS3DS1ChanTcRowStatusTable OBJECT-TYPE
   SYNTAX     SEQUENCE OF MscLpDS3DS1ChanTcRowStatusEntry
   ACCESS     not-accessible
   STATUS     mandatory
   DESCRIPTION
     "This entry controls the addition and deletion of 
      mscLpDS3DS1ChanTc components."
::= { mscLpDS3DS1ChanTc 1 }

mscLpDS3DS1ChanTcRowStatusEntry OBJECT-TYPE
   SYNTAX     MscLpDS3DS1ChanTcRowStatusEntry
   ACCESS     not-accessible
   STATUS     mandatory
   DESCRIPTION
     "A single entry in the table represents a single 
      mscLpDS3DS1ChanTc component."
   INDEX {
      mscLpIndex,
      mscLpDS3Index,
      mscLpDS3DS1Index,
      mscLpDS3DS1ChanIndex,
      mscLpDS3DS1ChanTcIndex }
::= { mscLpDS3DS1ChanTcRowStatusTable 1 }

MscLpDS3DS1ChanTcRowStatusEntry ::= SEQUENCE {
   mscLpDS3DS1ChanTcRowStatus
      RowStatus,
   mscLpDS3DS1ChanTcComponentName
      DisplayString,
   mscLpDS3DS1ChanTcStorageType
      StorageType,
   mscLpDS3DS1ChanTcIndex
      NonReplicated }

mscLpDS3DS1ChanTcRowStatus OBJECT-TYPE
   SYNTAX     RowStatus 
   ACCESS     read-write
   STATUS     mandatory
   DESCRIPTION
     "This variable is used as the basis for SNMP naming of
      mscLpDS3DS1ChanTc components.
      These components can be added and deleted."
::= { mscLpDS3DS1ChanTcRowStatusEntry 1 }

mscLpDS3DS1ChanTcComponentName OBJECT-TYPE
   SYNTAX     DisplayString 
   ACCESS     read-only
   STATUS     mandatory
   DESCRIPTION
     "This variable provides the component's string name for
      use with the ASCII Console Interface"
::= { mscLpDS3DS1ChanTcRowStatusEntry 2 }

mscLpDS3DS1ChanTcStorageType OBJECT-TYPE
   SYNTAX     StorageType 
   ACCESS     read-only
   STATUS     mandatory
   DESCRIPTION
     "This variable represents the storage type value for the
      mscLpDS3DS1ChanTc tables."
::= { mscLpDS3DS1ChanTcRowStatusEntry 4 }

mscLpDS3DS1ChanTcIndex OBJECT-TYPE
   SYNTAX     NonReplicated 
   ACCESS     not-accessible
   STATUS     mandatory
   DESCRIPTION
     "This variable represents the index for the mscLpDS3DS1ChanTc tables."
::= { mscLpDS3DS1ChanTcRowStatusEntry 10 }

mscLpDS3DS1ChanTcProvTable OBJECT-TYPE
   SYNTAX     SEQUENCE OF MscLpDS3DS1ChanTcProvEntry
   ACCESS     not-accessible
   STATUS     mandatory
   DESCRIPTION
     "This group contains all specific provisioning data for a Tc 
      component."
::= { mscLpDS3DS1ChanTc 10 }

mscLpDS3DS1ChanTcProvEntry OBJECT-TYPE
   SYNTAX     MscLpDS3DS1ChanTcProvEntry
   ACCESS     not-accessible
   STATUS     mandatory
   DESCRIPTION
     "An entry in the mscLpDS3DS1ChanTcProvTable."
   INDEX {
      mscLpIndex,
      mscLpDS3Index,
      mscLpDS3DS1Index,
      mscLpDS3DS1ChanIndex,
      mscLpDS3DS1ChanTcIndex }
::= { mscLpDS3DS1ChanTcProvTable 1 }

MscLpDS3DS1ChanTcProvEntry ::= SEQUENCE {
   mscLpDS3DS1ChanTcReplacementData
      Hex,
   mscLpDS3DS1ChanTcSignalOneDuration
      Unsigned32 }

mscLpDS3DS1ChanTcReplacementData OBJECT-TYPE
   SYNTAX     Hex (0..255)
   ACCESS     read-write
   STATUS     mandatory
   DESCRIPTION
     "This attribute specifies the trunk conditioning data byte to be 
      substituted into the timeslots defined by the Chan component under 
      fault conditions. 
      
      replacementData can be set to any two digit hexadecimal number. 
      The following are recommended values:
      DS1 MUX Out Of Service Code = 0x1A
      E1 MUX Out Of Service Code = 0xFF"
   DEFVAL     { 255 }
::= { mscLpDS3DS1ChanTcProvEntry 1 }

mscLpDS3DS1ChanTcSignalOneDuration OBJECT-TYPE
   SYNTAX     Unsigned32 (0..60)
   ACCESS     read-write
   STATUS     mandatory
   DESCRIPTION
     "This attribute specifies the time duration in seconds for which 
      signalOne is substituted into the appropriate signaling bits, when a 
      lineType that uses CAS has been defined. When signalOneDuration 
      has expired signalTwo is substituted into the appropriate signaling 
      bits.
      
      If signalOneDuration is set to zero then only signalTwo is 
      substituted into the appropriate signaling bits during error 
      conditions.
      
      signalOneDuration can be set to any integer value from 0 to 60 
      seconds."
   DEFVAL     { 0 }
::= { mscLpDS3DS1ChanTcProvEntry 2 }

mscLpDS3DS1ChanTcOpTable OBJECT-TYPE
   SYNTAX     SEQUENCE OF MscLpDS3DS1ChanTcOpEntry
   ACCESS     not-accessible
   STATUS     mandatory
   DESCRIPTION
     "This group contains all specific operational data for a Tc 
      component."
::= { mscLpDS3DS1ChanTc 11 }

mscLpDS3DS1ChanTcOpEntry OBJECT-TYPE
   SYNTAX     MscLpDS3DS1ChanTcOpEntry
   ACCESS     not-accessible
   STATUS     mandatory
   DESCRIPTION
     "An entry in the mscLpDS3DS1ChanTcOpTable."
   INDEX {
      mscLpIndex,
      mscLpDS3Index,
      mscLpDS3DS1Index,
      mscLpDS3DS1ChanIndex,
      mscLpDS3DS1ChanTcIndex }
::= { mscLpDS3DS1ChanTcOpTable 1 }

MscLpDS3DS1ChanTcOpEntry ::= SEQUENCE {
   mscLpDS3DS1ChanTcIngressConditioning
      INTEGER,
   mscLpDS3DS1ChanTcEgressConditioning
      INTEGER }

mscLpDS3DS1ChanTcIngressConditioning OBJECT-TYPE
   SYNTAX     INTEGER  {
                 off(0),
                 on(1) }
   ACCESS     read-only
   STATUS     mandatory
   DESCRIPTION
     "This attribute indicates the status of locally generated trunk 
      conditioning towards the ATM network.
      
      When trunk conditioning is being locally generated towards the 
      ATM network, ingressConditioning is set to on.
      
      When trunk conditioning is not being locally generated towards the 
      ATM network, ingressConditioning is set to off.
      
      Trunk conditioning is transmitted towards the ATM network under 
      the following conditions:
      lossOfSignal (LOS)
      lossOfFrame (LOF)
      remoteAlarmIndication (RAI)
      alarmIndicationSignal (AIS)
      bufferUnderflow (BU)
      and in addition for E1:
      lossOfMultiframe (LOMF)
      receiveMultiframeRemoteAlarmIndication (RMRAI)"
   DEFVAL     { off }
::= { mscLpDS3DS1ChanTcOpEntry 1 }

mscLpDS3DS1ChanTcEgressConditioning OBJECT-TYPE
   SYNTAX     INTEGER  {
                 off(0),
                 on(1) }
   ACCESS     read-only
   STATUS     mandatory
   DESCRIPTION
     "This attribute indicates the status of locally generated trunk 
      conditioning towards the PDH line.
      
      When trunk conditioning is being locally generated towards the 
      PDH line, egressConditioning is set to on.
      
      When trunk conditioning is not being locally generated towards the 
      PDH line, egressConditioning is set to off.
      
      Trunk conditioning is transmitted towards the PDH line under the 
      following conditions:
      bufferUnderflow (BU)
      AAL1 protocol errors."
   DEFVAL     { off }
::= { mscLpDS3DS1ChanTcOpEntry 2 }

mscLpDS3DS1ChanTcSigOneTable OBJECT-TYPE
   SYNTAX     SEQUENCE OF MscLpDS3DS1ChanTcSigOneEntry
   ACCESS     not-accessible
   STATUS     mandatory
   DESCRIPTION
     "This attribute specifies the value to be substituted into the ABCD 
      signaling bits for the timeslots defined by the Chan component 
      under fault conditions. The value will be substituted for the duration 
      provisioned in signalOneDuration when a lineType that uses CAS 
      has been defined. 
      
      For a lineType of d4Cas (Super Frame), signaling bits C and D are 
      required to equal bits A and B respectively."
::= { mscLpDS3DS1ChanTc 398 }

mscLpDS3DS1ChanTcSigOneEntry OBJECT-TYPE
   SYNTAX     MscLpDS3DS1ChanTcSigOneEntry
   ACCESS     not-accessible
   STATUS     mandatory
   DESCRIPTION
     "An entry in the mscLpDS3DS1ChanTcSigOneTable."
   INDEX {
      mscLpIndex,
      mscLpDS3Index,
      mscLpDS3DS1Index,
      mscLpDS3DS1ChanIndex,
      mscLpDS3DS1ChanTcIndex,
      mscLpDS3DS1ChanTcSigOneIndex }
::= { mscLpDS3DS1ChanTcSigOneTable 1 }

MscLpDS3DS1ChanTcSigOneEntry ::= SEQUENCE {
   mscLpDS3DS1ChanTcSigOneIndex
      INTEGER,
   mscLpDS3DS1ChanTcSigOneValue
      Unsigned32 }

mscLpDS3DS1ChanTcSigOneIndex OBJECT-TYPE
   SYNTAX     INTEGER  {
                 d(0),
                 c(1),
                 b(2),
                 a(3) }
   ACCESS     not-accessible
   STATUS     mandatory
   DESCRIPTION
     "This variable represents the mscLpDS3DS1ChanTcSigOneTable
      specific index for the mscLpDS3DS1ChanTcSigOneTable."
::= { mscLpDS3DS1ChanTcSigOneEntry 1 }

mscLpDS3DS1ChanTcSigOneValue OBJECT-TYPE
   SYNTAX     Unsigned32 (0..1)
   ACCESS     read-write
   STATUS     mandatory
   DESCRIPTION
     "This variable represents an individual value for the
      mscLpDS3DS1ChanTcSigOneTable."
::= { mscLpDS3DS1ChanTcSigOneEntry 2 }

mscLpDS3DS1ChanTcSigTwoTable OBJECT-TYPE
   SYNTAX     SEQUENCE OF MscLpDS3DS1ChanTcSigTwoEntry
   ACCESS     not-accessible
   STATUS     mandatory
   DESCRIPTION
     "This attribute specifies the value to be substituted into the ABCD 
      signaling bits for the timeslots defined by the Chan component 
      under fault conditions. The value will be substituted after the 
      duration provisioned in signalOneDuration has expired and when a 
      lineType that uses CAS has been defined. 
      
      For a lineType of d4Cas (Super Frame), signaling bits C and D are 
      required to equal bits A and B respectively."
::= { mscLpDS3DS1ChanTc 399 }

mscLpDS3DS1ChanTcSigTwoEntry OBJECT-TYPE
   SYNTAX     MscLpDS3DS1ChanTcSigTwoEntry
   ACCESS     not-accessible
   STATUS     mandatory
   DESCRIPTION
     "An entry in the mscLpDS3DS1ChanTcSigTwoTable."
   INDEX {
      mscLpIndex,
      mscLpDS3Index,
      mscLpDS3DS1Index,
      mscLpDS3DS1ChanIndex,
      mscLpDS3DS1ChanTcIndex,
      mscLpDS3DS1ChanTcSigTwoIndex }
::= { mscLpDS3DS1ChanTcSigTwoTable 1 }

MscLpDS3DS1ChanTcSigTwoEntry ::= SEQUENCE {
   mscLpDS3DS1ChanTcSigTwoIndex
      INTEGER,
   mscLpDS3DS1ChanTcSigTwoValue
      Unsigned32 }

mscLpDS3DS1ChanTcSigTwoIndex OBJECT-TYPE
   SYNTAX     INTEGER  {
                 d(0),
                 c(1),
                 b(2),
                 a(3) }
   ACCESS     not-accessible
   STATUS     mandatory
   DESCRIPTION
     "This variable represents the mscLpDS3DS1ChanTcSigTwoTable
      specific index for the mscLpDS3DS1ChanTcSigTwoTable."
::= { mscLpDS3DS1ChanTcSigTwoEntry 1 }

mscLpDS3DS1ChanTcSigTwoValue OBJECT-TYPE
   SYNTAX     Unsigned32 (0..1)
   ACCESS     read-write
   STATUS     mandatory
   DESCRIPTION
     "This variable represents an individual value for the
      mscLpDS3DS1ChanTcSigTwoTable."
::= { mscLpDS3DS1ChanTcSigTwoEntry 2 }


-- 
-- The Test component is configured to control a hardware facility test 
-- on a physical (V35, X21, DS1, E1, DS3, E3 etc.) or a logical port.

mscLpDS3DS1Test OBJECT IDENTIFIER ::= { mscLpDS3DS1 3 }



mscLpDS3DS1TestRowStatusTable OBJECT-TYPE
   SYNTAX     SEQUENCE OF MscLpDS3DS1TestRowStatusEntry
   ACCESS     not-accessible
   STATUS     mandatory
   DESCRIPTION
     "This entry controls the addition and deletion of 
      mscLpDS3DS1Test components."
::= { mscLpDS3DS1Test 1 }

mscLpDS3DS1TestRowStatusEntry OBJECT-TYPE
   SYNTAX     MscLpDS3DS1TestRowStatusEntry
   ACCESS     not-accessible
   STATUS     mandatory
   DESCRIPTION
     "A single entry in the table represents a single 
      mscLpDS3DS1Test component."
   INDEX {
      mscLpIndex,
      mscLpDS3Index,
      mscLpDS3DS1Index,
      mscLpDS3DS1TestIndex }
::= { mscLpDS3DS1TestRowStatusTable 1 }

MscLpDS3DS1TestRowStatusEntry ::= SEQUENCE {
   mscLpDS3DS1TestRowStatus
      RowStatus,
   mscLpDS3DS1TestComponentName
      DisplayString,
   mscLpDS3DS1TestStorageType
      StorageType,
   mscLpDS3DS1TestIndex
      NonReplicated }

mscLpDS3DS1TestRowStatus OBJECT-TYPE
   SYNTAX     RowStatus 
   ACCESS     read-only
   STATUS     mandatory
   DESCRIPTION
     "This variable is used as the basis for SNMP naming of
      mscLpDS3DS1Test components.
      These components cannot be added nor deleted."
::= { mscLpDS3DS1TestRowStatusEntry 1 }

mscLpDS3DS1TestComponentName OBJECT-TYPE
   SYNTAX     DisplayString 
   ACCESS     read-only
   STATUS     mandatory
   DESCRIPTION
     "This variable provides the component's string name for
      use with the ASCII Console Interface"
::= { mscLpDS3DS1TestRowStatusEntry 2 }

mscLpDS3DS1TestStorageType OBJECT-TYPE
   SYNTAX     StorageType 
   ACCESS     read-only
   STATUS     mandatory
   DESCRIPTION
     "This variable represents the storage type value for the
      mscLpDS3DS1Test tables."
::= { mscLpDS3DS1TestRowStatusEntry 4 }

mscLpDS3DS1TestIndex OBJECT-TYPE
   SYNTAX     NonReplicated 
   ACCESS     not-accessible
   STATUS     mandatory
   DESCRIPTION
     "This variable represents the index for the mscLpDS3DS1Test tables."
::= { mscLpDS3DS1TestRowStatusEntry 10 }

mscLpDS3DS1TestStateTable OBJECT-TYPE
   SYNTAX     SEQUENCE OF MscLpDS3DS1TestStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscLpDS3DS1Test 10 }

mscLpDS3DS1TestStateEntry OBJECT-TYPE
   SYNTAX     MscLpDS3DS1TestStateEntry
   ACCESS     not-accessible
   STATUS     mandatory
   DESCRIPTION
     "An entry in the mscLpDS3DS1TestStateTable."
   INDEX {
      mscLpIndex,
      mscLpDS3Index,
      mscLpDS3DS1Index,
      mscLpDS3DS1TestIndex }
::= { mscLpDS3DS1TestStateTable 1 }

MscLpDS3DS1TestStateEntry ::= SEQUENCE {
   mscLpDS3DS1TestAdminState
      INTEGER,
   mscLpDS3DS1TestOperationalState
      INTEGER,
   mscLpDS3DS1TestUsageState
      INTEGER }

mscLpDS3DS1TestAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscLpDS3DS1TestStateEntry 1 }

mscLpDS3DS1TestOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscLpDS3DS1TestStateEntry 2 }

mscLpDS3DS1TestUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscLpDS3DS1TestStateEntry 3 }

mscLpDS3DS1TestSetupTable OBJECT-TYPE
   SYNTAX     SEQUENCE OF MscLpDS3DS1TestSetupEntry
   ACCESS     not-accessible
   STATUS     mandatory
   DESCRIPTION
     "This group contains all of the operational data for a Test 
      component."
::= { mscLpDS3DS1Test 11 }

mscLpDS3DS1TestSetupEntry OBJECT-TYPE
   SYNTAX     MscLpDS3DS1TestSetupEntry
   ACCESS     not-accessible
   STATUS     mandatory
   DESCRIPTION
     "An entry in the mscLpDS3DS1TestSetupTable."
   INDEX {
      mscLpIndex,
      mscLpDS3Index,
      mscLpDS3DS1Index,
      mscLpDS3DS1TestIndex }
::= { mscLpDS3DS1TestSetupTable 1 }

MscLpDS3DS1TestSetupEntry ::= SEQUENCE {
   mscLpDS3DS1TestPurpose
      AsciiString,
   mscLpDS3DS1TestType
      INTEGER,
   mscLpDS3DS1TestFrmSize
      Unsigned32,
   mscLpDS3DS1TestFrmPatternType
      INTEGER,
   mscLpDS3DS1TestCustomizedPattern
      Hex,
   mscLpDS3DS1TestDataStartDelay
      Unsigned32,
   mscLpDS3DS1TestDisplayInterval
      Unsigned32,
   mscLpDS3DS1TestDuration
      Unsigned32 }

mscLpDS3DS1TestPurpose OBJECT-TYPE
   SYNTAX     AsciiString (SIZE (0..40))
   ACCESS     read-write
   STATUS     mandatory
   DESCRIPTION
     "This attribute records the purpose of the test so that the test results 
      can be associated and properly analyzed."
::= { mscLpDS3DS1TestSetupEntry 1 }

mscLpDS3DS1TestType OBJECT-TYPE
   SYNTAX     INTEGER  {
                 card(0),
                 manual(1),
                 localLoop(2),
                 remoteLoop(3),
                 externalLoop(4),
                 payloadLoop(5),
                 remoteLoopThisTrib(6),
                 v54RemoteLoop(7),
                 pn127RemoteLoop(8) }
   ACCESS     read-write
   STATUS     mandatory
   DESCRIPTION
     "This attribute is the type of test to be run. The available test types 
      include the following:
      card test sets up an internal loop on the board and runs a bit error 
      rate test.
      manual test assumes the line is looped back externally and a bit 
      error rate test is performed.
      localLoop test loops back the local modem and performs a bit error 
      rate test.
      remoteLoop test loops back the remote modem (or CSU) and 
      performs a bit error rate test.
      externalLoop test loops back the line to the far end.
      payloadLoop test only loops back the payload data received from 
      the incoming line.
      remoteLoopThisTrib loops this particular tributary back at the far 
      end, using services provided by the parent.
      v54RemoteLoop initiates a V.54 Remote Loopback test.
      pn127RemoteLoop initiates a PN127 Remote Loopback test.
      Note that not all test types are not supported by all function 
      processors."
   DEFVAL     { card }
::= { mscLpDS3DS1TestSetupEntry 2 }

mscLpDS3DS1TestFrmSize OBJECT-TYPE
   SYNTAX     Unsigned32 (4..4096)
   ACCESS     read-write
   STATUS     mandatory
   DESCRIPTION
     "This attribute defines the size of the test data frames in number of 
      bytes."
   DEFVAL     { 1024 }
::= { mscLpDS3DS1TestSetupEntry 3 }

mscLpDS3DS1TestFrmPatternType OBJECT-TYPE
   SYNTAX     INTEGER  {
                 ccitt32kBitPattern(0),
                 ccitt8MBitPattern(1),
                 customizedPattern(2) }
   ACCESS     read-write
   STATUS     mandatory
   DESCRIPTION
     "This attribute defines the type of data pattern generation to use. The 
      following lists the available pattern types:
      ccitt32kBitPattern is a pseudo-random sequence of 32 kbit.
      ccitt8MBitPattern is a pseudo-random sequence of 8Mbit.
      customizedPattern is the pattern defined in the customizedPattern 
      attribute."
   DEFVAL     { ccitt32kBitPattern }
::= { mscLpDS3DS1TestSetupEntry 4 }

mscLpDS3DS1TestCustomizedPattern OBJECT-TYPE
   SYNTAX     Hex (0..4294967295)
   ACCESS     read-write
   STATUS     mandatory
   DESCRIPTION
     "This attribute allows a customized 32 bit pattern to be defined for 
      use in the test data frames. This attribute is used when the attribute 
      frmPatternType is set to CustomizedPattern. Note that a 55 hex 
      pattern is an alternating 1 and 0 pattern."
   DEFVAL     { 1431655765 }
::= { mscLpDS3DS1TestSetupEntry 5 }

mscLpDS3DS1TestDataStartDelay OBJECT-TYPE
   SYNTAX     Unsigned32 (0..1814400)
   ACCESS     read-write
   STATUS     mandatory
   DESCRIPTION
     "This attribute specifies the time delay (in seconds) between when 
      the test expects the loop to have been set up, to when the test data 
      actually starts to be transmitted. This attribute is to accommodate 
      some non-standard equipment that requires extra time for setting up 
      a requested loop.
      This attribute is ignored when the test type is set to externalLoop."
   DEFVAL     { 0 }
::= { mscLpDS3DS1TestSetupEntry 6 }

mscLpDS3DS1TestDisplayInterval OBJECT-TYPE
   SYNTAX     Unsigned32 (0..30240)
   ACCESS     read-write
   STATUS     mandatory
   DESCRIPTION
     "This attribute defines the interval (in minutes) between which 
      interim test results are to be displayed. Results are displayed at the 
      operator console at which the test was started. When the test type is 
      set to externalLoop, this attribute is ignored. There will be no 
      display of results if displayInterval is set to 0. This attribute can be 
      changed anytime."
   DEFVAL     { 5 }
::= { mscLpDS3DS1TestSetupEntry 7 }

mscLpDS3DS1TestDuration OBJECT-TYPE
   SYNTAX     Unsigned32 (1..30240)
   ACCESS     read-write
   STATUS     mandatory
   DESCRIPTION
     "This attribute is the duration (in minutes) that test data will be 
      transmitted. In the case of an externalLoop, this is the time that the 
      loop is in effect. Note that dataStartDelay does not apply to the 
      externalLoop."
   DEFVAL     { 1 }
::= { mscLpDS3DS1TestSetupEntry 8 }

mscLpDS3DS1TestResultsTable OBJECT-TYPE
   SYNTAX     SEQUENCE OF MscLpDS3DS1TestResultsEntry
   ACCESS     not-accessible
   STATUS     mandatory
   DESCRIPTION
     "This group contains all the statistics related attributes of the Test 
      component."
::= { mscLpDS3DS1Test 12 }

mscLpDS3DS1TestResultsEntry OBJECT-TYPE
   SYNTAX     MscLpDS3DS1TestResultsEntry
   ACCESS     not-accessible
   STATUS     mandatory
   DESCRIPTION
     "An entry in the mscLpDS3DS1TestResultsTable."
   INDEX {
      mscLpIndex,
      mscLpDS3Index,
      mscLpDS3DS1Index,
      mscLpDS3DS1TestIndex }
::= { mscLpDS3DS1TestResultsTable 1 }

MscLpDS3DS1TestResultsEntry ::= SEQUENCE {
   mscLpDS3DS1TestElapsedTime
      Counter32,
   mscLpDS3DS1TestTimeRemaining
      Unsigned32,
   mscLpDS3DS1TestCauseOfTermination
      INTEGER,
   mscLpDS3DS1TestBitsTx
      PassportCounter64,
   mscLpDS3DS1TestBytesTx
      PassportCounter64,
   mscLpDS3DS1TestFrmTx
      PassportCounter64,
   mscLpDS3DS1TestBitsRx
      PassportCounter64,
   mscLpDS3DS1TestBytesRx
      PassportCounter64,
   mscLpDS3DS1TestFrmRx
      PassportCounter64,
   mscLpDS3DS1TestErroredFrmRx
      PassportCounter64,
   mscLpDS3DS1TestBitErrorRate
      AsciiString }

mscLpDS3DS1TestElapsedTime OBJECT-TYPE
   SYNTAX     Counter32 
   ACCESS     read-only
   STATUS     mandatory
   DESCRIPTION
     "This attribute is the number of minutes elapsed since the test started 
      for an externalLoop test. For a data test, this is the time since test 
      data was first transmitted."
::= { mscLpDS3DS1TestResultsEntry 1 }

mscLpDS3DS1TestTimeRemaining OBJECT-TYPE
   SYNTAX     Unsigned32 (0..4294967295)
   ACCESS     read-only
   STATUS     mandatory
   DESCRIPTION
     "This attribute is the number of minutes remaining before the test is 
      to be stopped according to the duration attribute."
   DEFVAL     { 0 }
::= { mscLpDS3DS1TestResultsEntry 2 }

mscLpDS3DS1TestCauseOfTermination OBJECT-TYPE
   SYNTAX     INTEGER  {
                 testTimeExpired(0),
                 stoppedByOperator(1),
                 unknown(2),
                 neverStarted(3),
                 testRunning(4),
                 hardwareReconfigured(5),
                 loopCodeSyncFailed(6),
                 patternSyncFailed(7),
                 patternSyncLost(8) }
   ACCESS     read-only
   STATUS     mandatory
   DESCRIPTION
     "This attribute indicates either the status of the test or the cause of 
      the test's termination:
      
      neverStarted indicates that the test has not yet been started.
      
      testRunning indicates that the test has been started.
      
      stoppedByOperator indicates that the operator issued a stop 
      command on a test that was running.
      
      testTimeExpired indicates that the test ran for the time specified by 
      the test's duration.
      
      loopCodeSyncFailed indicates that the local end failed to 
      synchronize to the loopCode pattern. The local end transmits the 
      loopCode pattern to cause the remote end to apply a loopback, after 
      which the local end should receive the loopCode pattern. The exact 
      pattern used to request loopCode depends on the test type. This 
      failure indicates a high rate of transmission errors, or that the 
      remote end has failed to apply the loopback.
      
      patternSyncFailed indicates that the local end failed to synchronize 
      to the frmPatternType test pattern, that should have been looped 
      back at the remote end. This failure indicates a high rate of 
      transmission errors or the absence of a loopback.
      
      patternSyncLost indicates that the local end gained and then lost 
      synchronization to the returned frmPatternType test pattern. This 
      failure indicates a sudden increase in transmission errors, frame 
      slippage, or the removal of an existing loopback.
      
      unknown is set when a reason to terminate other than those listed 
      here is encountered.
      
      Note: Only MSA cards support recognition of the failures 
      loopCodeSyncFailed, patternSyncFailed and patternSyncLost. 
      Other cards will not terminate the test under the conditions 
      described by these values."
   DEFVAL     { neverStarted }
::= { mscLpDS3DS1TestResultsEntry 3 }

mscLpDS3DS1TestBitsTx OBJECT-TYPE
   SYNTAX     PassportCounter64 
   ACCESS     read-only
   STATUS     mandatory
   DESCRIPTION
     "This attribute is the total number of bits sent during the test period. 
      As long as the line speed of the hardware interface is less than 
      70 Mbit/s, this counter is not expected to reach the maximum value."
::= { mscLpDS3DS1TestResultsEntry 4 }

mscLpDS3DS1TestBytesTx OBJECT-TYPE
   SYNTAX     PassportCounter64 
   ACCESS     read-only
   STATUS     mandatory
   DESCRIPTION
     "This attribute is the total number of bytes sent during the test 
      period. This counter is not expected to reach its maximum value."
::= { mscLpDS3DS1TestResultsEntry 5 }

mscLpDS3DS1TestFrmTx OBJECT-TYPE
   SYNTAX     PassportCounter64 
   ACCESS     read-only
   STATUS     mandatory
   DESCRIPTION
     "This attribute is the total number of frames sent during the test 
      period. This counter is not expected to reach its maximum value."
::= { mscLpDS3DS1TestResultsEntry 6 }

mscLpDS3DS1TestBitsRx OBJECT-TYPE
   SYNTAX     PassportCounter64 
   ACCESS     read-only
   STATUS     mandatory
   DESCRIPTION
     "This attribute is the total number of bits received during the test 
      period. This counter is not expected to reach its maximum value. 
      The counter will wrap around to 0 if it does reach the maximum 
      value."
::= { mscLpDS3DS1TestResultsEntry 7 }

mscLpDS3DS1TestBytesRx OBJECT-TYPE
   SYNTAX     PassportCounter64 
   ACCESS     read-only
   STATUS     mandatory
   DESCRIPTION
     "This attribute is the total number of bytes received during the test 
      period. This counter is not expected to reach its maximum value. 
      The counter will wrap around to 0 if it does reach its maximum 
      value."
::= { mscLpDS3DS1TestResultsEntry 8 }

mscLpDS3DS1TestFrmRx OBJECT-TYPE
   SYNTAX     PassportCounter64 
   ACCESS     read-only
   STATUS     mandatory
   DESCRIPTION
     "This attribute is the total number of frames received during the test 
      period. This counter is not expected to reach its maximum value. 
      The counter will wrap around to 0 if it does reach its maximum 
      value."
::= { mscLpDS3DS1TestResultsEntry 9 }

mscLpDS3DS1TestErroredFrmRx OBJECT-TYPE
   SYNTAX     PassportCounter64 
   ACCESS     read-only
   STATUS     mandatory
   DESCRIPTION
     "This attribute is not displayed for ATM cards because the physical 
      layer drops all errored frames at the controller interface. 
      
      For all other card types, this attribute is the total number of errored 
      frames received during the test period. This counter is not expected 
      to reach its maximum value. The counter will wrap around to 0 if it 
      does reach its maximum value."
::= { mscLpDS3DS1TestResultsEntry 10 }

mscLpDS3DS1TestBitErrorRate OBJECT-TYPE
   SYNTAX     AsciiString (SIZE (5))
   ACCESS     read-only
   STATUS     mandatory
   DESCRIPTION
     "This attribute is not displayed for ATM cards because the physical 
      layer drops all errored frames at the controller interface. 
      
      For all other card types, this attribute is the calculated bit error rate 
      on the link. Test data are generated and sent in frames of a preset 
      size (frameSize). The Test component will try to estimate the 
      number of bit errors in any errored frame which is identifiable. The 
      statistics will be updated accordingly. A lost frame (may be due to 
      an error on the flag sequence) will be discarded for the bit error rate 
      calculation. The result is presented in the form of xEsyy, where x is 
      the mantissa, syy is the exponent, for example 0E+00, 2E-09.
      Note that the bitErrorRate is an estimate only. For more reliable test 
      results, the test should be done over a long period. Multiple tests 
      would also improve the confidence level of the test results."
::= { mscLpDS3DS1TestResultsEntry 11 }


-- LP/n E3/n
-- The E3 component controls an E3 port on an E3 Function 
-- Processor.

mscLpE3 OBJECT IDENTIFIER ::= { mscLp 6 }



mscLpE3RowStatusTable OBJECT-TYPE
   SYNTAX     SEQUENCE OF MscLpE3RowStatusEntry
   ACCESS     not-accessible
   STATUS     mandatory
   DESCRIPTION
     "This entry controls the addition and deletion of 
      mscLpE3 components."
::= { mscLpE3 1 }

mscLpE3RowStatusEntry OBJECT-TYPE
   SYNTAX     MscLpE3RowStatusEntry
   ACCESS     not-accessible
   STATUS     mandatory
   DESCRIPTION
     "A single entry in the table represents a single 
      mscLpE3 component."
   INDEX {
      mscLpIndex,
      mscLpE3Index }
::= { mscLpE3RowStatusTable 1 }

MscLpE3RowStatusEntry ::= SEQUENCE {
   mscLpE3RowStatus
      RowStatus,
   mscLpE3ComponentName
      DisplayString,
   mscLpE3StorageType
      StorageType,
   mscLpE3Index
      Integer32 }

mscLpE3RowStatus OBJECT-TYPE
   SYNTAX     RowStatus 
   ACCESS     read-write
   STATUS     mandatory
   DESCRIPTION
     "This variable is used as the basis for SNMP naming of
      mscLpE3 components.
      These components can be added and deleted."
::= { mscLpE3RowStatusEntry 1 }

mscLpE3ComponentName OBJECT-TYPE
   SYNTAX     DisplayString 
   ACCESS     read-only
   STATUS     mandatory
   DESCRIPTION
     "This variable provides the component's string name for
      use with the ASCII Console Interface"
::= { mscLpE3RowStatusEntry 2 }

mscLpE3StorageType OBJECT-TYPE
   SYNTAX     StorageType 
   ACCESS     read-only
   STATUS     mandatory
   DESCRIPTION
     "This variable represents the storage type value for the
      mscLpE3 tables."
::= { mscLpE3RowStatusEntry 4 }

mscLpE3Index OBJECT-TYPE
   SYNTAX     Integer32 (0..11)
   ACCESS     not-accessible
   STATUS     mandatory
   DESCRIPTION
     "This variable represents the index for the mscLpE3 tables."
::= { mscLpE3RowStatusEntry 10 }

mscLpE3ProvTable OBJECT-TYPE
   SYNTAX     SEQUENCE OF MscLpE3ProvEntry
   ACCESS     not-accessible
   STATUS     mandatory
   DESCRIPTION
     "This group contains all of the provisioning data for a E3 
      component."
::= { mscLpE3 10 }

mscLpE3ProvEntry OBJECT-TYPE
   SYNTAX     MscLpE3ProvEntry
   ACCESS     not-accessible
   STATUS     mandatory
   DESCRIPTION
     "An entry in the mscLpE3ProvTable."
   INDEX {
      mscLpIndex,
      mscLpE3Index }
::= { mscLpE3ProvTable 1 }

MscLpE3ProvEntry ::= SEQUENCE {
   mscLpE3LineLength
      Unsigned32,
   mscLpE3ClockingSource
      INTEGER,
   mscLpE3ApplicationFramerName
      Link,
   mscLpE3Mapping
      INTEGER,
   mscLpE3Framing
      INTEGER,
   mscLpE3LinkAlarmActivationThreshold
      Unsigned32,
   mscLpE3LinkAlarmScanInterval
      Unsigned32 }

mscLpE3LineLength OBJECT-TYPE
   SYNTAX     Unsigned32 (0..300)
   ACCESS     read-write
   STATUS     mandatory
   DESCRIPTION
     "This attribute defines the line length for equalization calculations 
      for the E3 line. The line length range is between 0 and 300 metres 
      (1 metres = 3.28 feet)."
   DEFVAL     { 1 }
::= { mscLpE3ProvEntry 1 }

mscLpE3ClockingSource OBJECT-TYPE
   SYNTAX     INTEGER  {
                 local(0),
                 line(1),
                 module(2),
                 otherPort(4) }
   ACCESS     read-write
   STATUS     mandatory
   DESCRIPTION
     "This attribute defines the type of clocking source used for 
      synchronizing the E3 transmit clock: local means direct use of the 
      local clock oscillator at its centre frequency; line means use of a 
      signal phase-locked to the incoming E3 line rate; module means the 
      use of a signal phase-locked to the CP reference clock.
      Note that the multiport cell-based cards have one common clock 
      source for each of the three ports. For this reason, the following 
      rules apply for the value of clockingSource across the board's three 
      ports: 
      All three clockingSource values must be 'local' OR
      All three clockingSource values must be 'module' OR
      One clockingSource value must be 'line' and the other two must be 
      'otherPort'.
      The default value for this attribute will be module if a CP clock is 
      available, and local otherwise."
::= { mscLpE3ProvEntry 2 }

mscLpE3ApplicationFramerName OBJECT-TYPE
   SYNTAX     Link 
   ACCESS     read-write
   STATUS     mandatory
   DESCRIPTION
     "This attribute defines the link to the software stack. It defines which 
      application is running on top of the E3 component."
::= { mscLpE3ProvEntry 3 }

mscLpE3Mapping OBJECT-TYPE
   SYNTAX     INTEGER  {
                 direct(0),
                 plcp(1) }
   ACCESS     read-write
   STATUS     mandatory
   DESCRIPTION
     "This attribute indicates if ATM cells will be mapped directly into 
      the E3 payload, or whether PLCP mapping will be used. The PLCP 
      component will appear under the E3 component when this attribute 
      is set to plcp. This attribute will be ignored when set on frame-
      based cards."
   DEFVAL     { direct }
::= { mscLpE3ProvEntry 4 }

mscLpE3Framing OBJECT-TYPE
   SYNTAX     INTEGER  {
                 g751(0),
                 g832(1) }
   ACCESS     read-write
   STATUS     mandatory
   DESCRIPTION
     "This attribute indicates if the framing mode will be in accordance 
      with the CCITT G.751 or G.832 specification. The G832 
      component will appear under the E3 component when this attribute 
      is set to g832. This attribute may only be set on cell-based card 
      types. Note also that this attribute may only be set to g751 if the 
      mapping attribute is set to plcp.
      The default value of this attribute will be g751 for frame-based 
      cards, and g832 for cell-based cards.
      Note: when E3 framing is changed from g832 to g751, the G832 
      component must be deleted."
::= { mscLpE3ProvEntry 5 }

mscLpE3LinkAlarmActivationThreshold OBJECT-TYPE
   SYNTAX     Unsigned32 (100..2600)
   ACCESS     read-write
   STATUS     mandatory
   DESCRIPTION
     "This attribute specifies the time interval between the detection of a 
      sustained link failure and the activation of an alarm. It is 
      provisionable for E3 cards."
   DEFVAL     { 2200 }
::= { mscLpE3ProvEntry 6 }

mscLpE3LinkAlarmScanInterval OBJECT-TYPE
   SYNTAX     Unsigned32 (50..250)
   ACCESS     read-write
   STATUS     mandatory
   DESCRIPTION
     "This attribute specifies the alarm scan timer polling interval. It 
      determines how frequently the status of the link is monitored after a 
      first link error interrupt. It is provisionable for E3 cards."
   DEFVAL     { 200 }
::= { mscLpE3ProvEntry 7 }

mscLpE3CidDataTable OBJECT-TYPE
   SYNTAX     SEQUENCE OF MscLpE3CidDataEntry
   ACCESS     not-accessible
   STATUS     mandatory
   DESCRIPTION
     "This group contains the attribute for a component's Customer 
      Identifier (CID). Refer to the attribute description for a detailed 
      explanation of CIDs."
::= { mscLpE3 11 }

mscLpE3CidDataEntry OBJECT-TYPE
   SYNTAX     MscLpE3CidDataEntry
   ACCESS     not-accessible
   STATUS     mandatory
   DESCRIPTION
     "An entry in the mscLpE3CidDataTable."
   INDEX {
      mscLpIndex,
      mscLpE3Index }
::= { mscLpE3CidDataTable 1 }

MscLpE3CidDataEntry ::= SEQUENCE {
   mscLpE3CustomerIdentifier
      Unsigned32 }

mscLpE3CustomerIdentifier OBJECT-TYPE
   SYNTAX     Unsigned32 (0 | 1..8191)
   ACCESS     read-write
   STATUS     mandatory
   DESCRIPTION
     "This attribute holds the Customer Identifier (CID).
      
      Every component has a CID. If a component has a cid attribute, the 
      component's CID is the provisioned value of that attribute; 
      otherwise the component inherits the CID of its parent. The top-
      level component has a CID of 0.
      
      Every operator session also has a CID, which is the CID 
      provisioned for the operator's user ID. An operator will see only the 
      stream data for components having a matching CID. Also, the 
      operator will be allowed to issue commands for only those 
      components which have a matching CID.
      
      An operator CID of 0 is used to identify the Network Manager 
      (referred to as 'NetMan' in DPN). This CID matches the CID of 
      any component. Values 1 to 8191 inclusive (equivalent to 'basic 
      CIDs' in DPN) may be assigned to specific customers."
   DEFVAL     { 0 }
::= { mscLpE3CidDataEntry 1 }

mscLpE3AdminInfoTable OBJECT-TYPE
   SYNTAX     SEQUENCE OF MscLpE3AdminInfoEntry
   ACCESS     not-accessible
   STATUS     mandatory
   DESCRIPTION
     "This group contains the attributes pertaining to the vendor of the 
      equipment."
::= { mscLpE3 12 }

mscLpE3AdminInfoEntry OBJECT-TYPE
   SYNTAX     MscLpE3AdminInfoEntry
   ACCESS     not-accessible
   STATUS     mandatory
   DESCRIPTION
     "An entry in the mscLpE3AdminInfoTable."
   INDEX {
      mscLpIndex,
      mscLpE3Index }
::= { mscLpE3AdminInfoTable 1 }

MscLpE3AdminInfoEntry ::= SEQUENCE {
   mscLpE3Vendor
      AsciiString,
   mscLpE3CommentText
      AsciiString }

mscLpE3Vendor OBJECT-TYPE
   SYNTAX     AsciiString (SIZE (0..20))
   ACCESS     read-write
   STATUS     mandatory
   DESCRIPTION
     "This is the name of the vendor supplying the facility."
::= { mscLpE3AdminInfoEntry 1 }

mscLpE3CommentText OBJECT-TYPE
   SYNTAX     AsciiString (SIZE (0..60))
   ACCESS     read-write
   STATUS     mandatory
   DESCRIPTION
     "Any miscellaneous text about the facility."
::= { mscLpE3AdminInfoEntry 2 }

mscLpE3IfEntryTable OBJECT-TYPE
   SYNTAX     SEQUENCE OF MscLpE3IfEntryEntry
   ACCESS     not-accessible
   STATUS     mandatory
   DESCRIPTION
     "This group contains the provisionable attributes for the ifEntry."
::= { mscLpE3 13 }

mscLpE3IfEntryEntry OBJECT-TYPE
   SYNTAX     MscLpE3IfEntryEntry
   ACCESS     not-accessible
   STATUS     mandatory
   DESCRIPTION
     "An entry in the mscLpE3IfEntryTable."
   INDEX {
      mscLpIndex,
      mscLpE3Index }
::= { mscLpE3IfEntryTable 1 }

MscLpE3IfEntryEntry ::= SEQUENCE {
   mscLpE3IfAdminStatus
      INTEGER,
   mscLpE3IfIndex
      InterfaceIndex }

mscLpE3IfAdminStatus OBJECT-TYPE
   SYNTAX     INTEGER  {
                 up(1),
                 down(2),
                 testing(3) }
   ACCESS     read-write
   STATUS     mandatory
   DESCRIPTION
     "The desired state of the interface. The up state indicates the 
      interface is operational. The down state indicates the interface is not 
      operational. The testing state indicates that no operational packets 
      can be passed."
   DEFVAL     { up }
::= { mscLpE3IfEntryEntry 1 }

mscLpE3IfIndex OBJECT-TYPE
   SYNTAX     InterfaceIndex (1..65535)
   ACCESS     read-only
   STATUS     mandatory
   DESCRIPTION
     "This is the index for the IfEntry. Its value is automatically initialized 
      during the provisioning process."
::= { mscLpE3IfEntryEntry 2 }

mscLpE3OperStatusTable OBJECT-TYPE
   SYNTAX     SEQUENCE OF MscLpE3OperStatusEntry
   ACCESS     not-accessible
   STATUS     mandatory
   DESCRIPTION
     "This group includes the Operational Status attribute. This attribute 
      defines the current operational state of this component."
::= { mscLpE3 14 }

mscLpE3OperStatusEntry OBJECT-TYPE
   SYNTAX     MscLpE3OperStatusEntry
   ACCESS     not-accessible
   STATUS     mandatory
   DESCRIPTION
     "An entry in the mscLpE3OperStatusTable."
   INDEX {
      mscLpIndex,
      mscLpE3Index }
::= { mscLpE3OperStatusTable 1 }

MscLpE3OperStatusEntry ::= SEQUENCE {
   mscLpE3SnmpOperStatus
      INTEGER }

mscLpE3SnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { mscLpE3OperStatusEntry 1 }

mscLpE3StateTable OBJECT-TYPE
   SYNTAX     SEQUENCE OF MscLpE3StateEntry
   ACCESS     not-accessible
   STATUS     mandatory
   DESCRIPTION
     "This group contains the three OSI State attributes and the six OSI 
      Status attributes. The descriptions generically indicate what each 
      attribute implies about the component. Note that not all the values 
      and state combinations described here are supported by every 
      component which uses this group. For component-specific 
      information and the valid state combinations, refer to NTP 241-
      7001-150, Passport Operations and Maintenance Guide."
::= { mscLpE3 15 }

mscLpE3StateEntry OBJECT-TYPE
   SYNTAX     MscLpE3StateEntry
   ACCESS     not-accessible
   STATUS     mandatory
   DESCRIPTION
     "An entry in the mscLpE3StateTable."
   INDEX {
      mscLpIndex,
      mscLpE3Index }
::= { mscLpE3StateTable 1 }

MscLpE3StateEntry ::= SEQUENCE {
   mscLpE3AdminState
      INTEGER,
   mscLpE3OperationalState
      INTEGER,
   mscLpE3UsageState
      INTEGER,
   mscLpE3AvailabilityStatus
      OCTET STRING,
   mscLpE3ProceduralStatus
      OCTET STRING,
   mscLpE3ControlStatus
      OCTET STRING,
   mscLpE3AlarmStatus
      OCTET STRING,
   mscLpE3StandbyStatus
      INTEGER,
   mscLpE3UnknownStatus
      INTEGER }

mscLpE3AdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component.
      
      The OSI Status attributes, if supported by the component, may 
      provide more details, qualifying the state of the component."
   DEFVAL     { unlocked }
::= { mscLpE3StateEntry 1 }

mscLpE3OperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle.
      
      The OSI Status attributes, if supported by the component, may 
      provide more details, qualifying the state of the component."
   DEFVAL     { disabled }
::= { mscLpE3StateEntry 2 }

mscLpE3UsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time.
      
      The OSI Status attributes, if supported by the component, may 
      provide more details, qualifying the state of the component."
   DEFVAL     { idle }
::= { mscLpE3StateEntry 3 }

mscLpE3AvailabilityStatus OBJECT-TYPE
   SYNTAX     OCTET STRING (SIZE (2))
   ACCESS     read-only
   STATUS     mandatory
   DESCRIPTION
     "If supported by the component, this attribute indicates the OSI 
      Availability status of the component. Note that, even though it is 
      defined as a multi-valued set, at most one value is shown to the user.
      
      When no values are in the set, this indicates that either the attribute 
      is not supported or that none of the status conditions described 
      below are present.
      
      The value inTest indicates that the resource is undergoing a test 
      procedure. If adminState is locked or shuttingDown, the normal 
      users are precluded from using the resource and controlStatus is 
      reservedForTest. Tests that do not exclude additional users can be 
      present in any operational or administrative state but the 
      reservedForTest condition should not be present.
      
      The value failed indicates that the component has an internal fault 
      that prevents it from operating. The operationalState is disabled.
      
      The value dependency indicates that the component cannot operate 
      because some other resource on which it depends is unavailable. 
      The operationalState is disabled.
      
      The value powerOff indicates the resource requires power to be 
      applied and it is not powered on. The operationalState is disabled.
      
      The value offLine indicates the resource requires a routine 
      operation (either manual, automatic, or both) to be performed to 
      place it on-line and make it available for use. The operationalState 
      is disabled.
      
      The value offDuty indicates the resource is inactive in accordance 
      with a predetermined time schedule. In the absence of other 
      disabling conditions, the operationalState is enabled or disabled.
      
      The value degraded indicates the service provided by the 
      component is degraded in some way, such as in speed or operating 
      capacity. However, the resource remains available for service. The 
      operationalState is enabled.
      
      The value notInstalled indicates the resource is not present. The 
      operationalState is disabled.
      
      The value logFull is not used.

      Description of bits:
      inTest(0)
      failed(1)
      powerOff(2)
      offLine(3)
      offDuty(4)
      dependency(5)
      degraded(6)
      notInstalled(7)
      logFull(8)"
::= { mscLpE3StateEntry 4 }

mscLpE3ProceduralStatus OBJECT-TYPE
   SYNTAX     OCTET STRING (SIZE (1))
   ACCESS     read-only
   STATUS     mandatory
   DESCRIPTION
     "If supported by the component, this attribute indicates the OSI 
      Procedural status of the component. Note that, even though it is 
      defined as a multi-valued set, at most one value is shown to the user.
      
      When no values are in the set, this indicates that either the attribute 
      is not supported or that none of the status conditions described 
      below are present.
      
      The value initializationRequired indicates (for a resource which 
      doesn't initialize autonomously) that initialization is required before 
      it can perform its normal functions, and this procedure has not been 
      initiated. The operationalState is disabled.
      
      The value notInitialized indicates (for a resource which does 
      initialize autonomously) that initialization is required before it can 
      perform its normal functions, and this procedure has not been 
      initiated. The operationalState may be enabled or disabled.
      
      The value initializing indicates that initialization has been initiated 
      but is not yet complete. The operationalState may be enabled or 
      disabled.
      
      The value reporting indicates the resource has completed some 
      processing operation and is notifying the results. The 
      operationalState is enabled.
      
      The value terminating indicates the component is in a termination 
      phase. If the resource doesn't reinitialize autonomously, 
      operationalState is disabled; otherwise it is enabled or disabled.

      Description of bits:
      initializationRequired(0)
      notInitialized(1)
      initializing(2)
      reporting(3)
      terminating(4)"
::= { mscLpE3StateEntry 5 }

mscLpE3ControlStatus OBJECT-TYPE
   SYNTAX     OCTET STRING (SIZE (1))
   ACCESS     read-only
   STATUS     mandatory
   DESCRIPTION
     "If supported by the component, this attribute indicates the OSI 
      Control status of the component. Note that, even though it is defined 
      as a multi-valued set, at most one value is shown to the user.
      
      When no values are in the set, this indicates that either the attribute 
      is not supported or that none of the status conditions described 
      below are present.
      
      The value subjectToTest indicates the resource is available but tests 
      may be conducted simultaneously at unpredictable times, which 
      may cause it to exhibit unusual characteristics.
      
      The value partOfServicesLocked indicates that part of the service is 
      restricted from users of a resource. The adminState is unlocked.
      
      The value reservedForTest indicates that the component is 
      administratively unavailable because it is undergoing a test 
      procedure. The adminState is locked.
      
      The value suspended indicates that the service has been 
      administratively suspended.

      Description of bits:
      subjectToTest(0)
      partOfServicesLocked(1)
      reservedForTest(2)
      suspended(3)"
::= { mscLpE3StateEntry 6 }

mscLpE3AlarmStatus OBJECT-TYPE
   SYNTAX     OCTET STRING (SIZE (1))
   ACCESS     read-only
   STATUS     mandatory
   DESCRIPTION
     "If supported by the component, this attribute indicates the OSI 
      Alarm status of the component. Note that, even though it is defined 
      as a multi-valued set, at most one value is shown to the user.
      
      When no values are in the set, this indicates that either the attribute 
      is not supported or that none of the status conditions described 
      below are present.
      
      The value underRepair indicates the component is currently being 
      repaired. The operationalState is enabled or disabled.
      
      The value critical indicates one or more critical alarms are 
      outstanding against the component. Other, less severe, alarms may 
      also be outstanding. The operationalState is enabled or disabled.
      
      The value major indicates one or more major alarms are 
      outstanding against the component. Other, less severe, alarms may 
      also be outstanding. The operationalState is enabled or disabled.
      
      The value minor indicates one or more minor alarms are 
      outstanding against the component. Other, less severe, alarms may 
      also be outstanding. The operationalState is enabled or disabled.
      
      The value alarmOutstanding generically indicates that an alarm of 
      some severity is outstanding against the component.

      Description of bits:
      underRepair(0)
      critical(1)
      major(2)
      minor(3)
      alarmOutstanding(4)"
::= { mscLpE3StateEntry 7 }

mscLpE3StandbyStatus OBJECT-TYPE
   SYNTAX     INTEGER  {
                 hotStandby(0),
                 coldStandby(1),
                 providingService(2),
                 notSet(15) }
   ACCESS     read-only
   STATUS     mandatory
   DESCRIPTION
     "If supported by the component, this attribute indicates the OSI 
      Standby status of the component.
      
      The value notSet indicates that either the attribute is not supported 
      or that none of the status conditions described below are present. 
      Note that this is a non-standard value, used because the original 
      specification indicated this attribute was set-valued and thus, did not 
      provide a value to indicate that none of the other three are 
      applicable.
      
      The value hotStandby indicates that the resource is not providing 
      service but will be immediately able to take over the role of the 
      resource to be backed up, without initialization activity, and 
      containing the same information as the resource to be backed up.
      
      The value coldStandby indicates the resource is a backup for 
      another resource but will not be immediately able to take over the 
      role of the backed up resource and will require some initialization 
      activity.
      
      The value providingService indicates that this component, as a 
      backup resource, is currently backing up another resource."
   DEFVAL     { notSet }
::= { mscLpE3StateEntry 8 }

mscLpE3UnknownStatus OBJECT-TYPE
   SYNTAX     INTEGER  {
                 false(0),
                 true(1) }
   ACCESS     read-only
   STATUS     mandatory
   DESCRIPTION
     "This attribute indicates the OSI Unknown status of the component.
      
      The value false indicates that all of the other OSI State and Status 
      attribute values can be considered accurate.
      
      The value true indicates that the actual state of the component is not 
      known for sure."
   DEFVAL     { false }
::= { mscLpE3StateEntry 9 }

mscLpE3OperTable OBJECT-TYPE
   SYNTAX     SEQUENCE OF MscLpE3OperEntry
   ACCESS     not-accessible
   STATUS     mandatory
   DESCRIPTION
     "This group contains the common operational data for E3 
      component."
::= { mscLpE3 16 }

mscLpE3OperEntry OBJECT-TYPE
   SYNTAX     MscLpE3OperEntry
   ACCESS     not-accessible
   STATUS     mandatory
   DESCRIPTION
     "An entry in the mscLpE3OperTable."
   INDEX {
      mscLpIndex,
      mscLpE3Index }
::= { mscLpE3OperTable 1 }

MscLpE3OperEntry ::= SEQUENCE {
   mscLpE3LosAlarm
      INTEGER,
   mscLpE3LofAlarm
      INTEGER,
   mscLpE3RxAisAlarm
      INTEGER,
   mscLpE3RxRaiAlarm
      INTEGER,
   mscLpE3TxAis
      INTEGER,
   mscLpE3TxRai
      INTEGER }

mscLpE3LosAlarm OBJECT-TYPE
   SYNTAX     INTEGER  {
                 on(0),
                 off(1) }
   ACCESS     read-only
   STATUS     mandatory
   DESCRIPTION
     "This attribute displays whether a Loss Of Signal (LOS) alarm state 
      has been entered. An LOS alarm state is entered when LOS defects 
      has been observed and accumulated for a period of 2.5 seconds +/- 
      0.5 seconds. An LOS defect is detected at the E3 line interface upon 
      observing N continuous pulse positions with no pulses of either 
      positive or negative polarity, where N is between 10 and 255. If the 
      LOS defects are intermittently occurring, the LOS defect 
      accumulator is decremented at a rate of 1/10 of the incrementing 
      rate (alarm integration ratio of 1/10), with all measurements based 
      on a 200 ms polling cycle.
      The E3 component goes into an operational state of disabled until 
      the LOS alarm condition is cleared. The LOS alarm state is cleared 
      when the LOS defects are absent for a period of 10 seconds +/- 0.5 
      seconds.
      The losAlarm attribute is always set to off when the component has 
      been locked and left offline."
   DEFVAL     { off }
::= { mscLpE3OperEntry 1 }

mscLpE3LofAlarm OBJECT-TYPE
   SYNTAX     INTEGER  {
                 on(0),
                 off(1) }
   ACCESS     read-only
   STATUS     mandatory
   DESCRIPTION
     "This attribute displays whether a Loss Of Frame (LOF) alarm state 
      has been entered. An LOF alarm state is entered when Severely 
      Errored Frame (SEF) defects have been detected and accumulated 
      for a period of 2.5 seconds +/- 0.5 seconds. An E3 SEF defect is 
      reported after detecting Frame Alignment Signal (FAS) errors on 4 
      consecutive E3 frames received on the incoming line. If the LOF 
      defects are intermittently occurring, the LOF defect accumulator is 
      decremented at a rate of 1/10 of the incrementing rate (alarm 
      integration ratio of 1/10), with all measurements based on a 200 ms 
      polling cycle.
      The E3 component goes into an operational state of disabled until 
      the LOF alarm condition is cleared. The condition is cleared when 
      E3 framing has been achieved for a period of 10 seconds +/- 0.5 
      seconds. As long as SEF defects are detected, the node also 
      transmits the far-end SEF/AIS (in G.751 E3) or FERF (in G.832) 
      defect indicator over the outgoing line. The txRai attribute is set to 
      on when transmitting the far-end SEF/AIS defect indicator on the 
      outgoing line.
      The lofAlarm attribute is always set to off when the component has 
      been locked and left offline."
   DEFVAL     { off }
::= { mscLpE3OperEntry 2 }

mscLpE3RxAisAlarm OBJECT-TYPE
   SYNTAX     INTEGER  {
                 on(0),
                 off(1) }
   ACCESS     read-only
   STATUS     mandatory
   DESCRIPTION
     "This attribute displays whether an Alarm Indication Signal (AIS) 
      alarm when state has been entered. An AIS alarm state is entered 
      when AIS defects have been observed and accumulated for a period 
      of 2.5 seconds +/- 0.5 seconds on the incoming E3 line. An AIS 
      defect is the occurrence of the AIS (unframed signal with a density 
      of zeros below a certain threshold such as defined by ITU 
      Recommendation G.775). If the AIS defects are intermittently 
      occurring, the AIS defect accumulator is decremented at a rate of 1/
      10 of the incrementing rate (alarm integration ratio of 1/10), with all 
      measurements based on a 200 ms polling cycle.
      The E3 component goes into an operational state of disabled until 
      the AIS alarm condition is cleared (after AIS has been no longer 
      detected for a period of 10 seconds +/- 0.5 seconds). As long as AIS 
      is detected on the incoming line, the node also transmits the far-end 
      SEF/AIS (in G.751 E3) or FERF (in G.832) defect indicator over 
      the outgoing line. The txRai attribute is set to on when transmitting 
      the far-end SEF/AIS defect indicator on the outgoing line.
      The rxAisAlarm attribute is always set to off when the component 
      has been locked and left offline."
   DEFVAL     { off }
::= { mscLpE3OperEntry 3 }

mscLpE3RxRaiAlarm OBJECT-TYPE
   SYNTAX     INTEGER  {
                 on(0),
                 off(1) }
   ACCESS     read-only
   STATUS     mandatory
   DESCRIPTION
     "This attribute displays whether a Remote Alarm Indication (RAI) 
      alarm state has been entered. A RAI alarm state is entered when far-
      end SEF/AIS defects (or Far-End Receive Failure (FERF) defects in 
      G.832 E3 Framing mode) have been observed and accumulated for 
      a period of 2.5 seconds +/- 0.5 seconds on the E3 incoming line. If 
      the RAI defects are intermittently occurring, the RAI defect 
      accumulator is decremented at a rate of 1/10 of the incrementing 
      rate (alarm integration ratio of 1/10), with all measurements based 
      on a 200 ms polling cycle.
      The E3 component goes into an operational state of disabled until 
      the RAI alarm condition is cleared. The condition is cleared when 
      the far-end defect indicator has not been detected for 10 seconds +/- 
      0.5 seconds. The declaration of a RAI Alarm is usually a signal that 
      the far end facility is unable to gain synchronization.
      The rxRaiAlarm attribute is always set to off when the component 
      has been locked and left offline."
   DEFVAL     { off }
::= { mscLpE3OperEntry 4 }

mscLpE3TxAis OBJECT-TYPE
   SYNTAX     INTEGER  {
                 on(0),
                 off(1) }
   ACCESS     read-only
   STATUS     mandatory
   DESCRIPTION
     "This attribute displays whether an AIS alarm is being transmitted on 
      the E3 line. AIS is transmitted on the outgoing line when the E3 
      component is locked and not used for operational testing."
   DEFVAL     { off }
::= { mscLpE3OperEntry 5 }

mscLpE3TxRai OBJECT-TYPE
   SYNTAX     INTEGER  {
                 on(0),
                 off(1) }
   ACCESS     read-only
   STATUS     mandatory
   DESCRIPTION
     "This attribute displays whether the far-end SEF/AIS defect indicator 
      is transmitted over the outgoing line when the E3 component has 
      been unlocked or used in operational testing. When the E3 
      component is locked and not used in operational testing, this 
      attribute is always set to off. The far-end SEF/AIS defect indicator is 
      transmitted over the outgoing line when SEF/AIS defects are 
      detected on the incoming line. In G.832 E3 Framing mode, the 
      FERF bit is set to '1' to transmit the SEF/AIS defect indicator."
   DEFVAL     { off }
::= { mscLpE3OperEntry 6 }

mscLpE3StatsTable OBJECT-TYPE
   SYNTAX     SEQUENCE OF MscLpE3StatsEntry
   ACCESS     not-accessible
   STATUS     mandatory
   DESCRIPTION
     "This group contains the common operational data for E3 
      component. Each attribute type is a non-negative integer which 
      monotonically increases until it reaches a maximum value, at which 
      point it wraps around and starts increasing again from zero."
::= { mscLpE3 17 }

mscLpE3StatsEntry OBJECT-TYPE
   SYNTAX     MscLpE3StatsEntry
   ACCESS     not-accessible
   STATUS     mandatory
   DESCRIPTION
     "An entry in the mscLpE3StatsTable."
   INDEX {
      mscLpIndex,
      mscLpE3Index }
::= { mscLpE3StatsTable 1 }

MscLpE3StatsEntry ::= SEQUENCE {
   mscLpE3RunningTime
      Counter32,
   mscLpE3ErrorFreeSec
      Counter32,
   mscLpE3LineCodeViolations
      Counter32,
   mscLpE3LineErroredSec
      Counter32,
   mscLpE3LineSevErroredSec
      Counter32,
   mscLpE3LineLosSec
      Counter32,
   mscLpE3LineFailures
      Counter32,
   mscLpE3PathCodeViolations
      Counter32,
   mscLpE3PathErroredSec
      Counter32,
   mscLpE3PathSevErroredSec
      Counter32,
   mscLpE3PathSefAisSec
      Counter32,
   mscLpE3PathUnavailSec
      Counter32,
   mscLpE3PathFailures
      Counter32 }

mscLpE3RunningTime OBJECT-TYPE
   SYNTAX     Counter32 
   ACCESS     read-only
   STATUS     mandatory
   DESCRIPTION
     "This attribute indicates the total number of seconds since the E3 
      component has been activated and been in unlocked state or used 
      for operational testing. All the other error counts that follow as well 
      as each E3 subcomponent's error counts can be updated when this 
      count is active."
::= { mscLpE3StatsEntry 1 }

mscLpE3ErrorFreeSec OBJECT-TYPE
   SYNTAX     Counter32 
   ACCESS     read-only
   STATUS     mandatory
   DESCRIPTION
     "This attribute indicates the number of seconds that the E3 port has 
      been in an error free state."
::= { mscLpE3StatsEntry 2 }

mscLpE3LineCodeViolations OBJECT-TYPE
   SYNTAX     Counter32 
   ACCESS     read-only
   STATUS     mandatory
   DESCRIPTION
     "This attribute indicates the total number of Line Code Violations 
      (LCV) detected. An E3 Line Code Violation is an HDB3 coded 
      signal error. LCV counting is inhibited for second intervals where a 
      Line Severely Errored Second (LSES) is counted. 
      This attribute is a non-negative integer which monotonically 
      increases until it reaches a maximum value, at which point it wraps 
      around and starts increasing again from zero."
::= { mscLpE3StatsEntry 3 }

mscLpE3LineErroredSec OBJECT-TYPE
   SYNTAX     Counter32 
   ACCESS     read-only
   STATUS     mandatory
   DESCRIPTION
     "This attribute indicates the total number of Line Errored Seconds 
      (LES) that have been counted. A LES is declared for interval 
      seconds containing one or more Line Code Violations (LCV) or one 
      or more Loss Of Signal (LOS) defects."
::= { mscLpE3StatsEntry 4 }

mscLpE3LineSevErroredSec OBJECT-TYPE
   SYNTAX     Counter32 
   ACCESS     read-only
   STATUS     mandatory
   DESCRIPTION
     "This attribute indicates the total number of Line Severely Errored 
      Seconds (LSES) that have been counted. A LSES is declared for 
      second intervals containing more than 34 Line Code Violations 
      (LCV) or one or more Loss of Signal (LOS) defects."
::= { mscLpE3StatsEntry 5 }

mscLpE3LineLosSec OBJECT-TYPE
   SYNTAX     Counter32 
   ACCESS     read-only
   STATUS     mandatory
   DESCRIPTION
     "This attribute indicates the total number of Line LOS Seconds 
      (LOSS) that have been counted. A LOSS is declared for second 
      intervals containing one or more Loss of Signal (LOS) defects."
::= { mscLpE3StatsEntry 6 }

mscLpE3LineFailures OBJECT-TYPE
   SYNTAX     Counter32 
   ACCESS     read-only
   STATUS     mandatory
   DESCRIPTION
     "This attribute indicates the total number of times that a line failure 
      (LOS failure) has been declared.
      This attribute is a non-negative integer which monotonically 
      increases until it reaches a maximum value, at which point it wraps 
      around and starts increasing again from zero."
::= { mscLpE3StatsEntry 7 }

mscLpE3PathCodeViolations OBJECT-TYPE
   SYNTAX     Counter32 
   ACCESS     read-only
   STATUS     mandatory
   DESCRIPTION
     "This attribute indicates the total number of Path Code Violations 
      (PCV) detected. An E3 PCV is an error in the Frame Alignment 
      (FA) signal, or, in G.832 Framing Mode, an error in the Frame 
      Alignment signal or a BIP-8 error. PCV counting is inhibited over 
      second intervals where a Path Severely Errored Second (PSES) is 
      counted. Counting of PCVs is also inhibited over second intervals 
      where a Path Unavailable Second (PUAS) is counted. 
      This attribute is a non-negative integer which monotonically 
      increases until it reaches a maximum value, at which point it wraps 
      around and starts increasing again from zero."
::= { mscLpE3StatsEntry 8 }

mscLpE3PathErroredSec OBJECT-TYPE
   SYNTAX     Counter32 
   ACCESS     read-only
   STATUS     mandatory
   DESCRIPTION
     "This attribute indicates the total number of Path Errored Seconds 
      (PES) that have been counted. A PES is declared for second 
      intervals containing one or more Path Code Violations (PCV) or one 
      or more Severely Errored Frame (SEF) or Alarm Indication Signal 
      (AIS) defects. Counting of Path Errored Seconds is inhibited when 
      a Path Unavailable Second (PUAS) is counted over the monitored 
      second."
::= { mscLpE3StatsEntry 9 }

mscLpE3PathSevErroredSec OBJECT-TYPE
   SYNTAX     Counter32 
   ACCESS     read-only
   STATUS     mandatory
   DESCRIPTION
     "This attribute indicates the total number of Path Severely Errored 
      Seconds (PSES) that have been counted. A PSES is declared for 
      second intervals containing more than 22 (G.751 E3) or 34 (G.832 
      E3) Path Code Violations (PCV) or one or more Severely Errored 
      Frame (SEF) or Alarm Indication Signal (AIS) defects. Counting of 
      PSESs is inhibited when a Path Unavailable Second (PUAS) is 
      counted over the monitored second."
::= { mscLpE3StatsEntry 10 }

mscLpE3PathSefAisSec OBJECT-TYPE
   SYNTAX     Counter32 
   ACCESS     read-only
   STATUS     mandatory
   DESCRIPTION
     "This attribute indicates the total number of Path SEF/AIS Seconds 
      (PSAS). A PSAS is declared for second intervals containing one or 
      more Severely Errored Frame (SEF) or Alarm Indication Signal 
      (AIS) defects. Counting of PSAS is inhibited when Path 
      Unavailable Seconds (PUAS) is counted over the monitored second."
::= { mscLpE3StatsEntry 11 }

mscLpE3PathUnavailSec OBJECT-TYPE
   SYNTAX     Counter32 
   ACCESS     read-only
   STATUS     mandatory
   DESCRIPTION
     "This attribute indicates the total number of one second intervals for 
      which the E3 path is unavailable. The E3 path becomes unavailable 
      at the onset of 10 consecutive Path Severely Errored Seconds 
      (PSES). The 10 PSESs are included in the unavailable time. Once 
      unavailable, the E3 path becomes available at the onset of 10 
      contiguous seconds with no PSES. The 10 seconds with no PSES 
      are excluded from the unavailable time. For second intervals where 
      PUAS is counted, counting of Path Code Violations (PCV), Path 
      Errored Seconds (PES), Path Severely Errored Seconds (PSES) and 
      Path SefAis Seconds (PSAS) is inhibited."
::= { mscLpE3StatsEntry 12 }

mscLpE3PathFailures OBJECT-TYPE
   SYNTAX     Counter32 
   ACCESS     read-only
   STATUS     mandatory
   DESCRIPTION
     "This attribute indicates the total number of times that a path failure 
      (LOF/AIS failure) has been declared.
      This attribute is a non-negative integer which monotonically 
      increases until it reaches a maximum value, at which point it wraps 
      around and starts increasing again from zero."
::= { mscLpE3StatsEntry 13 }


-- 
-- The Test component is configured to control a hardware facility test 
-- on a physical (V35, X21, DS1, E1, DS3, E3 etc.) or a logical port.

mscLpE3Test OBJECT IDENTIFIER ::= { mscLpE3 2 }



mscLpE3TestRowStatusTable OBJECT-TYPE
   SYNTAX     SEQUENCE OF MscLpE3TestRowStatusEntry
   ACCESS     not-accessible
   STATUS     mandatory
   DESCRIPTION
     "This entry controls the addition and deletion of 
      mscLpE3Test components."
::= { mscLpE3Test 1 }

mscLpE3TestRowStatusEntry OBJECT-TYPE
   SYNTAX     MscLpE3TestRowStatusEntry
   ACCESS     not-accessible
   STATUS     mandatory
   DESCRIPTION
     "A single entry in the table represents a single 
      mscLpE3Test component."
   INDEX {
      mscLpIndex,
      mscLpE3Index,
      mscLpE3TestIndex }
::= { mscLpE3TestRowStatusTable 1 }

MscLpE3TestRowStatusEntry ::= SEQUENCE {
   mscLpE3TestRowStatus
      RowStatus,
   mscLpE3TestComponentName
      DisplayString,
   mscLpE3TestStorageType
      StorageType,
   mscLpE3TestIndex
      NonReplicated }

mscLpE3TestRowStatus OBJECT-TYPE
   SYNTAX     RowStatus 
   ACCESS     read-only
   STATUS     mandatory
   DESCRIPTION
     "This variable is used as the basis for SNMP naming of
      mscLpE3Test components.
      These components cannot be added nor deleted."
::= { mscLpE3TestRowStatusEntry 1 }

mscLpE3TestComponentName OBJECT-TYPE
   SYNTAX     DisplayString 
   ACCESS     read-only
   STATUS     mandatory
   DESCRIPTION
     "This variable provides the component's string name for
      use with the ASCII Console Interface"
::= { mscLpE3TestRowStatusEntry 2 }

mscLpE3TestStorageType OBJECT-TYPE
   SYNTAX     StorageType 
   ACCESS     read-only
   STATUS     mandatory
   DESCRIPTION
     "This variable represents the storage type value for the
      mscLpE3Test tables."
::= { mscLpE3TestRowStatusEntry 4 }

mscLpE3TestIndex OBJECT-TYPE
   SYNTAX     NonReplicated 
   ACCESS     not-accessible
   STATUS     mandatory
   DESCRIPTION
     "This variable represents the index for the mscLpE3Test tables."
::= { mscLpE3TestRowStatusEntry 10 }

mscLpE3TestStateTable OBJECT-TYPE
   SYNTAX     SEQUENCE OF MscLpE3TestStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscLpE3Test 10 }

mscLpE3TestStateEntry OBJECT-TYPE
   SYNTAX     MscLpE3TestStateEntry
   ACCESS     not-accessible
   STATUS     mandatory
   DESCRIPTION
     "An entry in the mscLpE3TestStateTable."
   INDEX {
      mscLpIndex,
      mscLpE3Index,
      mscLpE3TestIndex }
::= { mscLpE3TestStateTable 1 }

MscLpE3TestStateEntry ::= SEQUENCE {
   mscLpE3TestAdminState
      INTEGER,
   mscLpE3TestOperationalState
      INTEGER,
   mscLpE3TestUsageState
      INTEGER }

mscLpE3TestAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscLpE3TestStateEntry 1 }

mscLpE3TestOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscLpE3TestStateEntry 2 }

mscLpE3TestUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscLpE3TestStateEntry 3 }

mscLpE3TestSetupTable OBJECT-TYPE
   SYNTAX     SEQUENCE OF MscLpE3TestSetupEntry
   ACCESS     not-accessible
   STATUS     mandatory
   DESCRIPTION
     "This group contains all of the operational data for a Test 
      component."
::= { mscLpE3Test 11 }

mscLpE3TestSetupEntry OBJECT-TYPE
   SYNTAX     MscLpE3TestSetupEntry
   ACCESS     not-accessible
   STATUS     mandatory
   DESCRIPTION
     "An entry in the mscLpE3TestSetupTable."
   INDEX {
      mscLpIndex,
      mscLpE3Index,
      mscLpE3TestIndex }
::= { mscLpE3TestSetupTable 1 }

MscLpE3TestSetupEntry ::= SEQUENCE {
   mscLpE3TestPurpose
      AsciiString,
   mscLpE3TestType
      INTEGER,
   mscLpE3TestFrmSize
      Unsigned32,
   mscLpE3TestFrmPatternType
      INTEGER,
   mscLpE3TestCustomizedPattern
      Hex,
   mscLpE3TestDataStartDelay
      Unsigned32,
   mscLpE3TestDisplayInterval
      Unsigned32,
   mscLpE3TestDuration
      Unsigned32 }

mscLpE3TestPurpose OBJECT-TYPE
   SYNTAX     AsciiString (SIZE (0..40))
   ACCESS     read-write
   STATUS     mandatory
   DESCRIPTION
     "This attribute records the purpose of the test so that the test results 
      can be associated and properly analyzed."
::= { mscLpE3TestSetupEntry 1 }

mscLpE3TestType OBJECT-TYPE
   SYNTAX     INTEGER  {
                 card(0),
                 manual(1),
                 localLoop(2),
                 remoteLoop(3),
                 externalLoop(4),
                 payloadLoop(5),
                 remoteLoopThisTrib(6),
                 v54RemoteLoop(7),
                 pn127RemoteLoop(8) }
   ACCESS     read-write
   STATUS     mandatory
   DESCRIPTION
     "This attribute is the type of test to be run. The available test types 
      include the following:
      card test sets up an internal loop on the board and runs a bit error 
      rate test.
      manual test assumes the line is looped back externally and a bit 
      error rate test is performed.
      localLoop test loops back the local modem and performs a bit error 
      rate test.
      remoteLoop test loops back the remote modem (or CSU) and 
      performs a bit error rate test.
      externalLoop test loops back the line to the far end.
      payloadLoop test only loops back the payload data received from 
      the incoming line.
      remoteLoopThisTrib loops this particular tributary back at the far 
      end, using services provided by the parent.
      v54RemoteLoop initiates a V.54 Remote Loopback test.
      pn127RemoteLoop initiates a PN127 Remote Loopback test.
      Note that not all test types are not supported by all function 
      processors."
   DEFVAL     { card }
::= { mscLpE3TestSetupEntry 2 }

mscLpE3TestFrmSize OBJECT-TYPE
   SYNTAX     Unsigned32 (4..4096)
   ACCESS     read-write
   STATUS     mandatory
   DESCRIPTION
     "This attribute defines the size of the test data frames in number of 
      bytes."
   DEFVAL     { 1024 }
::= { mscLpE3TestSetupEntry 3 }

mscLpE3TestFrmPatternType OBJECT-TYPE
   SYNTAX     INTEGER  {
                 ccitt32kBitPattern(0),
                 ccitt8MBitPattern(1),
                 customizedPattern(2) }
   ACCESS     read-write
   STATUS     mandatory
   DESCRIPTION
     "This attribute defines the type of data pattern generation to use. The 
      following lists the available pattern types:
      ccitt32kBitPattern is a pseudo-random sequence of 32 kbit.
      ccitt8MBitPattern is a pseudo-random sequence of 8Mbit.
      customizedPattern is the pattern defined in the customizedPattern 
      attribute."
   DEFVAL     { ccitt32kBitPattern }
::= { mscLpE3TestSetupEntry 4 }

mscLpE3TestCustomizedPattern OBJECT-TYPE
   SYNTAX     Hex (0..4294967295)
   ACCESS     read-write
   STATUS     mandatory
   DESCRIPTION
     "This attribute allows a customized 32 bit pattern to be defined for 
      use in the test data frames. This attribute is used when the attribute 
      frmPatternType is set to CustomizedPattern. Note that a 55 hex 
      pattern is an alternating 1 and 0 pattern."
   DEFVAL     { 1431655765 }
::= { mscLpE3TestSetupEntry 5 }

mscLpE3TestDataStartDelay OBJECT-TYPE
   SYNTAX     Unsigned32 (0..1814400)
   ACCESS     read-write
   STATUS     mandatory
   DESCRIPTION
     "This attribute specifies the time delay (in seconds) between when 
      the test expects the loop to have been set up, to when the test data 
      actually starts to be transmitted. This attribute is to accommodate 
      some non-standard equipment that requires extra time for setting up 
      a requested loop.
      This attribute is ignored when the test type is set to externalLoop."
   DEFVAL     { 0 }
::= { mscLpE3TestSetupEntry 6 }

mscLpE3TestDisplayInterval OBJECT-TYPE
   SYNTAX     Unsigned32 (0..30240)
   ACCESS     read-write
   STATUS     mandatory
   DESCRIPTION
     "This attribute defines the interval (in minutes) between which 
      interim test results are to be displayed. Results are displayed at the 
      operator console at which the test was started. When the test type is 
      set to externalLoop, this attribute is ignored. There will be no 
      display of results if displayInterval is set to 0. This attribute can be 
      changed anytime."
   DEFVAL     { 5 }
::= { mscLpE3TestSetupEntry 7 }

mscLpE3TestDuration OBJECT-TYPE
   SYNTAX     Unsigned32 (1..30240)
   ACCESS     read-write
   STATUS     mandatory
   DESCRIPTION
     "This attribute is the duration (in minutes) that test data will be 
      transmitted. In the case of an externalLoop, this is the time that the 
      loop is in effect. Note that dataStartDelay does not apply to the 
      externalLoop."
   DEFVAL     { 1 }
::= { mscLpE3TestSetupEntry 8 }

mscLpE3TestResultsTable OBJECT-TYPE
   SYNTAX     SEQUENCE OF MscLpE3TestResultsEntry
   ACCESS     not-accessible
   STATUS     mandatory
   DESCRIPTION
     "This group contains all the statistics related attributes of the Test 
      component."
::= { mscLpE3Test 12 }

mscLpE3TestResultsEntry OBJECT-TYPE
   SYNTAX     MscLpE3TestResultsEntry
   ACCESS     not-accessible
   STATUS     mandatory
   DESCRIPTION
     "An entry in the mscLpE3TestResultsTable."
   INDEX {
      mscLpIndex,
      mscLpE3Index,
      mscLpE3TestIndex }
::= { mscLpE3TestResultsTable 1 }

MscLpE3TestResultsEntry ::= SEQUENCE {
   mscLpE3TestElapsedTime
      Counter32,
   mscLpE3TestTimeRemaining
      Unsigned32,
   mscLpE3TestCauseOfTermination
      INTEGER,
   mscLpE3TestBitsTx
      PassportCounter64,
   mscLpE3TestBytesTx
      PassportCounter64,
   mscLpE3TestFrmTx
      PassportCounter64,
   mscLpE3TestBitsRx
      PassportCounter64,
   mscLpE3TestBytesRx
      PassportCounter64,
   mscLpE3TestFrmRx
      PassportCounter64,
   mscLpE3TestErroredFrmRx
      PassportCounter64,
   mscLpE3TestBitErrorRate
      AsciiString }

mscLpE3TestElapsedTime OBJECT-TYPE
   SYNTAX     Counter32 
   ACCESS     read-only
   STATUS     mandatory
   DESCRIPTION
     "This attribute is the number of minutes elapsed since the test started 
      for an externalLoop test. For a data test, this is the time since test 
      data was first transmitted."
::= { mscLpE3TestResultsEntry 1 }

mscLpE3TestTimeRemaining OBJECT-TYPE
   SYNTAX     Unsigned32 (0..4294967295)
   ACCESS     read-only
   STATUS     mandatory
   DESCRIPTION
     "This attribute is the number of minutes remaining before the test is 
      to be stopped according to the duration attribute."
   DEFVAL     { 0 }
::= { mscLpE3TestResultsEntry 2 }

mscLpE3TestCauseOfTermination OBJECT-TYPE
   SYNTAX     INTEGER  {
                 testTimeExpired(0),
                 stoppedByOperator(1),
                 unknown(2),
                 neverStarted(3),
                 testRunning(4),
                 hardwareReconfigured(5),
                 loopCodeSyncFailed(6),
                 patternSyncFailed(7),
                 patternSyncLost(8) }
   ACCESS     read-only
   STATUS     mandatory
   DESCRIPTION
     "This attribute indicates either the status of the test or the cause of 
      the test's termination:
      
      neverStarted indicates that the test has not yet been started.
      
      testRunning indicates that the test has been started.
      
      stoppedByOperator indicates that the operator issued a stop 
      command on a test that was running.
      
      testTimeExpired indicates that the test ran for the time specified by 
      the test's duration.
      
      loopCodeSyncFailed indicates that the local end failed to 
      synchronize to the loopCode pattern. The local end transmits the 
      loopCode pattern to cause the remote end to apply a loopback, after 
      which the local end should receive the loopCode pattern. The exact 
      pattern used to request loopCode depends on the test type. This 
      failure indicates a high rate of transmission errors, or that the 
      remote end has failed to apply the loopback.
      
      patternSyncFailed indicates that the local end failed to synchronize 
      to the frmPatternType test pattern, that should have been looped 
      back at the remote end. This failure indicates a high rate of 
      transmission errors or the absence of a loopback.
      
      patternSyncLost indicates that the local end gained and then lost 
      synchronization to the returned frmPatternType test pattern. This 
      failure indicates a sudden increase in transmission errors, frame 
      slippage, or the removal of an existing loopback.
      
      unknown is set when a reason to terminate other than those listed 
      here is encountered.
      
      Note: Only MSA cards support recognition of the failures 
      loopCodeSyncFailed, patternSyncFailed and patternSyncLost. 
      Other cards will not terminate the test under the conditions 
      described by these values."
   DEFVAL     { neverStarted }
::= { mscLpE3TestResultsEntry 3 }

mscLpE3TestBitsTx OBJECT-TYPE
   SYNTAX     PassportCounter64 
   ACCESS     read-only
   STATUS     mandatory
   DESCRIPTION
     "This attribute is the total number of bits sent during the test period. 
      As long as the line speed of the hardware interface is less than 
      70 Mbit/s, this counter is not expected to reach the maximum value."
::= { mscLpE3TestResultsEntry 4 }

mscLpE3TestBytesTx OBJECT-TYPE
   SYNTAX     PassportCounter64 
   ACCESS     read-only
   STATUS     mandatory
   DESCRIPTION
     "This attribute is the total number of bytes sent during the test 
      period. This counter is not expected to reach its maximum value."
::= { mscLpE3TestResultsEntry 5 }

mscLpE3TestFrmTx OBJECT-TYPE
   SYNTAX     PassportCounter64 
   ACCESS     read-only
   STATUS     mandatory
   DESCRIPTION
     "This attribute is the total number of frames sent during the test 
      period. This counter is not expected to reach its maximum value."
::= { mscLpE3TestResultsEntry 6 }

mscLpE3TestBitsRx OBJECT-TYPE
   SYNTAX     PassportCounter64 
   ACCESS     read-only
   STATUS     mandatory
   DESCRIPTION
     "This attribute is the total number of bits received during the test 
      period. This counter is not expected to reach its maximum value. 
      The counter will wrap around to 0 if it does reach the maximum 
      value."
::= { mscLpE3TestResultsEntry 7 }

mscLpE3TestBytesRx OBJECT-TYPE
   SYNTAX     PassportCounter64 
   ACCESS     read-only
   STATUS     mandatory
   DESCRIPTION
     "This attribute is the total number of bytes received during the test 
      period. This counter is not expected to reach its maximum value. 
      The counter will wrap around to 0 if it does reach its maximum 
      value."
::= { mscLpE3TestResultsEntry 8 }

mscLpE3TestFrmRx OBJECT-TYPE
   SYNTAX     PassportCounter64 
   ACCESS     read-only
   STATUS     mandatory
   DESCRIPTION
     "This attribute is the total number of frames received during the test 
      period. This counter is not expected to reach its maximum value. 
      The counter will wrap around to 0 if it does reach its maximum 
      value."
::= { mscLpE3TestResultsEntry 9 }

mscLpE3TestErroredFrmRx OBJECT-TYPE
   SYNTAX     PassportCounter64 
   ACCESS     read-only
   STATUS     mandatory
   DESCRIPTION
     "This attribute is not displayed for ATM cards because the physical 
      layer drops all errored frames at the controller interface. 
      
      For all other card types, this attribute is the total number of errored 
      frames received during the test period. This counter is not expected 
      to reach its maximum value. The counter will wrap around to 0 if it 
      does reach its maximum value."
::= { mscLpE3TestResultsEntry 10 }

mscLpE3TestBitErrorRate OBJECT-TYPE
   SYNTAX     AsciiString (SIZE (5))
   ACCESS     read-only
   STATUS     mandatory
   DESCRIPTION
     "This attribute is not displayed for ATM cards because the physical 
      layer drops all errored frames at the controller interface. 
      
      For all other card types, this attribute is the calculated bit error rate 
      on the link. Test data are generated and sent in frames of a preset 
      size (frameSize). The Test component will try to estimate the 
      number of bit errors in any errored frame which is identifiable. The 
      statistics will be updated accordingly. A lost frame (may be due to 
      an error on the flag sequence) will be discarded for the bit error rate 
      calculation. The result is presented in the form of xEsyy, where x is 
      the mantissa, syy is the exponent, for example 0E+00, 2E-09.
      Note that the bitErrorRate is an estimate only. For more reliable test 
      results, the test should be done over a long period. Multiple tests 
      would also improve the confidence level of the test results."
::= { mscLpE3TestResultsEntry 11 }


-- G832
-- The G832 component is configured to display all E3 G832 related 
-- operational and statistical data. It will appear under the E3 
-- components when the E3 framing attribute is set to g832.
-- Note: when E3 framing is changed from g832 to g751, the G832 
-- component must be deleted.

mscLpE3G832 OBJECT IDENTIFIER ::= { mscLpE3 3 }



mscLpE3G832RowStatusTable OBJECT-TYPE
   SYNTAX     SEQUENCE OF MscLpE3G832RowStatusEntry
   ACCESS     not-accessible
   STATUS     mandatory
   DESCRIPTION
     "This entry controls the addition and deletion of 
      mscLpE3G832 components."
::= { mscLpE3G832 1 }

mscLpE3G832RowStatusEntry OBJECT-TYPE
   SYNTAX     MscLpE3G832RowStatusEntry
   ACCESS     not-accessible
   STATUS     mandatory
   DESCRIPTION
     "A single entry in the table represents a single 
      mscLpE3G832 component."
   INDEX {
      mscLpIndex,
      mscLpE3Index,
      mscLpE3G832Index }
::= { mscLpE3G832RowStatusTable 1 }

MscLpE3G832RowStatusEntry ::= SEQUENCE {
   mscLpE3G832RowStatus
      RowStatus,
   mscLpE3G832ComponentName
      DisplayString,
   mscLpE3G832StorageType
      StorageType,
   mscLpE3G832Index
      NonReplicated }

mscLpE3G832RowStatus OBJECT-TYPE
   SYNTAX     RowStatus 
   ACCESS     read-write
   STATUS     mandatory
   DESCRIPTION
     "This variable is used as the basis for SNMP naming of
      mscLpE3G832 components.
      These components can be added and deleted."
::= { mscLpE3G832RowStatusEntry 1 }

mscLpE3G832ComponentName OBJECT-TYPE
   SYNTAX     DisplayString 
   ACCESS     read-only
   STATUS     mandatory
   DESCRIPTION
     "This variable provides the component's string name for
      use with the ASCII Console Interface"
::= { mscLpE3G832RowStatusEntry 2 }

mscLpE3G832StorageType OBJECT-TYPE
   SYNTAX     StorageType 
   ACCESS     read-only
   STATUS     mandatory
   DESCRIPTION
     "This variable represents the storage type value for the
      mscLpE3G832 tables."
::= { mscLpE3G832RowStatusEntry 4 }

mscLpE3G832Index OBJECT-TYPE
   SYNTAX     NonReplicated 
   ACCESS     not-accessible
   STATUS     mandatory
   DESCRIPTION
     "This variable represents the index for the mscLpE3G832 tables."
::= { mscLpE3G832RowStatusEntry 10 }

mscLpE3G832ProvisionedTable OBJECT-TYPE
   SYNTAX     SEQUENCE OF MscLpE3G832ProvisionedEntry
   ACCESS     not-accessible
   STATUS     mandatory
   DESCRIPTION
     "This group contains the provisionable data for the G832 component."
::= { mscLpE3G832 10 }

mscLpE3G832ProvisionedEntry OBJECT-TYPE
   SYNTAX     MscLpE3G832ProvisionedEntry
   ACCESS     not-accessible
   STATUS     mandatory
   DESCRIPTION
     "An entry in the mscLpE3G832ProvisionedTable."
   INDEX {
      mscLpIndex,
      mscLpE3Index,
      mscLpE3G832Index }
::= { mscLpE3G832ProvisionedTable 1 }

MscLpE3G832ProvisionedEntry ::= SEQUENCE {
   mscLpE3G832TrailTraceTransmitted
      AsciiString,
   mscLpE3G832TrailTraceExpected
      AsciiString }

mscLpE3G832TrailTraceTransmitted OBJECT-TYPE
   SYNTAX     AsciiString (SIZE (0..15))
   ACCESS     read-write
   STATUS     mandatory
   DESCRIPTION
     "This attribute indicates the E.164 address which is to be encoded in 
      the trail access point identifier, which is transmitted using the Trail 
      Trace (TR) field of the transmitted E3 Frame. 
      Both the expected trail access point identifier and the transmitted 
      trail access point identifier are provisionable attributes of the G832 
      component.
      The 16 byte Trail Trace frame is composed of one byte containing a 
      frame start marker and a CRC-7 calculation over the previous 
      frame, and 15 bytes for transporting an E.164 address. If less than 
      the full 15 bytes are used, the address is padded with NULL 
      characters."
   DEFVAL     { ''H }  -- ""
::= { mscLpE3G832ProvisionedEntry 1 }

mscLpE3G832TrailTraceExpected OBJECT-TYPE
   SYNTAX     AsciiString (SIZE (0..15))
   ACCESS     read-write
   STATUS     mandatory
   DESCRIPTION
     "This attribute indicates the E.164 address which is expected in the 
      trail access point identifier, which is transmitted using the Trail 
      Trace (TR) field of the transmitted E3 Frame. 
      Both the expected trail access point identifier and the transmitted 
      trail access point identifier are provisionable attributes of the G832 
      component.
      The 16 byte Trail Trace frame is composed of one byte containing a 
      frame start marker and a CRC-7 calculation over the previous 
      frame, and 15 bytes for transporting an E.164 address. If less than 
      the full 15 bytes are used, the address is padded with NULL 
      characters."
   DEFVAL     { ''H }  -- ""
::= { mscLpE3G832ProvisionedEntry 2 }

mscLpE3G832OperationalTable OBJECT-TYPE
   SYNTAX     SEQUENCE OF MscLpE3G832OperationalEntry
   ACCESS     not-accessible
   STATUS     mandatory
   DESCRIPTION
     "This group contains the operational data for the G832 component."
::= { mscLpE3G832 11 }

mscLpE3G832OperationalEntry OBJECT-TYPE
   SYNTAX     MscLpE3G832OperationalEntry
   ACCESS     not-accessible
   STATUS     mandatory
   DESCRIPTION
     "An entry in the mscLpE3G832OperationalTable."
   INDEX {
      mscLpIndex,
      mscLpE3Index,
      mscLpE3G832Index }
::= { mscLpE3G832OperationalTable 1 }

MscLpE3G832OperationalEntry ::= SEQUENCE {
   mscLpE3G832UnexpectedPayloadType
      INTEGER,
   mscLpE3G832TrailTraceMismatch
      INTEGER,
   mscLpE3G832TimingMarker
      INTEGER,
   mscLpE3G832TrailTraceReceived
      AsciiString }

mscLpE3G832UnexpectedPayloadType OBJECT-TYPE
   SYNTAX     INTEGER  {
                 on(0),
                 off(1) }
   ACCESS     read-only
   STATUS     mandatory
   DESCRIPTION
     "This attribute displays whether the Unexpected Payload Type (UPT) 
      alarm state has been entered. The UPT alarm state is entered when 
      UPT defects have been observed and accumulated for a period of 
      2.5 seconds +/- 0.5 seconds. The UPT defect is reported when a 
      received frame fails to agree with the expected Payload Type. If the 
      UPT defects are intermittently occurring, the UPT defect 
      accumulator is decremented at a rate of 1/10 of the incrementing 
      rate (alarm integration ratio of 1/10), with all measurements based 
      on a 200 ms polling cycle..
      The UPT alarm is cleared when the Payload Type in the received 
      frame agrees with the expected Payload Type for a period of 10 
      seconds +/- 0.5 seconds.
      The unexpectedPayloadType attribute is always set to off when the 
      E3 component has been locked and left offline."
::= { mscLpE3G832OperationalEntry 1 }

mscLpE3G832TrailTraceMismatch OBJECT-TYPE
   SYNTAX     INTEGER  {
                 on(0),
                 off(1) }
   ACCESS     read-only
   STATUS     mandatory
   DESCRIPTION
     "This attribute displays whether the Trail Trace Mismatch (TTM) 
      alarm state has been entered. The TTM alarm state is entered when 
      TTM defects have been observed and accumulated for a period of 
      2.5 seconds +/- 0.5 seconds. The TTM defect is reported when the 
      trail access point identifier contained in the Trail Trace (TR) field in 
      the received frame fails to agree with the expected identifier. If the 
      TTM defects are intermittently occurring, the TTM defect 
      accumulator is decremented at a rate of 1/10 of the incrementing 
      rate (alarm integration ratio of 1/10), with all measurements based 
      on a 200 ms polling cycle.
      The TTM alarm is cleared when the trail access point identifier in 
      the received frame agrees with the expected identifier for a period of 
      10 seconds +/- 0.5 seconds.
      The trailTraceMismatch attribute is always set to off when the E3 
      component has been locked and left offline.
      Both the expected trail access identifier and the transmitted trail 
      access identifier are provisionable attributes of the G832 
      component."
::= { mscLpE3G832OperationalEntry 2 }

mscLpE3G832TimingMarker OBJECT-TYPE
   SYNTAX     INTEGER  {
                 notTraceable(0),
                 traceable(1) }
   ACCESS     read-only
   STATUS     mandatory
   DESCRIPTION
     "Indicates whether or not the timing source at the far-end node is 
      traceable to a Primary Reference Clock. 
      The timingMarker indication is controlled by the timing marker bit 
      in the G832 MA byte. If the received timing marker bit is 1 for five 
      consecutive frames, and five consecutive 0s are not received for two 
      seconds, the timingMarker indication will be set to not traceable. If 
      the received timing marker bit is 0 for five consecutive frames and 
      five consecutive 1s are not received for two seconds, the 
      timingMarker indication will be set to traceable."
::= { mscLpE3G832OperationalEntry 3 }

mscLpE3G832TrailTraceReceived OBJECT-TYPE
   SYNTAX     AsciiString (SIZE (0..15))
   ACCESS     read-only
   STATUS     mandatory
   DESCRIPTION
     "This attribute indicates the 15 byte E.164 address which is currently 
      being received in the trail trace (TR) field of the E3 G832 frame. If 
      this attribute differs from the provisioned trailTraceTransmitted 
      string a trail trace mismatch (TTM) defect is reported, possibly 
      resulting in a TTM alarm, as described for operational attribute 
      trailTraceMismatch."
::= { mscLpE3G832OperationalEntry 4 }

mscLpE3G832StatsTable OBJECT-TYPE
   SYNTAX     SEQUENCE OF MscLpE3G832StatsEntry
   ACCESS     not-accessible
   STATUS     mandatory
   DESCRIPTION
     "This group contains the statistical data for the G832 component. 
      Each attribute type is a non-negative integer which monotonically 
      increases until it reaches a maximum value, at which point it wraps 
      around and starts increasing again from zero."
::= { mscLpE3G832 12 }

mscLpE3G832StatsEntry OBJECT-TYPE
   SYNTAX     MscLpE3G832StatsEntry
   ACCESS     not-accessible
   STATUS     mandatory
   DESCRIPTION
     "An entry in the mscLpE3G832StatsTable."
   INDEX {
      mscLpIndex,
      mscLpE3Index,
      mscLpE3G832Index }
::= { mscLpE3G832StatsTable 1 }

MscLpE3G832StatsEntry ::= SEQUENCE {
   mscLpE3G832FarEndErrorFreeSec
      Counter32,
   mscLpE3G832FarEndCodeViolations
      Counter32,
   mscLpE3G832FarEndErroredSec
      Counter32,
   mscLpE3G832FarEndSevErroredSec
      Counter32,
   mscLpE3G832FarEndSefAisSec
      Counter32,
   mscLpE3G832FarEndUnavailSec
      Counter32 }

mscLpE3G832FarEndErrorFreeSec OBJECT-TYPE
   SYNTAX     Counter32 
   ACCESS     read-only
   STATUS     mandatory
   DESCRIPTION
     "This attribute indicates the number of seconds that the E3 line has 
      not suffered any G832 errors."
::= { mscLpE3G832StatsEntry 1 }

mscLpE3G832FarEndCodeViolations OBJECT-TYPE
   SYNTAX     Counter32 
   ACCESS     read-only
   STATUS     mandatory
   DESCRIPTION
     "A count of E3 frames containing a Far-End Block Error (FEBE). A 
      FEBE is reported over the FEBE bit each time the far-end terminal 
      detects a BIP-8 error in a received E3 frame. For second intervals 
      where Far End Unavailable Seconds (FEUAS) or Far End Severely 
      Errored Seconds (FESES) are counted, counting of FECVs is 
      inhibited.
      This attribute is a non-negative integer which monotonically 
      increases until it reaches a maximum value, at which point it wraps 
      around and starts increasing again from zero."
::= { mscLpE3G832StatsEntry 2 }

mscLpE3G832FarEndErroredSec OBJECT-TYPE
   SYNTAX     Counter32 
   ACCESS     read-only
   STATUS     mandatory
   DESCRIPTION
     "This attribute indicates the total number of Far-End Errored 
      Seconds (FEES). A FEES is declared for second intervals 
      containing with one or more Far-End Coding Violations (FECV) or 
      one or more Far-End Receive Failure (FERF) defects. A FERF 
      defect occurs when the FERF bit in the received frame is set to one. 
      For second intervals where Far End Unavailable Seconds (FEUAS) 
      are counted, counting of FEESs is inhibited."
::= { mscLpE3G832StatsEntry 3 }

mscLpE3G832FarEndSevErroredSec OBJECT-TYPE
   SYNTAX     Counter32 
   ACCESS     read-only
   STATUS     mandatory
   DESCRIPTION
     "This attribute indicates the total number of Far-End Severely 
      Errored Seconds (FESESs). A FESES is declared for second 
      intervals containing more than 34 Far-End Coding Violations 
      (FECV) or one or more Far-End Receive Failure (FERF) defects. 
      For second intervals where a Far-End Severely Errored Seconds 
      (FESES) is counted, counting of FECVs is inhibited. For second 
      intervals where Far End Unavailable Seconds (FEUAS) are counted, 
      counting of FESESs is inhibited."
::= { mscLpE3G832StatsEntry 4 }

mscLpE3G832FarEndSefAisSec OBJECT-TYPE
   SYNTAX     Counter32 
   ACCESS     read-only
   STATUS     mandatory
   DESCRIPTION
     "This attribute indicates the total number of Far-End SEF/AIS 
      Seconds (FESAS). A FESAS is declared for second intervals 
      containing one or more Far-End Receive Failure (FERF) defects. 
      For second intervals where Far End Unavailable Seconds (FEUAS) 
      are counted, counting of FESAS is inhibited."
::= { mscLpE3G832StatsEntry 5 }

mscLpE3G832FarEndUnavailSec OBJECT-TYPE
   SYNTAX     Counter32 
   ACCESS     read-only
   STATUS     mandatory
   DESCRIPTION
     "This attribute indicates the total number of one second intervals for 
      which the E3 far-end path is unavailable. The E3 far-end path 
      becomes unavailable at the onset of 10 consecutive Far End 
      Severely Errored Seconds (FESES). It comes available at the onset 
      of 10 contiguous seconds with no FESES. The unavailable time 
      includes the initial 10 seconds to enter the unavailable state but not 
      the 10 seconds to exit the state For second intervals where FEUAS 
      is counted, counting of Far End Coding Violations (FECV), Far-
      End Errored Seconds (FEES), Far-End Severely Errored Seconds 
      (FESES) and Far-End SefAis Seconds (FESAS) are inhibited."
::= { mscLpE3G832StatsEntry 6 }


-- LP/n DS3/n PLCP
-- LP/n E3/n PLCP
-- The PLCP component is configured to display all DS3/E3 PLCP 
-- related operational and statistical data. It will appear under the DS3 
-- or E3 components when the mapping attribute is set to plcp.

mscLpE3Plcp OBJECT IDENTIFIER ::= { mscLpE3 4 }



mscLpE3PlcpRowStatusTable OBJECT-TYPE
   SYNTAX     SEQUENCE OF MscLpE3PlcpRowStatusEntry
   ACCESS     not-accessible
   STATUS     mandatory
   DESCRIPTION
     "This entry controls the addition and deletion of 
      mscLpE3Plcp components."
::= { mscLpE3Plcp 1 }

mscLpE3PlcpRowStatusEntry OBJECT-TYPE
   SYNTAX     MscLpE3PlcpRowStatusEntry
   ACCESS     not-accessible
   STATUS     mandatory
   DESCRIPTION
     "A single entry in the table represents a single 
      mscLpE3Plcp component."
   INDEX {
      mscLpIndex,
      mscLpE3Index,
      mscLpE3PlcpIndex }
::= { mscLpE3PlcpRowStatusTable 1 }

MscLpE3PlcpRowStatusEntry ::= SEQUENCE {
   mscLpE3PlcpRowStatus
      RowStatus,
   mscLpE3PlcpComponentName
      DisplayString,
   mscLpE3PlcpStorageType
      StorageType,
   mscLpE3PlcpIndex
      NonReplicated }

mscLpE3PlcpRowStatus OBJECT-TYPE
   SYNTAX     RowStatus 
   ACCESS     read-only
   STATUS     mandatory
   DESCRIPTION
     "This variable is used as the basis for SNMP naming of
      mscLpE3Plcp components.
      These components cannot be added nor deleted."
::= { mscLpE3PlcpRowStatusEntry 1 }

mscLpE3PlcpComponentName OBJECT-TYPE
   SYNTAX     DisplayString 
   ACCESS     read-only
   STATUS     mandatory
   DESCRIPTION
     "This variable provides the component's string name for
      use with the ASCII Console Interface"
::= { mscLpE3PlcpRowStatusEntry 2 }

mscLpE3PlcpStorageType OBJECT-TYPE
   SYNTAX     StorageType 
   ACCESS     read-only
   STATUS     mandatory
   DESCRIPTION
     "This variable represents the storage type value for the
      mscLpE3Plcp tables."
::= { mscLpE3PlcpRowStatusEntry 4 }

mscLpE3PlcpIndex OBJECT-TYPE
   SYNTAX     NonReplicated 
   ACCESS     not-accessible
   STATUS     mandatory
   DESCRIPTION
     "This variable represents the index for the mscLpE3Plcp tables."
::= { mscLpE3PlcpRowStatusEntry 10 }

mscLpE3PlcpOperationalTable OBJECT-TYPE
   SYNTAX     SEQUENCE OF MscLpE3PlcpOperationalEntry
   ACCESS     not-accessible
   STATUS     mandatory
   DESCRIPTION
     "This group contains the operational data for the PLCP component."
::= { mscLpE3Plcp 10 }

mscLpE3PlcpOperationalEntry OBJECT-TYPE
   SYNTAX     MscLpE3PlcpOperationalEntry
   ACCESS     not-accessible
   STATUS     mandatory
   DESCRIPTION
     "An entry in the mscLpE3PlcpOperationalTable."
   INDEX {
      mscLpIndex,
      mscLpE3Index,
      mscLpE3PlcpIndex }
::= { mscLpE3PlcpOperationalTable 1 }

MscLpE3PlcpOperationalEntry ::= SEQUENCE {
   mscLpE3PlcpLofAlarm
      INTEGER,
   mscLpE3PlcpRxRaiAlarm
      INTEGER }

mscLpE3PlcpLofAlarm OBJECT-TYPE
   SYNTAX     INTEGER  {
                 on(0),
                 off(1) }
   ACCESS     read-only
   STATUS     mandatory
   DESCRIPTION
     "This attribute displays whether a PLCP Loss Of Frame (LOF) 
      failure alarm state has been entered. An LOF failure is declared 
      when a PLCP LOF defect persists for 2.5 s +/- 0.5 s. An LOF defect 
      occurs when an OOF (Out of Frame) state persists for more than 1 
      ms. If the OOF events are intermittent, the LOF defect counter is 
      decremented at a rate of 1/12 (for DS3 PLCP) or 1/9 (for G.751 E3 
      PLCP) of the incrementing rate, with all measurements based on a 
      200 ms polling cycle. An OOF event (also known as a PLCP SEF 
      event) is declared when an error is detected in both the A1 and A2 
      octets, or when two consecutive POHIDs are found in error.
      OOF is removed when two valid sets of framing octets and two 
      valid and sequential POHID octets have been found. The LOF 
      defect is removed when the defect counter reaches zero, i.e. when 
      OOF events are absent for more than 12 ms (DS3 PLCP) or 9 ms 
      (G.751 E3 PLCP). LOF failure alarm is cleared when LOF defect is 
      absent for 10.0 s +/- 0.5 s
      The DS3 or E3 component goes into an operational state of disabled 
      until the LOF failure alarm is cleared. The terminal declaring the 
      LOF failure alarm will transmit a PLCP RAI signal to the far-end 
      for the duration of the alarm.
      The lofAlarm attribute is always set to off when the DS3 or E3 
      component has been locked and left offline."
   DEFVAL     { off }
::= { mscLpE3PlcpOperationalEntry 1 }

mscLpE3PlcpRxRaiAlarm OBJECT-TYPE
   SYNTAX     INTEGER  {
                 on(0),
                 off(1) }
   ACCESS     read-only
   STATUS     mandatory
   DESCRIPTION
     "This attribute displays whether a PLCP Remote Alarm Indication 
      (RAI) failure alarm state has been entered. An RAI failure alarm 
      occurs when ten consecutive PLCP RAI bits (bit 5 in the G1 byte) 
      are high on the incoming line. An RAI failure alarm is cleared when 
      ten consecutive RAI bits are set to 0.
      Note: Some standards call this alarm RFI.
      The rxRaiAlarm attribute is always set to off when the DS3 or E3 
      component has been locked and left offline."
   DEFVAL     { off }
::= { mscLpE3PlcpOperationalEntry 2 }

mscLpE3PlcpStatsTable OBJECT-TYPE
   SYNTAX     SEQUENCE OF MscLpE3PlcpStatsEntry
   ACCESS     not-accessible
   STATUS     mandatory
   DESCRIPTION
     "This group contains the statistical data for the PLCP component. 
      Each attribute type is a non-negative integer which monotonically 
      increases until it reaches a maximum value, at which point it wraps 
      around and starts increasing again from zero."
::= { mscLpE3Plcp 11 }

mscLpE3PlcpStatsEntry OBJECT-TYPE
   SYNTAX     MscLpE3PlcpStatsEntry
   ACCESS     not-accessible
   STATUS     mandatory
   DESCRIPTION
     "An entry in the mscLpE3PlcpStatsTable."
   INDEX {
      mscLpIndex,
      mscLpE3Index,
      mscLpE3PlcpIndex }
::= { mscLpE3PlcpStatsTable 1 }

MscLpE3PlcpStatsEntry ::= SEQUENCE {
   mscLpE3PlcpErrorFreeSec
      Counter32,
   mscLpE3PlcpCodingViolations
      Counter32,
   mscLpE3PlcpErroredSec
      Counter32,
   mscLpE3PlcpSevErroredSec
      Counter32,
   mscLpE3PlcpSevErroredFramingSec
      Counter32,
   mscLpE3PlcpUnavailSec
      Counter32,
   mscLpE3PlcpFarEndErrorFreeSec
      Counter32,
   mscLpE3PlcpFarEndCodingViolations
      Counter32,
   mscLpE3PlcpFarEndErroredSec
      Counter32,
   mscLpE3PlcpFarEndSevErroredSec
      Counter32,
   mscLpE3PlcpFarEndUnavailableSec
      Counter32 }

mscLpE3PlcpErrorFreeSec OBJECT-TYPE
   SYNTAX     Counter32 
   ACCESS     read-only
   STATUS     mandatory
   DESCRIPTION
     "This attribute indicates the number of seconds during which the 
      near-end PLCP path layer had no errors."
::= { mscLpE3PlcpStatsEntry 1 }

mscLpE3PlcpCodingViolations OBJECT-TYPE
   SYNTAX     Counter32 
   ACCESS     read-only
   STATUS     mandatory
   DESCRIPTION
     "This attribute indicates the total number of BIP-8 Errors, framing 
      pattern octet errors, and path overhead identification errors detected 
      in received PLCP frames. 
      Counting of PLCP CV is inhibited for second intervals where PLCP 
      Severely Errored Framing Seconds (SEFS) or PLCP Unavailable 
      Seconds (UAS) are counted.
      This attribute is a non-negative integer which monotonically 
      increases until it reaches a maximum value, at which point it wraps 
      around and starts increasing again from zero."
::= { mscLpE3PlcpStatsEntry 2 }

mscLpE3PlcpErroredSec OBJECT-TYPE
   SYNTAX     Counter32 
   ACCESS     read-only
   STATUS     mandatory
   DESCRIPTION
     "This attribute indicates the number of seconds containing one or 
      more PLCP Coding Violations (CV) or in which a PLCP Severely 
      Errored Framing Second (SEFS) was counted. 
      Counting of PLCP ES is inhibited during second intervals where 
      PLCP Unavailable Seconds (UAS) are counted."
::= { mscLpE3PlcpStatsEntry 3 }

mscLpE3PlcpSevErroredSec OBJECT-TYPE
   SYNTAX     Counter32 
   ACCESS     read-only
   STATUS     mandatory
   DESCRIPTION
     "This attribute indicates the number of seconds containing 5 or more 
      PLCPCVs or in which a PLCPSEFS was counted (i.e. a PLCP OOF 
      event occurred). 
      Counting of PLCP SES is inhibited during second intervals where 
      PLCP Unavailable Seconds (UAS) are counted."
::= { mscLpE3PlcpStatsEntry 4 }

mscLpE3PlcpSevErroredFramingSec OBJECT-TYPE
   SYNTAX     Counter32 
   ACCESS     read-only
   STATUS     mandatory
   DESCRIPTION
     "This attribute indicates the number of seconds containing one or 
      more PLCP Severely Errored Frame (SEF) events. An SEF event is 
      equivalent to a PLCP OOF (Out of Frame) event.
      Counting of PLCPP SEFSs is inhibited for second intervals where 
      PLCP Unavailable Seconds (UAS) are counted."
::= { mscLpE3PlcpStatsEntry 5 }

mscLpE3PlcpUnavailSec OBJECT-TYPE
   SYNTAX     Counter32 
   ACCESS     read-only
   STATUS     mandatory
   DESCRIPTION
     "This attribute indicates the number of seconds when the near-end 
      PLCP layer is unavailable. The PLCP Path Layer becomes 
      unavailable at the declaration of PLCP LOF (Loss of Frame) failure 
      alarm state. The PLCP Path Layer becomes available again only 
      after clearing this condition.
      For second intervals where PLCP UAS are counted, counting of 
      PLCP Severely Errored Framing Seconds (SEFS), PLCP Coding 
      Violations (CV), PLCP Errored Seconds (ES), PLCP Severely 
      Errored Seconds (SES) and PLCP Far-End Severely Errored 
      Seconds (FESES) is inhibited."
::= { mscLpE3PlcpStatsEntry 6 }

mscLpE3PlcpFarEndErrorFreeSec OBJECT-TYPE
   SYNTAX     Counter32 
   ACCESS     read-only
   STATUS     mandatory
   DESCRIPTION
     "This attribute indicates the number of seconds during which the far-
      end PLCP path layer had no errors."
::= { mscLpE3PlcpStatsEntry 7 }

mscLpE3PlcpFarEndCodingViolations OBJECT-TYPE
   SYNTAX     Counter32 
   ACCESS     read-only
   STATUS     mandatory
   DESCRIPTION
     "This attribute indicates the total number of PLCP Far-End Block 
      Errors (FEBE) reported by the far-end terminal. 
      Counting of FEBEs is inhibited for second intervals where PLCP 
      Far-End Unavailable Seconds (FEUAS) are counted.
      This attribute is a non-negative integer which monotonically 
      increases until it reaches a maximum value, at which point it wraps 
      around and starts increasing again from zero."
::= { mscLpE3PlcpStatsEntry 8 }

mscLpE3PlcpFarEndErroredSec OBJECT-TYPE
   SYNTAX     Counter32 
   ACCESS     read-only
   STATUS     mandatory
   DESCRIPTION
     "This attribute indicates the number of seconds containing one or 
      more PLCP Far-End Coding Violations (FECV).
      Counting of PLCP FEES is inhibited during second intervals where 
      PLCP Far-End Unavailable Seconds (FEUAS) are counted."
::= { mscLpE3PlcpStatsEntry 9 }

mscLpE3PlcpFarEndSevErroredSec OBJECT-TYPE
   SYNTAX     Counter32 
   ACCESS     read-only
   STATUS     mandatory
   DESCRIPTION
     "This attribute indicates the number of seconds containing 5 or more 
      PLCP Far-End Coding Violations (FECV). 
      Counting of PLCP FESES is inhibited for second intervals where 
      PLCP Far-End Unavailable Seconds (FEUAS) are counted."
::= { mscLpE3PlcpStatsEntry 10 }

mscLpE3PlcpFarEndUnavailableSec OBJECT-TYPE
   SYNTAX     Counter32 
   ACCESS     read-only
   STATUS     mandatory
   DESCRIPTION
     "This attribute indicates the number of seconds during which the 
      PLCP far end is unavailable. The PLCP Path Layer becomes 
      unavailable at the declaration of PLCP RAI (Remote Alarm 
      Indication). Service becomes available again after this condition is 
      cleared. For second intervals where PLCP FEUAS are counted, 
      counting of PLCP Far-End Coding Violations (FECV), PLCP Far-
      End Errored Seconds (FEES), and PLCP Far-End Severely Errored 
      Seconds (FESES) is inhibited."
::= { mscLpE3PlcpStatsEntry 11 }


-- 
-- The AtmCell is a component that contains provisioning and 
-- operational attributes. The provisioning attributes are used to set the 
-- Loss of Cell Deliniation (LCD) alarm activation delay and to turn 
-- cell payload scrambling on or off. The operational attributes are 
-- used to report about the quality of the ATM cells received by the 
-- interface and the cell capacity utilization. The AtmCell component 
-- appears under all port components running on ATM cards.

mscLpE3Cell OBJECT IDENTIFIER ::= { mscLpE3 5 }



mscLpE3CellRowStatusTable OBJECT-TYPE
   SYNTAX     SEQUENCE OF MscLpE3CellRowStatusEntry
   ACCESS     not-accessible
   STATUS     mandatory
   DESCRIPTION
     "This entry controls the addition and deletion of 
      mscLpE3Cell components."
::= { mscLpE3Cell 1 }

mscLpE3CellRowStatusEntry OBJECT-TYPE
   SYNTAX     MscLpE3CellRowStatusEntry
   ACCESS     not-accessible
   STATUS     mandatory
   DESCRIPTION
     "A single entry in the table represents a single 
      mscLpE3Cell component."
   INDEX {
      mscLpIndex,
      mscLpE3Index,
      mscLpE3CellIndex }
::= { mscLpE3CellRowStatusTable 1 }

MscLpE3CellRowStatusEntry ::= SEQUENCE {
   mscLpE3CellRowStatus
      RowStatus,
   mscLpE3CellComponentName
      DisplayString,
   mscLpE3CellStorageType
      StorageType,
   mscLpE3CellIndex
      NonReplicated }

mscLpE3CellRowStatus OBJECT-TYPE
   SYNTAX     RowStatus 
   ACCESS     read-write
   STATUS     mandatory
   DESCRIPTION
     "This variable is used as the basis for SNMP naming of
      mscLpE3Cell components.
      These components can be added and deleted."
::= { mscLpE3CellRowStatusEntry 1 }

mscLpE3CellComponentName OBJECT-TYPE
   SYNTAX     DisplayString 
   ACCESS     read-only
   STATUS     mandatory
   DESCRIPTION
     "This variable provides the component's string name for
      use with the ASCII Console Interface"
::= { mscLpE3CellRowStatusEntry 2 }

mscLpE3CellStorageType OBJECT-TYPE
   SYNTAX     StorageType 
   ACCESS     read-only
   STATUS     mandatory
   DESCRIPTION
     "This variable represents the storage type value for the
      mscLpE3Cell tables."
::= { mscLpE3CellRowStatusEntry 4 }

mscLpE3CellIndex OBJECT-TYPE
   SYNTAX     NonReplicated 
   ACCESS     not-accessible
   STATUS     mandatory
   DESCRIPTION
     "This variable represents the index for the mscLpE3Cell tables."
::= { mscLpE3CellRowStatusEntry 10 }

mscLpE3CellProvTable OBJECT-TYPE
   SYNTAX     SEQUENCE OF MscLpE3CellProvEntry
   ACCESS     not-accessible
   STATUS     mandatory
   DESCRIPTION
     "This group contains the provisioning attributes for the AtmCell 
      component."
::= { mscLpE3Cell 10 }

mscLpE3CellProvEntry OBJECT-TYPE
   SYNTAX     MscLpE3CellProvEntry
   ACCESS     not-accessible
   STATUS     mandatory
   DESCRIPTION
     "An entry in the mscLpE3CellProvTable."
   INDEX {
      mscLpIndex,
      mscLpE3Index,
      mscLpE3CellIndex }
::= { mscLpE3CellProvTable 1 }

MscLpE3CellProvEntry ::= SEQUENCE {
   mscLpE3CellAlarmActDelay
      Unsigned32,
   mscLpE3CellScrambleCellPayload
      INTEGER,
   mscLpE3CellCorrectSingleBitHeaderErrors
      INTEGER }

mscLpE3CellAlarmActDelay OBJECT-TYPE
   SYNTAX     Unsigned32 (0..2000)
   ACCESS     read-write
   STATUS     mandatory
   DESCRIPTION
     "This attribute defines the time during which a Loss of Cell 
      Delineation (LCD) defect should be observed before declaring an 
      LCD alarm (alarm 70115501). The time is specified in milliseconds."
   DEFVAL     { 500 }
::= { mscLpE3CellProvEntry 1 }

mscLpE3CellScrambleCellPayload OBJECT-TYPE
   SYNTAX     INTEGER  {
                 off(0),
                 on(1) }
   ACCESS     read-write
   STATUS     mandatory
   DESCRIPTION
     "Cell scrambling, as defined by  ITU-T Recommendation I.432., can 
      provide a solution to the problem of transmission equipment which 
      is sensitive to certain bit patterns in the ATM cell payload. This 
      attribute controls whether or not the cell payload is scrambled.
      It defaults to off for DS1 interfaces, and on for all other interfaces.
      Note that this setting must be the same at both ends of the link."
::= { mscLpE3CellProvEntry 2 }

mscLpE3CellCorrectSingleBitHeaderErrors OBJECT-TYPE
   SYNTAX     INTEGER  {
                 off(0),
                 on(1) }
   ACCESS     read-write
   STATUS     mandatory
   DESCRIPTION
     "This attribute specifies whether the port corrects single bit errors 
      detected in the headers of received cells. If single bit errors are 
      corrected, the affected cells are passed up to the ATM layer 
      according to normal operation. If single bit errors are not corrected, 
      these errored cells are discarded by the physical layer. Note that 
      cells containing multiple bit errors in their headers are always 
      discarded.
      
      Single bit HEC error correction must remain off for the following 
      card types: 3pDS1Atm, 8pDS1Atm, 3pE1Atm, 8pE1Atm, 
      2pJ6MAtm, 3pDS3Atm, and 3pE3Atm."
   DEFVAL     { off }
::= { mscLpE3CellProvEntry 3 }

mscLpE3CellOperTable OBJECT-TYPE
   SYNTAX     SEQUENCE OF MscLpE3CellOperEntry
   ACCESS     not-accessible
   STATUS     mandatory
   DESCRIPTION
     "This group contains the common operational attributes for the 
      AtmCell component."
::= { mscLpE3Cell 11 }

mscLpE3CellOperEntry OBJECT-TYPE
   SYNTAX     MscLpE3CellOperEntry
   ACCESS     not-accessible
   STATUS     mandatory
   DESCRIPTION
     "An entry in the mscLpE3CellOperTable."
   INDEX {
      mscLpIndex,
      mscLpE3Index,
      mscLpE3CellIndex }
::= { mscLpE3CellOperTable 1 }

MscLpE3CellOperEntry ::= SEQUENCE {
   mscLpE3CellLcdAlarm
      INTEGER }

mscLpE3CellLcdAlarm OBJECT-TYPE
   SYNTAX     INTEGER  {
                 on(0),
                 off(1) }
   ACCESS     read-only
   STATUS     mandatory
   DESCRIPTION
     "This attribute displays whether the Loss of Cell Delineation (LCD) 
      failure alarm state has been entered. This state is entered when LCD 
      defects have been observed and accumulated for a period of time 
      specified through the alarmActDelay attribute.
      In ATM cell direct mapping mode, an LCD defect occurs when Out 
      of Cell Delineation (OCD) anomaly persists for x milliseconds, and 
      disappears when the Out of Cell Delineation (OCD) is absent for x 
      msec. An OCD anomaly occurs when 7 consecutive incorrect HECs 
      have been detected. An OCD anomaly terminates when 6 
      consecutive correct HECs have been detected.
      For an AtmCell component located under a DS3 or E3 component 
      with mapping = PLCP, the LCD defect is directly derived from the 
      PLCP LOF defect.
      If LCD defects are intermittently occurring, the LCD defect 
      accumulator is decremented at a rate of 1/10 of the incrementing 
      rate (alarm integration ratio of 1/10), with all measurements based 
      on a 200 ms polling cycle
      The component under which is located the AtmCell component goes 
      into an operational state of disabled until the LCD alarm condition 
      is cleared. The condition is cleared after the LCD defect has not 
      been reported for a period of 10 seconds +/- 0.5 seconds.
      The lcdAlarm attribute is always set to off when the parent of the 
      AtmCell component has been locked and left offline. This can also 
      happen when the Path or Channel component has been suspended 
      since its parent has been locked."
   DEFVAL     { off }
::= { mscLpE3CellOperEntry 1 }

mscLpE3CellStatsTable OBJECT-TYPE
   SYNTAX     SEQUENCE OF MscLpE3CellStatsEntry
   ACCESS     not-accessible
   STATUS     mandatory
   DESCRIPTION
     "This group contains the Statistics attribute for the AtmCell 
      component. Each attribute type is a non-negative integer which 
      monotonically increases until it reaches a maximum value, at which 
      point it wraps around and starts increasing again from zero."
::= { mscLpE3Cell 12 }

mscLpE3CellStatsEntry OBJECT-TYPE
   SYNTAX     MscLpE3CellStatsEntry
   ACCESS     not-accessible
   STATUS     mandatory
   DESCRIPTION
     "An entry in the mscLpE3CellStatsTable."
   INDEX {
      mscLpIndex,
      mscLpE3Index,
      mscLpE3CellIndex }
::= { mscLpE3CellStatsTable 1 }

MscLpE3CellStatsEntry ::= SEQUENCE {
   mscLpE3CellUncorrectableHecErrors
      Counter32,
   mscLpE3CellSevErroredSec
      Counter32,
   mscLpE3CellReceiveCellUtilization
      Gauge32,
   mscLpE3CellTransmitCellUtilization
      Gauge32,
   mscLpE3CellCorrectableHeaderErrors
      Counter32 }

mscLpE3CellUncorrectableHecErrors OBJECT-TYPE
   SYNTAX     Counter32 
   ACCESS     read-only
   STATUS     mandatory
   DESCRIPTION
     "This attribute indicates the number of uncorrectable ATM cell 
      header errors that have been detected. Counting of 
      uncorrectableHeaderErrors is inhibited when an Out of Cell 
      Delineation (OCD) defect is present. An OCD defect occurs when 
      seven consecutive incorrect HECs have been detected. An OCD 
      defect terminates when six consecutive correct HECs have been 
      detected."
::= { mscLpE3CellStatsEntry 1 }

mscLpE3CellSevErroredSec OBJECT-TYPE
   SYNTAX     Counter32 
   ACCESS     read-only
   STATUS     mandatory
   DESCRIPTION
     "This attribute indicates the total number of ATM Cell Severely 
      Errored Seconds (SESs) that have been counted. 
      
      In direct mapping mode, an ATM Cell SES is declared for second 
      intervals containing one or more Out of Cell Delineation (OCD) 
      defects. An OCD defect occurs when seven consecutive incorrect 
      HECs have been detected. An OCD defect terminates when six 
      consecutive correct HECs have been detected.
      
      In PLCP mapping mode, an ATM Cell SES is declared for second 
      intervals containing one or more PLCP LOF defects.
      
      Counting of uncorrectableHeaderErrors (ucErr) and 
      correctableHeaderErrors (cErr) is inhibited when the OCD defect 
      is present."
::= { mscLpE3CellStatsEntry 2 }

mscLpE3CellReceiveCellUtilization OBJECT-TYPE
   SYNTAX     Gauge32 (0..100)
   ACCESS     read-only
   STATUS     mandatory
   DESCRIPTION
     "This attribute is the ratio of the number of valid, assigned cells 
      received on the link to the nominal link capacity. The utilization is 
      calculated over a period of one minute.
      This attribute is always set to 0 when the parent of the AtmCell 
      component has been locked and left offline. This can also happen 
      when the Path or Channel component has been suspended since its 
      parent has been locked."
   DEFVAL     { 0 }
::= { mscLpE3CellStatsEntry 3 }

mscLpE3CellTransmitCellUtilization OBJECT-TYPE
   SYNTAX     Gauge32 (0..100)
   ACCESS     read-only
   STATUS     mandatory
   DESCRIPTION
     "This attribute is the ratio of the number of valid, assigned cells 
      transmitted on the link to the nominal link capacity. The utilization 
      is calculated over a period of one minute.
      This attribute is always set to 0 when the parent of the AtmCell 
      component has been locked and left offline. This can also happen 
      when the Path or Channel component has been suspended since its 
      parent has been locked."
   DEFVAL     { 0 }
::= { mscLpE3CellStatsEntry 4 }

mscLpE3CellCorrectableHeaderErrors OBJECT-TYPE
   SYNTAX     Counter32 
   ACCESS     read-only
   STATUS     mandatory
   DESCRIPTION
     "This attribute indicates the number of correctable ATM cell header 
      errors that have been detected and corrected. Counting of 
      correctableHeaderErrors is inhibited when an Out of Cell 
      Delineation (OCD) defect is present. An OCD defect occurs when 
      seven consecutive incorrect HECs have been detected. An OCD 
      defect terminates when six consecutive correct HECs have been 
      detected"
::= { mscLpE3CellStatsEntry 5 }


-- Lp/n DS1/n
-- The DS1 component controls and monitors a DS1 port on a 
-- Function Processor. The number of ports supported depends on the 
-- type of card, and is usually encoded in the Shelf Card/n cardType, 
-- for example 4pDS1Aal1: 4 port. The lowest instance value is 
-- always 0. 
-- 
-- Multi-Service cards have an instance range 0..31, except that 
-- instance values 30 and 31 are not available for an "ATM UNI port". 
-- (A DS1 "ATM UNI port" is a DS1 component with a single Chan 
-- whose applicationFramerName attribute is linked to an AtmIf 
-- component.)
-- 
-- The instance number of a DS1 "ATM UNI port" must not be the 
-- same as the instance number of an IMA group under the same Lp.

mscLpDS1 OBJECT IDENTIFIER ::= { mscLp 7 }



mscLpDS1RowStatusTable OBJECT-TYPE
   SYNTAX     SEQUENCE OF MscLpDS1RowStatusEntry
   ACCESS     not-accessible
   STATUS     mandatory
   DESCRIPTION
     "This entry controls the addition and deletion of 
      mscLpDS1 components."
::= { mscLpDS1 1 }

mscLpDS1RowStatusEntry OBJECT-TYPE
   SYNTAX     MscLpDS1RowStatusEntry
   ACCESS     not-accessible
   STATUS     mandatory
   DESCRIPTION
     "A single entry in the table represents a single 
      mscLpDS1 component."
   INDEX {
      mscLpIndex,
      mscLpDS1Index }
::= { mscLpDS1RowStatusTable 1 }

MscLpDS1RowStatusEntry ::= SEQUENCE {
   mscLpDS1RowStatus
      RowStatus,
   mscLpDS1ComponentName
      DisplayString,
   mscLpDS1StorageType
      StorageType,
   mscLpDS1Index
      Integer32 }

mscLpDS1RowStatus OBJECT-TYPE
   SYNTAX     RowStatus 
   ACCESS     read-write
   STATUS     mandatory
   DESCRIPTION
     "This variable is used as the basis for SNMP naming of
      mscLpDS1 components.
      These components can be added and deleted."
::= { mscLpDS1RowStatusEntry 1 }

mscLpDS1ComponentName OBJECT-TYPE
   SYNTAX     DisplayString 
   ACCESS     read-only
   STATUS     mandatory
   DESCRIPTION
     "This variable provides the component's string name for
      use with the ASCII Console Interface"
::= { mscLpDS1RowStatusEntry 2 }

mscLpDS1StorageType OBJECT-TYPE
   SYNTAX     StorageType 
   ACCESS     read-only
   STATUS     mandatory
   DESCRIPTION
     "This variable represents the storage type value for the
      mscLpDS1 tables."
::= { mscLpDS1RowStatusEntry 4 }

mscLpDS1Index OBJECT-TYPE
   SYNTAX     Integer32 (0..31)
   ACCESS     not-accessible
   STATUS     mandatory
   DESCRIPTION
     "This variable represents the index for the mscLpDS1 tables."
::= { mscLpDS1RowStatusEntry 10 }

mscLpDS1ProvTable OBJECT-TYPE
   SYNTAX     SEQUENCE OF MscLpDS1ProvEntry
   ACCESS     not-accessible
   STATUS     mandatory
   DESCRIPTION
     "This group contains all of the provisioning data for a DS1 
      component."
::= { mscLpDS1 10 }

mscLpDS1ProvEntry OBJECT-TYPE
   SYNTAX     MscLpDS1ProvEntry
   ACCESS     not-accessible
   STATUS     mandatory
   DESCRIPTION
     "An entry in the mscLpDS1ProvTable."
   INDEX {
      mscLpIndex,
      mscLpDS1Index }
::= { mscLpDS1ProvTable 1 }

MscLpDS1ProvEntry ::= SEQUENCE {
   mscLpDS1LineType
      INTEGER,
   mscLpDS1ZeroCoding
      INTEGER,
   mscLpDS1ClockingSource
      INTEGER,
   mscLpDS1RaiAlarmType
      INTEGER,
   mscLpDS1LineLength
      Unsigned32 }

mscLpDS1LineType OBJECT-TYPE
   SYNTAX     INTEGER  {
                 d4(0),
                 esf(1),
                 d4Cas(4),
                 esfCas(5),
                 unframed(6) }
   ACCESS     read-write
   STATUS     mandatory
   DESCRIPTION
     "This attribute defines the framing of the DS1 line.
      d4 defines a framing pattern of 12 frames per multiframe.
      esf defines a framing pattern of 24 frames per multiframe.
      d4Cas defines a framing pattern of 12 frames per multiframe with 
      channel associated signalling.
      esfCas defines a framing pattern of 24 frames per multiframe with 
      channel associated signalling.
      unframed defines an unknown framing pattern for clear channels.
      For cell-based cards only the default option esf is permitted."
   DEFVAL     { esf }
::= { mscLpDS1ProvEntry 1 }

mscLpDS1ZeroCoding OBJECT-TYPE
   SYNTAX     INTEGER  {
                 bit7Stuffing(0),
                 b8zs(1),
                 ami(2) }
   ACCESS     read-write
   STATUS     mandatory
   DESCRIPTION
     "This attribute defines the zero encoding on the DS1 line.
      bit7Stuffing sets bit 7 of every timeslot to a one to guarantee ones's 
      density. This reduces the available bandwidth of the channel by 1/8.
      b8zs substitutes a pattern of bipolar violations if more than 7 zeros 
      in a row are to be transported.
      ami specifies Alternate Mark Inversion, in which successive marks 
      (ones) alternate between positive and negative polarity voltage 
      signals, and spaces (zeros) are sent as a zero amplitude signal.
      When zeroCoding is set to ami and lineType is set to d4, it is 
      recommended that raiAlarmType be set to SBit in order to avoid 
      possible mimic RAI alarm.
      For cell-based cards only the default value b8zs is permitted."
   DEFVAL     { b8zs }
::= { mscLpDS1ProvEntry 2 }

mscLpDS1ClockingSource OBJECT-TYPE
   SYNTAX     INTEGER  {
                 local(0),
                 line(1),
                 module(2),
                 otherPort(3),
                 srtsMode(4),
                 adaptiveMode(5) }
   ACCESS     read-write
   STATUS     mandatory
   DESCRIPTION
     "This attribute defines the source of the transmit clock for the DS1 
      line.
      
      When local is selected, the crystal on the port generates the 
      clocking for the line.
      
      When line is selected, the port synchronizes to the clock from the 
      facility.
      
      When module is selected, the ports clock synchronizes to the clock 
      provided by the oscillator on the active CP.
      
      When otherPort is selected, the port synchronizes to the port with a 
      clocking source of line.
      
      When srtsMode is selected, the port transmit frequency depends on 
      the SRTS (Synchronous Residual Time-Stamp) received over the 
      ATM network. SRTS information is also generated sent over the 
      ATM network.
      
      When adaptiveMode is selected, the port transmit frequency 
      continually adapts to match the egress data received from the ATM 
      network.
      
      A port with srtsMode or adaptiveMode must have a single Chan 
      which may be linked only to an Aal1Ces.service with serviceType 
      unstructured 
      
      If the NetworkSynchronization component is present, the default 
      value of this attribute is module, otherwise it defaults to line, except 
      for the 3pDS1Atm card, which it defaults to local.
      
      On a 3pDS1Atm card all ports must have the same value, and be 
      either local or module.
      
      otherPort is valid only on AAL1 cards. srtsMode is valid only on 
      AAL1 and Multi-Service Access cards. adaptiveMode is valid only 
      on Multi-Service Access cards.
      On 4DS1Aal1 cards either:
      
      all four ports' clockingSource values must be local OR
      all four ports' clockingSource values must be module OR
      one port's clockingSource value must be line and the other three 
      must be otherPort. A port can only have srtsMode selected if the 
      other ports are module or srtsMode."
::= { mscLpDS1ProvEntry 3 }

mscLpDS1RaiAlarmType OBJECT-TYPE
   SYNTAX     INTEGER  {
                 sBit(0),
                 bit2(1),
                 fdl(2) }
   ACCESS     read-write
   STATUS     mandatory
   DESCRIPTION
     "This attribute defines the method of sending a RAI (Remote Alarm 
      Indication) alarm on a DS1 line.
      When SBit is selected, RAI alarm is sent by setting the S bit in 
      frame 12.
      When Bit2 is selected, RAI alarm is sent by setting bit 2 in all 
      timeslots to 0.
      When fdl is selected, RAI alarm is sent by a repeating pattern of 00 
      hex and FF hex on the FDL link.
      Note that for lineType of d4, only the SBit and the Bit2 methods are 
      applicable. Whereas for lineType of esf, only the Bit2 and the fdl 
      methods are applicable.
      SBit method is recommended if lineType is set to d4 and 
      zeroCoding is set to ami. This will help to avoid potential mimic 
      RAI alarm when 1's density is too low in the data transmitted.
      For cell-based cards only the default value fdl is permitted."
   DEFVAL     { fdl }
::= { mscLpDS1ProvEntry 4 }

mscLpDS1LineLength OBJECT-TYPE
   SYNTAX     Unsigned32 (0..655)
   ACCESS     read-write
   STATUS     mandatory
   DESCRIPTION
     "This attribute defines the line length (in feet) for equalization 
      calculations for the DS1 line. The value ranges between 0-655. For 
      8pDS1Atm cards the actual value used for equalization is rounded 
      up to the nearest 110 feet; for all other card types the actual value 
      used is rounded to the nearest 50 feet."
   DEFVAL     { 0 }
::= { mscLpDS1ProvEntry 5 }

mscLpDS1CidDataTable OBJECT-TYPE
   SYNTAX     SEQUENCE OF MscLpDS1CidDataEntry
   ACCESS     not-accessible
   STATUS     mandatory
   DESCRIPTION
     "This group contains the attribute for a component's Customer 
      Identifier (CID). Refer to the attribute description for a detailed 
      explanation of CIDs."
::= { mscLpDS1 11 }

mscLpDS1CidDataEntry OBJECT-TYPE
   SYNTAX     MscLpDS1CidDataEntry
   ACCESS     not-accessible
   STATUS     mandatory
   DESCRIPTION
     "An entry in the mscLpDS1CidDataTable."
   INDEX {
      mscLpIndex,
      mscLpDS1Index }
::= { mscLpDS1CidDataTable 1 }

MscLpDS1CidDataEntry ::= SEQUENCE {
   mscLpDS1CustomerIdentifier
      Unsigned32 }

mscLpDS1CustomerIdentifier OBJECT-TYPE
   SYNTAX     Unsigned32 (0 | 1..8191)
   ACCESS     read-write
   STATUS     mandatory
   DESCRIPTION
     "This attribute holds the Customer Identifier (CID).
      
      Every component has a CID. If a component has a cid attribute, the 
      component's CID is the provisioned value of that attribute; 
      otherwise the component inherits the CID of its parent. The top-
      level component has a CID of 0.
      
      Every operator session also has a CID, which is the CID 
      provisioned for the operator's user ID. An operator will see only the 
      stream data for components having a matching CID. Also, the 
      operator will be allowed to issue commands for only those 
      components which have a matching CID.
      
      An operator CID of 0 is used to identify the Network Manager 
      (referred to as 'NetMan' in DPN). This CID matches the CID of 
      any component. Values 1 to 8191 inclusive (equivalent to 'basic 
      CIDs' in DPN) may be assigned to specific customers."
   DEFVAL     { 0 }
::= { mscLpDS1CidDataEntry 1 }

mscLpDS1AdminInfoTable OBJECT-TYPE
   SYNTAX     SEQUENCE OF MscLpDS1AdminInfoEntry
   ACCESS     not-accessible
   STATUS     mandatory
   DESCRIPTION
     "This group contains the attributes pertaining to the vendor of the 
      equipment."
::= { mscLpDS1 12 }

mscLpDS1AdminInfoEntry OBJECT-TYPE
   SYNTAX     MscLpDS1AdminInfoEntry
   ACCESS     not-accessible
   STATUS     mandatory
   DESCRIPTION
     "An entry in the mscLpDS1AdminInfoTable."
   INDEX {
      mscLpIndex,
      mscLpDS1Index }
::= { mscLpDS1AdminInfoTable 1 }

MscLpDS1AdminInfoEntry ::= SEQUENCE {
   mscLpDS1Vendor
      AsciiString,
   mscLpDS1CommentText
      AsciiString }

mscLpDS1Vendor OBJECT-TYPE
   SYNTAX     AsciiString (SIZE (0..20))
   ACCESS     read-write
   STATUS     mandatory
   DESCRIPTION
     "This is the name of the vendor supplying the facility."
::= { mscLpDS1AdminInfoEntry 1 }

mscLpDS1CommentText OBJECT-TYPE
   SYNTAX     AsciiString (SIZE (0..60))
   ACCESS     read-write
   STATUS     mandatory
   DESCRIPTION
     "Any miscellaneous text about the facility."
::= { mscLpDS1AdminInfoEntry 2 }

mscLpDS1IfEntryTable OBJECT-TYPE
   SYNTAX     SEQUENCE OF MscLpDS1IfEntryEntry
   ACCESS     not-accessible
   STATUS     mandatory
   DESCRIPTION
     "This group contains the provisionable attributes for the ifEntry."
::= { mscLpDS1 13 }

mscLpDS1IfEntryEntry OBJECT-TYPE
   SYNTAX     MscLpDS1IfEntryEntry
   ACCESS     not-accessible
   STATUS     mandatory
   DESCRIPTION
     "An entry in the mscLpDS1IfEntryTable."
   INDEX {
      mscLpIndex,
      mscLpDS1Index }
::= { mscLpDS1IfEntryTable 1 }

MscLpDS1IfEntryEntry ::= SEQUENCE {
   mscLpDS1IfAdminStatus
      INTEGER,
   mscLpDS1IfIndex
      InterfaceIndex }

mscLpDS1IfAdminStatus OBJECT-TYPE
   SYNTAX     INTEGER  {
                 up(1),
                 down(2),
                 testing(3) }
   ACCESS     read-write
   STATUS     mandatory
   DESCRIPTION
     "The desired state of the interface. The up state indicates the 
      interface is operational. The down state indicates the interface is not 
      operational. The testing state indicates that no operational packets 
      can be passed."
   DEFVAL     { up }
::= { mscLpDS1IfEntryEntry 1 }

mscLpDS1IfIndex OBJECT-TYPE
   SYNTAX     InterfaceIndex (1..65535)
   ACCESS     read-only
   STATUS     mandatory
   DESCRIPTION
     "This is the index for the IfEntry. Its value is automatically initialized 
      during the provisioning process."
::= { mscLpDS1IfEntryEntry 2 }

mscLpDS1OperStatusTable OBJECT-TYPE
   SYNTAX     SEQUENCE OF MscLpDS1OperStatusEntry
   ACCESS     not-accessible
   STATUS     mandatory
   DESCRIPTION
     "This group includes the Operational Status attribute. This attribute 
      defines the current operational state of this component."
::= { mscLpDS1 14 }

mscLpDS1OperStatusEntry OBJECT-TYPE
   SYNTAX     MscLpDS1OperStatusEntry
   ACCESS     not-accessible
   STATUS     mandatory
   DESCRIPTION
     "An entry in the mscLpDS1OperStatusTable."
   INDEX {
      mscLpIndex,
      mscLpDS1Index }
::= { mscLpDS1OperStatusTable 1 }

MscLpDS1OperStatusEntry ::= SEQUENCE {
   mscLpDS1SnmpOperStatus
      INTEGER }

mscLpDS1SnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { mscLpDS1OperStatusEntry 1 }

mscLpDS1StateTable OBJECT-TYPE
   SYNTAX     SEQUENCE OF MscLpDS1StateEntry
   ACCESS     not-accessible
   STATUS     mandatory
   DESCRIPTION
     "This group contains the three OSI State attributes and the six OSI 
      Status attributes. The descriptions generically indicate what each 
      attribute implies about the component. Note that not all the values 
      and state combinations described here are supported by every 
      component which uses this group. For component-specific 
      information and the valid state combinations, refer to NTP 241-
      7001-150, Passport Operations and Maintenance Guide."
::= { mscLpDS1 15 }

mscLpDS1StateEntry OBJECT-TYPE
   SYNTAX     MscLpDS1StateEntry
   ACCESS     not-accessible
   STATUS     mandatory
   DESCRIPTION
     "An entry in the mscLpDS1StateTable."
   INDEX {
      mscLpIndex,
      mscLpDS1Index }
::= { mscLpDS1StateTable 1 }

MscLpDS1StateEntry ::= SEQUENCE {
   mscLpDS1AdminState
      INTEGER,
   mscLpDS1OperationalState
      INTEGER,
   mscLpDS1UsageState
      INTEGER,
   mscLpDS1AvailabilityStatus
      OCTET STRING,
   mscLpDS1ProceduralStatus
      OCTET STRING,
   mscLpDS1ControlStatus
      OCTET STRING,
   mscLpDS1AlarmStatus
      OCTET STRING,
   mscLpDS1StandbyStatus
      INTEGER,
   mscLpDS1UnknownStatus
      INTEGER }

mscLpDS1AdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component.
      
      The OSI Status attributes, if supported by the component, may 
      provide more details, qualifying the state of the component."
   DEFVAL     { unlocked }
::= { mscLpDS1StateEntry 1 }

mscLpDS1OperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle.
      
      The OSI Status attributes, if supported by the component, may 
      provide more details, qualifying the state of the component."
   DEFVAL     { disabled }
::= { mscLpDS1StateEntry 2 }

mscLpDS1UsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time.
      
      The OSI Status attributes, if supported by the component, may 
      provide more details, qualifying the state of the component."
   DEFVAL     { idle }
::= { mscLpDS1StateEntry 3 }

mscLpDS1AvailabilityStatus OBJECT-TYPE
   SYNTAX     OCTET STRING (SIZE (2))
   ACCESS     read-only
   STATUS     mandatory
   DESCRIPTION
     "If supported by the component, this attribute indicates the OSI 
      Availability status of the component. Note that, even though it is 
      defined as a multi-valued set, at most one value is shown to the user.
      
      When no values are in the set, this indicates that either the attribute 
      is not supported or that none of the status conditions described 
      below are present.
      
      The value inTest indicates that the resource is undergoing a test 
      procedure. If adminState is locked or shuttingDown, the normal 
      users are precluded from using the resource and controlStatus is 
      reservedForTest. Tests that do not exclude additional users can be 
      present in any operational or administrative state but the 
      reservedForTest condition should not be present.
      
      The value failed indicates that the component has an internal fault 
      that prevents it from operating. The operationalState is disabled.
      
      The value dependency indicates that the component cannot operate 
      because some other resource on which it depends is unavailable. 
      The operationalState is disabled.
      
      The value powerOff indicates the resource requires power to be 
      applied and it is not powered on. The operationalState is disabled.
      
      The value offLine indicates the resource requires a routine 
      operation (either manual, automatic, or both) to be performed to 
      place it on-line and make it available for use. The operationalState 
      is disabled.
      
      The value offDuty indicates the resource is inactive in accordance 
      with a predetermined time schedule. In the absence of other 
      disabling conditions, the operationalState is enabled or disabled.
      
      The value degraded indicates the service provided by the 
      component is degraded in some way, such as in speed or operating 
      capacity. However, the resource remains available for service. The 
      operationalState is enabled.
      
      The value notInstalled indicates the resource is not present. The 
      operationalState is disabled.
      
      The value logFull is not used.

      Description of bits:
      inTest(0)
      failed(1)
      powerOff(2)
      offLine(3)
      offDuty(4)
      dependency(5)
      degraded(6)
      notInstalled(7)
      logFull(8)"
::= { mscLpDS1StateEntry 4 }

mscLpDS1ProceduralStatus OBJECT-TYPE
   SYNTAX     OCTET STRING (SIZE (1))
   ACCESS     read-only
   STATUS     mandatory
   DESCRIPTION
     "If supported by the component, this attribute indicates the OSI 
      Procedural status of the component. Note that, even though it is 
      defined as a multi-valued set, at most one value is shown to the user.
      
      When no values are in the set, this indicates that either the attribute 
      is not supported or that none of the status conditions described 
      below are present.
      
      The value initializationRequired indicates (for a resource which 
      doesn't initialize autonomously) that initialization is required before 
      it can perform its normal functions, and this procedure has not been 
      initiated. The operationalState is disabled.
      
      The value notInitialized indicates (for a resource which does 
      initialize autonomously) that initialization is required before it can 
      perform its normal functions, and this procedure has not been 
      initiated. The operationalState may be enabled or disabled.
      
      The value initializing indicates that initialization has been initiated 
      but is not yet complete. The operationalState may be enabled or 
      disabled.
      
      The value reporting indicates the resource has completed some 
      processing operation and is notifying the results. The 
      operationalState is enabled.
      
      The value terminating indicates the component is in a termination 
      phase. If the resource doesn't reinitialize autonomously, 
      operationalState is disabled; otherwise it is enabled or disabled.

      Description of bits:
      initializationRequired(0)
      notInitialized(1)
      initializing(2)
      reporting(3)
      terminating(4)"
::= { mscLpDS1StateEntry 5 }

mscLpDS1ControlStatus OBJECT-TYPE
   SYNTAX     OCTET STRING (SIZE (1))
   ACCESS     read-only
   STATUS     mandatory
   DESCRIPTION
     "If supported by the component, this attribute indicates the OSI 
      Control status of the component. Note that, even though it is defined 
      as a multi-valued set, at most one value is shown to the user.
      
      When no values are in the set, this indicates that either the attribute 
      is not supported or that none of the status conditions described 
      below are present.
      
      The value subjectToTest indicates the resource is available but tests 
      may be conducted simultaneously at unpredictable times, which 
      may cause it to exhibit unusual characteristics.
      
      The value partOfServicesLocked indicates that part of the service is 
      restricted from users of a resource. The adminState is unlocked.
      
      The value reservedForTest indicates that the component is 
      administratively unavailable because it is undergoing a test 
      procedure. The adminState is locked.
      
      The value suspended indicates that the service has been 
      administratively suspended.

      Description of bits:
      subjectToTest(0)
      partOfServicesLocked(1)
      reservedForTest(2)
      suspended(3)"
::= { mscLpDS1StateEntry 6 }

mscLpDS1AlarmStatus OBJECT-TYPE
   SYNTAX     OCTET STRING (SIZE (1))
   ACCESS     read-only
   STATUS     mandatory
   DESCRIPTION
     "If supported by the component, this attribute indicates the OSI 
      Alarm status of the component. Note that, even though it is defined 
      as a multi-valued set, at most one value is shown to the user.
      
      When no values are in the set, this indicates that either the attribute 
      is not supported or that none of the status conditions described 
      below are present.
      
      The value underRepair indicates the component is currently being 
      repaired. The operationalState is enabled or disabled.
      
      The value critical indicates one or more critical alarms are 
      outstanding against the component. Other, less severe, alarms may 
      also be outstanding. The operationalState is enabled or disabled.
      
      The value major indicates one or more major alarms are 
      outstanding against the component. Other, less severe, alarms may 
      also be outstanding. The operationalState is enabled or disabled.
      
      The value minor indicates one or more minor alarms are 
      outstanding against the component. Other, less severe, alarms may 
      also be outstanding. The operationalState is enabled or disabled.
      
      The value alarmOutstanding generically indicates that an alarm of 
      some severity is outstanding against the component.

      Description of bits:
      underRepair(0)
      critical(1)
      major(2)
      minor(3)
      alarmOutstanding(4)"
::= { mscLpDS1StateEntry 7 }

mscLpDS1StandbyStatus OBJECT-TYPE
   SYNTAX     INTEGER  {
                 hotStandby(0),
                 coldStandby(1),
                 providingService(2),
                 notSet(15) }
   ACCESS     read-only
   STATUS     mandatory
   DESCRIPTION
     "If supported by the component, this attribute indicates the OSI 
      Standby status of the component.
      
      The value notSet indicates that either the attribute is not supported 
      or that none of the status conditions described below are present. 
      Note that this is a non-standard value, used because the original 
      specification indicated this attribute was set-valued and thus, did not 
      provide a value to indicate that none of the other three are 
      applicable.
      
      The value hotStandby indicates that the resource is not providing 
      service but will be immediately able to take over the role of the 
      resource to be backed up, without initialization activity, and 
      containing the same information as the resource to be backed up.
      
      The value coldStandby indicates the resource is a backup for 
      another resource but will not be immediately able to take over the 
      role of the backed up resource and will require some initialization 
      activity.
      
      The value providingService indicates that this component, as a 
      backup resource, is currently backing up another resource."
   DEFVAL     { notSet }
::= { mscLpDS1StateEntry 8 }

mscLpDS1UnknownStatus OBJECT-TYPE
   SYNTAX     INTEGER  {
                 false(0),
                 true(1) }
   ACCESS     read-only
   STATUS     mandatory
   DESCRIPTION
     "This attribute indicates the OSI Unknown status of the component.
      
      The value false indicates that all of the other OSI State and Status 
      attribute values can be considered accurate.
      
      The value true indicates that the actual state of the component is not 
      known for sure."
   DEFVAL     { false }
::= { mscLpDS1StateEntry 9 }

mscLpDS1OperTable OBJECT-TYPE
   SYNTAX     SEQUENCE OF MscLpDS1OperEntry
   ACCESS     not-accessible
   STATUS     mandatory
   DESCRIPTION
     "This group contains the common operational data for a component 
      in a digital hierarchy interface."
::= { mscLpDS1 16 }

mscLpDS1OperEntry OBJECT-TYPE
   SYNTAX     MscLpDS1OperEntry
   ACCESS     not-accessible
   STATUS     mandatory
   DESCRIPTION
     "An entry in the mscLpDS1OperTable."
   INDEX {
      mscLpIndex,
      mscLpDS1Index }
::= { mscLpDS1OperTable 1 }

MscLpDS1OperEntry ::= SEQUENCE {
   mscLpDS1LosAlarm
      INTEGER,
   mscLpDS1RxAisAlarm
      INTEGER,
   mscLpDS1LofAlarm
      INTEGER,
   mscLpDS1RxRaiAlarm
      INTEGER,
   mscLpDS1TxAisAlarm
      INTEGER,
   mscLpDS1TxRaiAlarm
      INTEGER }

mscLpDS1LosAlarm OBJECT-TYPE
   SYNTAX     INTEGER  {
                 on(0),
                 off(1) }
   ACCESS     read-only
   STATUS     mandatory
   DESCRIPTION
     "This attribute displays whether a LOS (Loss of Signal) alarm state 
      has been entered. A LOS alarm is declared after LOS defects have 
      been observed and accumulated for a period of 2 seconds +/- 0.5 
      seconds (for 3pDS1Atm, 3pE1Atm, 8pDS1Atm, and 8pE1Atm 
      cards: 2.5 seconds +/- 0.5 seconds).  A LOS defect is detected upon 
      observing all zeros for 150 ms (for 3pDS1Atm, 3pE1Atm, 
      8pDS1Atm, and 8pE1Atm cards: upon observing 175 +/- 75 pulse 
      positions with no pulses of either positive or negative polarity). If 
      the LOS defects are intermittently occurring, the LOS defect 
      accumulator is decremented at a rate of 1/10 of the incrementing 
      rate (alarm integration ratio of 1/10), with all measurements based 
      on a 200 ms polling cycle.
      The port goes into an operational state of disabled until the LOS 
      alarm state is cleared. Also, an RAI alarm is transmitted to the far 
      end for the duration of the LOS alarm state.
      The LOS alarm state is cleared when LOS defects are absent for 10 
      seconds +/- 0.5 seconds."
   DEFVAL     { off }
::= { mscLpDS1OperEntry 1 }

mscLpDS1RxAisAlarm OBJECT-TYPE
   SYNTAX     INTEGER  {
                 on(0),
                 off(1) }
   ACCESS     read-only
   STATUS     mandatory
   DESCRIPTION
     "This attribute displays whether an AIS (Alarm Indication Signal) 
      alarm state has been entered. The AIS Alarm state is entered when 
      AIS defects have been observed and accumulated for 2.5 seconds +/
      - 0.5 seconds. An AIS defect is detected after having received less 
      than 3 zeros in a 2048 bit period (for 8pDS1Atm cards: when both 
      an Out Of Frame condition exists and a 1's density of at least 99.9% 
      is present for a time T, where 3 ms  T  75 ms; for 8pE1Atm 
      cards: when both an Out Of Frame condition exists and fewer than 
      three 0's have been received in 512 bit periods). If the AIS defects 
      are intermittently occurring, the AIS defect accumulator is 
      decremented at a rate of 1/10 of the incrementing rate (alarm 
      integration ratio of 1/10), with all measurements based on a 200 ms 
      polling cycle.
      The port goes into an operational state of disabled for the duration 
      of an AIS alarm state.
      The AIS alarm state is cleared when AIS defects are absent for 10 
      seconds +/- 0.5 seconds."
   DEFVAL     { off }
::= { mscLpDS1OperEntry 2 }

mscLpDS1LofAlarm OBJECT-TYPE
   SYNTAX     INTEGER  {
                 on(0),
                 off(1) }
   ACCESS     read-only
   STATUS     mandatory
   DESCRIPTION
     "This attribute displays whether a LOF (Loss of Frame) alarm state 
      has been entered. The LOF alarm state is entered when LOF defects 
      (for DS1: 2 out of 5 framing bits in error; for E1: 3 consecutive 
      frame alignment patterns in error) have been detected for 3 seconds 
      +/- 0.5 seconds (for 3pDS1Atm, 3pE1Atm, 8pDS1Atm, and 
      8pE1Atm cards: 2.5 seconds +/- 0.5 seconds). If the LOF defects 
      are intermittently occurring, the LOF defect accumulator is 
      decremented at a rate of 1/10 of the incrementing rate (alarm 
      integration ratio of 1/10), with all measurements based on a 200 ms 
      polling cycle.
      The port goes into an operational state of disabled until the LOF 
      alarm state is cleared. Also, an RAI alarm is transmitted to the far 
      end for the duration of the LOF alarm state 
      The condition is cleared when framing has been achieved for 10 
      seconds +/- 0.5 seconds."
   DEFVAL     { off }
::= { mscLpDS1OperEntry 3 }

mscLpDS1RxRaiAlarm OBJECT-TYPE
   SYNTAX     INTEGER  {
                 on(0),
                 off(1) }
   ACCESS     read-only
   STATUS     mandatory
   DESCRIPTION
     "This attribute displays whether an RAI (Remote Alarm Indication) 
      alarm state has been entered. An RAI alarm state is entered when 
      the RAI defect indicator has been observed and accumulated for 3.5 
      seconds +/- 0.5 seconds. For 3pDS1Atm, and 8pDS1Atm cards: 
      alarm is declared immediately upon observing the defect is present, 
      with no integration time. For 3pE1Atm, and 8pE1Atm cards: alarm 
      state is entered when the RAI defect indicator has been observed 
      and accumulated for 2.5 seconds +/- 0.5 seconds. If the RAI defects 
      are intermittently occurring, the RAI defect accumulator is 
      decremented at a rate of 1/10 of the incrementing rate (alarm 
      integration ratio of 1/10), with all measurements based on a 200 ms 
      polling cycle. 
      The RAI alarm state is cleared when the RAI defect indicator has 
      been absent for 10 seconds +/- 0.5 seconds (for 3pDS1Atm, and 
      8pDS1Atm cards: alarm is cleared immediately upon observing the 
      defect is absent, with no integration time).
      The RAI alarm is usually an indication that the far end facility is 
      unable to gain synchronization."
   DEFVAL     { off }
::= { mscLpDS1OperEntry 4 }

mscLpDS1TxAisAlarm OBJECT-TYPE
   SYNTAX     INTEGER  {
                 on(0),
                 off(1) }
   ACCESS     read-only
   STATUS     mandatory
   DESCRIPTION
     "This attribute displays whether an AIS (Alarm Indication Signal) 
      alarm is being transmitted on the line. An AIS alarm is transmitted 
      when the port is in a locked state."
   DEFVAL     { off }
::= { mscLpDS1OperEntry 5 }

mscLpDS1TxRaiAlarm OBJECT-TYPE
   SYNTAX     INTEGER  {
                 on(0),
                 off(1) }
   ACCESS     read-only
   STATUS     mandatory
   DESCRIPTION
     "This attribute displays whether a RAI signal is being sent on the 
      outgoing line. The RAI signal is transmitted when the port detects a 
      LOF alarm condition (for 3pDS1Atm, 3pE1Atm, 8pDS1Atm, and 
      8pE1Atm cards: RAI is transmitted when the port detects a LOS, 
      LOF, or AIS condition)."
   DEFVAL     { off }
::= { mscLpDS1OperEntry 6 }

mscLpDS1StatsTable OBJECT-TYPE
   SYNTAX     SEQUENCE OF MscLpDS1StatsEntry
   ACCESS     not-accessible
   STATUS     mandatory
   DESCRIPTION
     "This group contains the common statistical data for a component in 
      a digital hierarchy interface."
::= { mscLpDS1 17 }

mscLpDS1StatsEntry OBJECT-TYPE
   SYNTAX     MscLpDS1StatsEntry
   ACCESS     not-accessible
   STATUS     mandatory
   DESCRIPTION
     "An entry in the mscLpDS1StatsTable."
   INDEX {
      mscLpIndex,
      mscLpDS1Index }
::= { mscLpDS1StatsTable 1 }

MscLpDS1StatsEntry ::= SEQUENCE {
   mscLpDS1RunningTime
      Counter32,
   mscLpDS1ErrorFreeSec
      Counter32,
   mscLpDS1ErroredSec
      Counter32,
   mscLpDS1SevErroredSec
      Counter32,
   mscLpDS1SevErroredFrmSec
      Counter32,
   mscLpDS1UnavailSec
      Counter32,
   mscLpDS1BpvErrors
      Counter32,
   mscLpDS1CrcErrors
      Counter32,
   mscLpDS1FrmErrors
      Counter32,
   mscLpDS1LosStateChanges
      Counter32,
   mscLpDS1SlipErrors
      Counter32 }

mscLpDS1RunningTime OBJECT-TYPE
   SYNTAX     Counter32 
   ACCESS     read-only
   STATUS     mandatory
   DESCRIPTION
     "The number of seconds since the port component was activated."
::= { mscLpDS1StatsEntry 1 }

mscLpDS1ErrorFreeSec OBJECT-TYPE
   SYNTAX     Counter32 
   ACCESS     read-only
   STATUS     mandatory
   DESCRIPTION
     "The number of seconds that the port has been in an error free state."
::= { mscLpDS1StatsEntry 2 }

mscLpDS1ErroredSec OBJECT-TYPE
   SYNTAX     Counter32 
   ACCESS     read-only
   STATUS     mandatory
   DESCRIPTION
     "An errored second is declared when a second with one or more 
      Code Violation Error events, or one or more Out Of Frame events 
      occurs. A code violation error may be a CRC error or a BPV error. 
      An Out Of Frame event occurs when 2 out of 5 framing bits are in 
      error."
::= { mscLpDS1StatsEntry 3 }

mscLpDS1SevErroredSec OBJECT-TYPE
   SYNTAX     Counter32 
   ACCESS     read-only
   STATUS     mandatory
   DESCRIPTION
     "A severely errored second occurs when a second with 320 or more 
      Code Violation Error events or one or more Out Of Frame events 
      occurs."
::= { mscLpDS1StatsEntry 4 }

mscLpDS1SevErroredFrmSec OBJECT-TYPE
   SYNTAX     Counter32 
   ACCESS     read-only
   STATUS     mandatory
   DESCRIPTION
     "A severely errored framing second occurs when a second with one 
      or more Out Of Frame events occurs."
::= { mscLpDS1StatsEntry 5 }

mscLpDS1UnavailSec OBJECT-TYPE
   SYNTAX     Counter32 
   ACCESS     read-only
   STATUS     mandatory
   DESCRIPTION
     "The total number of seconds that the interface is in an unavailable 
      signal state. An unavailable signal state occurs at the onset of 10 
      consecutive Severely Errored Seconds. The state is cleared at the 
      onset of 10 seconds with no Severely Errored Seconds."
::= { mscLpDS1StatsEntry 6 }

mscLpDS1BpvErrors OBJECT-TYPE
   SYNTAX     Counter32 
   ACCESS     read-only
   STATUS     mandatory
   DESCRIPTION
     "The current count of Bipolar Violations. A bipolar violation is an 
      error in the alternate mark inversion pattern (AMI) on the line."
::= { mscLpDS1StatsEntry 7 }

mscLpDS1CrcErrors OBJECT-TYPE
   SYNTAX     Counter32 
   ACCESS     read-only
   STATUS     mandatory
   DESCRIPTION
     "If the interface is a DS1 line, it is the current count of CRC-6 errors. 
      These will only be counted when the lineType is ESF.
      If the interface is an E1 line, it is the total number of CRC-4 errors. 
      These will only be counted when crc4Mode is on."
::= { mscLpDS1StatsEntry 8 }

mscLpDS1FrmErrors OBJECT-TYPE
   SYNTAX     Counter32 
   ACCESS     read-only
   STATUS     mandatory
   DESCRIPTION
     "The current count of frame errors. A frame error is an error in the 
      framing bits"
::= { mscLpDS1StatsEntry 9 }

mscLpDS1LosStateChanges OBJECT-TYPE
   SYNTAX     Counter32 
   ACCESS     read-only
   STATUS     mandatory
   DESCRIPTION
     "The total number of times that the line lost signal."
::= { mscLpDS1StatsEntry 10 }

mscLpDS1SlipErrors OBJECT-TYPE
   SYNTAX     Counter32 
   ACCESS     read-only
   STATUS     mandatory
   DESCRIPTION
     "The total number of times that the line experienced a controlled 
      frame slip. This attribute is incremented for ports on the voice cards 
      (for example the 1pDS1V and the 1pE1V function processors) only."
::= { mscLpDS1StatsEntry 11 }


-- Channel
-- The Channel component is configured to control a group of 
-- timeslots that form a fractional group on a DS1 or E1 port. 
-- Cell-based cards allow only one channel per port, and this is 
-- automatically provisioned with all available timeslots. Similarly, the 
-- 1pDS3C card type only allows one channel per port, and this is 
-- automatically provisioned with all available timeslots.

mscLpDS1Chan OBJECT IDENTIFIER ::= { mscLpDS1 2 }



mscLpDS1ChanRowStatusTable OBJECT-TYPE
   SYNTAX     SEQUENCE OF MscLpDS1ChanRowStatusEntry
   ACCESS     not-accessible
   STATUS     mandatory
   DESCRIPTION
     "This entry controls the addition and deletion of 
      mscLpDS1Chan components."
::= { mscLpDS1Chan 1 }

mscLpDS1ChanRowStatusEntry OBJECT-TYPE
   SYNTAX     MscLpDS1ChanRowStatusEntry
   ACCESS     not-accessible
   STATUS     mandatory
   DESCRIPTION
     "A single entry in the table represents a single 
      mscLpDS1Chan component."
   INDEX {
      mscLpIndex,
      mscLpDS1Index,
      mscLpDS1ChanIndex }
::= { mscLpDS1ChanRowStatusTable 1 }

MscLpDS1ChanRowStatusEntry ::= SEQUENCE {
   mscLpDS1ChanRowStatus
      RowStatus,
   mscLpDS1ChanComponentName
      DisplayString,
   mscLpDS1ChanStorageType
      StorageType,
   mscLpDS1ChanIndex
      Integer32 }

mscLpDS1ChanRowStatus OBJECT-TYPE
   SYNTAX     RowStatus 
   ACCESS     read-write
   STATUS     mandatory
   DESCRIPTION
     "This variable is used as the basis for SNMP naming of
      mscLpDS1Chan components.
      These components can be added and deleted."
::= { mscLpDS1ChanRowStatusEntry 1 }

mscLpDS1ChanComponentName OBJECT-TYPE
   SYNTAX     DisplayString 
   ACCESS     read-only
   STATUS     mandatory
   DESCRIPTION
     "This variable provides the component's string name for
      use with the ASCII Console Interface"
::= { mscLpDS1ChanRowStatusEntry 2 }

mscLpDS1ChanStorageType OBJECT-TYPE
   SYNTAX     StorageType 
   ACCESS     read-only
   STATUS     mandatory
   DESCRIPTION
     "This variable represents the storage type value for the
      mscLpDS1Chan tables."
::= { mscLpDS1ChanRowStatusEntry 4 }

mscLpDS1ChanIndex OBJECT-TYPE
   SYNTAX     Integer32 (0..24)
   ACCESS     not-accessible
   STATUS     mandatory
   DESCRIPTION
     "This variable represents the index for the mscLpDS1Chan tables."
::= { mscLpDS1ChanRowStatusEntry 10 }

mscLpDS1ChanProvTable OBJECT-TYPE
   SYNTAX     SEQUENCE OF MscLpDS1ChanProvEntry
   ACCESS     not-accessible
   STATUS     mandatory
   DESCRIPTION
     "This group contains all of the provisional data for a Channel 
      component."
::= { mscLpDS1Chan 10 }

mscLpDS1ChanProvEntry OBJECT-TYPE
   SYNTAX     MscLpDS1ChanProvEntry
   ACCESS     not-accessible
   STATUS     mandatory
   DESCRIPTION
     "An entry in the mscLpDS1ChanProvTable."
   INDEX {
      mscLpIndex,
      mscLpDS1Index,
      mscLpDS1ChanIndex }
::= { mscLpDS1ChanProvTable 1 }

MscLpDS1ChanProvEntry ::= SEQUENCE {
   mscLpDS1ChanTimeslots
      OCTET STRING,
   mscLpDS1ChanTimeslotDataRate
      INTEGER,
   mscLpDS1ChanApplicationFramerName
      Link }

mscLpDS1ChanTimeslots OBJECT-TYPE
   SYNTAX     OCTET STRING (SIZE (4))
   ACCESS     read-write
   STATUS     mandatory
   DESCRIPTION
     "This attribute contains the list of timeslots that are used by the 
      Channel component. Valid numbers are 1-24 for a Channel used by 
      a DS1 component, and 1-31 for a Channel used by an E1 
      component.

      Description of bits:
      notused0(0)
      n1(1)
      n2(2)
      n3(3)
      n4(4)
      n5(5)
      n6(6)
      n7(7)
      n8(8)
      n9(9)
      n10(10)
      n11(11)
      n12(12)
      n13(13)
      n14(14)
      n15(15)
      n16(16)
      n17(17)
      n18(18)
      n19(19)
      n20(20)
      n21(21)
      n22(22)
      n23(23)
      n24(24)
      n25(25)
      n26(26)
      n27(27)
      n28(28)
      n29(29)
      n30(30)
      n31(31)"
::= { mscLpDS1ChanProvEntry 1 }

mscLpDS1ChanTimeslotDataRate OBJECT-TYPE
   SYNTAX     INTEGER  {
                 n56k(0),
                 doNotOverride(1) }
   ACCESS     read-write
   STATUS     mandatory
   DESCRIPTION
     "This attribute selects the data rate of the timeslots in a channel of a 
      DS1 component. For E1, the data rate of the timeslots will always 
      be 64kbit/s regardless of this attribute.
      When doNotOverride is selected for a channel on a DS1, the data 
      rate of the channel's timeslots are dependant on the zeroCoding 
      selection of the DS1 component. If the zeroCoding is B8ZS (where 
      supported on the FP) or none, the timeslot's data rate will be 64kbit/
      s. If the zeroCoding option is bit7Stuffing, the data rate of a timeslot 
      will be 56kbit/s.
      When 56k is selected for a channel on a DS1, the least significant 
      bit of each timeslot of this Channel will always be set to 1 and not 
      used for data. The data rate for the timeslots of this channel is 
      therefore restricted to 56kbit/s.
      One application of this attribute is to allow a DS1 line to support 
      mixing channels that originate from lines that use different 
      zeroCoding schemes."
   DEFVAL     { doNotOverride }
::= { mscLpDS1ChanProvEntry 2 }

mscLpDS1ChanApplicationFramerName OBJECT-TYPE
   SYNTAX     Link 
   ACCESS     read-write
   STATUS     mandatory
   DESCRIPTION
     "This attribute defines the link to the software stack. It defines which 
      application is running on top of this hardware component."
::= { mscLpDS1ChanProvEntry 3 }

mscLpDS1ChanCidDataTable OBJECT-TYPE
   SYNTAX     SEQUENCE OF MscLpDS1ChanCidDataEntry
   ACCESS     not-accessible
   STATUS     mandatory
   DESCRIPTION
     "This group contains the attribute for a component's Customer 
      Identifier (CID). Refer to the attribute description for a detailed 
      explanation of CIDs."
::= { mscLpDS1Chan 11 }

mscLpDS1ChanCidDataEntry OBJECT-TYPE
   SYNTAX     MscLpDS1ChanCidDataEntry
   ACCESS     not-accessible
   STATUS     mandatory
   DESCRIPTION
     "An entry in the mscLpDS1ChanCidDataTable."
   INDEX {
      mscLpIndex,
      mscLpDS1Index,
      mscLpDS1ChanIndex }
::= { mscLpDS1ChanCidDataTable 1 }

MscLpDS1ChanCidDataEntry ::= SEQUENCE {
   mscLpDS1ChanCustomerIdentifier
      Unsigned32 }

mscLpDS1ChanCustomerIdentifier OBJECT-TYPE
   SYNTAX     Unsigned32 (0 | 1..8191)
   ACCESS     read-write
   STATUS     mandatory
   DESCRIPTION
     "This attribute holds the Customer Identifier (CID).
      
      Every component has a CID. If a component has a cid attribute, the 
      component's CID is the provisioned value of that attribute; 
      otherwise the component inherits the CID of its parent. The top-
      level component has a CID of 0.
      
      Every operator session also has a CID, which is the CID 
      provisioned for the operator's user ID. An operator will see only the 
      stream data for components having a matching CID. Also, the 
      operator will be allowed to issue commands for only those 
      components which have a matching CID.
      
      An operator CID of 0 is used to identify the Network Manager 
      (referred to as 'NetMan' in DPN). This CID matches the CID of 
      any component. Values 1 to 8191 inclusive (equivalent to 'basic 
      CIDs' in DPN) may be assigned to specific customers."
   DEFVAL     { 0 }
::= { mscLpDS1ChanCidDataEntry 1 }

mscLpDS1ChanIfEntryTable OBJECT-TYPE
   SYNTAX     SEQUENCE OF MscLpDS1ChanIfEntryEntry
   ACCESS     not-accessible
   STATUS     mandatory
   DESCRIPTION
     "This group contains the provisionable attributes for the ifEntry."
::= { mscLpDS1Chan 12 }

mscLpDS1ChanIfEntryEntry OBJECT-TYPE
   SYNTAX     MscLpDS1ChanIfEntryEntry
   ACCESS     not-accessible
   STATUS     mandatory
   DESCRIPTION
     "An entry in the mscLpDS1ChanIfEntryTable."
   INDEX {
      mscLpIndex,
      mscLpDS1Index,
      mscLpDS1ChanIndex }
::= { mscLpDS1ChanIfEntryTable 1 }

MscLpDS1ChanIfEntryEntry ::= SEQUENCE {
   mscLpDS1ChanIfAdminStatus
      INTEGER,
   mscLpDS1ChanIfIndex
      InterfaceIndex }

mscLpDS1ChanIfAdminStatus OBJECT-TYPE
   SYNTAX     INTEGER  {
                 up(1),
                 down(2),
                 testing(3) }
   ACCESS     read-write
   STATUS     mandatory
   DESCRIPTION
     "The desired state of the interface. The up state indicates the 
      interface is operational. The down state indicates the interface is not 
      operational. The testing state indicates that no operational packets 
      can be passed."
   DEFVAL     { up }
::= { mscLpDS1ChanIfEntryEntry 1 }

mscLpDS1ChanIfIndex OBJECT-TYPE
   SYNTAX     InterfaceIndex (1..65535)
   ACCESS     read-only
   STATUS     mandatory
   DESCRIPTION
     "This is the index for the IfEntry. Its value is automatically initialized 
      during the provisioning process."
::= { mscLpDS1ChanIfEntryEntry 2 }

mscLpDS1ChanOperStatusTable OBJECT-TYPE
   SYNTAX     SEQUENCE OF MscLpDS1ChanOperStatusEntry
   ACCESS     not-accessible
   STATUS     mandatory
   DESCRIPTION
     "This group includes the Operational Status attribute. This attribute 
      defines the current operational state of this component."
::= { mscLpDS1Chan 13 }

mscLpDS1ChanOperStatusEntry OBJECT-TYPE
   SYNTAX     MscLpDS1ChanOperStatusEntry
   ACCESS     not-accessible
   STATUS     mandatory
   DESCRIPTION
     "An entry in the mscLpDS1ChanOperStatusTable."
   INDEX {
      mscLpIndex,
      mscLpDS1Index,
      mscLpDS1ChanIndex }
::= { mscLpDS1ChanOperStatusTable 1 }

MscLpDS1ChanOperStatusEntry ::= SEQUENCE {
   mscLpDS1ChanSnmpOperStatus
      INTEGER }

mscLpDS1ChanSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { mscLpDS1ChanOperStatusEntry 1 }

mscLpDS1ChanStateTable OBJECT-TYPE
   SYNTAX     SEQUENCE OF MscLpDS1ChanStateEntry
   ACCESS     not-accessible
   STATUS     mandatory
   DESCRIPTION
     "This group contains the three OSI State attributes and the six OSI 
      Status attributes. The descriptions generically indicate what each 
      attribute implies about the component. Note that not all the values 
      and state combinations described here are supported by every 
      component which uses this group. For component-specific 
      information and the valid state combinations, refer to NTP 241-
      7001-150, Passport Operations and Maintenance Guide."
::= { mscLpDS1Chan 14 }

mscLpDS1ChanStateEntry OBJECT-TYPE
   SYNTAX     MscLpDS1ChanStateEntry
   ACCESS     not-accessible
   STATUS     mandatory
   DESCRIPTION
     "An entry in the mscLpDS1ChanStateTable."
   INDEX {
      mscLpIndex,
      mscLpDS1Index,
      mscLpDS1ChanIndex }
::= { mscLpDS1ChanStateTable 1 }

MscLpDS1ChanStateEntry ::= SEQUENCE {
   mscLpDS1ChanAdminState
      INTEGER,
   mscLpDS1ChanOperationalState
      INTEGER,
   mscLpDS1ChanUsageState
      INTEGER,
   mscLpDS1ChanAvailabilityStatus
      OCTET STRING,
   mscLpDS1ChanProceduralStatus
      OCTET STRING,
   mscLpDS1ChanControlStatus
      OCTET STRING,
   mscLpDS1ChanAlarmStatus
      OCTET STRING,
   mscLpDS1ChanStandbyStatus
      INTEGER,
   mscLpDS1ChanUnknownStatus
      INTEGER }

mscLpDS1ChanAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component.
      
      The OSI Status attributes, if supported by the component, may 
      provide more details, qualifying the state of the component."
   DEFVAL     { unlocked }
::= { mscLpDS1ChanStateEntry 1 }

mscLpDS1ChanOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle.
      
      The OSI Status attributes, if supported by the component, may 
      provide more details, qualifying the state of the component."
   DEFVAL     { disabled }
::= { mscLpDS1ChanStateEntry 2 }

mscLpDS1ChanUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time.
      
      The OSI Status attributes, if supported by the component, may 
      provide more details, qualifying the state of the component."
   DEFVAL     { idle }
::= { mscLpDS1ChanStateEntry 3 }

mscLpDS1ChanAvailabilityStatus OBJECT-TYPE
   SYNTAX     OCTET STRING (SIZE (2))
   ACCESS     read-only
   STATUS     mandatory
   DESCRIPTION
     "If supported by the component, this attribute indicates the OSI 
      Availability status of the component. Note that, even though it is 
      defined as a multi-valued set, at most one value is shown to the user.
      
      When no values are in the set, this indicates that either the attribute 
      is not supported or that none of the status conditions described 
      below are present.
      
      The value inTest indicates that the resource is undergoing a test 
      procedure. If adminState is locked or shuttingDown, the normal 
      users are precluded from using the resource and controlStatus is 
      reservedForTest. Tests that do not exclude additional users can be 
      present in any operational or administrative state but the 
      reservedForTest condition should not be present.
      
      The value failed indicates that the component has an internal fault 
      that prevents it from operating. The operationalState is disabled.
      
      The value dependency indicates that the component cannot operate 
      because some other resource on which it depends is unavailable. 
      The operationalState is disabled.
      
      The value powerOff indicates the resource requires power to be 
      applied and it is not powered on. The operationalState is disabled.
      
      The value offLine indicates the resource requires a routine 
      operation (either manual, automatic, or both) to be performed to 
      place it on-line and make it available for use. The operationalState 
      is disabled.
      
      The value offDuty indicates the resource is inactive in accordance 
      with a predetermined time schedule. In the absence of other 
      disabling conditions, the operationalState is enabled or disabled.
      
      The value degraded indicates the service provided by the 
      component is degraded in some way, such as in speed or operating 
      capacity. However, the resource remains available for service. The 
      operationalState is enabled.
      
      The value notInstalled indicates the resource is not present. The 
      operationalState is disabled.
      
      The value logFull is not used.

      Description of bits:
      inTest(0)
      failed(1)
      powerOff(2)
      offLine(3)
      offDuty(4)
      dependency(5)
      degraded(6)
      notInstalled(7)
      logFull(8)"
::= { mscLpDS1ChanStateEntry 4 }

mscLpDS1ChanProceduralStatus OBJECT-TYPE
   SYNTAX     OCTET STRING (SIZE (1))
   ACCESS     read-only
   STATUS     mandatory
   DESCRIPTION
     "If supported by the component, this attribute indicates the OSI 
      Procedural status of the component. Note that, even though it is 
      defined as a multi-valued set, at most one value is shown to the user.
      
      When no values are in the set, this indicates that either the attribute 
      is not supported or that none of the status conditions described 
      below are present.
      
      The value initializationRequired indicates (for a resource which 
      doesn't initialize autonomously) that initialization is required before 
      it can perform its normal functions, and this procedure has not been 
      initiated. The operationalState is disabled.
      
      The value notInitialized indicates (for a resource which does 
      initialize autonomously) that initialization is required before it can 
      perform its normal functions, and this procedure has not been 
      initiated. The operationalState may be enabled or disabled.
      
      The value initializing indicates that initialization has been initiated 
      but is not yet complete. The operationalState may be enabled or 
      disabled.
      
      The value reporting indicates the resource has completed some 
      processing operation and is notifying the results. The 
      operationalState is enabled.
      
      The value terminating indicates the component is in a termination 
      phase. If the resource doesn't reinitialize autonomously, 
      operationalState is disabled; otherwise it is enabled or disabled.

      Description of bits:
      initializationRequired(0)
      notInitialized(1)
      initializing(2)
      reporting(3)
      terminating(4)"
::= { mscLpDS1ChanStateEntry 5 }

mscLpDS1ChanControlStatus OBJECT-TYPE
   SYNTAX     OCTET STRING (SIZE (1))
   ACCESS     read-only
   STATUS     mandatory
   DESCRIPTION
     "If supported by the component, this attribute indicates the OSI 
      Control status of the component. Note that, even though it is defined 
      as a multi-valued set, at most one value is shown to the user.
      
      When no values are in the set, this indicates that either the attribute 
      is not supported or that none of the status conditions described 
      below are present.
      
      The value subjectToTest indicates the resource is available but tests 
      may be conducted simultaneously at unpredictable times, which 
      may cause it to exhibit unusual characteristics.
      
      The value partOfServicesLocked indicates that part of the service is 
      restricted from users of a resource. The adminState is unlocked.
      
      The value reservedForTest indicates that the component is 
      administratively unavailable because it is undergoing a test 
      procedure. The adminState is locked.
      
      The value suspended indicates that the service has been 
      administratively suspended.

      Description of bits:
      subjectToTest(0)
      partOfServicesLocked(1)
      reservedForTest(2)
      suspended(3)"
::= { mscLpDS1ChanStateEntry 6 }

mscLpDS1ChanAlarmStatus OBJECT-TYPE
   SYNTAX     OCTET STRING (SIZE (1))
   ACCESS     read-only
   STATUS     mandatory
   DESCRIPTION
     "If supported by the component, this attribute indicates the OSI 
      Alarm status of the component. Note that, even though it is defined 
      as a multi-valued set, at most one value is shown to the user.
      
      When no values are in the set, this indicates that either the attribute 
      is not supported or that none of the status conditions described 
      below are present.
      
      The value underRepair indicates the component is currently being 
      repaired. The operationalState is enabled or disabled.
      
      The value critical indicates one or more critical alarms are 
      outstanding against the component. Other, less severe, alarms may 
      also be outstanding. The operationalState is enabled or disabled.
      
      The value major indicates one or more major alarms are 
      outstanding against the component. Other, less severe, alarms may 
      also be outstanding. The operationalState is enabled or disabled.
      
      The value minor indicates one or more minor alarms are 
      outstanding against the component. Other, less severe, alarms may 
      also be outstanding. The operationalState is enabled or disabled.
      
      The value alarmOutstanding generically indicates that an alarm of 
      some severity is outstanding against the component.

      Description of bits:
      underRepair(0)
      critical(1)
      major(2)
      minor(3)
      alarmOutstanding(4)"
::= { mscLpDS1ChanStateEntry 7 }

mscLpDS1ChanStandbyStatus OBJECT-TYPE
   SYNTAX     INTEGER  {
                 hotStandby(0),
                 coldStandby(1),
                 providingService(2),
                 notSet(15) }
   ACCESS     read-only
   STATUS     mandatory
   DESCRIPTION
     "If supported by the component, this attribute indicates the OSI 
      Standby status of the component.
      
      The value notSet indicates that either the attribute is not supported 
      or that none of the status conditions described below are present. 
      Note that this is a non-standard value, used because the original 
      specification indicated this attribute was set-valued and thus, did not 
      provide a value to indicate that none of the other three are 
      applicable.
      
      The value hotStandby indicates that the resource is not providing 
      service but will be immediately able to take over the role of the 
      resource to be backed up, without initialization activity, and 
      containing the same information as the resource to be backed up.
      
      The value coldStandby indicates the resource is a backup for 
      another resource but will not be immediately able to take over the 
      role of the backed up resource and will require some initialization 
      activity.
      
      The value providingService indicates that this component, as a 
      backup resource, is currently backing up another resource."
   DEFVAL     { notSet }
::= { mscLpDS1ChanStateEntry 8 }

mscLpDS1ChanUnknownStatus OBJECT-TYPE
   SYNTAX     INTEGER  {
                 false(0),
                 true(1) }
   ACCESS     read-only
   STATUS     mandatory
   DESCRIPTION
     "This attribute indicates the OSI Unknown status of the component.
      
      The value false indicates that all of the other OSI State and Status 
      attribute values can be considered accurate.
      
      The value true indicates that the actual state of the component is not 
      known for sure."
   DEFVAL     { false }
::= { mscLpDS1ChanStateEntry 9 }

mscLpDS1ChanOperTable OBJECT-TYPE
   SYNTAX     SEQUENCE OF MscLpDS1ChanOperEntry
   ACCESS     not-accessible
   STATUS     mandatory
   DESCRIPTION
     "This group contains all of the operational data for a Channel 
      component."
::= { mscLpDS1Chan 15 }

mscLpDS1ChanOperEntry OBJECT-TYPE
   SYNTAX     MscLpDS1ChanOperEntry
   ACCESS     not-accessible
   STATUS     mandatory
   DESCRIPTION
     "An entry in the mscLpDS1ChanOperTable."
   INDEX {
      mscLpIndex,
      mscLpDS1Index,
      mscLpDS1ChanIndex }
::= { mscLpDS1ChanOperTable 1 }

MscLpDS1ChanOperEntry ::= SEQUENCE {
   mscLpDS1ChanActualChannelSpeed
      Gauge32 }

mscLpDS1ChanActualChannelSpeed OBJECT-TYPE
   SYNTAX     Gauge32 (0..4294967295)
   ACCESS     read-only
   STATUS     mandatory
   DESCRIPTION
     "This attribute displays the measured link speed of the Channel 
      component."
   DEFVAL     { 0 }
::= { mscLpDS1ChanOperEntry 1 }

mscLpDS1ChanAdminInfoTable OBJECT-TYPE
   SYNTAX     SEQUENCE OF MscLpDS1ChanAdminInfoEntry
   ACCESS     not-accessible
   STATUS     mandatory
   DESCRIPTION
     "This group contains the attributes pertaining to the vendor of the 
      equipment."
::= { mscLpDS1Chan 16 }

mscLpDS1ChanAdminInfoEntry OBJECT-TYPE
   SYNTAX     MscLpDS1ChanAdminInfoEntry
   ACCESS     not-accessible
   STATUS     mandatory
   DESCRIPTION
     "An entry in the mscLpDS1ChanAdminInfoTable."
   INDEX {
      mscLpIndex,
      mscLpDS1Index,
      mscLpDS1ChanIndex }
::= { mscLpDS1ChanAdminInfoTable 1 }

MscLpDS1ChanAdminInfoEntry ::= SEQUENCE {
   mscLpDS1ChanVendor
      AsciiString,
   mscLpDS1ChanCommentText
      AsciiString }

mscLpDS1ChanVendor OBJECT-TYPE
   SYNTAX     AsciiString (SIZE (0..20))
   ACCESS     read-write
   STATUS     mandatory
   DESCRIPTION
     "This is the name of the vendor supplying the facility."
::= { mscLpDS1ChanAdminInfoEntry 1 }

mscLpDS1ChanCommentText OBJECT-TYPE
   SYNTAX     AsciiString (SIZE (0..60))
   ACCESS     read-write
   STATUS     mandatory
   DESCRIPTION
     "Any miscellaneous text about the facility."
::= { mscLpDS1ChanAdminInfoEntry 2 }


-- 
-- The Test component is configured to control a hardware facility test 
-- on a physical (V35, X21, DS1, E1, DS3, E3 etc.) or a logical port.

mscLpDS1ChanTest OBJECT IDENTIFIER ::= { mscLpDS1Chan 2 }



mscLpDS1ChanTestRowStatusTable OBJECT-TYPE
   SYNTAX     SEQUENCE OF MscLpDS1ChanTestRowStatusEntry
   ACCESS     not-accessible
   STATUS     mandatory
   DESCRIPTION
     "This entry controls the addition and deletion of 
      mscLpDS1ChanTest components."
::= { mscLpDS1ChanTest 1 }

mscLpDS1ChanTestRowStatusEntry OBJECT-TYPE
   SYNTAX     MscLpDS1ChanTestRowStatusEntry
   ACCESS     not-accessible
   STATUS     mandatory
   DESCRIPTION
     "A single entry in the table represents a single 
      mscLpDS1ChanTest component."
   INDEX {
      mscLpIndex,
      mscLpDS1Index,
      mscLpDS1ChanIndex,
      mscLpDS1ChanTestIndex }
::= { mscLpDS1ChanTestRowStatusTable 1 }

MscLpDS1ChanTestRowStatusEntry ::= SEQUENCE {
   mscLpDS1ChanTestRowStatus
      RowStatus,
   mscLpDS1ChanTestComponentName
      DisplayString,
   mscLpDS1ChanTestStorageType
      StorageType,
   mscLpDS1ChanTestIndex
      NonReplicated }

mscLpDS1ChanTestRowStatus OBJECT-TYPE
   SYNTAX     RowStatus 
   ACCESS     read-only
   STATUS     mandatory
   DESCRIPTION
     "This variable is used as the basis for SNMP naming of
      mscLpDS1ChanTest components.
      These components cannot be added nor deleted."
::= { mscLpDS1ChanTestRowStatusEntry 1 }

mscLpDS1ChanTestComponentName OBJECT-TYPE
   SYNTAX     DisplayString 
   ACCESS     read-only
   STATUS     mandatory
   DESCRIPTION
     "This variable provides the component's string name for
      use with the ASCII Console Interface"
::= { mscLpDS1ChanTestRowStatusEntry 2 }

mscLpDS1ChanTestStorageType OBJECT-TYPE
   SYNTAX     StorageType 
   ACCESS     read-only
   STATUS     mandatory
   DESCRIPTION
     "This variable represents the storage type value for the
      mscLpDS1ChanTest tables."
::= { mscLpDS1ChanTestRowStatusEntry 4 }

mscLpDS1ChanTestIndex OBJECT-TYPE
   SYNTAX     NonReplicated 
   ACCESS     not-accessible
   STATUS     mandatory
   DESCRIPTION
     "This variable represents the index for the mscLpDS1ChanTest tables."
::= { mscLpDS1ChanTestRowStatusEntry 10 }

mscLpDS1ChanTestStateTable OBJECT-TYPE
   SYNTAX     SEQUENCE OF MscLpDS1ChanTestStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscLpDS1ChanTest 10 }

mscLpDS1ChanTestStateEntry OBJECT-TYPE
   SYNTAX     MscLpDS1ChanTestStateEntry
   ACCESS     not-accessible
   STATUS     mandatory
   DESCRIPTION
     "An entry in the mscLpDS1ChanTestStateTable."
   INDEX {
      mscLpIndex,
      mscLpDS1Index,
      mscLpDS1ChanIndex,
      mscLpDS1ChanTestIndex }
::= { mscLpDS1ChanTestStateTable 1 }

MscLpDS1ChanTestStateEntry ::= SEQUENCE {
   mscLpDS1ChanTestAdminState
      INTEGER,
   mscLpDS1ChanTestOperationalState
      INTEGER,
   mscLpDS1ChanTestUsageState
      INTEGER }

mscLpDS1ChanTestAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscLpDS1ChanTestStateEntry 1 }

mscLpDS1ChanTestOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscLpDS1ChanTestStateEntry 2 }

mscLpDS1ChanTestUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscLpDS1ChanTestStateEntry 3 }

mscLpDS1ChanTestSetupTable OBJECT-TYPE
   SYNTAX     SEQUENCE OF MscLpDS1ChanTestSetupEntry
   ACCESS     not-accessible
   STATUS     mandatory
   DESCRIPTION
     "This group contains all of the operational data for a Test 
      component."
::= { mscLpDS1ChanTest 11 }

mscLpDS1ChanTestSetupEntry OBJECT-TYPE
   SYNTAX     MscLpDS1ChanTestSetupEntry
   ACCESS     not-accessible
   STATUS     mandatory
   DESCRIPTION
     "An entry in the mscLpDS1ChanTestSetupTable."
   INDEX {
      mscLpIndex,
      mscLpDS1Index,
      mscLpDS1ChanIndex,
      mscLpDS1ChanTestIndex }
::= { mscLpDS1ChanTestSetupTable 1 }

MscLpDS1ChanTestSetupEntry ::= SEQUENCE {
   mscLpDS1ChanTestPurpose
      AsciiString,
   mscLpDS1ChanTestType
      INTEGER,
   mscLpDS1ChanTestFrmSize
      Unsigned32,
   mscLpDS1ChanTestFrmPatternType
      INTEGER,
   mscLpDS1ChanTestCustomizedPattern
      Hex,
   mscLpDS1ChanTestDataStartDelay
      Unsigned32,
   mscLpDS1ChanTestDisplayInterval
      Unsigned32,
   mscLpDS1ChanTestDuration
      Unsigned32 }

mscLpDS1ChanTestPurpose OBJECT-TYPE
   SYNTAX     AsciiString (SIZE (0..40))
   ACCESS     read-write
   STATUS     mandatory
   DESCRIPTION
     "This attribute records the purpose of the test so that the test results 
      can be associated and properly analyzed."
::= { mscLpDS1ChanTestSetupEntry 1 }

mscLpDS1ChanTestType OBJECT-TYPE
   SYNTAX     INTEGER  {
                 card(0),
                 manual(1),
                 localLoop(2),
                 remoteLoop(3),
                 externalLoop(4),
                 payloadLoop(5),
                 remoteLoopThisTrib(6),
                 v54RemoteLoop(7),
                 pn127RemoteLoop(8) }
   ACCESS     read-write
   STATUS     mandatory
   DESCRIPTION
     "This attribute is the type of test to be run. The available test types 
      include the following:
      card test sets up an internal loop on the board and runs a bit error 
      rate test.
      manual test assumes the line is looped back externally and a bit 
      error rate test is performed.
      localLoop test loops back the local modem and performs a bit error 
      rate test.
      remoteLoop test loops back the remote modem (or CSU) and 
      performs a bit error rate test.
      externalLoop test loops back the line to the far end.
      payloadLoop test only loops back the payload data received from 
      the incoming line.
      remoteLoopThisTrib loops this particular tributary back at the far 
      end, using services provided by the parent.
      v54RemoteLoop initiates a V.54 Remote Loopback test.
      pn127RemoteLoop initiates a PN127 Remote Loopback test.
      Note that not all test types are not supported by all function 
      processors."
   DEFVAL     { card }
::= { mscLpDS1ChanTestSetupEntry 2 }

mscLpDS1ChanTestFrmSize OBJECT-TYPE
   SYNTAX     Unsigned32 (4..4096)
   ACCESS     read-write
   STATUS     mandatory
   DESCRIPTION
     "This attribute defines the size of the test data frames in number of 
      bytes."
   DEFVAL     { 1024 }
::= { mscLpDS1ChanTestSetupEntry 3 }

mscLpDS1ChanTestFrmPatternType OBJECT-TYPE
   SYNTAX     INTEGER  {
                 ccitt32kBitPattern(0),
                 ccitt8MBitPattern(1),
                 customizedPattern(2) }
   ACCESS     read-write
   STATUS     mandatory
   DESCRIPTION
     "This attribute defines the type of data pattern generation to use. The 
      following lists the available pattern types:
      ccitt32kBitPattern is a pseudo-random sequence of 32 kbit.
      ccitt8MBitPattern is a pseudo-random sequence of 8Mbit.
      customizedPattern is the pattern defined in the customizedPattern 
      attribute."
   DEFVAL     { ccitt32kBitPattern }
::= { mscLpDS1ChanTestSetupEntry 4 }

mscLpDS1ChanTestCustomizedPattern OBJECT-TYPE
   SYNTAX     Hex (0..4294967295)
   ACCESS     read-write
   STATUS     mandatory
   DESCRIPTION
     "This attribute allows a customized 32 bit pattern to be defined for 
      use in the test data frames. This attribute is used when the attribute 
      frmPatternType is set to CustomizedPattern. Note that a 55 hex 
      pattern is an alternating 1 and 0 pattern."
   DEFVAL     { 1431655765 }
::= { mscLpDS1ChanTestSetupEntry 5 }

mscLpDS1ChanTestDataStartDelay OBJECT-TYPE
   SYNTAX     Unsigned32 (0..1814400)
   ACCESS     read-write
   STATUS     mandatory
   DESCRIPTION
     "This attribute specifies the time delay (in seconds) between when 
      the test expects the loop to have been set up, to when the test data 
      actually starts to be transmitted. This attribute is to accommodate 
      some non-standard equipment that requires extra time for setting up 
      a requested loop.
      This attribute is ignored when the test type is set to externalLoop."
   DEFVAL     { 0 }
::= { mscLpDS1ChanTestSetupEntry 6 }

mscLpDS1ChanTestDisplayInterval OBJECT-TYPE
   SYNTAX     Unsigned32 (0..30240)
   ACCESS     read-write
   STATUS     mandatory
   DESCRIPTION
     "This attribute defines the interval (in minutes) between which 
      interim test results are to be displayed. Results are displayed at the 
      operator console at which the test was started. When the test type is 
      set to externalLoop, this attribute is ignored. There will be no 
      display of results if displayInterval is set to 0. This attribute can be 
      changed anytime."
   DEFVAL     { 5 }
::= { mscLpDS1ChanTestSetupEntry 7 }

mscLpDS1ChanTestDuration OBJECT-TYPE
   SYNTAX     Unsigned32 (1..30240)
   ACCESS     read-write
   STATUS     mandatory
   DESCRIPTION
     "This attribute is the duration (in minutes) that test data will be 
      transmitted. In the case of an externalLoop, this is the time that the 
      loop is in effect. Note that dataStartDelay does not apply to the 
      externalLoop."
   DEFVAL     { 1 }
::= { mscLpDS1ChanTestSetupEntry 8 }

mscLpDS1ChanTestResultsTable OBJECT-TYPE
   SYNTAX     SEQUENCE OF MscLpDS1ChanTestResultsEntry
   ACCESS     not-accessible
   STATUS     mandatory
   DESCRIPTION
     "This group contains all the statistics related attributes of the Test 
      component."
::= { mscLpDS1ChanTest 12 }

mscLpDS1ChanTestResultsEntry OBJECT-TYPE
   SYNTAX     MscLpDS1ChanTestResultsEntry
   ACCESS     not-accessible
   STATUS     mandatory
   DESCRIPTION
     "An entry in the mscLpDS1ChanTestResultsTable."
   INDEX {
      mscLpIndex,
      mscLpDS1Index,
      mscLpDS1ChanIndex,
      mscLpDS1ChanTestIndex }
::= { mscLpDS1ChanTestResultsTable 1 }

MscLpDS1ChanTestResultsEntry ::= SEQUENCE {
   mscLpDS1ChanTestElapsedTime
      Counter32,
   mscLpDS1ChanTestTimeRemaining
      Unsigned32,
   mscLpDS1ChanTestCauseOfTermination
      INTEGER,
   mscLpDS1ChanTestBitsTx
      PassportCounter64,
   mscLpDS1ChanTestBytesTx
      PassportCounter64,
   mscLpDS1ChanTestFrmTx
      PassportCounter64,
   mscLpDS1ChanTestBitsRx
      PassportCounter64,
   mscLpDS1ChanTestBytesRx
      PassportCounter64,
   mscLpDS1ChanTestFrmRx
      PassportCounter64,
   mscLpDS1ChanTestErroredFrmRx
      PassportCounter64,
   mscLpDS1ChanTestBitErrorRate
      AsciiString }

mscLpDS1ChanTestElapsedTime OBJECT-TYPE
   SYNTAX     Counter32 
   ACCESS     read-only
   STATUS     mandatory
   DESCRIPTION
     "This attribute is the number of minutes elapsed since the test started 
      for an externalLoop test. For a data test, this is the time since test 
      data was first transmitted."
::= { mscLpDS1ChanTestResultsEntry 1 }

mscLpDS1ChanTestTimeRemaining OBJECT-TYPE
   SYNTAX     Unsigned32 (0..4294967295)
   ACCESS     read-only
   STATUS     mandatory
   DESCRIPTION
     "This attribute is the number of minutes remaining before the test is 
      to be stopped according to the duration attribute."
   DEFVAL     { 0 }
::= { mscLpDS1ChanTestResultsEntry 2 }

mscLpDS1ChanTestCauseOfTermination OBJECT-TYPE
   SYNTAX     INTEGER  {
                 testTimeExpired(0),
                 stoppedByOperator(1),
                 unknown(2),
                 neverStarted(3),
                 testRunning(4),
                 hardwareReconfigured(5),
                 loopCodeSyncFailed(6),
                 patternSyncFailed(7),
                 patternSyncLost(8) }
   ACCESS     read-only
   STATUS     mandatory
   DESCRIPTION
     "This attribute indicates either the status of the test or the cause of 
      the test's termination:
      
      neverStarted indicates that the test has not yet been started.
      
      testRunning indicates that the test has been started.
      
      stoppedByOperator indicates that the operator issued a stop 
      command on a test that was running.
      
      testTimeExpired indicates that the test ran for the time specified by 
      the test's duration.
      
      loopCodeSyncFailed indicates that the local end failed to 
      synchronize to the loopCode pattern. The local end transmits the 
      loopCode pattern to cause the remote end to apply a loopback, after 
      which the local end should receive the loopCode pattern. The exact 
      pattern used to request loopCode depends on the test type. This 
      failure indicates a high rate of transmission errors, or that the 
      remote end has failed to apply the loopback.
      
      patternSyncFailed indicates that the local end failed to synchronize 
      to the frmPatternType test pattern, that should have been looped 
      back at the remote end. This failure indicates a high rate of 
      transmission errors or the absence of a loopback.
      
      patternSyncLost indicates that the local end gained and then lost 
      synchronization to the returned frmPatternType test pattern. This 
      failure indicates a sudden increase in transmission errors, frame 
      slippage, or the removal of an existing loopback.
      
      unknown is set when a reason to terminate other than those listed 
      here is encountered.
      
      Note: Only MSA cards support recognition of the failures 
      loopCodeSyncFailed, patternSyncFailed and patternSyncLost. 
      Other cards will not terminate the test under the conditions 
      described by these values."
   DEFVAL     { neverStarted }
::= { mscLpDS1ChanTestResultsEntry 3 }

mscLpDS1ChanTestBitsTx OBJECT-TYPE
   SYNTAX     PassportCounter64 
   ACCESS     read-only
   STATUS     mandatory
   DESCRIPTION
     "This attribute is the total number of bits sent during the test period. 
      As long as the line speed of the hardware interface is less than 
      70 Mbit/s, this counter is not expected to reach the maximum value."
::= { mscLpDS1ChanTestResultsEntry 4 }

mscLpDS1ChanTestBytesTx OBJECT-TYPE
   SYNTAX     PassportCounter64 
   ACCESS     read-only
   STATUS     mandatory
   DESCRIPTION
     "This attribute is the total number of bytes sent during the test 
      period. This counter is not expected to reach its maximum value."
::= { mscLpDS1ChanTestResultsEntry 5 }

mscLpDS1ChanTestFrmTx OBJECT-TYPE
   SYNTAX     PassportCounter64 
   ACCESS     read-only
   STATUS     mandatory
   DESCRIPTION
     "This attribute is the total number of frames sent during the test 
      period. This counter is not expected to reach its maximum value."
::= { mscLpDS1ChanTestResultsEntry 6 }

mscLpDS1ChanTestBitsRx OBJECT-TYPE
   SYNTAX     PassportCounter64 
   ACCESS     read-only
   STATUS     mandatory
   DESCRIPTION
     "This attribute is the total number of bits received during the test 
      period. This counter is not expected to reach its maximum value. 
      The counter will wrap around to 0 if it does reach the maximum 
      value."
::= { mscLpDS1ChanTestResultsEntry 7 }

mscLpDS1ChanTestBytesRx OBJECT-TYPE
   SYNTAX     PassportCounter64 
   ACCESS     read-only
   STATUS     mandatory
   DESCRIPTION
     "This attribute is the total number of bytes received during the test 
      period. This counter is not expected to reach its maximum value. 
      The counter will wrap around to 0 if it does reach its maximum 
      value."
::= { mscLpDS1ChanTestResultsEntry 8 }

mscLpDS1ChanTestFrmRx OBJECT-TYPE
   SYNTAX     PassportCounter64 
   ACCESS     read-only
   STATUS     mandatory
   DESCRIPTION
     "This attribute is the total number of frames received during the test 
      period. This counter is not expected to reach its maximum value. 
      The counter will wrap around to 0 if it does reach its maximum 
      value."
::= { mscLpDS1ChanTestResultsEntry 9 }

mscLpDS1ChanTestErroredFrmRx OBJECT-TYPE
   SYNTAX     PassportCounter64 
   ACCESS     read-only
   STATUS     mandatory
   DESCRIPTION
     "This attribute is not displayed for ATM cards because the physical 
      layer drops all errored frames at the controller interface. 
      
      For all other card types, this attribute is the total number of errored 
      frames received during the test period. This counter is not expected 
      to reach its maximum value. The counter will wrap around to 0 if it 
      does reach its maximum value."
::= { mscLpDS1ChanTestResultsEntry 10 }

mscLpDS1ChanTestBitErrorRate OBJECT-TYPE
   SYNTAX     AsciiString (SIZE (5))
   ACCESS     read-only
   STATUS     mandatory
   DESCRIPTION
     "This attribute is not displayed for ATM cards because the physical 
      layer drops all errored frames at the controller interface. 
      
      For all other card types, this attribute is the calculated bit error rate 
      on the link. Test data are generated and sent in frames of a preset 
      size (frameSize). The Test component will try to estimate the 
      number of bit errors in any errored frame which is identifiable. The 
      statistics will be updated accordingly. A lost frame (may be due to 
      an error on the flag sequence) will be discarded for the bit error rate 
      calculation. The result is presented in the form of xEsyy, where x is 
      the mantissa, syy is the exponent, for example 0E+00, 2E-09.
      Note that the bitErrorRate is an estimate only. For more reliable test 
      results, the test should be done over a long period. Multiple tests 
      would also improve the confidence level of the test results."
::= { mscLpDS1ChanTestResultsEntry 11 }


-- 
-- The AtmCell is a component that contains provisioning and 
-- operational attributes. The provisioning attributes are used to set the 
-- Loss of Cell Deliniation (LCD) alarm activation delay and to turn 
-- cell payload scrambling on or off. The operational attributes are 
-- used to report about the quality of the ATM cells received by the 
-- interface and the cell capacity utilization. The AtmCell component 
-- appears under all port components running on ATM cards.

mscLpDS1ChanCell OBJECT IDENTIFIER ::= { mscLpDS1Chan 3 }



mscLpDS1ChanCellRowStatusTable OBJECT-TYPE
   SYNTAX     SEQUENCE OF MscLpDS1ChanCellRowStatusEntry
   ACCESS     not-accessible
   STATUS     mandatory
   DESCRIPTION
     "This entry controls the addition and deletion of 
      mscLpDS1ChanCell components."
::= { mscLpDS1ChanCell 1 }

mscLpDS1ChanCellRowStatusEntry OBJECT-TYPE
   SYNTAX     MscLpDS1ChanCellRowStatusEntry
   ACCESS     not-accessible
   STATUS     mandatory
   DESCRIPTION
     "A single entry in the table represents a single 
      mscLpDS1ChanCell component."
   INDEX {
      mscLpIndex,
      mscLpDS1Index,
      mscLpDS1ChanIndex,
      mscLpDS1ChanCellIndex }
::= { mscLpDS1ChanCellRowStatusTable 1 }

MscLpDS1ChanCellRowStatusEntry ::= SEQUENCE {
   mscLpDS1ChanCellRowStatus
      RowStatus,
   mscLpDS1ChanCellComponentName
      DisplayString,
   mscLpDS1ChanCellStorageType
      StorageType,
   mscLpDS1ChanCellIndex
      NonReplicated }

mscLpDS1ChanCellRowStatus OBJECT-TYPE
   SYNTAX     RowStatus 
   ACCESS     read-write
   STATUS     mandatory
   DESCRIPTION
     "This variable is used as the basis for SNMP naming of
      mscLpDS1ChanCell components.
      These components can be added and deleted."
::= { mscLpDS1ChanCellRowStatusEntry 1 }

mscLpDS1ChanCellComponentName OBJECT-TYPE
   SYNTAX     DisplayString 
   ACCESS     read-only
   STATUS     mandatory
   DESCRIPTION
     "This variable provides the component's string name for
      use with the ASCII Console Interface"
::= { mscLpDS1ChanCellRowStatusEntry 2 }

mscLpDS1ChanCellStorageType OBJECT-TYPE
   SYNTAX     StorageType 
   ACCESS     read-only
   STATUS     mandatory
   DESCRIPTION
     "This variable represents the storage type value for the
      mscLpDS1ChanCell tables."
::= { mscLpDS1ChanCellRowStatusEntry 4 }

mscLpDS1ChanCellIndex OBJECT-TYPE
   SYNTAX     NonReplicated 
   ACCESS     not-accessible
   STATUS     mandatory
   DESCRIPTION
     "This variable represents the index for the mscLpDS1ChanCell tables."
::= { mscLpDS1ChanCellRowStatusEntry 10 }

mscLpDS1ChanCellProvTable OBJECT-TYPE
   SYNTAX     SEQUENCE OF MscLpDS1ChanCellProvEntry
   ACCESS     not-accessible
   STATUS     mandatory
   DESCRIPTION
     "This group contains the provisioning attributes for the AtmCell 
      component."
::= { mscLpDS1ChanCell 10 }

mscLpDS1ChanCellProvEntry OBJECT-TYPE
   SYNTAX     MscLpDS1ChanCellProvEntry
   ACCESS     not-accessible
   STATUS     mandatory
   DESCRIPTION
     "An entry in the mscLpDS1ChanCellProvTable."
   INDEX {
      mscLpIndex,
      mscLpDS1Index,
      mscLpDS1ChanIndex,
      mscLpDS1ChanCellIndex }
::= { mscLpDS1ChanCellProvTable 1 }

MscLpDS1ChanCellProvEntry ::= SEQUENCE {
   mscLpDS1ChanCellAlarmActDelay
      Unsigned32,
   mscLpDS1ChanCellScrambleCellPayload
      INTEGER,
   mscLpDS1ChanCellCorrectSingleBitHeaderErrors
      INTEGER }

mscLpDS1ChanCellAlarmActDelay OBJECT-TYPE
   SYNTAX     Unsigned32 (0..2000)
   ACCESS     read-write
   STATUS     mandatory
   DESCRIPTION
     "This attribute defines the time during which a Loss of Cell 
      Delineation (LCD) defect should be observed before declaring an 
      LCD alarm (alarm 70115501). The time is specified in milliseconds."
   DEFVAL     { 500 }
::= { mscLpDS1ChanCellProvEntry 1 }

mscLpDS1ChanCellScrambleCellPayload OBJECT-TYPE
   SYNTAX     INTEGER  {
                 off(0),
                 on(1) }
   ACCESS     read-write
   STATUS     mandatory
   DESCRIPTION
     "Cell scrambling, as defined by  ITU-T Recommendation I.432., can 
      provide a solution to the problem of transmission equipment which 
      is sensitive to certain bit patterns in the ATM cell payload. This 
      attribute controls whether or not the cell payload is scrambled.
      It defaults to off for DS1 interfaces, and on for all other interfaces.
      Note that this setting must be the same at both ends of the link."
::= { mscLpDS1ChanCellProvEntry 2 }

mscLpDS1ChanCellCorrectSingleBitHeaderErrors OBJECT-TYPE
   SYNTAX     INTEGER  {
                 off(0),
                 on(1) }
   ACCESS     read-write
   STATUS     mandatory
   DESCRIPTION
     "This attribute specifies whether the port corrects single bit errors 
      detected in the headers of received cells. If single bit errors are 
      corrected, the affected cells are passed up to the ATM layer 
      according to normal operation. If single bit errors are not corrected, 
      these errored cells are discarded by the physical layer. Note that 
      cells containing multiple bit errors in their headers are always 
      discarded.
      
      Single bit HEC error correction must remain off for the following 
      card types: 3pDS1Atm, 8pDS1Atm, 3pE1Atm, 8pE1Atm, 
      2pJ6MAtm, 3pDS3Atm, and 3pE3Atm."
   DEFVAL     { off }
::= { mscLpDS1ChanCellProvEntry 3 }

mscLpDS1ChanCellOperTable OBJECT-TYPE
   SYNTAX     SEQUENCE OF MscLpDS1ChanCellOperEntry
   ACCESS     not-accessible
   STATUS     mandatory
   DESCRIPTION
     "This group contains the common operational attributes for the 
      AtmCell component."
::= { mscLpDS1ChanCell 11 }

mscLpDS1ChanCellOperEntry OBJECT-TYPE
   SYNTAX     MscLpDS1ChanCellOperEntry
   ACCESS     not-accessible
   STATUS     mandatory
   DESCRIPTION
     "An entry in the mscLpDS1ChanCellOperTable."
   INDEX {
      mscLpIndex,
      mscLpDS1Index,
      mscLpDS1ChanIndex,
      mscLpDS1ChanCellIndex }
::= { mscLpDS1ChanCellOperTable 1 }

MscLpDS1ChanCellOperEntry ::= SEQUENCE {
   mscLpDS1ChanCellLcdAlarm
      INTEGER }

mscLpDS1ChanCellLcdAlarm OBJECT-TYPE
   SYNTAX     INTEGER  {
                 on(0),
                 off(1) }
   ACCESS     read-only
   STATUS     mandatory
   DESCRIPTION
     "This attribute displays whether the Loss of Cell Delineation (LCD) 
      failure alarm state has been entered. This state is entered when LCD 
      defects have been observed and accumulated for a period of time 
      specified through the alarmActDelay attribute.
      In ATM cell direct mapping mode, an LCD defect occurs when Out 
      of Cell Delineation (OCD) anomaly persists for x milliseconds, and 
      disappears when the Out of Cell Delineation (OCD) is absent for x 
      msec. An OCD anomaly occurs when 7 consecutive incorrect HECs 
      have been detected. An OCD anomaly terminates when 6 
      consecutive correct HECs have been detected.
      For an AtmCell component located under a DS3 or E3 component 
      with mapping = PLCP, the LCD defect is directly derived from the 
      PLCP LOF defect.
      If LCD defects are intermittently occurring, the LCD defect 
      accumulator is decremented at a rate of 1/10 of the incrementing 
      rate (alarm integration ratio of 1/10), with all measurements based 
      on a 200 ms polling cycle
      The component under which is located the AtmCell component goes 
      into an operational state of disabled until the LCD alarm condition 
      is cleared. The condition is cleared after the LCD defect has not 
      been reported for a period of 10 seconds +/- 0.5 seconds.
      The lcdAlarm attribute is always set to off when the parent of the 
      AtmCell component has been locked and left offline. This can also 
      happen when the Path or Channel component has been suspended 
      since its parent has been locked."
   DEFVAL     { off }
::= { mscLpDS1ChanCellOperEntry 1 }

mscLpDS1ChanCellStatsTable OBJECT-TYPE
   SYNTAX     SEQUENCE OF MscLpDS1ChanCellStatsEntry
   ACCESS     not-accessible
   STATUS     mandatory
   DESCRIPTION
     "This group contains the Statistics attribute for the AtmCell 
      component. Each attribute type is a non-negative integer which 
      monotonically increases until it reaches a maximum value, at which 
      point it wraps around and starts increasing again from zero."
::= { mscLpDS1ChanCell 12 }

mscLpDS1ChanCellStatsEntry OBJECT-TYPE
   SYNTAX     MscLpDS1ChanCellStatsEntry
   ACCESS     not-accessible
   STATUS     mandatory
   DESCRIPTION
     "An entry in the mscLpDS1ChanCellStatsTable."
   INDEX {
      mscLpIndex,
      mscLpDS1Index,
      mscLpDS1ChanIndex,
      mscLpDS1ChanCellIndex }
::= { mscLpDS1ChanCellStatsTable 1 }

MscLpDS1ChanCellStatsEntry ::= SEQUENCE {
   mscLpDS1ChanCellUncorrectableHecErrors
      Counter32,
   mscLpDS1ChanCellSevErroredSec
      Counter32,
   mscLpDS1ChanCellReceiveCellUtilization
      Gauge32,
   mscLpDS1ChanCellTransmitCellUtilization
      Gauge32,
   mscLpDS1ChanCellCorrectableHeaderErrors
      Counter32 }

mscLpDS1ChanCellUncorrectableHecErrors OBJECT-TYPE
   SYNTAX     Counter32 
   ACCESS     read-only
   STATUS     mandatory
   DESCRIPTION
     "This attribute indicates the number of uncorrectable ATM cell 
      header errors that have been detected. Counting of 
      uncorrectableHeaderErrors is inhibited when an Out of Cell 
      Delineation (OCD) defect is present. An OCD defect occurs when 
      seven consecutive incorrect HECs have been detected. An OCD 
      defect terminates when six consecutive correct HECs have been 
      detected."
::= { mscLpDS1ChanCellStatsEntry 1 }

mscLpDS1ChanCellSevErroredSec OBJECT-TYPE
   SYNTAX     Counter32 
   ACCESS     read-only
   STATUS     mandatory
   DESCRIPTION
     "This attribute indicates the total number of ATM Cell Severely 
      Errored Seconds (SESs) that have been counted. 
      
      In direct mapping mode, an ATM Cell SES is declared for second 
      intervals containing one or more Out of Cell Delineation (OCD) 
      defects. An OCD defect occurs when seven consecutive incorrect 
      HECs have been detected. An OCD defect terminates when six 
      consecutive correct HECs have been detected.
      
      In PLCP mapping mode, an ATM Cell SES is declared for second 
      intervals containing one or more PLCP LOF defects.
      
      Counting of uncorrectableHeaderErrors (ucErr) and 
      correctableHeaderErrors (cErr) is inhibited when the OCD defect 
      is present."
::= { mscLpDS1ChanCellStatsEntry 2 }

mscLpDS1ChanCellReceiveCellUtilization OBJECT-TYPE
   SYNTAX     Gauge32 (0..100)
   ACCESS     read-only
   STATUS     mandatory
   DESCRIPTION
     "This attribute is the ratio of the number of valid, assigned cells 
      received on the link to the nominal link capacity. The utilization is 
      calculated over a period of one minute.
      This attribute is always set to 0 when the parent of the AtmCell 
      component has been locked and left offline. This can also happen 
      when the Path or Channel component has been suspended since its 
      parent has been locked."
   DEFVAL     { 0 }
::= { mscLpDS1ChanCellStatsEntry 3 }

mscLpDS1ChanCellTransmitCellUtilization OBJECT-TYPE
   SYNTAX     Gauge32 (0..100)
   ACCESS     read-only
   STATUS     mandatory
   DESCRIPTION
     "This attribute is the ratio of the number of valid, assigned cells 
      transmitted on the link to the nominal link capacity. The utilization 
      is calculated over a period of one minute.
      This attribute is always set to 0 when the parent of the AtmCell 
      component has been locked and left offline. This can also happen 
      when the Path or Channel component has been suspended since its 
      parent has been locked."
   DEFVAL     { 0 }
::= { mscLpDS1ChanCellStatsEntry 4 }

mscLpDS1ChanCellCorrectableHeaderErrors OBJECT-TYPE
   SYNTAX     Counter32 
   ACCESS     read-only
   STATUS     mandatory
   DESCRIPTION
     "This attribute indicates the number of correctable ATM cell header 
      errors that have been detected and corrected. Counting of 
      correctableHeaderErrors is inhibited when an Out of Cell 
      Delineation (OCD) defect is present. An OCD defect occurs when 
      seven consecutive incorrect HECs have been detected. An OCD 
      defect terminates when six consecutive correct HECs have been 
      detected"
::= { mscLpDS1ChanCellStatsEntry 5 }


-- Lp/x Ds1/y Chan/z Tc
-- Lp/x E1/y Chan/z Tc
-- 
-- The Tc component is used to provision and monitor trunk 
-- conditioning options. A separate instance of this component is 
-- required for each Chan on a Port which is offering a structured 
-- constant bit rate service.
-- 
-- Under certain failure alarm conditions, trunk conditioning 
-- replacementData is substituted into the timeslots as defined by the 
-- Chan component. Trunk conditioning signaling is also substituted 
-- into the appropriate Channel Associated Signaling (CAS) bits when 
-- a lineType that uses CAS has been defined.
-- 
-- When used with AAL1 Circuit Emulation Service, trunk 
-- conditioning is transmitted towards the ATM network under the 
-- following conditions:
-- lossOfSignal (LOS)
-- lossOfFrame (LOF)
-- remoteAlarmIndication (RAI)
-- alarmIndicationSignal (AIS)
-- bufferUnderflow (BU)
-- and in addition for E1:
-- lossOfMultiframe (LOMF)
-- receiveMultiframeRemoteAlarmIndication (RMRAI)
-- 
-- When used with AAL1 Circuit Emulation Service, trunk 
-- conditioning is transmitted towards the PDH network under the 
-- following conditions:
-- bufferUnderflow (BU)
-- AAL1 protocol errors.
-- 

mscLpDS1ChanTc OBJECT IDENTIFIER ::= { mscLpDS1Chan 4 }



mscLpDS1ChanTcRowStatusTable OBJECT-TYPE
   SYNTAX     SEQUENCE OF MscLpDS1ChanTcRowStatusEntry
   ACCESS     not-accessible
   STATUS     mandatory
   DESCRIPTION
     "This entry controls the addition and deletion of 
      mscLpDS1ChanTc components."
::= { mscLpDS1ChanTc 1 }

mscLpDS1ChanTcRowStatusEntry OBJECT-TYPE
   SYNTAX     MscLpDS1ChanTcRowStatusEntry
   ACCESS     not-accessible
   STATUS     mandatory
   DESCRIPTION
     "A single entry in the table represents a single 
      mscLpDS1ChanTc component."
   INDEX {
      mscLpIndex,
      mscLpDS1Index,
      mscLpDS1ChanIndex,
      mscLpDS1ChanTcIndex }
::= { mscLpDS1ChanTcRowStatusTable 1 }

MscLpDS1ChanTcRowStatusEntry ::= SEQUENCE {
   mscLpDS1ChanTcRowStatus
      RowStatus,
   mscLpDS1ChanTcComponentName
      DisplayString,
   mscLpDS1ChanTcStorageType
      StorageType,
   mscLpDS1ChanTcIndex
      NonReplicated }

mscLpDS1ChanTcRowStatus OBJECT-TYPE
   SYNTAX     RowStatus 
   ACCESS     read-write
   STATUS     mandatory
   DESCRIPTION
     "This variable is used as the basis for SNMP naming of
      mscLpDS1ChanTc components.
      These components can be added and deleted."
::= { mscLpDS1ChanTcRowStatusEntry 1 }

mscLpDS1ChanTcComponentName OBJECT-TYPE
   SYNTAX     DisplayString 
   ACCESS     read-only
   STATUS     mandatory
   DESCRIPTION
     "This variable provides the component's string name for
      use with the ASCII Console Interface"
::= { mscLpDS1ChanTcRowStatusEntry 2 }

mscLpDS1ChanTcStorageType OBJECT-TYPE
   SYNTAX     StorageType 
   ACCESS     read-only
   STATUS     mandatory
   DESCRIPTION
     "This variable represents the storage type value for the
      mscLpDS1ChanTc tables."
::= { mscLpDS1ChanTcRowStatusEntry 4 }

mscLpDS1ChanTcIndex OBJECT-TYPE
   SYNTAX     NonReplicated 
   ACCESS     not-accessible
   STATUS     mandatory
   DESCRIPTION
     "This variable represents the index for the mscLpDS1ChanTc tables."
::= { mscLpDS1ChanTcRowStatusEntry 10 }

mscLpDS1ChanTcProvTable OBJECT-TYPE
   SYNTAX     SEQUENCE OF MscLpDS1ChanTcProvEntry
   ACCESS     not-accessible
   STATUS     mandatory
   DESCRIPTION
     "This group contains all specific provisioning data for a Tc 
      component."
::= { mscLpDS1ChanTc 10 }

mscLpDS1ChanTcProvEntry OBJECT-TYPE
   SYNTAX     MscLpDS1ChanTcProvEntry
   ACCESS     not-accessible
   STATUS     mandatory
   DESCRIPTION
     "An entry in the mscLpDS1ChanTcProvTable."
   INDEX {
      mscLpIndex,
      mscLpDS1Index,
      mscLpDS1ChanIndex,
      mscLpDS1ChanTcIndex }
::= { mscLpDS1ChanTcProvTable 1 }

MscLpDS1ChanTcProvEntry ::= SEQUENCE {
   mscLpDS1ChanTcReplacementData
      Hex,
   mscLpDS1ChanTcSignalOneDuration
      Unsigned32 }

mscLpDS1ChanTcReplacementData OBJECT-TYPE
   SYNTAX     Hex (0..255)
   ACCESS     read-write
   STATUS     mandatory
   DESCRIPTION
     "This attribute specifies the trunk conditioning data byte to be 
      substituted into the timeslots defined by the Chan component under 
      fault conditions. 
      
      replacementData can be set to any two digit hexadecimal number. 
      The following are recommended values:
      DS1 MUX Out Of Service Code = 0x1A
      E1 MUX Out Of Service Code = 0xFF"
   DEFVAL     { 255 }
::= { mscLpDS1ChanTcProvEntry 1 }

mscLpDS1ChanTcSignalOneDuration OBJECT-TYPE
   SYNTAX     Unsigned32 (0..60)
   ACCESS     read-write
   STATUS     mandatory
   DESCRIPTION
     "This attribute specifies the time duration in seconds for which 
      signalOne is substituted into the appropriate signaling bits, when a 
      lineType that uses CAS has been defined. When signalOneDuration 
      has expired signalTwo is substituted into the appropriate signaling 
      bits.
      
      If signalOneDuration is set to zero then only signalTwo is 
      substituted into the appropriate signaling bits during error 
      conditions.
      
      signalOneDuration can be set to any integer value from 0 to 60 
      seconds."
   DEFVAL     { 0 }
::= { mscLpDS1ChanTcProvEntry 2 }

mscLpDS1ChanTcOpTable OBJECT-TYPE
   SYNTAX     SEQUENCE OF MscLpDS1ChanTcOpEntry
   ACCESS     not-accessible
   STATUS     mandatory
   DESCRIPTION
     "This group contains all specific operational data for a Tc 
      component."
::= { mscLpDS1ChanTc 11 }

mscLpDS1ChanTcOpEntry OBJECT-TYPE
   SYNTAX     MscLpDS1ChanTcOpEntry
   ACCESS     not-accessible
   STATUS     mandatory
   DESCRIPTION
     "An entry in the mscLpDS1ChanTcOpTable."
   INDEX {
      mscLpIndex,
      mscLpDS1Index,
      mscLpDS1ChanIndex,
      mscLpDS1ChanTcIndex }
::= { mscLpDS1ChanTcOpTable 1 }

MscLpDS1ChanTcOpEntry ::= SEQUENCE {
   mscLpDS1ChanTcIngressConditioning
      INTEGER,
   mscLpDS1ChanTcEgressConditioning
      INTEGER }

mscLpDS1ChanTcIngressConditioning OBJECT-TYPE
   SYNTAX     INTEGER  {
                 off(0),
                 on(1) }
   ACCESS     read-only
   STATUS     mandatory
   DESCRIPTION
     "This attribute indicates the status of locally generated trunk 
      conditioning towards the ATM network.
      
      When trunk conditioning is being locally generated towards the 
      ATM network, ingressConditioning is set to on.
      
      When trunk conditioning is not being locally generated towards the 
      ATM network, ingressConditioning is set to off.
      
      Trunk conditioning is transmitted towards the ATM network under 
      the following conditions:
      lossOfSignal (LOS)
      lossOfFrame (LOF)
      remoteAlarmIndication (RAI)
      alarmIndicationSignal (AIS)
      bufferUnderflow (BU)
      and in addition for E1:
      lossOfMultiframe (LOMF)
      receiveMultiframeRemoteAlarmIndication (RMRAI)"
   DEFVAL     { off }
::= { mscLpDS1ChanTcOpEntry 1 }

mscLpDS1ChanTcEgressConditioning OBJECT-TYPE
   SYNTAX     INTEGER  {
                 off(0),
                 on(1) }
   ACCESS     read-only
   STATUS     mandatory
   DESCRIPTION
     "This attribute indicates the status of locally generated trunk 
      conditioning towards the PDH line.
      
      When trunk conditioning is being locally generated towards the 
      PDH line, egressConditioning is set to on.
      
      When trunk conditioning is not being locally generated towards the 
      PDH line, egressConditioning is set to off.
      
      Trunk conditioning is transmitted towards the PDH line under the 
      following conditions:
      bufferUnderflow (BU)
      AAL1 protocol errors."
   DEFVAL     { off }
::= { mscLpDS1ChanTcOpEntry 2 }

mscLpDS1ChanTcSigOneTable OBJECT-TYPE
   SYNTAX     SEQUENCE OF MscLpDS1ChanTcSigOneEntry
   ACCESS     not-accessible
   STATUS     mandatory
   DESCRIPTION
     "This attribute specifies the value to be substituted into the ABCD 
      signaling bits for the timeslots defined by the Chan component 
      under fault conditions. The value will be substituted for the duration 
      provisioned in signalOneDuration when a lineType that uses CAS 
      has been defined. 
      
      For a lineType of d4Cas (Super Frame), signaling bits C and D are 
      required to equal bits A and B respectively."
::= { mscLpDS1ChanTc 398 }

mscLpDS1ChanTcSigOneEntry OBJECT-TYPE
   SYNTAX     MscLpDS1ChanTcSigOneEntry
   ACCESS     not-accessible
   STATUS     mandatory
   DESCRIPTION
     "An entry in the mscLpDS1ChanTcSigOneTable."
   INDEX {
      mscLpIndex,
      mscLpDS1Index,
      mscLpDS1ChanIndex,
      mscLpDS1ChanTcIndex,
      mscLpDS1ChanTcSigOneIndex }
::= { mscLpDS1ChanTcSigOneTable 1 }

MscLpDS1ChanTcSigOneEntry ::= SEQUENCE {
   mscLpDS1ChanTcSigOneIndex
      INTEGER,
   mscLpDS1ChanTcSigOneValue
      Unsigned32 }

mscLpDS1ChanTcSigOneIndex OBJECT-TYPE
   SYNTAX     INTEGER  {
                 d(0),
                 c(1),
                 b(2),
                 a(3) }
   ACCESS     not-accessible
   STATUS     mandatory
   DESCRIPTION
     "This variable represents the mscLpDS1ChanTcSigOneTable
      specific index for the mscLpDS1ChanTcSigOneTable."
::= { mscLpDS1ChanTcSigOneEntry 1 }

mscLpDS1ChanTcSigOneValue OBJECT-TYPE
   SYNTAX     Unsigned32 (0..1)
   ACCESS     read-write
   STATUS     mandatory
   DESCRIPTION
     "This variable represents an individual value for the
      mscLpDS1ChanTcSigOneTable."
::= { mscLpDS1ChanTcSigOneEntry 2 }

mscLpDS1ChanTcSigTwoTable OBJECT-TYPE
   SYNTAX     SEQUENCE OF MscLpDS1ChanTcSigTwoEntry
   ACCESS     not-accessible
   STATUS     mandatory
   DESCRIPTION
     "This attribute specifies the value to be substituted into the ABCD 
      signaling bits for the timeslots defined by the Chan component 
      under fault conditions. The value will be substituted after the 
      duration provisioned in signalOneDuration has expired and when a 
      lineType that uses CAS has been defined. 
      
      For a lineType of d4Cas (Super Frame), signaling bits C and D are 
      required to equal bits A and B respectively."
::= { mscLpDS1ChanTc 399 }

mscLpDS1ChanTcSigTwoEntry OBJECT-TYPE
   SYNTAX     MscLpDS1ChanTcSigTwoEntry
   ACCESS     not-accessible
   STATUS     mandatory
   DESCRIPTION
     "An entry in the mscLpDS1ChanTcSigTwoTable."
   INDEX {
      mscLpIndex,
      mscLpDS1Index,
      mscLpDS1ChanIndex,
      mscLpDS1ChanTcIndex,
      mscLpDS1ChanTcSigTwoIndex }
::= { mscLpDS1ChanTcSigTwoTable 1 }

MscLpDS1ChanTcSigTwoEntry ::= SEQUENCE {
   mscLpDS1ChanTcSigTwoIndex
      INTEGER,
   mscLpDS1ChanTcSigTwoValue
      Unsigned32 }

mscLpDS1ChanTcSigTwoIndex OBJECT-TYPE
   SYNTAX     INTEGER  {
                 d(0),
                 c(1),
                 b(2),
                 a(3) }
   ACCESS     not-accessible
   STATUS     mandatory
   DESCRIPTION
     "This variable represents the mscLpDS1ChanTcSigTwoTable
      specific index for the mscLpDS1ChanTcSigTwoTable."
::= { mscLpDS1ChanTcSigTwoEntry 1 }

mscLpDS1ChanTcSigTwoValue OBJECT-TYPE
   SYNTAX     Unsigned32 (0..1)
   ACCESS     read-write
   STATUS     mandatory
   DESCRIPTION
     "This variable represents an individual value for the
      mscLpDS1ChanTcSigTwoTable."
::= { mscLpDS1ChanTcSigTwoEntry 2 }


-- 
-- The Test component is configured to control a hardware facility test 
-- on a physical (V35, X21, DS1, E1, DS3, E3 etc.) or a logical port.

mscLpDS1Test OBJECT IDENTIFIER ::= { mscLpDS1 3 }



mscLpDS1TestRowStatusTable OBJECT-TYPE
   SYNTAX     SEQUENCE OF MscLpDS1TestRowStatusEntry
   ACCESS     not-accessible
   STATUS     mandatory
   DESCRIPTION
     "This entry controls the addition and deletion of 
      mscLpDS1Test components."
::= { mscLpDS1Test 1 }

mscLpDS1TestRowStatusEntry OBJECT-TYPE
   SYNTAX     MscLpDS1TestRowStatusEntry
   ACCESS     not-accessible
   STATUS     mandatory
   DESCRIPTION
     "A single entry in the table represents a single 
      mscLpDS1Test component."
   INDEX {
      mscLpIndex,
      mscLpDS1Index,
      mscLpDS1TestIndex }
::= { mscLpDS1TestRowStatusTable 1 }

MscLpDS1TestRowStatusEntry ::= SEQUENCE {
   mscLpDS1TestRowStatus
      RowStatus,
   mscLpDS1TestComponentName
      DisplayString,
   mscLpDS1TestStorageType
      StorageType,
   mscLpDS1TestIndex
      NonReplicated }

mscLpDS1TestRowStatus OBJECT-TYPE
   SYNTAX     RowStatus 
   ACCESS     read-only
   STATUS     mandatory
   DESCRIPTION
     "This variable is used as the basis for SNMP naming of
      mscLpDS1Test components.
      These components cannot be added nor deleted."
::= { mscLpDS1TestRowStatusEntry 1 }

mscLpDS1TestComponentName OBJECT-TYPE
   SYNTAX     DisplayString 
   ACCESS     read-only
   STATUS     mandatory
   DESCRIPTION
     "This variable provides the component's string name for
      use with the ASCII Console Interface"
::= { mscLpDS1TestRowStatusEntry 2 }

mscLpDS1TestStorageType OBJECT-TYPE
   SYNTAX     StorageType 
   ACCESS     read-only
   STATUS     mandatory
   DESCRIPTION
     "This variable represents the storage type value for the
      mscLpDS1Test tables."
::= { mscLpDS1TestRowStatusEntry 4 }

mscLpDS1TestIndex OBJECT-TYPE
   SYNTAX     NonReplicated 
   ACCESS     not-accessible
   STATUS     mandatory
   DESCRIPTION
     "This variable represents the index for the mscLpDS1Test tables."
::= { mscLpDS1TestRowStatusEntry 10 }

mscLpDS1TestStateTable OBJECT-TYPE
   SYNTAX     SEQUENCE OF MscLpDS1TestStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscLpDS1Test 10 }

mscLpDS1TestStateEntry OBJECT-TYPE
   SYNTAX     MscLpDS1TestStateEntry
   ACCESS     not-accessible
   STATUS     mandatory
   DESCRIPTION
     "An entry in the mscLpDS1TestStateTable."
   INDEX {
      mscLpIndex,
      mscLpDS1Index,
      mscLpDS1TestIndex }
::= { mscLpDS1TestStateTable 1 }

MscLpDS1TestStateEntry ::= SEQUENCE {
   mscLpDS1TestAdminState
      INTEGER,
   mscLpDS1TestOperationalState
      INTEGER,
   mscLpDS1TestUsageState
      INTEGER }

mscLpDS1TestAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscLpDS1TestStateEntry 1 }

mscLpDS1TestOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscLpDS1TestStateEntry 2 }

mscLpDS1TestUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscLpDS1TestStateEntry 3 }

mscLpDS1TestSetupTable OBJECT-TYPE
   SYNTAX     SEQUENCE OF MscLpDS1TestSetupEntry
   ACCESS     not-accessible
   STATUS     mandatory
   DESCRIPTION
     "This group contains all of the operational data for a Test 
      component."
::= { mscLpDS1Test 11 }

mscLpDS1TestSetupEntry OBJECT-TYPE
   SYNTAX     MscLpDS1TestSetupEntry
   ACCESS     not-accessible
   STATUS     mandatory
   DESCRIPTION
     "An entry in the mscLpDS1TestSetupTable."
   INDEX {
      mscLpIndex,
      mscLpDS1Index,
      mscLpDS1TestIndex }
::= { mscLpDS1TestSetupTable 1 }

MscLpDS1TestSetupEntry ::= SEQUENCE {
   mscLpDS1TestPurpose
      AsciiString,
   mscLpDS1TestType
      INTEGER,
   mscLpDS1TestFrmSize
      Unsigned32,
   mscLpDS1TestFrmPatternType
      INTEGER,
   mscLpDS1TestCustomizedPattern
      Hex,
   mscLpDS1TestDataStartDelay
      Unsigned32,
   mscLpDS1TestDisplayInterval
      Unsigned32,
   mscLpDS1TestDuration
      Unsigned32 }

mscLpDS1TestPurpose OBJECT-TYPE
   SYNTAX     AsciiString (SIZE (0..40))
   ACCESS     read-write
   STATUS     mandatory
   DESCRIPTION
     "This attribute records the purpose of the test so that the test results 
      can be associated and properly analyzed."
::= { mscLpDS1TestSetupEntry 1 }

mscLpDS1TestType OBJECT-TYPE
   SYNTAX     INTEGER  {
                 card(0),
                 manual(1),
                 localLoop(2),
                 remoteLoop(3),
                 externalLoop(4),
                 payloadLoop(5),
                 remoteLoopThisTrib(6),
                 v54RemoteLoop(7),
                 pn127RemoteLoop(8) }
   ACCESS     read-write
   STATUS     mandatory
   DESCRIPTION
     "This attribute is the type of test to be run. The available test types 
      include the following:
      card test sets up an internal loop on the board and runs a bit error 
      rate test.
      manual test assumes the line is looped back externally and a bit 
      error rate test is performed.
      localLoop test loops back the local modem and performs a bit error 
      rate test.
      remoteLoop test loops back the remote modem (or CSU) and 
      performs a bit error rate test.
      externalLoop test loops back the line to the far end.
      payloadLoop test only loops back the payload data received from 
      the incoming line.
      remoteLoopThisTrib loops this particular tributary back at the far 
      end, using services provided by the parent.
      v54RemoteLoop initiates a V.54 Remote Loopback test.
      pn127RemoteLoop initiates a PN127 Remote Loopback test.
      Note that not all test types are not supported by all function 
      processors."
   DEFVAL     { card }
::= { mscLpDS1TestSetupEntry 2 }

mscLpDS1TestFrmSize OBJECT-TYPE
   SYNTAX     Unsigned32 (4..4096)
   ACCESS     read-write
   STATUS     mandatory
   DESCRIPTION
     "This attribute defines the size of the test data frames in number of 
      bytes."
   DEFVAL     { 1024 }
::= { mscLpDS1TestSetupEntry 3 }

mscLpDS1TestFrmPatternType OBJECT-TYPE
   SYNTAX     INTEGER  {
                 ccitt32kBitPattern(0),
                 ccitt8MBitPattern(1),
                 customizedPattern(2) }
   ACCESS     read-write
   STATUS     mandatory
   DESCRIPTION
     "This attribute defines the type of data pattern generation to use. The 
      following lists the available pattern types:
      ccitt32kBitPattern is a pseudo-random sequence of 32 kbit.
      ccitt8MBitPattern is a pseudo-random sequence of 8Mbit.
      customizedPattern is the pattern defined in the customizedPattern 
      attribute."
   DEFVAL     { ccitt32kBitPattern }
::= { mscLpDS1TestSetupEntry 4 }

mscLpDS1TestCustomizedPattern OBJECT-TYPE
   SYNTAX     Hex (0..4294967295)
   ACCESS     read-write
   STATUS     mandatory
   DESCRIPTION
     "This attribute allows a customized 32 bit pattern to be defined for 
      use in the test data frames. This attribute is used when the attribute 
      frmPatternType is set to CustomizedPattern. Note that a 55 hex 
      pattern is an alternating 1 and 0 pattern."
   DEFVAL     { 1431655765 }
::= { mscLpDS1TestSetupEntry 5 }

mscLpDS1TestDataStartDelay OBJECT-TYPE
   SYNTAX     Unsigned32 (0..1814400)
   ACCESS     read-write
   STATUS     mandatory
   DESCRIPTION
     "This attribute specifies the time delay (in seconds) between when 
      the test expects the loop to have been set up, to when the test data 
      actually starts to be transmitted. This attribute is to accommodate 
      some non-standard equipment that requires extra time for setting up 
      a requested loop.
      This attribute is ignored when the test type is set to externalLoop."
   DEFVAL     { 0 }
::= { mscLpDS1TestSetupEntry 6 }

mscLpDS1TestDisplayInterval OBJECT-TYPE
   SYNTAX     Unsigned32 (0..30240)
   ACCESS     read-write
   STATUS     mandatory
   DESCRIPTION
     "This attribute defines the interval (in minutes) between which 
      interim test results are to be displayed. Results are displayed at the 
      operator console at which the test was started. When the test type is 
      set to externalLoop, this attribute is ignored. There will be no 
      display of results if displayInterval is set to 0. This attribute can be 
      changed anytime."
   DEFVAL     { 5 }
::= { mscLpDS1TestSetupEntry 7 }

mscLpDS1TestDuration OBJECT-TYPE
   SYNTAX     Unsigned32 (1..30240)
   ACCESS     read-write
   STATUS     mandatory
   DESCRIPTION
     "This attribute is the duration (in minutes) that test data will be 
      transmitted. In the case of an externalLoop, this is the time that the 
      loop is in effect. Note that dataStartDelay does not apply to the 
      externalLoop."
   DEFVAL     { 1 }
::= { mscLpDS1TestSetupEntry 8 }

mscLpDS1TestResultsTable OBJECT-TYPE
   SYNTAX     SEQUENCE OF MscLpDS1TestResultsEntry
   ACCESS     not-accessible
   STATUS     mandatory
   DESCRIPTION
     "This group contains all the statistics related attributes of the Test 
      component."
::= { mscLpDS1Test 12 }

mscLpDS1TestResultsEntry OBJECT-TYPE
   SYNTAX     MscLpDS1TestResultsEntry
   ACCESS     not-accessible
   STATUS     mandatory
   DESCRIPTION
     "An entry in the mscLpDS1TestResultsTable."
   INDEX {
      mscLpIndex,
      mscLpDS1Index,
      mscLpDS1TestIndex }
::= { mscLpDS1TestResultsTable 1 }

MscLpDS1TestResultsEntry ::= SEQUENCE {
   mscLpDS1TestElapsedTime
      Counter32,
   mscLpDS1TestTimeRemaining
      Unsigned32,
   mscLpDS1TestCauseOfTermination
      INTEGER,
   mscLpDS1TestBitsTx
      PassportCounter64,
   mscLpDS1TestBytesTx
      PassportCounter64,
   mscLpDS1TestFrmTx
      PassportCounter64,
   mscLpDS1TestBitsRx
      PassportCounter64,
   mscLpDS1TestBytesRx
      PassportCounter64,
   mscLpDS1TestFrmRx
      PassportCounter64,
   mscLpDS1TestErroredFrmRx
      PassportCounter64,
   mscLpDS1TestBitErrorRate
      AsciiString }

mscLpDS1TestElapsedTime OBJECT-TYPE
   SYNTAX     Counter32 
   ACCESS     read-only
   STATUS     mandatory
   DESCRIPTION
     "This attribute is the number of minutes elapsed since the test started 
      for an externalLoop test. For a data test, this is the time since test 
      data was first transmitted."
::= { mscLpDS1TestResultsEntry 1 }

mscLpDS1TestTimeRemaining OBJECT-TYPE
   SYNTAX     Unsigned32 (0..4294967295)
   ACCESS     read-only
   STATUS     mandatory
   DESCRIPTION
     "This attribute is the number of minutes remaining before the test is 
      to be stopped according to the duration attribute."
   DEFVAL     { 0 }
::= { mscLpDS1TestResultsEntry 2 }

mscLpDS1TestCauseOfTermination OBJECT-TYPE
   SYNTAX     INTEGER  {
                 testTimeExpired(0),
                 stoppedByOperator(1),
                 unknown(2),
                 neverStarted(3),
                 testRunning(4),
                 hardwareReconfigured(5),
                 loopCodeSyncFailed(6),
                 patternSyncFailed(7),
                 patternSyncLost(8) }
   ACCESS     read-only
   STATUS     mandatory
   DESCRIPTION
     "This attribute indicates either the status of the test or the cause of 
      the test's termination:
      
      neverStarted indicates that the test has not yet been started.
      
      testRunning indicates that the test has been started.
      
      stoppedByOperator indicates that the operator issued a stop 
      command on a test that was running.
      
      testTimeExpired indicates that the test ran for the time specified by 
      the test's duration.
      
      loopCodeSyncFailed indicates that the local end failed to 
      synchronize to the loopCode pattern. The local end transmits the 
      loopCode pattern to cause the remote end to apply a loopback, after 
      which the local end should receive the loopCode pattern. The exact 
      pattern used to request loopCode depends on the test type. This 
      failure indicates a high rate of transmission errors, or that the 
      remote end has failed to apply the loopback.
      
      patternSyncFailed indicates that the local end failed to synchronize 
      to the frmPatternType test pattern, that should have been looped 
      back at the remote end. This failure indicates a high rate of 
      transmission errors or the absence of a loopback.
      
      patternSyncLost indicates that the local end gained and then lost 
      synchronization to the returned frmPatternType test pattern. This 
      failure indicates a sudden increase in transmission errors, frame 
      slippage, or the removal of an existing loopback.
      
      unknown is set when a reason to terminate other than those listed 
      here is encountered.
      
      Note: Only MSA cards support recognition of the failures 
      loopCodeSyncFailed, patternSyncFailed and patternSyncLost. 
      Other cards will not terminate the test under the conditions 
      described by these values."
   DEFVAL     { neverStarted }
::= { mscLpDS1TestResultsEntry 3 }

mscLpDS1TestBitsTx OBJECT-TYPE
   SYNTAX     PassportCounter64 
   ACCESS     read-only
   STATUS     mandatory
   DESCRIPTION
     "This attribute is the total number of bits sent during the test period. 
      As long as the line speed of the hardware interface is less than 
      70 Mbit/s, this counter is not expected to reach the maximum value."
::= { mscLpDS1TestResultsEntry 4 }

mscLpDS1TestBytesTx OBJECT-TYPE
   SYNTAX     PassportCounter64 
   ACCESS     read-only
   STATUS     mandatory
   DESCRIPTION
     "This attribute is the total number of bytes sent during the test 
      period. This counter is not expected to reach its maximum value."
::= { mscLpDS1TestResultsEntry 5 }

mscLpDS1TestFrmTx OBJECT-TYPE
   SYNTAX     PassportCounter64 
   ACCESS     read-only
   STATUS     mandatory
   DESCRIPTION
     "This attribute is the total number of frames sent during the test 
      period. This counter is not expected to reach its maximum value."
::= { mscLpDS1TestResultsEntry 6 }

mscLpDS1TestBitsRx OBJECT-TYPE
   SYNTAX     PassportCounter64 
   ACCESS     read-only
   STATUS     mandatory
   DESCRIPTION
     "This attribute is the total number of bits received during the test 
      period. This counter is not expected to reach its maximum value. 
      The counter will wrap around to 0 if it does reach the maximum 
      value."
::= { mscLpDS1TestResultsEntry 7 }

mscLpDS1TestBytesRx OBJECT-TYPE
   SYNTAX     PassportCounter64 
   ACCESS     read-only
   STATUS     mandatory
   DESCRIPTION
     "This attribute is the total number of bytes received during the test 
      period. This counter is not expected to reach its maximum value. 
      The counter will wrap around to 0 if it does reach its maximum 
      value."
::= { mscLpDS1TestResultsEntry 8 }

mscLpDS1TestFrmRx OBJECT-TYPE
   SYNTAX     PassportCounter64 
   ACCESS     read-only
   STATUS     mandatory
   DESCRIPTION
     "This attribute is the total number of frames received during the test 
      period. This counter is not expected to reach its maximum value. 
      The counter will wrap around to 0 if it does reach its maximum 
      value."
::= { mscLpDS1TestResultsEntry 9 }

mscLpDS1TestErroredFrmRx OBJECT-TYPE
   SYNTAX     PassportCounter64 
   ACCESS     read-only
   STATUS     mandatory
   DESCRIPTION
     "This attribute is not displayed for ATM cards because the physical 
      layer drops all errored frames at the controller interface. 
      
      For all other card types, this attribute is the total number of errored 
      frames received during the test period. This counter is not expected 
      to reach its maximum value. The counter will wrap around to 0 if it 
      does reach its maximum value."
::= { mscLpDS1TestResultsEntry 10 }

mscLpDS1TestBitErrorRate OBJECT-TYPE
   SYNTAX     AsciiString (SIZE (5))
   ACCESS     read-only
   STATUS     mandatory
   DESCRIPTION
     "This attribute is not displayed for ATM cards because the physical 
      layer drops all errored frames at the controller interface. 
      
      For all other card types, this attribute is the calculated bit error rate 
      on the link. Test data are generated and sent in frames of a preset 
      size (frameSize). The Test component will try to estimate the 
      number of bit errors in any errored frame which is identifiable. The 
      statistics will be updated accordingly. A lost frame (may be due to 
      an error on the flag sequence) will be discarded for the bit error rate 
      calculation. The result is presented in the form of xEsyy, where x is 
      the mantissa, syy is the exponent, for example 0E+00, 2E-09.
      Note that the bitErrorRate is an estimate only. For more reliable test 
      results, the test should be done over a long period. Multiple tests 
      would also improve the confidence level of the test results."
::= { mscLpDS1TestResultsEntry 11 }


-- LogicalProcessor/n Ds1/0 Dsp
-- The Dsp component presents the status of the Digital Signal 
-- Processors (DSPs) present on a voice card.
-- A voice card's Dsp component is created automatically whenever 
-- the parent DS1 component becomes active, and remains in 
-- existence as long as the card remains operational. Dsp components 
-- cannot be added or deleted.

mscLpDS1Dsp OBJECT IDENTIFIER ::= { mscLpDS1 4 }



mscLpDS1DspRowStatusTable OBJECT-TYPE
   SYNTAX     SEQUENCE OF MscLpDS1DspRowStatusEntry
   ACCESS     not-accessible
   STATUS     mandatory
   DESCRIPTION
     "This entry controls the addition and deletion of 
      mscLpDS1Dsp components."
::= { mscLpDS1Dsp 1 }

mscLpDS1DspRowStatusEntry OBJECT-TYPE
   SYNTAX     MscLpDS1DspRowStatusEntry
   ACCESS     not-accessible
   STATUS     mandatory
   DESCRIPTION
     "A single entry in the table represents a single 
      mscLpDS1Dsp component."
   INDEX {
      mscLpIndex,
      mscLpDS1Index,
      mscLpDS1DspIndex }
::= { mscLpDS1DspRowStatusTable 1 }

MscLpDS1DspRowStatusEntry ::= SEQUENCE {
   mscLpDS1DspRowStatus
      RowStatus,
   mscLpDS1DspComponentName
      DisplayString,
   mscLpDS1DspStorageType
      StorageType,
   mscLpDS1DspIndex
      NonReplicated }

mscLpDS1DspRowStatus OBJECT-TYPE
   SYNTAX     RowStatus 
   ACCESS     read-only
   STATUS     mandatory
   DESCRIPTION
     "This variable is used as the basis for SNMP naming of
      mscLpDS1Dsp components.
      These components cannot be added nor deleted."
::= { mscLpDS1DspRowStatusEntry 1 }

mscLpDS1DspComponentName OBJECT-TYPE
   SYNTAX     DisplayString 
   ACCESS     read-only
   STATUS     mandatory
   DESCRIPTION
     "This variable provides the component's string name for
      use with the ASCII Console Interface"
::= { mscLpDS1DspRowStatusEntry 2 }

mscLpDS1DspStorageType OBJECT-TYPE
   SYNTAX     StorageType 
   ACCESS     read-only
   STATUS     mandatory
   DESCRIPTION
     "This variable represents the storage type value for the
      mscLpDS1Dsp tables."
::= { mscLpDS1DspRowStatusEntry 4 }

mscLpDS1DspIndex OBJECT-TYPE
   SYNTAX     NonReplicated 
   ACCESS     not-accessible
   STATUS     mandatory
   DESCRIPTION
     "This variable represents the index for the mscLpDS1Dsp tables."
::= { mscLpDS1DspRowStatusEntry 10 }


-- LogicalProcessor/n Ds1/0 Audio
-- The Audio component presents the audio status of all timeslots on a 
-- given DS1.
-- A voice card's Audio component is created automatically whenever 
-- the parent DS1 component becomes active, and remains in 
-- existence as long as the card remains operational. Audio 
-- components cannot be added or deleted.

mscLpDS1Audio OBJECT IDENTIFIER ::= { mscLpDS1 5 }



mscLpDS1AudioRowStatusTable OBJECT-TYPE
   SYNTAX     SEQUENCE OF MscLpDS1AudioRowStatusEntry
   ACCESS     not-accessible
   STATUS     mandatory
   DESCRIPTION
     "This entry controls the addition and deletion of 
      mscLpDS1Audio components."
::= { mscLpDS1Audio 1 }

mscLpDS1AudioRowStatusEntry OBJECT-TYPE
   SYNTAX     MscLpDS1AudioRowStatusEntry
   ACCESS     not-accessible
   STATUS     mandatory
   DESCRIPTION
     "A single entry in the table represents a single 
      mscLpDS1Audio component."
   INDEX {
      mscLpIndex,
      mscLpDS1Index,
      mscLpDS1AudioIndex }
::= { mscLpDS1AudioRowStatusTable 1 }

MscLpDS1AudioRowStatusEntry ::= SEQUENCE {
   mscLpDS1AudioRowStatus
      RowStatus,
   mscLpDS1AudioComponentName
      DisplayString,
   mscLpDS1AudioStorageType
      StorageType,
   mscLpDS1AudioIndex
      NonReplicated }

mscLpDS1AudioRowStatus OBJECT-TYPE
   SYNTAX     RowStatus 
   ACCESS     read-only
   STATUS     mandatory
   DESCRIPTION
     "This variable is used as the basis for SNMP naming of
      mscLpDS1Audio components.
      These components cannot be added nor deleted."
::= { mscLpDS1AudioRowStatusEntry 1 }

mscLpDS1AudioComponentName OBJECT-TYPE
   SYNTAX     DisplayString 
   ACCESS     read-only
   STATUS     mandatory
   DESCRIPTION
     "This variable provides the component's string name for
      use with the ASCII Console Interface"
::= { mscLpDS1AudioRowStatusEntry 2 }

mscLpDS1AudioStorageType OBJECT-TYPE
   SYNTAX     StorageType 
   ACCESS     read-only
   STATUS     mandatory
   DESCRIPTION
     "This variable represents the storage type value for the
      mscLpDS1Audio tables."
::= { mscLpDS1AudioRowStatusEntry 4 }

mscLpDS1AudioIndex OBJECT-TYPE
   SYNTAX     NonReplicated 
   ACCESS     not-accessible
   STATUS     mandatory
   DESCRIPTION
     "This variable represents the index for the mscLpDS1Audio tables."
::= { mscLpDS1AudioRowStatusEntry 10 }


-- Lp/n E1/n
-- The E1 component controls and monitors an E1 port on a Function 
-- Processor. The number of ports supported depends on the type of 
-- card, and is usually encoded in the Shelf Card/n cardType, for 
-- example 4pE1Aal1: 4 port. The lowest instance value is always 0. 
-- Multi-Service cards have an instance range 0..31, except that 
-- instance values 30 and 31 are not available for an "ATM UNI port". 
-- (An E1 "ATM UNI port" is an E1 component with a single Chan 
-- whose applicationFramerName attribute is linked to an AtmIf 
-- component.)
-- The instance number of a E1 "ATM UNI port" must not be the same 
-- as the instance number of an IMA group under the same Lp.

mscLpE1 OBJECT IDENTIFIER ::= { mscLp 8 }



mscLpE1RowStatusTable OBJECT-TYPE
   SYNTAX     SEQUENCE OF MscLpE1RowStatusEntry
   ACCESS     not-accessible
   STATUS     mandatory
   DESCRIPTION
     "This entry controls the addition and deletion of 
      mscLpE1 components."
::= { mscLpE1 1 }

mscLpE1RowStatusEntry OBJECT-TYPE
   SYNTAX     MscLpE1RowStatusEntry
   ACCESS     not-accessible
   STATUS     mandatory
   DESCRIPTION
     "A single entry in the table represents a single 
      mscLpE1 component."
   INDEX {
      mscLpIndex,
      mscLpE1Index }
::= { mscLpE1RowStatusTable 1 }

MscLpE1RowStatusEntry ::= SEQUENCE {
   mscLpE1RowStatus
      RowStatus,
   mscLpE1ComponentName
      DisplayString,
   mscLpE1StorageType
      StorageType,
   mscLpE1Index
      Integer32 }

mscLpE1RowStatus OBJECT-TYPE
   SYNTAX     RowStatus 
   ACCESS     read-write
   STATUS     mandatory
   DESCRIPTION
     "This variable is used as the basis for SNMP naming of
      mscLpE1 components.
      These components can be added and deleted."
::= { mscLpE1RowStatusEntry 1 }

mscLpE1ComponentName OBJECT-TYPE
   SYNTAX     DisplayString 
   ACCESS     read-only
   STATUS     mandatory
   DESCRIPTION
     "This variable provides the component's string name for
      use with the ASCII Console Interface"
::= { mscLpE1RowStatusEntry 2 }

mscLpE1StorageType OBJECT-TYPE
   SYNTAX     StorageType 
   ACCESS     read-only
   STATUS     mandatory
   DESCRIPTION
     "This variable represents the storage type value for the
      mscLpE1 tables."
::= { mscLpE1RowStatusEntry 4 }

mscLpE1Index OBJECT-TYPE
   SYNTAX     Integer32 (0..31)
   ACCESS     not-accessible
   STATUS     mandatory
   DESCRIPTION
     "This variable represents the index for the mscLpE1 tables."
::= { mscLpE1RowStatusEntry 10 }

mscLpE1ProvTable OBJECT-TYPE
   SYNTAX     SEQUENCE OF MscLpE1ProvEntry
   ACCESS     not-accessible
   STATUS     mandatory
   DESCRIPTION
     "This group contains all of the provisioning data for an E1 
      component."
::= { mscLpE1 10 }

mscLpE1ProvEntry OBJECT-TYPE
   SYNTAX     MscLpE1ProvEntry
   ACCESS     not-accessible
   STATUS     mandatory
   DESCRIPTION
     "An entry in the mscLpE1ProvTable."
   INDEX {
      mscLpIndex,
      mscLpE1Index }
::= { mscLpE1ProvTable 1 }

MscLpE1ProvEntry ::= SEQUENCE {
   mscLpE1LineType
      INTEGER,
   mscLpE1ClockingSource
      INTEGER,
   mscLpE1Crc4Mode
      INTEGER,
   mscLpE1SendRaiOnAis
      INTEGER,
   mscLpE1RaiDeclareAlarmTime
      Unsigned32,
   mscLpE1RaiClearAlarmTime
      Unsigned32 }

mscLpE1LineType OBJECT-TYPE
   SYNTAX     INTEGER  {
                 ccs(2),
                 cas(3),
                 unframed(6) }
   ACCESS     read-write
   STATUS     mandatory
   DESCRIPTION
     "This attribute specifies the framing of the E1 line.
      When cas (channel associated signalling) is selected, timeslot 16 is 
      reserved for multiframe signalling and only 30 timeslots are 
      available for data. The signalling bits are not interpreted.
      When ccs (common channel signalling) is selected, timeslot 16 is 
      not reserved for multiframe signalling and 31 timeslots are available 
      for data. The signalling bits are not interpreted. 
      When unframed is selected, a clear channel is defined whereby data 
      from all timeslots including the framing data (in timeslot 0) and 
      timeslot 16 are passed transparently. This value is valid only for 
      AAL1 cards.
      
      For cell-based cards the ATM Forum specifies that timeslot 16 be 
      reserved, leaving 30 timeslots available for data.
      
      The default value is cas except for the 8pE1Atm card, for which the 
      default and only valid value is ccs."
::= { mscLpE1ProvEntry 1 }

mscLpE1ClockingSource OBJECT-TYPE
   SYNTAX     INTEGER  {
                 local(0),
                 line(1),
                 module(2),
                 otherPort(3),
                 srtsMode(4),
                 adaptiveMode(5) }
   ACCESS     read-write
   STATUS     mandatory
   DESCRIPTION
     "This attribute defines the source of the transmit clock for the E1 
      line.
      
      When local is selected, the crystal on the port generates the 
      clocking for the line.
      
      When line is selected, the port synchronizes to the clock from the 
      facility.
      
      When module is selected, the ports clock synchronizes to the clock 
      provided by the oscillator on the active CP.
      
      When otherPort is selected, the port synchronizes to the port with a 
      clocking source of line.
      
      When srtsMode is selected, the port transmit frequency depends on 
      the SRTS (Synchronous Residual Time-Stamp) received over the 
      ATM network. SRTS information is also generated sent over the 
      ATM network.
      
      When adaptiveMode is selected, the port transmit frequency 
      continually adapts to match the egress data received from the ATM 
      network.
      
      A port with srtsMode or adaptiveMode must have a single Chan 
      which may be linked only to an Aal1Ces.service with serviceType 
      unstructured 
      
      If the NetworkSynchronization component is present, the default 
      value of this attribute is module, otherwise it defaults to line, except 
      for the 3pE1Atm card, which it defaults to local.
      On a 3pE1Atm card all ports must have the same value, and be 
      either local or module.
      
      otherPort is valid only on AAL1 cards. srtsMode is valid only on 
      AAL1 and Multi-Service Access cards. adaptiveMode is valid only 
      on Multi-Service Access cards.
      
      On 4E1Aal1 cards either:
      
      all four ports' clockingSource values must be local OR
      all four ports' clockingSource values must be module OR
      one port's clockingSource value must be line and the other three 
      must be otherPort. A port can only have srtsMode selected if the 
      other ports are module or srtsMode."
::= { mscLpE1ProvEntry 2 }

mscLpE1Crc4Mode OBJECT-TYPE
   SYNTAX     INTEGER  {
                 on(0),
                 off(1) }
   ACCESS     read-write
   STATUS     mandatory
   DESCRIPTION
     "This attribute defines whether the CRC-4 checking and generation 
      on the E1 line is enabled or disabled.
      
      The default CRC-4 mode is off except for the cell-based cards 
      which default to on as per the ATM Forum."
::= { mscLpE1ProvEntry 3 }

mscLpE1SendRaiOnAis OBJECT-TYPE
   SYNTAX     INTEGER  {
                 no(0),
                 yes(1) }
   ACCESS     read-write
   STATUS     mandatory
   DESCRIPTION
     "This attribute defines whether the Remote Alarm Indicator (RAI) 
      will be sent when receiving an AIS alarm. The value is yes by 
      default; it can be changed to no only for ports on J2MV cards."
   DEFVAL     { yes }
::= { mscLpE1ProvEntry 4 }

mscLpE1RaiDeclareAlarmTime OBJECT-TYPE
   SYNTAX     Unsigned32 (0 | 1..20000)
   ACCESS     read-write
   STATUS     mandatory
   DESCRIPTION
     "This attribute specifies the period of time that a Remote Alarm 
      Indicator (RAI) must be present before declaring an RAI alarm. The 
      value of auto sets the RAI declare time to the default value for E1 
      and E1C card types which do not have hardware support for RAI 
      response. On E1C card types with hardware support, if the value of 
      auto is set, RAI response is done according to the standards. If auto 
      is set, the value of the raiClearAlarmTime attribute is ignored and 
      auto is used. This attribute is for E1 and E1C card types only. For 
      all other card types, the default value must be used.

      VALUES (

      0 = auto

      )"
   DEFVAL     { 100 }
::= { mscLpE1ProvEntry 5 }

mscLpE1RaiClearAlarmTime OBJECT-TYPE
   SYNTAX     Unsigned32 (0 | 1..20000)
   ACCESS     read-write
   STATUS     mandatory
   DESCRIPTION
     "This attribute specifies the period of time that a Remote Alarm 
      Indicator (RAI) has been absent before clearing an RAI alarm. The 
      value of auto sets the RAI clear time to the default value for E1 and 
      E1C card types which do not have hardware support for RAI 
      response. On E1C card types with hardware support, if the value of 
      auto is set, RAI response is done according to the standards. If auto 
      is set, the value of the raiDeclareAlarmTime attribute is ignored and 
      auto is used. This attribute is for E1 and E1C card types only. For 
      all other card types, the default value must be used.

      VALUES (

      0 = auto

      )"
   DEFVAL     { 100 }
::= { mscLpE1ProvEntry 6 }

mscLpE1CidDataTable OBJECT-TYPE
   SYNTAX     SEQUENCE OF MscLpE1CidDataEntry
   ACCESS     not-accessible
   STATUS     mandatory
   DESCRIPTION
     "This group contains the attribute for a component's Customer 
      Identifier (CID). Refer to the attribute description for a detailed 
      explanation of CIDs."
::= { mscLpE1 11 }

mscLpE1CidDataEntry OBJECT-TYPE
   SYNTAX     MscLpE1CidDataEntry
   ACCESS     not-accessible
   STATUS     mandatory
   DESCRIPTION
     "An entry in the mscLpE1CidDataTable."
   INDEX {
      mscLpIndex,
      mscLpE1Index }
::= { mscLpE1CidDataTable 1 }

MscLpE1CidDataEntry ::= SEQUENCE {
   mscLpE1CustomerIdentifier
      Unsigned32 }

mscLpE1CustomerIdentifier OBJECT-TYPE
   SYNTAX     Unsigned32 (0 | 1..8191)
   ACCESS     read-write
   STATUS     mandatory
   DESCRIPTION
     "This attribute holds the Customer Identifier (CID).
      
      Every component has a CID. If a component has a cid attribute, the 
      component's CID is the provisioned value of that attribute; 
      otherwise the component inherits the CID of its parent. The top-
      level component has a CID of 0.
      
      Every operator session also has a CID, which is the CID 
      provisioned for the operator's user ID. An operator will see only the 
      stream data for components having a matching CID. Also, the 
      operator will be allowed to issue commands for only those 
      components which have a matching CID.
      
      An operator CID of 0 is used to identify the Network Manager 
      (referred to as 'NetMan' in DPN). This CID matches the CID of 
      any component. Values 1 to 8191 inclusive (equivalent to 'basic 
      CIDs' in DPN) may be assigned to specific customers."
   DEFVAL     { 0 }
::= { mscLpE1CidDataEntry 1 }

mscLpE1AdminInfoTable OBJECT-TYPE
   SYNTAX     SEQUENCE OF MscLpE1AdminInfoEntry
   ACCESS     not-accessible
   STATUS     mandatory
   DESCRIPTION
     "This group contains the attributes pertaining to the vendor of the 
      equipment."
::= { mscLpE1 12 }

mscLpE1AdminInfoEntry OBJECT-TYPE
   SYNTAX     MscLpE1AdminInfoEntry
   ACCESS     not-accessible
   STATUS     mandatory
   DESCRIPTION
     "An entry in the mscLpE1AdminInfoTable."
   INDEX {
      mscLpIndex,
      mscLpE1Index }
::= { mscLpE1AdminInfoTable 1 }

MscLpE1AdminInfoEntry ::= SEQUENCE {
   mscLpE1Vendor
      AsciiString,
   mscLpE1CommentText
      AsciiString }

mscLpE1Vendor OBJECT-TYPE
   SYNTAX     AsciiString (SIZE (0..20))
   ACCESS     read-write
   STATUS     mandatory
   DESCRIPTION
     "This is the name of the vendor supplying the facility."
::= { mscLpE1AdminInfoEntry 1 }

mscLpE1CommentText OBJECT-TYPE
   SYNTAX     AsciiString (SIZE (0..60))
   ACCESS     read-write
   STATUS     mandatory
   DESCRIPTION
     "Any miscellaneous text about the facility."
::= { mscLpE1AdminInfoEntry 2 }

mscLpE1IfEntryTable OBJECT-TYPE
   SYNTAX     SEQUENCE OF MscLpE1IfEntryEntry
   ACCESS     not-accessible
   STATUS     mandatory
   DESCRIPTION
     "This group contains the provisionable attributes for the ifEntry."
::= { mscLpE1 13 }

mscLpE1IfEntryEntry OBJECT-TYPE
   SYNTAX     MscLpE1IfEntryEntry
   ACCESS     not-accessible
   STATUS     mandatory
   DESCRIPTION
     "An entry in the mscLpE1IfEntryTable."
   INDEX {
      mscLpIndex,
      mscLpE1Index }
::= { mscLpE1IfEntryTable 1 }

MscLpE1IfEntryEntry ::= SEQUENCE {
   mscLpE1IfAdminStatus
      INTEGER,
   mscLpE1IfIndex
      InterfaceIndex }

mscLpE1IfAdminStatus OBJECT-TYPE
   SYNTAX     INTEGER  {
                 up(1),
                 down(2),
                 testing(3) }
   ACCESS     read-write
   STATUS     mandatory
   DESCRIPTION
     "The desired state of the interface. The up state indicates the 
      interface is operational. The down state indicates the interface is not 
      operational. The testing state indicates that no operational packets 
      can be passed."
   DEFVAL     { up }
::= { mscLpE1IfEntryEntry 1 }

mscLpE1IfIndex OBJECT-TYPE
   SYNTAX     InterfaceIndex (1..65535)
   ACCESS     read-only
   STATUS     mandatory
   DESCRIPTION
     "This is the index for the IfEntry. Its value is automatically initialized 
      during the provisioning process."
::= { mscLpE1IfEntryEntry 2 }

mscLpE1OperStatusTable OBJECT-TYPE
   SYNTAX     SEQUENCE OF MscLpE1OperStatusEntry
   ACCESS     not-accessible
   STATUS     mandatory
   DESCRIPTION
     "This group includes the Operational Status attribute. This attribute 
      defines the current operational state of this component."
::= { mscLpE1 14 }

mscLpE1OperStatusEntry OBJECT-TYPE
   SYNTAX     MscLpE1OperStatusEntry
   ACCESS     not-accessible
   STATUS     mandatory
   DESCRIPTION
     "An entry in the mscLpE1OperStatusTable."
   INDEX {
      mscLpIndex,
      mscLpE1Index }
::= { mscLpE1OperStatusTable 1 }

MscLpE1OperStatusEntry ::= SEQUENCE {
   mscLpE1SnmpOperStatus
      INTEGER }

mscLpE1SnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { mscLpE1OperStatusEntry 1 }

mscLpE1StateTable OBJECT-TYPE
   SYNTAX     SEQUENCE OF MscLpE1StateEntry
   ACCESS     not-accessible
   STATUS     mandatory
   DESCRIPTION
     "This group contains the three OSI State attributes and the six OSI 
      Status attributes. The descriptions generically indicate what each 
      attribute implies about the component. Note that not all the values 
      and state combinations described here are supported by every 
      component which uses this group. For component-specific 
      information and the valid state combinations, refer to NTP 241-
      7001-150, Passport Operations and Maintenance Guide."
::= { mscLpE1 15 }

mscLpE1StateEntry OBJECT-TYPE
   SYNTAX     MscLpE1StateEntry
   ACCESS     not-accessible
   STATUS     mandatory
   DESCRIPTION
     "An entry in the mscLpE1StateTable."
   INDEX {
      mscLpIndex,
      mscLpE1Index }
::= { mscLpE1StateTable 1 }

MscLpE1StateEntry ::= SEQUENCE {
   mscLpE1AdminState
      INTEGER,
   mscLpE1OperationalState
      INTEGER,
   mscLpE1UsageState
      INTEGER,
   mscLpE1AvailabilityStatus
      OCTET STRING,
   mscLpE1ProceduralStatus
      OCTET STRING,
   mscLpE1ControlStatus
      OCTET STRING,
   mscLpE1AlarmStatus
      OCTET STRING,
   mscLpE1StandbyStatus
      INTEGER,
   mscLpE1UnknownStatus
      INTEGER }

mscLpE1AdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component.
      
      The OSI Status attributes, if supported by the component, may 
      provide more details, qualifying the state of the component."
   DEFVAL     { unlocked }
::= { mscLpE1StateEntry 1 }

mscLpE1OperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle.
      
      The OSI Status attributes, if supported by the component, may 
      provide more details, qualifying the state of the component."
   DEFVAL     { disabled }
::= { mscLpE1StateEntry 2 }

mscLpE1UsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time.
      
      The OSI Status attributes, if supported by the component, may 
      provide more details, qualifying the state of the component."
   DEFVAL     { idle }
::= { mscLpE1StateEntry 3 }

mscLpE1AvailabilityStatus OBJECT-TYPE
   SYNTAX     OCTET STRING (SIZE (2))
   ACCESS     read-only
   STATUS     mandatory
   DESCRIPTION
     "If supported by the component, this attribute indicates the OSI 
      Availability status of the component. Note that, even though it is 
      defined as a multi-valued set, at most one value is shown to the user.
      
      When no values are in the set, this indicates that either the attribute 
      is not supported or that none of the status conditions described 
      below are present.
      
      The value inTest indicates that the resource is undergoing a test 
      procedure. If adminState is locked or shuttingDown, the normal 
      users are precluded from using the resource and controlStatus is 
      reservedForTest. Tests that do not exclude additional users can be 
      present in any operational or administrative state but the 
      reservedForTest condition should not be present.
      
      The value failed indicates that the component has an internal fault 
      that prevents it from operating. The operationalState is disabled.
      
      The value dependency indicates that the component cannot operate 
      because some other resource on which it depends is unavailable. 
      The operationalState is disabled.
      
      The value powerOff indicates the resource requires power to be 
      applied and it is not powered on. The operationalState is disabled.
      
      The value offLine indicates the resource requires a routine 
      operation (either manual, automatic, or both) to be performed to 
      place it on-line and make it available for use. The operationalState 
      is disabled.
      
      The value offDuty indicates the resource is inactive in accordance 
      with a predetermined time schedule. In the absence of other 
      disabling conditions, the operationalState is enabled or disabled.
      
      The value degraded indicates the service provided by the 
      component is degraded in some way, such as in speed or operating 
      capacity. However, the resource remains available for service. The 
      operationalState is enabled.
      
      The value notInstalled indicates the resource is not present. The 
      operationalState is disabled.
      
      The value logFull is not used.

      Description of bits:
      inTest(0)
      failed(1)
      powerOff(2)
      offLine(3)
      offDuty(4)
      dependency(5)
      degraded(6)
      notInstalled(7)
      logFull(8)"
::= { mscLpE1StateEntry 4 }

mscLpE1ProceduralStatus OBJECT-TYPE
   SYNTAX     OCTET STRING (SIZE (1))
   ACCESS     read-only
   STATUS     mandatory
   DESCRIPTION
     "If supported by the component, this attribute indicates the OSI 
      Procedural status of the component. Note that, even though it is 
      defined as a multi-valued set, at most one value is shown to the user.
      
      When no values are in the set, this indicates that either the attribute 
      is not supported or that none of the status conditions described 
      below are present.
      
      The value initializationRequired indicates (for a resource which 
      doesn't initialize autonomously) that initialization is required before 
      it can perform its normal functions, and this procedure has not been 
      initiated. The operationalState is disabled.
      
      The value notInitialized indicates (for a resource which does 
      initialize autonomously) that initialization is required before it can 
      perform its normal functions, and this procedure has not been 
      initiated. The operationalState may be enabled or disabled.
      
      The value initializing indicates that initialization has been initiated 
      but is not yet complete. The operationalState may be enabled or 
      disabled.
      
      The value reporting indicates the resource has completed some 
      processing operation and is notifying the results. The 
      operationalState is enabled.
      
      The value terminating indicates the component is in a termination 
      phase. If the resource doesn't reinitialize autonomously, 
      operationalState is disabled; otherwise it is enabled or disabled.

      Description of bits:
      initializationRequired(0)
      notInitialized(1)
      initializing(2)
      reporting(3)
      terminating(4)"
::= { mscLpE1StateEntry 5 }

mscLpE1ControlStatus OBJECT-TYPE
   SYNTAX     OCTET STRING (SIZE (1))
   ACCESS     read-only
   STATUS     mandatory
   DESCRIPTION
     "If supported by the component, this attribute indicates the OSI 
      Control status of the component. Note that, even though it is defined 
      as a multi-valued set, at most one value is shown to the user.
      
      When no values are in the set, this indicates that either the attribute 
      is not supported or that none of the status conditions described 
      below are present.
      
      The value subjectToTest indicates the resource is available but tests 
      may be conducted simultaneously at unpredictable times, which 
      may cause it to exhibit unusual characteristics.
      
      The value partOfServicesLocked indicates that part of the service is 
      restricted from users of a resource. The adminState is unlocked.
      
      The value reservedForTest indicates that the component is 
      administratively unavailable because it is undergoing a test 
      procedure. The adminState is locked.
      
      The value suspended indicates that the service has been 
      administratively suspended.

      Description of bits:
      subjectToTest(0)
      partOfServicesLocked(1)
      reservedForTest(2)
      suspended(3)"
::= { mscLpE1StateEntry 6 }

mscLpE1AlarmStatus OBJECT-TYPE
   SYNTAX     OCTET STRING (SIZE (1))
   ACCESS     read-only
   STATUS     mandatory
   DESCRIPTION
     "If supported by the component, this attribute indicates the OSI 
      Alarm status of the component. Note that, even though it is defined 
      as a multi-valued set, at most one value is shown to the user.
      
      When no values are in the set, this indicates that either the attribute 
      is not supported or that none of the status conditions described 
      below are present.
      
      The value underRepair indicates the component is currently being 
      repaired. The operationalState is enabled or disabled.
      
      The value critical indicates one or more critical alarms are 
      outstanding against the component. Other, less severe, alarms may 
      also be outstanding. The operationalState is enabled or disabled.
      
      The value major indicates one or more major alarms are 
      outstanding against the component. Other, less severe, alarms may 
      also be outstanding. The operationalState is enabled or disabled.
      
      The value minor indicates one or more minor alarms are 
      outstanding against the component. Other, less severe, alarms may 
      also be outstanding. The operationalState is enabled or disabled.
      
      The value alarmOutstanding generically indicates that an alarm of 
      some severity is outstanding against the component.

      Description of bits:
      underRepair(0)
      critical(1)
      major(2)
      minor(3)
      alarmOutstanding(4)"
::= { mscLpE1StateEntry 7 }

mscLpE1StandbyStatus OBJECT-TYPE
   SYNTAX     INTEGER  {
                 hotStandby(0),
                 coldStandby(1),
                 providingService(2),
                 notSet(15) }
   ACCESS     read-only
   STATUS     mandatory
   DESCRIPTION
     "If supported by the component, this attribute indicates the OSI 
      Standby status of the component.
      
      The value notSet indicates that either the attribute is not supported 
      or that none of the status conditions described below are present. 
      Note that this is a non-standard value, used because the original 
      specification indicated this attribute was set-valued and thus, did not 
      provide a value to indicate that none of the other three are 
      applicable.
      
      The value hotStandby indicates that the resource is not providing 
      service but will be immediately able to take over the role of the 
      resource to be backed up, without initialization activity, and 
      containing the same information as the resource to be backed up.
      
      The value coldStandby indicates the resource is a backup for 
      another resource but will not be immediately able to take over the 
      role of the backed up resource and will require some initialization 
      activity.
      
      The value providingService indicates that this component, as a 
      backup resource, is currently backing up another resource."
   DEFVAL     { notSet }
::= { mscLpE1StateEntry 8 }

mscLpE1UnknownStatus OBJECT-TYPE
   SYNTAX     INTEGER  {
                 false(0),
                 true(1) }
   ACCESS     read-only
   STATUS     mandatory
   DESCRIPTION
     "This attribute indicates the OSI Unknown status of the component.
      
      The value false indicates that all of the other OSI State and Status 
      attribute values can be considered accurate.
      
      The value true indicates that the actual state of the component is not 
      known for sure."
   DEFVAL     { false }
::= { mscLpE1StateEntry 9 }

mscLpE1OperTable OBJECT-TYPE
   SYNTAX     SEQUENCE OF MscLpE1OperEntry
   ACCESS     not-accessible
   STATUS     mandatory
   DESCRIPTION
     "This group contains the common operational data for a component 
      in a digital hierarchy interface."
::= { mscLpE1 16 }

mscLpE1OperEntry OBJECT-TYPE
   SYNTAX     MscLpE1OperEntry
   ACCESS     not-accessible
   STATUS     mandatory
   DESCRIPTION
     "An entry in the mscLpE1OperTable."
   INDEX {
      mscLpIndex,
      mscLpE1Index }
::= { mscLpE1OperTable 1 }

MscLpE1OperEntry ::= SEQUENCE {
   mscLpE1LosAlarm
      INTEGER,
   mscLpE1RxAisAlarm
      INTEGER,
   mscLpE1LofAlarm
      INTEGER,
   mscLpE1RxRaiAlarm
      INTEGER,
   mscLpE1TxAisAlarm
      INTEGER,
   mscLpE1TxRaiAlarm
      INTEGER }

mscLpE1LosAlarm OBJECT-TYPE
   SYNTAX     INTEGER  {
                 on(0),
                 off(1) }
   ACCESS     read-only
   STATUS     mandatory
   DESCRIPTION
     "This attribute displays whether a LOS (Loss of Signal) alarm state 
      has been entered. A LOS alarm is declared after LOS defects have 
      been observed and accumulated for a period of 2 seconds +/- 0.5 
      seconds (for 3pDS1Atm, 3pE1Atm, 8pDS1Atm, and 8pE1Atm 
      cards: 2.5 seconds +/- 0.5 seconds).  A LOS defect is detected upon 
      observing all zeros for 150 ms (for 3pDS1Atm, 3pE1Atm, 
      8pDS1Atm, and 8pE1Atm cards: upon observing 175 +/- 75 pulse 
      positions with no pulses of either positive or negative polarity). If 
      the LOS defects are intermittently occurring, the LOS defect 
      accumulator is decremented at a rate of 1/10 of the incrementing 
      rate (alarm integration ratio of 1/10), with all measurements based 
      on a 200 ms polling cycle.
      The port goes into an operational state of disabled until the LOS 
      alarm state is cleared. Also, an RAI alarm is transmitted to the far 
      end for the duration of the LOS alarm state.
      The LOS alarm state is cleared when LOS defects are absent for 10 
      seconds +/- 0.5 seconds."
   DEFVAL     { off }
::= { mscLpE1OperEntry 1 }

mscLpE1RxAisAlarm OBJECT-TYPE
   SYNTAX     INTEGER  {
                 on(0),
                 off(1) }
   ACCESS     read-only
   STATUS     mandatory
   DESCRIPTION
     "This attribute displays whether an AIS (Alarm Indication Signal) 
      alarm state has been entered. The AIS Alarm state is entered when 
      AIS defects have been observed and accumulated for 2.5 seconds +/
      - 0.5 seconds. An AIS defect is detected after having received less 
      than 3 zeros in a 2048 bit period (for 8pDS1Atm cards: when both 
      an Out Of Frame condition exists and a 1's density of at least 99.9% 
      is present for a time T, where 3 ms  T  75 ms; for 8pE1Atm 
      cards: when both an Out Of Frame condition exists and fewer than 
      three 0's have been received in 512 bit periods). If the AIS defects 
      are intermittently occurring, the AIS defect accumulator is 
      decremented at a rate of 1/10 of the incrementing rate (alarm 
      integration ratio of 1/10), with all measurements based on a 200 ms 
      polling cycle.
      The port goes into an operational state of disabled for the duration 
      of an AIS alarm state.
      The AIS alarm state is cleared when AIS defects are absent for 10 
      seconds +/- 0.5 seconds."
   DEFVAL     { off }
::= { mscLpE1OperEntry 2 }

mscLpE1LofAlarm OBJECT-TYPE
   SYNTAX     INTEGER  {
                 on(0),
                 off(1) }
   ACCESS     read-only
   STATUS     mandatory
   DESCRIPTION
     "This attribute displays whether a LOF (Loss of Frame) alarm state 
      has been entered. The LOF alarm state is entered when LOF defects 
      (for DS1: 2 out of 5 framing bits in error; for E1: 3 consecutive 
      frame alignment patterns in error) have been detected for 3 seconds 
      +/- 0.5 seconds (for 3pDS1Atm, 3pE1Atm, 8pDS1Atm, and 
      8pE1Atm cards: 2.5 seconds +/- 0.5 seconds). If the LOF defects 
      are intermittently occurring, the LOF defect accumulator is 
      decremented at a rate of 1/10 of the incrementing rate (alarm 
      integration ratio of 1/10), with all measurements based on a 200 ms 
      polling cycle.
      The port goes into an operational state of disabled until the LOF 
      alarm state is cleared. Also, an RAI alarm is transmitted to the far 
      end for the duration of the LOF alarm state 
      The condition is cleared when framing has been achieved for 10 
      seconds +/- 0.5 seconds."
   DEFVAL     { off }
::= { mscLpE1OperEntry 3 }

mscLpE1RxRaiAlarm OBJECT-TYPE
   SYNTAX     INTEGER  {
                 on(0),
                 off(1) }
   ACCESS     read-only
   STATUS     mandatory
   DESCRIPTION
     "This attribute displays whether an RAI (Remote Alarm Indication) 
      alarm state has been entered. An RAI alarm state is entered when 
      the RAI defect indicator has been observed and accumulated for 3.5 
      seconds +/- 0.5 seconds. For 3pDS1Atm, and 8pDS1Atm cards: 
      alarm is declared immediately upon observing the defect is present, 
      with no integration time. For 3pE1Atm, and 8pE1Atm cards: alarm 
      state is entered when the RAI defect indicator has been observed 
      and accumulated for 2.5 seconds +/- 0.5 seconds. If the RAI defects 
      are intermittently occurring, the RAI defect accumulator is 
      decremented at a rate of 1/10 of the incrementing rate (alarm 
      integration ratio of 1/10), with all measurements based on a 200 ms 
      polling cycle. 
      The RAI alarm state is cleared when the RAI defect indicator has 
      been absent for 10 seconds +/- 0.5 seconds (for 3pDS1Atm, and 
      8pDS1Atm cards: alarm is cleared immediately upon observing the 
      defect is absent, with no integration time).
      The RAI alarm is usually an indication that the far end facility is 
      unable to gain synchronization."
   DEFVAL     { off }
::= { mscLpE1OperEntry 4 }

mscLpE1TxAisAlarm OBJECT-TYPE
   SYNTAX     INTEGER  {
                 on(0),
                 off(1) }
   ACCESS     read-only
   STATUS     mandatory
   DESCRIPTION
     "This attribute displays whether an AIS (Alarm Indication Signal) 
      alarm is being transmitted on the line. An AIS alarm is transmitted 
      when the port is in a locked state."
   DEFVAL     { off }
::= { mscLpE1OperEntry 5 }

mscLpE1TxRaiAlarm OBJECT-TYPE
   SYNTAX     INTEGER  {
                 on(0),
                 off(1) }
   ACCESS     read-only
   STATUS     mandatory
   DESCRIPTION
     "This attribute displays whether a RAI signal is being sent on the 
      outgoing line. The RAI signal is transmitted when the port detects a 
      LOF alarm condition (for 3pDS1Atm, 3pE1Atm, 8pDS1Atm, and 
      8pE1Atm cards: RAI is transmitted when the port detects a LOS, 
      LOF, or AIS condition)."
   DEFVAL     { off }
::= { mscLpE1OperEntry 6 }

mscLpE1E1OperTable OBJECT-TYPE
   SYNTAX     SEQUENCE OF MscLpE1E1OperEntry
   ACCESS     not-accessible
   STATUS     mandatory
   DESCRIPTION
     "This group contains all of the operational data for a E1 component 
      that are not defined in the DSCommonOp group."
::= { mscLpE1 17 }

mscLpE1E1OperEntry OBJECT-TYPE
   SYNTAX     MscLpE1E1OperEntry
   ACCESS     not-accessible
   STATUS     mandatory
   DESCRIPTION
     "An entry in the mscLpE1E1OperTable."
   INDEX {
      mscLpIndex,
      mscLpE1Index }
::= { mscLpE1E1OperTable 1 }

MscLpE1E1OperEntry ::= SEQUENCE {
   mscLpE1MultifrmLofAlarm
      INTEGER,
   mscLpE1RxMultifrmRaiAlarm
      INTEGER,
   mscLpE1TxMultifrmRaiAlarm
      INTEGER }

mscLpE1MultifrmLofAlarm OBJECT-TYPE
   SYNTAX     INTEGER  {
                 on(0),
                 off(1) }
   ACCESS     read-only
   STATUS     mandatory
   DESCRIPTION
     "This attribute indicates whether a multiframe LOF (loss of frame) 
      alarm state is entered. A multiframe LOF alarm state is entered 
      when a multiframe LOF defect (2 consecutive errors in the 
      multiframe alignment signal) has been detected and accumulated 
      for 2.5 seconds +/- 0.5 seconds. If the multiframe LOF defects are 
      intermittently occurring, the multiframe LOF defect accumulator is 
      decremented at a rate of 1/10 of the incrementing rate (alarm 
      integration ratio of 1/10), with all measurements based on a 200 ms 
      polling cycle.
      The alarm is cleared when the defect is not detected for 10 seconds 
      +/- 0.5 seconds. When the multiframe LOF alarm is on, a 
      multiframe RAI alarm indicator is transmitted on the line.
      
      The 8pE1Atm card does not support the multiframe LOF alarm."
   DEFVAL     { off }
::= { mscLpE1E1OperEntry 1 }

mscLpE1RxMultifrmRaiAlarm OBJECT-TYPE
   SYNTAX     INTEGER  {
                 on(0),
                 off(1) }
   ACCESS     read-only
   STATUS     mandatory
   DESCRIPTION
     "This attribute displays whether a multiframe RAI (remote alarm 
      indicator) alarm state has been entered. A multiframe RAI alarm 
      state is entered when a multiframe RAI alarm indicator (bit 6 of 
      timeslot 16 in frame 0 is set to a one) is observed and accumulated 
      for 2.5 seconds +/- 0.5 seconds. If the multiframe RAI indicator is 
      intermittently received, the multiframe RAI defect accumulator is 
      decremented at a rate of 1/10 of the incrementing rate (alarm 
      integration ratio of 1/10), with all measurements based on a 200 ms 
      polling cycle.
      The multiframe RAI alarm condition is cleared when the 
      multiframe RAI alarm indication is not received for 10 seconds +/- 
      0.5 seconds. The multiframe RAI alarm is usually an indication that 
      the far end facility is unable to gain multiframe synchronization.
      
      The 8pE1Atm card does not support the multiframe RAI alarm."
   DEFVAL     { off }
::= { mscLpE1E1OperEntry 2 }

mscLpE1TxMultifrmRaiAlarm OBJECT-TYPE
   SYNTAX     INTEGER  {
                 on(0),
                 off(1) }
   ACCESS     read-only
   STATUS     mandatory
   DESCRIPTION
     "This attribute displays whether a multiframe RAI (remote alarm 
      indicator) alarm is being sent on the E1 line. This is transmitted 
      when the E1 port detects a multiframe LOF condition.
      
      The 8pE1Atm card does not generate the multiframe RAI alarm."
   DEFVAL     { off }
::= { mscLpE1E1OperEntry 3 }

mscLpE1StatsTable OBJECT-TYPE
   SYNTAX     SEQUENCE OF MscLpE1StatsEntry
   ACCESS     not-accessible
   STATUS     mandatory
   DESCRIPTION
     "This group contains the common statistical data for a component in 
      a digital hierarchy interface."
::= { mscLpE1 18 }

mscLpE1StatsEntry OBJECT-TYPE
   SYNTAX     MscLpE1StatsEntry
   ACCESS     not-accessible
   STATUS     mandatory
   DESCRIPTION
     "An entry in the mscLpE1StatsTable."
   INDEX {
      mscLpIndex,
      mscLpE1Index }
::= { mscLpE1StatsTable 1 }

MscLpE1StatsEntry ::= SEQUENCE {
   mscLpE1RunningTime
      Counter32,
   mscLpE1ErrorFreeSec
      Counter32,
   mscLpE1ErroredSec
      Counter32,
   mscLpE1SevErroredSec
      Counter32,
   mscLpE1SevErroredFrmSec
      Counter32,
   mscLpE1UnavailSec
      Counter32,
   mscLpE1BpvErrors
      Counter32,
   mscLpE1CrcErrors
      Counter32,
   mscLpE1FrmErrors
      Counter32,
   mscLpE1LosStateChanges
      Counter32,
   mscLpE1SlipErrors
      Counter32 }

mscLpE1RunningTime OBJECT-TYPE
   SYNTAX     Counter32 
   ACCESS     read-only
   STATUS     mandatory
   DESCRIPTION
     "The number of seconds since the port component was activated."
::= { mscLpE1StatsEntry 1 }

mscLpE1ErrorFreeSec OBJECT-TYPE
   SYNTAX     Counter32 
   ACCESS     read-only
   STATUS     mandatory
   DESCRIPTION
     "The number of seconds that the port has been in an error free state."
::= { mscLpE1StatsEntry 2 }

mscLpE1ErroredSec OBJECT-TYPE
   SYNTAX     Counter32 
   ACCESS     read-only
   STATUS     mandatory
   DESCRIPTION
     "An errored second is declared when a second with one or more 
      Code Violation Error events, or one or more Out Of Frame events 
      occurs. A code violation error may be a CRC error or a BPV error. 
      An Out Of Frame event occurs when 2 out of 5 framing bits are in 
      error."
::= { mscLpE1StatsEntry 3 }

mscLpE1SevErroredSec OBJECT-TYPE
   SYNTAX     Counter32 
   ACCESS     read-only
   STATUS     mandatory
   DESCRIPTION
     "A severely errored second occurs when a second with 320 or more 
      Code Violation Error events or one or more Out Of Frame events 
      occurs."
::= { mscLpE1StatsEntry 4 }

mscLpE1SevErroredFrmSec OBJECT-TYPE
   SYNTAX     Counter32 
   ACCESS     read-only
   STATUS     mandatory
   DESCRIPTION
     "A severely errored framing second occurs when a second with one 
      or more Out Of Frame events occurs."
::= { mscLpE1StatsEntry 5 }

mscLpE1UnavailSec OBJECT-TYPE
   SYNTAX     Counter32 
   ACCESS     read-only
   STATUS     mandatory
   DESCRIPTION
     "The total number of seconds that the interface is in an unavailable 
      signal state. An unavailable signal state occurs at the onset of 10 
      consecutive Severely Errored Seconds. The state is cleared at the 
      onset of 10 seconds with no Severely Errored Seconds."
::= { mscLpE1StatsEntry 6 }

mscLpE1BpvErrors OBJECT-TYPE
   SYNTAX     Counter32 
   ACCESS     read-only
   STATUS     mandatory
   DESCRIPTION
     "The current count of Bipolar Violations. A bipolar violation is an 
      error in the alternate mark inversion pattern (AMI) on the line."
::= { mscLpE1StatsEntry 7 }

mscLpE1CrcErrors OBJECT-TYPE
   SYNTAX     Counter32 
   ACCESS     read-only
   STATUS     mandatory
   DESCRIPTION
     "If the interface is a DS1 line, it is the current count of CRC-6 errors. 
      These will only be counted when the lineType is ESF.
      If the interface is an E1 line, it is the total number of CRC-4 errors. 
      These will only be counted when crc4Mode is on."
::= { mscLpE1StatsEntry 8 }

mscLpE1FrmErrors OBJECT-TYPE
   SYNTAX     Counter32 
   ACCESS     read-only
   STATUS     mandatory
   DESCRIPTION
     "The current count of frame errors. A frame error is an error in the 
      framing bits"
::= { mscLpE1StatsEntry 9 }

mscLpE1LosStateChanges OBJECT-TYPE
   SYNTAX     Counter32 
   ACCESS     read-only
   STATUS     mandatory
   DESCRIPTION
     "The total number of times that the line lost signal."
::= { mscLpE1StatsEntry 10 }

mscLpE1SlipErrors OBJECT-TYPE
   SYNTAX     Counter32 
   ACCESS     read-only
   STATUS     mandatory
   DESCRIPTION
     "The total number of times that the line experienced a controlled 
      frame slip. This attribute is incremented for ports on the voice cards 
      (for example the 1pDS1V and the 1pE1V function processors) only."
::= { mscLpE1StatsEntry 11 }


-- Channel
-- The Channel component is configured to control a group of 
-- timeslots that form a fractional group on a DS1 or E1 port. 
-- Cell-based cards allow only one channel per port, and this is 
-- automatically provisioned with all available timeslots.

mscLpE1Chan OBJECT IDENTIFIER ::= { mscLpE1 2 }



mscLpE1ChanRowStatusTable OBJECT-TYPE
   SYNTAX     SEQUENCE OF MscLpE1ChanRowStatusEntry
   ACCESS     not-accessible
   STATUS     mandatory
   DESCRIPTION
     "This entry controls the addition and deletion of 
      mscLpE1Chan components."
::= { mscLpE1Chan 1 }

mscLpE1ChanRowStatusEntry OBJECT-TYPE
   SYNTAX     MscLpE1ChanRowStatusEntry
   ACCESS     not-accessible
   STATUS     mandatory
   DESCRIPTION
     "A single entry in the table represents a single 
      mscLpE1Chan component."
   INDEX {
      mscLpIndex,
      mscLpE1Index,
      mscLpE1ChanIndex }
::= { mscLpE1ChanRowStatusTable 1 }

MscLpE1ChanRowStatusEntry ::= SEQUENCE {
   mscLpE1ChanRowStatus
      RowStatus,
   mscLpE1ChanComponentName
      DisplayString,
   mscLpE1ChanStorageType
      StorageType,
   mscLpE1ChanIndex
      Integer32 }

mscLpE1ChanRowStatus OBJECT-TYPE
   SYNTAX     RowStatus 
   ACCESS     read-write
   STATUS     mandatory
   DESCRIPTION
     "This variable is used as the basis for SNMP naming of
      mscLpE1Chan components.
      These components can be added and deleted."
::= { mscLpE1ChanRowStatusEntry 1 }

mscLpE1ChanComponentName OBJECT-TYPE
   SYNTAX     DisplayString 
   ACCESS     read-only
   STATUS     mandatory
   DESCRIPTION
     "This variable provides the component's string name for
      use with the ASCII Console Interface"
::= { mscLpE1ChanRowStatusEntry 2 }

mscLpE1ChanStorageType OBJECT-TYPE
   SYNTAX     StorageType 
   ACCESS     read-only
   STATUS     mandatory
   DESCRIPTION
     "This variable represents the storage type value for the
      mscLpE1Chan tables."
::= { mscLpE1ChanRowStatusEntry 4 }

mscLpE1ChanIndex OBJECT-TYPE
   SYNTAX     Integer32 (0..31)
   ACCESS     not-accessible
   STATUS     mandatory
   DESCRIPTION
     "This variable represents the index for the mscLpE1Chan tables."
::= { mscLpE1ChanRowStatusEntry 10 }

mscLpE1ChanProvTable OBJECT-TYPE
   SYNTAX     SEQUENCE OF MscLpE1ChanProvEntry
   ACCESS     not-accessible
   STATUS     mandatory
   DESCRIPTION
     "This group contains all of the provisional data for a Channel 
      component."
::= { mscLpE1Chan 10 }

mscLpE1ChanProvEntry OBJECT-TYPE
   SYNTAX     MscLpE1ChanProvEntry
   ACCESS     not-accessible
   STATUS     mandatory
   DESCRIPTION
     "An entry in the mscLpE1ChanProvTable."
   INDEX {
      mscLpIndex,
      mscLpE1Index,
      mscLpE1ChanIndex }
::= { mscLpE1ChanProvTable 1 }

MscLpE1ChanProvEntry ::= SEQUENCE {
   mscLpE1ChanTimeslots
      OCTET STRING,
   mscLpE1ChanTimeslotDataRate
      INTEGER,
   mscLpE1ChanApplicationFramerName
      Link }

mscLpE1ChanTimeslots OBJECT-TYPE
   SYNTAX     OCTET STRING (SIZE (4))
   ACCESS     read-write
   STATUS     mandatory
   DESCRIPTION
     "This attribute contains the list of timeslots that are used by the 
      Channel component. Valid numbers are 1-24 for a Channel used by 
      a DS1 component, and 1-31 for a Channel used by an E1 
      component.

      Description of bits:
      notused0(0)
      n1(1)
      n2(2)
      n3(3)
      n4(4)
      n5(5)
      n6(6)
      n7(7)
      n8(8)
      n9(9)
      n10(10)
      n11(11)
      n12(12)
      n13(13)
      n14(14)
      n15(15)
      n16(16)
      n17(17)
      n18(18)
      n19(19)
      n20(20)
      n21(21)
      n22(22)
      n23(23)
      n24(24)
      n25(25)
      n26(26)
      n27(27)
      n28(28)
      n29(29)
      n30(30)
      n31(31)"
::= { mscLpE1ChanProvEntry 1 }

mscLpE1ChanTimeslotDataRate OBJECT-TYPE
   SYNTAX     INTEGER  {
                 n56k(0),
                 doNotOverride(1) }
   ACCESS     read-write
   STATUS     mandatory
   DESCRIPTION
     "This attribute selects the data rate of the timeslots in a channel of a 
      DS1 component. For E1, the data rate of the timeslots will always 
      be 64kbit/s regardless of this attribute.
      When doNotOverride is selected for a channel on a DS1, the data 
      rate of the channel's timeslots are dependant on the zeroCoding 
      selection of the DS1 component. If the zeroCoding is B8ZS (where 
      supported on the FP) or none, the timeslot's data rate will be 64kbit/
      s. If the zeroCoding option is bit7Stuffing, the data rate of a timeslot 
      will be 56kbit/s.
      When 56k is selected for a channel on a DS1, the least significant 
      bit of each timeslot of this Channel will always be set to 1 and not 
      used for data. The data rate for the timeslots of this channel is 
      therefore restricted to 56kbit/s.
      One application of this attribute is to allow a DS1 line to support 
      mixing channels that originate from lines that use different 
      zeroCoding schemes."
   DEFVAL     { doNotOverride }
::= { mscLpE1ChanProvEntry 2 }

mscLpE1ChanApplicationFramerName OBJECT-TYPE
   SYNTAX     Link 
   ACCESS     read-write
   STATUS     mandatory
   DESCRIPTION
     "This attribute defines the link to the software stack. It defines which 
      application is running on top of this hardware component."
::= { mscLpE1ChanProvEntry 3 }

mscLpE1ChanCidDataTable OBJECT-TYPE
   SYNTAX     SEQUENCE OF MscLpE1ChanCidDataEntry
   ACCESS     not-accessible
   STATUS     mandatory
   DESCRIPTION
     "This group contains the attribute for a component's Customer 
      Identifier (CID). Refer to the attribute description for a detailed 
      explanation of CIDs."
::= { mscLpE1Chan 11 }

mscLpE1ChanCidDataEntry OBJECT-TYPE
   SYNTAX     MscLpE1ChanCidDataEntry
   ACCESS     not-accessible
   STATUS     mandatory
   DESCRIPTION
     "An entry in the mscLpE1ChanCidDataTable."
   INDEX {
      mscLpIndex,
      mscLpE1Index,
      mscLpE1ChanIndex }
::= { mscLpE1ChanCidDataTable 1 }

MscLpE1ChanCidDataEntry ::= SEQUENCE {
   mscLpE1ChanCustomerIdentifier
      Unsigned32 }

mscLpE1ChanCustomerIdentifier OBJECT-TYPE
   SYNTAX     Unsigned32 (0 | 1..8191)
   ACCESS     read-write
   STATUS     mandatory
   DESCRIPTION
     "This attribute holds the Customer Identifier (CID).
      
      Every component has a CID. If a component has a cid attribute, the 
      component's CID is the provisioned value of that attribute; 
      otherwise the component inherits the CID of its parent. The top-
      level component has a CID of 0.
      
      Every operator session also has a CID, which is the CID 
      provisioned for the operator's user ID. An operator will see only the 
      stream data for components having a matching CID. Also, the 
      operator will be allowed to issue commands for only those 
      components which have a matching CID.
      
      An operator CID of 0 is used to identify the Network Manager 
      (referred to as 'NetMan' in DPN). This CID matches the CID of 
      any component. Values 1 to 8191 inclusive (equivalent to 'basic 
      CIDs' in DPN) may be assigned to specific customers."
   DEFVAL     { 0 }
::= { mscLpE1ChanCidDataEntry 1 }

mscLpE1ChanIfEntryTable OBJECT-TYPE
   SYNTAX     SEQUENCE OF MscLpE1ChanIfEntryEntry
   ACCESS     not-accessible
   STATUS     mandatory
   DESCRIPTION
     "This group contains the provisionable attributes for the ifEntry."
::= { mscLpE1Chan 12 }

mscLpE1ChanIfEntryEntry OBJECT-TYPE
   SYNTAX     MscLpE1ChanIfEntryEntry
   ACCESS     not-accessible
   STATUS     mandatory
   DESCRIPTION
     "An entry in the mscLpE1ChanIfEntryTable."
   INDEX {
      mscLpIndex,
      mscLpE1Index,
      mscLpE1ChanIndex }
::= { mscLpE1ChanIfEntryTable 1 }

MscLpE1ChanIfEntryEntry ::= SEQUENCE {
   mscLpE1ChanIfAdminStatus
      INTEGER,
   mscLpE1ChanIfIndex
      InterfaceIndex }

mscLpE1ChanIfAdminStatus OBJECT-TYPE
   SYNTAX     INTEGER  {
                 up(1),
                 down(2),
                 testing(3) }
   ACCESS     read-write
   STATUS     mandatory
   DESCRIPTION
     "The desired state of the interface. The up state indicates the 
      interface is operational. The down state indicates the interface is not 
      operational. The testing state indicates that no operational packets 
      can be passed."
   DEFVAL     { up }
::= { mscLpE1ChanIfEntryEntry 1 }

mscLpE1ChanIfIndex OBJECT-TYPE
   SYNTAX     InterfaceIndex (1..65535)
   ACCESS     read-only
   STATUS     mandatory
   DESCRIPTION
     "This is the index for the IfEntry. Its value is automatically initialized 
      during the provisioning process."
::= { mscLpE1ChanIfEntryEntry 2 }

mscLpE1ChanOperStatusTable OBJECT-TYPE
   SYNTAX     SEQUENCE OF MscLpE1ChanOperStatusEntry
   ACCESS     not-accessible
   STATUS     mandatory
   DESCRIPTION
     "This group includes the Operational Status attribute. This attribute 
      defines the current operational state of this component."
::= { mscLpE1Chan 13 }

mscLpE1ChanOperStatusEntry OBJECT-TYPE
   SYNTAX     MscLpE1ChanOperStatusEntry
   ACCESS     not-accessible
   STATUS     mandatory
   DESCRIPTION
     "An entry in the mscLpE1ChanOperStatusTable."
   INDEX {
      mscLpIndex,
      mscLpE1Index,
      mscLpE1ChanIndex }
::= { mscLpE1ChanOperStatusTable 1 }

MscLpE1ChanOperStatusEntry ::= SEQUENCE {
   mscLpE1ChanSnmpOperStatus
      INTEGER }

mscLpE1ChanSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { mscLpE1ChanOperStatusEntry 1 }

mscLpE1ChanStateTable OBJECT-TYPE
   SYNTAX     SEQUENCE OF MscLpE1ChanStateEntry
   ACCESS     not-accessible
   STATUS     mandatory
   DESCRIPTION
     "This group contains the three OSI State attributes and the six OSI 
      Status attributes. The descriptions generically indicate what each 
      attribute implies about the component. Note that not all the values 
      and state combinations described here are supported by every 
      component which uses this group. For component-specific 
      information and the valid state combinations, refer to NTP 241-
      7001-150, Passport Operations and Maintenance Guide."
::= { mscLpE1Chan 14 }

mscLpE1ChanStateEntry OBJECT-TYPE
   SYNTAX     MscLpE1ChanStateEntry
   ACCESS     not-accessible
   STATUS     mandatory
   DESCRIPTION
     "An entry in the mscLpE1ChanStateTable."
   INDEX {
      mscLpIndex,
      mscLpE1Index,
      mscLpE1ChanIndex }
::= { mscLpE1ChanStateTable 1 }

MscLpE1ChanStateEntry ::= SEQUENCE {
   mscLpE1ChanAdminState
      INTEGER,
   mscLpE1ChanOperationalState
      INTEGER,
   mscLpE1ChanUsageState
      INTEGER,
   mscLpE1ChanAvailabilityStatus
      OCTET STRING,
   mscLpE1ChanProceduralStatus
      OCTET STRING,
   mscLpE1ChanControlStatus
      OCTET STRING,
   mscLpE1ChanAlarmStatus
      OCTET STRING,
   mscLpE1ChanStandbyStatus
      INTEGER,
   mscLpE1ChanUnknownStatus
      INTEGER }

mscLpE1ChanAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component.
      
      The OSI Status attributes, if supported by the component, may 
      provide more details, qualifying the state of the component."
   DEFVAL     { unlocked }
::= { mscLpE1ChanStateEntry 1 }

mscLpE1ChanOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle.
      
      The OSI Status attributes, if supported by the component, may 
      provide more details, qualifying the state of the component."
   DEFVAL     { disabled }
::= { mscLpE1ChanStateEntry 2 }

mscLpE1ChanUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time.
      
      The OSI Status attributes, if supported by the component, may 
      provide more details, qualifying the state of the component."
   DEFVAL     { idle }
::= { mscLpE1ChanStateEntry 3 }

mscLpE1ChanAvailabilityStatus OBJECT-TYPE
   SYNTAX     OCTET STRING (SIZE (2))
   ACCESS     read-only
   STATUS     mandatory
   DESCRIPTION
     "If supported by the component, this attribute indicates the OSI 
      Availability status of the component. Note that, even though it is 
      defined as a multi-valued set, at most one value is shown to the user.
      
      When no values are in the set, this indicates that either the attribute 
      is not supported or that none of the status conditions described 
      below are present.
      
      The value inTest indicates that the resource is undergoing a test 
      procedure. If adminState is locked or shuttingDown, the normal 
      users are precluded from using the resource and controlStatus is 
      reservedForTest. Tests that do not exclude additional users can be 
      present in any operational or administrative state but the 
      reservedForTest condition should not be present.
      
      The value failed indicates that the component has an internal fault 
      that prevents it from operating. The operationalState is disabled.
      
      The value dependency indicates that the component cannot operate 
      because some other resource on which it depends is unavailable. 
      The operationalState is disabled.
      
      The value powerOff indicates the resource requires power to be 
      applied and it is not powered on. The operationalState is disabled.
      
      The value offLine indicates the resource requires a routine 
      operation (either manual, automatic, or both) to be performed to 
      place it on-line and make it available for use. The operationalState 
      is disabled.
      
      The value offDuty indicates the resource is inactive in accordance 
      with a predetermined time schedule. In the absence of other 
      disabling conditions, the operationalState is enabled or disabled.
      
      The value degraded indicates the service provided by the 
      component is degraded in some way, such as in speed or operating 
      capacity. However, the resource remains available for service. The 
      operationalState is enabled.
      
      The value notInstalled indicates the resource is not present. The 
      operationalState is disabled.
      
      The value logFull is not used.

      Description of bits:
      inTest(0)
      failed(1)
      powerOff(2)
      offLine(3)
      offDuty(4)
      dependency(5)
      degraded(6)
      notInstalled(7)
      logFull(8)"
::= { mscLpE1ChanStateEntry 4 }

mscLpE1ChanProceduralStatus OBJECT-TYPE
   SYNTAX     OCTET STRING (SIZE (1))
   ACCESS     read-only
   STATUS     mandatory
   DESCRIPTION
     "If supported by the component, this attribute indicates the OSI 
      Procedural status of the component. Note that, even though it is 
      defined as a multi-valued set, at most one value is shown to the user.
      
      When no values are in the set, this indicates that either the attribute 
      is not supported or that none of the status conditions described 
      below are present.
      
      The value initializationRequired indicates (for a resource which 
      doesn't initialize autonomously) that initialization is required before 
      it can perform its normal functions, and this procedure has not been 
      initiated. The operationalState is disabled.
      
      The value notInitialized indicates (for a resource which does 
      initialize autonomously) that initialization is required before it can 
      perform its normal functions, and this procedure has not been 
      initiated. The operationalState may be enabled or disabled.
      
      The value initializing indicates that initialization has been initiated 
      but is not yet complete. The operationalState may be enabled or 
      disabled.
      
      The value reporting indicates the resource has completed some 
      processing operation and is notifying the results. The 
      operationalState is enabled.
      
      The value terminating indicates the component is in a termination 
      phase. If the resource doesn't reinitialize autonomously, 
      operationalState is disabled; otherwise it is enabled or disabled.

      Description of bits:
      initializationRequired(0)
      notInitialized(1)
      initializing(2)
      reporting(3)
      terminating(4)"
::= { mscLpE1ChanStateEntry 5 }

mscLpE1ChanControlStatus OBJECT-TYPE
   SYNTAX     OCTET STRING (SIZE (1))
   ACCESS     read-only
   STATUS     mandatory
   DESCRIPTION
     "If supported by the component, this attribute indicates the OSI 
      Control status of the component. Note that, even though it is defined 
      as a multi-valued set, at most one value is shown to the user.
      
      When no values are in the set, this indicates that either the attribute 
      is not supported or that none of the status conditions described 
      below are present.
      
      The value subjectToTest indicates the resource is available but tests 
      may be conducted simultaneously at unpredictable times, which 
      may cause it to exhibit unusual characteristics.
      
      The value partOfServicesLocked indicates that part of the service is 
      restricted from users of a resource. The adminState is unlocked.
      
      The value reservedForTest indicates that the component is 
      administratively unavailable because it is undergoing a test 
      procedure. The adminState is locked.
      
      The value suspended indicates that the service has been 
      administratively suspended.

      Description of bits:
      subjectToTest(0)
      partOfServicesLocked(1)
      reservedForTest(2)
      suspended(3)"
::= { mscLpE1ChanStateEntry 6 }

mscLpE1ChanAlarmStatus OBJECT-TYPE
   SYNTAX     OCTET STRING (SIZE (1))
   ACCESS     read-only
   STATUS     mandatory
   DESCRIPTION
     "If supported by the component, this attribute indicates the OSI 
      Alarm status of the component. Note that, even though it is defined 
      as a multi-valued set, at most one value is shown to the user.
      
      When no values are in the set, this indicates that either the attribute 
      is not supported or that none of the status conditions described 
      below are present.
      
      The value underRepair indicates the component is currently being 
      repaired. The operationalState is enabled or disabled.
      
      The value critical indicates one or more critical alarms are 
      outstanding against the component. Other, less severe, alarms may 
      also be outstanding. The operationalState is enabled or disabled.
      
      The value major indicates one or more major alarms are 
      outstanding against the component. Other, less severe, alarms may 
      also be outstanding. The operationalState is enabled or disabled.
      
      The value minor indicates one or more minor alarms are 
      outstanding against the component. Other, less severe, alarms may 
      also be outstanding. The operationalState is enabled or disabled.
      
      The value alarmOutstanding generically indicates that an alarm of 
      some severity is outstanding against the component.

      Description of bits:
      underRepair(0)
      critical(1)
      major(2)
      minor(3)
      alarmOutstanding(4)"
::= { mscLpE1ChanStateEntry 7 }

mscLpE1ChanStandbyStatus OBJECT-TYPE
   SYNTAX     INTEGER  {
                 hotStandby(0),
                 coldStandby(1),
                 providingService(2),
                 notSet(15) }
   ACCESS     read-only
   STATUS     mandatory
   DESCRIPTION
     "If supported by the component, this attribute indicates the OSI 
      Standby status of the component.
      
      The value notSet indicates that either the attribute is not supported 
      or that none of the status conditions described below are present. 
      Note that this is a non-standard value, used because the original 
      specification indicated this attribute was set-valued and thus, did not 
      provide a value to indicate that none of the other three are 
      applicable.
      
      The value hotStandby indicates that the resource is not providing 
      service but will be immediately able to take over the role of the 
      resource to be backed up, without initialization activity, and 
      containing the same information as the resource to be backed up.
      
      The value coldStandby indicates the resource is a backup for 
      another resource but will not be immediately able to take over the 
      role of the backed up resource and will require some initialization 
      activity.
      
      The value providingService indicates that this component, as a 
      backup resource, is currently backing up another resource."
   DEFVAL     { notSet }
::= { mscLpE1ChanStateEntry 8 }

mscLpE1ChanUnknownStatus OBJECT-TYPE
   SYNTAX     INTEGER  {
                 false(0),
                 true(1) }
   ACCESS     read-only
   STATUS     mandatory
   DESCRIPTION
     "This attribute indicates the OSI Unknown status of the component.
      
      The value false indicates that all of the other OSI State and Status 
      attribute values can be considered accurate.
      
      The value true indicates that the actual state of the component is not 
      known for sure."
   DEFVAL     { false }
::= { mscLpE1ChanStateEntry 9 }

mscLpE1ChanOperTable OBJECT-TYPE
   SYNTAX     SEQUENCE OF MscLpE1ChanOperEntry
   ACCESS     not-accessible
   STATUS     mandatory
   DESCRIPTION
     "This group contains all of the operational data for a Channel 
      component."
::= { mscLpE1Chan 15 }

mscLpE1ChanOperEntry OBJECT-TYPE
   SYNTAX     MscLpE1ChanOperEntry
   ACCESS     not-accessible
   STATUS     mandatory
   DESCRIPTION
     "An entry in the mscLpE1ChanOperTable."
   INDEX {
      mscLpIndex,
      mscLpE1Index,
      mscLpE1ChanIndex }
::= { mscLpE1ChanOperTable 1 }

MscLpE1ChanOperEntry ::= SEQUENCE {
   mscLpE1ChanActualChannelSpeed
      Gauge32 }

mscLpE1ChanActualChannelSpeed OBJECT-TYPE
   SYNTAX     Gauge32 (0..4294967295)
   ACCESS     read-only
   STATUS     mandatory
   DESCRIPTION
     "This attribute displays the measured link speed of the Channel 
      component."
   DEFVAL     { 0 }
::= { mscLpE1ChanOperEntry 1 }

mscLpE1ChanAdminInfoTable OBJECT-TYPE
   SYNTAX     SEQUENCE OF MscLpE1ChanAdminInfoEntry
   ACCESS     not-accessible
   STATUS     mandatory
   DESCRIPTION
     "This group contains the attributes pertaining to the vendor of the 
      equipment."
::= { mscLpE1Chan 16 }

mscLpE1ChanAdminInfoEntry OBJECT-TYPE
   SYNTAX     MscLpE1ChanAdminInfoEntry
   ACCESS     not-accessible
   STATUS     mandatory
   DESCRIPTION
     "An entry in the mscLpE1ChanAdminInfoTable."
   INDEX {
      mscLpIndex,
      mscLpE1Index,
      mscLpE1ChanIndex }
::= { mscLpE1ChanAdminInfoTable 1 }

MscLpE1ChanAdminInfoEntry ::= SEQUENCE {
   mscLpE1ChanVendor
      AsciiString,
   mscLpE1ChanCommentText
      AsciiString }

mscLpE1ChanVendor OBJECT-TYPE
   SYNTAX     AsciiString (SIZE (0..20))
   ACCESS     read-write
   STATUS     mandatory
   DESCRIPTION
     "This is the name of the vendor supplying the facility."
::= { mscLpE1ChanAdminInfoEntry 1 }

mscLpE1ChanCommentText OBJECT-TYPE
   SYNTAX     AsciiString (SIZE (0..60))
   ACCESS     read-write
   STATUS     mandatory
   DESCRIPTION
     "Any miscellaneous text about the facility."
::= { mscLpE1ChanAdminInfoEntry 2 }


-- 
-- The Test component is configured to control a hardware facility test 
-- on a physical (V35, X21, DS1, E1, DS3, E3 etc.) or a logical port.

mscLpE1ChanTest OBJECT IDENTIFIER ::= { mscLpE1Chan 2 }



mscLpE1ChanTestRowStatusTable OBJECT-TYPE
   SYNTAX     SEQUENCE OF MscLpE1ChanTestRowStatusEntry
   ACCESS     not-accessible
   STATUS     mandatory
   DESCRIPTION
     "This entry controls the addition and deletion of 
      mscLpE1ChanTest components."
::= { mscLpE1ChanTest 1 }

mscLpE1ChanTestRowStatusEntry OBJECT-TYPE
   SYNTAX     MscLpE1ChanTestRowStatusEntry
   ACCESS     not-accessible
   STATUS     mandatory
   DESCRIPTION
     "A single entry in the table represents a single 
      mscLpE1ChanTest component."
   INDEX {
      mscLpIndex,
      mscLpE1Index,
      mscLpE1ChanIndex,
      mscLpE1ChanTestIndex }
::= { mscLpE1ChanTestRowStatusTable 1 }

MscLpE1ChanTestRowStatusEntry ::= SEQUENCE {
   mscLpE1ChanTestRowStatus
      RowStatus,
   mscLpE1ChanTestComponentName
      DisplayString,
   mscLpE1ChanTestStorageType
      StorageType,
   mscLpE1ChanTestIndex
      NonReplicated }

mscLpE1ChanTestRowStatus OBJECT-TYPE
   SYNTAX     RowStatus 
   ACCESS     read-only
   STATUS     mandatory
   DESCRIPTION
     "This variable is used as the basis for SNMP naming of
      mscLpE1ChanTest components.
      These components cannot be added nor deleted."
::= { mscLpE1ChanTestRowStatusEntry 1 }

mscLpE1ChanTestComponentName OBJECT-TYPE
   SYNTAX     DisplayString 
   ACCESS     read-only
   STATUS     mandatory
   DESCRIPTION
     "This variable provides the component's string name for
      use with the ASCII Console Interface"
::= { mscLpE1ChanTestRowStatusEntry 2 }

mscLpE1ChanTestStorageType OBJECT-TYPE
   SYNTAX     StorageType 
   ACCESS     read-only
   STATUS     mandatory
   DESCRIPTION
     "This variable represents the storage type value for the
      mscLpE1ChanTest tables."
::= { mscLpE1ChanTestRowStatusEntry 4 }

mscLpE1ChanTestIndex OBJECT-TYPE
   SYNTAX     NonReplicated 
   ACCESS     not-accessible
   STATUS     mandatory
   DESCRIPTION
     "This variable represents the index for the mscLpE1ChanTest tables."
::= { mscLpE1ChanTestRowStatusEntry 10 }

mscLpE1ChanTestStateTable OBJECT-TYPE
   SYNTAX     SEQUENCE OF MscLpE1ChanTestStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscLpE1ChanTest 10 }

mscLpE1ChanTestStateEntry OBJECT-TYPE
   SYNTAX     MscLpE1ChanTestStateEntry
   ACCESS     not-accessible
   STATUS     mandatory
   DESCRIPTION
     "An entry in the mscLpE1ChanTestStateTable."
   INDEX {
      mscLpIndex,
      mscLpE1Index,
      mscLpE1ChanIndex,
      mscLpE1ChanTestIndex }
::= { mscLpE1ChanTestStateTable 1 }

MscLpE1ChanTestStateEntry ::= SEQUENCE {
   mscLpE1ChanTestAdminState
      INTEGER,
   mscLpE1ChanTestOperationalState
      INTEGER,
   mscLpE1ChanTestUsageState
      INTEGER }

mscLpE1ChanTestAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscLpE1ChanTestStateEntry 1 }

mscLpE1ChanTestOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscLpE1ChanTestStateEntry 2 }

mscLpE1ChanTestUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscLpE1ChanTestStateEntry 3 }

mscLpE1ChanTestSetupTable OBJECT-TYPE
   SYNTAX     SEQUENCE OF MscLpE1ChanTestSetupEntry
   ACCESS     not-accessible
   STATUS     mandatory
   DESCRIPTION
     "This group contains all of the operational data for a Test 
      component."
::= { mscLpE1ChanTest 11 }

mscLpE1ChanTestSetupEntry OBJECT-TYPE
   SYNTAX     MscLpE1ChanTestSetupEntry
   ACCESS     not-accessible
   STATUS     mandatory
   DESCRIPTION
     "An entry in the mscLpE1ChanTestSetupTable."
   INDEX {
      mscLpIndex,
      mscLpE1Index,
      mscLpE1ChanIndex,
      mscLpE1ChanTestIndex }
::= { mscLpE1ChanTestSetupTable 1 }

MscLpE1ChanTestSetupEntry ::= SEQUENCE {
   mscLpE1ChanTestPurpose
      AsciiString,
   mscLpE1ChanTestType
      INTEGER,
   mscLpE1ChanTestFrmSize
      Unsigned32,
   mscLpE1ChanTestFrmPatternType
      INTEGER,
   mscLpE1ChanTestCustomizedPattern
      Hex,
   mscLpE1ChanTestDataStartDelay
      Unsigned32,
   mscLpE1ChanTestDisplayInterval
      Unsigned32,
   mscLpE1ChanTestDuration
      Unsigned32 }

mscLpE1ChanTestPurpose OBJECT-TYPE
   SYNTAX     AsciiString (SIZE (0..40))
   ACCESS     read-write
   STATUS     mandatory
   DESCRIPTION
     "This attribute records the purpose of the test so that the test results 
      can be associated and properly analyzed."
::= { mscLpE1ChanTestSetupEntry 1 }

mscLpE1ChanTestType OBJECT-TYPE
   SYNTAX     INTEGER  {
                 card(0),
                 manual(1),
                 localLoop(2),
                 remoteLoop(3),
                 externalLoop(4),
                 payloadLoop(5),
                 remoteLoopThisTrib(6),
                 v54RemoteLoop(7),
                 pn127RemoteLoop(8) }
   ACCESS     read-write
   STATUS     mandatory
   DESCRIPTION
     "This attribute is the type of test to be run. The available test types 
      include the following:
      card test sets up an internal loop on the board and runs a bit error 
      rate test.
      manual test assumes the line is looped back externally and a bit 
      error rate test is performed.
      localLoop test loops back the local modem and performs a bit error 
      rate test.
      remoteLoop test loops back the remote modem (or CSU) and 
      performs a bit error rate test.
      externalLoop test loops back the line to the far end.
      payloadLoop test only loops back the payload data received from 
      the incoming line.
      remoteLoopThisTrib loops this particular tributary back at the far 
      end, using services provided by the parent.
      v54RemoteLoop initiates a V.54 Remote Loopback test.
      pn127RemoteLoop initiates a PN127 Remote Loopback test.
      Note that not all test types are not supported by all function 
      processors."
   DEFVAL     { card }
::= { mscLpE1ChanTestSetupEntry 2 }

mscLpE1ChanTestFrmSize OBJECT-TYPE
   SYNTAX     Unsigned32 (4..4096)
   ACCESS     read-write
   STATUS     mandatory
   DESCRIPTION
     "This attribute defines the size of the test data frames in number of 
      bytes."
   DEFVAL     { 1024 }
::= { mscLpE1ChanTestSetupEntry 3 }

mscLpE1ChanTestFrmPatternType OBJECT-TYPE
   SYNTAX     INTEGER  {
                 ccitt32kBitPattern(0),
                 ccitt8MBitPattern(1),
                 customizedPattern(2) }
   ACCESS     read-write
   STATUS     mandatory
   DESCRIPTION
     "This attribute defines the type of data pattern generation to use. The 
      following lists the available pattern types:
      ccitt32kBitPattern is a pseudo-random sequence of 32 kbit.
      ccitt8MBitPattern is a pseudo-random sequence of 8Mbit.
      customizedPattern is the pattern defined in the customizedPattern 
      attribute."
   DEFVAL     { ccitt32kBitPattern }
::= { mscLpE1ChanTestSetupEntry 4 }

mscLpE1ChanTestCustomizedPattern OBJECT-TYPE
   SYNTAX     Hex (0..4294967295)
   ACCESS     read-write
   STATUS     mandatory
   DESCRIPTION
     "This attribute allows a customized 32 bit pattern to be defined for 
      use in the test data frames. This attribute is used when the attribute 
      frmPatternType is set to CustomizedPattern. Note that a 55 hex 
      pattern is an alternating 1 and 0 pattern."
   DEFVAL     { 1431655765 }
::= { mscLpE1ChanTestSetupEntry 5 }

mscLpE1ChanTestDataStartDelay OBJECT-TYPE
   SYNTAX     Unsigned32 (0..1814400)
   ACCESS     read-write
   STATUS     mandatory
   DESCRIPTION
     "This attribute specifies the time delay (in seconds) between when 
      the test expects the loop to have been set up, to when the test data 
      actually starts to be transmitted. This attribute is to accommodate 
      some non-standard equipment that requires extra time for setting up 
      a requested loop.
      This attribute is ignored when the test type is set to externalLoop."
   DEFVAL     { 0 }
::= { mscLpE1ChanTestSetupEntry 6 }

mscLpE1ChanTestDisplayInterval OBJECT-TYPE
   SYNTAX     Unsigned32 (0..30240)
   ACCESS     read-write
   STATUS     mandatory
   DESCRIPTION
     "This attribute defines the interval (in minutes) between which 
      interim test results are to be displayed. Results are displayed at the 
      operator console at which the test was started. When the test type is 
      set to externalLoop, this attribute is ignored. There will be no 
      display of results if displayInterval is set to 0. This attribute can be 
      changed anytime."
   DEFVAL     { 5 }
::= { mscLpE1ChanTestSetupEntry 7 }

mscLpE1ChanTestDuration OBJECT-TYPE
   SYNTAX     Unsigned32 (1..30240)
   ACCESS     read-write
   STATUS     mandatory
   DESCRIPTION
     "This attribute is the duration (in minutes) that test data will be 
      transmitted. In the case of an externalLoop, this is the time that the 
      loop is in effect. Note that dataStartDelay does not apply to the 
      externalLoop."
   DEFVAL     { 1 }
::= { mscLpE1ChanTestSetupEntry 8 }

mscLpE1ChanTestResultsTable OBJECT-TYPE
   SYNTAX     SEQUENCE OF MscLpE1ChanTestResultsEntry
   ACCESS     not-accessible
   STATUS     mandatory
   DESCRIPTION
     "This group contains all the statistics related attributes of the Test 
      component."
::= { mscLpE1ChanTest 12 }

mscLpE1ChanTestResultsEntry OBJECT-TYPE
   SYNTAX     MscLpE1ChanTestResultsEntry
   ACCESS     not-accessible
   STATUS     mandatory
   DESCRIPTION
     "An entry in the mscLpE1ChanTestResultsTable."
   INDEX {
      mscLpIndex,
      mscLpE1Index,
      mscLpE1ChanIndex,
      mscLpE1ChanTestIndex }
::= { mscLpE1ChanTestResultsTable 1 }

MscLpE1ChanTestResultsEntry ::= SEQUENCE {
   mscLpE1ChanTestElapsedTime
      Counter32,
   mscLpE1ChanTestTimeRemaining
      Unsigned32,
   mscLpE1ChanTestCauseOfTermination
      INTEGER,
   mscLpE1ChanTestBitsTx
      PassportCounter64,
   mscLpE1ChanTestBytesTx
      PassportCounter64,
   mscLpE1ChanTestFrmTx
      PassportCounter64,
   mscLpE1ChanTestBitsRx
      PassportCounter64,
   mscLpE1ChanTestBytesRx
      PassportCounter64,
   mscLpE1ChanTestFrmRx
      PassportCounter64,
   mscLpE1ChanTestErroredFrmRx
      PassportCounter64,
   mscLpE1ChanTestBitErrorRate
      AsciiString }

mscLpE1ChanTestElapsedTime OBJECT-TYPE
   SYNTAX     Counter32 
   ACCESS     read-only
   STATUS     mandatory
   DESCRIPTION
     "This attribute is the number of minutes elapsed since the test started 
      for an externalLoop test. For a data test, this is the time since test 
      data was first transmitted."
::= { mscLpE1ChanTestResultsEntry 1 }

mscLpE1ChanTestTimeRemaining OBJECT-TYPE
   SYNTAX     Unsigned32 (0..4294967295)
   ACCESS     read-only
   STATUS     mandatory
   DESCRIPTION
     "This attribute is the number of minutes remaining before the test is 
      to be stopped according to the duration attribute."
   DEFVAL     { 0 }
::= { mscLpE1ChanTestResultsEntry 2 }

mscLpE1ChanTestCauseOfTermination OBJECT-TYPE
   SYNTAX     INTEGER  {
                 testTimeExpired(0),
                 stoppedByOperator(1),
                 unknown(2),
                 neverStarted(3),
                 testRunning(4),
                 hardwareReconfigured(5),
                 loopCodeSyncFailed(6),
                 patternSyncFailed(7),
                 patternSyncLost(8) }
   ACCESS     read-only
   STATUS     mandatory
   DESCRIPTION
     "This attribute indicates either the status of the test or the cause of 
      the test's termination:
      
      neverStarted indicates that the test has not yet been started.
      
      testRunning indicates that the test has been started.
      
      stoppedByOperator indicates that the operator issued a stop 
      command on a test that was running.
      
      testTimeExpired indicates that the test ran for the time specified by 
      the test's duration.
      
      loopCodeSyncFailed indicates that the local end failed to 
      synchronize to the loopCode pattern. The local end transmits the 
      loopCode pattern to cause the remote end to apply a loopback, after 
      which the local end should receive the loopCode pattern. The exact 
      pattern used to request loopCode depends on the test type. This 
      failure indicates a high rate of transmission errors, or that the 
      remote end has failed to apply the loopback.
      
      patternSyncFailed indicates that the local end failed to synchronize 
      to the frmPatternType test pattern, that should have been looped 
      back at the remote end. This failure indicates a high rate of 
      transmission errors or the absence of a loopback.
      
      patternSyncLost indicates that the local end gained and then lost 
      synchronization to the returned frmPatternType test pattern. This 
      failure indicates a sudden increase in transmission errors, frame 
      slippage, or the removal of an existing loopback.
      
      unknown is set when a reason to terminate other than those listed 
      here is encountered.
      
      Note: Only MSA cards support recognition of the failures 
      loopCodeSyncFailed, patternSyncFailed and patternSyncLost. 
      Other cards will not terminate the test under the conditions 
      described by these values."
   DEFVAL     { neverStarted }
::= { mscLpE1ChanTestResultsEntry 3 }

mscLpE1ChanTestBitsTx OBJECT-TYPE
   SYNTAX     PassportCounter64 
   ACCESS     read-only
   STATUS     mandatory
   DESCRIPTION
     "This attribute is the total number of bits sent during the test period. 
      As long as the line speed of the hardware interface is less than 
      70 Mbit/s, this counter is not expected to reach the maximum value."
::= { mscLpE1ChanTestResultsEntry 4 }

mscLpE1ChanTestBytesTx OBJECT-TYPE
   SYNTAX     PassportCounter64 
   ACCESS     read-only
   STATUS     mandatory
   DESCRIPTION
     "This attribute is the total number of bytes sent during the test 
      period. This counter is not expected to reach its maximum value."
::= { mscLpE1ChanTestResultsEntry 5 }

mscLpE1ChanTestFrmTx OBJECT-TYPE
   SYNTAX     PassportCounter64 
   ACCESS     read-only
   STATUS     mandatory
   DESCRIPTION
     "This attribute is the total number of frames sent during the test 
      period. This counter is not expected to reach its maximum value."
::= { mscLpE1ChanTestResultsEntry 6 }

mscLpE1ChanTestBitsRx OBJECT-TYPE
   SYNTAX     PassportCounter64 
   ACCESS     read-only
   STATUS     mandatory
   DESCRIPTION
     "This attribute is the total number of bits received during the test 
      period. This counter is not expected to reach its maximum value. 
      The counter will wrap around to 0 if it does reach the maximum 
      value."
::= { mscLpE1ChanTestResultsEntry 7 }

mscLpE1ChanTestBytesRx OBJECT-TYPE
   SYNTAX     PassportCounter64 
   ACCESS     read-only
   STATUS     mandatory
   DESCRIPTION
     "This attribute is the total number of bytes received during the test 
      period. This counter is not expected to reach its maximum value. 
      The counter will wrap around to 0 if it does reach its maximum 
      value."
::= { mscLpE1ChanTestResultsEntry 8 }

mscLpE1ChanTestFrmRx OBJECT-TYPE
   SYNTAX     PassportCounter64 
   ACCESS     read-only
   STATUS     mandatory
   DESCRIPTION
     "This attribute is the total number of frames received during the test 
      period. This counter is not expected to reach its maximum value. 
      The counter will wrap around to 0 if it does reach its maximum 
      value."
::= { mscLpE1ChanTestResultsEntry 9 }

mscLpE1ChanTestErroredFrmRx OBJECT-TYPE
   SYNTAX     PassportCounter64 
   ACCESS     read-only
   STATUS     mandatory
   DESCRIPTION
     "This attribute is not displayed for ATM cards because the physical 
      layer drops all errored frames at the controller interface. 
      
      For all other card types, this attribute is the total number of errored 
      frames received during the test period. This counter is not expected 
      to reach its maximum value. The counter will wrap around to 0 if it 
      does reach its maximum value."
::= { mscLpE1ChanTestResultsEntry 10 }

mscLpE1ChanTestBitErrorRate OBJECT-TYPE
   SYNTAX     AsciiString (SIZE (5))
   ACCESS     read-only
   STATUS     mandatory
   DESCRIPTION
     "This attribute is not displayed for ATM cards because the physical 
      layer drops all errored frames at the controller interface. 
      
      For all other card types, this attribute is the calculated bit error rate 
      on the link. Test data are generated and sent in frames of a preset 
      size (frameSize). The Test component will try to estimate the 
      number of bit errors in any errored frame which is identifiable. The 
      statistics will be updated accordingly. A lost frame (may be due to 
      an error on the flag sequence) will be discarded for the bit error rate 
      calculation. The result is presented in the form of xEsyy, where x is 
      the mantissa, syy is the exponent, for example 0E+00, 2E-09.
      Note that the bitErrorRate is an estimate only. For more reliable test 
      results, the test should be done over a long period. Multiple tests 
      would also improve the confidence level of the test results."
::= { mscLpE1ChanTestResultsEntry 11 }


-- 
-- The AtmCell is a component that contains provisioning and 
-- operational attributes. The provisioning attributes are used to set the 
-- Loss of Cell Deliniation (LCD) alarm activation delay and to turn 
-- cell payload scrambling on or off. The operational attributes are 
-- used to report about the quality of the ATM cells received by the 
-- interface and the cell capacity utilization. The AtmCell component 
-- appears under all port components running on ATM cards.

mscLpE1ChanCell OBJECT IDENTIFIER ::= { mscLpE1Chan 3 }



mscLpE1ChanCellRowStatusTable OBJECT-TYPE
   SYNTAX     SEQUENCE OF MscLpE1ChanCellRowStatusEntry
   ACCESS     not-accessible
   STATUS     mandatory
   DESCRIPTION
     "This entry controls the addition and deletion of 
      mscLpE1ChanCell components."
::= { mscLpE1ChanCell 1 }

mscLpE1ChanCellRowStatusEntry OBJECT-TYPE
   SYNTAX     MscLpE1ChanCellRowStatusEntry
   ACCESS     not-accessible
   STATUS     mandatory
   DESCRIPTION
     "A single entry in the table represents a single 
      mscLpE1ChanCell component."
   INDEX {
      mscLpIndex,
      mscLpE1Index,
      mscLpE1ChanIndex,
      mscLpE1ChanCellIndex }
::= { mscLpE1ChanCellRowStatusTable 1 }

MscLpE1ChanCellRowStatusEntry ::= SEQUENCE {
   mscLpE1ChanCellRowStatus
      RowStatus,
   mscLpE1ChanCellComponentName
      DisplayString,
   mscLpE1ChanCellStorageType
      StorageType,
   mscLpE1ChanCellIndex
      NonReplicated }

mscLpE1ChanCellRowStatus OBJECT-TYPE
   SYNTAX     RowStatus 
   ACCESS     read-write
   STATUS     mandatory
   DESCRIPTION
     "This variable is used as the basis for SNMP naming of
      mscLpE1ChanCell components.
      These components can be added and deleted."
::= { mscLpE1ChanCellRowStatusEntry 1 }

mscLpE1ChanCellComponentName OBJECT-TYPE
   SYNTAX     DisplayString 
   ACCESS     read-only
   STATUS     mandatory
   DESCRIPTION
     "This variable provides the component's string name for
      use with the ASCII Console Interface"
::= { mscLpE1ChanCellRowStatusEntry 2 }

mscLpE1ChanCellStorageType OBJECT-TYPE
   SYNTAX     StorageType 
   ACCESS     read-only
   STATUS     mandatory
   DESCRIPTION
     "This variable represents the storage type value for the
      mscLpE1ChanCell tables."
::= { mscLpE1ChanCellRowStatusEntry 4 }

mscLpE1ChanCellIndex OBJECT-TYPE
   SYNTAX     NonReplicated 
   ACCESS     not-accessible
   STATUS     mandatory
   DESCRIPTION
     "This variable represents the index for the mscLpE1ChanCell tables."
::= { mscLpE1ChanCellRowStatusEntry 10 }

mscLpE1ChanCellProvTable OBJECT-TYPE
   SYNTAX     SEQUENCE OF MscLpE1ChanCellProvEntry
   ACCESS     not-accessible
   STATUS     mandatory
   DESCRIPTION
     "This group contains the provisioning attributes for the AtmCell 
      component."
::= { mscLpE1ChanCell 10 }

mscLpE1ChanCellProvEntry OBJECT-TYPE
   SYNTAX     MscLpE1ChanCellProvEntry
   ACCESS     not-accessible
   STATUS     mandatory
   DESCRIPTION
     "An entry in the mscLpE1ChanCellProvTable."
   INDEX {
      mscLpIndex,
      mscLpE1Index,
      mscLpE1ChanIndex,
      mscLpE1ChanCellIndex }
::= { mscLpE1ChanCellProvTable 1 }

MscLpE1ChanCellProvEntry ::= SEQUENCE {
   mscLpE1ChanCellAlarmActDelay
      Unsigned32,
   mscLpE1ChanCellScrambleCellPayload
      INTEGER,
   mscLpE1ChanCellCorrectSingleBitHeaderErrors
      INTEGER }

mscLpE1ChanCellAlarmActDelay OBJECT-TYPE
   SYNTAX     Unsigned32 (0..2000)
   ACCESS     read-write
   STATUS     mandatory
   DESCRIPTION
     "This attribute defines the time during which a Loss of Cell 
      Delineation (LCD) defect should be observed before declaring an 
      LCD alarm (alarm 70115501). The time is specified in milliseconds."
   DEFVAL     { 500 }
::= { mscLpE1ChanCellProvEntry 1 }

mscLpE1ChanCellScrambleCellPayload OBJECT-TYPE
   SYNTAX     INTEGER  {
                 off(0),
                 on(1) }
   ACCESS     read-write
   STATUS     mandatory
   DESCRIPTION
     "Cell scrambling, as defined by  ITU-T Recommendation I.432., can 
      provide a solution to the problem of transmission equipment which 
      is sensitive to certain bit patterns in the ATM cell payload. This 
      attribute controls whether or not the cell payload is scrambled.
      It defaults to off for DS1 interfaces, and on for all other interfaces.
      Note that this setting must be the same at both ends of the link."
::= { mscLpE1ChanCellProvEntry 2 }

mscLpE1ChanCellCorrectSingleBitHeaderErrors OBJECT-TYPE
   SYNTAX     INTEGER  {
                 off(0),
                 on(1) }
   ACCESS     read-write
   STATUS     mandatory
   DESCRIPTION
     "This attribute specifies whether the port corrects single bit errors 
      detected in the headers of received cells. If single bit errors are 
      corrected, the affected cells are passed up to the ATM layer 
      according to normal operation. If single bit errors are not corrected, 
      these errored cells are discarded by the physical layer. Note that 
      cells containing multiple bit errors in their headers are always 
      discarded.
      
      Single bit HEC error correction must remain off for the following 
      card types: 3pDS1Atm, 8pDS1Atm, 3pE1Atm, 8pE1Atm, 
      2pJ6MAtm, 3pDS3Atm, and 3pE3Atm."
   DEFVAL     { off }
::= { mscLpE1ChanCellProvEntry 3 }

mscLpE1ChanCellOperTable OBJECT-TYPE
   SYNTAX     SEQUENCE OF MscLpE1ChanCellOperEntry
   ACCESS     not-accessible
   STATUS     mandatory
   DESCRIPTION
     "This group contains the common operational attributes for the 
      AtmCell component."
::= { mscLpE1ChanCell 11 }

mscLpE1ChanCellOperEntry OBJECT-TYPE
   SYNTAX     MscLpE1ChanCellOperEntry
   ACCESS     not-accessible
   STATUS     mandatory
   DESCRIPTION
     "An entry in the mscLpE1ChanCellOperTable."
   INDEX {
      mscLpIndex,
      mscLpE1Index,
      mscLpE1ChanIndex,
      mscLpE1ChanCellIndex }
::= { mscLpE1ChanCellOperTable 1 }

MscLpE1ChanCellOperEntry ::= SEQUENCE {
   mscLpE1ChanCellLcdAlarm
      INTEGER }

mscLpE1ChanCellLcdAlarm OBJECT-TYPE
   SYNTAX     INTEGER  {
                 on(0),
                 off(1) }
   ACCESS     read-only
   STATUS     mandatory
   DESCRIPTION
     "This attribute displays whether the Loss of Cell Delineation (LCD) 
      failure alarm state has been entered. This state is entered when LCD 
      defects have been observed and accumulated for a period of time 
      specified through the alarmActDelay attribute.
      In ATM cell direct mapping mode, an LCD defect occurs when Out 
      of Cell Delineation (OCD) anomaly persists for x milliseconds, and 
      disappears when the Out of Cell Delineation (OCD) is absent for x 
      msec. An OCD anomaly occurs when 7 consecutive incorrect HECs 
      have been detected. An OCD anomaly terminates when 6 
      consecutive correct HECs have been detected.
      For an AtmCell component located under a DS3 or E3 component 
      with mapping = PLCP, the LCD defect is directly derived from the 
      PLCP LOF defect.
      If LCD defects are intermittently occurring, the LCD defect 
      accumulator is decremented at a rate of 1/10 of the incrementing 
      rate (alarm integration ratio of 1/10), with all measurements based 
      on a 200 ms polling cycle
      The component under which is located the AtmCell component goes 
      into an operational state of disabled until the LCD alarm condition 
      is cleared. The condition is cleared after the LCD defect has not 
      been reported for a period of 10 seconds +/- 0.5 seconds.
      The lcdAlarm attribute is always set to off when the parent of the 
      AtmCell component has been locked and left offline. This can also 
      happen when the Path or Channel component has been suspended 
      since its parent has been locked."
   DEFVAL     { off }
::= { mscLpE1ChanCellOperEntry 1 }

mscLpE1ChanCellStatsTable OBJECT-TYPE
   SYNTAX     SEQUENCE OF MscLpE1ChanCellStatsEntry
   ACCESS     not-accessible
   STATUS     mandatory
   DESCRIPTION
     "This group contains the Statistics attribute for the AtmCell 
      component. Each attribute type is a non-negative integer which 
      monotonically increases until it reaches a maximum value, at which 
      point it wraps around and starts increasing again from zero."
::= { mscLpE1ChanCell 12 }

mscLpE1ChanCellStatsEntry OBJECT-TYPE
   SYNTAX     MscLpE1ChanCellStatsEntry
   ACCESS     not-accessible
   STATUS     mandatory
   DESCRIPTION
     "An entry in the mscLpE1ChanCellStatsTable."
   INDEX {
      mscLpIndex,
      mscLpE1Index,
      mscLpE1ChanIndex,
      mscLpE1ChanCellIndex }
::= { mscLpE1ChanCellStatsTable 1 }

MscLpE1ChanCellStatsEntry ::= SEQUENCE {
   mscLpE1ChanCellUncorrectableHecErrors
      Counter32,
   mscLpE1ChanCellSevErroredSec
      Counter32,
   mscLpE1ChanCellReceiveCellUtilization
      Gauge32,
   mscLpE1ChanCellTransmitCellUtilization
      Gauge32,
   mscLpE1ChanCellCorrectableHeaderErrors
      Counter32 }

mscLpE1ChanCellUncorrectableHecErrors OBJECT-TYPE
   SYNTAX     Counter32 
   ACCESS     read-only
   STATUS     mandatory
   DESCRIPTION
     "This attribute indicates the number of uncorrectable ATM cell 
      header errors that have been detected. Counting of 
      uncorrectableHeaderErrors is inhibited when an Out of Cell 
      Delineation (OCD) defect is present. An OCD defect occurs when 
      seven consecutive incorrect HECs have been detected. An OCD 
      defect terminates when six consecutive correct HECs have been 
      detected."
::= { mscLpE1ChanCellStatsEntry 1 }

mscLpE1ChanCellSevErroredSec OBJECT-TYPE
   SYNTAX     Counter32 
   ACCESS     read-only
   STATUS     mandatory
   DESCRIPTION
     "This attribute indicates the total number of ATM Cell Severely 
      Errored Seconds (SESs) that have been counted. 
      
      In direct mapping mode, an ATM Cell SES is declared for second 
      intervals containing one or more Out of Cell Delineation (OCD) 
      defects. An OCD defect occurs when seven consecutive incorrect 
      HECs have been detected. An OCD defect terminates when six 
      consecutive correct HECs have been detected.
      
      In PLCP mapping mode, an ATM Cell SES is declared for second 
      intervals containing one or more PLCP LOF defects.
      
      Counting of uncorrectableHeaderErrors (ucErr) and 
      correctableHeaderErrors (cErr) is inhibited when the OCD defect 
      is present."
::= { mscLpE1ChanCellStatsEntry 2 }

mscLpE1ChanCellReceiveCellUtilization OBJECT-TYPE
   SYNTAX     Gauge32 (0..100)
   ACCESS     read-only
   STATUS     mandatory
   DESCRIPTION
     "This attribute is the ratio of the number of valid, assigned cells 
      received on the link to the nominal link capacity. The utilization is 
      calculated over a period of one minute.
      This attribute is always set to 0 when the parent of the AtmCell 
      component has been locked and left offline. This can also happen 
      when the Path or Channel component has been suspended since its 
      parent has been locked."
   DEFVAL     { 0 }
::= { mscLpE1ChanCellStatsEntry 3 }

mscLpE1ChanCellTransmitCellUtilization OBJECT-TYPE
   SYNTAX     Gauge32 (0..100)
   ACCESS     read-only
   STATUS     mandatory
   DESCRIPTION
     "This attribute is the ratio of the number of valid, assigned cells 
      transmitted on the link to the nominal link capacity. The utilization 
      is calculated over a period of one minute.
      This attribute is always set to 0 when the parent of the AtmCell 
      component has been locked and left offline. This can also happen 
      when the Path or Channel component has been suspended since its 
      parent has been locked."
   DEFVAL     { 0 }
::= { mscLpE1ChanCellStatsEntry 4 }

mscLpE1ChanCellCorrectableHeaderErrors OBJECT-TYPE
   SYNTAX     Counter32 
   ACCESS     read-only
   STATUS     mandatory
   DESCRIPTION
     "This attribute indicates the number of correctable ATM cell header 
      errors that have been detected and corrected. Counting of 
      correctableHeaderErrors is inhibited when an Out of Cell 
      Delineation (OCD) defect is present. An OCD defect occurs when 
      seven consecutive incorrect HECs have been detected. An OCD 
      defect terminates when six consecutive correct HECs have been 
      detected"
::= { mscLpE1ChanCellStatsEntry 5 }


-- Lp/x Ds1/y Chan/z Tc
-- Lp/x E1/y Chan/z Tc
-- 
-- The Tc component is used to provision and monitor trunk 
-- conditioning options. A separate instance of this component is 
-- required for each Chan on a Port which is offering a structured 
-- constant bit rate service.
-- 
-- Under certain failure alarm conditions, trunk conditioning 
-- replacementData is substituted into the timeslots as defined by the 
-- Chan component. Trunk conditioning signaling is also substituted 
-- into the appropriate Channel Associated Signaling (CAS) bits when 
-- a lineType that uses CAS has been defined.
-- 
-- When used with AAL1 Circuit Emulation Service, trunk 
-- conditioning is transmitted towards the ATM network under the 
-- following conditions:
-- lossOfSignal (LOS)
-- lossOfFrame (LOF)
-- remoteAlarmIndication (RAI)
-- alarmIndicationSignal (AIS)
-- bufferUnderflow (BU)
-- and in addition for E1:
-- lossOfMultiframe (LOMF)
-- receiveMultiframeRemoteAlarmIndication (RMRAI)
-- 
-- When used with AAL1 Circuit Emulation Service, trunk 
-- conditioning is transmitted towards the PDH network under the 
-- following conditions:
-- bufferUnderflow (BU)
-- AAL1 protocol errors.
-- 

mscLpE1ChanTc OBJECT IDENTIFIER ::= { mscLpE1Chan 4 }



mscLpE1ChanTcRowStatusTable OBJECT-TYPE
   SYNTAX     SEQUENCE OF MscLpE1ChanTcRowStatusEntry
   ACCESS     not-accessible
   STATUS     mandatory
   DESCRIPTION
     "This entry controls the addition and deletion of 
      mscLpE1ChanTc components."
::= { mscLpE1ChanTc 1 }

mscLpE1ChanTcRowStatusEntry OBJECT-TYPE
   SYNTAX     MscLpE1ChanTcRowStatusEntry
   ACCESS     not-accessible
   STATUS     mandatory
   DESCRIPTION
     "A single entry in the table represents a single 
      mscLpE1ChanTc component."
   INDEX {
      mscLpIndex,
      mscLpE1Index,
      mscLpE1ChanIndex,
      mscLpE1ChanTcIndex }
::= { mscLpE1ChanTcRowStatusTable 1 }

MscLpE1ChanTcRowStatusEntry ::= SEQUENCE {
   mscLpE1ChanTcRowStatus
      RowStatus,
   mscLpE1ChanTcComponentName
      DisplayString,
   mscLpE1ChanTcStorageType
      StorageType,
   mscLpE1ChanTcIndex
      NonReplicated }

mscLpE1ChanTcRowStatus OBJECT-TYPE
   SYNTAX     RowStatus 
   ACCESS     read-write
   STATUS     mandatory
   DESCRIPTION
     "This variable is used as the basis for SNMP naming of
      mscLpE1ChanTc components.
      These components can be added and deleted."
::= { mscLpE1ChanTcRowStatusEntry 1 }

mscLpE1ChanTcComponentName OBJECT-TYPE
   SYNTAX     DisplayString 
   ACCESS     read-only
   STATUS     mandatory
   DESCRIPTION
     "This variable provides the component's string name for
      use with the ASCII Console Interface"
::= { mscLpE1ChanTcRowStatusEntry 2 }

mscLpE1ChanTcStorageType OBJECT-TYPE
   SYNTAX     StorageType 
   ACCESS     read-only
   STATUS     mandatory
   DESCRIPTION
     "This variable represents the storage type value for the
      mscLpE1ChanTc tables."
::= { mscLpE1ChanTcRowStatusEntry 4 }

mscLpE1ChanTcIndex OBJECT-TYPE
   SYNTAX     NonReplicated 
   ACCESS     not-accessible
   STATUS     mandatory
   DESCRIPTION
     "This variable represents the index for the mscLpE1ChanTc tables."
::= { mscLpE1ChanTcRowStatusEntry 10 }

mscLpE1ChanTcProvTable OBJECT-TYPE
   SYNTAX     SEQUENCE OF MscLpE1ChanTcProvEntry
   ACCESS     not-accessible
   STATUS     mandatory
   DESCRIPTION
     "This group contains all specific provisioning data for a Tc 
      component."
::= { mscLpE1ChanTc 10 }

mscLpE1ChanTcProvEntry OBJECT-TYPE
   SYNTAX     MscLpE1ChanTcProvEntry
   ACCESS     not-accessible
   STATUS     mandatory
   DESCRIPTION
     "An entry in the mscLpE1ChanTcProvTable."
   INDEX {
      mscLpIndex,
      mscLpE1Index,
      mscLpE1ChanIndex,
      mscLpE1ChanTcIndex }
::= { mscLpE1ChanTcProvTable 1 }

MscLpE1ChanTcProvEntry ::= SEQUENCE {
   mscLpE1ChanTcReplacementData
      Hex,
   mscLpE1ChanTcSignalOneDuration
      Unsigned32 }

mscLpE1ChanTcReplacementData OBJECT-TYPE
   SYNTAX     Hex (0..255)
   ACCESS     read-write
   STATUS     mandatory
   DESCRIPTION
     "This attribute specifies the trunk conditioning data byte to be 
      substituted into the timeslots defined by the Chan component under 
      fault conditions. 
      
      replacementData can be set to any two digit hexadecimal number. 
      The following are recommended values:
      DS1 MUX Out Of Service Code = 0x1A
      E1 MUX Out Of Service Code = 0xFF"
   DEFVAL     { 255 }
::= { mscLpE1ChanTcProvEntry 1 }

mscLpE1ChanTcSignalOneDuration OBJECT-TYPE
   SYNTAX     Unsigned32 (0..60)
   ACCESS     read-write
   STATUS     mandatory
   DESCRIPTION
     "This attribute specifies the time duration in seconds for which 
      signalOne is substituted into the appropriate signaling bits, when a 
      lineType that uses CAS has been defined. When signalOneDuration 
      has expired signalTwo is substituted into the appropriate signaling 
      bits.
      
      If signalOneDuration is set to zero then only signalTwo is 
      substituted into the appropriate signaling bits during error 
      conditions.
      
      signalOneDuration can be set to any integer value from 0 to 60 
      seconds."
   DEFVAL     { 0 }
::= { mscLpE1ChanTcProvEntry 2 }

mscLpE1ChanTcOpTable OBJECT-TYPE
   SYNTAX     SEQUENCE OF MscLpE1ChanTcOpEntry
   ACCESS     not-accessible
   STATUS     mandatory
   DESCRIPTION
     "This group contains all specific operational data for a Tc 
      component."
::= { mscLpE1ChanTc 11 }

mscLpE1ChanTcOpEntry OBJECT-TYPE
   SYNTAX     MscLpE1ChanTcOpEntry
   ACCESS     not-accessible
   STATUS     mandatory
   DESCRIPTION
     "An entry in the mscLpE1ChanTcOpTable."
   INDEX {
      mscLpIndex,
      mscLpE1Index,
      mscLpE1ChanIndex,
      mscLpE1ChanTcIndex }
::= { mscLpE1ChanTcOpTable 1 }

MscLpE1ChanTcOpEntry ::= SEQUENCE {
   mscLpE1ChanTcIngressConditioning
      INTEGER,
   mscLpE1ChanTcEgressConditioning
      INTEGER }

mscLpE1ChanTcIngressConditioning OBJECT-TYPE
   SYNTAX     INTEGER  {
                 off(0),
                 on(1) }
   ACCESS     read-only
   STATUS     mandatory
   DESCRIPTION
     "This attribute indicates the status of locally generated trunk 
      conditioning towards the ATM network.
      
      When trunk conditioning is being locally generated towards the 
      ATM network, ingressConditioning is set to on.
      
      When trunk conditioning is not being locally generated towards the 
      ATM network, ingressConditioning is set to off.
      
      Trunk conditioning is transmitted towards the ATM network under 
      the following conditions:
      lossOfSignal (LOS)
      lossOfFrame (LOF)
      remoteAlarmIndication (RAI)
      alarmIndicationSignal (AIS)
      bufferUnderflow (BU)
      and in addition for E1:
      lossOfMultiframe (LOMF)
      receiveMultiframeRemoteAlarmIndication (RMRAI)"
   DEFVAL     { off }
::= { mscLpE1ChanTcOpEntry 1 }

mscLpE1ChanTcEgressConditioning OBJECT-TYPE
   SYNTAX     INTEGER  {
                 off(0),
                 on(1) }
   ACCESS     read-only
   STATUS     mandatory
   DESCRIPTION
     "This attribute indicates the status of locally generated trunk 
      conditioning towards the PDH line.
      
      When trunk conditioning is being locally generated towards the 
      PDH line, egressConditioning is set to on.
      
      When trunk conditioning is not being locally generated towards the 
      PDH line, egressConditioning is set to off.
      
      Trunk conditioning is transmitted towards the PDH line under the 
      following conditions:
      bufferUnderflow (BU)
      AAL1 protocol errors."
   DEFVAL     { off }
::= { mscLpE1ChanTcOpEntry 2 }

mscLpE1ChanTcSigOneTable OBJECT-TYPE
   SYNTAX     SEQUENCE OF MscLpE1ChanTcSigOneEntry
   ACCESS     not-accessible
   STATUS     mandatory
   DESCRIPTION
     "This attribute specifies the value to be substituted into the ABCD 
      signaling bits for the timeslots defined by the Chan component 
      under fault conditions. The value will be substituted for the duration 
      provisioned in signalOneDuration when a lineType that uses CAS 
      has been defined. 
      
      For a lineType of d4Cas (Super Frame), signaling bits C and D are 
      required to equal bits A and B respectively."
::= { mscLpE1ChanTc 398 }

mscLpE1ChanTcSigOneEntry OBJECT-TYPE
   SYNTAX     MscLpE1ChanTcSigOneEntry
   ACCESS     not-accessible
   STATUS     mandatory
   DESCRIPTION
     "An entry in the mscLpE1ChanTcSigOneTable."
   INDEX {
      mscLpIndex,
      mscLpE1Index,
      mscLpE1ChanIndex,
      mscLpE1ChanTcIndex,
      mscLpE1ChanTcSigOneIndex }
::= { mscLpE1ChanTcSigOneTable 1 }

MscLpE1ChanTcSigOneEntry ::= SEQUENCE {
   mscLpE1ChanTcSigOneIndex
      INTEGER,
   mscLpE1ChanTcSigOneValue
      Unsigned32 }

mscLpE1ChanTcSigOneIndex OBJECT-TYPE
   SYNTAX     INTEGER  {
                 d(0),
                 c(1),
                 b(2),
                 a(3) }
   ACCESS     not-accessible
   STATUS     mandatory
   DESCRIPTION
     "This variable represents the mscLpE1ChanTcSigOneTable
      specific index for the mscLpE1ChanTcSigOneTable."
::= { mscLpE1ChanTcSigOneEntry 1 }

mscLpE1ChanTcSigOneValue OBJECT-TYPE
   SYNTAX     Unsigned32 (0..1)
   ACCESS     read-write
   STATUS     mandatory
   DESCRIPTION
     "This variable represents an individual value for the
      mscLpE1ChanTcSigOneTable."
::= { mscLpE1ChanTcSigOneEntry 2 }

mscLpE1ChanTcSigTwoTable OBJECT-TYPE
   SYNTAX     SEQUENCE OF MscLpE1ChanTcSigTwoEntry
   ACCESS     not-accessible
   STATUS     mandatory
   DESCRIPTION
     "This attribute specifies the value to be substituted into the ABCD 
      signaling bits for the timeslots defined by the Chan component 
      under fault conditions. The value will be substituted after the 
      duration provisioned in signalOneDuration has expired and when a 
      lineType that uses CAS has been defined. 
      
      For a lineType of d4Cas (Super Frame), signaling bits C and D are 
      required to equal bits A and B respectively."
::= { mscLpE1ChanTc 399 }

mscLpE1ChanTcSigTwoEntry OBJECT-TYPE
   SYNTAX     MscLpE1ChanTcSigTwoEntry
   ACCESS     not-accessible
   STATUS     mandatory
   DESCRIPTION
     "An entry in the mscLpE1ChanTcSigTwoTable."
   INDEX {
      mscLpIndex,
      mscLpE1Index,
      mscLpE1ChanIndex,
      mscLpE1ChanTcIndex,
      mscLpE1ChanTcSigTwoIndex }
::= { mscLpE1ChanTcSigTwoTable 1 }

MscLpE1ChanTcSigTwoEntry ::= SEQUENCE {
   mscLpE1ChanTcSigTwoIndex
      INTEGER,
   mscLpE1ChanTcSigTwoValue
      Unsigned32 }

mscLpE1ChanTcSigTwoIndex OBJECT-TYPE
   SYNTAX     INTEGER  {
                 d(0),
                 c(1),
                 b(2),
                 a(3) }
   ACCESS     not-accessible
   STATUS     mandatory
   DESCRIPTION
     "This variable represents the mscLpE1ChanTcSigTwoTable
      specific index for the mscLpE1ChanTcSigTwoTable."
::= { mscLpE1ChanTcSigTwoEntry 1 }

mscLpE1ChanTcSigTwoValue OBJECT-TYPE
   SYNTAX     Unsigned32 (0..1)
   ACCESS     read-write
   STATUS     mandatory
   DESCRIPTION
     "This variable represents an individual value for the
      mscLpE1ChanTcSigTwoTable."
::= { mscLpE1ChanTcSigTwoEntry 2 }


-- Lp/n E1/n Chan/n FrameLinkMonitoring
-- 
-- This component provides a monitoring function specific to a Frame 
-- Relay Channel n an E1 line. It combines the status of E1 channel-
-- associated-signalling A-bits and HDLC frame defect. 

mscLpE1ChanFlm OBJECT IDENTIFIER ::= { mscLpE1Chan 5 }



mscLpE1ChanFlmRowStatusTable OBJECT-TYPE
   SYNTAX     SEQUENCE OF MscLpE1ChanFlmRowStatusEntry
   ACCESS     not-accessible
   STATUS     mandatory
   DESCRIPTION
     "This entry controls the addition and deletion of 
      mscLpE1ChanFlm components."
::= { mscLpE1ChanFlm 1 }

mscLpE1ChanFlmRowStatusEntry OBJECT-TYPE
   SYNTAX     MscLpE1ChanFlmRowStatusEntry
   ACCESS     not-accessible
   STATUS     mandatory
   DESCRIPTION
     "A single entry in the table represents a single 
      mscLpE1ChanFlm component."
   INDEX {
      mscLpIndex,
      mscLpE1Index,
      mscLpE1ChanIndex,
      mscLpE1ChanFlmIndex }
::= { mscLpE1ChanFlmRowStatusTable 1 }

MscLpE1ChanFlmRowStatusEntry ::= SEQUENCE {
   mscLpE1ChanFlmRowStatus
      RowStatus,
   mscLpE1ChanFlmComponentName
      DisplayString,
   mscLpE1ChanFlmStorageType
      StorageType,
   mscLpE1ChanFlmIndex
      NonReplicated }

mscLpE1ChanFlmRowStatus OBJECT-TYPE
   SYNTAX     RowStatus 
   ACCESS     read-write
   STATUS     mandatory
   DESCRIPTION
     "This variable is used as the basis for SNMP naming of
      mscLpE1ChanFlm components.
      These components can be added and deleted."
::= { mscLpE1ChanFlmRowStatusEntry 1 }

mscLpE1ChanFlmComponentName OBJECT-TYPE
   SYNTAX     DisplayString 
   ACCESS     read-only
   STATUS     mandatory
   DESCRIPTION
     "This variable provides the component's string name for
      use with the ASCII Console Interface"
::= { mscLpE1ChanFlmRowStatusEntry 2 }

mscLpE1ChanFlmStorageType OBJECT-TYPE
   SYNTAX     StorageType 
   ACCESS     read-only
   STATUS     mandatory
   DESCRIPTION
     "This variable represents the storage type value for the
      mscLpE1ChanFlm tables."
::= { mscLpE1ChanFlmRowStatusEntry 4 }

mscLpE1ChanFlmIndex OBJECT-TYPE
   SYNTAX     NonReplicated 
   ACCESS     not-accessible
   STATUS     mandatory
   DESCRIPTION
     "This variable represents the index for the mscLpE1ChanFlm tables."
::= { mscLpE1ChanFlmRowStatusEntry 10 }

mscLpE1ChanFlmProvTable OBJECT-TYPE
   SYNTAX     SEQUENCE OF MscLpE1ChanFlmProvEntry
   ACCESS     not-accessible
   STATUS     mandatory
   DESCRIPTION
     "This group contains all specific provisioning data for an Flm 
      component."
::= { mscLpE1ChanFlm 10 }

mscLpE1ChanFlmProvEntry OBJECT-TYPE
   SYNTAX     MscLpE1ChanFlmProvEntry
   ACCESS     not-accessible
   STATUS     mandatory
   DESCRIPTION
     "An entry in the mscLpE1ChanFlmProvTable."
   INDEX {
      mscLpIndex,
      mscLpE1Index,
      mscLpE1ChanIndex,
      mscLpE1ChanFlmIndex }
::= { mscLpE1ChanFlmProvTable 1 }

MscLpE1ChanFlmProvEntry ::= SEQUENCE {
   mscLpE1ChanFlmABitMonitoring
      INTEGER,
   mscLpE1ChanFlmHdlcMonitoring
      INTEGER }

mscLpE1ChanFlmABitMonitoring OBJECT-TYPE
   SYNTAX     INTEGER  {
                 disabled(0),
                 enabled(1) }
   ACCESS     read-write
   STATUS     mandatory
   DESCRIPTION
     "This attribute controls the monitoring of A-bit defects."
   DEFVAL     { enabled }
::= { mscLpE1ChanFlmProvEntry 1 }

mscLpE1ChanFlmHdlcMonitoring OBJECT-TYPE
   SYNTAX     INTEGER  {
                 disabled(0),
                 enabled(1) }
   ACCESS     read-write
   STATUS     mandatory
   DESCRIPTION
     "This attribute controls the monitoring of HDLC defect."
   DEFVAL     { enabled }
::= { mscLpE1ChanFlmProvEntry 2 }

mscLpE1ChanFlmOpTable OBJECT-TYPE
   SYNTAX     SEQUENCE OF MscLpE1ChanFlmOpEntry
   ACCESS     not-accessible
   STATUS     mandatory
   DESCRIPTION
     "This group contains all specific operational data for an Flm
      component."
::= { mscLpE1ChanFlm 11 }

mscLpE1ChanFlmOpEntry OBJECT-TYPE
   SYNTAX     MscLpE1ChanFlmOpEntry
   ACCESS     not-accessible
   STATUS     mandatory
   DESCRIPTION
     "An entry in the mscLpE1ChanFlmOpTable."
   INDEX {
      mscLpIndex,
      mscLpE1Index,
      mscLpE1ChanIndex,
      mscLpE1ChanFlmIndex }
::= { mscLpE1ChanFlmOpTable 1 }

MscLpE1ChanFlmOpEntry ::= SEQUENCE {
   mscLpE1ChanFlmFlmStatus
      INTEGER }

mscLpE1ChanFlmFlmStatus OBJECT-TYPE
   SYNTAX     INTEGER  {
                 notMonitoring(0),
                 frameLinkUp(1),
                 frameLinkDown(2),
                 lossOfHdlc(3),
                 lossOfAbit(4) }
   ACCESS     read-only
   STATUS     mandatory
   DESCRIPTION
     "This attribute indicates the status of a Frame Relay channel on an 
      E1 line. By combining the E1 channel-associated-signalling (CAS) 
      A-bits status, and HDLC defect, a single value indicates the likely 
      cause of the failure. This mechanism assumes that the far end 
      equipment loops back signaling A-bits for some or all of the 
      timeslots in a channel. The A-bits in channel are transmitted as '0'. 
      If they are all received as '0', it is assumed that the E1 link is up in 
      both directions. The presence of HDLC frames indicates that the 
      service is connected. 
      
      When A-bits and HDLC frames are correctly received, 
      frameLinkUp is indicated. 
      
      When neither are received, frameLinkDown is indicated. 
      
      When HDLC frames are not receive but A-bits are not at fault,
      lossOfHdlc is indicated. 
      
      When HDLC frames are received, but there is a fault in the any of 
      timeslot's A-bits on a channel lossOfAbit is indicated."
::= { mscLpE1ChanFlmOpEntry 1 }


-- 
-- The Test component is configured to control a hardware facility test 
-- on a physical (V35, X21, DS1, E1, DS3, E3 etc.) or a logical port.

mscLpE1Test OBJECT IDENTIFIER ::= { mscLpE1 3 }



mscLpE1TestRowStatusTable OBJECT-TYPE
   SYNTAX     SEQUENCE OF MscLpE1TestRowStatusEntry
   ACCESS     not-accessible
   STATUS     mandatory
   DESCRIPTION
     "This entry controls the addition and deletion of 
      mscLpE1Test components."
::= { mscLpE1Test 1 }

mscLpE1TestRowStatusEntry OBJECT-TYPE
   SYNTAX     MscLpE1TestRowStatusEntry
   ACCESS     not-accessible
   STATUS     mandatory
   DESCRIPTION
     "A single entry in the table represents a single 
      mscLpE1Test component."
   INDEX {
      mscLpIndex,
      mscLpE1Index,
      mscLpE1TestIndex }
::= { mscLpE1TestRowStatusTable 1 }

MscLpE1TestRowStatusEntry ::= SEQUENCE {
   mscLpE1TestRowStatus
      RowStatus,
   mscLpE1TestComponentName
      DisplayString,
   mscLpE1TestStorageType
      StorageType,
   mscLpE1TestIndex
      NonReplicated }

mscLpE1TestRowStatus OBJECT-TYPE
   SYNTAX     RowStatus 
   ACCESS     read-only
   STATUS     mandatory
   DESCRIPTION
     "This variable is used as the basis for SNMP naming of
      mscLpE1Test components.
      These components cannot be added nor deleted."
::= { mscLpE1TestRowStatusEntry 1 }

mscLpE1TestComponentName OBJECT-TYPE
   SYNTAX     DisplayString 
   ACCESS     read-only
   STATUS     mandatory
   DESCRIPTION
     "This variable provides the component's string name for
      use with the ASCII Console Interface"
::= { mscLpE1TestRowStatusEntry 2 }

mscLpE1TestStorageType OBJECT-TYPE
   SYNTAX     StorageType 
   ACCESS     read-only
   STATUS     mandatory
   DESCRIPTION
     "This variable represents the storage type value for the
      mscLpE1Test tables."
::= { mscLpE1TestRowStatusEntry 4 }

mscLpE1TestIndex OBJECT-TYPE
   SYNTAX     NonReplicated 
   ACCESS     not-accessible
   STATUS     mandatory
   DESCRIPTION
     "This variable represents the index for the mscLpE1Test tables."
::= { mscLpE1TestRowStatusEntry 10 }

mscLpE1TestStateTable OBJECT-TYPE
   SYNTAX     SEQUENCE OF MscLpE1TestStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscLpE1Test 10 }

mscLpE1TestStateEntry OBJECT-TYPE
   SYNTAX     MscLpE1TestStateEntry
   ACCESS     not-accessible
   STATUS     mandatory
   DESCRIPTION
     "An entry in the mscLpE1TestStateTable."
   INDEX {
      mscLpIndex,
      mscLpE1Index,
      mscLpE1TestIndex }
::= { mscLpE1TestStateTable 1 }

MscLpE1TestStateEntry ::= SEQUENCE {
   mscLpE1TestAdminState
      INTEGER,
   mscLpE1TestOperationalState
      INTEGER,
   mscLpE1TestUsageState
      INTEGER }

mscLpE1TestAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscLpE1TestStateEntry 1 }

mscLpE1TestOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscLpE1TestStateEntry 2 }

mscLpE1TestUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscLpE1TestStateEntry 3 }

mscLpE1TestSetupTable OBJECT-TYPE
   SYNTAX     SEQUENCE OF MscLpE1TestSetupEntry
   ACCESS     not-accessible
   STATUS     mandatory
   DESCRIPTION
     "This group contains all of the operational data for a Test 
      component."
::= { mscLpE1Test 11 }

mscLpE1TestSetupEntry OBJECT-TYPE
   SYNTAX     MscLpE1TestSetupEntry
   ACCESS     not-accessible
   STATUS     mandatory
   DESCRIPTION
     "An entry in the mscLpE1TestSetupTable."
   INDEX {
      mscLpIndex,
      mscLpE1Index,
      mscLpE1TestIndex }
::= { mscLpE1TestSetupTable 1 }

MscLpE1TestSetupEntry ::= SEQUENCE {
   mscLpE1TestPurpose
      AsciiString,
   mscLpE1TestType
      INTEGER,
   mscLpE1TestFrmSize
      Unsigned32,
   mscLpE1TestFrmPatternType
      INTEGER,
   mscLpE1TestCustomizedPattern
      Hex,
   mscLpE1TestDataStartDelay
      Unsigned32,
   mscLpE1TestDisplayInterval
      Unsigned32,
   mscLpE1TestDuration
      Unsigned32 }

mscLpE1TestPurpose OBJECT-TYPE
   SYNTAX     AsciiString (SIZE (0..40))
   ACCESS     read-write
   STATUS     mandatory
   DESCRIPTION
     "This attribute records the purpose of the test so that the test results 
      can be associated and properly analyzed."
::= { mscLpE1TestSetupEntry 1 }

mscLpE1TestType OBJECT-TYPE
   SYNTAX     INTEGER  {
                 card(0),
                 manual(1),
                 localLoop(2),
                 remoteLoop(3),
                 externalLoop(4),
                 payloadLoop(5),
                 remoteLoopThisTrib(6),
                 v54RemoteLoop(7),
                 pn127RemoteLoop(8) }
   ACCESS     read-write
   STATUS     mandatory
   DESCRIPTION
     "This attribute is the type of test to be run. The available test types 
      include the following:
      card test sets up an internal loop on the board and runs a bit error 
      rate test.
      manual test assumes the line is looped back externally and a bit 
      error rate test is performed.
      localLoop test loops back the local modem and performs a bit error 
      rate test.
      remoteLoop test loops back the remote modem (or CSU) and 
      performs a bit error rate test.
      externalLoop test loops back the line to the far end.
      payloadLoop test only loops back the payload data received from 
      the incoming line.
      remoteLoopThisTrib loops this particular tributary back at the far 
      end, using services provided by the parent.
      v54RemoteLoop initiates a V.54 Remote Loopback test.
      pn127RemoteLoop initiates a PN127 Remote Loopback test.
      Note that not all test types are not supported by all function 
      processors."
   DEFVAL     { card }
::= { mscLpE1TestSetupEntry 2 }

mscLpE1TestFrmSize OBJECT-TYPE
   SYNTAX     Unsigned32 (4..4096)
   ACCESS     read-write
   STATUS     mandatory
   DESCRIPTION
     "This attribute defines the size of the test data frames in number of 
      bytes."
   DEFVAL     { 1024 }
::= { mscLpE1TestSetupEntry 3 }

mscLpE1TestFrmPatternType OBJECT-TYPE
   SYNTAX     INTEGER  {
                 ccitt32kBitPattern(0),
                 ccitt8MBitPattern(1),
                 customizedPattern(2) }
   ACCESS     read-write
   STATUS     mandatory
   DESCRIPTION
     "This attribute defines the type of data pattern generation to use. The 
      following lists the available pattern types:
      ccitt32kBitPattern is a pseudo-random sequence of 32 kbit.
      ccitt8MBitPattern is a pseudo-random sequence of 8Mbit.
      customizedPattern is the pattern defined in the customizedPattern 
      attribute."
   DEFVAL     { ccitt32kBitPattern }
::= { mscLpE1TestSetupEntry 4 }

mscLpE1TestCustomizedPattern OBJECT-TYPE
   SYNTAX     Hex (0..4294967295)
   ACCESS     read-write
   STATUS     mandatory
   DESCRIPTION
     "This attribute allows a customized 32 bit pattern to be defined for 
      use in the test data frames. This attribute is used when the attribute 
      frmPatternType is set to CustomizedPattern. Note that a 55 hex 
      pattern is an alternating 1 and 0 pattern."
   DEFVAL     { 1431655765 }
::= { mscLpE1TestSetupEntry 5 }

mscLpE1TestDataStartDelay OBJECT-TYPE
   SYNTAX     Unsigned32 (0..1814400)
   ACCESS     read-write
   STATUS     mandatory
   DESCRIPTION
     "This attribute specifies the time delay (in seconds) between when 
      the test expects the loop to have been set up, to when the test data 
      actually starts to be transmitted. This attribute is to accommodate 
      some non-standard equipment that requires extra time for setting up 
      a requested loop.
      This attribute is ignored when the test type is set to externalLoop."
   DEFVAL     { 0 }
::= { mscLpE1TestSetupEntry 6 }

mscLpE1TestDisplayInterval OBJECT-TYPE
   SYNTAX     Unsigned32 (0..30240)
   ACCESS     read-write
   STATUS     mandatory
   DESCRIPTION
     "This attribute defines the interval (in minutes) between which 
      interim test results are to be displayed. Results are displayed at the 
      operator console at which the test was started. When the test type is 
      set to externalLoop, this attribute is ignored. There will be no 
      display of results if displayInterval is set to 0. This attribute can be 
      changed anytime."
   DEFVAL     { 5 }
::= { mscLpE1TestSetupEntry 7 }

mscLpE1TestDuration OBJECT-TYPE
   SYNTAX     Unsigned32 (1..30240)
   ACCESS     read-write
   STATUS     mandatory
   DESCRIPTION
     "This attribute is the duration (in minutes) that test data will be 
      transmitted. In the case of an externalLoop, this is the time that the 
      loop is in effect. Note that dataStartDelay does not apply to the 
      externalLoop."
   DEFVAL     { 1 }
::= { mscLpE1TestSetupEntry 8 }

mscLpE1TestResultsTable OBJECT-TYPE
   SYNTAX     SEQUENCE OF MscLpE1TestResultsEntry
   ACCESS     not-accessible
   STATUS     mandatory
   DESCRIPTION
     "This group contains all the statistics related attributes of the Test 
      component."
::= { mscLpE1Test 12 }

mscLpE1TestResultsEntry OBJECT-TYPE
   SYNTAX     MscLpE1TestResultsEntry
   ACCESS     not-accessible
   STATUS     mandatory
   DESCRIPTION
     "An entry in the mscLpE1TestResultsTable."
   INDEX {
      mscLpIndex,
      mscLpE1Index,
      mscLpE1TestIndex }
::= { mscLpE1TestResultsTable 1 }

MscLpE1TestResultsEntry ::= SEQUENCE {
   mscLpE1TestElapsedTime
      Counter32,
   mscLpE1TestTimeRemaining
      Unsigned32,
   mscLpE1TestCauseOfTermination
      INTEGER,
   mscLpE1TestBitsTx
      PassportCounter64,
   mscLpE1TestBytesTx
      PassportCounter64,
   mscLpE1TestFrmTx
      PassportCounter64,
   mscLpE1TestBitsRx
      PassportCounter64,
   mscLpE1TestBytesRx
      PassportCounter64,
   mscLpE1TestFrmRx
      PassportCounter64,
   mscLpE1TestErroredFrmRx
      PassportCounter64,
   mscLpE1TestBitErrorRate
      AsciiString }

mscLpE1TestElapsedTime OBJECT-TYPE
   SYNTAX     Counter32 
   ACCESS     read-only
   STATUS     mandatory
   DESCRIPTION
     "This attribute is the number of minutes elapsed since the test started 
      for an externalLoop test. For a data test, this is the time since test 
      data was first transmitted."
::= { mscLpE1TestResultsEntry 1 }

mscLpE1TestTimeRemaining OBJECT-TYPE
   SYNTAX     Unsigned32 (0..4294967295)
   ACCESS     read-only
   STATUS     mandatory
   DESCRIPTION
     "This attribute is the number of minutes remaining before the test is 
      to be stopped according to the duration attribute."
   DEFVAL     { 0 }
::= { mscLpE1TestResultsEntry 2 }

mscLpE1TestCauseOfTermination OBJECT-TYPE
   SYNTAX     INTEGER  {
                 testTimeExpired(0),
                 stoppedByOperator(1),
                 unknown(2),
                 neverStarted(3),
                 testRunning(4),
                 hardwareReconfigured(5),
                 loopCodeSyncFailed(6),
                 patternSyncFailed(7),
                 patternSyncLost(8) }
   ACCESS     read-only
   STATUS     mandatory
   DESCRIPTION
     "This attribute indicates either the status of the test or the cause of 
      the test's termination:
      
      neverStarted indicates that the test has not yet been started.
      
      testRunning indicates that the test has been started.
      
      stoppedByOperator indicates that the operator issued a stop 
      command on a test that was running.
      
      testTimeExpired indicates that the test ran for the time specified by 
      the test's duration.
      
      loopCodeSyncFailed indicates that the local end failed to 
      synchronize to the loopCode pattern. The local end transmits the 
      loopCode pattern to cause the remote end to apply a loopback, after 
      which the local end should receive the loopCode pattern. The exact 
      pattern used to request loopCode depends on the test type. This 
      failure indicates a high rate of transmission errors, or that the 
      remote end has failed to apply the loopback.
      
      patternSyncFailed indicates that the local end failed to synchronize 
      to the frmPatternType test pattern, that should have been looped 
      back at the remote end. This failure indicates a high rate of 
      transmission errors or the absence of a loopback.
      
      patternSyncLost indicates that the local end gained and then lost 
      synchronization to the returned frmPatternType test pattern. This 
      failure indicates a sudden increase in transmission errors, frame 
      slippage, or the removal of an existing loopback.
      
      unknown is set when a reason to terminate other than those listed 
      here is encountered.
      
      Note: Only MSA cards support recognition of the failures 
      loopCodeSyncFailed, patternSyncFailed and patternSyncLost. 
      Other cards will not terminate the test under the conditions 
      described by these values."
   DEFVAL     { neverStarted }
::= { mscLpE1TestResultsEntry 3 }

mscLpE1TestBitsTx OBJECT-TYPE
   SYNTAX     PassportCounter64 
   ACCESS     read-only
   STATUS     mandatory
   DESCRIPTION
     "This attribute is the total number of bits sent during the test period. 
      As long as the line speed of the hardware interface is less than 
      70 Mbit/s, this counter is not expected to reach the maximum value."
::= { mscLpE1TestResultsEntry 4 }

mscLpE1TestBytesTx OBJECT-TYPE
   SYNTAX     PassportCounter64 
   ACCESS     read-only
   STATUS     mandatory
   DESCRIPTION
     "This attribute is the total number of bytes sent during the test 
      period. This counter is not expected to reach its maximum value."
::= { mscLpE1TestResultsEntry 5 }

mscLpE1TestFrmTx OBJECT-TYPE
   SYNTAX     PassportCounter64 
   ACCESS     read-only
   STATUS     mandatory
   DESCRIPTION
     "This attribute is the total number of frames sent during the test 
      period. This counter is not expected to reach its maximum value."
::= { mscLpE1TestResultsEntry 6 }

mscLpE1TestBitsRx OBJECT-TYPE
   SYNTAX     PassportCounter64 
   ACCESS     read-only
   STATUS     mandatory
   DESCRIPTION
     "This attribute is the total number of bits received during the test 
      period. This counter is not expected to reach its maximum value. 
      The counter will wrap around to 0 if it does reach the maximum 
      value."
::= { mscLpE1TestResultsEntry 7 }

mscLpE1TestBytesRx OBJECT-TYPE
   SYNTAX     PassportCounter64 
   ACCESS     read-only
   STATUS     mandatory
   DESCRIPTION
     "This attribute is the total number of bytes received during the test 
      period. This counter is not expected to reach its maximum value. 
      The counter will wrap around to 0 if it does reach its maximum 
      value."
::= { mscLpE1TestResultsEntry 8 }

mscLpE1TestFrmRx OBJECT-TYPE
   SYNTAX     PassportCounter64 
   ACCESS     read-only
   STATUS     mandatory
   DESCRIPTION
     "This attribute is the total number of frames received during the test 
      period. This counter is not expected to reach its maximum value. 
      The counter will wrap around to 0 if it does reach its maximum 
      value."
::= { mscLpE1TestResultsEntry 9 }

mscLpE1TestErroredFrmRx OBJECT-TYPE
   SYNTAX     PassportCounter64 
   ACCESS     read-only
   STATUS     mandatory
   DESCRIPTION
     "This attribute is not displayed for ATM cards because the physical 
      layer drops all errored frames at the controller interface. 
      
      For all other card types, this attribute is the total number of errored 
      frames received during the test period. This counter is not expected 
      to reach its maximum value. The counter will wrap around to 0 if it 
      does reach its maximum value."
::= { mscLpE1TestResultsEntry 10 }

mscLpE1TestBitErrorRate OBJECT-TYPE
   SYNTAX     AsciiString (SIZE (5))
   ACCESS     read-only
   STATUS     mandatory
   DESCRIPTION
     "This attribute is not displayed for ATM cards because the physical 
      layer drops all errored frames at the controller interface. 
      
      For all other card types, this attribute is the calculated bit error rate 
      on the link. Test data are generated and sent in frames of a preset 
      size (frameSize). The Test component will try to estimate the 
      number of bit errors in any errored frame which is identifiable. The 
      statistics will be updated accordingly. A lost frame (may be due to 
      an error on the flag sequence) will be discarded for the bit error rate 
      calculation. The result is presented in the form of xEsyy, where x is 
      the mantissa, syy is the exponent, for example 0E+00, 2E-09.
      Note that the bitErrorRate is an estimate only. For more reliable test 
      results, the test should be done over a long period. Multiple tests 
      would also improve the confidence level of the test results."
::= { mscLpE1TestResultsEntry 11 }


-- LogicalProcessor/n E1/0 Dsp
-- The Dsp component presents the status of the Digital Signal 
-- Processors (DSPs) present on a voice card.
-- A voice card's Dsp component is created automatically whenever 
-- the parent E1 component becomes active, and remains in existence 
-- as long as the E1 component exists. Dsp components cannot be 
-- added or deleted.

mscLpE1Dsp OBJECT IDENTIFIER ::= { mscLpE1 4 }



mscLpE1DspRowStatusTable OBJECT-TYPE
   SYNTAX     SEQUENCE OF MscLpE1DspRowStatusEntry
   ACCESS     not-accessible
   STATUS     mandatory
   DESCRIPTION
     "This entry controls the addition and deletion of 
      mscLpE1Dsp components."
::= { mscLpE1Dsp 1 }

mscLpE1DspRowStatusEntry OBJECT-TYPE
   SYNTAX     MscLpE1DspRowStatusEntry
   ACCESS     not-accessible
   STATUS     mandatory
   DESCRIPTION
     "A single entry in the table represents a single 
      mscLpE1Dsp component."
   INDEX {
      mscLpIndex,
      mscLpE1Index,
      mscLpE1DspIndex }
::= { mscLpE1DspRowStatusTable 1 }

MscLpE1DspRowStatusEntry ::= SEQUENCE {
   mscLpE1DspRowStatus
      RowStatus,
   mscLpE1DspComponentName
      DisplayString,
   mscLpE1DspStorageType
      StorageType,
   mscLpE1DspIndex
      NonReplicated }

mscLpE1DspRowStatus OBJECT-TYPE
   SYNTAX     RowStatus 
   ACCESS     read-only
   STATUS     mandatory
   DESCRIPTION
     "This variable is used as the basis for SNMP naming of
      mscLpE1Dsp components.
      These components cannot be added nor deleted."
::= { mscLpE1DspRowStatusEntry 1 }

mscLpE1DspComponentName OBJECT-TYPE
   SYNTAX     DisplayString 
   ACCESS     read-only
   STATUS     mandatory
   DESCRIPTION
     "This variable provides the component's string name for
      use with the ASCII Console Interface"
::= { mscLpE1DspRowStatusEntry 2 }

mscLpE1DspStorageType OBJECT-TYPE
   SYNTAX     StorageType 
   ACCESS     read-only
   STATUS     mandatory
   DESCRIPTION
     "This variable represents the storage type value for the
      mscLpE1Dsp tables."
::= { mscLpE1DspRowStatusEntry 4 }

mscLpE1DspIndex OBJECT-TYPE
   SYNTAX     NonReplicated 
   ACCESS     not-accessible
   STATUS     mandatory
   DESCRIPTION
     "This variable represents the index for the mscLpE1Dsp tables."
::= { mscLpE1DspRowStatusEntry 10 }


-- LogicalProcessor/n E1/0 Audio
-- The Audio component presents the audio status of the channels on a 
-- voice card.
-- A voice card's Audio component is created automatically whenever 
-- the parent E1 component becomes active, and remains in existence 
-- as long as the E1 component exists. Audio components cannot be 
-- added or deleted.

mscLpE1Audio OBJECT IDENTIFIER ::= { mscLpE1 5 }



mscLpE1AudioRowStatusTable OBJECT-TYPE
   SYNTAX     SEQUENCE OF MscLpE1AudioRowStatusEntry
   ACCESS     not-accessible
   STATUS     mandatory
   DESCRIPTION
     "This entry controls the addition and deletion of 
      mscLpE1Audio components."
::= { mscLpE1Audio 1 }

mscLpE1AudioRowStatusEntry OBJECT-TYPE
   SYNTAX     MscLpE1AudioRowStatusEntry
   ACCESS     not-accessible
   STATUS     mandatory
   DESCRIPTION
     "A single entry in the table represents a single 
      mscLpE1Audio component."
   INDEX {
      mscLpIndex,
      mscLpE1Index,
      mscLpE1AudioIndex }
::= { mscLpE1AudioRowStatusTable 1 }

MscLpE1AudioRowStatusEntry ::= SEQUENCE {
   mscLpE1AudioRowStatus
      RowStatus,
   mscLpE1AudioComponentName
      DisplayString,
   mscLpE1AudioStorageType
      StorageType,
   mscLpE1AudioIndex
      NonReplicated }

mscLpE1AudioRowStatus OBJECT-TYPE
   SYNTAX     RowStatus 
   ACCESS     read-only
   STATUS     mandatory
   DESCRIPTION
     "This variable is used as the basis for SNMP naming of
      mscLpE1Audio components.
      These components cannot be added nor deleted."
::= { mscLpE1AudioRowStatusEntry 1 }

mscLpE1AudioComponentName OBJECT-TYPE
   SYNTAX     DisplayString 
   ACCESS     read-only
   STATUS     mandatory
   DESCRIPTION
     "This variable provides the component's string name for
      use with the ASCII Console Interface"
::= { mscLpE1AudioRowStatusEntry 2 }

mscLpE1AudioStorageType OBJECT-TYPE
   SYNTAX     StorageType 
   ACCESS     read-only
   STATUS     mandatory
   DESCRIPTION
     "This variable represents the storage type value for the
      mscLpE1Audio tables."
::= { mscLpE1AudioRowStatusEntry 4 }

mscLpE1AudioIndex OBJECT-TYPE
   SYNTAX     NonReplicated 
   ACCESS     not-accessible
   STATUS     mandatory
   DESCRIPTION
     "This variable represents the index for the mscLpE1Audio tables."
::= { mscLpE1AudioRowStatusEntry 10 }


-- 
-- Lp/n V35/n
-- 
-- The V35 component controls a Passport V.35 interface.

mscLpV35 OBJECT IDENTIFIER ::= { mscLp 9 }



mscLpV35RowStatusTable OBJECT-TYPE
   SYNTAX     SEQUENCE OF MscLpV35RowStatusEntry
   ACCESS     not-accessible
   STATUS     mandatory
   DESCRIPTION
     "This entry controls the addition and deletion of 
      mscLpV35 components."
::= { mscLpV35 1 }

mscLpV35RowStatusEntry OBJECT-TYPE
   SYNTAX     MscLpV35RowStatusEntry
   ACCESS     not-accessible
   STATUS     mandatory
   DESCRIPTION
     "A single entry in the table represents a single 
      mscLpV35 component."
   INDEX {
      mscLpIndex,
      mscLpV35Index }
::= { mscLpV35RowStatusTable 1 }

MscLpV35RowStatusEntry ::= SEQUENCE {
   mscLpV35RowStatus
      RowStatus,
   mscLpV35ComponentName
      DisplayString,
   mscLpV35StorageType
      StorageType,
   mscLpV35Index
      Integer32 }

mscLpV35RowStatus OBJECT-TYPE
   SYNTAX     RowStatus 
   ACCESS     read-write
   STATUS     mandatory
   DESCRIPTION
     "This variable is used as the basis for SNMP naming of
      mscLpV35 components.
      These components can be added and deleted."
::= { mscLpV35RowStatusEntry 1 }

mscLpV35ComponentName OBJECT-TYPE
   SYNTAX     DisplayString 
   ACCESS     read-only
   STATUS     mandatory
   DESCRIPTION
     "This variable provides the component's string name for
      use with the ASCII Console Interface"
::= { mscLpV35RowStatusEntry 2 }

mscLpV35StorageType OBJECT-TYPE
   SYNTAX     StorageType 
   ACCESS     read-only
   STATUS     mandatory
   DESCRIPTION
     "This variable represents the storage type value for the
      mscLpV35 tables."
::= { mscLpV35RowStatusEntry 4 }

mscLpV35Index OBJECT-TYPE
   SYNTAX     Integer32 (0..7)
   ACCESS     not-accessible
   STATUS     mandatory
   DESCRIPTION
     "This variable represents the index for the mscLpV35 tables."
::= { mscLpV35RowStatusEntry 10 }

mscLpV35ProvTable OBJECT-TYPE
   SYNTAX     SEQUENCE OF MscLpV35ProvEntry
   ACCESS     not-accessible
   STATUS     mandatory
   DESCRIPTION
     "This group contains all specific provisioning data for a V35 
      component."
::= { mscLpV35 10 }

mscLpV35ProvEntry OBJECT-TYPE
   SYNTAX     MscLpV35ProvEntry
   ACCESS     not-accessible
   STATUS     mandatory
   DESCRIPTION
     "An entry in the mscLpV35ProvTable."
   INDEX {
      mscLpIndex,
      mscLpV35Index }
::= { mscLpV35ProvTable 1 }

MscLpV35ProvEntry ::= SEQUENCE {
   mscLpV35LinkMode
      INTEGER,
   mscLpV35ReadyLineState
      OCTET STRING,
   mscLpV35DataTransferLineState
      OCTET STRING,
   mscLpV35LineStatusTimeOut
      Unsigned32,
   mscLpV35LineSpeed
      Unsigned32,
   mscLpV35ClockingSource
      INTEGER,
   mscLpV35DteDataClockSource
      INTEGER,
   mscLpV35ApplicationFramerName
      Link,
   mscLpV35EnableDynamicSpeed
      INTEGER }

mscLpV35LinkMode OBJECT-TYPE
   SYNTAX     INTEGER  {
                 dte(0),
                 dce(128) }
   ACCESS     read-write
   STATUS     mandatory
   DESCRIPTION
     "This attribute defines the intended gender of the V.35 interface. The 
      actual gender of the interface is determined by the physical 
      connection to the patch panel. If the hardware setup does not match 
      this attribute, an alarm will be generated.
      
      In dte mode, the RTS line signal is driven as specified by the 
      attribute readyLineState when the interface passes its initial 
      diagnostics. Then, the RTS line signal will be driven as specified in 
      the attribute dataTransferLineState when the application is ready to 
      transfer data. On the other hand, the input line signals (RFS, DSR, 
      and DCD) are compared against those specified in the attributes 
      readyLineState and dataTransferLineState. The application will be 
      notified when the specified input line states are observed.
      
      In dce mode, the V35 component behaves similarly as when it is in 
      dte mode. However, it will be driving the DCE line signals (RFS, 
      DSR, and DCD) and monitoring the DTE line signal (RTS) as 
      specified by the attributes readyLineState and 
      dataTransferLineState."
   DEFVAL     { dte }
::= { mscLpV35ProvEntry 1 }

mscLpV35ReadyLineState OBJECT-TYPE
   SYNTAX     OCTET STRING (SIZE (1))
   ACCESS     read-write
   STATUS     mandatory
   DESCRIPTION
     "This attribute specifies the line signals originating from the V.35 
      interface that will always be turned on, provided the interface passes 
      its diagnostics. This set of signals is generally required for 
      maintaining the connection. Note that both DTE and DCE signals 
      are specified in this attribute. The appropriate set of specified 
      signals will be turned on or checked according to the 
      actualLinkMode.
      See also linkMode.

      Description of bits:
      rfs(0)
      dsr(1)
      dcd(2)
      rts(3)"
   DEFVAL     { 'f0'H }
::= { mscLpV35ProvEntry 2 }

mscLpV35DataTransferLineState OBJECT-TYPE
   SYNTAX     OCTET STRING (SIZE (1))
   ACCESS     read-write
   STATUS     mandatory
   DESCRIPTION
     "This attribute specifies the line signals required to indicate that the 
      external equipment is in a good state (that is, data transfer can 
      proceed). Note that both DTE and DCE signals are specified in this 
      attribute. The appropriate set of specified signals will be turned on 
      or checked according to the actualLinkMode. The value of this 
      attribute must be a superset of that of the readyLineState attribute.
      See also linkMode.

      Description of bits:
      rfs(0)
      dsr(1)
      dcd(2)
      rts(3)"
   DEFVAL     { 'f0'H }
::= { mscLpV35ProvEntry 3 }

mscLpV35LineStatusTimeOut OBJECT-TYPE
   SYNTAX     Unsigned32 (10..20000)
   ACCESS     read-write
   STATUS     mandatory
   DESCRIPTION
     "This attribute defines the time that the line state must be stable 
      (good or bad) before a line state change is declared."
   DEFVAL     { 1000 }
::= { mscLpV35ProvEntry 4 }

mscLpV35LineSpeed OBJECT-TYPE
   SYNTAX     Unsigned32 (9600..3840000)
   ACCESS     read-write
   STATUS     mandatory
   DESCRIPTION
     "This attribute defines the speed of the line for source clocking. This 
      attribute is ignored if the interface is not providing a clock. The 
      clock rate is rounded up to the nearest available value. Note that the 
      actual clock rates are available in the operational attributes 
      actualTxLineSpeed and actualRxLineSpeed. The actual lineSpeeds 
      configurable on a V.35 DCE interface are: 3840000, 2560000, 
      2048000, 1920000, 1536000, 1344000, 1280000, 1024000, 960000, 
      768000, 672000, 640000, 512000, 448000, 384000, 336000, 
      320000, 256000, 224000, 192000, 168000, 128000, 112000, 64000, 
      56000, 48000, 32000, 19200, 9600. Note that linspeeds of 1024000 
      and 2048000 cannot be provisioned on cards that have ports 
      provisioned at 3840000, 2560000, 1920000, 1280000, 960000, 
      640000 or 320000."
   DEFVAL     { 192000 }
::= { mscLpV35ProvEntry 5 }

mscLpV35ClockingSource OBJECT-TYPE
   SYNTAX     INTEGER  {
                 local(0),
                 module(1) }
   ACCESS     read-write
   STATUS     mandatory
   DESCRIPTION
     "This attribute defines the source of synchronization of the outgoing 
      clocks. This attribute is only used when the actualLinkMode is dce.
      
      If the value of the attribute is local, the outgoing clocks are 
      synchronized to a local oscillator on the FP.
      
      If the value of the attribute is module, the outgoing clocks are 
      synchronized to the oscillator on the active CP."
::= { mscLpV35ProvEntry 6 }

mscLpV35DteDataClockSource OBJECT-TYPE
   SYNTAX     INTEGER  {
                 fromDce(0),
                 fromDte(2) }
   ACCESS     read-write
   STATUS     mandatory
   DESCRIPTION
     "This attribute is only used when the actualLinkMode  is dce. It is 
      used to determine the clock to be used to recover the receive data. A 
      DTE interface uses TSET(DCE) and RSET(DCE) for timing.
      
      If the value of the attribute is fromDce, the DCE uses the internally 
      generated transmit clock to supply both TSET(DCE) and 
      RSET(DCE).
      
      If the value of the attribute is fromDte, the DCE still uses the 
      internally generated transmit clock to supply TSET(DCE), but the 
      receive timing is derived from TSET(DTE) on the link. 
      
      The fromDte mode is recommended when the DTE is far away from 
      the DCE interface. Note that TSET(DTE) is CCITT V.24 circuit 
      113; TSET(DCE) is CCITT V.24 circuit 114; and RSET(DCE) is 
      CCITT V.24 circuit 115."
   DEFVAL     { fromDce }
::= { mscLpV35ProvEntry 7 }

mscLpV35ApplicationFramerName OBJECT-TYPE
   SYNTAX     Link 
   ACCESS     read-write
   STATUS     mandatory
   DESCRIPTION
     "This attribute contains the component name of a Framer which is 
      associated with the V35 component."
::= { mscLpV35ProvEntry 8 }

mscLpV35EnableDynamicSpeed OBJECT-TYPE
   SYNTAX     INTEGER  {
                 no(0),
                 yes(1) }
   ACCESS     read-write
   STATUS     mandatory
   DESCRIPTION
     "When set to yes, this attribute specifies that the transmit link speed 
      should be set to the calculated receiver link speed. This attribute can 
      be set to yes only if the linkMode is dce and the 
      dteDataClockSource is fromDte."
   DEFVAL     { no }
::= { mscLpV35ProvEntry 9 }

mscLpV35CidDataTable OBJECT-TYPE
   SYNTAX     SEQUENCE OF MscLpV35CidDataEntry
   ACCESS     not-accessible
   STATUS     mandatory
   DESCRIPTION
     "This group contains the attribute for a component's Customer 
      Identifier (CID). Refer to the attribute description for a detailed 
      explanation of CIDs."
::= { mscLpV35 11 }

mscLpV35CidDataEntry OBJECT-TYPE
   SYNTAX     MscLpV35CidDataEntry
   ACCESS     not-accessible
   STATUS     mandatory
   DESCRIPTION
     "An entry in the mscLpV35CidDataTable."
   INDEX {
      mscLpIndex,
      mscLpV35Index }
::= { mscLpV35CidDataTable 1 }

MscLpV35CidDataEntry ::= SEQUENCE {
   mscLpV35CustomerIdentifier
      Unsigned32 }

mscLpV35CustomerIdentifier OBJECT-TYPE
   SYNTAX     Unsigned32 (0 | 1..8191)
   ACCESS     read-write
   STATUS     mandatory
   DESCRIPTION
     "This attribute holds the Customer Identifier (CID).
      
      Every component has a CID. If a component has a cid attribute, the 
      component's CID is the provisioned value of that attribute; 
      otherwise the component inherits the CID of its parent. The top-
      level component has a CID of 0.
      
      Every operator session also has a CID, which is the CID 
      provisioned for the operator's user ID. An operator will see only the 
      stream data for components having a matching CID. Also, the 
      operator will be allowed to issue commands for only those 
      components which have a matching CID.
      
      An operator CID of 0 is used to identify the Network Manager 
      (referred to as 'NetMan' in DPN). This CID matches the CID of 
      any component. Values 1 to 8191 inclusive (equivalent to 'basic 
      CIDs' in DPN) may be assigned to specific customers."
   DEFVAL     { 0 }
::= { mscLpV35CidDataEntry 1 }

mscLpV35AdminInfoTable OBJECT-TYPE
   SYNTAX     SEQUENCE OF MscLpV35AdminInfoEntry
   ACCESS     not-accessible
   STATUS     mandatory
   DESCRIPTION
     "This group contains the attributes pertaining to the vendor of the 
      equipment."
::= { mscLpV35 12 }

mscLpV35AdminInfoEntry OBJECT-TYPE
   SYNTAX     MscLpV35AdminInfoEntry
   ACCESS     not-accessible
   STATUS     mandatory
   DESCRIPTION
     "An entry in the mscLpV35AdminInfoTable."
   INDEX {
      mscLpIndex,
      mscLpV35Index }
::= { mscLpV35AdminInfoTable 1 }

MscLpV35AdminInfoEntry ::= SEQUENCE {
   mscLpV35Vendor
      AsciiString,
   mscLpV35CommentText
      AsciiString }

mscLpV35Vendor OBJECT-TYPE
   SYNTAX     AsciiString (SIZE (0..20))
   ACCESS     read-write
   STATUS     mandatory
   DESCRIPTION
     "This is the name of the vendor supplying the facility."
::= { mscLpV35AdminInfoEntry 1 }

mscLpV35CommentText OBJECT-TYPE
   SYNTAX     AsciiString (SIZE (0..60))
   ACCESS     read-write
   STATUS     mandatory
   DESCRIPTION
     "Any miscellaneous text about the facility."
::= { mscLpV35AdminInfoEntry 2 }

mscLpV35IfEntryTable OBJECT-TYPE
   SYNTAX     SEQUENCE OF MscLpV35IfEntryEntry
   ACCESS     not-accessible
   STATUS     mandatory
   DESCRIPTION
     "This group contains the provisionable attributes for the ifEntry."
::= { mscLpV35 13 }

mscLpV35IfEntryEntry OBJECT-TYPE
   SYNTAX     MscLpV35IfEntryEntry
   ACCESS     not-accessible
   STATUS     mandatory
   DESCRIPTION
     "An entry in the mscLpV35IfEntryTable."
   INDEX {
      mscLpIndex,
      mscLpV35Index }
::= { mscLpV35IfEntryTable 1 }

MscLpV35IfEntryEntry ::= SEQUENCE {
   mscLpV35IfAdminStatus
      INTEGER,
   mscLpV35IfIndex
      InterfaceIndex }

mscLpV35IfAdminStatus OBJECT-TYPE
   SYNTAX     INTEGER  {
                 up(1),
                 down(2),
                 testing(3) }
   ACCESS     read-write
   STATUS     mandatory
   DESCRIPTION
     "The desired state of the interface. The up state indicates the 
      interface is operational. The down state indicates the interface is not 
      operational. The testing state indicates that no operational packets 
      can be passed."
   DEFVAL     { up }
::= { mscLpV35IfEntryEntry 1 }

mscLpV35IfIndex OBJECT-TYPE
   SYNTAX     InterfaceIndex (1..65535)
   ACCESS     read-only
   STATUS     mandatory
   DESCRIPTION
     "This is the index for the IfEntry. Its value is automatically initialized 
      during the provisioning process."
::= { mscLpV35IfEntryEntry 2 }

mscLpV35OperStatusTable OBJECT-TYPE
   SYNTAX     SEQUENCE OF MscLpV35OperStatusEntry
   ACCESS     not-accessible
   STATUS     mandatory
   DESCRIPTION
     "This group includes the Operational Status attribute. This attribute 
      defines the current operational state of this component."
::= { mscLpV35 14 }

mscLpV35OperStatusEntry OBJECT-TYPE
   SYNTAX     MscLpV35OperStatusEntry
   ACCESS     not-accessible
   STATUS     mandatory
   DESCRIPTION
     "An entry in the mscLpV35OperStatusTable."
   INDEX {
      mscLpIndex,
      mscLpV35Index }
::= { mscLpV35OperStatusTable 1 }

MscLpV35OperStatusEntry ::= SEQUENCE {
   mscLpV35SnmpOperStatus
      INTEGER }

mscLpV35SnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { mscLpV35OperStatusEntry 1 }

mscLpV35StateTable OBJECT-TYPE
   SYNTAX     SEQUENCE OF MscLpV35StateEntry
   ACCESS     not-accessible
   STATUS     mandatory
   DESCRIPTION
     "This group contains the three OSI State attributes and the six OSI 
      Status attributes. The descriptions generically indicate what each 
      attribute implies about the component. Note that not all the values 
      and state combinations described here are supported by every 
      component which uses this group. For component-specific 
      information and the valid state combinations, refer to NTP 241-
      7001-150, Passport Operations and Maintenance Guide."
::= { mscLpV35 15 }

mscLpV35StateEntry OBJECT-TYPE
   SYNTAX     MscLpV35StateEntry
   ACCESS     not-accessible
   STATUS     mandatory
   DESCRIPTION
     "An entry in the mscLpV35StateTable."
   INDEX {
      mscLpIndex,
      mscLpV35Index }
::= { mscLpV35StateTable 1 }

MscLpV35StateEntry ::= SEQUENCE {
   mscLpV35AdminState
      INTEGER,
   mscLpV35OperationalState
      INTEGER,
   mscLpV35UsageState
      INTEGER,
   mscLpV35AvailabilityStatus
      OCTET STRING,
   mscLpV35ProceduralStatus
      OCTET STRING,
   mscLpV35ControlStatus
      OCTET STRING,
   mscLpV35AlarmStatus
      OCTET STRING,
   mscLpV35StandbyStatus
      INTEGER,
   mscLpV35UnknownStatus
      INTEGER }

mscLpV35AdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component.
      
      The OSI Status attributes, if supported by the component, may 
      provide more details, qualifying the state of the component."
   DEFVAL     { unlocked }
::= { mscLpV35StateEntry 1 }

mscLpV35OperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle.
      
      The OSI Status attributes, if supported by the component, may 
      provide more details, qualifying the state of the component."
   DEFVAL     { disabled }
::= { mscLpV35StateEntry 2 }

mscLpV35UsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time.
      
      The OSI Status attributes, if supported by the component, may 
      provide more details, qualifying the state of the component."
   DEFVAL     { idle }
::= { mscLpV35StateEntry 3 }

mscLpV35AvailabilityStatus OBJECT-TYPE
   SYNTAX     OCTET STRING (SIZE (2))
   ACCESS     read-only
   STATUS     mandatory
   DESCRIPTION
     "If supported by the component, this attribute indicates the OSI 
      Availability status of the component. Note that, even though it is 
      defined as a multi-valued set, at most one value is shown to the user.
      
      When no values are in the set, this indicates that either the attribute 
      is not supported or that none of the status conditions described 
      below are present.
      
      The value inTest indicates that the resource is undergoing a test 
      procedure. If adminState is locked or shuttingDown, the normal 
      users are precluded from using the resource and controlStatus is 
      reservedForTest. Tests that do not exclude additional users can be 
      present in any operational or administrative state but the 
      reservedForTest condition should not be present.
      
      The value failed indicates that the component has an internal fault 
      that prevents it from operating. The operationalState is disabled.
      
      The value dependency indicates that the component cannot operate 
      because some other resource on which it depends is unavailable. 
      The operationalState is disabled.
      
      The value powerOff indicates the resource requires power to be 
      applied and it is not powered on. The operationalState is disabled.
      
      The value offLine indicates the resource requires a routine 
      operation (either manual, automatic, or both) to be performed to 
      place it on-line and make it available for use. The operationalState 
      is disabled.
      
      The value offDuty indicates the resource is inactive in accordance 
      with a predetermined time schedule. In the absence of other 
      disabling conditions, the operationalState is enabled or disabled.
      
      The value degraded indicates the service provided by the 
      component is degraded in some way, such as in speed or operating 
      capacity. However, the resource remains available for service. The 
      operationalState is enabled.
      
      The value notInstalled indicates the resource is not present. The 
      operationalState is disabled.
      
      The value logFull is not used.

      Description of bits:
      inTest(0)
      failed(1)
      powerOff(2)
      offLine(3)
      offDuty(4)
      dependency(5)
      degraded(6)
      notInstalled(7)
      logFull(8)"
::= { mscLpV35StateEntry 4 }

mscLpV35ProceduralStatus OBJECT-TYPE
   SYNTAX     OCTET STRING (SIZE (1))
   ACCESS     read-only
   STATUS     mandatory
   DESCRIPTION
     "If supported by the component, this attribute indicates the OSI 
      Procedural status of the component. Note that, even though it is 
      defined as a multi-valued set, at most one value is shown to the user.
      
      When no values are in the set, this indicates that either the attribute 
      is not supported or that none of the status conditions described 
      below are present.
      
      The value initializationRequired indicates (for a resource which 
      doesn't initialize autonomously) that initialization is required before 
      it can perform its normal functions, and this procedure has not been 
      initiated. The operationalState is disabled.
      
      The value notInitialized indicates (for a resource which does 
      initialize autonomously) that initialization is required before it can 
      perform its normal functions, and this procedure has not been 
      initiated. The operationalState may be enabled or disabled.
      
      The value initializing indicates that initialization has been initiated 
      but is not yet complete. The operationalState may be enabled or 
      disabled.
      
      The value reporting indicates the resource has completed some 
      processing operation and is notifying the results. The 
      operationalState is enabled.
      
      The value terminating indicates the component is in a termination 
      phase. If the resource doesn't reinitialize autonomously, 
      operationalState is disabled; otherwise it is enabled or disabled.

      Description of bits:
      initializationRequired(0)
      notInitialized(1)
      initializing(2)
      reporting(3)
      terminating(4)"
::= { mscLpV35StateEntry 5 }

mscLpV35ControlStatus OBJECT-TYPE
   SYNTAX     OCTET STRING (SIZE (1))
   ACCESS     read-only
   STATUS     mandatory
   DESCRIPTION
     "If supported by the component, this attribute indicates the OSI 
      Control status of the component. Note that, even though it is defined 
      as a multi-valued set, at most one value is shown to the user.
      
      When no values are in the set, this indicates that either the attribute 
      is not supported or that none of the status conditions described 
      below are present.
      
      The value subjectToTest indicates the resource is available but tests 
      may be conducted simultaneously at unpredictable times, which 
      may cause it to exhibit unusual characteristics.
      
      The value partOfServicesLocked indicates that part of the service is 
      restricted from users of a resource. The adminState is unlocked.
      
      The value reservedForTest indicates that the component is 
      administratively unavailable because it is undergoing a test 
      procedure. The adminState is locked.
      
      The value suspended indicates that the service has been 
      administratively suspended.

      Description of bits:
      subjectToTest(0)
      partOfServicesLocked(1)
      reservedForTest(2)
      suspended(3)"
::= { mscLpV35StateEntry 6 }

mscLpV35AlarmStatus OBJECT-TYPE
   SYNTAX     OCTET STRING (SIZE (1))
   ACCESS     read-only
   STATUS     mandatory
   DESCRIPTION
     "If supported by the component, this attribute indicates the OSI 
      Alarm status of the component. Note that, even though it is defined 
      as a multi-valued set, at most one value is shown to the user.
      
      When no values are in the set, this indicates that either the attribute 
      is not supported or that none of the status conditions described 
      below are present.
      
      The value underRepair indicates the component is currently being 
      repaired. The operationalState is enabled or disabled.
      
      The value critical indicates one or more critical alarms are 
      outstanding against the component. Other, less severe, alarms may 
      also be outstanding. The operationalState is enabled or disabled.
      
      The value major indicates one or more major alarms are 
      outstanding against the component. Other, less severe, alarms may 
      also be outstanding. The operationalState is enabled or disabled.
      
      The value minor indicates one or more minor alarms are 
      outstanding against the component. Other, less severe, alarms may 
      also be outstanding. The operationalState is enabled or disabled.
      
      The value alarmOutstanding generically indicates that an alarm of 
      some severity is outstanding against the component.

      Description of bits:
      underRepair(0)
      critical(1)
      major(2)
      minor(3)
      alarmOutstanding(4)"
::= { mscLpV35StateEntry 7 }

mscLpV35StandbyStatus OBJECT-TYPE
   SYNTAX     INTEGER  {
                 hotStandby(0),
                 coldStandby(1),
                 providingService(2),
                 notSet(15) }
   ACCESS     read-only
   STATUS     mandatory
   DESCRIPTION
     "If supported by the component, this attribute indicates the OSI 
      Standby status of the component.
      
      The value notSet indicates that either the attribute is not supported 
      or that none of the status conditions described below are present. 
      Note that this is a non-standard value, used because the original 
      specification indicated this attribute was set-valued and thus, did not 
      provide a value to indicate that none of the other three are 
      applicable.
      
      The value hotStandby indicates that the resource is not providing 
      service but will be immediately able to take over the role of the 
      resource to be backed up, without initialization activity, and 
      containing the same information as the resource to be backed up.
      
      The value coldStandby indicates the resource is a backup for 
      another resource but will not be immediately able to take over the 
      role of the backed up resource and will require some initialization 
      activity.
      
      The value providingService indicates that this component, as a 
      backup resource, is currently backing up another resource."
   DEFVAL     { notSet }
::= { mscLpV35StateEntry 8 }

mscLpV35UnknownStatus OBJECT-TYPE
   SYNTAX     INTEGER  {
                 false(0),
                 true(1) }
   ACCESS     read-only
   STATUS     mandatory
   DESCRIPTION
     "This attribute indicates the OSI Unknown status of the component.
      
      The value false indicates that all of the other OSI State and Status 
      attribute values can be considered accurate.
      
      The value true indicates that the actual state of the component is not 
      known for sure."
   DEFVAL     { false }
::= { mscLpV35StateEntry 9 }

mscLpV35OperTable OBJECT-TYPE
   SYNTAX     SEQUENCE OF MscLpV35OperEntry
   ACCESS     not-accessible
   STATUS     mandatory
   DESCRIPTION
     "This group contains all specific operational data for a V35 
      component."
::= { mscLpV35 16 }

mscLpV35OperEntry OBJECT-TYPE
   SYNTAX     MscLpV35OperEntry
   ACCESS     not-accessible
   STATUS     mandatory
   DESCRIPTION
     "An entry in the mscLpV35OperTable."
   INDEX {
      mscLpIndex,
      mscLpV35Index }
::= { mscLpV35OperTable 1 }

MscLpV35OperEntry ::= SEQUENCE {
   mscLpV35ActualLinkMode
      INTEGER,
   mscLpV35LineState
      OCTET STRING,
   mscLpV35ActualTxLineSpeed
      Gauge32,
   mscLpV35ActualRxLineSpeed
      Gauge32,
   mscLpV35DataXferStateChanges
      Counter32 }

mscLpV35ActualLinkMode OBJECT-TYPE
   SYNTAX     INTEGER  {
                 dte(0),
                 dce(128) }
   ACCESS     read-only
   STATUS     mandatory
   DESCRIPTION
     "This attribute contains the actual link mode defined by the 
      hardware. Note that the hardware overrides the provisionable data. 
      The interface behaves as a DCE or DTE according to the 
      actualLinkMode."
::= { mscLpV35OperEntry 1 }

mscLpV35LineState OBJECT-TYPE
   SYNTAX     OCTET STRING (SIZE (1))
   ACCESS     read-only
   STATUS     mandatory
   DESCRIPTION
     "This attribute contains the current state of the interface signals.

      Description of bits:
      rfs(0)
      dsr(1)
      dcd(2)
      rts(3)"
::= { mscLpV35OperEntry 2 }

mscLpV35ActualTxLineSpeed OBJECT-TYPE
   SYNTAX     Gauge32 (0..4294967295)
   ACCESS     read-only
   STATUS     mandatory
   DESCRIPTION
     "This attribute is the measured speed of the transmit clock."
::= { mscLpV35OperEntry 3 }

mscLpV35ActualRxLineSpeed OBJECT-TYPE
   SYNTAX     Gauge32 (0..4294967295)
   ACCESS     read-only
   STATUS     mandatory
   DESCRIPTION
     "This attribute is the measured speed of the receive clock."
::= { mscLpV35OperEntry 4 }

mscLpV35DataXferStateChanges OBJECT-TYPE
   SYNTAX     Counter32 
   ACCESS     read-only
   STATUS     mandatory
   DESCRIPTION
     "This attribute contains the number of times that the line has entered 
      or exited the data transfer state."
::= { mscLpV35OperEntry 5 }


-- 
-- The Test component is configured to control a hardware facility test 
-- on a physical (V35, X21, DS1, E1, DS3, E3 etc.) or a logical port.

mscLpV35Test OBJECT IDENTIFIER ::= { mscLpV35 2 }



mscLpV35TestRowStatusTable OBJECT-TYPE
   SYNTAX     SEQUENCE OF MscLpV35TestRowStatusEntry
   ACCESS     not-accessible
   STATUS     mandatory
   DESCRIPTION
     "This entry controls the addition and deletion of 
      mscLpV35Test components."
::= { mscLpV35Test 1 }

mscLpV35TestRowStatusEntry OBJECT-TYPE
   SYNTAX     MscLpV35TestRowStatusEntry
   ACCESS     not-accessible
   STATUS     mandatory
   DESCRIPTION
     "A single entry in the table represents a single 
      mscLpV35Test component."
   INDEX {
      mscLpIndex,
      mscLpV35Index,
      mscLpV35TestIndex }
::= { mscLpV35TestRowStatusTable 1 }

MscLpV35TestRowStatusEntry ::= SEQUENCE {
   mscLpV35TestRowStatus
      RowStatus,
   mscLpV35TestComponentName
      DisplayString,
   mscLpV35TestStorageType
      StorageType,
   mscLpV35TestIndex
      NonReplicated }

mscLpV35TestRowStatus OBJECT-TYPE
   SYNTAX     RowStatus 
   ACCESS     read-only
   STATUS     mandatory
   DESCRIPTION
     "This variable is used as the basis for SNMP naming of
      mscLpV35Test components.
      These components cannot be added nor deleted."
::= { mscLpV35TestRowStatusEntry 1 }

mscLpV35TestComponentName OBJECT-TYPE
   SYNTAX     DisplayString 
   ACCESS     read-only
   STATUS     mandatory
   DESCRIPTION
     "This variable provides the component's string name for
      use with the ASCII Console Interface"
::= { mscLpV35TestRowStatusEntry 2 }

mscLpV35TestStorageType OBJECT-TYPE
   SYNTAX     StorageType 
   ACCESS     read-only
   STATUS     mandatory
   DESCRIPTION
     "This variable represents the storage type value for the
      mscLpV35Test tables."
::= { mscLpV35TestRowStatusEntry 4 }

mscLpV35TestIndex OBJECT-TYPE
   SYNTAX     NonReplicated 
   ACCESS     not-accessible
   STATUS     mandatory
   DESCRIPTION
     "This variable represents the index for the mscLpV35Test tables."
::= { mscLpV35TestRowStatusEntry 10 }

mscLpV35TestStateTable OBJECT-TYPE
   SYNTAX     SEQUENCE OF MscLpV35TestStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscLpV35Test 10 }

mscLpV35TestStateEntry OBJECT-TYPE
   SYNTAX     MscLpV35TestStateEntry
   ACCESS     not-accessible
   STATUS     mandatory
   DESCRIPTION
     "An entry in the mscLpV35TestStateTable."
   INDEX {
      mscLpIndex,
      mscLpV35Index,
      mscLpV35TestIndex }
::= { mscLpV35TestStateTable 1 }

MscLpV35TestStateEntry ::= SEQUENCE {
   mscLpV35TestAdminState
      INTEGER,
   mscLpV35TestOperationalState
      INTEGER,
   mscLpV35TestUsageState
      INTEGER }

mscLpV35TestAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscLpV35TestStateEntry 1 }

mscLpV35TestOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscLpV35TestStateEntry 2 }

mscLpV35TestUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscLpV35TestStateEntry 3 }

mscLpV35TestSetupTable OBJECT-TYPE
   SYNTAX     SEQUENCE OF MscLpV35TestSetupEntry
   ACCESS     not-accessible
   STATUS     mandatory
   DESCRIPTION
     "This group contains all of the operational data for a Test 
      component."
::= { mscLpV35Test 11 }

mscLpV35TestSetupEntry OBJECT-TYPE
   SYNTAX     MscLpV35TestSetupEntry
   ACCESS     not-accessible
   STATUS     mandatory
   DESCRIPTION
     "An entry in the mscLpV35TestSetupTable."
   INDEX {
      mscLpIndex,
      mscLpV35Index,
      mscLpV35TestIndex }
::= { mscLpV35TestSetupTable 1 }

MscLpV35TestSetupEntry ::= SEQUENCE {
   mscLpV35TestPurpose
      AsciiString,
   mscLpV35TestType
      INTEGER,
   mscLpV35TestFrmSize
      Unsigned32,
   mscLpV35TestFrmPatternType
      INTEGER,
   mscLpV35TestCustomizedPattern
      Hex,
   mscLpV35TestDataStartDelay
      Unsigned32,
   mscLpV35TestDisplayInterval
      Unsigned32,
   mscLpV35TestDuration
      Unsigned32 }

mscLpV35TestPurpose OBJECT-TYPE
   SYNTAX     AsciiString (SIZE (0..40))
   ACCESS     read-write
   STATUS     mandatory
   DESCRIPTION
     "This attribute records the purpose of the test so that the test results 
      can be associated and properly analyzed."
::= { mscLpV35TestSetupEntry 1 }

mscLpV35TestType OBJECT-TYPE
   SYNTAX     INTEGER  {
                 card(0),
                 manual(1),
                 localLoop(2),
                 remoteLoop(3),
                 externalLoop(4),
                 payloadLoop(5),
                 remoteLoopThisTrib(6),
                 v54RemoteLoop(7),
                 pn127RemoteLoop(8) }
   ACCESS     read-write
   STATUS     mandatory
   DESCRIPTION
     "This attribute is the type of test to be run. The available test types 
      include the following:
      card test sets up an internal loop on the board and runs a bit error 
      rate test.
      manual test assumes the line is looped back externally and a bit 
      error rate test is performed.
      localLoop test loops back the local modem and performs a bit error 
      rate test.
      remoteLoop test loops back the remote modem (or CSU) and 
      performs a bit error rate test.
      externalLoop test loops back the line to the far end.
      payloadLoop test only loops back the payload data received from 
      the incoming line.
      remoteLoopThisTrib loops this particular tributary back at the far 
      end, using services provided by the parent.
      v54RemoteLoop initiates a V.54 Remote Loopback test.
      pn127RemoteLoop initiates a PN127 Remote Loopback test.
      Note that not all test types are not supported by all function 
      processors."
   DEFVAL     { card }
::= { mscLpV35TestSetupEntry 2 }

mscLpV35TestFrmSize OBJECT-TYPE
   SYNTAX     Unsigned32 (4..4096)
   ACCESS     read-write
   STATUS     mandatory
   DESCRIPTION
     "This attribute defines the size of the test data frames in number of 
      bytes."
   DEFVAL     { 1024 }
::= { mscLpV35TestSetupEntry 3 }

mscLpV35TestFrmPatternType OBJECT-TYPE
   SYNTAX     INTEGER  {
                 ccitt32kBitPattern(0),
                 ccitt8MBitPattern(1),
                 customizedPattern(2) }
   ACCESS     read-write
   STATUS     mandatory
   DESCRIPTION
     "This attribute defines the type of data pattern generation to use. The 
      following lists the available pattern types:
      ccitt32kBitPattern is a pseudo-random sequence of 32 kbit.
      ccitt8MBitPattern is a pseudo-random sequence of 8Mbit.
      customizedPattern is the pattern defined in the customizedPattern 
      attribute."
   DEFVAL     { ccitt32kBitPattern }
::= { mscLpV35TestSetupEntry 4 }

mscLpV35TestCustomizedPattern OBJECT-TYPE
   SYNTAX     Hex (0..4294967295)
   ACCESS     read-write
   STATUS     mandatory
   DESCRIPTION
     "This attribute allows a customized 32 bit pattern to be defined for 
      use in the test data frames. This attribute is used when the attribute 
      frmPatternType is set to CustomizedPattern. Note that a 55 hex 
      pattern is an alternating 1 and 0 pattern."
   DEFVAL     { 1431655765 }
::= { mscLpV35TestSetupEntry 5 }

mscLpV35TestDataStartDelay OBJECT-TYPE
   SYNTAX     Unsigned32 (0..1814400)
   ACCESS     read-write
   STATUS     mandatory
   DESCRIPTION
     "This attribute specifies the time delay (in seconds) between when 
      the test expects the loop to have been set up, to when the test data 
      actually starts to be transmitted. This attribute is to accommodate 
      some non-standard equipment that requires extra time for setting up 
      a requested loop.
      This attribute is ignored when the test type is set to externalLoop."
   DEFVAL     { 0 }
::= { mscLpV35TestSetupEntry 6 }

mscLpV35TestDisplayInterval OBJECT-TYPE
   SYNTAX     Unsigned32 (0..30240)
   ACCESS     read-write
   STATUS     mandatory
   DESCRIPTION
     "This attribute defines the interval (in minutes) between which 
      interim test results are to be displayed. Results are displayed at the 
      operator console at which the test was started. When the test type is 
      set to externalLoop, this attribute is ignored. There will be no 
      display of results if displayInterval is set to 0. This attribute can be 
      changed anytime."
   DEFVAL     { 5 }
::= { mscLpV35TestSetupEntry 7 }

mscLpV35TestDuration OBJECT-TYPE
   SYNTAX     Unsigned32 (1..30240)
   ACCESS     read-write
   STATUS     mandatory
   DESCRIPTION
     "This attribute is the duration (in minutes) that test data will be 
      transmitted. In the case of an externalLoop, this is the time that the 
      loop is in effect. Note that dataStartDelay does not apply to the 
      externalLoop."
   DEFVAL     { 1 }
::= { mscLpV35TestSetupEntry 8 }

mscLpV35TestResultsTable OBJECT-TYPE
   SYNTAX     SEQUENCE OF MscLpV35TestResultsEntry
   ACCESS     not-accessible
   STATUS     mandatory
   DESCRIPTION
     "This group contains all the statistics related attributes of the Test 
      component."
::= { mscLpV35Test 12 }

mscLpV35TestResultsEntry OBJECT-TYPE
   SYNTAX     MscLpV35TestResultsEntry
   ACCESS     not-accessible
   STATUS     mandatory
   DESCRIPTION
     "An entry in the mscLpV35TestResultsTable."
   INDEX {
      mscLpIndex,
      mscLpV35Index,
      mscLpV35TestIndex }
::= { mscLpV35TestResultsTable 1 }

MscLpV35TestResultsEntry ::= SEQUENCE {
   mscLpV35TestElapsedTime
      Counter32,
   mscLpV35TestTimeRemaining
      Unsigned32,
   mscLpV35TestCauseOfTermination
      INTEGER,
   mscLpV35TestBitsTx
      PassportCounter64,
   mscLpV35TestBytesTx
      PassportCounter64,
   mscLpV35TestFrmTx
      PassportCounter64,
   mscLpV35TestBitsRx
      PassportCounter64,
   mscLpV35TestBytesRx
      PassportCounter64,
   mscLpV35TestFrmRx
      PassportCounter64,
   mscLpV35TestErroredFrmRx
      PassportCounter64,
   mscLpV35TestBitErrorRate
      AsciiString }

mscLpV35TestElapsedTime OBJECT-TYPE
   SYNTAX     Counter32 
   ACCESS     read-only
   STATUS     mandatory
   DESCRIPTION
     "This attribute is the number of minutes elapsed since the test started 
      for an externalLoop test. For a data test, this is the time since test 
      data was first transmitted."
::= { mscLpV35TestResultsEntry 1 }

mscLpV35TestTimeRemaining OBJECT-TYPE
   SYNTAX     Unsigned32 (0..4294967295)
   ACCESS     read-only
   STATUS     mandatory
   DESCRIPTION
     "This attribute is the number of minutes remaining before the test is 
      to be stopped according to the duration attribute."
   DEFVAL     { 0 }
::= { mscLpV35TestResultsEntry 2 }

mscLpV35TestCauseOfTermination OBJECT-TYPE
   SYNTAX     INTEGER  {
                 testTimeExpired(0),
                 stoppedByOperator(1),
                 unknown(2),
                 neverStarted(3),
                 testRunning(4),
                 hardwareReconfigured(5),
                 loopCodeSyncFailed(6),
                 patternSyncFailed(7),
                 patternSyncLost(8) }
   ACCESS     read-only
   STATUS     mandatory
   DESCRIPTION
     "This attribute indicates either the status of the test or the cause of 
      the test's termination:
      
      neverStarted indicates that the test has not yet been started.
      
      testRunning indicates that the test has been started.
      
      stoppedByOperator indicates that the operator issued a stop 
      command on a test that was running.
      
      testTimeExpired indicates that the test ran for the time specified by 
      the test's duration.
      
      loopCodeSyncFailed indicates that the local end failed to 
      synchronize to the loopCode pattern. The local end transmits the 
      loopCode pattern to cause the remote end to apply a loopback, after 
      which the local end should receive the loopCode pattern. The exact 
      pattern used to request loopCode depends on the test type. This 
      failure indicates a high rate of transmission errors, or that the 
      remote end has failed to apply the loopback.
      
      patternSyncFailed indicates that the local end failed to synchronize 
      to the frmPatternType test pattern, that should have been looped 
      back at the remote end. This failure indicates a high rate of 
      transmission errors or the absence of a loopback.
      
      patternSyncLost indicates that the local end gained and then lost 
      synchronization to the returned frmPatternType test pattern. This 
      failure indicates a sudden increase in transmission errors, frame 
      slippage, or the removal of an existing loopback.
      
      unknown is set when a reason to terminate other than those listed 
      here is encountered.
      
      Note: Only MSA cards support recognition of the failures 
      loopCodeSyncFailed, patternSyncFailed and patternSyncLost. 
      Other cards will not terminate the test under the conditions 
      described by these values."
   DEFVAL     { neverStarted }
::= { mscLpV35TestResultsEntry 3 }

mscLpV35TestBitsTx OBJECT-TYPE
   SYNTAX     PassportCounter64 
   ACCESS     read-only
   STATUS     mandatory
   DESCRIPTION
     "This attribute is the total number of bits sent during the test period. 
      As long as the line speed of the hardware interface is less than 
      70 Mbit/s, this counter is not expected to reach the maximum value."
::= { mscLpV35TestResultsEntry 4 }

mscLpV35TestBytesTx OBJECT-TYPE
   SYNTAX     PassportCounter64 
   ACCESS     read-only
   STATUS     mandatory
   DESCRIPTION
     "This attribute is the total number of bytes sent during the test 
      period. This counter is not expected to reach its maximum value."
::= { mscLpV35TestResultsEntry 5 }

mscLpV35TestFrmTx OBJECT-TYPE
   SYNTAX     PassportCounter64 
   ACCESS     read-only
   STATUS     mandatory
   DESCRIPTION
     "This attribute is the total number of frames sent during the test 
      period. This counter is not expected to reach its maximum value."
::= { mscLpV35TestResultsEntry 6 }

mscLpV35TestBitsRx OBJECT-TYPE
   SYNTAX     PassportCounter64 
   ACCESS     read-only
   STATUS     mandatory
   DESCRIPTION
     "This attribute is the total number of bits received during the test 
      period. This counter is not expected to reach its maximum value. 
      The counter will wrap around to 0 if it does reach the maximum 
      value."
::= { mscLpV35TestResultsEntry 7 }

mscLpV35TestBytesRx OBJECT-TYPE
   SYNTAX     PassportCounter64 
   ACCESS     read-only
   STATUS     mandatory
   DESCRIPTION
     "This attribute is the total number of bytes received during the test 
      period. This counter is not expected to reach its maximum value. 
      The counter will wrap around to 0 if it does reach its maximum 
      value."
::= { mscLpV35TestResultsEntry 8 }

mscLpV35TestFrmRx OBJECT-TYPE
   SYNTAX     PassportCounter64 
   ACCESS     read-only
   STATUS     mandatory
   DESCRIPTION
     "This attribute is the total number of frames received during the test 
      period. This counter is not expected to reach its maximum value. 
      The counter will wrap around to 0 if it does reach its maximum 
      value."
::= { mscLpV35TestResultsEntry 9 }

mscLpV35TestErroredFrmRx OBJECT-TYPE
   SYNTAX     PassportCounter64 
   ACCESS     read-only
   STATUS     mandatory
   DESCRIPTION
     "This attribute is not displayed for ATM cards because the physical 
      layer drops all errored frames at the controller interface. 
      
      For all other card types, this attribute is the total number of errored 
      frames received during the test period. This counter is not expected 
      to reach its maximum value. The counter will wrap around to 0 if it 
      does reach its maximum value."
::= { mscLpV35TestResultsEntry 10 }

mscLpV35TestBitErrorRate OBJECT-TYPE
   SYNTAX     AsciiString (SIZE (5))
   ACCESS     read-only
   STATUS     mandatory
   DESCRIPTION
     "This attribute is not displayed for ATM cards because the physical 
      layer drops all errored frames at the controller interface. 
      
      For all other card types, this attribute is the calculated bit error rate 
      on the link. Test data are generated and sent in frames of a preset 
      size (frameSize). The Test component will try to estimate the 
      number of bit errors in any errored frame which is identifiable. The 
      statistics will be updated accordingly. A lost frame (may be due to 
      an error on the flag sequence) will be discarded for the bit error rate 
      calculation. The result is presented in the form of xEsyy, where x is 
      the mantissa, syy is the exponent, for example 0E+00, 2E-09.
      Note that the bitErrorRate is an estimate only. For more reliable test 
      results, the test should be done over a long period. Multiple tests 
      would also improve the confidence level of the test results."
::= { mscLpV35TestResultsEntry 11 }


-- 
-- Lp/n X21/n
-- 
-- The X21 component controls a Passport V.11 interface.

mscLpX21 OBJECT IDENTIFIER ::= { mscLp 10 }



mscLpX21RowStatusTable OBJECT-TYPE
   SYNTAX     SEQUENCE OF MscLpX21RowStatusEntry
   ACCESS     not-accessible
   STATUS     mandatory
   DESCRIPTION
     "This entry controls the addition and deletion of 
      mscLpX21 components."
::= { mscLpX21 1 }

mscLpX21RowStatusEntry OBJECT-TYPE
   SYNTAX     MscLpX21RowStatusEntry
   ACCESS     not-accessible
   STATUS     mandatory
   DESCRIPTION
     "A single entry in the table represents a single 
      mscLpX21 component."
   INDEX {
      mscLpIndex,
      mscLpX21Index }
::= { mscLpX21RowStatusTable 1 }

MscLpX21RowStatusEntry ::= SEQUENCE {
   mscLpX21RowStatus
      RowStatus,
   mscLpX21ComponentName
      DisplayString,
   mscLpX21StorageType
      StorageType,
   mscLpX21Index
      Integer32 }

mscLpX21RowStatus OBJECT-TYPE
   SYNTAX     RowStatus 
   ACCESS     read-write
   STATUS     mandatory
   DESCRIPTION
     "This variable is used as the basis for SNMP naming of
      mscLpX21 components.
      These components can be added and deleted."
::= { mscLpX21RowStatusEntry 1 }

mscLpX21ComponentName OBJECT-TYPE
   SYNTAX     DisplayString 
   ACCESS     read-only
   STATUS     mandatory
   DESCRIPTION
     "This variable provides the component's string name for
      use with the ASCII Console Interface"
::= { mscLpX21RowStatusEntry 2 }

mscLpX21StorageType OBJECT-TYPE
   SYNTAX     StorageType 
   ACCESS     read-only
   STATUS     mandatory
   DESCRIPTION
     "This variable represents the storage type value for the
      mscLpX21 tables."
::= { mscLpX21RowStatusEntry 4 }

mscLpX21Index OBJECT-TYPE
   SYNTAX     Integer32 (0..7)
   ACCESS     not-accessible
   STATUS     mandatory
   DESCRIPTION
     "This variable represents the index for the mscLpX21 tables."
::= { mscLpX21RowStatusEntry 10 }

mscLpX21ProvTable OBJECT-TYPE
   SYNTAX     SEQUENCE OF MscLpX21ProvEntry
   ACCESS     not-accessible
   STATUS     mandatory
   DESCRIPTION
     "This group contains all specific provisioning data for an X21 
      component."
::= { mscLpX21 10 }

mscLpX21ProvEntry OBJECT-TYPE
   SYNTAX     MscLpX21ProvEntry
   ACCESS     not-accessible
   STATUS     mandatory
   DESCRIPTION
     "An entry in the mscLpX21ProvTable."
   INDEX {
      mscLpIndex,
      mscLpX21Index }
::= { mscLpX21ProvTable 1 }

MscLpX21ProvEntry ::= SEQUENCE {
   mscLpX21LinkMode
      INTEGER,
   mscLpX21ReadyLineState
      OCTET STRING,
   mscLpX21DataTransferLineState
      OCTET STRING,
   mscLpX21LineStatusTimeOut
      Unsigned32,
   mscLpX21LineSpeed
      Unsigned32,
   mscLpX21ClockingSource
      INTEGER,
   mscLpX21DteDataClockSource
      INTEGER,
   mscLpX21LineTerminationRequired
      INTEGER,
   mscLpX21ApplicationFramerName
      Link,
   mscLpX21EnableDynamicSpeed
      INTEGER }

mscLpX21LinkMode OBJECT-TYPE
   SYNTAX     INTEGER  {
                 dte(0),
                 dce(128) }
   ACCESS     read-write
   STATUS     mandatory
   DESCRIPTION
     "This attribute defines the intended gender of the X21 component 
      (V.11 interface). The actual gender of the interface is determined by 
      the physical connection to the patch panel. If the hardware setup 
      does not match this attribute, an alarm will be generated.
      
      In dte mode, the control line signal is driven as specified by the 
      attribute readyLineState when the interface passes its initial 
      diagnostics. Then, the control line signal will be driven as specified 
      in the attribute dataTransferLineState when the application is ready 
      to transfer data. On the other hand, the input line signal (indication) 
      is compared against those specified in the attributes readyLineState 
      and dataTransferLineState. The application will be notified when 
      the specified line states are observed.
      
      In dce mode, the X21 component behaves similarly as when it is in 
      dte mode. However, it will be driving the DCE line signal (control) 
      and monitoring the DTE line signal (indication) as specified by the 
      attributes readyLineState and dataTransferLineState."
   DEFVAL     { dte }
::= { mscLpX21ProvEntry 1 }

mscLpX21ReadyLineState OBJECT-TYPE
   SYNTAX     OCTET STRING (SIZE (1))
   ACCESS     read-write
   STATUS     mandatory
   DESCRIPTION
     "This attribute specifies the line signals originating from the V.11 
      interface that will always be turned on, provided the interface passes 
      its diagnostics. This set of signals is generally required to maintain 
      the connection. Note that both DTE and DCE signals are specified 
      in this attribute. The appropriate set of specified signals will be 
      turned on or checked according to the actualLinkMode.
      See also linkMode.

      Description of bits:
      indication(0)
      control(1)"
   DEFVAL     { 'c0'H }
::= { mscLpX21ProvEntry 2 }

mscLpX21DataTransferLineState OBJECT-TYPE
   SYNTAX     OCTET STRING (SIZE (1))
   ACCESS     read-write
   STATUS     mandatory
   DESCRIPTION
     "The state of the line signals required to indicate that the external 
      equipment is in a good state (that is, data transfer can proceed). 
      Note that both DTE and DCE signals are specified in this attribute. 
      The appropriate set of specified signals will be turned on or checked 
      according to the actualLinkMode. The value of this attribute must 
      be a superset of that of the readyLineState attribute.
      See also linkMode.

      Description of bits:
      indication(0)
      control(1)"
   DEFVAL     { 'c0'H }
::= { mscLpX21ProvEntry 3 }

mscLpX21LineStatusTimeOut OBJECT-TYPE
   SYNTAX     Unsigned32 (10..20000)
   ACCESS     read-write
   STATUS     mandatory
   DESCRIPTION
     "This attribute defines the time the line state must be stable (good or 
      bad) before a state change is declared."
   DEFVAL     { 1000 }
::= { mscLpX21ProvEntry 4 }

mscLpX21LineSpeed OBJECT-TYPE
   SYNTAX     Unsigned32 (9600..7680000)
   ACCESS     read-write
   STATUS     mandatory
   DESCRIPTION
     "This attribute defines the speed of the line for source clocking. This 
      attribute is ignored if the interface is not providing a clock. The 
      clock rate is rounded up to the nearest available value. Note that the 
      actual clock rates are available in the operational attributes 
      actualTxLineSpeed and actualRxLineSpeed. The actual lineSpeeds 
      configurable on a V.11 DCE interface are: 7680000, 3840000, 
      2560000, 2048000, 1920000, 1536000, 1344000, 1280000, 
      1024000, 960000, 768000, 672000, 640000, 512000, 448000, 
      384000, 336000, 320000, 256000, 224000, 192000, 168000, 
      128000, 112000, 64000, 56000, 48000, 32000, 19200, 9600. Note 
      that linspeeds of 1024000 and 2048000 cannot be provisioned on 
      cards that have ports provisioned at 3840000, 2560000, 1920000, 
      1280000, 960000, 640000 or 320000."
   DEFVAL     { 192000 }
::= { mscLpX21ProvEntry 5 }

mscLpX21ClockingSource OBJECT-TYPE
   SYNTAX     INTEGER  {
                 local(0),
                 module(1) }
   ACCESS     read-write
   STATUS     mandatory
   DESCRIPTION
     "This attribute defines the source of synchronization of the outgoing 
      clocks. This attribute is only used when the actualLinkMode is dce.
      
      If the value of the attribute is local, the outgoing clocks are 
      synchronized to a local oscillator on the FP.
      
      If the value of the attribute is module, the outgoing clocks are 
      synchronized to the oscillator on the active CP."
::= { mscLpX21ProvEntry 6 }

mscLpX21DteDataClockSource OBJECT-TYPE
   SYNTAX     INTEGER  {
                 fromDce(0),
                 fromDte(2) }
   ACCESS     read-write
   STATUS     mandatory
   DESCRIPTION
     "This attribute is only used when the actualLinkMode is dce. It is 
      used to determine the clock to be used to recover the receive data. 
      Note that a V.11 DTE interface uses the S clock (see X.21 standard) 
      for both receive data and transmit data timing. The DTE interface 
      always loops the received S clock back to the DCE as the X clock 
      (see X.21 standard).
      
      If the value of the attribute is fromDce, the DCE V.11 interface uses 
      the internally generated transmit clock as the S clock and for both 
      receive and transmit data timing. The X clock is ignored.
      
      If the value of the attribute is fromDte, the DCE still uses the 
      internally generated transmit clock as the S clock and for transmit 
      data timing, but the receive data timing is derived from the X clock.
      
      The fromDte mode is recommended when the DTE is far away from 
      the DCE interface."
   DEFVAL     { fromDce }
::= { mscLpX21ProvEntry 7 }

mscLpX21LineTerminationRequired OBJECT-TYPE
   SYNTAX     INTEGER  {
                 no(0),
                 yes(1) }
   ACCESS     read-write
   STATUS     mandatory
   DESCRIPTION
     "This attribute specifies whether termination is required for this 
      interface. If the hardware setup does not match this attribute, an 
      alarm will be generated."
   DEFVAL     { yes }
::= { mscLpX21ProvEntry 8 }

mscLpX21ApplicationFramerName OBJECT-TYPE
   SYNTAX     Link 
   ACCESS     read-write
   STATUS     mandatory
   DESCRIPTION
     "This attribute contains the component name of a Framer which is 
      associated with the X21 component."
::= { mscLpX21ProvEntry 9 }

mscLpX21EnableDynamicSpeed OBJECT-TYPE
   SYNTAX     INTEGER  {
                 no(0),
                 yes(1) }
   ACCESS     read-write
   STATUS     mandatory
   DESCRIPTION
     "When set to yes, this attribute specifies that the transmit link speed 
      should be set to the calculated receiver link speed. This attribute can 
      be set to yes only if the linkMode is dce and the 
      dteDataClockSource is fromDte.."
   DEFVAL     { no }
::= { mscLpX21ProvEntry 10 }

mscLpX21CidDataTable OBJECT-TYPE
   SYNTAX     SEQUENCE OF MscLpX21CidDataEntry
   ACCESS     not-accessible
   STATUS     mandatory
   DESCRIPTION
     "This group contains the attribute for a component's Customer 
      Identifier (CID). Refer to the attribute description for a detailed 
      explanation of CIDs."
::= { mscLpX21 11 }

mscLpX21CidDataEntry OBJECT-TYPE
   SYNTAX     MscLpX21CidDataEntry
   ACCESS     not-accessible
   STATUS     mandatory
   DESCRIPTION
     "An entry in the mscLpX21CidDataTable."
   INDEX {
      mscLpIndex,
      mscLpX21Index }
::= { mscLpX21CidDataTable 1 }

MscLpX21CidDataEntry ::= SEQUENCE {
   mscLpX21CustomerIdentifier
      Unsigned32 }

mscLpX21CustomerIdentifier OBJECT-TYPE
   SYNTAX     Unsigned32 (0 | 1..8191)
   ACCESS     read-write
   STATUS     mandatory
   DESCRIPTION
     "This attribute holds the Customer Identifier (CID).
      
      Every component has a CID. If a component has a cid attribute, the 
      component's CID is the provisioned value of that attribute; 
      otherwise the component inherits the CID of its parent. The top-
      level component has a CID of 0.
      
      Every operator session also has a CID, which is the CID 
      provisioned for the operator's user ID. An operator will see only the 
      stream data for components having a matching CID. Also, the 
      operator will be allowed to issue commands for only those 
      components which have a matching CID.
      
      An operator CID of 0 is used to identify the Network Manager 
      (referred to as 'NetMan' in DPN). This CID matches the CID of 
      any component. Values 1 to 8191 inclusive (equivalent to 'basic 
      CIDs' in DPN) may be assigned to specific customers."
   DEFVAL     { 0 }
::= { mscLpX21CidDataEntry 1 }

mscLpX21AdminInfoTable OBJECT-TYPE
   SYNTAX     SEQUENCE OF MscLpX21AdminInfoEntry
   ACCESS     not-accessible
   STATUS     mandatory
   DESCRIPTION
     "This group contains the attributes pertaining to the vendor of the 
      equipment."
::= { mscLpX21 12 }

mscLpX21AdminInfoEntry OBJECT-TYPE
   SYNTAX     MscLpX21AdminInfoEntry
   ACCESS     not-accessible
   STATUS     mandatory
   DESCRIPTION
     "An entry in the mscLpX21AdminInfoTable."
   INDEX {
      mscLpIndex,
      mscLpX21Index }
::= { mscLpX21AdminInfoTable 1 }

MscLpX21AdminInfoEntry ::= SEQUENCE {
   mscLpX21Vendor
      AsciiString,
   mscLpX21CommentText
      AsciiString }

mscLpX21Vendor OBJECT-TYPE
   SYNTAX     AsciiString (SIZE (0..20))
   ACCESS     read-write
   STATUS     mandatory
   DESCRIPTION
     "This is the name of the vendor supplying the facility."
::= { mscLpX21AdminInfoEntry 1 }

mscLpX21CommentText OBJECT-TYPE
   SYNTAX     AsciiString (SIZE (0..60))
   ACCESS     read-write
   STATUS     mandatory
   DESCRIPTION
     "Any miscellaneous text about the facility."
::= { mscLpX21AdminInfoEntry 2 }

mscLpX21IfEntryTable OBJECT-TYPE
   SYNTAX     SEQUENCE OF MscLpX21IfEntryEntry
   ACCESS     not-accessible
   STATUS     mandatory
   DESCRIPTION
     "This group contains the provisionable attributes for the ifEntry."
::= { mscLpX21 13 }

mscLpX21IfEntryEntry OBJECT-TYPE
   SYNTAX     MscLpX21IfEntryEntry
   ACCESS     not-accessible
   STATUS     mandatory
   DESCRIPTION
     "An entry in the mscLpX21IfEntryTable."
   INDEX {
      mscLpIndex,
      mscLpX21Index }
::= { mscLpX21IfEntryTable 1 }

MscLpX21IfEntryEntry ::= SEQUENCE {
   mscLpX21IfAdminStatus
      INTEGER,
   mscLpX21IfIndex
      InterfaceIndex }

mscLpX21IfAdminStatus OBJECT-TYPE
   SYNTAX     INTEGER  {
                 up(1),
                 down(2),
                 testing(3) }
   ACCESS     read-write
   STATUS     mandatory
   DESCRIPTION
     "The desired state of the interface. The up state indicates the 
      interface is operational. The down state indicates the interface is not 
      operational. The testing state indicates that no operational packets 
      can be passed."
   DEFVAL     { up }
::= { mscLpX21IfEntryEntry 1 }

mscLpX21IfIndex OBJECT-TYPE
   SYNTAX     InterfaceIndex (1..65535)
   ACCESS     read-only
   STATUS     mandatory
   DESCRIPTION
     "This is the index for the IfEntry. Its value is automatically initialized 
      during the provisioning process."
::= { mscLpX21IfEntryEntry 2 }

mscLpX21OperStatusTable OBJECT-TYPE
   SYNTAX     SEQUENCE OF MscLpX21OperStatusEntry
   ACCESS     not-accessible
   STATUS     mandatory
   DESCRIPTION
     "This group includes the Operational Status attribute. This attribute 
      defines the current operational state of this component."
::= { mscLpX21 14 }

mscLpX21OperStatusEntry OBJECT-TYPE
   SYNTAX     MscLpX21OperStatusEntry
   ACCESS     not-accessible
   STATUS     mandatory
   DESCRIPTION
     "An entry in the mscLpX21OperStatusTable."
   INDEX {
      mscLpIndex,
      mscLpX21Index }
::= { mscLpX21OperStatusTable 1 }

MscLpX21OperStatusEntry ::= SEQUENCE {
   mscLpX21SnmpOperStatus
      INTEGER }

mscLpX21SnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { mscLpX21OperStatusEntry 1 }

mscLpX21StateTable OBJECT-TYPE
   SYNTAX     SEQUENCE OF MscLpX21StateEntry
   ACCESS     not-accessible
   STATUS     mandatory
   DESCRIPTION
     "This group contains the three OSI State attributes and the six OSI 
      Status attributes. The descriptions generically indicate what each 
      attribute implies about the component. Note that not all the values 
      and state combinations described here are supported by every 
      component which uses this group. For component-specific 
      information and the valid state combinations, refer to NTP 241-
      7001-150, Passport Operations and Maintenance Guide."
::= { mscLpX21 15 }

mscLpX21StateEntry OBJECT-TYPE
   SYNTAX     MscLpX21StateEntry
   ACCESS     not-accessible
   STATUS     mandatory
   DESCRIPTION
     "An entry in the mscLpX21StateTable."
   INDEX {
      mscLpIndex,
      mscLpX21Index }
::= { mscLpX21StateTable 1 }

MscLpX21StateEntry ::= SEQUENCE {
   mscLpX21AdminState
      INTEGER,
   mscLpX21OperationalState
      INTEGER,
   mscLpX21UsageState
      INTEGER,
   mscLpX21AvailabilityStatus
      OCTET STRING,
   mscLpX21ProceduralStatus
      OCTET STRING,
   mscLpX21ControlStatus
      OCTET STRING,
   mscLpX21AlarmStatus
      OCTET STRING,
   mscLpX21StandbyStatus
      INTEGER,
   mscLpX21UnknownStatus
      INTEGER }

mscLpX21AdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component.
      
      The OSI Status attributes, if supported by the component, may 
      provide more details, qualifying the state of the component."
   DEFVAL     { unlocked }
::= { mscLpX21StateEntry 1 }

mscLpX21OperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle.
      
      The OSI Status attributes, if supported by the component, may 
      provide more details, qualifying the state of the component."
   DEFVAL     { disabled }
::= { mscLpX21StateEntry 2 }

mscLpX21UsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time.
      
      The OSI Status attributes, if supported by the component, may 
      provide more details, qualifying the state of the component."
   DEFVAL     { idle }
::= { mscLpX21StateEntry 3 }

mscLpX21AvailabilityStatus OBJECT-TYPE
   SYNTAX     OCTET STRING (SIZE (2))
   ACCESS     read-only
   STATUS     mandatory
   DESCRIPTION
     "If supported by the component, this attribute indicates the OSI 
      Availability status of the component. Note that, even though it is 
      defined as a multi-valued set, at most one value is shown to the user.
      
      When no values are in the set, this indicates that either the attribute 
      is not supported or that none of the status conditions described 
      below are present.
      
      The value inTest indicates that the resource is undergoing a test 
      procedure. If adminState is locked or shuttingDown, the normal 
      users are precluded from using the resource and controlStatus is 
      reservedForTest. Tests that do not exclude additional users can be 
      present in any operational or administrative state but the 
      reservedForTest condition should not be present.
      
      The value failed indicates that the component has an internal fault 
      that prevents it from operating. The operationalState is disabled.
      
      The value dependency indicates that the component cannot operate 
      because some other resource on which it depends is unavailable. 
      The operationalState is disabled.
      
      The value powerOff indicates the resource requires power to be 
      applied and it is not powered on. The operationalState is disabled.
      
      The value offLine indicates the resource requires a routine 
      operation (either manual, automatic, or both) to be performed to 
      place it on-line and make it available for use. The operationalState 
      is disabled.
      
      The value offDuty indicates the resource is inactive in accordance 
      with a predetermined time schedule. In the absence of other 
      disabling conditions, the operationalState is enabled or disabled.
      
      The value degraded indicates the service provided by the 
      component is degraded in some way, such as in speed or operating 
      capacity. However, the resource remains available for service. The 
      operationalState is enabled.
      
      The value notInstalled indicates the resource is not present. The 
      operationalState is disabled.
      
      The value logFull is not used.

      Description of bits:
      inTest(0)
      failed(1)
      powerOff(2)
      offLine(3)
      offDuty(4)
      dependency(5)
      degraded(6)
      notInstalled(7)
      logFull(8)"
::= { mscLpX21StateEntry 4 }

mscLpX21ProceduralStatus OBJECT-TYPE
   SYNTAX     OCTET STRING (SIZE (1))
   ACCESS     read-only
   STATUS     mandatory
   DESCRIPTION
     "If supported by the component, this attribute indicates the OSI 
      Procedural status of the component. Note that, even though it is 
      defined as a multi-valued set, at most one value is shown to the user.
      
      When no values are in the set, this indicates that either the attribute 
      is not supported or that none of the status conditions described 
      below are present.
      
      The value initializationRequired indicates (for a resource which 
      doesn't initialize autonomously) that initialization is required before 
      it can perform its normal functions, and this procedure has not been 
      initiated. The operationalState is disabled.
      
      The value notInitialized indicates (for a resource which does 
      initialize autonomously) that initialization is required before it can 
      perform its normal functions, and this procedure has not been 
      initiated. The operationalState may be enabled or disabled.
      
      The value initializing indicates that initialization has been initiated 
      but is not yet complete. The operationalState may be enabled or 
      disabled.
      
      The value reporting indicates the resource has completed some 
      processing operation and is notifying the results. The 
      operationalState is enabled.
      
      The value terminating indicates the component is in a termination 
      phase. If the resource doesn't reinitialize autonomously, 
      operationalState is disabled; otherwise it is enabled or disabled.

      Description of bits:
      initializationRequired(0)
      notInitialized(1)
      initializing(2)
      reporting(3)
      terminating(4)"
::= { mscLpX21StateEntry 5 }

mscLpX21ControlStatus OBJECT-TYPE
   SYNTAX     OCTET STRING (SIZE (1))
   ACCESS     read-only
   STATUS     mandatory
   DESCRIPTION
     "If supported by the component, this attribute indicates the OSI 
      Control status of the component. Note that, even though it is defined 
      as a multi-valued set, at most one value is shown to the user.
      
      When no values are in the set, this indicates that either the attribute 
      is not supported or that none of the status conditions described 
      below are present.
      
      The value subjectToTest indicates the resource is available but tests 
      may be conducted simultaneously at unpredictable times, which 
      may cause it to exhibit unusual characteristics.
      
      The value partOfServicesLocked indicates that part of the service is 
      restricted from users of a resource. The adminState is unlocked.
      
      The value reservedForTest indicates that the component is 
      administratively unavailable because it is undergoing a test 
      procedure. The adminState is locked.
      
      The value suspended indicates that the service has been 
      administratively suspended.

      Description of bits:
      subjectToTest(0)
      partOfServicesLocked(1)
      reservedForTest(2)
      suspended(3)"
::= { mscLpX21StateEntry 6 }

mscLpX21AlarmStatus OBJECT-TYPE
   SYNTAX     OCTET STRING (SIZE (1))
   ACCESS     read-only
   STATUS     mandatory
   DESCRIPTION
     "If supported by the component, this attribute indicates the OSI 
      Alarm status of the component. Note that, even though it is defined 
      as a multi-valued set, at most one value is shown to the user.
      
      When no values are in the set, this indicates that either the attribute 
      is not supported or that none of the status conditions described 
      below are present.
      
      The value underRepair indicates the component is currently being 
      repaired. The operationalState is enabled or disabled.
      
      The value critical indicates one or more critical alarms are 
      outstanding against the component. Other, less severe, alarms may 
      also be outstanding. The operationalState is enabled or disabled.
      
      The value major indicates one or more major alarms are 
      outstanding against the component. Other, less severe, alarms may 
      also be outstanding. The operationalState is enabled or disabled.
      
      The value minor indicates one or more minor alarms are 
      outstanding against the component. Other, less severe, alarms may 
      also be outstanding. The operationalState is enabled or disabled.
      
      The value alarmOutstanding generically indicates that an alarm of 
      some severity is outstanding against the component.

      Description of bits:
      underRepair(0)
      critical(1)
      major(2)
      minor(3)
      alarmOutstanding(4)"
::= { mscLpX21StateEntry 7 }

mscLpX21StandbyStatus OBJECT-TYPE
   SYNTAX     INTEGER  {
                 hotStandby(0),
                 coldStandby(1),
                 providingService(2),
                 notSet(15) }
   ACCESS     read-only
   STATUS     mandatory
   DESCRIPTION
     "If supported by the component, this attribute indicates the OSI 
      Standby status of the component.
      
      The value notSet indicates that either the attribute is not supported 
      or that none of the status conditions described below are present. 
      Note that this is a non-standard value, used because the original 
      specification indicated this attribute was set-valued and thus, did not 
      provide a value to indicate that none of the other three are 
      applicable.
      
      The value hotStandby indicates that the resource is not providing 
      service but will be immediately able to take over the role of the 
      resource to be backed up, without initialization activity, and 
      containing the same information as the resource to be backed up.
      
      The value coldStandby indicates the resource is a backup for 
      another resource but will not be immediately able to take over the 
      role of the backed up resource and will require some initialization 
      activity.
      
      The value providingService indicates that this component, as a 
      backup resource, is currently backing up another resource."
   DEFVAL     { notSet }
::= { mscLpX21StateEntry 8 }

mscLpX21UnknownStatus OBJECT-TYPE
   SYNTAX     INTEGER  {
                 false(0),
                 true(1) }
   ACCESS     read-only
   STATUS     mandatory
   DESCRIPTION
     "This attribute indicates the OSI Unknown status of the component.
      
      The value false indicates that all of the other OSI State and Status 
      attribute values can be considered accurate.
      
      The value true indicates that the actual state of the component is not 
      known for sure."
   DEFVAL     { false }
::= { mscLpX21StateEntry 9 }

mscLpX21OperTable OBJECT-TYPE
   SYNTAX     SEQUENCE OF MscLpX21OperEntry
   ACCESS     not-accessible
   STATUS     mandatory
   DESCRIPTION
     "This group contains all specific operational data for an X21 
      component."
::= { mscLpX21 16 }

mscLpX21OperEntry OBJECT-TYPE
   SYNTAX     MscLpX21OperEntry
   ACCESS     not-accessible
   STATUS     mandatory
   DESCRIPTION
     "An entry in the mscLpX21OperTable."
   INDEX {
      mscLpIndex,
      mscLpX21Index }
::= { mscLpX21OperTable 1 }

MscLpX21OperEntry ::= SEQUENCE {
   mscLpX21ActualLinkMode
      INTEGER,
   mscLpX21LineState
      OCTET STRING,
   mscLpX21ActualTxLineSpeed
      Gauge32,
   mscLpX21ActualRxLineSpeed
      Gauge32,
   mscLpX21DataXferStateChanges
      Counter32 }

mscLpX21ActualLinkMode OBJECT-TYPE
   SYNTAX     INTEGER  {
                 dte(0),
                 dce(128) }
   ACCESS     read-only
   STATUS     mandatory
   DESCRIPTION
     "This attribute contains the actual link mode defined by the 
      hardware. Note that the hardware overrides the provisionable data. 
      The interface behaves as a DCE or DTE according to the 
      actualLinkMode."
::= { mscLpX21OperEntry 1 }

mscLpX21LineState OBJECT-TYPE
   SYNTAX     OCTET STRING (SIZE (1))
   ACCESS     read-only
   STATUS     mandatory
   DESCRIPTION
     "This attribute contains the current state of the interface signals.

      Description of bits:
      indication(0)
      control(1)"
::= { mscLpX21OperEntry 2 }

mscLpX21ActualTxLineSpeed OBJECT-TYPE
   SYNTAX     Gauge32 (0..4294967295)
   ACCESS     read-only
   STATUS     mandatory
   DESCRIPTION
     "This attribute is the measured speed of the transmit clock."
::= { mscLpX21OperEntry 3 }

mscLpX21ActualRxLineSpeed OBJECT-TYPE
   SYNTAX     Gauge32 (0..4294967295)
   ACCESS     read-only
   STATUS     mandatory
   DESCRIPTION
     "This attribute is the measured speed of the receive clock."
::= { mscLpX21OperEntry 4 }

mscLpX21DataXferStateChanges OBJECT-TYPE
   SYNTAX     Counter32 
   ACCESS     read-only
   STATUS     mandatory
   DESCRIPTION
     "This attribute contains the number of times that the line has entered 
      or exited the data transfer state."
::= { mscLpX21OperEntry 5 }


-- 
-- The Test component is configured to control a hardware facility test 
-- on a physical (V35, X21, DS1, E1, DS3, E3 etc.) or a logical port.

mscLpX21Test OBJECT IDENTIFIER ::= { mscLpX21 2 }



mscLpX21TestRowStatusTable OBJECT-TYPE
   SYNTAX     SEQUENCE OF MscLpX21TestRowStatusEntry
   ACCESS     not-accessible
   STATUS     mandatory
   DESCRIPTION
     "This entry controls the addition and deletion of 
      mscLpX21Test components."
::= { mscLpX21Test 1 }

mscLpX21TestRowStatusEntry OBJECT-TYPE
   SYNTAX     MscLpX21TestRowStatusEntry
   ACCESS     not-accessible
   STATUS     mandatory
   DESCRIPTION
     "A single entry in the table represents a single 
      mscLpX21Test component."
   INDEX {
      mscLpIndex,
      mscLpX21Index,
      mscLpX21TestIndex }
::= { mscLpX21TestRowStatusTable 1 }

MscLpX21TestRowStatusEntry ::= SEQUENCE {
   mscLpX21TestRowStatus
      RowStatus,
   mscLpX21TestComponentName
      DisplayString,
   mscLpX21TestStorageType
      StorageType,
   mscLpX21TestIndex
      NonReplicated }

mscLpX21TestRowStatus OBJECT-TYPE
   SYNTAX     RowStatus 
   ACCESS     read-only
   STATUS     mandatory
   DESCRIPTION
     "This variable is used as the basis for SNMP naming of
      mscLpX21Test components.
      These components cannot be added nor deleted."
::= { mscLpX21TestRowStatusEntry 1 }

mscLpX21TestComponentName OBJECT-TYPE
   SYNTAX     DisplayString 
   ACCESS     read-only
   STATUS     mandatory
   DESCRIPTION
     "This variable provides the component's string name for
      use with the ASCII Console Interface"
::= { mscLpX21TestRowStatusEntry 2 }

mscLpX21TestStorageType OBJECT-TYPE
   SYNTAX     StorageType 
   ACCESS     read-only
   STATUS     mandatory
   DESCRIPTION
     "This variable represents the storage type value for the
      mscLpX21Test tables."
::= { mscLpX21TestRowStatusEntry 4 }

mscLpX21TestIndex OBJECT-TYPE
   SYNTAX     NonReplicated 
   ACCESS     not-accessible
   STATUS     mandatory
   DESCRIPTION
     "This variable represents the index for the mscLpX21Test tables."
::= { mscLpX21TestRowStatusEntry 10 }

mscLpX21TestStateTable OBJECT-TYPE
   SYNTAX     SEQUENCE OF MscLpX21TestStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscLpX21Test 10 }

mscLpX21TestStateEntry OBJECT-TYPE
   SYNTAX     MscLpX21TestStateEntry
   ACCESS     not-accessible
   STATUS     mandatory
   DESCRIPTION
     "An entry in the mscLpX21TestStateTable."
   INDEX {
      mscLpIndex,
      mscLpX21Index,
      mscLpX21TestIndex }
::= { mscLpX21TestStateTable 1 }

MscLpX21TestStateEntry ::= SEQUENCE {
   mscLpX21TestAdminState
      INTEGER,
   mscLpX21TestOperationalState
      INTEGER,
   mscLpX21TestUsageState
      INTEGER }

mscLpX21TestAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscLpX21TestStateEntry 1 }

mscLpX21TestOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscLpX21TestStateEntry 2 }

mscLpX21TestUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscLpX21TestStateEntry 3 }

mscLpX21TestSetupTable OBJECT-TYPE
   SYNTAX     SEQUENCE OF MscLpX21TestSetupEntry
   ACCESS     not-accessible
   STATUS     mandatory
   DESCRIPTION
     "This group contains all of the operational data for a Test 
      component."
::= { mscLpX21Test 11 }

mscLpX21TestSetupEntry OBJECT-TYPE
   SYNTAX     MscLpX21TestSetupEntry
   ACCESS     not-accessible
   STATUS     mandatory
   DESCRIPTION
     "An entry in the mscLpX21TestSetupTable."
   INDEX {
      mscLpIndex,
      mscLpX21Index,
      mscLpX21TestIndex }
::= { mscLpX21TestSetupTable 1 }

MscLpX21TestSetupEntry ::= SEQUENCE {
   mscLpX21TestPurpose
      AsciiString,
   mscLpX21TestType
      INTEGER,
   mscLpX21TestFrmSize
      Unsigned32,
   mscLpX21TestFrmPatternType
      INTEGER,
   mscLpX21TestCustomizedPattern
      Hex,
   mscLpX21TestDataStartDelay
      Unsigned32,
   mscLpX21TestDisplayInterval
      Unsigned32,
   mscLpX21TestDuration
      Unsigned32 }

mscLpX21TestPurpose OBJECT-TYPE
   SYNTAX     AsciiString (SIZE (0..40))
   ACCESS     read-write
   STATUS     mandatory
   DESCRIPTION
     "This attribute records the purpose of the test so that the test results 
      can be associated and properly analyzed."
::= { mscLpX21TestSetupEntry 1 }

mscLpX21TestType OBJECT-TYPE
   SYNTAX     INTEGER  {
                 card(0),
                 manual(1),
                 localLoop(2),
                 remoteLoop(3),
                 externalLoop(4),
                 payloadLoop(5),
                 remoteLoopThisTrib(6),
                 v54RemoteLoop(7),
                 pn127RemoteLoop(8) }
   ACCESS     read-write
   STATUS     mandatory
   DESCRIPTION
     "This attribute is the type of test to be run. The available test types 
      include the following:
      card test sets up an internal loop on the board and runs a bit error 
      rate test.
      manual test assumes the line is looped back externally and a bit 
      error rate test is performed.
      localLoop test loops back the local modem and performs a bit error 
      rate test.
      remoteLoop test loops back the remote modem (or CSU) and 
      performs a bit error rate test.
      externalLoop test loops back the line to the far end.
      payloadLoop test only loops back the payload data received from 
      the incoming line.
      remoteLoopThisTrib loops this particular tributary back at the far 
      end, using services provided by the parent.
      v54RemoteLoop initiates a V.54 Remote Loopback test.
      pn127RemoteLoop initiates a PN127 Remote Loopback test.
      Note that not all test types are not supported by all function 
      processors."
   DEFVAL     { card }
::= { mscLpX21TestSetupEntry 2 }

mscLpX21TestFrmSize OBJECT-TYPE
   SYNTAX     Unsigned32 (4..4096)
   ACCESS     read-write
   STATUS     mandatory
   DESCRIPTION
     "This attribute defines the size of the test data frames in number of 
      bytes."
   DEFVAL     { 1024 }
::= { mscLpX21TestSetupEntry 3 }

mscLpX21TestFrmPatternType OBJECT-TYPE
   SYNTAX     INTEGER  {
                 ccitt32kBitPattern(0),
                 ccitt8MBitPattern(1),
                 customizedPattern(2) }
   ACCESS     read-write
   STATUS     mandatory
   DESCRIPTION
     "This attribute defines the type of data pattern generation to use. The 
      following lists the available pattern types:
      ccitt32kBitPattern is a pseudo-random sequence of 32 kbit.
      ccitt8MBitPattern is a pseudo-random sequence of 8Mbit.
      customizedPattern is the pattern defined in the customizedPattern 
      attribute."
   DEFVAL     { ccitt32kBitPattern }
::= { mscLpX21TestSetupEntry 4 }

mscLpX21TestCustomizedPattern OBJECT-TYPE
   SYNTAX     Hex (0..4294967295)
   ACCESS     read-write
   STATUS     mandatory
   DESCRIPTION
     "This attribute allows a customized 32 bit pattern to be defined for 
      use in the test data frames. This attribute is used when the attribute 
      frmPatternType is set to CustomizedPattern. Note that a 55 hex 
      pattern is an alternating 1 and 0 pattern."
   DEFVAL     { 1431655765 }
::= { mscLpX21TestSetupEntry 5 }

mscLpX21TestDataStartDelay OBJECT-TYPE
   SYNTAX     Unsigned32 (0..1814400)
   ACCESS     read-write
   STATUS     mandatory
   DESCRIPTION
     "This attribute specifies the time delay (in seconds) between when 
      the test expects the loop to have been set up, to when the test data 
      actually starts to be transmitted. This attribute is to accommodate 
      some non-standard equipment that requires extra time for setting up 
      a requested loop.
      This attribute is ignored when the test type is set to externalLoop."
   DEFVAL     { 0 }
::= { mscLpX21TestSetupEntry 6 }

mscLpX21TestDisplayInterval OBJECT-TYPE
   SYNTAX     Unsigned32 (0..30240)
   ACCESS     read-write
   STATUS     mandatory
   DESCRIPTION
     "This attribute defines the interval (in minutes) between which 
      interim test results are to be displayed. Results are displayed at the 
      operator console at which the test was started. When the test type is 
      set to externalLoop, this attribute is ignored. There will be no 
      display of results if displayInterval is set to 0. This attribute can be 
      changed anytime."
   DEFVAL     { 5 }
::= { mscLpX21TestSetupEntry 7 }

mscLpX21TestDuration OBJECT-TYPE
   SYNTAX     Unsigned32 (1..30240)
   ACCESS     read-write
   STATUS     mandatory
   DESCRIPTION
     "This attribute is the duration (in minutes) that test data will be 
      transmitted. In the case of an externalLoop, this is the time that the 
      loop is in effect. Note that dataStartDelay does not apply to the 
      externalLoop."
   DEFVAL     { 1 }
::= { mscLpX21TestSetupEntry 8 }

mscLpX21TestResultsTable OBJECT-TYPE
   SYNTAX     SEQUENCE OF MscLpX21TestResultsEntry
   ACCESS     not-accessible
   STATUS     mandatory
   DESCRIPTION
     "This group contains all the statistics related attributes of the Test 
      component."
::= { mscLpX21Test 12 }

mscLpX21TestResultsEntry OBJECT-TYPE
   SYNTAX     MscLpX21TestResultsEntry
   ACCESS     not-accessible
   STATUS     mandatory
   DESCRIPTION
     "An entry in the mscLpX21TestResultsTable."
   INDEX {
      mscLpIndex,
      mscLpX21Index,
      mscLpX21TestIndex }
::= { mscLpX21TestResultsTable 1 }

MscLpX21TestResultsEntry ::= SEQUENCE {
   mscLpX21TestElapsedTime
      Counter32,
   mscLpX21TestTimeRemaining
      Unsigned32,
   mscLpX21TestCauseOfTermination
      INTEGER,
   mscLpX21TestBitsTx
      PassportCounter64,
   mscLpX21TestBytesTx
      PassportCounter64,
   mscLpX21TestFrmTx
      PassportCounter64,
   mscLpX21TestBitsRx
      PassportCounter64,
   mscLpX21TestBytesRx
      PassportCounter64,
   mscLpX21TestFrmRx
      PassportCounter64,
   mscLpX21TestErroredFrmRx
      PassportCounter64,
   mscLpX21TestBitErrorRate
      AsciiString }

mscLpX21TestElapsedTime OBJECT-TYPE
   SYNTAX     Counter32 
   ACCESS     read-only
   STATUS     mandatory
   DESCRIPTION
     "This attribute is the number of minutes elapsed since the test started 
      for an externalLoop test. For a data test, this is the time since test 
      data was first transmitted."
::= { mscLpX21TestResultsEntry 1 }

mscLpX21TestTimeRemaining OBJECT-TYPE
   SYNTAX     Unsigned32 (0..4294967295)
   ACCESS     read-only
   STATUS     mandatory
   DESCRIPTION
     "This attribute is the number of minutes remaining before the test is 
      to be stopped according to the duration attribute."
   DEFVAL     { 0 }
::= { mscLpX21TestResultsEntry 2 }

mscLpX21TestCauseOfTermination OBJECT-TYPE
   SYNTAX     INTEGER  {
                 testTimeExpired(0),
                 stoppedByOperator(1),
                 unknown(2),
                 neverStarted(3),
                 testRunning(4),
                 hardwareReconfigured(5),
                 loopCodeSyncFailed(6),
                 patternSyncFailed(7),
                 patternSyncLost(8) }
   ACCESS     read-only
   STATUS     mandatory
   DESCRIPTION
     "This attribute indicates either the status of the test or the cause of 
      the test's termination:
      
      neverStarted indicates that the test has not yet been started.
      
      testRunning indicates that the test has been started.
      
      stoppedByOperator indicates that the operator issued a stop 
      command on a test that was running.
      
      testTimeExpired indicates that the test ran for the time specified by 
      the test's duration.
      
      loopCodeSyncFailed indicates that the local end failed to 
      synchronize to the loopCode pattern. The local end transmits the 
      loopCode pattern to cause the remote end to apply a loopback, after 
      which the local end should receive the loopCode pattern. The exact 
      pattern used to request loopCode depends on the test type. This 
      failure indicates a high rate of transmission errors, or that the 
      remote end has failed to apply the loopback.
      
      patternSyncFailed indicates that the local end failed to synchronize 
      to the frmPatternType test pattern, that should have been looped 
      back at the remote end. This failure indicates a high rate of 
      transmission errors or the absence of a loopback.
      
      patternSyncLost indicates that the local end gained and then lost 
      synchronization to the returned frmPatternType test pattern. This 
      failure indicates a sudden increase in transmission errors, frame 
      slippage, or the removal of an existing loopback.
      
      unknown is set when a reason to terminate other than those listed 
      here is encountered.
      
      Note: Only MSA cards support recognition of the failures 
      loopCodeSyncFailed, patternSyncFailed and patternSyncLost. 
      Other cards will not terminate the test under the conditions 
      described by these values."
   DEFVAL     { neverStarted }
::= { mscLpX21TestResultsEntry 3 }

mscLpX21TestBitsTx OBJECT-TYPE
   SYNTAX     PassportCounter64 
   ACCESS     read-only
   STATUS     mandatory
   DESCRIPTION
     "This attribute is the total number of bits sent during the test period. 
      As long as the line speed of the hardware interface is less than 
      70 Mbit/s, this counter is not expected to reach the maximum value."
::= { mscLpX21TestResultsEntry 4 }

mscLpX21TestBytesTx OBJECT-TYPE
   SYNTAX     PassportCounter64 
   ACCESS     read-only
   STATUS     mandatory
   DESCRIPTION
     "This attribute is the total number of bytes sent during the test 
      period. This counter is not expected to reach its maximum value."
::= { mscLpX21TestResultsEntry 5 }

mscLpX21TestFrmTx OBJECT-TYPE
   SYNTAX     PassportCounter64 
   ACCESS     read-only
   STATUS     mandatory
   DESCRIPTION
     "This attribute is the total number of frames sent during the test 
      period. This counter is not expected to reach its maximum value."
::= { mscLpX21TestResultsEntry 6 }

mscLpX21TestBitsRx OBJECT-TYPE
   SYNTAX     PassportCounter64 
   ACCESS     read-only
   STATUS     mandatory
   DESCRIPTION
     "This attribute is the total number of bits received during the test 
      period. This counter is not expected to reach its maximum value. 
      The counter will wrap around to 0 if it does reach the maximum 
      value."
::= { mscLpX21TestResultsEntry 7 }

mscLpX21TestBytesRx OBJECT-TYPE
   SYNTAX     PassportCounter64 
   ACCESS     read-only
   STATUS     mandatory
   DESCRIPTION
     "This attribute is the total number of bytes received during the test 
      period. This counter is not expected to reach its maximum value. 
      The counter will wrap around to 0 if it does reach its maximum 
      value."
::= { mscLpX21TestResultsEntry 8 }

mscLpX21TestFrmRx OBJECT-TYPE
   SYNTAX     PassportCounter64 
   ACCESS     read-only
   STATUS     mandatory
   DESCRIPTION
     "This attribute is the total number of frames received during the test 
      period. This counter is not expected to reach its maximum value. 
      The counter will wrap around to 0 if it does reach its maximum 
      value."
::= { mscLpX21TestResultsEntry 9 }

mscLpX21TestErroredFrmRx OBJECT-TYPE
   SYNTAX     PassportCounter64 
   ACCESS     read-only
   STATUS     mandatory
   DESCRIPTION
     "This attribute is not displayed for ATM cards because the physical 
      layer drops all errored frames at the controller interface. 
      
      For all other card types, this attribute is the total number of errored 
      frames received during the test period. This counter is not expected 
      to reach its maximum value. The counter will wrap around to 0 if it 
      does reach its maximum value."
::= { mscLpX21TestResultsEntry 10 }

mscLpX21TestBitErrorRate OBJECT-TYPE
   SYNTAX     AsciiString (SIZE (5))
   ACCESS     read-only
   STATUS     mandatory
   DESCRIPTION
     "This attribute is not displayed for ATM cards because the physical 
      layer drops all errored frames at the controller interface. 
      
      For all other card types, this attribute is the calculated bit error rate 
      on the link. Test data are generated and sent in frames of a preset 
      size (frameSize). The Test component will try to estimate the 
      number of bit errors in any errored frame which is identifiable. The 
      statistics will be updated accordingly. A lost frame (may be due to 
      an error on the flag sequence) will be discarded for the bit error rate 
      calculation. The result is presented in the form of xEsyy, where x is 
      the mantissa, syy is the exponent, for example 0E+00, 2E-09.
      Note that the bitErrorRate is an estimate only. For more reliable test 
      results, the test should be done over a long period. Multiple tests 
      would also improve the confidence level of the test results."
::= { mscLpX21TestResultsEntry 11 }


-- ApmSonet
-- The Lp/m Sonet/n component controls an OC-3 port on an OC-3 
-- Function Processor. In particular, it deals with SONET medium, 
-- section and line layers. 
-- Note that there can be Sonet and Sdh components coexisting under 
-- the same LP. However they cannot use the same instance.

mscLpSonet OBJECT IDENTIFIER ::= { mscLp 14 }



mscLpSonetRowStatusTable OBJECT-TYPE
   SYNTAX     SEQUENCE OF MscLpSonetRowStatusEntry
   ACCESS     not-accessible
   STATUS     mandatory
   DESCRIPTION
     "This entry controls the addition and deletion of 
      mscLpSonet components."
::= { mscLpSonet 1 }

mscLpSonetRowStatusEntry OBJECT-TYPE
   SYNTAX     MscLpSonetRowStatusEntry
   ACCESS     not-accessible
   STATUS     mandatory
   DESCRIPTION
     "A single entry in the table represents a single 
      mscLpSonet component."
   INDEX {
      mscLpIndex,
      mscLpSonetIndex }
::= { mscLpSonetRowStatusTable 1 }

MscLpSonetRowStatusEntry ::= SEQUENCE {
   mscLpSonetRowStatus
      RowStatus,
   mscLpSonetComponentName
      DisplayString,
   mscLpSonetStorageType
      StorageType,
   mscLpSonetIndex
      Integer32 }

mscLpSonetRowStatus OBJECT-TYPE
   SYNTAX     RowStatus 
   ACCESS     read-write
   STATUS     mandatory
   DESCRIPTION
     "This variable is used as the basis for SNMP naming of
      mscLpSonet components.
      These components can be added and deleted."
::= { mscLpSonetRowStatusEntry 1 }

mscLpSonetComponentName OBJECT-TYPE
   SYNTAX     DisplayString 
   ACCESS     read-only
   STATUS     mandatory
   DESCRIPTION
     "This variable provides the component's string name for
      use with the ASCII Console Interface"
::= { mscLpSonetRowStatusEntry 2 }

mscLpSonetStorageType OBJECT-TYPE
   SYNTAX     StorageType 
   ACCESS     read-only
   STATUS     mandatory
   DESCRIPTION
     "This variable represents the storage type value for the
      mscLpSonet tables."
::= { mscLpSonetRowStatusEntry 4 }

mscLpSonetIndex OBJECT-TYPE
   SYNTAX     Integer32 (0..3)
   ACCESS     not-accessible
   STATUS     mandatory
   DESCRIPTION
     "This variable represents the index for the mscLpSonet tables."
::= { mscLpSonetRowStatusEntry 10 }

mscLpSonetProvTable OBJECT-TYPE
   SYNTAX     SEQUENCE OF MscLpSonetProvEntry
   ACCESS     not-accessible
   STATUS     mandatory
   DESCRIPTION
     "This group contains all of the provisioning data for a Sonet or Sdh 
      component."
::= { mscLpSonet 10 }

mscLpSonetProvEntry OBJECT-TYPE
   SYNTAX     MscLpSonetProvEntry
   ACCESS     not-accessible
   STATUS     mandatory
   DESCRIPTION
     "An entry in the mscLpSonetProvTable."
   INDEX {
      mscLpIndex,
      mscLpSonetIndex }
::= { mscLpSonetProvTable 1 }

MscLpSonetProvEntry ::= SEQUENCE {
   mscLpSonetClockingSource
      INTEGER }

mscLpSonetClockingSource OBJECT-TYPE
   SYNTAX     INTEGER  {
                 local(0),
                 line(1),
                 module(2) }
   ACCESS     read-write
   STATUS     mandatory
   DESCRIPTION
     "This attribute defines the type of clocking source used for 
      synchronizing the OC-3 transmit clock: local means direct use of 
      the local clock oscillator at its centre frequency; line means the use 
      of a signal phase-locked to the incoming OC-3 line rate; module 
      means the use of a signal phase-locked to the CP reference clock. 
      When adding a Sonet/Sdh component, the clockingSource attribute 
      is set to module if the NetworkSynchronization component has 
      been added and is set to local otherwise.
      Note that the multiport OC-3 cell-based cards has one common 
      clock source for each of the three ports when either the clocking 
      source local or module is selected. For this reason, it is not allowed 
      to have at the same time the clockingSource attribute set to local on 
      one port and module on another port. Furthermore, the 
      clockingSource attribute cannot be set to module if the 
      NetworkSynchronization component has not been added."
::= { mscLpSonetProvEntry 1 }

mscLpSonetCidDataTable OBJECT-TYPE
   SYNTAX     SEQUENCE OF MscLpSonetCidDataEntry
   ACCESS     not-accessible
   STATUS     mandatory
   DESCRIPTION
     "This group contains the attribute for a component's Customer 
      Identifier (CID). Refer to the attribute description for a detailed 
      explanation of CIDs."
::= { mscLpSonet 11 }

mscLpSonetCidDataEntry OBJECT-TYPE
   SYNTAX     MscLpSonetCidDataEntry
   ACCESS     not-accessible
   STATUS     mandatory
   DESCRIPTION
     "An entry in the mscLpSonetCidDataTable."
   INDEX {
      mscLpIndex,
      mscLpSonetIndex }
::= { mscLpSonetCidDataTable 1 }

MscLpSonetCidDataEntry ::= SEQUENCE {
   mscLpSonetCustomerIdentifier
      Unsigned32 }

mscLpSonetCustomerIdentifier OBJECT-TYPE
   SYNTAX     Unsigned32 (0 | 1..8191)
   ACCESS     read-write
   STATUS     mandatory
   DESCRIPTION
     "This attribute holds the Customer Identifier (CID).
      
      Every component has a CID. If a component has a cid attribute, the 
      component's CID is the provisioned value of that attribute; 
      otherwise the component inherits the CID of its parent. The top-
      level component has a CID of 0.
      
      Every operator session also has a CID, which is the CID 
      provisioned for the operator's user ID. An operator will see only the 
      stream data for components having a matching CID. Also, the 
      operator will be allowed to issue commands for only those 
      components which have a matching CID.
      
      An operator CID of 0 is used to identify the Network Manager 
      (referred to as 'NetMan' in DPN). This CID matches the CID of 
      any component. Values 1 to 8191 inclusive (equivalent to 'basic 
      CIDs' in DPN) may be assigned to specific customers."
   DEFVAL     { 0 }
::= { mscLpSonetCidDataEntry 1 }

mscLpSonetAdminInfoTable OBJECT-TYPE
   SYNTAX     SEQUENCE OF MscLpSonetAdminInfoEntry
   ACCESS     not-accessible
   STATUS     mandatory
   DESCRIPTION
     "This group contains the attributes pertaining to the vendor of the 
      equipment."
::= { mscLpSonet 12 }

mscLpSonetAdminInfoEntry OBJECT-TYPE
   SYNTAX     MscLpSonetAdminInfoEntry
   ACCESS     not-accessible
   STATUS     mandatory
   DESCRIPTION
     "An entry in the mscLpSonetAdminInfoTable."
   INDEX {
      mscLpIndex,
      mscLpSonetIndex }
::= { mscLpSonetAdminInfoTable 1 }

MscLpSonetAdminInfoEntry ::= SEQUENCE {
   mscLpSonetVendor
      AsciiString,
   mscLpSonetCommentText
      AsciiString }

mscLpSonetVendor OBJECT-TYPE
   SYNTAX     AsciiString (SIZE (0..20))
   ACCESS     read-write
   STATUS     mandatory
   DESCRIPTION
     "This is the name of the vendor supplying the facility."
::= { mscLpSonetAdminInfoEntry 1 }

mscLpSonetCommentText OBJECT-TYPE
   SYNTAX     AsciiString (SIZE (0..60))
   ACCESS     read-write
   STATUS     mandatory
   DESCRIPTION
     "Any miscellaneous text about the facility."
::= { mscLpSonetAdminInfoEntry 2 }

mscLpSonetIfEntryTable OBJECT-TYPE
   SYNTAX     SEQUENCE OF MscLpSonetIfEntryEntry
   ACCESS     not-accessible
   STATUS     mandatory
   DESCRIPTION
     "This group contains the provisionable attributes for the ifEntry."
::= { mscLpSonet 13 }

mscLpSonetIfEntryEntry OBJECT-TYPE
   SYNTAX     MscLpSonetIfEntryEntry
   ACCESS     not-accessible
   STATUS     mandatory
   DESCRIPTION
     "An entry in the mscLpSonetIfEntryTable."
   INDEX {
      mscLpIndex,
      mscLpSonetIndex }
::= { mscLpSonetIfEntryTable 1 }

MscLpSonetIfEntryEntry ::= SEQUENCE {
   mscLpSonetIfAdminStatus
      INTEGER,
   mscLpSonetIfIndex
      InterfaceIndex }

mscLpSonetIfAdminStatus OBJECT-TYPE
   SYNTAX     INTEGER  {
                 up(1),
                 down(2),
                 testing(3) }
   ACCESS     read-write
   STATUS     mandatory
   DESCRIPTION
     "The desired state of the interface. The up state indicates the 
      interface is operational. The down state indicates the interface is not 
      operational. The testing state indicates that no operational packets 
      can be passed."
   DEFVAL     { up }
::= { mscLpSonetIfEntryEntry 1 }

mscLpSonetIfIndex OBJECT-TYPE
   SYNTAX     InterfaceIndex (1..65535)
   ACCESS     read-only
   STATUS     mandatory
   DESCRIPTION
     "This is the index for the IfEntry. Its value is automatically initialized 
      during the provisioning process."
::= { mscLpSonetIfEntryEntry 2 }

mscLpSonetOperStatusTable OBJECT-TYPE
   SYNTAX     SEQUENCE OF MscLpSonetOperStatusEntry
   ACCESS     not-accessible
   STATUS     mandatory
   DESCRIPTION
     "This group includes the Operational Status attribute. This attribute 
      defines the current operational state of this component."
::= { mscLpSonet 14 }

mscLpSonetOperStatusEntry OBJECT-TYPE
   SYNTAX     MscLpSonetOperStatusEntry
   ACCESS     not-accessible
   STATUS     mandatory
   DESCRIPTION
     "An entry in the mscLpSonetOperStatusTable."
   INDEX {
      mscLpIndex,
      mscLpSonetIndex }
::= { mscLpSonetOperStatusTable 1 }

MscLpSonetOperStatusEntry ::= SEQUENCE {
   mscLpSonetSnmpOperStatus
      INTEGER }

mscLpSonetSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { mscLpSonetOperStatusEntry 1 }

mscLpSonetStateTable OBJECT-TYPE
   SYNTAX     SEQUENCE OF MscLpSonetStateEntry
   ACCESS     not-accessible
   STATUS     mandatory
   DESCRIPTION
     "This group contains the three OSI State attributes and the six OSI 
      Status attributes. The descriptions generically indicate what each 
      attribute implies about the component. Note that not all the values 
      and state combinations described here are supported by every 
      component which uses this group. For component-specific 
      information and the valid state combinations, refer to NTP 241-
      7001-150, Passport Operations and Maintenance Guide."
::= { mscLpSonet 15 }

mscLpSonetStateEntry OBJECT-TYPE
   SYNTAX     MscLpSonetStateEntry
   ACCESS     not-accessible
   STATUS     mandatory
   DESCRIPTION
     "An entry in the mscLpSonetStateTable."
   INDEX {
      mscLpIndex,
      mscLpSonetIndex }
::= { mscLpSonetStateTable 1 }

MscLpSonetStateEntry ::= SEQUENCE {
   mscLpSonetAdminState
      INTEGER,
   mscLpSonetOperationalState
      INTEGER,
   mscLpSonetUsageState
      INTEGER,
   mscLpSonetAvailabilityStatus
      OCTET STRING,
   mscLpSonetProceduralStatus
      OCTET STRING,
   mscLpSonetControlStatus
      OCTET STRING,
   mscLpSonetAlarmStatus
      OCTET STRING,
   mscLpSonetStandbyStatus
      INTEGER,
   mscLpSonetUnknownStatus
      INTEGER }

mscLpSonetAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component.
      
      The OSI Status attributes, if supported by the component, may 
      provide more details, qualifying the state of the component."
   DEFVAL     { unlocked }
::= { mscLpSonetStateEntry 1 }

mscLpSonetOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle.
      
      The OSI Status attributes, if supported by the component, may 
      provide more details, qualifying the state of the component."
   DEFVAL     { disabled }
::= { mscLpSonetStateEntry 2 }

mscLpSonetUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time.
      
      The OSI Status attributes, if supported by the component, may 
      provide more details, qualifying the state of the component."
   DEFVAL     { idle }
::= { mscLpSonetStateEntry 3 }

mscLpSonetAvailabilityStatus OBJECT-TYPE
   SYNTAX     OCTET STRING (SIZE (2))
   ACCESS     read-only
   STATUS     mandatory
   DESCRIPTION
     "If supported by the component, this attribute indicates the OSI 
      Availability status of the component. Note that, even though it is 
      defined as a multi-valued set, at most one value is shown to the user.
      
      When no values are in the set, this indicates that either the attribute 
      is not supported or that none of the status conditions described 
      below are present.
      
      The value inTest indicates that the resource is undergoing a test 
      procedure. If adminState is locked or shuttingDown, the normal 
      users are precluded from using the resource and controlStatus is 
      reservedForTest. Tests that do not exclude additional users can be 
      present in any operational or administrative state but the 
      reservedForTest condition should not be present.
      
      The value failed indicates that the component has an internal fault 
      that prevents it from operating. The operationalState is disabled.
      
      The value dependency indicates that the component cannot operate 
      because some other resource on which it depends is unavailable. 
      The operationalState is disabled.
      
      The value powerOff indicates the resource requires power to be 
      applied and it is not powered on. The operationalState is disabled.
      
      The value offLine indicates the resource requires a routine 
      operation (either manual, automatic, or both) to be performed to 
      place it on-line and make it available for use. The operationalState 
      is disabled.
      
      The value offDuty indicates the resource is inactive in accordance 
      with a predetermined time schedule. In the absence of other 
      disabling conditions, the operationalState is enabled or disabled.
      
      The value degraded indicates the service provided by the 
      component is degraded in some way, such as in speed or operating 
      capacity. However, the resource remains available for service. The 
      operationalState is enabled.
      
      The value notInstalled indicates the resource is not present. The 
      operationalState is disabled.
      
      The value logFull is not used.

      Description of bits:
      inTest(0)
      failed(1)
      powerOff(2)
      offLine(3)
      offDuty(4)
      dependency(5)
      degraded(6)
      notInstalled(7)
      logFull(8)"
::= { mscLpSonetStateEntry 4 }

mscLpSonetProceduralStatus OBJECT-TYPE
   SYNTAX     OCTET STRING (SIZE (1))
   ACCESS     read-only
   STATUS     mandatory
   DESCRIPTION
     "If supported by the component, this attribute indicates the OSI 
      Procedural status of the component. Note that, even though it is 
      defined as a multi-valued set, at most one value is shown to the user.
      
      When no values are in the set, this indicates that either the attribute 
      is not supported or that none of the status conditions described 
      below are present.
      
      The value initializationRequired indicates (for a resource which 
      doesn't initialize autonomously) that initialization is required before 
      it can perform its normal functions, and this procedure has not been 
      initiated. The operationalState is disabled.
      
      The value notInitialized indicates (for a resource which does 
      initialize autonomously) that initialization is required before it can 
      perform its normal functions, and this procedure has not been 
      initiated. The operationalState may be enabled or disabled.
      
      The value initializing indicates that initialization has been initiated 
      but is not yet complete. The operationalState may be enabled or 
      disabled.
      
      The value reporting indicates the resource has completed some 
      processing operation and is notifying the results. The 
      operationalState is enabled.
      
      The value terminating indicates the component is in a termination 
      phase. If the resource doesn't reinitialize autonomously, 
      operationalState is disabled; otherwise it is enabled or disabled.

      Description of bits:
      initializationRequired(0)
      notInitialized(1)
      initializing(2)
      reporting(3)
      terminating(4)"
::= { mscLpSonetStateEntry 5 }

mscLpSonetControlStatus OBJECT-TYPE
   SYNTAX     OCTET STRING (SIZE (1))
   ACCESS     read-only
   STATUS     mandatory
   DESCRIPTION
     "If supported by the component, this attribute indicates the OSI 
      Control status of the component. Note that, even though it is defined 
      as a multi-valued set, at most one value is shown to the user.
      
      When no values are in the set, this indicates that either the attribute 
      is not supported or that none of the status conditions described 
      below are present.
      
      The value subjectToTest indicates the resource is available but tests 
      may be conducted simultaneously at unpredictable times, which 
      may cause it to exhibit unusual characteristics.
      
      The value partOfServicesLocked indicates that part of the service is 
      restricted from users of a resource. The adminState is unlocked.
      
      The value reservedForTest indicates that the component is 
      administratively unavailable because it is undergoing a test 
      procedure. The adminState is locked.
      
      The value suspended indicates that the service has been 
      administratively suspended.

      Description of bits:
      subjectToTest(0)
      partOfServicesLocked(1)
      reservedForTest(2)
      suspended(3)"
::= { mscLpSonetStateEntry 6 }

mscLpSonetAlarmStatus OBJECT-TYPE
   SYNTAX     OCTET STRING (SIZE (1))
   ACCESS     read-only
   STATUS     mandatory
   DESCRIPTION
     "If supported by the component, this attribute indicates the OSI 
      Alarm status of the component. Note that, even though it is defined 
      as a multi-valued set, at most one value is shown to the user.
      
      When no values are in the set, this indicates that either the attribute 
      is not supported or that none of the status conditions described 
      below are present.
      
      The value underRepair indicates the component is currently being 
      repaired. The operationalState is enabled or disabled.
      
      The value critical indicates one or more critical alarms are 
      outstanding against the component. Other, less severe, alarms may 
      also be outstanding. The operationalState is enabled or disabled.
      
      The value major indicates one or more major alarms are 
      outstanding against the component. Other, less severe, alarms may 
      also be outstanding. The operationalState is enabled or disabled.
      
      The value minor indicates one or more minor alarms are 
      outstanding against the component. Other, less severe, alarms may 
      also be outstanding. The operationalState is enabled or disabled.
      
      The value alarmOutstanding generically indicates that an alarm of 
      some severity is outstanding against the component.

      Description of bits:
      underRepair(0)
      critical(1)
      major(2)
      minor(3)
      alarmOutstanding(4)"
::= { mscLpSonetStateEntry 7 }

mscLpSonetStandbyStatus OBJECT-TYPE
   SYNTAX     INTEGER  {
                 hotStandby(0),
                 coldStandby(1),
                 providingService(2),
                 notSet(15) }
   ACCESS     read-only
   STATUS     mandatory
   DESCRIPTION
     "If supported by the component, this attribute indicates the OSI 
      Standby status of the component.
      
      The value notSet indicates that either the attribute is not supported 
      or that none of the status conditions described below are present. 
      Note that this is a non-standard value, used because the original 
      specification indicated this attribute was set-valued and thus, did not 
      provide a value to indicate that none of the other three are 
      applicable.
      
      The value hotStandby indicates that the resource is not providing 
      service but will be immediately able to take over the role of the 
      resource to be backed up, without initialization activity, and 
      containing the same information as the resource to be backed up.
      
      The value coldStandby indicates the resource is a backup for 
      another resource but will not be immediately able to take over the 
      role of the backed up resource and will require some initialization 
      activity.
      
      The value providingService indicates that this component, as a 
      backup resource, is currently backing up another resource."
   DEFVAL     { notSet }
::= { mscLpSonetStateEntry 8 }

mscLpSonetUnknownStatus OBJECT-TYPE
   SYNTAX     INTEGER  {
                 false(0),
                 true(1) }
   ACCESS     read-only
   STATUS     mandatory
   DESCRIPTION
     "This attribute indicates the OSI Unknown status of the component.
      
      The value false indicates that all of the other OSI State and Status 
      attribute values can be considered accurate.
      
      The value true indicates that the actual state of the component is not 
      known for sure."
   DEFVAL     { false }
::= { mscLpSonetStateEntry 9 }

mscLpSonetOperTable OBJECT-TYPE
   SYNTAX     SEQUENCE OF MscLpSonetOperEntry
   ACCESS     not-accessible
   STATUS     mandatory
   DESCRIPTION
     "This group contains the common operational data for Sonet or Sdh 
      component."
::= { mscLpSonet 16 }

mscLpSonetOperEntry OBJECT-TYPE
   SYNTAX     MscLpSonetOperEntry
   ACCESS     not-accessible
   STATUS     mandatory
   DESCRIPTION
     "An entry in the mscLpSonetOperTable."
   INDEX {
      mscLpIndex,
      mscLpSonetIndex }
::= { mscLpSonetOperTable 1 }

MscLpSonetOperEntry ::= SEQUENCE {
   mscLpSonetLosAlarm
      INTEGER,
   mscLpSonetLofAlarm
      INTEGER,
   mscLpSonetRxAisAlarm
      INTEGER,
   mscLpSonetRxRfiAlarm
      INTEGER,
   mscLpSonetTxAis
      INTEGER,
   mscLpSonetTxRdi
      INTEGER,
   mscLpSonetUnusableTxClockRefAlarm
      INTEGER }

mscLpSonetLosAlarm OBJECT-TYPE
   SYNTAX     INTEGER  {
                 on(0),
                 off(1) }
   ACCESS     read-only
   STATUS     mandatory
   DESCRIPTION
     "This attribute indicates whether a Loss Of Signal (LOS) alarm state 
      has been entered. An LOS alarm state is entered when LOS defects 
      have been observed and accumulated for a period of 2.5 seconds +/- 
      0.5 seconds, or if an LOS defect is present when the criteria for 
      LOF failure declaration have been met. A LOS defect is declared 
      when 20+/-3 us of all-zeros pattern is detected. The LOS defect is 
      cleared when two valid framing words are detected and no Loss Of 
      Signal condition is detected during an interval of 20+/-3 us. If the 
      LOS defects are intermittently occurring, the LOS defect 
      accumulator is decremented at a rate of 1/10 of the incrementing 
      rate (alarm integration ratio of 1/10), with all measurements based 
      on a 200 ms polling cycle.
      The Sonet/Sdh component goes into an operational state of disabled 
      until the LOS alarm condition is cleared. The LOS alarm state is 
      cleared after LOS defects have been absent for a period of 10 
      seconds +/- 0.5 seconds.
      The losAlarm attribute is always set to off when the component has 
      been locked and left offline."
::= { mscLpSonetOperEntry 1 }

mscLpSonetLofAlarm OBJECT-TYPE
   SYNTAX     INTEGER  {
                 on(0),
                 off(1) }
   ACCESS     read-only
   STATUS     mandatory
   DESCRIPTION
     "This attribute displays whether a Loss Of Frame (LOF) alarm state 
      has been entered. An LOF alarm state is entered when LOF defects 
      have been observed and accumulated for a period of 2.5 seconds +/- 
      0.5 seconds, except when an LOS defect or failure is present. An 
      LOF defect is detected when getting contiguous errored frame 
      alignment for at least 3 msec. If the LOF defects are intermittently 
      occurring, the LOF defect accumulator is decremented at a rate of 
      1/10 of the incrementing rate (alarm integration ratio of 1/10), with 
      all measurements based on a 200 ms polling cycle.
      The Sonet/Sdh component goes into an operational state of disabled 
      until the LOF alarm condition is cleared. The condition is cleared 
      when framing has been achieved for a period of 10 seconds +/- 0.5 
      seconds.
      The lofAlarm attribute is always set to off when the component has 
      been locked and left offline."
::= { mscLpSonetOperEntry 2 }

mscLpSonetRxAisAlarm OBJECT-TYPE
   SYNTAX     INTEGER  {
                 on(0),
                 off(1) }
   ACCESS     read-only
   STATUS     mandatory
   DESCRIPTION
     "This attribute displays whether a Line Alarm Indication Signal (L-
      AIS) alarm state has been entered. An L-AIS alarm state is entered 
      when L-AIS defects have been observed and accumulated for a 
      period of 2.5 seconds +/- 0.5 seconds. The L-AIS defect is the 
      occurrence of the L-AIS signal in five contiguous STS (STM) 
      frames (111 pattern in bits 6,7, and 8 of the K2 bytes). If the L-AIS 
      defects are intermittently occurring, the L-AIS defect accumulator 
      is decremented at a rate of 1/10 of the incrementing rate (alarm 
      integration ratio of 1/10), with all measurements based on a 200 ms 
      polling cycle.
      The Sonet/Sdh component goes into an operational state of disabled 
      until the L-AIS alarm condition is cleared. The condition is cleared 
      after not detecting the L-AIS signal for a period of 10 seconds +/- 
      0.5 seconds.
      The rxAisAlarm attribute is always set to off when the component 
      has been locked and left offline."
::= { mscLpSonetOperEntry 3 }

mscLpSonetRxRfiAlarm OBJECT-TYPE
   SYNTAX     INTEGER  {
                 on(0),
                 off(1) }
   ACCESS     read-only
   STATUS     mandatory
   DESCRIPTION
     "This attribute displays whether a Line Remote Failure Indication 
      (LRFI) alarm state has been entered. An L-RFI alarm state is 
      entered when Line Remote Failure Indication (L-RDI) defects have 
      been observed and accumulated for a period of 2.5 seconds +/- 0.5 
      seconds. The L-RDI defect is the occurrence of the L-RDI signal in 
      five contiguous valid STS (STM) frame (110 pattern in bits 6,7, and 
      8 of the K2 bytes). If the L-RDI defects are intermittently occurring, 
      the L-RDI defect accumulator is decremented at a rate of 1/10 of 
      the incrementing rate (alarm integration ratio of 1/10), with all 
      measurements based on a 200 ms polling cycle.
      The Sonet/Sdh component goes into an operational state of disabled 
      until the L-RFI alarm condition is cleared. The condition is cleared 
      after not detecting the L-RDI signal for a period of 10 seconds +/- 
      0.5 seconds.
      The rxRfiAlarm attribute is always set to off when the component 
      has been locked and left offline."
::= { mscLpSonetOperEntry 4 }

mscLpSonetTxAis OBJECT-TYPE
   SYNTAX     INTEGER  {
                 on(0),
                 off(1) }
   ACCESS     read-only
   STATUS     mandatory
   DESCRIPTION
     "This attribute displays whether the Line Alarm Indication Signal (L-
      AIS) signal is being transmitted on the outgoing line. This signal is 
      transmitted when the Sonet/Sdh is locked and left offline."
::= { mscLpSonetOperEntry 5 }

mscLpSonetTxRdi OBJECT-TYPE
   SYNTAX     INTEGER  {
                 on(0),
                 off(1) }
   ACCESS     read-only
   STATUS     mandatory
   DESCRIPTION
     "This attribute displays whether the Line Remote Defect Indicator 
      (L-RDI) signal is being transmitted over the OC-3 line. The L-RDI 
      signal is transmitted upon the detection of the LOS, LOF or L-AIS 
      defect. This attribute is always set to off when the component has 
      been locked and left offline."
::= { mscLpSonetOperEntry 6 }

mscLpSonetUnusableTxClockRefAlarm OBJECT-TYPE
   SYNTAX     INTEGER  {
                 on(0),
                 off(1) }
   ACCESS     read-only
   STATUS     mandatory
   DESCRIPTION
     "This attribute displays whether an Unusable Transmit Clock 
      Reference (UTCR) alarm state has been entered. A UTCR alarm 
      state is entered when a Sonet/Sdh port provisioned to act as a 
      transmit clock reference has received the code 'do not use for 
      synchronization' in the S1 byte (in the SONET/ SDH line 
      overhead) for 2.5 +/- 0.5 seconds.
      The condition is cleared after not detecting the 'do not use for 
      synchronization' code for a period of 10 +/- 0.5 seconds or when 
      the port is no longer provisioned to act as a transmit clock 
      reference.
      A port is acting as a transmit clock reference if it is provisioned 
      with a) a clockingSource of line, or b) it has been provisioned as a 
      primaryReference, secondaryReference or tertiaryReference in the 
      NetworkSynchronization component.
      The unusableTxClockRefAlarm attribute is always set to off when 
      the component has been locked and left offline."
::= { mscLpSonetOperEntry 7 }

mscLpSonetStatsTable OBJECT-TYPE
   SYNTAX     SEQUENCE OF MscLpSonetStatsEntry
   ACCESS     not-accessible
   STATUS     mandatory
   DESCRIPTION
     "This group contains the statistics data for a Sonet or Sdh 
      component. Each attribute type is a non-negative integer which 
      monotonically increases until it reaches a maximum value, at which 
      point it wraps around and starts increasing again from zero."
::= { mscLpSonet 17 }

mscLpSonetStatsEntry OBJECT-TYPE
   SYNTAX     MscLpSonetStatsEntry
   ACCESS     not-accessible
   STATUS     mandatory
   DESCRIPTION
     "An entry in the mscLpSonetStatsTable."
   INDEX {
      mscLpIndex,
      mscLpSonetIndex }
::= { mscLpSonetStatsTable 1 }

MscLpSonetStatsEntry ::= SEQUENCE {
   mscLpSonetRunningTime
      Counter32,
   mscLpSonetErrorFreeSec
      Counter32,
   mscLpSonetSectCodeViolations
      Counter32,
   mscLpSonetSectErroredSec
      Counter32,
   mscLpSonetSectSevErroredSec
      Counter32,
   mscLpSonetSectLosSec
      Counter32,
   mscLpSonetSectSevErroredFrmSec
      Counter32,
   mscLpSonetSectFailures
      Counter32,
   mscLpSonetLineCodeViolations
      Counter32,
   mscLpSonetLineErroredSec
      Counter32,
   mscLpSonetLineSevErroredSec
      Counter32,
   mscLpSonetLineAisSec
      Counter32,
   mscLpSonetLineUnavailSec
      Counter32,
   mscLpSonetLineFailures
      Counter32,
   mscLpSonetFarEndLineErrorFreeSec
      Counter32,
   mscLpSonetFarEndLineCodeViolations
      Counter32,
   mscLpSonetFarEndLineErroredSec
      Counter32,
   mscLpSonetFarEndLineSevErroredSec
      Counter32,
   mscLpSonetFarEndLineAisSec
      Counter32,
   mscLpSonetFarEndLineUnavailSec
      Counter32,
   mscLpSonetFarEndLineFailures
      Counter32 }

mscLpSonetRunningTime OBJECT-TYPE
   SYNTAX     Counter32 
   ACCESS     read-only
   STATUS     mandatory
   DESCRIPTION
     "This attribute indicates the total number of seconds since the Sonet/
      Sdh component has been activated and been in unlocked state. All 
      the other error counts that follow can be updated when this count is 
      active."
::= { mscLpSonetStatsEntry 1 }

mscLpSonetErrorFreeSec OBJECT-TYPE
   SYNTAX     Counter32 
   ACCESS     read-only
   STATUS     mandatory
   DESCRIPTION
     "This attribute indicates the number of seconds that the Sonet/Sdh 
      component has been in an near-end error free state."
::= { mscLpSonetStatsEntry 2 }

mscLpSonetSectCodeViolations OBJECT-TYPE
   SYNTAX     Counter32 
   ACCESS     read-only
   STATUS     mandatory
   DESCRIPTION
     "This attribute indicates the total number of Section Code Violations 
      (SCVs) detected. A SCV corresponds to section BIP-8 error. SCV 
      counting is inhibited for second intervals where a Section Severely 
      Errored Second (SSES) is counted. The count wraps at its 
      maximum value."
::= { mscLpSonetStatsEntry 3 }

mscLpSonetSectErroredSec OBJECT-TYPE
   SYNTAX     Counter32 
   ACCESS     read-only
   STATUS     mandatory
   DESCRIPTION
     "This attribute indicates the total number of Section Errored Seconds 
      (SESs) that have been counted. A SES is declared for second 
      intervals containing one or more SCVs or one or more Loss Of 
      Signal (LOS) or Severely Errored Frame (SEF) defects. A SEF 
      defect is the occurrence of 4 contiguous errored STS or STM frame 
      alignment words."
::= { mscLpSonetStatsEntry 4 }

mscLpSonetSectSevErroredSec OBJECT-TYPE
   SYNTAX     Counter32 
   ACCESS     read-only
   STATUS     mandatory
   DESCRIPTION
     "This attribute indicates the total number of Section Severely Errored 
      Seconds (SSESs) that have been counted. A SSES is declared for 
      second intervals containing more than x SCVs or one or more LOS 
      or SEF defects. The value of x is 155 for a 155 Mbits/sec interface."
::= { mscLpSonetStatsEntry 5 }

mscLpSonetSectLosSec OBJECT-TYPE
   SYNTAX     Counter32 
   ACCESS     read-only
   STATUS     mandatory
   DESCRIPTION
     "This attribute indicates the total number of Section LOS Seconds 
      (SLOSSs) that have been counted. A SLOSS is declared for second 
      intervals containing one or more LOS defects."
::= { mscLpSonetStatsEntry 6 }

mscLpSonetSectSevErroredFrmSec OBJECT-TYPE
   SYNTAX     Counter32 
   ACCESS     read-only
   STATUS     mandatory
   DESCRIPTION
     "This attribute indicates the total number of Section Severely Errored 
      Frame Seconds (SSEFSs) that have been counted. A SSEFS is 
      declared for second intervals containing one or more SEF defects."
::= { mscLpSonetStatsEntry 7 }

mscLpSonetSectFailures OBJECT-TYPE
   SYNTAX     Counter32 
   ACCESS     read-only
   STATUS     mandatory
   DESCRIPTION
     "This attribute indicates the total number of times that a section 
      failure (LOS or LOF failure) has been declared."
::= { mscLpSonetStatsEntry 8 }

mscLpSonetLineCodeViolations OBJECT-TYPE
   SYNTAX     Counter32 
   ACCESS     read-only
   STATUS     mandatory
   DESCRIPTION
     "This attribute indicates the total number of Line Code Violations 
      (LCVs) detected. A LCV corresponds to a line BIP-24 errors. LCV 
      counting is inhibited for second intervals where a Line Severely 
      Errored Second (LSES) is counted. Counting of LCVs is also 
      inhibited over second intervals where a Line Unavailable Second 
      (LUAS) is counted. The count wraps at its maximum value."
::= { mscLpSonetStatsEntry 9 }

mscLpSonetLineErroredSec OBJECT-TYPE
   SYNTAX     Counter32 
   ACCESS     read-only
   STATUS     mandatory
   DESCRIPTION
     "This attribute indicates the total number of Line Errored Seconds 
      (LESs) that have been counted. A LES is declared for second 
      intervals containing one or more LCVs or one or more line AIS 
      defects. Counting of LES is inhibited over second intervals where a 
      LUAS is counted."
::= { mscLpSonetStatsEntry 10 }

mscLpSonetLineSevErroredSec OBJECT-TYPE
   SYNTAX     Counter32 
   ACCESS     read-only
   STATUS     mandatory
   DESCRIPTION
     "This attribute indicates the total number of Line Severely Errored 
      Seconds (LSESs) that have been counted. A LSES is declared for 
      second intervals containing more than x LCVs or one or more L-
      AIS defects. The value of x is 154 for a 155 Mbits/sec interface. 
      Counting of LSES is inhibited over second intervals where a LUAS 
      is counted."
::= { mscLpSonetStatsEntry 11 }

mscLpSonetLineAisSec OBJECT-TYPE
   SYNTAX     Counter32 
   ACCESS     read-only
   STATUS     mandatory
   DESCRIPTION
     "This attribute indicates the total number of Line AIS Seconds 
      (LAISSs) that have been counted. A LAISS is declared for second 
      intervals containing one or more L-AIS defects. Counting of LAISS 
      is inhibited over second intervals where a LUAS is counted."
::= { mscLpSonetStatsEntry 12 }

mscLpSonetLineUnavailSec OBJECT-TYPE
   SYNTAX     Counter32 
   ACCESS     read-only
   STATUS     mandatory
   DESCRIPTION
     "This attribute indicates the total number of one second intervals for 
      which the STS line is unavailable. The STS line becomes 
      unavailable at the onset of 10 consecutive LSESs. The 10 LSESs are 
      included in the unavailable time. Once unavailable, the STS line 
      becomes available at the onset of 10 contiguous seconds with no 
      LSES. The 10 seconds with no LSES are excluded from the 
      unavailable time. For second intervals where a Line Unavailable 
      Second (LUAS) is counted, counting of LCV, LES, LSES and 
      LAISS is inhibited."
::= { mscLpSonetStatsEntry 13 }

mscLpSonetLineFailures OBJECT-TYPE
   SYNTAX     Counter32 
   ACCESS     read-only
   STATUS     mandatory
   DESCRIPTION
     "This attribute indicates the total number of times that a line failure 
      (L-AIS failure) has been declared."
::= { mscLpSonetStatsEntry 14 }

mscLpSonetFarEndLineErrorFreeSec OBJECT-TYPE
   SYNTAX     Counter32 
   ACCESS     read-only
   STATUS     mandatory
   DESCRIPTION
     "This attribute indicates the number of seconds that the Sonet/Sdh 
      component has been in an far-end error free state."
::= { mscLpSonetStatsEntry 15 }

mscLpSonetFarEndLineCodeViolations OBJECT-TYPE
   SYNTAX     Counter32 
   ACCESS     read-only
   STATUS     mandatory
   DESCRIPTION
     "This attribute indicates the total number of line FEBE detected from 
      the incoming line. The counting of line FEBE is inhibited for 
      second intervals where a Far-End Line Severely Errored Second 
      (FELSES) is counted. Counting of FELCVs is also inhibited over 
      second intervals where a Far-End Line Unavailable Second 
      (FELUAS) is counted. The count wraps at its maximum value."
::= { mscLpSonetStatsEntry 16 }

mscLpSonetFarEndLineErroredSec OBJECT-TYPE
   SYNTAX     Counter32 
   ACCESS     read-only
   STATUS     mandatory
   DESCRIPTION
     "This attribute indicates the total number of Far-End Line Errored 
      Seconds (FELESs) that have been counted. A FELES is declared 
      for second intervals containing one or more Far-End Line CVs 
      (FELCVs) or one or more L-RDI defects. Counting of FELES is 
      inhibited over second intervals where a FELUAS is counted."
::= { mscLpSonetStatsEntry 17 }

mscLpSonetFarEndLineSevErroredSec OBJECT-TYPE
   SYNTAX     Counter32 
   ACCESS     read-only
   STATUS     mandatory
   DESCRIPTION
     "This attribute indicates the total number of Far-End Line Severely 
      Errored Seconds (FELSESs) that have been counted. A FELSES is 
      declared for second intervals containing more than x FELCVs or 
      one or more L-RDI defects. The value of x is 154 for a 155 Mbits/
      sec interface. Counting of FELSES is inhibited over second 
      intervals where a FELUAS is counted."
::= { mscLpSonetStatsEntry 18 }

mscLpSonetFarEndLineAisSec OBJECT-TYPE
   SYNTAX     Counter32 
   ACCESS     read-only
   STATUS     mandatory
   DESCRIPTION
     "This attribute indicates the total number of Far-End Line AIS 
      Seconds (FELAISSs) that have been counted. A FELAISS is 
      declared for second intervals one or more L-RDI defects. Counting 
      of FELAISS is inhibited over second intervals where a FELUAS is 
      counted."
::= { mscLpSonetStatsEntry 19 }

mscLpSonetFarEndLineUnavailSec OBJECT-TYPE
   SYNTAX     Counter32 
   ACCESS     read-only
   STATUS     mandatory
   DESCRIPTION
     "This attribute indicates the total number of one second intervals for 
      which the STS far-end line is unavailable. The STS far-end line 
      becomes unavailable at the onset of 10 consecutive FELSESs. The 
      10 FELSESs are included in the unavailable time. Once unavailable, 
      the STS far-end line becomes available at the onset of 10 
      contiguous seconds with no FELSES. The 10 seconds with no 
      FELSES are excluded from the unavailable time. For second 
      intervals where a Far-End Line Unavailable Second (FELUAS) is 
      counted, counting of FELCV, FELES, FELSES and FELAISS is 
      inhibited."
::= { mscLpSonetStatsEntry 20 }

mscLpSonetFarEndLineFailures OBJECT-TYPE
   SYNTAX     Counter32 
   ACCESS     read-only
   STATUS     mandatory
   DESCRIPTION
     "This attribute indicates the total number of times that a far-end line 
      failure (L-RFI failure) has been declared."
::= { mscLpSonetStatsEntry 21 }


-- ApmSonetSdhPath
-- The Lp/m Sonet/n Path or Lp/m Sdh/n Path component controls a 
-- path signal that is carried within a SONET or SDH signal. The Path 
-- component can only be added under a Sonet or Sdh component.

mscLpSonetPath OBJECT IDENTIFIER ::= { mscLpSonet 2 }



mscLpSonetPathRowStatusTable OBJECT-TYPE
   SYNTAX     SEQUENCE OF MscLpSonetPathRowStatusEntry
   ACCESS     not-accessible
   STATUS     mandatory
   DESCRIPTION
     "This entry controls the addition and deletion of 
      mscLpSonetPath components."
::= { mscLpSonetPath 1 }

mscLpSonetPathRowStatusEntry OBJECT-TYPE
   SYNTAX     MscLpSonetPathRowStatusEntry
   ACCESS     not-accessible
   STATUS     mandatory
   DESCRIPTION
     "A single entry in the table represents a single 
      mscLpSonetPath component."
   INDEX {
      mscLpIndex,
      mscLpSonetIndex,
      mscLpSonetPathIndex }
::= { mscLpSonetPathRowStatusTable 1 }

MscLpSonetPathRowStatusEntry ::= SEQUENCE {
   mscLpSonetPathRowStatus
      RowStatus,
   mscLpSonetPathComponentName
      DisplayString,
   mscLpSonetPathStorageType
      StorageType,
   mscLpSonetPathIndex
      Integer32 }

mscLpSonetPathRowStatus OBJECT-TYPE
   SYNTAX     RowStatus 
   ACCESS     read-write
   STATUS     mandatory
   DESCRIPTION
     "This variable is used as the basis for SNMP naming of
      mscLpSonetPath components.
      These components can be added and deleted."
::= { mscLpSonetPathRowStatusEntry 1 }

mscLpSonetPathComponentName OBJECT-TYPE
   SYNTAX     DisplayString 
   ACCESS     read-only
   STATUS     mandatory
   DESCRIPTION
     "This variable provides the component's string name for
      use with the ASCII Console Interface"
::= { mscLpSonetPathRowStatusEntry 2 }

mscLpSonetPathStorageType OBJECT-TYPE
   SYNTAX     StorageType 
   ACCESS     read-only
   STATUS     mandatory
   DESCRIPTION
     "This variable represents the storage type value for the
      mscLpSonetPath tables."
::= { mscLpSonetPathRowStatusEntry 4 }

mscLpSonetPathIndex OBJECT-TYPE
   SYNTAX     Integer32 (0..0)
   ACCESS     not-accessible
   STATUS     mandatory
   DESCRIPTION
     "This variable represents the index for the mscLpSonetPath tables."
::= { mscLpSonetPathRowStatusEntry 10 }

mscLpSonetPathProvTable OBJECT-TYPE
   SYNTAX     SEQUENCE OF MscLpSonetPathProvEntry
   ACCESS     not-accessible
   STATUS     mandatory
   DESCRIPTION
     "This group contains all of the provisioning data for a Sonet/Sdh 
      Path component."
::= { mscLpSonetPath 10 }

mscLpSonetPathProvEntry OBJECT-TYPE
   SYNTAX     MscLpSonetPathProvEntry
   ACCESS     not-accessible
   STATUS     mandatory
   DESCRIPTION
     "An entry in the mscLpSonetPathProvTable."
   INDEX {
      mscLpIndex,
      mscLpSonetIndex,
      mscLpSonetPathIndex }
::= { mscLpSonetPathProvTable 1 }

MscLpSonetPathProvEntry ::= SEQUENCE {
   mscLpSonetPathApplicationFramerName
      Link }

mscLpSonetPathApplicationFramerName OBJECT-TYPE
   SYNTAX     Link 
   ACCESS     read-write
   STATUS     mandatory
   DESCRIPTION
     "This attribute defines the link to the software stack. It defines which 
      application is running on top of the Path component."
::= { mscLpSonetPathProvEntry 1 }

mscLpSonetPathCidDataTable OBJECT-TYPE
   SYNTAX     SEQUENCE OF MscLpSonetPathCidDataEntry
   ACCESS     not-accessible
   STATUS     mandatory
   DESCRIPTION
     "This group contains the attribute for a component's Customer 
      Identifier (CID). Refer to the attribute description for a detailed 
      explanation of CIDs."
::= { mscLpSonetPath 11 }

mscLpSonetPathCidDataEntry OBJECT-TYPE
   SYNTAX     MscLpSonetPathCidDataEntry
   ACCESS     not-accessible
   STATUS     mandatory
   DESCRIPTION
     "An entry in the mscLpSonetPathCidDataTable."
   INDEX {
      mscLpIndex,
      mscLpSonetIndex,
      mscLpSonetPathIndex }
::= { mscLpSonetPathCidDataTable 1 }

MscLpSonetPathCidDataEntry ::= SEQUENCE {
   mscLpSonetPathCustomerIdentifier
      Unsigned32 }

mscLpSonetPathCustomerIdentifier OBJECT-TYPE
   SYNTAX     Unsigned32 (0 | 1..8191)
   ACCESS     read-write
   STATUS     mandatory
   DESCRIPTION
     "This attribute holds the Customer Identifier (CID).
      
      Every component has a CID. If a component has a cid attribute, the 
      component's CID is the provisioned value of that attribute; 
      otherwise the component inherits the CID of its parent. The top-
      level component has a CID of 0.
      
      Every operator session also has a CID, which is the CID 
      provisioned for the operator's user ID. An operator will see only the 
      stream data for components having a matching CID. Also, the 
      operator will be allowed to issue commands for only those 
      components which have a matching CID.
      
      An operator CID of 0 is used to identify the Network Manager 
      (referred to as 'NetMan' in DPN). This CID matches the CID of 
      any component. Values 1 to 8191 inclusive (equivalent to 'basic 
      CIDs' in DPN) may be assigned to specific customers."
   DEFVAL     { 0 }
::= { mscLpSonetPathCidDataEntry 1 }

mscLpSonetPathStateTable OBJECT-TYPE
   SYNTAX     SEQUENCE OF MscLpSonetPathStateEntry
   ACCESS     not-accessible
   STATUS     mandatory
   DESCRIPTION
     "This group contains the three OSI State attributes and the six OSI 
      Status attributes. The descriptions generically indicate what each 
      attribute implies about the component. Note that not all the values 
      and state combinations described here are supported by every 
      component which uses this group. For component-specific 
      information and the valid state combinations, refer to NTP 241-
      7001-150, Passport Operations and Maintenance Guide."
::= { mscLpSonetPath 12 }

mscLpSonetPathStateEntry OBJECT-TYPE
   SYNTAX     MscLpSonetPathStateEntry
   ACCESS     not-accessible
   STATUS     mandatory
   DESCRIPTION
     "An entry in the mscLpSonetPathStateTable."
   INDEX {
      mscLpIndex,
      mscLpSonetIndex,
      mscLpSonetPathIndex }
::= { mscLpSonetPathStateTable 1 }

MscLpSonetPathStateEntry ::= SEQUENCE {
   mscLpSonetPathAdminState
      INTEGER,
   mscLpSonetPathOperationalState
      INTEGER,
   mscLpSonetPathUsageState
      INTEGER,
   mscLpSonetPathAvailabilityStatus
      OCTET STRING,
   mscLpSonetPathProceduralStatus
      OCTET STRING,
   mscLpSonetPathControlStatus
      OCTET STRING,
   mscLpSonetPathAlarmStatus
      OCTET STRING,
   mscLpSonetPathStandbyStatus
      INTEGER,
   mscLpSonetPathUnknownStatus
      INTEGER }

mscLpSonetPathAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component.
      
      The OSI Status attributes, if supported by the component, may 
      provide more details, qualifying the state of the component."
   DEFVAL     { unlocked }
::= { mscLpSonetPathStateEntry 1 }

mscLpSonetPathOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle.
      
      The OSI Status attributes, if supported by the component, may 
      provide more details, qualifying the state of the component."
   DEFVAL     { disabled }
::= { mscLpSonetPathStateEntry 2 }

mscLpSonetPathUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time.
      
      The OSI Status attributes, if supported by the component, may 
      provide more details, qualifying the state of the component."
   DEFVAL     { idle }
::= { mscLpSonetPathStateEntry 3 }

mscLpSonetPathAvailabilityStatus OBJECT-TYPE
   SYNTAX     OCTET STRING (SIZE (2))
   ACCESS     read-only
   STATUS     mandatory
   DESCRIPTION
     "If supported by the component, this attribute indicates the OSI 
      Availability status of the component. Note that, even though it is 
      defined as a multi-valued set, at most one value is shown to the user.
      
      When no values are in the set, this indicates that either the attribute 
      is not supported or that none of the status conditions described 
      below are present.
      
      The value inTest indicates that the resource is undergoing a test 
      procedure. If adminState is locked or shuttingDown, the normal 
      users are precluded from using the resource and controlStatus is 
      reservedForTest. Tests that do not exclude additional users can be 
      present in any operational or administrative state but the 
      reservedForTest condition should not be present.
      
      The value failed indicates that the component has an internal fault 
      that prevents it from operating. The operationalState is disabled.
      
      The value dependency indicates that the component cannot operate 
      because some other resource on which it depends is unavailable. 
      The operationalState is disabled.
      
      The value powerOff indicates the resource requires power to be 
      applied and it is not powered on. The operationalState is disabled.
      
      The value offLine indicates the resource requires a routine 
      operation (either manual, automatic, or both) to be performed to 
      place it on-line and make it available for use. The operationalState 
      is disabled.
      
      The value offDuty indicates the resource is inactive in accordance 
      with a predetermined time schedule. In the absence of other 
      disabling conditions, the operationalState is enabled or disabled.
      
      The value degraded indicates the service provided by the 
      component is degraded in some way, such as in speed or operating 
      capacity. However, the resource remains available for service. The 
      operationalState is enabled.
      
      The value notInstalled indicates the resource is not present. The 
      operationalState is disabled.
      
      The value logFull is not used.

      Description of bits:
      inTest(0)
      failed(1)
      powerOff(2)
      offLine(3)
      offDuty(4)
      dependency(5)
      degraded(6)
      notInstalled(7)
      logFull(8)"
::= { mscLpSonetPathStateEntry 4 }

mscLpSonetPathProceduralStatus OBJECT-TYPE
   SYNTAX     OCTET STRING (SIZE (1))
   ACCESS     read-only
   STATUS     mandatory
   DESCRIPTION
     "If supported by the component, this attribute indicates the OSI 
      Procedural status of the component. Note that, even though it is 
      defined as a multi-valued set, at most one value is shown to the user.
      
      When no values are in the set, this indicates that either the attribute 
      is not supported or that none of the status conditions described 
      below are present.
      
      The value initializationRequired indicates (for a resource which 
      doesn't initialize autonomously) that initialization is required before 
      it can perform its normal functions, and this procedure has not been 
      initiated. The operationalState is disabled.
      
      The value notInitialized indicates (for a resource which does 
      initialize autonomously) that initialization is required before it can 
      perform its normal functions, and this procedure has not been 
      initiated. The operationalState may be enabled or disabled.
      
      The value initializing indicates that initialization has been initiated 
      but is not yet complete. The operationalState may be enabled or 
      disabled.
      
      The value reporting indicates the resource has completed some 
      processing operation and is notifying the results. The 
      operationalState is enabled.
      
      The value terminating indicates the component is in a termination 
      phase. If the resource doesn't reinitialize autonomously, 
      operationalState is disabled; otherwise it is enabled or disabled.

      Description of bits:
      initializationRequired(0)
      notInitialized(1)
      initializing(2)
      reporting(3)
      terminating(4)"
::= { mscLpSonetPathStateEntry 5 }

mscLpSonetPathControlStatus OBJECT-TYPE
   SYNTAX     OCTET STRING (SIZE (1))
   ACCESS     read-only
   STATUS     mandatory
   DESCRIPTION
     "If supported by the component, this attribute indicates the OSI 
      Control status of the component. Note that, even though it is defined 
      as a multi-valued set, at most one value is shown to the user.
      
      When no values are in the set, this indicates that either the attribute 
      is not supported or that none of the status conditions described 
      below are present.
      
      The value subjectToTest indicates the resource is available but tests 
      may be conducted simultaneously at unpredictable times, which 
      may cause it to exhibit unusual characteristics.
      
      The value partOfServicesLocked indicates that part of the service is 
      restricted from users of a resource. The adminState is unlocked.
      
      The value reservedForTest indicates that the component is 
      administratively unavailable because it is undergoing a test 
      procedure. The adminState is locked.
      
      The value suspended indicates that the service has been 
      administratively suspended.

      Description of bits:
      subjectToTest(0)
      partOfServicesLocked(1)
      reservedForTest(2)
      suspended(3)"
::= { mscLpSonetPathStateEntry 6 }

mscLpSonetPathAlarmStatus OBJECT-TYPE
   SYNTAX     OCTET STRING (SIZE (1))
   ACCESS     read-only
   STATUS     mandatory
   DESCRIPTION
     "If supported by the component, this attribute indicates the OSI 
      Alarm status of the component. Note that, even though it is defined 
      as a multi-valued set, at most one value is shown to the user.
      
      When no values are in the set, this indicates that either the attribute 
      is not supported or that none of the status conditions described 
      below are present.
      
      The value underRepair indicates the component is currently being 
      repaired. The operationalState is enabled or disabled.
      
      The value critical indicates one or more critical alarms are 
      outstanding against the component. Other, less severe, alarms may 
      also be outstanding. The operationalState is enabled or disabled.
      
      The value major indicates one or more major alarms are 
      outstanding against the component. Other, less severe, alarms may 
      also be outstanding. The operationalState is enabled or disabled.
      
      The value minor indicates one or more minor alarms are 
      outstanding against the component. Other, less severe, alarms may 
      also be outstanding. The operationalState is enabled or disabled.
      
      The value alarmOutstanding generically indicates that an alarm of 
      some severity is outstanding against the component.

      Description of bits:
      underRepair(0)
      critical(1)
      major(2)
      minor(3)
      alarmOutstanding(4)"
::= { mscLpSonetPathStateEntry 7 }

mscLpSonetPathStandbyStatus OBJECT-TYPE
   SYNTAX     INTEGER  {
                 hotStandby(0),
                 coldStandby(1),
                 providingService(2),
                 notSet(15) }
   ACCESS     read-only
   STATUS     mandatory
   DESCRIPTION
     "If supported by the component, this attribute indicates the OSI 
      Standby status of the component.
      
      The value notSet indicates that either the attribute is not supported 
      or that none of the status conditions described below are present. 
      Note that this is a non-standard value, used because the original 
      specification indicated this attribute was set-valued and thus, did not 
      provide a value to indicate that none of the other three are 
      applicable.
      
      The value hotStandby indicates that the resource is not providing 
      service but will be immediately able to take over the role of the 
      resource to be backed up, without initialization activity, and 
      containing the same information as the resource to be backed up.
      
      The value coldStandby indicates the resource is a backup for 
      another resource but will not be immediately able to take over the 
      role of the backed up resource and will require some initialization 
      activity.
      
      The value providingService indicates that this component, as a 
      backup resource, is currently backing up another resource."
   DEFVAL     { notSet }
::= { mscLpSonetPathStateEntry 8 }

mscLpSonetPathUnknownStatus OBJECT-TYPE
   SYNTAX     INTEGER  {
                 false(0),
                 true(1) }
   ACCESS     read-only
   STATUS     mandatory
   DESCRIPTION
     "This attribute indicates the OSI Unknown status of the component.
      
      The value false indicates that all of the other OSI State and Status 
      attribute values can be considered accurate.
      
      The value true indicates that the actual state of the component is not 
      known for sure."
   DEFVAL     { false }
::= { mscLpSonetPathStateEntry 9 }

mscLpSonetPathIfEntryTable OBJECT-TYPE
   SYNTAX     SEQUENCE OF MscLpSonetPathIfEntryEntry
   ACCESS     not-accessible
   STATUS     mandatory
   DESCRIPTION
     "This group contains the provisionable attributes for the ifEntry."
::= { mscLpSonetPath 13 }

mscLpSonetPathIfEntryEntry OBJECT-TYPE
   SYNTAX     MscLpSonetPathIfEntryEntry
   ACCESS     not-accessible
   STATUS     mandatory
   DESCRIPTION
     "An entry in the mscLpSonetPathIfEntryTable."
   INDEX {
      mscLpIndex,
      mscLpSonetIndex,
      mscLpSonetPathIndex }
::= { mscLpSonetPathIfEntryTable 1 }

MscLpSonetPathIfEntryEntry ::= SEQUENCE {
   mscLpSonetPathIfAdminStatus
      INTEGER,
   mscLpSonetPathIfIndex
      InterfaceIndex }

mscLpSonetPathIfAdminStatus OBJECT-TYPE
   SYNTAX     INTEGER  {
                 up(1),
                 down(2),
                 testing(3) }
   ACCESS     read-write
   STATUS     mandatory
   DESCRIPTION
     "The desired state of the interface. The up state indicates the 
      interface is operational. The down state indicates the interface is not 
      operational. The testing state indicates that no operational packets 
      can be passed."
   DEFVAL     { up }
::= { mscLpSonetPathIfEntryEntry 1 }

mscLpSonetPathIfIndex OBJECT-TYPE
   SYNTAX     InterfaceIndex (1..65535)
   ACCESS     read-only
   STATUS     mandatory
   DESCRIPTION
     "This is the index for the IfEntry. Its value is automatically initialized 
      during the provisioning process."
::= { mscLpSonetPathIfEntryEntry 2 }

mscLpSonetPathOperStatusTable OBJECT-TYPE
   SYNTAX     SEQUENCE OF MscLpSonetPathOperStatusEntry
   ACCESS     not-accessible
   STATUS     mandatory
   DESCRIPTION
     "This group includes the Operational Status attribute. This attribute 
      defines the current operational state of this component."
::= { mscLpSonetPath 14 }

mscLpSonetPathOperStatusEntry OBJECT-TYPE
   SYNTAX     MscLpSonetPathOperStatusEntry
   ACCESS     not-accessible
   STATUS     mandatory
   DESCRIPTION
     "An entry in the mscLpSonetPathOperStatusTable."
   INDEX {
      mscLpIndex,
      mscLpSonetIndex,
      mscLpSonetPathIndex }
::= { mscLpSonetPathOperStatusTable 1 }

MscLpSonetPathOperStatusEntry ::= SEQUENCE {
   mscLpSonetPathSnmpOperStatus
      INTEGER }

mscLpSonetPathSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { mscLpSonetPathOperStatusEntry 1 }

mscLpSonetPathOperTable OBJECT-TYPE
   SYNTAX     SEQUENCE OF MscLpSonetPathOperEntry
   ACCESS     not-accessible
   STATUS     mandatory
   DESCRIPTION
     "This group contains the common operational data for Path 
      component."
::= { mscLpSonetPath 15 }

mscLpSonetPathOperEntry OBJECT-TYPE
   SYNTAX     MscLpSonetPathOperEntry
   ACCESS     not-accessible
   STATUS     mandatory
   DESCRIPTION
     "An entry in the mscLpSonetPathOperTable."
   INDEX {
      mscLpIndex,
      mscLpSonetIndex,
      mscLpSonetPathIndex }
::= { mscLpSonetPathOperTable 1 }

MscLpSonetPathOperEntry ::= SEQUENCE {
   mscLpSonetPathLopAlarm
      INTEGER,
   mscLpSonetPathRxAisAlarm
      INTEGER,
   mscLpSonetPathRxRfiAlarm
      INTEGER,
   mscLpSonetPathSignalLabelMismatch
      INTEGER,
   mscLpSonetPathTxAis
      INTEGER,
   mscLpSonetPathTxRdi
      INTEGER }

mscLpSonetPathLopAlarm OBJECT-TYPE
   SYNTAX     INTEGER  {
                 on(0),
                 off(1) }
   ACCESS     read-only
   STATUS     mandatory
   DESCRIPTION
     "This attribute displays whether a Loss Of Pointer (LOP) alarm state 
      has been entered. An LOP alarm state is entered when LOP defects 
      have been observed and accumulated for a period of 2.5 seconds +/- 
      0.5 seconds. An LOP defect occurs when no valid SPE or VC 
      pointer was received in 8 contiguous frames. If the LOP defects are 
      intermittently occurring, the LOP defect accumulator is 
      decremented at a rate of 1/10 of the incrementing rate (alarm 
      integration ratio of 1/10), with all measurements based on a 200 ms 
      polling cycle.
      The Path component goes into an operational state of disabled until 
      the LOP alarm condition is cleared. The condition is cleared when 
      no more invalid pointer has been reported for 10 seconds +/- 0.5 
      seconds.
      The lopAlarm attribute is always set to off when the Path 
      component has been locked and left offline by the operator or when 
      the Path component has been suspended since the parent component 
      has been locked."
::= { mscLpSonetPathOperEntry 1 }

mscLpSonetPathRxAisAlarm OBJECT-TYPE
   SYNTAX     INTEGER  {
                 on(0),
                 off(1) }
   ACCESS     read-only
   STATUS     mandatory
   DESCRIPTION
     "This attribute displays whether an Path Alarm Indication Signal (P-
      AIS) alarm state has been entered. An P-AIS alarm state is entered 
      when P-AIS defects have been observed and accumulated for a 
      period of 2.5 seconds +/- 0.5 seconds. The P-AIS defect is the 
      occurrence of the P-AIS signal in three contiguous valid STS or 
      STM frames (all one's in bytes H1 and H2). If the P-AIS defects are 
      intermittently occurring, the P-AIS defect accumulator is 
      decremented at a rate of 1/10 of the incrementing rate (alarm 
      integration ratio of 1/10), with all measurements based on a 200 ms 
      polling cycle.
      The Path component goes into an operational state of disabled until 
      the P-AIS alarm condition is cleared. The condition is cleared after 
      no P-AIS defect has been detected for 10 seconds +/- 0.5 seconds.
      The rxAisAlarm attribute is always set to off when the Path 
      component has been locked and left offline by the operator or when 
      the Path component has been suspended since the parent component 
      has been locked."
::= { mscLpSonetPathOperEntry 2 }

mscLpSonetPathRxRfiAlarm OBJECT-TYPE
   SYNTAX     INTEGER  {
                 on(0),
                 off(1) }
   ACCESS     read-only
   STATUS     mandatory
   DESCRIPTION
     "This attribute displays whether the Path Remote Failure Indication 
      (P-RFI) alarm state has been entered. An P-RFI alarm state is 
      entered when Path Remote Defect Indicator (P-RDI) defects have 
      been observed and accumulated for a period of 2.5 seconds +/- 0.5 
      seconds. The P-RDI defect is the occurrence of the P-RDI signal in 
      five contiguous valid STS or STM frames (bit 5 of the G1 byte set 
      to 1). If the P-RDI defects are intermittently occurring, the P-RDI 
      defect accumulator is decremented at a rate of 1/10 of the 
      incrementing rate (alarm integration ratio of 1/10)with all 
      measurements based on a 200 ms polling cycle.
      The Path component goes into an operational state of disabled until 
      the P-RFI alarm condition is cleared. The condition is cleared after 
      no P-RDI defect has been detected for 10 seconds +/- 0.5 seconds.
      The rxRfiAlarm attribute is always set to off when the Path 
      component has been locked and left offline by the operator or when 
      the Path component has been suspended since the parent component 
      has been locked."
::= { mscLpSonetPathOperEntry 3 }

mscLpSonetPathSignalLabelMismatch OBJECT-TYPE
   SYNTAX     INTEGER  {
                 on(0),
                 off(1) }
   ACCESS     read-only
   STATUS     mandatory
   DESCRIPTION
     "This attribute displays whether the Path Signal Label Mismatch (P-
      SLM) failure condition has been entered. An P-SLM failure 
      condition is entered when P-SLM defects have been observed and 
      accumulated for period of 2.5 seconds +/- 0.5 seconds. An P-SLM 
      defect occurs when detecting an unexpected path signal label. The 
      expected Path signal labels are 'Mapping for ATM' or 'Equipped - 
      Non Specific Payload'. If the P-SLM defects are intermittently 
      occurring, the P-SLM defect accumulator is decremented at a rate 
      of 1/10 of the incrementing rate (alarm integration ratio of 1/10), 
      with all measurements based on a 200 ms polling cycle.
      The Path component goes into an operational state of disabled until 
      the Path Signal Label Mismatch failure condition is cleared. The 
      condition is cleared when an expected path signal label is received 
      for 10 seconds +/- 0.5 seconds.
      The signalLabelMismatch attribute is always set to off when the 
      Path component has been locked and left offline by the operator or 
      when the Path component has been suspended since the parent 
      component has been locked."
::= { mscLpSonetPathOperEntry 4 }

mscLpSonetPathTxAis OBJECT-TYPE
   SYNTAX     INTEGER  {
                 on(0),
                 off(1) }
   ACCESS     read-only
   STATUS     mandatory
   DESCRIPTION
     "This attribute displays whether the Path Alarm Indication Signal (P-
      AIS) signal is being transmitted on the path. The P-AIS signal is 
      transmitted when the Path component has been locked and left 
      offline by the operator or when the Path component has been 
      suspended since the parent component has been locked."
::= { mscLpSonetPathOperEntry 5 }

mscLpSonetPathTxRdi OBJECT-TYPE
   SYNTAX     INTEGER  {
                 on(0),
                 off(1) }
   ACCESS     read-only
   STATUS     mandatory
   DESCRIPTION
     "This attribute displays whether the Path Remote Defect Indicator 
      (P-RDI) signal is being transmitted over the path signal. The P-RDI 
      signal is transmitted over the outgoing line upon detection of LOP, 
      P-AIS or the occurrence of the LCD state. This attribute is always 
      set to off when the Path component has been locked and left offline 
      by the operator or when the Path component has been suspended 
      since the parent component has been locked."
::= { mscLpSonetPathOperEntry 6 }

mscLpSonetPathStatsTable OBJECT-TYPE
   SYNTAX     SEQUENCE OF MscLpSonetPathStatsEntry
   ACCESS     not-accessible
   STATUS     mandatory
   DESCRIPTION
     "This group contains the statistics data for a Sonet/Sdh Path 
      component. Each attribute type is a non-negative integer which 
      monotonically increases until it reaches a maximum value, at which 
      point it wraps around and starts increasing again from zero."
::= { mscLpSonetPath 16 }

mscLpSonetPathStatsEntry OBJECT-TYPE
   SYNTAX     MscLpSonetPathStatsEntry
   ACCESS     not-accessible
   STATUS     mandatory
   DESCRIPTION
     "An entry in the mscLpSonetPathStatsTable."
   INDEX {
      mscLpIndex,
      mscLpSonetIndex,
      mscLpSonetPathIndex }
::= { mscLpSonetPathStatsTable 1 }

MscLpSonetPathStatsEntry ::= SEQUENCE {
   mscLpSonetPathPathErrorFreeSec
      Counter32,
   mscLpSonetPathPathCodeViolations
      Counter32,
   mscLpSonetPathPathErroredSec
      Counter32,
   mscLpSonetPathPathSevErroredSec
      Counter32,
   mscLpSonetPathPathAisLopSec
      Counter32,
   mscLpSonetPathPathUnavailSec
      Counter32,
   mscLpSonetPathPathFailures
      Counter32,
   mscLpSonetPathFarEndPathErrorFreeSec
      Counter32,
   mscLpSonetPathFarEndPathCodeViolations
      Counter32,
   mscLpSonetPathFarEndPathErroredSec
      Counter32,
   mscLpSonetPathFarEndPathSevErroredSec
      Counter32,
   mscLpSonetPathFarEndPathAisLopSec
      Counter32,
   mscLpSonetPathFarEndPathUnavailSec
      Counter32,
   mscLpSonetPathFarEndPathFailures
      Counter32 }

mscLpSonetPathPathErrorFreeSec OBJECT-TYPE
   SYNTAX     Counter32 
   ACCESS     read-only
   STATUS     mandatory
   DESCRIPTION
     "This attribute indicates the number of seconds that the Sonet/Sdh 
      Path component has been in an near-end error free state."
::= { mscLpSonetPathStatsEntry 1 }

mscLpSonetPathPathCodeViolations OBJECT-TYPE
   SYNTAX     Counter32 
   ACCESS     read-only
   STATUS     mandatory
   DESCRIPTION
     "This attribute indicates the total number of Path Code Violations 
      (PCVs) detected. Each PCV corresponds to a path BIP-8 error. PCV 
      counting is inhibited over second intervals where a Path Severely 
      Errored Second (PSES) is counted. Counting of PCVs is also 
      inhibited over second intervals where a Path Unavailable Second 
      (PUAS) is counted. The count wraps at its maximum value."
::= { mscLpSonetPathStatsEntry 2 }

mscLpSonetPathPathErroredSec OBJECT-TYPE
   SYNTAX     Counter32 
   ACCESS     read-only
   STATUS     mandatory
   DESCRIPTION
     "This attribute indicates the total number of Path Errored Seconds 
      (PESs) that have been counted. A PES is declared for second 
      intervals containing one or more PCVs or one or more LOP or path 
      AIS defects. Counting of PES is inhibited when PUAS is counted 
      over the monitored second."
::= { mscLpSonetPathStatsEntry 3 }

mscLpSonetPathPathSevErroredSec OBJECT-TYPE
   SYNTAX     Counter32 
   ACCESS     read-only
   STATUS     mandatory
   DESCRIPTION
     "This attribute indicates the total number of Path Severely Errored 
      Seconds (PSESs) that have been counted. A PSES is declared for 
      second intervals containing more than x PCVs or one or more LOP 
      or path AIS defects. The value of x is 2400 for a 155 Mbits/sec 
      interface. Counting of PSES is inhibited when PUAS is counted 
      over the monitored second."
::= { mscLpSonetPathStatsEntry 4 }

mscLpSonetPathPathAisLopSec OBJECT-TYPE
   SYNTAX     Counter32 
   ACCESS     read-only
   STATUS     mandatory
   DESCRIPTION
     "This attribute indicates the total number of path AIS and LOP 
      Seconds (PALSs). A PALS is declared for second intervals 
      containing one or more path AIS or LOP defects. Counting of PALS 
      is inhibited when PUAS is counted over the monitored second."
::= { mscLpSonetPathStatsEntry 5 }

mscLpSonetPathPathUnavailSec OBJECT-TYPE
   SYNTAX     Counter32 
   ACCESS     read-only
   STATUS     mandatory
   DESCRIPTION
     "This attribute indicates the total number of one second intervals for 
      which the STS/STM path is unavailable. The path becomes 
      unavailable at the onset of 10 consecutive PSESs. The 10 PSESs are 
      included in the unavailable time. Once unavailable, the path 
      becomes available at the onset of 10 contiguous seconds with no 
      PSES. The 10 seconds with no PSES are excluded from the 
      unavailable time. For second intervals where a Path Unavailable 
      Second (PUAS) is counted, counting of PCV, PES, PSES and PALS 
      is inhibited."
::= { mscLpSonetPathStatsEntry 6 }

mscLpSonetPathPathFailures OBJECT-TYPE
   SYNTAX     Counter32 
   ACCESS     read-only
   STATUS     mandatory
   DESCRIPTION
     "This attribute indicates the total number of times that a path failure 
      (LOP, P-AIS or Path Signal Label Mismatch failure) has been 
      declared."
::= { mscLpSonetPathStatsEntry 7 }

mscLpSonetPathFarEndPathErrorFreeSec OBJECT-TYPE
   SYNTAX     Counter32 
   ACCESS     read-only
   STATUS     mandatory
   DESCRIPTION
     "This attribute indicates the number of seconds that the Sonet/Sdh 
      Path component has been in an far-end error free state."
::= { mscLpSonetPathStatsEntry 8 }

mscLpSonetPathFarEndPathCodeViolations OBJECT-TYPE
   SYNTAX     Counter32 
   ACCESS     read-only
   STATUS     mandatory
   DESCRIPTION
     "This attribute indicates the total number of Far-End Path Code 
      Violations (FEPCVs) detected. Each FEPCV corresponds to a path 
      FEBE. FEPCV counting is inhibited over second intervals where a 
      Far-End Path Severely Errored Second (FEPSES) is counted. 
      Counting of PCVs is also inhibited over second intervals where a 
      Far-End Path Unavailable Second (FEPUAS) is counted. The count 
      wraps at its maximum value."
::= { mscLpSonetPathStatsEntry 9 }

mscLpSonetPathFarEndPathErroredSec OBJECT-TYPE
   SYNTAX     Counter32 
   ACCESS     read-only
   STATUS     mandatory
   DESCRIPTION
     "This attribute indicates the total number of Far-End Path Errored 
      Seconds (FEPESs) that have been counted. A FEPES is declared for 
      second intervals containing one or more FEPCVs or one or more 
      path RDI (P-RDI) defects. Counting of FEPES is inhibited when 
      FEPUAS is counted over the monitored second."
::= { mscLpSonetPathStatsEntry 10 }

mscLpSonetPathFarEndPathSevErroredSec OBJECT-TYPE
   SYNTAX     Counter32 
   ACCESS     read-only
   STATUS     mandatory
   DESCRIPTION
     "This attribute indicates the total number of Far-End Path Severely 
      Errored Seconds (FEPSESs) that have been counted. A FEPSES is 
      declared for second intervals containing more than x FEPCVs or 
      one or more P-RDI defects. The value of x is 2400 for a 155 Mbits/
      sec interface. Counting of FEPSESs is inhibited when FEPUAS is 
      counted over the monitored second."
::= { mscLpSonetPathStatsEntry 11 }

mscLpSonetPathFarEndPathAisLopSec OBJECT-TYPE
   SYNTAX     Counter32 
   ACCESS     read-only
   STATUS     mandatory
   DESCRIPTION
     "This attribute indicates the total number of Far-End Path AIS and 
      LOP Seconds (FEPALSs). A FEPALS is declared for second 
      intervals containing one or more P-RDI defects. Counting of 
      FEPALS is inhibited when FEPUAS is counted over the monitored 
      second."
::= { mscLpSonetPathStatsEntry 12 }

mscLpSonetPathFarEndPathUnavailSec OBJECT-TYPE
   SYNTAX     Counter32 
   ACCESS     read-only
   STATUS     mandatory
   DESCRIPTION
     "This attribute indicates the total number of one second intervals for 
      which the STS/STM far-end path is unavailable. The far-end path 
      becomes unavailable at the onset of 10 consecutive FEPSESs. The 
      10 FEPSESs are included in the unavailable time. Once unavailable, 
      the far-end path becomes available at the onset of 10 contiguous 
      seconds with no FEPSES. The 10 seconds with no FEPSES are 
      excluded from the unavailable time. For second intervals where a 
      Far-End Path Unavailable Second (FEPUAS) is counted, counting 
      of FEPCV, FEPES, FEPSES and FEPALS is inhibited."
::= { mscLpSonetPathStatsEntry 13 }

mscLpSonetPathFarEndPathFailures OBJECT-TYPE
   SYNTAX     Counter32 
   ACCESS     read-only
   STATUS     mandatory
   DESCRIPTION
     "This attribute indicates the total number of times that a STS/STM 
      far-end path failure (P-RFI failure) has been declared."
::= { mscLpSonetPathStatsEntry 14 }


-- 
-- The AtmCell is a component that contains provisioning and 
-- operational attributes. The provisioning attributes are used to set the 
-- Loss of Cell Deliniation (LCD) alarm activation delay and to turn 
-- cell payload scrambling on or off. The operational attributes are 
-- used to report about the quality of the ATM cells received by the 
-- interface and the cell capacity utilization. The AtmCell component 
-- appears under all port components running on ATM cards.

mscLpSonetPathCell OBJECT IDENTIFIER ::= { mscLpSonetPath 2 }



mscLpSonetPathCellRowStatusTable OBJECT-TYPE
   SYNTAX     SEQUENCE OF MscLpSonetPathCellRowStatusEntry
   ACCESS     not-accessible
   STATUS     mandatory
   DESCRIPTION
     "This entry controls the addition and deletion of 
      mscLpSonetPathCell components."
::= { mscLpSonetPathCell 1 }

mscLpSonetPathCellRowStatusEntry OBJECT-TYPE
   SYNTAX     MscLpSonetPathCellRowStatusEntry
   ACCESS     not-accessible
   STATUS     mandatory
   DESCRIPTION
     "A single entry in the table represents a single 
      mscLpSonetPathCell component."
   INDEX {
      mscLpIndex,
      mscLpSonetIndex,
      mscLpSonetPathIndex,
      mscLpSonetPathCellIndex }
::= { mscLpSonetPathCellRowStatusTable 1 }

MscLpSonetPathCellRowStatusEntry ::= SEQUENCE {
   mscLpSonetPathCellRowStatus
      RowStatus,
   mscLpSonetPathCellComponentName
      DisplayString,
   mscLpSonetPathCellStorageType
      StorageType,
   mscLpSonetPathCellIndex
      NonReplicated }

mscLpSonetPathCellRowStatus OBJECT-TYPE
   SYNTAX     RowStatus 
   ACCESS     read-only
   STATUS     mandatory
   DESCRIPTION
     "This variable is used as the basis for SNMP naming of
      mscLpSonetPathCell components.
      These components cannot be added nor deleted."
::= { mscLpSonetPathCellRowStatusEntry 1 }

mscLpSonetPathCellComponentName OBJECT-TYPE
   SYNTAX     DisplayString 
   ACCESS     read-only
   STATUS     mandatory
   DESCRIPTION
     "This variable provides the component's string name for
      use with the ASCII Console Interface"
::= { mscLpSonetPathCellRowStatusEntry 2 }

mscLpSonetPathCellStorageType OBJECT-TYPE
   SYNTAX     StorageType 
   ACCESS     read-only
   STATUS     mandatory
   DESCRIPTION
     "This variable represents the storage type value for the
      mscLpSonetPathCell tables."
::= { mscLpSonetPathCellRowStatusEntry 4 }

mscLpSonetPathCellIndex OBJECT-TYPE
   SYNTAX     NonReplicated 
   ACCESS     not-accessible
   STATUS     mandatory
   DESCRIPTION
     "This variable represents the index for the mscLpSonetPathCell tables."
::= { mscLpSonetPathCellRowStatusEntry 10 }

mscLpSonetPathCellProvTable OBJECT-TYPE
   SYNTAX     SEQUENCE OF MscLpSonetPathCellProvEntry
   ACCESS     not-accessible
   STATUS     mandatory
   DESCRIPTION
     "This group contains the provisioning attributes for the AtmCell 
      component."
::= { mscLpSonetPathCell 10 }

mscLpSonetPathCellProvEntry OBJECT-TYPE
   SYNTAX     MscLpSonetPathCellProvEntry
   ACCESS     not-accessible
   STATUS     mandatory
   DESCRIPTION
     "An entry in the mscLpSonetPathCellProvTable."
   INDEX {
      mscLpIndex,
      mscLpSonetIndex,
      mscLpSonetPathIndex,
      mscLpSonetPathCellIndex }
::= { mscLpSonetPathCellProvTable 1 }

MscLpSonetPathCellProvEntry ::= SEQUENCE {
   mscLpSonetPathCellAlarmActDelay
      Unsigned32,
   mscLpSonetPathCellScrambleCellPayload
      INTEGER,
   mscLpSonetPathCellCorrectSingleBitHeaderErrors
      INTEGER }

mscLpSonetPathCellAlarmActDelay OBJECT-TYPE
   SYNTAX     Unsigned32 (0..2000)
   ACCESS     read-write
   STATUS     mandatory
   DESCRIPTION
     "This attribute defines the time during which a Loss of Cell 
      Delineation (LCD) defect should be observed before declaring an 
      LCD alarm (alarm 70115501). The time is specified in milliseconds."
   DEFVAL     { 500 }
::= { mscLpSonetPathCellProvEntry 1 }

mscLpSonetPathCellScrambleCellPayload OBJECT-TYPE
   SYNTAX     INTEGER  {
                 off(0),
                 on(1) }
   ACCESS     read-write
   STATUS     mandatory
   DESCRIPTION
     "Cell scrambling, as defined by  ITU-T Recommendation I.432., can 
      provide a solution to the problem of transmission equipment which 
      is sensitive to certain bit patterns in the ATM cell payload. This 
      attribute controls whether or not the cell payload is scrambled.
      It defaults to off for DS1 interfaces, and on for all other interfaces.
      Note that this setting must be the same at both ends of the link."
::= { mscLpSonetPathCellProvEntry 2 }

mscLpSonetPathCellCorrectSingleBitHeaderErrors OBJECT-TYPE
   SYNTAX     INTEGER  {
                 off(0),
                 on(1) }
   ACCESS     read-write
   STATUS     mandatory
   DESCRIPTION
     "This attribute specifies whether the port corrects single bit errors 
      detected in the headers of received cells. If single bit errors are 
      corrected, the affected cells are passed up to the ATM layer 
      according to normal operation. If single bit errors are not corrected, 
      these errored cells are discarded by the physical layer. Note that 
      cells containing multiple bit errors in their headers are always 
      discarded.
      
      Single bit HEC error correction must remain off for the following 
      card types: 3pDS1Atm, 8pDS1Atm, 3pE1Atm, 8pE1Atm, 
      2pJ6MAtm, 3pDS3Atm, and 3pE3Atm."
   DEFVAL     { off }
::= { mscLpSonetPathCellProvEntry 3 }

mscLpSonetPathCellOperTable OBJECT-TYPE
   SYNTAX     SEQUENCE OF MscLpSonetPathCellOperEntry
   ACCESS     not-accessible
   STATUS     mandatory
   DESCRIPTION
     "This group contains the common operational attributes for the 
      AtmCell component."
::= { mscLpSonetPathCell 11 }

mscLpSonetPathCellOperEntry OBJECT-TYPE
   SYNTAX     MscLpSonetPathCellOperEntry
   ACCESS     not-accessible
   STATUS     mandatory
   DESCRIPTION
     "An entry in the mscLpSonetPathCellOperTable."
   INDEX {
      mscLpIndex,
      mscLpSonetIndex,
      mscLpSonetPathIndex,
      mscLpSonetPathCellIndex }
::= { mscLpSonetPathCellOperTable 1 }

MscLpSonetPathCellOperEntry ::= SEQUENCE {
   mscLpSonetPathCellLcdAlarm
      INTEGER }

mscLpSonetPathCellLcdAlarm OBJECT-TYPE
   SYNTAX     INTEGER  {
                 on(0),
                 off(1) }
   ACCESS     read-only
   STATUS     mandatory
   DESCRIPTION
     "This attribute displays whether the Loss of Cell Delineation (LCD) 
      failure alarm state has been entered. This state is entered when LCD 
      defects have been observed and accumulated for a period of time 
      specified through the alarmActDelay attribute.
      In ATM cell direct mapping mode, an LCD defect occurs when Out 
      of Cell Delineation (OCD) anomaly persists for x milliseconds, and 
      disappears when the Out of Cell Delineation (OCD) is absent for x 
      msec. An OCD anomaly occurs when 7 consecutive incorrect HECs 
      have been detected. An OCD anomaly terminates when 6 
      consecutive correct HECs have been detected.
      For an AtmCell component located under a DS3 or E3 component 
      with mapping = PLCP, the LCD defect is directly derived from the 
      PLCP LOF defect.
      If LCD defects are intermittently occurring, the LCD defect 
      accumulator is decremented at a rate of 1/10 of the incrementing 
      rate (alarm integration ratio of 1/10), with all measurements based 
      on a 200 ms polling cycle
      The component under which is located the AtmCell component goes 
      into an operational state of disabled until the LCD alarm condition 
      is cleared. The condition is cleared after the LCD defect has not 
      been reported for a period of 10 seconds +/- 0.5 seconds.
      The lcdAlarm attribute is always set to off when the parent of the 
      AtmCell component has been locked and left offline. This can also 
      happen when the Path or Channel component has been suspended 
      since its parent has been locked."
   DEFVAL     { off }
::= { mscLpSonetPathCellOperEntry 1 }

mscLpSonetPathCellStatsTable OBJECT-TYPE
   SYNTAX     SEQUENCE OF MscLpSonetPathCellStatsEntry
   ACCESS     not-accessible
   STATUS     mandatory
   DESCRIPTION
     "This group contains the Statistics attribute for the AtmCell 
      component. Each attribute type is a non-negative integer which 
      monotonically increases until it reaches a maximum value, at which 
      point it wraps around and starts increasing again from zero."
::= { mscLpSonetPathCell 12 }

mscLpSonetPathCellStatsEntry OBJECT-TYPE
   SYNTAX     MscLpSonetPathCellStatsEntry
   ACCESS     not-accessible
   STATUS     mandatory
   DESCRIPTION
     "An entry in the mscLpSonetPathCellStatsTable."
   INDEX {
      mscLpIndex,
      mscLpSonetIndex,
      mscLpSonetPathIndex,
      mscLpSonetPathCellIndex }
::= { mscLpSonetPathCellStatsTable 1 }

MscLpSonetPathCellStatsEntry ::= SEQUENCE {
   mscLpSonetPathCellUncorrectableHecErrors
      Counter32,
   mscLpSonetPathCellSevErroredSec
      Counter32,
   mscLpSonetPathCellReceiveCellUtilization
      Gauge32,
   mscLpSonetPathCellTransmitCellUtilization
      Gauge32,
   mscLpSonetPathCellCorrectableHeaderErrors
      Counter32 }

mscLpSonetPathCellUncorrectableHecErrors OBJECT-TYPE
   SYNTAX     Counter32 
   ACCESS     read-only
   STATUS     mandatory
   DESCRIPTION
     "This attribute indicates the number of uncorrectable ATM cell 
      header errors that have been detected. Counting of 
      uncorrectableHeaderErrors is inhibited when an Out of Cell 
      Delineation (OCD) defect is present. An OCD defect occurs when 
      seven consecutive incorrect HECs have been detected. An OCD 
      defect terminates when six consecutive correct HECs have been 
      detected."
::= { mscLpSonetPathCellStatsEntry 1 }

mscLpSonetPathCellSevErroredSec OBJECT-TYPE
   SYNTAX     Counter32 
   ACCESS     read-only
   STATUS     mandatory
   DESCRIPTION
     "This attribute indicates the total number of ATM Cell Severely 
      Errored Seconds (SESs) that have been counted. 
      
      In direct mapping mode, an ATM Cell SES is declared for second 
      intervals containing one or more Out of Cell Delineation (OCD) 
      defects. An OCD defect occurs when seven consecutive incorrect 
      HECs have been detected. An OCD defect terminates when six 
      consecutive correct HECs have been detected.
      
      In PLCP mapping mode, an ATM Cell SES is declared for second 
      intervals containing one or more PLCP LOF defects.
      
      Counting of uncorrectableHeaderErrors (ucErr) and 
      correctableHeaderErrors (cErr) is inhibited when the OCD defect 
      is present."
::= { mscLpSonetPathCellStatsEntry 2 }

mscLpSonetPathCellReceiveCellUtilization OBJECT-TYPE
   SYNTAX     Gauge32 (0..100)
   ACCESS     read-only
   STATUS     mandatory
   DESCRIPTION
     "This attribute is the ratio of the number of valid, assigned cells 
      received on the link to the nominal link capacity. The utilization is 
      calculated over a period of one minute.
      This attribute is always set to 0 when the parent of the AtmCell 
      component has been locked and left offline. This can also happen 
      when the Path or Channel component has been suspended since its 
      parent has been locked."
   DEFVAL     { 0 }
::= { mscLpSonetPathCellStatsEntry 3 }

mscLpSonetPathCellTransmitCellUtilization OBJECT-TYPE
   SYNTAX     Gauge32 (0..100)
   ACCESS     read-only
   STATUS     mandatory
   DESCRIPTION
     "This attribute is the ratio of the number of valid, assigned cells 
      transmitted on the link to the nominal link capacity. The utilization 
      is calculated over a period of one minute.
      This attribute is always set to 0 when the parent of the AtmCell 
      component has been locked and left offline. This can also happen 
      when the Path or Channel component has been suspended since its 
      parent has been locked."
   DEFVAL     { 0 }
::= { mscLpSonetPathCellStatsEntry 4 }

mscLpSonetPathCellCorrectableHeaderErrors OBJECT-TYPE
   SYNTAX     Counter32 
   ACCESS     read-only
   STATUS     mandatory
   DESCRIPTION
     "This attribute indicates the number of correctable ATM cell header 
      errors that have been detected and corrected. Counting of 
      correctableHeaderErrors is inhibited when an Out of Cell 
      Delineation (OCD) defect is present. An OCD defect occurs when 
      seven consecutive incorrect HECs have been detected. An OCD 
      defect terminates when six consecutive correct HECs have been 
      detected"
::= { mscLpSonetPathCellStatsEntry 5 }


-- 
-- The Test component is configured to control a hardware facility test 
-- on a physical (V35, X21, DS1, E1, DS3, E3 etc.) or a logical port.

mscLpSonetTest OBJECT IDENTIFIER ::= { mscLpSonet 3 }



mscLpSonetTestRowStatusTable OBJECT-TYPE
   SYNTAX     SEQUENCE OF MscLpSonetTestRowStatusEntry
   ACCESS     not-accessible
   STATUS     mandatory
   DESCRIPTION
     "This entry controls the addition and deletion of 
      mscLpSonetTest components."
::= { mscLpSonetTest 1 }

mscLpSonetTestRowStatusEntry OBJECT-TYPE
   SYNTAX     MscLpSonetTestRowStatusEntry
   ACCESS     not-accessible
   STATUS     mandatory
   DESCRIPTION
     "A single entry in the table represents a single 
      mscLpSonetTest component."
   INDEX {
      mscLpIndex,
      mscLpSonetIndex,
      mscLpSonetTestIndex }
::= { mscLpSonetTestRowStatusTable 1 }

MscLpSonetTestRowStatusEntry ::= SEQUENCE {
   mscLpSonetTestRowStatus
      RowStatus,
   mscLpSonetTestComponentName
      DisplayString,
   mscLpSonetTestStorageType
      StorageType,
   mscLpSonetTestIndex
      NonReplicated }

mscLpSonetTestRowStatus OBJECT-TYPE
   SYNTAX     RowStatus 
   ACCESS     read-only
   STATUS     mandatory
   DESCRIPTION
     "This variable is used as the basis for SNMP naming of
      mscLpSonetTest components.
      These components cannot be added nor deleted."
::= { mscLpSonetTestRowStatusEntry 1 }

mscLpSonetTestComponentName OBJECT-TYPE
   SYNTAX     DisplayString 
   ACCESS     read-only
   STATUS     mandatory
   DESCRIPTION
     "This variable provides the component's string name for
      use with the ASCII Console Interface"
::= { mscLpSonetTestRowStatusEntry 2 }

mscLpSonetTestStorageType OBJECT-TYPE
   SYNTAX     StorageType 
   ACCESS     read-only
   STATUS     mandatory
   DESCRIPTION
     "This variable represents the storage type value for the
      mscLpSonetTest tables."
::= { mscLpSonetTestRowStatusEntry 4 }

mscLpSonetTestIndex OBJECT-TYPE
   SYNTAX     NonReplicated 
   ACCESS     not-accessible
   STATUS     mandatory
   DESCRIPTION
     "This variable represents the index for the mscLpSonetTest tables."
::= { mscLpSonetTestRowStatusEntry 10 }

mscLpSonetTestStateTable OBJECT-TYPE
   SYNTAX     SEQUENCE OF MscLpSonetTestStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscLpSonetTest 10 }

mscLpSonetTestStateEntry OBJECT-TYPE
   SYNTAX     MscLpSonetTestStateEntry
   ACCESS     not-accessible
   STATUS     mandatory
   DESCRIPTION
     "An entry in the mscLpSonetTestStateTable."
   INDEX {
      mscLpIndex,
      mscLpSonetIndex,
      mscLpSonetTestIndex }
::= { mscLpSonetTestStateTable 1 }

MscLpSonetTestStateEntry ::= SEQUENCE {
   mscLpSonetTestAdminState
      INTEGER,
   mscLpSonetTestOperationalState
      INTEGER,
   mscLpSonetTestUsageState
      INTEGER }

mscLpSonetTestAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscLpSonetTestStateEntry 1 }

mscLpSonetTestOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscLpSonetTestStateEntry 2 }

mscLpSonetTestUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscLpSonetTestStateEntry 3 }

mscLpSonetTestSetupTable OBJECT-TYPE
   SYNTAX     SEQUENCE OF MscLpSonetTestSetupEntry
   ACCESS     not-accessible
   STATUS     mandatory
   DESCRIPTION
     "This group contains all of the operational data for a Test 
      component."
::= { mscLpSonetTest 11 }

mscLpSonetTestSetupEntry OBJECT-TYPE
   SYNTAX     MscLpSonetTestSetupEntry
   ACCESS     not-accessible
   STATUS     mandatory
   DESCRIPTION
     "An entry in the mscLpSonetTestSetupTable."
   INDEX {
      mscLpIndex,
      mscLpSonetIndex,
      mscLpSonetTestIndex }
::= { mscLpSonetTestSetupTable 1 }

MscLpSonetTestSetupEntry ::= SEQUENCE {
   mscLpSonetTestPurpose
      AsciiString,
   mscLpSonetTestType
      INTEGER,
   mscLpSonetTestFrmSize
      Unsigned32,
   mscLpSonetTestFrmPatternType
      INTEGER,
   mscLpSonetTestCustomizedPattern
      Hex,
   mscLpSonetTestDataStartDelay
      Unsigned32,
   mscLpSonetTestDisplayInterval
      Unsigned32,
   mscLpSonetTestDuration
      Unsigned32 }

mscLpSonetTestPurpose OBJECT-TYPE
   SYNTAX     AsciiString (SIZE (0..40))
   ACCESS     read-write
   STATUS     mandatory
   DESCRIPTION
     "This attribute records the purpose of the test so that the test results 
      can be associated and properly analyzed."
::= { mscLpSonetTestSetupEntry 1 }

mscLpSonetTestType OBJECT-TYPE
   SYNTAX     INTEGER  {
                 card(0),
                 manual(1),
                 localLoop(2),
                 remoteLoop(3),
                 externalLoop(4),
                 payloadLoop(5),
                 remoteLoopThisTrib(6),
                 v54RemoteLoop(7),
                 pn127RemoteLoop(8) }
   ACCESS     read-write
   STATUS     mandatory
   DESCRIPTION
     "This attribute is the type of test to be run. The available test types 
      include the following:
      card test sets up an internal loop on the board and runs a bit error 
      rate test.
      manual test assumes the line is looped back externally and a bit 
      error rate test is performed.
      localLoop test loops back the local modem and performs a bit error 
      rate test.
      remoteLoop test loops back the remote modem (or CSU) and 
      performs a bit error rate test.
      externalLoop test loops back the line to the far end.
      payloadLoop test only loops back the payload data received from 
      the incoming line.
      remoteLoopThisTrib loops this particular tributary back at the far 
      end, using services provided by the parent.
      v54RemoteLoop initiates a V.54 Remote Loopback test.
      pn127RemoteLoop initiates a PN127 Remote Loopback test.
      Note that not all test types are not supported by all function 
      processors."
   DEFVAL     { card }
::= { mscLpSonetTestSetupEntry 2 }

mscLpSonetTestFrmSize OBJECT-TYPE
   SYNTAX     Unsigned32 (4..4096)
   ACCESS     read-write
   STATUS     mandatory
   DESCRIPTION
     "This attribute defines the size of the test data frames in number of 
      bytes."
   DEFVAL     { 1024 }
::= { mscLpSonetTestSetupEntry 3 }

mscLpSonetTestFrmPatternType OBJECT-TYPE
   SYNTAX     INTEGER  {
                 ccitt32kBitPattern(0),
                 ccitt8MBitPattern(1),
                 customizedPattern(2) }
   ACCESS     read-write
   STATUS     mandatory
   DESCRIPTION
     "This attribute defines the type of data pattern generation to use. The 
      following lists the available pattern types:
      ccitt32kBitPattern is a pseudo-random sequence of 32 kbit.
      ccitt8MBitPattern is a pseudo-random sequence of 8Mbit.
      customizedPattern is the pattern defined in the customizedPattern 
      attribute."
   DEFVAL     { ccitt32kBitPattern }
::= { mscLpSonetTestSetupEntry 4 }

mscLpSonetTestCustomizedPattern OBJECT-TYPE
   SYNTAX     Hex (0..4294967295)
   ACCESS     read-write
   STATUS     mandatory
   DESCRIPTION
     "This attribute allows a customized 32 bit pattern to be defined for 
      use in the test data frames. This attribute is used when the attribute 
      frmPatternType is set to CustomizedPattern. Note that a 55 hex 
      pattern is an alternating 1 and 0 pattern."
   DEFVAL     { 1431655765 }
::= { mscLpSonetTestSetupEntry 5 }

mscLpSonetTestDataStartDelay OBJECT-TYPE
   SYNTAX     Unsigned32 (0..1814400)
   ACCESS     read-write
   STATUS     mandatory
   DESCRIPTION
     "This attribute specifies the time delay (in seconds) between when 
      the test expects the loop to have been set up, to when the test data 
      actually starts to be transmitted. This attribute is to accommodate 
      some non-standard equipment that requires extra time for setting up 
      a requested loop.
      This attribute is ignored when the test type is set to externalLoop."
   DEFVAL     { 0 }
::= { mscLpSonetTestSetupEntry 6 }

mscLpSonetTestDisplayInterval OBJECT-TYPE
   SYNTAX     Unsigned32 (0..30240)
   ACCESS     read-write
   STATUS     mandatory
   DESCRIPTION
     "This attribute defines the interval (in minutes) between which 
      interim test results are to be displayed. Results are displayed at the 
      operator console at which the test was started. When the test type is 
      set to externalLoop, this attribute is ignored. There will be no 
      display of results if displayInterval is set to 0. This attribute can be 
      changed anytime."
   DEFVAL     { 5 }
::= { mscLpSonetTestSetupEntry 7 }

mscLpSonetTestDuration OBJECT-TYPE
   SYNTAX     Unsigned32 (1..30240)
   ACCESS     read-write
   STATUS     mandatory
   DESCRIPTION
     "This attribute is the duration (in minutes) that test data will be 
      transmitted. In the case of an externalLoop, this is the time that the 
      loop is in effect. Note that dataStartDelay does not apply to the 
      externalLoop."
   DEFVAL     { 1 }
::= { mscLpSonetTestSetupEntry 8 }

mscLpSonetTestResultsTable OBJECT-TYPE
   SYNTAX     SEQUENCE OF MscLpSonetTestResultsEntry
   ACCESS     not-accessible
   STATUS     mandatory
   DESCRIPTION
     "This group contains all the statistics related attributes of the Test 
      component."
::= { mscLpSonetTest 12 }

mscLpSonetTestResultsEntry OBJECT-TYPE
   SYNTAX     MscLpSonetTestResultsEntry
   ACCESS     not-accessible
   STATUS     mandatory
   DESCRIPTION
     "An entry in the mscLpSonetTestResultsTable."
   INDEX {
      mscLpIndex,
      mscLpSonetIndex,
      mscLpSonetTestIndex }
::= { mscLpSonetTestResultsTable 1 }

MscLpSonetTestResultsEntry ::= SEQUENCE {
   mscLpSonetTestElapsedTime
      Counter32,
   mscLpSonetTestTimeRemaining
      Unsigned32,
   mscLpSonetTestCauseOfTermination
      INTEGER,
   mscLpSonetTestBitsTx
      PassportCounter64,
   mscLpSonetTestBytesTx
      PassportCounter64,
   mscLpSonetTestFrmTx
      PassportCounter64,
   mscLpSonetTestBitsRx
      PassportCounter64,
   mscLpSonetTestBytesRx
      PassportCounter64,
   mscLpSonetTestFrmRx
      PassportCounter64,
   mscLpSonetTestErroredFrmRx
      PassportCounter64,
   mscLpSonetTestBitErrorRate
      AsciiString }

mscLpSonetTestElapsedTime OBJECT-TYPE
   SYNTAX     Counter32 
   ACCESS     read-only
   STATUS     mandatory
   DESCRIPTION
     "This attribute is the number of minutes elapsed since the test started 
      for an externalLoop test. For a data test, this is the time since test 
      data was first transmitted."
::= { mscLpSonetTestResultsEntry 1 }

mscLpSonetTestTimeRemaining OBJECT-TYPE
   SYNTAX     Unsigned32 (0..4294967295)
   ACCESS     read-only
   STATUS     mandatory
   DESCRIPTION
     "This attribute is the number of minutes remaining before the test is 
      to be stopped according to the duration attribute."
   DEFVAL     { 0 }
::= { mscLpSonetTestResultsEntry 2 }

mscLpSonetTestCauseOfTermination OBJECT-TYPE
   SYNTAX     INTEGER  {
                 testTimeExpired(0),
                 stoppedByOperator(1),
                 unknown(2),
                 neverStarted(3),
                 testRunning(4),
                 hardwareReconfigured(5),
                 loopCodeSyncFailed(6),
                 patternSyncFailed(7),
                 patternSyncLost(8) }
   ACCESS     read-only
   STATUS     mandatory
   DESCRIPTION
     "This attribute indicates either the status of the test or the cause of 
      the test's termination:
      
      neverStarted indicates that the test has not yet been started.
      
      testRunning indicates that the test has been started.
      
      stoppedByOperator indicates that the operator issued a stop 
      command on a test that was running.
      
      testTimeExpired indicates that the test ran for the time specified by 
      the test's duration.
      
      loopCodeSyncFailed indicates that the local end failed to 
      synchronize to the loopCode pattern. The local end transmits the 
      loopCode pattern to cause the remote end to apply a loopback, after 
      which the local end should receive the loopCode pattern. The exact 
      pattern used to request loopCode depends on the test type. This 
      failure indicates a high rate of transmission errors, or that the 
      remote end has failed to apply the loopback.
      
      patternSyncFailed indicates that the local end failed to synchronize 
      to the frmPatternType test pattern, that should have been looped 
      back at the remote end. This failure indicates a high rate of 
      transmission errors or the absence of a loopback.
      
      patternSyncLost indicates that the local end gained and then lost 
      synchronization to the returned frmPatternType test pattern. This 
      failure indicates a sudden increase in transmission errors, frame 
      slippage, or the removal of an existing loopback.
      
      unknown is set when a reason to terminate other than those listed 
      here is encountered.
      
      Note: Only MSA cards support recognition of the failures 
      loopCodeSyncFailed, patternSyncFailed and patternSyncLost. 
      Other cards will not terminate the test under the conditions 
      described by these values."
   DEFVAL     { neverStarted }
::= { mscLpSonetTestResultsEntry 3 }

mscLpSonetTestBitsTx OBJECT-TYPE
   SYNTAX     PassportCounter64 
   ACCESS     read-only
   STATUS     mandatory
   DESCRIPTION
     "This attribute is the total number of bits sent during the test period. 
      As long as the line speed of the hardware interface is less than 
      70 Mbit/s, this counter is not expected to reach the maximum value."
::= { mscLpSonetTestResultsEntry 4 }

mscLpSonetTestBytesTx OBJECT-TYPE
   SYNTAX     PassportCounter64 
   ACCESS     read-only
   STATUS     mandatory
   DESCRIPTION
     "This attribute is the total number of bytes sent during the test 
      period. This counter is not expected to reach its maximum value."
::= { mscLpSonetTestResultsEntry 5 }

mscLpSonetTestFrmTx OBJECT-TYPE
   SYNTAX     PassportCounter64 
   ACCESS     read-only
   STATUS     mandatory
   DESCRIPTION
     "This attribute is the total number of frames sent during the test 
      period. This counter is not expected to reach its maximum value."
::= { mscLpSonetTestResultsEntry 6 }

mscLpSonetTestBitsRx OBJECT-TYPE
   SYNTAX     PassportCounter64 
   ACCESS     read-only
   STATUS     mandatory
   DESCRIPTION
     "This attribute is the total number of bits received during the test 
      period. This counter is not expected to reach its maximum value. 
      The counter will wrap around to 0 if it does reach the maximum 
      value."
::= { mscLpSonetTestResultsEntry 7 }

mscLpSonetTestBytesRx OBJECT-TYPE
   SYNTAX     PassportCounter64 
   ACCESS     read-only
   STATUS     mandatory
   DESCRIPTION
     "This attribute is the total number of bytes received during the test 
      period. This counter is not expected to reach its maximum value. 
      The counter will wrap around to 0 if it does reach its maximum 
      value."
::= { mscLpSonetTestResultsEntry 8 }

mscLpSonetTestFrmRx OBJECT-TYPE
   SYNTAX     PassportCounter64 
   ACCESS     read-only
   STATUS     mandatory
   DESCRIPTION
     "This attribute is the total number of frames received during the test 
      period. This counter is not expected to reach its maximum value. 
      The counter will wrap around to 0 if it does reach its maximum 
      value."
::= { mscLpSonetTestResultsEntry 9 }

mscLpSonetTestErroredFrmRx OBJECT-TYPE
   SYNTAX     PassportCounter64 
   ACCESS     read-only
   STATUS     mandatory
   DESCRIPTION
     "This attribute is not displayed for ATM cards because the physical 
      layer drops all errored frames at the controller interface. 
      
      For all other card types, this attribute is the total number of errored 
      frames received during the test period. This counter is not expected 
      to reach its maximum value. The counter will wrap around to 0 if it 
      does reach its maximum value."
::= { mscLpSonetTestResultsEntry 10 }

mscLpSonetTestBitErrorRate OBJECT-TYPE
   SYNTAX     AsciiString (SIZE (5))
   ACCESS     read-only
   STATUS     mandatory
   DESCRIPTION
     "This attribute is not displayed for ATM cards because the physical 
      layer drops all errored frames at the controller interface. 
      
      For all other card types, this attribute is the calculated bit error rate 
      on the link. Test data are generated and sent in frames of a preset 
      size (frameSize). The Test component will try to estimate the 
      number of bit errors in any errored frame which is identifiable. The 
      statistics will be updated accordingly. A lost frame (may be due to 
      an error on the flag sequence) will be discarded for the bit error rate 
      calculation. The result is presented in the form of xEsyy, where x is 
      the mantissa, syy is the exponent, for example 0E+00, 2E-09.
      Note that the bitErrorRate is an estimate only. For more reliable test 
      results, the test should be done over a long period. Multiple tests 
      would also improve the confidence level of the test results."
::= { mscLpSonetTestResultsEntry 11 }


-- Sdh
-- The Lp/m Sdh/n component controls an OC-3 port on an OC-3 
-- Function Processor. In particular, it deals with SDH medium, 
-- section and line layers.
-- Note that there can be Sonet and Sdh components coexisting under 
-- the same LP. However they cannot use the same instance.

mscLpSdh OBJECT IDENTIFIER ::= { mscLp 15 }



mscLpSdhRowStatusTable OBJECT-TYPE
   SYNTAX     SEQUENCE OF MscLpSdhRowStatusEntry
   ACCESS     not-accessible
   STATUS     mandatory
   DESCRIPTION
     "This entry controls the addition and deletion of 
      mscLpSdh components."
::= { mscLpSdh 1 }

mscLpSdhRowStatusEntry OBJECT-TYPE
   SYNTAX     MscLpSdhRowStatusEntry
   ACCESS     not-accessible
   STATUS     mandatory
   DESCRIPTION
     "A single entry in the table represents a single 
      mscLpSdh component."
   INDEX {
      mscLpIndex,
      mscLpSdhIndex }
::= { mscLpSdhRowStatusTable 1 }

MscLpSdhRowStatusEntry ::= SEQUENCE {
   mscLpSdhRowStatus
      RowStatus,
   mscLpSdhComponentName
      DisplayString,
   mscLpSdhStorageType
      StorageType,
   mscLpSdhIndex
      Integer32 }

mscLpSdhRowStatus OBJECT-TYPE
   SYNTAX     RowStatus 
   ACCESS     read-write
   STATUS     mandatory
   DESCRIPTION
     "This variable is used as the basis for SNMP naming of
      mscLpSdh components.
      These components can be added and deleted."
::= { mscLpSdhRowStatusEntry 1 }

mscLpSdhComponentName OBJECT-TYPE
   SYNTAX     DisplayString 
   ACCESS     read-only
   STATUS     mandatory
   DESCRIPTION
     "This variable provides the component's string name for
      use with the ASCII Console Interface"
::= { mscLpSdhRowStatusEntry 2 }

mscLpSdhStorageType OBJECT-TYPE
   SYNTAX     StorageType 
   ACCESS     read-only
   STATUS     mandatory
   DESCRIPTION
     "This variable represents the storage type value for the
      mscLpSdh tables."
::= { mscLpSdhRowStatusEntry 4 }

mscLpSdhIndex OBJECT-TYPE
   SYNTAX     Integer32 (0..3)
   ACCESS     not-accessible
   STATUS     mandatory
   DESCRIPTION
     "This variable represents the index for the mscLpSdh tables."
::= { mscLpSdhRowStatusEntry 10 }

mscLpSdhProvTable OBJECT-TYPE
   SYNTAX     SEQUENCE OF MscLpSdhProvEntry
   ACCESS     not-accessible
   STATUS     mandatory
   DESCRIPTION
     "This group contains all of the provisioning data for a Sonet or Sdh 
      component."
::= { mscLpSdh 10 }

mscLpSdhProvEntry OBJECT-TYPE
   SYNTAX     MscLpSdhProvEntry
   ACCESS     not-accessible
   STATUS     mandatory
   DESCRIPTION
     "An entry in the mscLpSdhProvTable."
   INDEX {
      mscLpIndex,
      mscLpSdhIndex }
::= { mscLpSdhProvTable 1 }

MscLpSdhProvEntry ::= SEQUENCE {
   mscLpSdhClockingSource
      INTEGER }

mscLpSdhClockingSource OBJECT-TYPE
   SYNTAX     INTEGER  {
                 local(0),
                 line(1),
                 module(2) }
   ACCESS     read-write
   STATUS     mandatory
   DESCRIPTION
     "This attribute defines the type of clocking source used for 
      synchronizing the OC-3 transmit clock: local means direct use of 
      the local clock oscillator at its centre frequency; line means the use 
      of a signal phase-locked to the incoming OC-3 line rate; module 
      means the use of a signal phase-locked to the CP reference clock. 
      When adding a Sonet/Sdh component, the clockingSource attribute 
      is set to module if the NetworkSynchronization component has 
      been added and is set to local otherwise.
      Note that the multiport OC-3 cell-based cards has one common 
      clock source for each of the three ports when either the clocking 
      source local or module is selected. For this reason, it is not allowed 
      to have at the same time the clockingSource attribute set to local on 
      one port and module on another port. Furthermore, the 
      clockingSource attribute cannot be set to module if the 
      NetworkSynchronization component has not been added."
::= { mscLpSdhProvEntry 1 }

mscLpSdhCidDataTable OBJECT-TYPE
   SYNTAX     SEQUENCE OF MscLpSdhCidDataEntry
   ACCESS     not-accessible
   STATUS     mandatory
   DESCRIPTION
     "This group contains the attribute for a component's Customer 
      Identifier (CID). Refer to the attribute description for a detailed 
      explanation of CIDs."
::= { mscLpSdh 11 }

mscLpSdhCidDataEntry OBJECT-TYPE
   SYNTAX     MscLpSdhCidDataEntry
   ACCESS     not-accessible
   STATUS     mandatory
   DESCRIPTION
     "An entry in the mscLpSdhCidDataTable."
   INDEX {
      mscLpIndex,
      mscLpSdhIndex }
::= { mscLpSdhCidDataTable 1 }

MscLpSdhCidDataEntry ::= SEQUENCE {
   mscLpSdhCustomerIdentifier
      Unsigned32 }

mscLpSdhCustomerIdentifier OBJECT-TYPE
   SYNTAX     Unsigned32 (0 | 1..8191)
   ACCESS     read-write
   STATUS     mandatory
   DESCRIPTION
     "This attribute holds the Customer Identifier (CID).
      
      Every component has a CID. If a component has a cid attribute, the 
      component's CID is the provisioned value of that attribute; 
      otherwise the component inherits the CID of its parent. The top-
      level component has a CID of 0.
      
      Every operator session also has a CID, which is the CID 
      provisioned for the operator's user ID. An operator will see only the 
      stream data for components having a matching CID. Also, the 
      operator will be allowed to issue commands for only those 
      components which have a matching CID.
      
      An operator CID of 0 is used to identify the Network Manager 
      (referred to as 'NetMan' in DPN). This CID matches the CID of 
      any component. Values 1 to 8191 inclusive (equivalent to 'basic 
      CIDs' in DPN) may be assigned to specific customers."
   DEFVAL     { 0 }
::= { mscLpSdhCidDataEntry 1 }

mscLpSdhAdminInfoTable OBJECT-TYPE
   SYNTAX     SEQUENCE OF MscLpSdhAdminInfoEntry
   ACCESS     not-accessible
   STATUS     mandatory
   DESCRIPTION
     "This group contains the attributes pertaining to the vendor of the 
      equipment."
::= { mscLpSdh 12 }

mscLpSdhAdminInfoEntry OBJECT-TYPE
   SYNTAX     MscLpSdhAdminInfoEntry
   ACCESS     not-accessible
   STATUS     mandatory
   DESCRIPTION
     "An entry in the mscLpSdhAdminInfoTable."
   INDEX {
      mscLpIndex,
      mscLpSdhIndex }
::= { mscLpSdhAdminInfoTable 1 }

MscLpSdhAdminInfoEntry ::= SEQUENCE {
   mscLpSdhVendor
      AsciiString,
   mscLpSdhCommentText
      AsciiString }

mscLpSdhVendor OBJECT-TYPE
   SYNTAX     AsciiString (SIZE (0..20))
   ACCESS     read-write
   STATUS     mandatory
   DESCRIPTION
     "This is the name of the vendor supplying the facility."
::= { mscLpSdhAdminInfoEntry 1 }

mscLpSdhCommentText OBJECT-TYPE
   SYNTAX     AsciiString (SIZE (0..60))
   ACCESS     read-write
   STATUS     mandatory
   DESCRIPTION
     "Any miscellaneous text about the facility."
::= { mscLpSdhAdminInfoEntry 2 }

mscLpSdhIfEntryTable OBJECT-TYPE
   SYNTAX     SEQUENCE OF MscLpSdhIfEntryEntry
   ACCESS     not-accessible
   STATUS     mandatory
   DESCRIPTION
     "This group contains the provisionable attributes for the ifEntry."
::= { mscLpSdh 13 }

mscLpSdhIfEntryEntry OBJECT-TYPE
   SYNTAX     MscLpSdhIfEntryEntry
   ACCESS     not-accessible
   STATUS     mandatory
   DESCRIPTION
     "An entry in the mscLpSdhIfEntryTable."
   INDEX {
      mscLpIndex,
      mscLpSdhIndex }
::= { mscLpSdhIfEntryTable 1 }

MscLpSdhIfEntryEntry ::= SEQUENCE {
   mscLpSdhIfAdminStatus
      INTEGER,
   mscLpSdhIfIndex
      InterfaceIndex }

mscLpSdhIfAdminStatus OBJECT-TYPE
   SYNTAX     INTEGER  {
                 up(1),
                 down(2),
                 testing(3) }
   ACCESS     read-write
   STATUS     mandatory
   DESCRIPTION
     "The desired state of the interface. The up state indicates the 
      interface is operational. The down state indicates the interface is not 
      operational. The testing state indicates that no operational packets 
      can be passed."
   DEFVAL     { up }
::= { mscLpSdhIfEntryEntry 1 }

mscLpSdhIfIndex OBJECT-TYPE
   SYNTAX     InterfaceIndex (1..65535)
   ACCESS     read-only
   STATUS     mandatory
   DESCRIPTION
     "This is the index for the IfEntry. Its value is automatically initialized 
      during the provisioning process."
::= { mscLpSdhIfEntryEntry 2 }

mscLpSdhOperStatusTable OBJECT-TYPE
   SYNTAX     SEQUENCE OF MscLpSdhOperStatusEntry
   ACCESS     not-accessible
   STATUS     mandatory
   DESCRIPTION
     "This group includes the Operational Status attribute. This attribute 
      defines the current operational state of this component."
::= { mscLpSdh 14 }

mscLpSdhOperStatusEntry OBJECT-TYPE
   SYNTAX     MscLpSdhOperStatusEntry
   ACCESS     not-accessible
   STATUS     mandatory
   DESCRIPTION
     "An entry in the mscLpSdhOperStatusTable."
   INDEX {
      mscLpIndex,
      mscLpSdhIndex }
::= { mscLpSdhOperStatusTable 1 }

MscLpSdhOperStatusEntry ::= SEQUENCE {
   mscLpSdhSnmpOperStatus
      INTEGER }

mscLpSdhSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { mscLpSdhOperStatusEntry 1 }

mscLpSdhStateTable OBJECT-TYPE
   SYNTAX     SEQUENCE OF MscLpSdhStateEntry
   ACCESS     not-accessible
   STATUS     mandatory
   DESCRIPTION
     "This group contains the three OSI State attributes and the six OSI 
      Status attributes. The descriptions generically indicate what each 
      attribute implies about the component. Note that not all the values 
      and state combinations described here are supported by every 
      component which uses this group. For component-specific 
      information and the valid state combinations, refer to NTP 241-
      7001-150, Passport Operations and Maintenance Guide."
::= { mscLpSdh 15 }

mscLpSdhStateEntry OBJECT-TYPE
   SYNTAX     MscLpSdhStateEntry
   ACCESS     not-accessible
   STATUS     mandatory
   DESCRIPTION
     "An entry in the mscLpSdhStateTable."
   INDEX {
      mscLpIndex,
      mscLpSdhIndex }
::= { mscLpSdhStateTable 1 }

MscLpSdhStateEntry ::= SEQUENCE {
   mscLpSdhAdminState
      INTEGER,
   mscLpSdhOperationalState
      INTEGER,
   mscLpSdhUsageState
      INTEGER,
   mscLpSdhAvailabilityStatus
      OCTET STRING,
   mscLpSdhProceduralStatus
      OCTET STRING,
   mscLpSdhControlStatus
      OCTET STRING,
   mscLpSdhAlarmStatus
      OCTET STRING,
   mscLpSdhStandbyStatus
      INTEGER,
   mscLpSdhUnknownStatus
      INTEGER }

mscLpSdhAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component.
      
      The OSI Status attributes, if supported by the component, may 
      provide more details, qualifying the state of the component."
   DEFVAL     { unlocked }
::= { mscLpSdhStateEntry 1 }

mscLpSdhOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle.
      
      The OSI Status attributes, if supported by the component, may 
      provide more details, qualifying the state of the component."
   DEFVAL     { disabled }
::= { mscLpSdhStateEntry 2 }

mscLpSdhUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time.
      
      The OSI Status attributes, if supported by the component, may 
      provide more details, qualifying the state of the component."
   DEFVAL     { idle }
::= { mscLpSdhStateEntry 3 }

mscLpSdhAvailabilityStatus OBJECT-TYPE
   SYNTAX     OCTET STRING (SIZE (2))
   ACCESS     read-only
   STATUS     mandatory
   DESCRIPTION
     "If supported by the component, this attribute indicates the OSI 
      Availability status of the component. Note that, even though it is 
      defined as a multi-valued set, at most one value is shown to the user.
      
      When no values are in the set, this indicates that either the attribute 
      is not supported or that none of the status conditions described 
      below are present.
      
      The value inTest indicates that the resource is undergoing a test 
      procedure. If adminState is locked or shuttingDown, the normal 
      users are precluded from using the resource and controlStatus is 
      reservedForTest. Tests that do not exclude additional users can be 
      present in any operational or administrative state but the 
      reservedForTest condition should not be present.
      
      The value failed indicates that the component has an internal fault 
      that prevents it from operating. The operationalState is disabled.
      
      The value dependency indicates that the component cannot operate 
      because some other resource on which it depends is unavailable. 
      The operationalState is disabled.
      
      The value powerOff indicates the resource requires power to be 
      applied and it is not powered on. The operationalState is disabled.
      
      The value offLine indicates the resource requires a routine 
      operation (either manual, automatic, or both) to be performed to 
      place it on-line and make it available for use. The operationalState 
      is disabled.
      
      The value offDuty indicates the resource is inactive in accordance 
      with a predetermined time schedule. In the absence of other 
      disabling conditions, the operationalState is enabled or disabled.
      
      The value degraded indicates the service provided by the 
      component is degraded in some way, such as in speed or operating 
      capacity. However, the resource remains available for service. The 
      operationalState is enabled.
      
      The value notInstalled indicates the resource is not present. The 
      operationalState is disabled.
      
      The value logFull is not used.

      Description of bits:
      inTest(0)
      failed(1)
      powerOff(2)
      offLine(3)
      offDuty(4)
      dependency(5)
      degraded(6)
      notInstalled(7)
      logFull(8)"
::= { mscLpSdhStateEntry 4 }

mscLpSdhProceduralStatus OBJECT-TYPE
   SYNTAX     OCTET STRING (SIZE (1))
   ACCESS     read-only
   STATUS     mandatory
   DESCRIPTION
     "If supported by the component, this attribute indicates the OSI 
      Procedural status of the component. Note that, even though it is 
      defined as a multi-valued set, at most one value is shown to the user.
      
      When no values are in the set, this indicates that either the attribute 
      is not supported or that none of the status conditions described 
      below are present.
      
      The value initializationRequired indicates (for a resource which 
      doesn't initialize autonomously) that initialization is required before 
      it can perform its normal functions, and this procedure has not been 
      initiated. The operationalState is disabled.
      
      The value notInitialized indicates (for a resource which does 
      initialize autonomously) that initialization is required before it can 
      perform its normal functions, and this procedure has not been 
      initiated. The operationalState may be enabled or disabled.
      
      The value initializing indicates that initialization has been initiated 
      but is not yet complete. The operationalState may be enabled or 
      disabled.
      
      The value reporting indicates the resource has completed some 
      processing operation and is notifying the results. The 
      operationalState is enabled.
      
      The value terminating indicates the component is in a termination 
      phase. If the resource doesn't reinitialize autonomously, 
      operationalState is disabled; otherwise it is enabled or disabled.

      Description of bits:
      initializationRequired(0)
      notInitialized(1)
      initializing(2)
      reporting(3)
      terminating(4)"
::= { mscLpSdhStateEntry 5 }

mscLpSdhControlStatus OBJECT-TYPE
   SYNTAX     OCTET STRING (SIZE (1))
   ACCESS     read-only
   STATUS     mandatory
   DESCRIPTION
     "If supported by the component, this attribute indicates the OSI 
      Control status of the component. Note that, even though it is defined 
      as a multi-valued set, at most one value is shown to the user.
      
      When no values are in the set, this indicates that either the attribute 
      is not supported or that none of the status conditions described 
      below are present.
      
      The value subjectToTest indicates the resource is available but tests 
      may be conducted simultaneously at unpredictable times, which 
      may cause it to exhibit unusual characteristics.
      
      The value partOfServicesLocked indicates that part of the service is 
      restricted from users of a resource. The adminState is unlocked.
      
      The value reservedForTest indicates that the component is 
      administratively unavailable because it is undergoing a test 
      procedure. The adminState is locked.
      
      The value suspended indicates that the service has been 
      administratively suspended.

      Description of bits:
      subjectToTest(0)
      partOfServicesLocked(1)
      reservedForTest(2)
      suspended(3)"
::= { mscLpSdhStateEntry 6 }

mscLpSdhAlarmStatus OBJECT-TYPE
   SYNTAX     OCTET STRING (SIZE (1))
   ACCESS     read-only
   STATUS     mandatory
   DESCRIPTION
     "If supported by the component, this attribute indicates the OSI 
      Alarm status of the component. Note that, even though it is defined 
      as a multi-valued set, at most one value is shown to the user.
      
      When no values are in the set, this indicates that either the attribute 
      is not supported or that none of the status conditions described 
      below are present.
      
      The value underRepair indicates the component is currently being 
      repaired. The operationalState is enabled or disabled.
      
      The value critical indicates one or more critical alarms are 
      outstanding against the component. Other, less severe, alarms may 
      also be outstanding. The operationalState is enabled or disabled.
      
      The value major indicates one or more major alarms are 
      outstanding against the component. Other, less severe, alarms may 
      also be outstanding. The operationalState is enabled or disabled.
      
      The value minor indicates one or more minor alarms are 
      outstanding against the component. Other, less severe, alarms may 
      also be outstanding. The operationalState is enabled or disabled.
      
      The value alarmOutstanding generically indicates that an alarm of 
      some severity is outstanding against the component.

      Description of bits:
      underRepair(0)
      critical(1)
      major(2)
      minor(3)
      alarmOutstanding(4)"
::= { mscLpSdhStateEntry 7 }

mscLpSdhStandbyStatus OBJECT-TYPE
   SYNTAX     INTEGER  {
                 hotStandby(0),
                 coldStandby(1),
                 providingService(2),
                 notSet(15) }
   ACCESS     read-only
   STATUS     mandatory
   DESCRIPTION
     "If supported by the component, this attribute indicates the OSI 
      Standby status of the component.
      
      The value notSet indicates that either the attribute is not supported 
      or that none of the status conditions described below are present. 
      Note that this is a non-standard value, used because the original 
      specification indicated this attribute was set-valued and thus, did not 
      provide a value to indicate that none of the other three are 
      applicable.
      
      The value hotStandby indicates that the resource is not providing 
      service but will be immediately able to take over the role of the 
      resource to be backed up, without initialization activity, and 
      containing the same information as the resource to be backed up.
      
      The value coldStandby indicates the resource is a backup for 
      another resource but will not be immediately able to take over the 
      role of the backed up resource and will require some initialization 
      activity.
      
      The value providingService indicates that this component, as a 
      backup resource, is currently backing up another resource."
   DEFVAL     { notSet }
::= { mscLpSdhStateEntry 8 }

mscLpSdhUnknownStatus OBJECT-TYPE
   SYNTAX     INTEGER  {
                 false(0),
                 true(1) }
   ACCESS     read-only
   STATUS     mandatory
   DESCRIPTION
     "This attribute indicates the OSI Unknown status of the component.
      
      The value false indicates that all of the other OSI State and Status 
      attribute values can be considered accurate.
      
      The value true indicates that the actual state of the component is not 
      known for sure."
   DEFVAL     { false }
::= { mscLpSdhStateEntry 9 }

mscLpSdhOperTable OBJECT-TYPE
   SYNTAX     SEQUENCE OF MscLpSdhOperEntry
   ACCESS     not-accessible
   STATUS     mandatory
   DESCRIPTION
     "This group contains the common operational data for Sonet or Sdh 
      component."
::= { mscLpSdh 16 }

mscLpSdhOperEntry OBJECT-TYPE
   SYNTAX     MscLpSdhOperEntry
   ACCESS     not-accessible
   STATUS     mandatory
   DESCRIPTION
     "An entry in the mscLpSdhOperTable."
   INDEX {
      mscLpIndex,
      mscLpSdhIndex }
::= { mscLpSdhOperTable 1 }

MscLpSdhOperEntry ::= SEQUENCE {
   mscLpSdhLosAlarm
      INTEGER,
   mscLpSdhLofAlarm
      INTEGER,
   mscLpSdhRxAisAlarm
      INTEGER,
   mscLpSdhRxRfiAlarm
      INTEGER,
   mscLpSdhTxAis
      INTEGER,
   mscLpSdhTxRdi
      INTEGER,
   mscLpSdhUnusableTxClockRefAlarm
      INTEGER }

mscLpSdhLosAlarm OBJECT-TYPE
   SYNTAX     INTEGER  {
                 on(0),
                 off(1) }
   ACCESS     read-only
   STATUS     mandatory
   DESCRIPTION
     "This attribute indicates whether a Loss Of Signal (LOS) alarm state 
      has been entered. An LOS alarm state is entered when LOS defects 
      have been observed and accumulated for a period of 2.5 seconds +/- 
      0.5 seconds, or if an LOS defect is present when the criteria for 
      LOF failure declaration have been met. A LOS defect is declared 
      when 20+/-3 us of all-zeros pattern is detected. The LOS defect is 
      cleared when two valid framing words are detected and no Loss Of 
      Signal condition is detected during an interval of 20+/-3 us. If the 
      LOS defects are intermittently occurring, the LOS defect 
      accumulator is decremented at a rate of 1/10 of the incrementing 
      rate (alarm integration ratio of 1/10), with all measurements based 
      on a 200 ms polling cycle.
      The Sonet/Sdh component goes into an operational state of disabled 
      until the LOS alarm condition is cleared. The LOS alarm state is 
      cleared after LOS defects have been absent for a period of 10 
      seconds +/- 0.5 seconds.
      The losAlarm attribute is always set to off when the component has 
      been locked and left offline."
::= { mscLpSdhOperEntry 1 }

mscLpSdhLofAlarm OBJECT-TYPE
   SYNTAX     INTEGER  {
                 on(0),
                 off(1) }
   ACCESS     read-only
   STATUS     mandatory
   DESCRIPTION
     "This attribute displays whether a Loss Of Frame (LOF) alarm state 
      has been entered. An LOF alarm state is entered when LOF defects 
      have been observed and accumulated for a period of 2.5 seconds +/- 
      0.5 seconds, except when an LOS defect or failure is present. An 
      LOF defect is detected when getting contiguous errored frame 
      alignment for at least 3 msec. If the LOF defects are intermittently 
      occurring, the LOF defect accumulator is decremented at a rate of 
      1/10 of the incrementing rate (alarm integration ratio of 1/10), with 
      all measurements based on a 200 ms polling cycle.
      The Sonet/Sdh component goes into an operational state of disabled 
      until the LOF alarm condition is cleared. The condition is cleared 
      when framing has been achieved for a period of 10 seconds +/- 0.5 
      seconds.
      The lofAlarm attribute is always set to off when the component has 
      been locked and left offline."
::= { mscLpSdhOperEntry 2 }

mscLpSdhRxAisAlarm OBJECT-TYPE
   SYNTAX     INTEGER  {
                 on(0),
                 off(1) }
   ACCESS     read-only
   STATUS     mandatory
   DESCRIPTION
     "This attribute displays whether a Line Alarm Indication Signal (L-
      AIS) alarm state has been entered. An L-AIS alarm state is entered 
      when L-AIS defects have been observed and accumulated for a 
      period of 2.5 seconds +/- 0.5 seconds. The L-AIS defect is the 
      occurrence of the L-AIS signal in five contiguous STS (STM) 
      frames (111 pattern in bits 6,7, and 8 of the K2 bytes). If the L-AIS 
      defects are intermittently occurring, the L-AIS defect accumulator 
      is decremented at a rate of 1/10 of the incrementing rate (alarm 
      integration ratio of 1/10), with all measurements based on a 200 ms 
      polling cycle.
      The Sonet/Sdh component goes into an operational state of disabled 
      until the L-AIS alarm condition is cleared. The condition is cleared 
      after not detecting the L-AIS signal for a period of 10 seconds +/- 
      0.5 seconds.
      The rxAisAlarm attribute is always set to off when the component 
      has been locked and left offline."
::= { mscLpSdhOperEntry 3 }

mscLpSdhRxRfiAlarm OBJECT-TYPE
   SYNTAX     INTEGER  {
                 on(0),
                 off(1) }
   ACCESS     read-only
   STATUS     mandatory
   DESCRIPTION
     "This attribute displays whether a Line Remote Failure Indication 
      (LRFI) alarm state has been entered. An L-RFI alarm state is 
      entered when Line Remote Failure Indication (L-RDI) defects have 
      been observed and accumulated for a period of 2.5 seconds +/- 0.5 
      seconds. The L-RDI defect is the occurrence of the L-RDI signal in 
      five contiguous valid STS (STM) frame (110 pattern in bits 6,7, and 
      8 of the K2 bytes). If the L-RDI defects are intermittently occurring, 
      the L-RDI defect accumulator is decremented at a rate of 1/10 of 
      the incrementing rate (alarm integration ratio of 1/10), with all 
      measurements based on a 200 ms polling cycle.
      The Sonet/Sdh component goes into an operational state of disabled 
      until the L-RFI alarm condition is cleared. The condition is cleared 
      after not detecting the L-RDI signal for a period of 10 seconds +/- 
      0.5 seconds.
      The rxRfiAlarm attribute is always set to off when the component 
      has been locked and left offline."
::= { mscLpSdhOperEntry 4 }

mscLpSdhTxAis OBJECT-TYPE
   SYNTAX     INTEGER  {
                 on(0),
                 off(1) }
   ACCESS     read-only
   STATUS     mandatory
   DESCRIPTION
     "This attribute displays whether the Line Alarm Indication Signal (L-
      AIS) signal is being transmitted on the outgoing line. This signal is 
      transmitted when the Sonet/Sdh is locked and left offline."
::= { mscLpSdhOperEntry 5 }

mscLpSdhTxRdi OBJECT-TYPE
   SYNTAX     INTEGER  {
                 on(0),
                 off(1) }
   ACCESS     read-only
   STATUS     mandatory
   DESCRIPTION
     "This attribute displays whether the Line Remote Defect Indicator 
      (L-RDI) signal is being transmitted over the OC-3 line. The L-RDI 
      signal is transmitted upon the detection of the LOS, LOF or L-AIS 
      defect. This attribute is always set to off when the component has 
      been locked and left offline."
::= { mscLpSdhOperEntry 6 }

mscLpSdhUnusableTxClockRefAlarm OBJECT-TYPE
   SYNTAX     INTEGER  {
                 on(0),
                 off(1) }
   ACCESS     read-only
   STATUS     mandatory
   DESCRIPTION
     "This attribute displays whether an Unusable Transmit Clock 
      Reference (UTCR) alarm state has been entered. A UTCR alarm 
      state is entered when a Sonet/Sdh port provisioned to act as a 
      transmit clock reference has received the code 'do not use for 
      synchronization' in the S1 byte (in the SONET/ SDH line 
      overhead) for 2.5 +/- 0.5 seconds.
      The condition is cleared after not detecting the 'do not use for 
      synchronization' code for a period of 10 +/- 0.5 seconds or when 
      the port is no longer provisioned to act as a transmit clock 
      reference.
      A port is acting as a transmit clock reference if it is provisioned 
      with a) a clockingSource of line, or b) it has been provisioned as a 
      primaryReference, secondaryReference or tertiaryReference in the 
      NetworkSynchronization component.
      The unusableTxClockRefAlarm attribute is always set to off when 
      the component has been locked and left offline."
::= { mscLpSdhOperEntry 7 }

mscLpSdhStatsTable OBJECT-TYPE
   SYNTAX     SEQUENCE OF MscLpSdhStatsEntry
   ACCESS     not-accessible
   STATUS     mandatory
   DESCRIPTION
     "This group contains the statistics data for a Sonet or Sdh 
      component. Each attribute type is a non-negative integer which 
      monotonically increases until it reaches a maximum value, at which 
      point it wraps around and starts increasing again from zero."
::= { mscLpSdh 17 }

mscLpSdhStatsEntry OBJECT-TYPE
   SYNTAX     MscLpSdhStatsEntry
   ACCESS     not-accessible
   STATUS     mandatory
   DESCRIPTION
     "An entry in the mscLpSdhStatsTable."
   INDEX {
      mscLpIndex,
      mscLpSdhIndex }
::= { mscLpSdhStatsTable 1 }

MscLpSdhStatsEntry ::= SEQUENCE {
   mscLpSdhRunningTime
      Counter32,
   mscLpSdhErrorFreeSec
      Counter32,
   mscLpSdhSectCodeViolations
      Counter32,
   mscLpSdhSectErroredSec
      Counter32,
   mscLpSdhSectSevErroredSec
      Counter32,
   mscLpSdhSectLosSec
      Counter32,
   mscLpSdhSectSevErroredFrmSec
      Counter32,
   mscLpSdhSectFailures
      Counter32,
   mscLpSdhLineCodeViolations
      Counter32,
   mscLpSdhLineErroredSec
      Counter32,
   mscLpSdhLineSevErroredSec
      Counter32,
   mscLpSdhLineAisSec
      Counter32,
   mscLpSdhLineUnavailSec
      Counter32,
   mscLpSdhLineFailures
      Counter32,
   mscLpSdhFarEndLineErrorFreeSec
      Counter32,
   mscLpSdhFarEndLineCodeViolations
      Counter32,
   mscLpSdhFarEndLineErroredSec
      Counter32,
   mscLpSdhFarEndLineSevErroredSec
      Counter32,
   mscLpSdhFarEndLineAisSec
      Counter32,
   mscLpSdhFarEndLineUnavailSec
      Counter32,
   mscLpSdhFarEndLineFailures
      Counter32 }

mscLpSdhRunningTime OBJECT-TYPE
   SYNTAX     Counter32 
   ACCESS     read-only
   STATUS     mandatory
   DESCRIPTION
     "This attribute indicates the total number of seconds since the Sonet/
      Sdh component has been activated and been in unlocked state. All 
      the other error counts that follow can be updated when this count is 
      active."
::= { mscLpSdhStatsEntry 1 }

mscLpSdhErrorFreeSec OBJECT-TYPE
   SYNTAX     Counter32 
   ACCESS     read-only
   STATUS     mandatory
   DESCRIPTION
     "This attribute indicates the number of seconds that the Sonet/Sdh 
      component has been in an near-end error free state."
::= { mscLpSdhStatsEntry 2 }

mscLpSdhSectCodeViolations OBJECT-TYPE
   SYNTAX     Counter32 
   ACCESS     read-only
   STATUS     mandatory
   DESCRIPTION
     "This attribute indicates the total number of Section Code Violations 
      (SCVs) detected. A SCV corresponds to section BIP-8 error. SCV 
      counting is inhibited for second intervals where a Section Severely 
      Errored Second (SSES) is counted. The count wraps at its 
      maximum value."
::= { mscLpSdhStatsEntry 3 }

mscLpSdhSectErroredSec OBJECT-TYPE
   SYNTAX     Counter32 
   ACCESS     read-only
   STATUS     mandatory
   DESCRIPTION
     "This attribute indicates the total number of Section Errored Seconds 
      (SESs) that have been counted. A SES is declared for second 
      intervals containing one or more SCVs or one or more Loss Of 
      Signal (LOS) or Severely Errored Frame (SEF) defects. A SEF 
      defect is the occurrence of 4 contiguous errored STS or STM frame 
      alignment words."
::= { mscLpSdhStatsEntry 4 }

mscLpSdhSectSevErroredSec OBJECT-TYPE
   SYNTAX     Counter32 
   ACCESS     read-only
   STATUS     mandatory
   DESCRIPTION
     "This attribute indicates the total number of Section Severely Errored 
      Seconds (SSESs) that have been counted. A SSES is declared for 
      second intervals containing more than x SCVs or one or more LOS 
      or SEF defects. The value of x is 155 for a 155 Mbits/sec interface."
::= { mscLpSdhStatsEntry 5 }

mscLpSdhSectLosSec OBJECT-TYPE
   SYNTAX     Counter32 
   ACCESS     read-only
   STATUS     mandatory
   DESCRIPTION
     "This attribute indicates the total number of Section LOS Seconds 
      (SLOSSs) that have been counted. A SLOSS is declared for second 
      intervals containing one or more LOS defects."
::= { mscLpSdhStatsEntry 6 }

mscLpSdhSectSevErroredFrmSec OBJECT-TYPE
   SYNTAX     Counter32 
   ACCESS     read-only
   STATUS     mandatory
   DESCRIPTION
     "This attribute indicates the total number of Section Severely Errored 
      Frame Seconds (SSEFSs) that have been counted. A SSEFS is 
      declared for second intervals containing one or more SEF defects."
::= { mscLpSdhStatsEntry 7 }

mscLpSdhSectFailures OBJECT-TYPE
   SYNTAX     Counter32 
   ACCESS     read-only
   STATUS     mandatory
   DESCRIPTION
     "This attribute indicates the total number of times that a section 
      failure (LOS or LOF failure) has been declared."
::= { mscLpSdhStatsEntry 8 }

mscLpSdhLineCodeViolations OBJECT-TYPE
   SYNTAX     Counter32 
   ACCESS     read-only
   STATUS     mandatory
   DESCRIPTION
     "This attribute indicates the total number of Line Code Violations 
      (LCVs) detected. A LCV corresponds to a line BIP-24 errors. LCV 
      counting is inhibited for second intervals where a Line Severely 
      Errored Second (LSES) is counted. Counting of LCVs is also 
      inhibited over second intervals where a Line Unavailable Second 
      (LUAS) is counted. The count wraps at its maximum value."
::= { mscLpSdhStatsEntry 9 }

mscLpSdhLineErroredSec OBJECT-TYPE
   SYNTAX     Counter32 
   ACCESS     read-only
   STATUS     mandatory
   DESCRIPTION
     "This attribute indicates the total number of Line Errored Seconds 
      (LESs) that have been counted. A LES is declared for second 
      intervals containing one or more LCVs or one or more line AIS 
      defects. Counting of LES is inhibited over second intervals where a 
      LUAS is counted."
::= { mscLpSdhStatsEntry 10 }

mscLpSdhLineSevErroredSec OBJECT-TYPE
   SYNTAX     Counter32 
   ACCESS     read-only
   STATUS     mandatory
   DESCRIPTION
     "This attribute indicates the total number of Line Severely Errored 
      Seconds (LSESs) that have been counted. A LSES is declared for 
      second intervals containing more than x LCVs or one or more L-
      AIS defects. The value of x is 154 for a 155 Mbits/sec interface. 
      Counting of LSES is inhibited over second intervals where a LUAS 
      is counted."
::= { mscLpSdhStatsEntry 11 }

mscLpSdhLineAisSec OBJECT-TYPE
   SYNTAX     Counter32 
   ACCESS     read-only
   STATUS     mandatory
   DESCRIPTION
     "This attribute indicates the total number of Line AIS Seconds 
      (LAISSs) that have been counted. A LAISS is declared for second 
      intervals containing one or more L-AIS defects. Counting of LAISS 
      is inhibited over second intervals where a LUAS is counted."
::= { mscLpSdhStatsEntry 12 }

mscLpSdhLineUnavailSec OBJECT-TYPE
   SYNTAX     Counter32 
   ACCESS     read-only
   STATUS     mandatory
   DESCRIPTION
     "This attribute indicates the total number of one second intervals for 
      which the STS line is unavailable. The STS line becomes 
      unavailable at the onset of 10 consecutive LSESs. The 10 LSESs are 
      included in the unavailable time. Once unavailable, the STS line 
      becomes available at the onset of 10 contiguous seconds with no 
      LSES. The 10 seconds with no LSES are excluded from the 
      unavailable time. For second intervals where a Line Unavailable 
      Second (LUAS) is counted, counting of LCV, LES, LSES and 
      LAISS is inhibited."
::= { mscLpSdhStatsEntry 13 }

mscLpSdhLineFailures OBJECT-TYPE
   SYNTAX     Counter32 
   ACCESS     read-only
   STATUS     mandatory
   DESCRIPTION
     "This attribute indicates the total number of times that a line failure 
      (L-AIS failure) has been declared."
::= { mscLpSdhStatsEntry 14 }

mscLpSdhFarEndLineErrorFreeSec OBJECT-TYPE
   SYNTAX     Counter32 
   ACCESS     read-only
   STATUS     mandatory
   DESCRIPTION
     "This attribute indicates the number of seconds that the Sonet/Sdh 
      component has been in an far-end error free state."
::= { mscLpSdhStatsEntry 15 }

mscLpSdhFarEndLineCodeViolations OBJECT-TYPE
   SYNTAX     Counter32 
   ACCESS     read-only
   STATUS     mandatory
   DESCRIPTION
     "This attribute indicates the total number of line FEBE detected from 
      the incoming line. The counting of line FEBE is inhibited for 
      second intervals where a Far-End Line Severely Errored Second 
      (FELSES) is counted. Counting of FELCVs is also inhibited over 
      second intervals where a Far-End Line Unavailable Second 
      (FELUAS) is counted. The count wraps at its maximum value."
::= { mscLpSdhStatsEntry 16 }

mscLpSdhFarEndLineErroredSec OBJECT-TYPE
   SYNTAX     Counter32 
   ACCESS     read-only
   STATUS     mandatory
   DESCRIPTION
     "This attribute indicates the total number of Far-End Line Errored 
      Seconds (FELESs) that have been counted. A FELES is declared 
      for second intervals containing one or more Far-End Line CVs 
      (FELCVs) or one or more L-RDI defects. Counting of FELES is 
      inhibited over second intervals where a FELUAS is counted."
::= { mscLpSdhStatsEntry 17 }

mscLpSdhFarEndLineSevErroredSec OBJECT-TYPE
   SYNTAX     Counter32 
   ACCESS     read-only
   STATUS     mandatory
   DESCRIPTION
     "This attribute indicates the total number of Far-End Line Severely 
      Errored Seconds (FELSESs) that have been counted. A FELSES is 
      declared for second intervals containing more than x FELCVs or 
      one or more L-RDI defects. The value of x is 154 for a 155 Mbits/
      sec interface. Counting of FELSES is inhibited over second 
      intervals where a FELUAS is counted."
::= { mscLpSdhStatsEntry 18 }

mscLpSdhFarEndLineAisSec OBJECT-TYPE
   SYNTAX     Counter32 
   ACCESS     read-only
   STATUS     mandatory
   DESCRIPTION
     "This attribute indicates the total number of Far-End Line AIS 
      Seconds (FELAISSs) that have been counted. A FELAISS is 
      declared for second intervals one or more L-RDI defects. Counting 
      of FELAISS is inhibited over second intervals where a FELUAS is 
      counted."
::= { mscLpSdhStatsEntry 19 }

mscLpSdhFarEndLineUnavailSec OBJECT-TYPE
   SYNTAX     Counter32 
   ACCESS     read-only
   STATUS     mandatory
   DESCRIPTION
     "This attribute indicates the total number of one second intervals for 
      which the STS far-end line is unavailable. The STS far-end line 
      becomes unavailable at the onset of 10 consecutive FELSESs. The 
      10 FELSESs are included in the unavailable time. Once unavailable, 
      the STS far-end line becomes available at the onset of 10 
      contiguous seconds with no FELSES. The 10 seconds with no 
      FELSES are excluded from the unavailable time. For second 
      intervals where a Far-End Line Unavailable Second (FELUAS) is 
      counted, counting of FELCV, FELES, FELSES and FELAISS is 
      inhibited."
::= { mscLpSdhStatsEntry 20 }

mscLpSdhFarEndLineFailures OBJECT-TYPE
   SYNTAX     Counter32 
   ACCESS     read-only
   STATUS     mandatory
   DESCRIPTION
     "This attribute indicates the total number of times that a far-end line 
      failure (L-RFI failure) has been declared."
::= { mscLpSdhStatsEntry 21 }


-- ApmSonetSdhPath
-- The Lp/m Sonet/n Path or Lp/m Sdh/n Path component controls a 
-- path signal that is carried within a SONET or SDH signal. The Path 
-- component can only be added under a Sonet or Sdh component.

mscLpSdhPath OBJECT IDENTIFIER ::= { mscLpSdh 2 }



mscLpSdhPathRowStatusTable OBJECT-TYPE
   SYNTAX     SEQUENCE OF MscLpSdhPathRowStatusEntry
   ACCESS     not-accessible
   STATUS     mandatory
   DESCRIPTION
     "This entry controls the addition and deletion of 
      mscLpSdhPath components."
::= { mscLpSdhPath 1 }

mscLpSdhPathRowStatusEntry OBJECT-TYPE
   SYNTAX     MscLpSdhPathRowStatusEntry
   ACCESS     not-accessible
   STATUS     mandatory
   DESCRIPTION
     "A single entry in the table represents a single 
      mscLpSdhPath component."
   INDEX {
      mscLpIndex,
      mscLpSdhIndex,
      mscLpSdhPathIndex }
::= { mscLpSdhPathRowStatusTable 1 }

MscLpSdhPathRowStatusEntry ::= SEQUENCE {
   mscLpSdhPathRowStatus
      RowStatus,
   mscLpSdhPathComponentName
      DisplayString,
   mscLpSdhPathStorageType
      StorageType,
   mscLpSdhPathIndex
      Integer32 }

mscLpSdhPathRowStatus OBJECT-TYPE
   SYNTAX     RowStatus 
   ACCESS     read-write
   STATUS     mandatory
   DESCRIPTION
     "This variable is used as the basis for SNMP naming of
      mscLpSdhPath components.
      These components can be added and deleted."
::= { mscLpSdhPathRowStatusEntry 1 }

mscLpSdhPathComponentName OBJECT-TYPE
   SYNTAX     DisplayString 
   ACCESS     read-only
   STATUS     mandatory
   DESCRIPTION
     "This variable provides the component's string name for
      use with the ASCII Console Interface"
::= { mscLpSdhPathRowStatusEntry 2 }

mscLpSdhPathStorageType OBJECT-TYPE
   SYNTAX     StorageType 
   ACCESS     read-only
   STATUS     mandatory
   DESCRIPTION
     "This variable represents the storage type value for the
      mscLpSdhPath tables."
::= { mscLpSdhPathRowStatusEntry 4 }

mscLpSdhPathIndex OBJECT-TYPE
   SYNTAX     Integer32 (0..0)
   ACCESS     not-accessible
   STATUS     mandatory
   DESCRIPTION
     "This variable represents the index for the mscLpSdhPath tables."
::= { mscLpSdhPathRowStatusEntry 10 }

mscLpSdhPathProvTable OBJECT-TYPE
   SYNTAX     SEQUENCE OF MscLpSdhPathProvEntry
   ACCESS     not-accessible
   STATUS     mandatory
   DESCRIPTION
     "This group contains all of the provisioning data for a Sonet/Sdh 
      Path component."
::= { mscLpSdhPath 10 }

mscLpSdhPathProvEntry OBJECT-TYPE
   SYNTAX     MscLpSdhPathProvEntry
   ACCESS     not-accessible
   STATUS     mandatory
   DESCRIPTION
     "An entry in the mscLpSdhPathProvTable."
   INDEX {
      mscLpIndex,
      mscLpSdhIndex,
      mscLpSdhPathIndex }
::= { mscLpSdhPathProvTable 1 }

MscLpSdhPathProvEntry ::= SEQUENCE {
   mscLpSdhPathApplicationFramerName
      Link }

mscLpSdhPathApplicationFramerName OBJECT-TYPE
   SYNTAX     Link 
   ACCESS     read-write
   STATUS     mandatory
   DESCRIPTION
     "This attribute defines the link to the software stack. It defines which 
      application is running on top of the Path component."
::= { mscLpSdhPathProvEntry 1 }

mscLpSdhPathCidDataTable OBJECT-TYPE
   SYNTAX     SEQUENCE OF MscLpSdhPathCidDataEntry
   ACCESS     not-accessible
   STATUS     mandatory
   DESCRIPTION
     "This group contains the attribute for a component's Customer 
      Identifier (CID). Refer to the attribute description for a detailed 
      explanation of CIDs."
::= { mscLpSdhPath 11 }

mscLpSdhPathCidDataEntry OBJECT-TYPE
   SYNTAX     MscLpSdhPathCidDataEntry
   ACCESS     not-accessible
   STATUS     mandatory
   DESCRIPTION
     "An entry in the mscLpSdhPathCidDataTable."
   INDEX {
      mscLpIndex,
      mscLpSdhIndex,
      mscLpSdhPathIndex }
::= { mscLpSdhPathCidDataTable 1 }

MscLpSdhPathCidDataEntry ::= SEQUENCE {
   mscLpSdhPathCustomerIdentifier
      Unsigned32 }

mscLpSdhPathCustomerIdentifier OBJECT-TYPE
   SYNTAX     Unsigned32 (0 | 1..8191)
   ACCESS     read-write
   STATUS     mandatory
   DESCRIPTION
     "This attribute holds the Customer Identifier (CID).
      
      Every component has a CID. If a component has a cid attribute, the 
      component's CID is the provisioned value of that attribute; 
      otherwise the component inherits the CID of its parent. The top-
      level component has a CID of 0.
      
      Every operator session also has a CID, which is the CID 
      provisioned for the operator's user ID. An operator will see only the 
      stream data for components having a matching CID. Also, the 
      operator will be allowed to issue commands for only those 
      components which have a matching CID.
      
      An operator CID of 0 is used to identify the Network Manager 
      (referred to as 'NetMan' in DPN). This CID matches the CID of 
      any component. Values 1 to 8191 inclusive (equivalent to 'basic 
      CIDs' in DPN) may be assigned to specific customers."
   DEFVAL     { 0 }
::= { mscLpSdhPathCidDataEntry 1 }

mscLpSdhPathStateTable OBJECT-TYPE
   SYNTAX     SEQUENCE OF MscLpSdhPathStateEntry
   ACCESS     not-accessible
   STATUS     mandatory
   DESCRIPTION
     "This group contains the three OSI State attributes and the six OSI 
      Status attributes. The descriptions generically indicate what each 
      attribute implies about the component. Note that not all the values 
      and state combinations described here are supported by every 
      component which uses this group. For component-specific 
      information and the valid state combinations, refer to NTP 241-
      7001-150, Passport Operations and Maintenance Guide."
::= { mscLpSdhPath 12 }

mscLpSdhPathStateEntry OBJECT-TYPE
   SYNTAX     MscLpSdhPathStateEntry
   ACCESS     not-accessible
   STATUS     mandatory
   DESCRIPTION
     "An entry in the mscLpSdhPathStateTable."
   INDEX {
      mscLpIndex,
      mscLpSdhIndex,
      mscLpSdhPathIndex }
::= { mscLpSdhPathStateTable 1 }

MscLpSdhPathStateEntry ::= SEQUENCE {
   mscLpSdhPathAdminState
      INTEGER,
   mscLpSdhPathOperationalState
      INTEGER,
   mscLpSdhPathUsageState
      INTEGER,
   mscLpSdhPathAvailabilityStatus
      OCTET STRING,
   mscLpSdhPathProceduralStatus
      OCTET STRING,
   mscLpSdhPathControlStatus
      OCTET STRING,
   mscLpSdhPathAlarmStatus
      OCTET STRING,
   mscLpSdhPathStandbyStatus
      INTEGER,
   mscLpSdhPathUnknownStatus
      INTEGER }

mscLpSdhPathAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component.
      
      The OSI Status attributes, if supported by the component, may 
      provide more details, qualifying the state of the component."
   DEFVAL     { unlocked }
::= { mscLpSdhPathStateEntry 1 }

mscLpSdhPathOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle.
      
      The OSI Status attributes, if supported by the component, may 
      provide more details, qualifying the state of the component."
   DEFVAL     { disabled }
::= { mscLpSdhPathStateEntry 2 }

mscLpSdhPathUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time.
      
      The OSI Status attributes, if supported by the component, may 
      provide more details, qualifying the state of the component."
   DEFVAL     { idle }
::= { mscLpSdhPathStateEntry 3 }

mscLpSdhPathAvailabilityStatus OBJECT-TYPE
   SYNTAX     OCTET STRING (SIZE (2))
   ACCESS     read-only
   STATUS     mandatory
   DESCRIPTION
     "If supported by the component, this attribute indicates the OSI 
      Availability status of the component. Note that, even though it is 
      defined as a multi-valued set, at most one value is shown to the user.
      
      When no values are in the set, this indicates that either the attribute 
      is not supported or that none of the status conditions described 
      below are present.
      
      The value inTest indicates that the resource is undergoing a test 
      procedure. If adminState is locked or shuttingDown, the normal 
      users are precluded from using the resource and controlStatus is 
      reservedForTest. Tests that do not exclude additional users can be 
      present in any operational or administrative state but the 
      reservedForTest condition should not be present.
      
      The value failed indicates that the component has an internal fault 
      that prevents it from operating. The operationalState is disabled.
      
      The value dependency indicates that the component cannot operate 
      because some other resource on which it depends is unavailable. 
      The operationalState is disabled.
      
      The value powerOff indicates the resource requires power to be 
      applied and it is not powered on. The operationalState is disabled.
      
      The value offLine indicates the resource requires a routine 
      operation (either manual, automatic, or both) to be performed to 
      place it on-line and make it available for use. The operationalState 
      is disabled.
      
      The value offDuty indicates the resource is inactive in accordance 
      with a predetermined time schedule. In the absence of other 
      disabling conditions, the operationalState is enabled or disabled.
      
      The value degraded indicates the service provided by the 
      component is degraded in some way, such as in speed or operating 
      capacity. However, the resource remains available for service. The 
      operationalState is enabled.
      
      The value notInstalled indicates the resource is not present. The 
      operationalState is disabled.
      
      The value logFull is not used.

      Description of bits:
      inTest(0)
      failed(1)
      powerOff(2)
      offLine(3)
      offDuty(4)
      dependency(5)
      degraded(6)
      notInstalled(7)
      logFull(8)"
::= { mscLpSdhPathStateEntry 4 }

mscLpSdhPathProceduralStatus OBJECT-TYPE
   SYNTAX     OCTET STRING (SIZE (1))
   ACCESS     read-only
   STATUS     mandatory
   DESCRIPTION
     "If supported by the component, this attribute indicates the OSI 
      Procedural status of the component. Note that, even though it is 
      defined as a multi-valued set, at most one value is shown to the user.
      
      When no values are in the set, this indicates that either the attribute 
      is not supported or that none of the status conditions described 
      below are present.
      
      The value initializationRequired indicates (for a resource which 
      doesn't initialize autonomously) that initialization is required before 
      it can perform its normal functions, and this procedure has not been 
      initiated. The operationalState is disabled.
      
      The value notInitialized indicates (for a resource which does 
      initialize autonomously) that initialization is required before it can 
      perform its normal functions, and this procedure has not been 
      initiated. The operationalState may be enabled or disabled.
      
      The value initializing indicates that initialization has been initiated 
      but is not yet complete. The operationalState may be enabled or 
      disabled.
      
      The value reporting indicates the resource has completed some 
      processing operation and is notifying the results. The 
      operationalState is enabled.
      
      The value terminating indicates the component is in a termination 
      phase. If the resource doesn't reinitialize autonomously, 
      operationalState is disabled; otherwise it is enabled or disabled.

      Description of bits:
      initializationRequired(0)
      notInitialized(1)
      initializing(2)
      reporting(3)
      terminating(4)"
::= { mscLpSdhPathStateEntry 5 }

mscLpSdhPathControlStatus OBJECT-TYPE
   SYNTAX     OCTET STRING (SIZE (1))
   ACCESS     read-only
   STATUS     mandatory
   DESCRIPTION
     "If supported by the component, this attribute indicates the OSI 
      Control status of the component. Note that, even though it is defined 
      as a multi-valued set, at most one value is shown to the user.
      
      When no values are in the set, this indicates that either the attribute 
      is not supported or that none of the status conditions described 
      below are present.
      
      The value subjectToTest indicates the resource is available but tests 
      may be conducted simultaneously at unpredictable times, which 
      may cause it to exhibit unusual characteristics.
      
      The value partOfServicesLocked indicates that part of the service is 
      restricted from users of a resource. The adminState is unlocked.
      
      The value reservedForTest indicates that the component is 
      administratively unavailable because it is undergoing a test 
      procedure. The adminState is locked.
      
      The value suspended indicates that the service has been 
      administratively suspended.

      Description of bits:
      subjectToTest(0)
      partOfServicesLocked(1)
      reservedForTest(2)
      suspended(3)"
::= { mscLpSdhPathStateEntry 6 }

mscLpSdhPathAlarmStatus OBJECT-TYPE
   SYNTAX     OCTET STRING (SIZE (1))
   ACCESS     read-only
   STATUS     mandatory
   DESCRIPTION
     "If supported by the component, this attribute indicates the OSI 
      Alarm status of the component. Note that, even though it is defined 
      as a multi-valued set, at most one value is shown to the user.
      
      When no values are in the set, this indicates that either the attribute 
      is not supported or that none of the status conditions described 
      below are present.
      
      The value underRepair indicates the component is currently being 
      repaired. The operationalState is enabled or disabled.
      
      The value critical indicates one or more critical alarms are 
      outstanding against the component. Other, less severe, alarms may 
      also be outstanding. The operationalState is enabled or disabled.
      
      The value major indicates one or more major alarms are 
      outstanding against the component. Other, less severe, alarms may 
      also be outstanding. The operationalState is enabled or disabled.
      
      The value minor indicates one or more minor alarms are 
      outstanding against the component. Other, less severe, alarms may 
      also be outstanding. The operationalState is enabled or disabled.
      
      The value alarmOutstanding generically indicates that an alarm of 
      some severity is outstanding against the component.

      Description of bits:
      underRepair(0)
      critical(1)
      major(2)
      minor(3)
      alarmOutstanding(4)"
::= { mscLpSdhPathStateEntry 7 }

mscLpSdhPathStandbyStatus OBJECT-TYPE
   SYNTAX     INTEGER  {
                 hotStandby(0),
                 coldStandby(1),
                 providingService(2),
                 notSet(15) }
   ACCESS     read-only
   STATUS     mandatory
   DESCRIPTION
     "If supported by the component, this attribute indicates the OSI 
      Standby status of the component.
      
      The value notSet indicates that either the attribute is not supported 
      or that none of the status conditions described below are present. 
      Note that this is a non-standard value, used because the original 
      specification indicated this attribute was set-valued and thus, did not 
      provide a value to indicate that none of the other three are 
      applicable.
      
      The value hotStandby indicates that the resource is not providing 
      service but will be immediately able to take over the role of the 
      resource to be backed up, without initialization activity, and 
      containing the same information as the resource to be backed up.
      
      The value coldStandby indicates the resource is a backup for 
      another resource but will not be immediately able to take over the 
      role of the backed up resource and will require some initialization 
      activity.
      
      The value providingService indicates that this component, as a 
      backup resource, is currently backing up another resource."
   DEFVAL     { notSet }
::= { mscLpSdhPathStateEntry 8 }

mscLpSdhPathUnknownStatus OBJECT-TYPE
   SYNTAX     INTEGER  {
                 false(0),
                 true(1) }
   ACCESS     read-only
   STATUS     mandatory
   DESCRIPTION
     "This attribute indicates the OSI Unknown status of the component.
      
      The value false indicates that all of the other OSI State and Status 
      attribute values can be considered accurate.
      
      The value true indicates that the actual state of the component is not 
      known for sure."
   DEFVAL     { false }
::= { mscLpSdhPathStateEntry 9 }

mscLpSdhPathIfEntryTable OBJECT-TYPE
   SYNTAX     SEQUENCE OF MscLpSdhPathIfEntryEntry
   ACCESS     not-accessible
   STATUS     mandatory
   DESCRIPTION
     "This group contains the provisionable attributes for the ifEntry."
::= { mscLpSdhPath 13 }

mscLpSdhPathIfEntryEntry OBJECT-TYPE
   SYNTAX     MscLpSdhPathIfEntryEntry
   ACCESS     not-accessible
   STATUS     mandatory
   DESCRIPTION
     "An entry in the mscLpSdhPathIfEntryTable."
   INDEX {
      mscLpIndex,
      mscLpSdhIndex,
      mscLpSdhPathIndex }
::= { mscLpSdhPathIfEntryTable 1 }

MscLpSdhPathIfEntryEntry ::= SEQUENCE {
   mscLpSdhPathIfAdminStatus
      INTEGER,
   mscLpSdhPathIfIndex
      InterfaceIndex }

mscLpSdhPathIfAdminStatus OBJECT-TYPE
   SYNTAX     INTEGER  {
                 up(1),
                 down(2),
                 testing(3) }
   ACCESS     read-write
   STATUS     mandatory
   DESCRIPTION
     "The desired state of the interface. The up state indicates the 
      interface is operational. The down state indicates the interface is not 
      operational. The testing state indicates that no operational packets 
      can be passed."
   DEFVAL     { up }
::= { mscLpSdhPathIfEntryEntry 1 }

mscLpSdhPathIfIndex OBJECT-TYPE
   SYNTAX     InterfaceIndex (1..65535)
   ACCESS     read-only
   STATUS     mandatory
   DESCRIPTION
     "This is the index for the IfEntry. Its value is automatically initialized 
      during the provisioning process."
::= { mscLpSdhPathIfEntryEntry 2 }

mscLpSdhPathOperStatusTable OBJECT-TYPE
   SYNTAX     SEQUENCE OF MscLpSdhPathOperStatusEntry
   ACCESS     not-accessible
   STATUS     mandatory
   DESCRIPTION
     "This group includes the Operational Status attribute. This attribute 
      defines the current operational state of this component."
::= { mscLpSdhPath 14 }

mscLpSdhPathOperStatusEntry OBJECT-TYPE
   SYNTAX     MscLpSdhPathOperStatusEntry
   ACCESS     not-accessible
   STATUS     mandatory
   DESCRIPTION
     "An entry in the mscLpSdhPathOperStatusTable."
   INDEX {
      mscLpIndex,
      mscLpSdhIndex,
      mscLpSdhPathIndex }
::= { mscLpSdhPathOperStatusTable 1 }

MscLpSdhPathOperStatusEntry ::= SEQUENCE {
   mscLpSdhPathSnmpOperStatus
      INTEGER }

mscLpSdhPathSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { mscLpSdhPathOperStatusEntry 1 }

mscLpSdhPathOperTable OBJECT-TYPE
   SYNTAX     SEQUENCE OF MscLpSdhPathOperEntry
   ACCESS     not-accessible
   STATUS     mandatory
   DESCRIPTION
     "This group contains the common operational data for Path 
      component."
::= { mscLpSdhPath 15 }

mscLpSdhPathOperEntry OBJECT-TYPE
   SYNTAX     MscLpSdhPathOperEntry
   ACCESS     not-accessible
   STATUS     mandatory
   DESCRIPTION
     "An entry in the mscLpSdhPathOperTable."
   INDEX {
      mscLpIndex,
      mscLpSdhIndex,
      mscLpSdhPathIndex }
::= { mscLpSdhPathOperTable 1 }

MscLpSdhPathOperEntry ::= SEQUENCE {
   mscLpSdhPathLopAlarm
      INTEGER,
   mscLpSdhPathRxAisAlarm
      INTEGER,
   mscLpSdhPathRxRfiAlarm
      INTEGER,
   mscLpSdhPathSignalLabelMismatch
      INTEGER,
   mscLpSdhPathTxAis
      INTEGER,
   mscLpSdhPathTxRdi
      INTEGER }

mscLpSdhPathLopAlarm OBJECT-TYPE
   SYNTAX     INTEGER  {
                 on(0),
                 off(1) }
   ACCESS     read-only
   STATUS     mandatory
   DESCRIPTION
     "This attribute displays whether a Loss Of Pointer (LOP) alarm state 
      has been entered. An LOP alarm state is entered when LOP defects 
      have been observed and accumulated for a period of 2.5 seconds +/- 
      0.5 seconds. An LOP defect occurs when no valid SPE or VC 
      pointer was received in 8 contiguous frames. If the LOP defects are 
      intermittently occurring, the LOP defect accumulator is 
      decremented at a rate of 1/10 of the incrementing rate (alarm 
      integration ratio of 1/10), with all measurements based on a 200 ms 
      polling cycle.
      The Path component goes into an operational state of disabled until 
      the LOP alarm condition is cleared. The condition is cleared when 
      no more invalid pointer has been reported for 10 seconds +/- 0.5 
      seconds.
      The lopAlarm attribute is always set to off when the Path 
      component has been locked and left offline by the operator or when 
      the Path component has been suspended since the parent component 
      has been locked."
::= { mscLpSdhPathOperEntry 1 }

mscLpSdhPathRxAisAlarm OBJECT-TYPE
   SYNTAX     INTEGER  {
                 on(0),
                 off(1) }
   ACCESS     read-only
   STATUS     mandatory
   DESCRIPTION
     "This attribute displays whether an Path Alarm Indication Signal (P-
      AIS) alarm state has been entered. An P-AIS alarm state is entered 
      when P-AIS defects have been observed and accumulated for a 
      period of 2.5 seconds +/- 0.5 seconds. The P-AIS defect is the 
      occurrence of the P-AIS signal in three contiguous valid STS or 
      STM frames (all one's in bytes H1 and H2). If the P-AIS defects are 
      intermittently occurring, the P-AIS defect accumulator is 
      decremented at a rate of 1/10 of the incrementing rate (alarm 
      integration ratio of 1/10), with all measurements based on a 200 ms 
      polling cycle.
      The Path component goes into an operational state of disabled until 
      the P-AIS alarm condition is cleared. The condition is cleared after 
      no P-AIS defect has been detected for 10 seconds +/- 0.5 seconds.
      The rxAisAlarm attribute is always set to off when the Path 
      component has been locked and left offline by the operator or when 
      the Path component has been suspended since the parent component 
      has been locked."
::= { mscLpSdhPathOperEntry 2 }

mscLpSdhPathRxRfiAlarm OBJECT-TYPE
   SYNTAX     INTEGER  {
                 on(0),
                 off(1) }
   ACCESS     read-only
   STATUS     mandatory
   DESCRIPTION
     "This attribute displays whether the Path Remote Failure Indication 
      (P-RFI) alarm state has been entered. An P-RFI alarm state is 
      entered when Path Remote Defect Indicator (P-RDI) defects have 
      been observed and accumulated for a period of 2.5 seconds +/- 0.5 
      seconds. The P-RDI defect is the occurrence of the P-RDI signal in 
      five contiguous valid STS or STM frames (bit 5 of the G1 byte set 
      to 1). If the P-RDI defects are intermittently occurring, the P-RDI 
      defect accumulator is decremented at a rate of 1/10 of the 
      incrementing rate (alarm integration ratio of 1/10)with all 
      measurements based on a 200 ms polling cycle.
      The Path component goes into an operational state of disabled until 
      the P-RFI alarm condition is cleared. The condition is cleared after 
      no P-RDI defect has been detected for 10 seconds +/- 0.5 seconds.
      The rxRfiAlarm attribute is always set to off when the Path 
      component has been locked and left offline by the operator or when 
      the Path component has been suspended since the parent component 
      has been locked."
::= { mscLpSdhPathOperEntry 3 }

mscLpSdhPathSignalLabelMismatch OBJECT-TYPE
   SYNTAX     INTEGER  {
                 on(0),
                 off(1) }
   ACCESS     read-only
   STATUS     mandatory
   DESCRIPTION
     "This attribute displays whether the Path Signal Label Mismatch (P-
      SLM) failure condition has been entered. An P-SLM failure 
      condition is entered when P-SLM defects have been observed and 
      accumulated for period of 2.5 seconds +/- 0.5 seconds. An P-SLM 
      defect occurs when detecting an unexpected path signal label. The 
      expected Path signal labels are 'Mapping for ATM' or 'Equipped - 
      Non Specific Payload'. If the P-SLM defects are intermittently 
      occurring, the P-SLM defect accumulator is decremented at a rate 
      of 1/10 of the incrementing rate (alarm integration ratio of 1/10), 
      with all measurements based on a 200 ms polling cycle.
      The Path component goes into an operational state of disabled until 
      the Path Signal Label Mismatch failure condition is cleared. The 
      condition is cleared when an expected path signal label is received 
      for 10 seconds +/- 0.5 seconds.
      The signalLabelMismatch attribute is always set to off when the 
      Path component has been locked and left offline by the operator or 
      when the Path component has been suspended since the parent 
      component has been locked."
::= { mscLpSdhPathOperEntry 4 }

mscLpSdhPathTxAis OBJECT-TYPE
   SYNTAX     INTEGER  {
                 on(0),
                 off(1) }
   ACCESS     read-only
   STATUS     mandatory
   DESCRIPTION
     "This attribute displays whether the Path Alarm Indication Signal (P-
      AIS) signal is being transmitted on the path. The P-AIS signal is 
      transmitted when the Path component has been locked and left 
      offline by the operator or when the Path component has been 
      suspended since the parent component has been locked."
::= { mscLpSdhPathOperEntry 5 }

mscLpSdhPathTxRdi OBJECT-TYPE
   SYNTAX     INTEGER  {
                 on(0),
                 off(1) }
   ACCESS     read-only
   STATUS     mandatory
   DESCRIPTION
     "This attribute displays whether the Path Remote Defect Indicator 
      (P-RDI) signal is being transmitted over the path signal. The P-RDI 
      signal is transmitted over the outgoing line upon detection of LOP, 
      P-AIS or the occurrence of the LCD state. This attribute is always 
      set to off when the Path component has been locked and left offline 
      by the operator or when the Path component has been suspended 
      since the parent component has been locked."
::= { mscLpSdhPathOperEntry 6 }

mscLpSdhPathStatsTable OBJECT-TYPE
   SYNTAX     SEQUENCE OF MscLpSdhPathStatsEntry
   ACCESS     not-accessible
   STATUS     mandatory
   DESCRIPTION
     "This group contains the statistics data for a Sonet/Sdh Path 
      component. Each attribute type is a non-negative integer which 
      monotonically increases until it reaches a maximum value, at which 
      point it wraps around and starts increasing again from zero."
::= { mscLpSdhPath 16 }

mscLpSdhPathStatsEntry OBJECT-TYPE
   SYNTAX     MscLpSdhPathStatsEntry
   ACCESS     not-accessible
   STATUS     mandatory
   DESCRIPTION
     "An entry in the mscLpSdhPathStatsTable."
   INDEX {
      mscLpIndex,
      mscLpSdhIndex,
      mscLpSdhPathIndex }
::= { mscLpSdhPathStatsTable 1 }

MscLpSdhPathStatsEntry ::= SEQUENCE {
   mscLpSdhPathPathErrorFreeSec
      Counter32,
   mscLpSdhPathPathCodeViolations
      Counter32,
   mscLpSdhPathPathErroredSec
      Counter32,
   mscLpSdhPathPathSevErroredSec
      Counter32,
   mscLpSdhPathPathAisLopSec
      Counter32,
   mscLpSdhPathPathUnavailSec
      Counter32,
   mscLpSdhPathPathFailures
      Counter32,
   mscLpSdhPathFarEndPathErrorFreeSec
      Counter32,
   mscLpSdhPathFarEndPathCodeViolations
      Counter32,
   mscLpSdhPathFarEndPathErroredSec
      Counter32,
   mscLpSdhPathFarEndPathSevErroredSec
      Counter32,
   mscLpSdhPathFarEndPathAisLopSec
      Counter32,
   mscLpSdhPathFarEndPathUnavailSec
      Counter32,
   mscLpSdhPathFarEndPathFailures
      Counter32 }

mscLpSdhPathPathErrorFreeSec OBJECT-TYPE
   SYNTAX     Counter32 
   ACCESS     read-only
   STATUS     mandatory
   DESCRIPTION
     "This attribute indicates the number of seconds that the Sonet/Sdh 
      Path component has been in an near-end error free state."
::= { mscLpSdhPathStatsEntry 1 }

mscLpSdhPathPathCodeViolations OBJECT-TYPE
   SYNTAX     Counter32 
   ACCESS     read-only
   STATUS     mandatory
   DESCRIPTION
     "This attribute indicates the total number of Path Code Violations 
      (PCVs) detected. Each PCV corresponds to a path BIP-8 error. PCV 
      counting is inhibited over second intervals where a Path Severely 
      Errored Second (PSES) is counted. Counting of PCVs is also 
      inhibited over second intervals where a Path Unavailable Second 
      (PUAS) is counted. The count wraps at its maximum value."
::= { mscLpSdhPathStatsEntry 2 }

mscLpSdhPathPathErroredSec OBJECT-TYPE
   SYNTAX     Counter32 
   ACCESS     read-only
   STATUS     mandatory
   DESCRIPTION
     "This attribute indicates the total number of Path Errored Seconds 
      (PESs) that have been counted. A PES is declared for second 
      intervals containing one or more PCVs or one or more LOP or path 
      AIS defects. Counting of PES is inhibited when PUAS is counted 
      over the monitored second."
::= { mscLpSdhPathStatsEntry 3 }

mscLpSdhPathPathSevErroredSec OBJECT-TYPE
   SYNTAX     Counter32 
   ACCESS     read-only
   STATUS     mandatory
   DESCRIPTION
     "This attribute indicates the total number of Path Severely Errored 
      Seconds (PSESs) that have been counted. A PSES is declared for 
      second intervals containing more than x PCVs or one or more LOP 
      or path AIS defects. The value of x is 2400 for a 155 Mbits/sec 
      interface. Counting of PSES is inhibited when PUAS is counted 
      over the monitored second."
::= { mscLpSdhPathStatsEntry 4 }

mscLpSdhPathPathAisLopSec OBJECT-TYPE
   SYNTAX     Counter32 
   ACCESS     read-only
   STATUS     mandatory
   DESCRIPTION
     "This attribute indicates the total number of path AIS and LOP 
      Seconds (PALSs). A PALS is declared for second intervals 
      containing one or more path AIS or LOP defects. Counting of PALS 
      is inhibited when PUAS is counted over the monitored second."
::= { mscLpSdhPathStatsEntry 5 }

mscLpSdhPathPathUnavailSec OBJECT-TYPE
   SYNTAX     Counter32 
   ACCESS     read-only
   STATUS     mandatory
   DESCRIPTION
     "This attribute indicates the total number of one second intervals for 
      which the STS/STM path is unavailable. The path becomes 
      unavailable at the onset of 10 consecutive PSESs. The 10 PSESs are 
      included in the unavailable time. Once unavailable, the path 
      becomes available at the onset of 10 contiguous seconds with no 
      PSES. The 10 seconds with no PSES are excluded from the 
      unavailable time. For second intervals where a Path Unavailable 
      Second (PUAS) is counted, counting of PCV, PES, PSES and PALS 
      is inhibited."
::= { mscLpSdhPathStatsEntry 6 }

mscLpSdhPathPathFailures OBJECT-TYPE
   SYNTAX     Counter32 
   ACCESS     read-only
   STATUS     mandatory
   DESCRIPTION
     "This attribute indicates the total number of times that a path failure 
      (LOP, P-AIS or Path Signal Label Mismatch failure) has been 
      declared."
::= { mscLpSdhPathStatsEntry 7 }

mscLpSdhPathFarEndPathErrorFreeSec OBJECT-TYPE
   SYNTAX     Counter32 
   ACCESS     read-only
   STATUS     mandatory
   DESCRIPTION
     "This attribute indicates the number of seconds that the Sonet/Sdh 
      Path component has been in an far-end error free state."
::= { mscLpSdhPathStatsEntry 8 }

mscLpSdhPathFarEndPathCodeViolations OBJECT-TYPE
   SYNTAX     Counter32 
   ACCESS     read-only
   STATUS     mandatory
   DESCRIPTION
     "This attribute indicates the total number of Far-End Path Code 
      Violations (FEPCVs) detected. Each FEPCV corresponds to a path 
      FEBE. FEPCV counting is inhibited over second intervals where a 
      Far-End Path Severely Errored Second (FEPSES) is counted. 
      Counting of PCVs is also inhibited over second intervals where a 
      Far-End Path Unavailable Second (FEPUAS) is counted. The count 
      wraps at its maximum value."
::= { mscLpSdhPathStatsEntry 9 }

mscLpSdhPathFarEndPathErroredSec OBJECT-TYPE
   SYNTAX     Counter32 
   ACCESS     read-only
   STATUS     mandatory
   DESCRIPTION
     "This attribute indicates the total number of Far-End Path Errored 
      Seconds (FEPESs) that have been counted. A FEPES is declared for 
      second intervals containing one or more FEPCVs or one or more 
      path RDI (P-RDI) defects. Counting of FEPES is inhibited when 
      FEPUAS is counted over the monitored second."
::= { mscLpSdhPathStatsEntry 10 }

mscLpSdhPathFarEndPathSevErroredSec OBJECT-TYPE
   SYNTAX     Counter32 
   ACCESS     read-only
   STATUS     mandatory
   DESCRIPTION
     "This attribute indicates the total number of Far-End Path Severely 
      Errored Seconds (FEPSESs) that have been counted. A FEPSES is 
      declared for second intervals containing more than x FEPCVs or 
      one or more P-RDI defects. The value of x is 2400 for a 155 Mbits/
      sec interface. Counting of FEPSESs is inhibited when FEPUAS is 
      counted over the monitored second."
::= { mscLpSdhPathStatsEntry 11 }

mscLpSdhPathFarEndPathAisLopSec OBJECT-TYPE
   SYNTAX     Counter32 
   ACCESS     read-only
   STATUS     mandatory
   DESCRIPTION
     "This attribute indicates the total number of Far-End Path AIS and 
      LOP Seconds (FEPALSs). A FEPALS is declared for second 
      intervals containing one or more P-RDI defects. Counting of 
      FEPALS is inhibited when FEPUAS is counted over the monitored 
      second."
::= { mscLpSdhPathStatsEntry 12 }

mscLpSdhPathFarEndPathUnavailSec OBJECT-TYPE
   SYNTAX     Counter32 
   ACCESS     read-only
   STATUS     mandatory
   DESCRIPTION
     "This attribute indicates the total number of one second intervals for 
      which the STS/STM far-end path is unavailable. The far-end path 
      becomes unavailable at the onset of 10 consecutive FEPSESs. The 
      10 FEPSESs are included in the unavailable time. Once unavailable, 
      the far-end path becomes available at the onset of 10 contiguous 
      seconds with no FEPSES. The 10 seconds with no FEPSES are 
      excluded from the unavailable time. For second intervals where a 
      Far-End Path Unavailable Second (FEPUAS) is counted, counting 
      of FEPCV, FEPES, FEPSES and FEPALS is inhibited."
::= { mscLpSdhPathStatsEntry 13 }

mscLpSdhPathFarEndPathFailures OBJECT-TYPE
   SYNTAX     Counter32 
   ACCESS     read-only
   STATUS     mandatory
   DESCRIPTION
     "This attribute indicates the total number of times that a STS/STM 
      far-end path failure (P-RFI failure) has been declared."
::= { mscLpSdhPathStatsEntry 14 }


-- 
-- The AtmCell is a component that contains provisioning and 
-- operational attributes. The provisioning attributes are used to set the 
-- Loss of Cell Deliniation (LCD) alarm activation delay and to turn 
-- cell payload scrambling on or off. The operational attributes are 
-- used to report about the quality of the ATM cells received by the 
-- interface and the cell capacity utilization. The AtmCell component 
-- appears under all port components running on ATM cards.

mscLpSdhPathCell OBJECT IDENTIFIER ::= { mscLpSdhPath 2 }



mscLpSdhPathCellRowStatusTable OBJECT-TYPE
   SYNTAX     SEQUENCE OF MscLpSdhPathCellRowStatusEntry
   ACCESS     not-accessible
   STATUS     mandatory
   DESCRIPTION
     "This entry controls the addition and deletion of 
      mscLpSdhPathCell components."
::= { mscLpSdhPathCell 1 }

mscLpSdhPathCellRowStatusEntry OBJECT-TYPE
   SYNTAX     MscLpSdhPathCellRowStatusEntry
   ACCESS     not-accessible
   STATUS     mandatory
   DESCRIPTION
     "A single entry in the table represents a single 
      mscLpSdhPathCell component."
   INDEX {
      mscLpIndex,
      mscLpSdhIndex,
      mscLpSdhPathIndex,
      mscLpSdhPathCellIndex }
::= { mscLpSdhPathCellRowStatusTable 1 }

MscLpSdhPathCellRowStatusEntry ::= SEQUENCE {
   mscLpSdhPathCellRowStatus
      RowStatus,
   mscLpSdhPathCellComponentName
      DisplayString,
   mscLpSdhPathCellStorageType
      StorageType,
   mscLpSdhPathCellIndex
      NonReplicated }

mscLpSdhPathCellRowStatus OBJECT-TYPE
   SYNTAX     RowStatus 
   ACCESS     read-only
   STATUS     mandatory
   DESCRIPTION
     "This variable is used as the basis for SNMP naming of
      mscLpSdhPathCell components.
      These components cannot be added nor deleted."
::= { mscLpSdhPathCellRowStatusEntry 1 }

mscLpSdhPathCellComponentName OBJECT-TYPE
   SYNTAX     DisplayString 
   ACCESS     read-only
   STATUS     mandatory
   DESCRIPTION
     "This variable provides the component's string name for
      use with the ASCII Console Interface"
::= { mscLpSdhPathCellRowStatusEntry 2 }

mscLpSdhPathCellStorageType OBJECT-TYPE
   SYNTAX     StorageType 
   ACCESS     read-only
   STATUS     mandatory
   DESCRIPTION
     "This variable represents the storage type value for the
      mscLpSdhPathCell tables."
::= { mscLpSdhPathCellRowStatusEntry 4 }

mscLpSdhPathCellIndex OBJECT-TYPE
   SYNTAX     NonReplicated 
   ACCESS     not-accessible
   STATUS     mandatory
   DESCRIPTION
     "This variable represents the index for the mscLpSdhPathCell tables."
::= { mscLpSdhPathCellRowStatusEntry 10 }

mscLpSdhPathCellProvTable OBJECT-TYPE
   SYNTAX     SEQUENCE OF MscLpSdhPathCellProvEntry
   ACCESS     not-accessible
   STATUS     mandatory
   DESCRIPTION
     "This group contains the provisioning attributes for the AtmCell 
      component."
::= { mscLpSdhPathCell 10 }

mscLpSdhPathCellProvEntry OBJECT-TYPE
   SYNTAX     MscLpSdhPathCellProvEntry
   ACCESS     not-accessible
   STATUS     mandatory
   DESCRIPTION
     "An entry in the mscLpSdhPathCellProvTable."
   INDEX {
      mscLpIndex,
      mscLpSdhIndex,
      mscLpSdhPathIndex,
      mscLpSdhPathCellIndex }
::= { mscLpSdhPathCellProvTable 1 }

MscLpSdhPathCellProvEntry ::= SEQUENCE {
   mscLpSdhPathCellAlarmActDelay
      Unsigned32,
   mscLpSdhPathCellScrambleCellPayload
      INTEGER,
   mscLpSdhPathCellCorrectSingleBitHeaderErrors
      INTEGER }

mscLpSdhPathCellAlarmActDelay OBJECT-TYPE
   SYNTAX     Unsigned32 (0..2000)
   ACCESS     read-write
   STATUS     mandatory
   DESCRIPTION
     "This attribute defines the time during which a Loss of Cell 
      Delineation (LCD) defect should be observed before declaring an 
      LCD alarm (alarm 70115501). The time is specified in milliseconds."
   DEFVAL     { 500 }
::= { mscLpSdhPathCellProvEntry 1 }

mscLpSdhPathCellScrambleCellPayload OBJECT-TYPE
   SYNTAX     INTEGER  {
                 off(0),
                 on(1) }
   ACCESS     read-write
   STATUS     mandatory
   DESCRIPTION
     "Cell scrambling, as defined by  ITU-T Recommendation I.432., can 
      provide a solution to the problem of transmission equipment which 
      is sensitive to certain bit patterns in the ATM cell payload. This 
      attribute controls whether or not the cell payload is scrambled.
      It defaults to off for DS1 interfaces, and on for all other interfaces.
      Note that this setting must be the same at both ends of the link."
::= { mscLpSdhPathCellProvEntry 2 }

mscLpSdhPathCellCorrectSingleBitHeaderErrors OBJECT-TYPE
   SYNTAX     INTEGER  {
                 off(0),
                 on(1) }
   ACCESS     read-write
   STATUS     mandatory
   DESCRIPTION
     "This attribute specifies whether the port corrects single bit errors 
      detected in the headers of received cells. If single bit errors are 
      corrected, the affected cells are passed up to the ATM layer 
      according to normal operation. If single bit errors are not corrected, 
      these errored cells are discarded by the physical layer. Note that 
      cells containing multiple bit errors in their headers are always 
      discarded.
      
      Single bit HEC error correction must remain off for the following 
      card types: 3pDS1Atm, 8pDS1Atm, 3pE1Atm, 8pE1Atm, 
      2pJ6MAtm, 3pDS3Atm, and 3pE3Atm."
   DEFVAL     { off }
::= { mscLpSdhPathCellProvEntry 3 }

mscLpSdhPathCellOperTable OBJECT-TYPE
   SYNTAX     SEQUENCE OF MscLpSdhPathCellOperEntry
   ACCESS     not-accessible
   STATUS     mandatory
   DESCRIPTION
     "This group contains the common operational attributes for the 
      AtmCell component."
::= { mscLpSdhPathCell 11 }

mscLpSdhPathCellOperEntry OBJECT-TYPE
   SYNTAX     MscLpSdhPathCellOperEntry
   ACCESS     not-accessible
   STATUS     mandatory
   DESCRIPTION
     "An entry in the mscLpSdhPathCellOperTable."
   INDEX {
      mscLpIndex,
      mscLpSdhIndex,
      mscLpSdhPathIndex,
      mscLpSdhPathCellIndex }
::= { mscLpSdhPathCellOperTable 1 }

MscLpSdhPathCellOperEntry ::= SEQUENCE {
   mscLpSdhPathCellLcdAlarm
      INTEGER }

mscLpSdhPathCellLcdAlarm OBJECT-TYPE
   SYNTAX     INTEGER  {
                 on(0),
                 off(1) }
   ACCESS     read-only
   STATUS     mandatory
   DESCRIPTION
     "This attribute displays whether the Loss of Cell Delineation (LCD) 
      failure alarm state has been entered. This state is entered when LCD 
      defects have been observed and accumulated for a period of time 
      specified through the alarmActDelay attribute.
      In ATM cell direct mapping mode, an LCD defect occurs when Out 
      of Cell Delineation (OCD) anomaly persists for x milliseconds, and 
      disappears when the Out of Cell Delineation (OCD) is absent for x 
      msec. An OCD anomaly occurs when 7 consecutive incorrect HECs 
      have been detected. An OCD anomaly terminates when 6 
      consecutive correct HECs have been detected.
      For an AtmCell component located under a DS3 or E3 component 
      with mapping = PLCP, the LCD defect is directly derived from the 
      PLCP LOF defect.
      If LCD defects are intermittently occurring, the LCD defect 
      accumulator is decremented at a rate of 1/10 of the incrementing 
      rate (alarm integration ratio of 1/10), with all measurements based 
      on a 200 ms polling cycle
      The component under which is located the AtmCell component goes 
      into an operational state of disabled until the LCD alarm condition 
      is cleared. The condition is cleared after the LCD defect has not 
      been reported for a period of 10 seconds +/- 0.5 seconds.
      The lcdAlarm attribute is always set to off when the parent of the 
      AtmCell component has been locked and left offline. This can also 
      happen when the Path or Channel component has been suspended 
      since its parent has been locked."
   DEFVAL     { off }
::= { mscLpSdhPathCellOperEntry 1 }

mscLpSdhPathCellStatsTable OBJECT-TYPE
   SYNTAX     SEQUENCE OF MscLpSdhPathCellStatsEntry
   ACCESS     not-accessible
   STATUS     mandatory
   DESCRIPTION
     "This group contains the Statistics attribute for the AtmCell 
      component. Each attribute type is a non-negative integer which 
      monotonically increases until it reaches a maximum value, at which 
      point it wraps around and starts increasing again from zero."
::= { mscLpSdhPathCell 12 }

mscLpSdhPathCellStatsEntry OBJECT-TYPE
   SYNTAX     MscLpSdhPathCellStatsEntry
   ACCESS     not-accessible
   STATUS     mandatory
   DESCRIPTION
     "An entry in the mscLpSdhPathCellStatsTable."
   INDEX {
      mscLpIndex,
      mscLpSdhIndex,
      mscLpSdhPathIndex,
      mscLpSdhPathCellIndex }
::= { mscLpSdhPathCellStatsTable 1 }

MscLpSdhPathCellStatsEntry ::= SEQUENCE {
   mscLpSdhPathCellUncorrectableHecErrors
      Counter32,
   mscLpSdhPathCellSevErroredSec
      Counter32,
   mscLpSdhPathCellReceiveCellUtilization
      Gauge32,
   mscLpSdhPathCellTransmitCellUtilization
      Gauge32,
   mscLpSdhPathCellCorrectableHeaderErrors
      Counter32 }

mscLpSdhPathCellUncorrectableHecErrors OBJECT-TYPE
   SYNTAX     Counter32 
   ACCESS     read-only
   STATUS     mandatory
   DESCRIPTION
     "This attribute indicates the number of uncorrectable ATM cell 
      header errors that have been detected. Counting of 
      uncorrectableHeaderErrors is inhibited when an Out of Cell 
      Delineation (OCD) defect is present. An OCD defect occurs when 
      seven consecutive incorrect HECs have been detected. An OCD 
      defect terminates when six consecutive correct HECs have been 
      detected."
::= { mscLpSdhPathCellStatsEntry 1 }

mscLpSdhPathCellSevErroredSec OBJECT-TYPE
   SYNTAX     Counter32 
   ACCESS     read-only
   STATUS     mandatory
   DESCRIPTION
     "This attribute indicates the total number of ATM Cell Severely 
      Errored Seconds (SESs) that have been counted. 
      
      In direct mapping mode, an ATM Cell SES is declared for second 
      intervals containing one or more Out of Cell Delineation (OCD) 
      defects. An OCD defect occurs when seven consecutive incorrect 
      HECs have been detected. An OCD defect terminates when six 
      consecutive correct HECs have been detected.
      
      In PLCP mapping mode, an ATM Cell SES is declared for second 
      intervals containing one or more PLCP LOF defects.
      
      Counting of uncorrectableHeaderErrors (ucErr) and 
      correctableHeaderErrors (cErr) is inhibited when the OCD defect 
      is present."
::= { mscLpSdhPathCellStatsEntry 2 }

mscLpSdhPathCellReceiveCellUtilization OBJECT-TYPE
   SYNTAX     Gauge32 (0..100)
   ACCESS     read-only
   STATUS     mandatory
   DESCRIPTION
     "This attribute is the ratio of the number of valid, assigned cells 
      received on the link to the nominal link capacity. The utilization is 
      calculated over a period of one minute.
      This attribute is always set to 0 when the parent of the AtmCell 
      component has been locked and left offline. This can also happen 
      when the Path or Channel component has been suspended since its 
      parent has been locked."
   DEFVAL     { 0 }
::= { mscLpSdhPathCellStatsEntry 3 }

mscLpSdhPathCellTransmitCellUtilization OBJECT-TYPE
   SYNTAX     Gauge32 (0..100)
   ACCESS     read-only
   STATUS     mandatory
   DESCRIPTION
     "This attribute is the ratio of the number of valid, assigned cells 
      transmitted on the link to the nominal link capacity. The utilization 
      is calculated over a period of one minute.
      This attribute is always set to 0 when the parent of the AtmCell 
      component has been locked and left offline. This can also happen 
      when the Path or Channel component has been suspended since its 
      parent has been locked."
   DEFVAL     { 0 }
::= { mscLpSdhPathCellStatsEntry 4 }

mscLpSdhPathCellCorrectableHeaderErrors OBJECT-TYPE
   SYNTAX     Counter32 
   ACCESS     read-only
   STATUS     mandatory
   DESCRIPTION
     "This attribute indicates the number of correctable ATM cell header 
      errors that have been detected and corrected. Counting of 
      correctableHeaderErrors is inhibited when an Out of Cell 
      Delineation (OCD) defect is present. An OCD defect occurs when 
      seven consecutive incorrect HECs have been detected. An OCD 
      defect terminates when six consecutive correct HECs have been 
      detected"
::= { mscLpSdhPathCellStatsEntry 5 }


-- 
-- The Test component is configured to control a hardware facility test 
-- on a physical (V35, X21, DS1, E1, DS3, E3 etc.) or a logical port.

mscLpSdhTest OBJECT IDENTIFIER ::= { mscLpSdh 3 }



mscLpSdhTestRowStatusTable OBJECT-TYPE
   SYNTAX     SEQUENCE OF MscLpSdhTestRowStatusEntry
   ACCESS     not-accessible
   STATUS     mandatory
   DESCRIPTION
     "This entry controls the addition and deletion of 
      mscLpSdhTest components."
::= { mscLpSdhTest 1 }

mscLpSdhTestRowStatusEntry OBJECT-TYPE
   SYNTAX     MscLpSdhTestRowStatusEntry
   ACCESS     not-accessible
   STATUS     mandatory
   DESCRIPTION
     "A single entry in the table represents a single 
      mscLpSdhTest component."
   INDEX {
      mscLpIndex,
      mscLpSdhIndex,
      mscLpSdhTestIndex }
::= { mscLpSdhTestRowStatusTable 1 }

MscLpSdhTestRowStatusEntry ::= SEQUENCE {
   mscLpSdhTestRowStatus
      RowStatus,
   mscLpSdhTestComponentName
      DisplayString,
   mscLpSdhTestStorageType
      StorageType,
   mscLpSdhTestIndex
      NonReplicated }

mscLpSdhTestRowStatus OBJECT-TYPE
   SYNTAX     RowStatus 
   ACCESS     read-only
   STATUS     mandatory
   DESCRIPTION
     "This variable is used as the basis for SNMP naming of
      mscLpSdhTest components.
      These components cannot be added nor deleted."
::= { mscLpSdhTestRowStatusEntry 1 }

mscLpSdhTestComponentName OBJECT-TYPE
   SYNTAX     DisplayString 
   ACCESS     read-only
   STATUS     mandatory
   DESCRIPTION
     "This variable provides the component's string name for
      use with the ASCII Console Interface"
::= { mscLpSdhTestRowStatusEntry 2 }

mscLpSdhTestStorageType OBJECT-TYPE
   SYNTAX     StorageType 
   ACCESS     read-only
   STATUS     mandatory
   DESCRIPTION
     "This variable represents the storage type value for the
      mscLpSdhTest tables."
::= { mscLpSdhTestRowStatusEntry 4 }

mscLpSdhTestIndex OBJECT-TYPE
   SYNTAX     NonReplicated 
   ACCESS     not-accessible
   STATUS     mandatory
   DESCRIPTION
     "This variable represents the index for the mscLpSdhTest tables."
::= { mscLpSdhTestRowStatusEntry 10 }

mscLpSdhTestStateTable OBJECT-TYPE
   SYNTAX     SEQUENCE OF MscLpSdhTestStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscLpSdhTest 10 }

mscLpSdhTestStateEntry OBJECT-TYPE
   SYNTAX     MscLpSdhTestStateEntry
   ACCESS     not-accessible
   STATUS     mandatory
   DESCRIPTION
     "An entry in the mscLpSdhTestStateTable."
   INDEX {
      mscLpIndex,
      mscLpSdhIndex,
      mscLpSdhTestIndex }
::= { mscLpSdhTestStateTable 1 }

MscLpSdhTestStateEntry ::= SEQUENCE {
   mscLpSdhTestAdminState
      INTEGER,
   mscLpSdhTestOperationalState
      INTEGER,
   mscLpSdhTestUsageState
      INTEGER }

mscLpSdhTestAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscLpSdhTestStateEntry 1 }

mscLpSdhTestOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscLpSdhTestStateEntry 2 }

mscLpSdhTestUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscLpSdhTestStateEntry 3 }

mscLpSdhTestSetupTable OBJECT-TYPE
   SYNTAX     SEQUENCE OF MscLpSdhTestSetupEntry
   ACCESS     not-accessible
   STATUS     mandatory
   DESCRIPTION
     "This group contains all of the operational data for a Test 
      component."
::= { mscLpSdhTest 11 }

mscLpSdhTestSetupEntry OBJECT-TYPE
   SYNTAX     MscLpSdhTestSetupEntry
   ACCESS     not-accessible
   STATUS     mandatory
   DESCRIPTION
     "An entry in the mscLpSdhTestSetupTable."
   INDEX {
      mscLpIndex,
      mscLpSdhIndex,
      mscLpSdhTestIndex }
::= { mscLpSdhTestSetupTable 1 }

MscLpSdhTestSetupEntry ::= SEQUENCE {
   mscLpSdhTestPurpose
      AsciiString,
   mscLpSdhTestType
      INTEGER,
   mscLpSdhTestFrmSize
      Unsigned32,
   mscLpSdhTestFrmPatternType
      INTEGER,
   mscLpSdhTestCustomizedPattern
      Hex,
   mscLpSdhTestDataStartDelay
      Unsigned32,
   mscLpSdhTestDisplayInterval
      Unsigned32,
   mscLpSdhTestDuration
      Unsigned32 }

mscLpSdhTestPurpose OBJECT-TYPE
   SYNTAX     AsciiString (SIZE (0..40))
   ACCESS     read-write
   STATUS     mandatory
   DESCRIPTION
     "This attribute records the purpose of the test so that the test results 
      can be associated and properly analyzed."
::= { mscLpSdhTestSetupEntry 1 }

mscLpSdhTestType OBJECT-TYPE
   SYNTAX     INTEGER  {
                 card(0),
                 manual(1),
                 localLoop(2),
                 remoteLoop(3),
                 externalLoop(4),
                 payloadLoop(5),
                 remoteLoopThisTrib(6),
                 v54RemoteLoop(7),
                 pn127RemoteLoop(8) }
   ACCESS     read-write
   STATUS     mandatory
   DESCRIPTION
     "This attribute is the type of test to be run. The available test types 
      include the following:
      card test sets up an internal loop on the board and runs a bit error 
      rate test.
      manual test assumes the line is looped back externally and a bit 
      error rate test is performed.
      localLoop test loops back the local modem and performs a bit error 
      rate test.
      remoteLoop test loops back the remote modem (or CSU) and 
      performs a bit error rate test.
      externalLoop test loops back the line to the far end.
      payloadLoop test only loops back the payload data received from 
      the incoming line.
      remoteLoopThisTrib loops this particular tributary back at the far 
      end, using services provided by the parent.
      v54RemoteLoop initiates a V.54 Remote Loopback test.
      pn127RemoteLoop initiates a PN127 Remote Loopback test.
      Note that not all test types are not supported by all function 
      processors."
   DEFVAL     { card }
::= { mscLpSdhTestSetupEntry 2 }

mscLpSdhTestFrmSize OBJECT-TYPE
   SYNTAX     Unsigned32 (4..4096)
   ACCESS     read-write
   STATUS     mandatory
   DESCRIPTION
     "This attribute defines the size of the test data frames in number of 
      bytes."
   DEFVAL     { 1024 }
::= { mscLpSdhTestSetupEntry 3 }

mscLpSdhTestFrmPatternType OBJECT-TYPE
   SYNTAX     INTEGER  {
                 ccitt32kBitPattern(0),
                 ccitt8MBitPattern(1),
                 customizedPattern(2) }
   ACCESS     read-write
   STATUS     mandatory
   DESCRIPTION
     "This attribute defines the type of data pattern generation to use. The 
      following lists the available pattern types:
      ccitt32kBitPattern is a pseudo-random sequence of 32 kbit.
      ccitt8MBitPattern is a pseudo-random sequence of 8Mbit.
      customizedPattern is the pattern defined in the customizedPattern 
      attribute."
   DEFVAL     { ccitt32kBitPattern }
::= { mscLpSdhTestSetupEntry 4 }

mscLpSdhTestCustomizedPattern OBJECT-TYPE
   SYNTAX     Hex (0..4294967295)
   ACCESS     read-write
   STATUS     mandatory
   DESCRIPTION
     "This attribute allows a customized 32 bit pattern to be defined for 
      use in the test data frames. This attribute is used when the attribute 
      frmPatternType is set to CustomizedPattern. Note that a 55 hex 
      pattern is an alternating 1 and 0 pattern."
   DEFVAL     { 1431655765 }
::= { mscLpSdhTestSetupEntry 5 }

mscLpSdhTestDataStartDelay OBJECT-TYPE
   SYNTAX     Unsigned32 (0..1814400)
   ACCESS     read-write
   STATUS     mandatory
   DESCRIPTION
     "This attribute specifies the time delay (in seconds) between when 
      the test expects the loop to have been set up, to when the test data 
      actually starts to be transmitted. This attribute is to accommodate 
      some non-standard equipment that requires extra time for setting up 
      a requested loop.
      This attribute is ignored when the test type is set to externalLoop."
   DEFVAL     { 0 }
::= { mscLpSdhTestSetupEntry 6 }

mscLpSdhTestDisplayInterval OBJECT-TYPE
   SYNTAX     Unsigned32 (0..30240)
   ACCESS     read-write
   STATUS     mandatory
   DESCRIPTION
     "This attribute defines the interval (in minutes) between which 
      interim test results are to be displayed. Results are displayed at the 
      operator console at which the test was started. When the test type is 
      set to externalLoop, this attribute is ignored. There will be no 
      display of results if displayInterval is set to 0. This attribute can be 
      changed anytime."
   DEFVAL     { 5 }
::= { mscLpSdhTestSetupEntry 7 }

mscLpSdhTestDuration OBJECT-TYPE
   SYNTAX     Unsigned32 (1..30240)
   ACCESS     read-write
   STATUS     mandatory
   DESCRIPTION
     "This attribute is the duration (in minutes) that test data will be 
      transmitted. In the case of an externalLoop, this is the time that the 
      loop is in effect. Note that dataStartDelay does not apply to the 
      externalLoop."
   DEFVAL     { 1 }
::= { mscLpSdhTestSetupEntry 8 }

mscLpSdhTestResultsTable OBJECT-TYPE
   SYNTAX     SEQUENCE OF MscLpSdhTestResultsEntry
   ACCESS     not-accessible
   STATUS     mandatory
   DESCRIPTION
     "This group contains all the statistics related attributes of the Test 
      component."
::= { mscLpSdhTest 12 }

mscLpSdhTestResultsEntry OBJECT-TYPE
   SYNTAX     MscLpSdhTestResultsEntry
   ACCESS     not-accessible
   STATUS     mandatory
   DESCRIPTION
     "An entry in the mscLpSdhTestResultsTable."
   INDEX {
      mscLpIndex,
      mscLpSdhIndex,
      mscLpSdhTestIndex }
::= { mscLpSdhTestResultsTable 1 }

MscLpSdhTestResultsEntry ::= SEQUENCE {
   mscLpSdhTestElapsedTime
      Counter32,
   mscLpSdhTestTimeRemaining
      Unsigned32,
   mscLpSdhTestCauseOfTermination
      INTEGER,
   mscLpSdhTestBitsTx
      PassportCounter64,
   mscLpSdhTestBytesTx
      PassportCounter64,
   mscLpSdhTestFrmTx
      PassportCounter64,
   mscLpSdhTestBitsRx
      PassportCounter64,
   mscLpSdhTestBytesRx
      PassportCounter64,
   mscLpSdhTestFrmRx
      PassportCounter64,
   mscLpSdhTestErroredFrmRx
      PassportCounter64,
   mscLpSdhTestBitErrorRate
      AsciiString }

mscLpSdhTestElapsedTime OBJECT-TYPE
   SYNTAX     Counter32 
   ACCESS     read-only
   STATUS     mandatory
   DESCRIPTION
     "This attribute is the number of minutes elapsed since the test started 
      for an externalLoop test. For a data test, this is the time since test 
      data was first transmitted."
::= { mscLpSdhTestResultsEntry 1 }

mscLpSdhTestTimeRemaining OBJECT-TYPE
   SYNTAX     Unsigned32 (0..4294967295)
   ACCESS     read-only
   STATUS     mandatory
   DESCRIPTION
     "This attribute is the number of minutes remaining before the test is 
      to be stopped according to the duration attribute."
   DEFVAL     { 0 }
::= { mscLpSdhTestResultsEntry 2 }

mscLpSdhTestCauseOfTermination OBJECT-TYPE
   SYNTAX     INTEGER  {
                 testTimeExpired(0),
                 stoppedByOperator(1),
                 unknown(2),
                 neverStarted(3),
                 testRunning(4),
                 hardwareReconfigured(5),
                 loopCodeSyncFailed(6),
                 patternSyncFailed(7),
                 patternSyncLost(8) }
   ACCESS     read-only
   STATUS     mandatory
   DESCRIPTION
     "This attribute indicates either the status of the test or the cause of 
      the test's termination:
      
      neverStarted indicates that the test has not yet been started.
      
      testRunning indicates that the test has been started.
      
      stoppedByOperator indicates that the operator issued a stop 
      command on a test that was running.
      
      testTimeExpired indicates that the test ran for the time specified by 
      the test's duration.
      
      loopCodeSyncFailed indicates that the local end failed to 
      synchronize to the loopCode pattern. The local end transmits the 
      loopCode pattern to cause the remote end to apply a loopback, after 
      which the local end should receive the loopCode pattern. The exact 
      pattern used to request loopCode depends on the test type. This 
      failure indicates a high rate of transmission errors, or that the 
      remote end has failed to apply the loopback.
      
      patternSyncFailed indicates that the local end failed to synchronize 
      to the frmPatternType test pattern, that should have been looped 
      back at the remote end. This failure indicates a high rate of 
      transmission errors or the absence of a loopback.
      
      patternSyncLost indicates that the local end gained and then lost 
      synchronization to the returned frmPatternType test pattern. This 
      failure indicates a sudden increase in transmission errors, frame 
      slippage, or the removal of an existing loopback.
      
      unknown is set when a reason to terminate other than those listed 
      here is encountered.
      
      Note: Only MSA cards support recognition of the failures 
      loopCodeSyncFailed, patternSyncFailed and patternSyncLost. 
      Other cards will not terminate the test under the conditions 
      described by these values."
   DEFVAL     { neverStarted }
::= { mscLpSdhTestResultsEntry 3 }

mscLpSdhTestBitsTx OBJECT-TYPE
   SYNTAX     PassportCounter64 
   ACCESS     read-only
   STATUS     mandatory
   DESCRIPTION
     "This attribute is the total number of bits sent during the test period. 
      As long as the line speed of the hardware interface is less than 
      70 Mbit/s, this counter is not expected to reach the maximum value."
::= { mscLpSdhTestResultsEntry 4 }

mscLpSdhTestBytesTx OBJECT-TYPE
   SYNTAX     PassportCounter64 
   ACCESS     read-only
   STATUS     mandatory
   DESCRIPTION
     "This attribute is the total number of bytes sent during the test 
      period. This counter is not expected to reach its maximum value."
::= { mscLpSdhTestResultsEntry 5 }

mscLpSdhTestFrmTx OBJECT-TYPE
   SYNTAX     PassportCounter64 
   ACCESS     read-only
   STATUS     mandatory
   DESCRIPTION
     "This attribute is the total number of frames sent during the test 
      period. This counter is not expected to reach its maximum value."
::= { mscLpSdhTestResultsEntry 6 }

mscLpSdhTestBitsRx OBJECT-TYPE
   SYNTAX     PassportCounter64 
   ACCESS     read-only
   STATUS     mandatory
   DESCRIPTION
     "This attribute is the total number of bits received during the test 
      period. This counter is not expected to reach its maximum value. 
      The counter will wrap around to 0 if it does reach the maximum 
      value."
::= { mscLpSdhTestResultsEntry 7 }

mscLpSdhTestBytesRx OBJECT-TYPE
   SYNTAX     PassportCounter64 
   ACCESS     read-only
   STATUS     mandatory
   DESCRIPTION
     "This attribute is the total number of bytes received during the test 
      period. This counter is not expected to reach its maximum value. 
      The counter will wrap around to 0 if it does reach its maximum 
      value."
::= { mscLpSdhTestResultsEntry 8 }

mscLpSdhTestFrmRx OBJECT-TYPE
   SYNTAX     PassportCounter64 
   ACCESS     read-only
   STATUS     mandatory
   DESCRIPTION
     "This attribute is the total number of frames received during the test 
      period. This counter is not expected to reach its maximum value. 
      The counter will wrap around to 0 if it does reach its maximum 
      value."
::= { mscLpSdhTestResultsEntry 9 }

mscLpSdhTestErroredFrmRx OBJECT-TYPE
   SYNTAX     PassportCounter64 
   ACCESS     read-only
   STATUS     mandatory
   DESCRIPTION
     "This attribute is not displayed for ATM cards because the physical 
      layer drops all errored frames at the controller interface. 
      
      For all other card types, this attribute is the total number of errored 
      frames received during the test period. This counter is not expected 
      to reach its maximum value. The counter will wrap around to 0 if it 
      does reach its maximum value."
::= { mscLpSdhTestResultsEntry 10 }

mscLpSdhTestBitErrorRate OBJECT-TYPE
   SYNTAX     AsciiString (SIZE (5))
   ACCESS     read-only
   STATUS     mandatory
   DESCRIPTION
     "This attribute is not displayed for ATM cards because the physical 
      layer drops all errored frames at the controller interface. 
      
      For all other card types, this attribute is the calculated bit error rate 
      on the link. Test data are generated and sent in frames of a preset 
      size (frameSize). The Test component will try to estimate the 
      number of bit errors in any errored frame which is identifiable. The 
      statistics will be updated accordingly. A lost frame (may be due to 
      an error on the flag sequence) will be discarded for the bit error rate 
      calculation. The result is presented in the form of xEsyy, where x is 
      the mantissa, syy is the exponent, for example 0E+00, 2E-09.
      Note that the bitErrorRate is an estimate only. For more reliable test 
      results, the test should be done over a long period. Multiple tests 
      would also improve the confidence level of the test results."
::= { mscLpSdhTestResultsEntry 11 }


-- Lp/n JT2/n
-- The JT2 component controls and monitors a JT2 port on a 
-- 2pJ6MAtm Function Processor. Up to two ports may be provisioned 
-- on the 2pJ6MAtm interface card.

mscLpJT2 OBJECT IDENTIFIER ::= { mscLp 16 }



mscLpJT2RowStatusTable OBJECT-TYPE
   SYNTAX     SEQUENCE OF MscLpJT2RowStatusEntry
   ACCESS     not-accessible
   STATUS     mandatory
   DESCRIPTION
     "This entry controls the addition and deletion of 
      mscLpJT2 components."
::= { mscLpJT2 1 }

mscLpJT2RowStatusEntry OBJECT-TYPE
   SYNTAX     MscLpJT2RowStatusEntry
   ACCESS     not-accessible
   STATUS     mandatory
   DESCRIPTION
     "A single entry in the table represents a single 
      mscLpJT2 component."
   INDEX {
      mscLpIndex,
      mscLpJT2Index }
::= { mscLpJT2RowStatusTable 1 }

MscLpJT2RowStatusEntry ::= SEQUENCE {
   mscLpJT2RowStatus
      RowStatus,
   mscLpJT2ComponentName
      DisplayString,
   mscLpJT2StorageType
      StorageType,
   mscLpJT2Index
      Integer32 }

mscLpJT2RowStatus OBJECT-TYPE
   SYNTAX     RowStatus 
   ACCESS     read-write
   STATUS     mandatory
   DESCRIPTION
     "This variable is used as the basis for SNMP naming of
      mscLpJT2 components.
      These components can be added and deleted."
::= { mscLpJT2RowStatusEntry 1 }

mscLpJT2ComponentName OBJECT-TYPE
   SYNTAX     DisplayString 
   ACCESS     read-only
   STATUS     mandatory
   DESCRIPTION
     "This variable provides the component's string name for
      use with the ASCII Console Interface"
::= { mscLpJT2RowStatusEntry 2 }

mscLpJT2StorageType OBJECT-TYPE
   SYNTAX     StorageType 
   ACCESS     read-only
   STATUS     mandatory
   DESCRIPTION
     "This variable represents the storage type value for the
      mscLpJT2 tables."
::= { mscLpJT2RowStatusEntry 4 }

mscLpJT2Index OBJECT-TYPE
   SYNTAX     Integer32 (0..1)
   ACCESS     not-accessible
   STATUS     mandatory
   DESCRIPTION
     "This variable represents the index for the mscLpJT2 tables."
::= { mscLpJT2RowStatusEntry 10 }

mscLpJT2CidDataTable OBJECT-TYPE
   SYNTAX     SEQUENCE OF MscLpJT2CidDataEntry
   ACCESS     not-accessible
   STATUS     mandatory
   DESCRIPTION
     "This group contains the attribute for a component's Customer 
      Identifier (CID). Refer to the attribute description for a detailed 
      explanation of CIDs."
::= { mscLpJT2 10 }

mscLpJT2CidDataEntry OBJECT-TYPE
   SYNTAX     MscLpJT2CidDataEntry
   ACCESS     not-accessible
   STATUS     mandatory
   DESCRIPTION
     "An entry in the mscLpJT2CidDataTable."
   INDEX {
      mscLpIndex,
      mscLpJT2Index }
::= { mscLpJT2CidDataTable 1 }

MscLpJT2CidDataEntry ::= SEQUENCE {
   mscLpJT2CustomerIdentifier
      Unsigned32 }

mscLpJT2CustomerIdentifier OBJECT-TYPE
   SYNTAX     Unsigned32 (0 | 1..8191)
   ACCESS     read-write
   STATUS     mandatory
   DESCRIPTION
     "This attribute holds the Customer Identifier (CID).
      
      Every component has a CID. If a component has a cid attribute, the 
      component's CID is the provisioned value of that attribute; 
      otherwise the component inherits the CID of its parent. The top-
      level component has a CID of 0.
      
      Every operator session also has a CID, which is the CID 
      provisioned for the operator's user ID. An operator will see only the 
      stream data for components having a matching CID. Also, the 
      operator will be allowed to issue commands for only those 
      components which have a matching CID.
      
      An operator CID of 0 is used to identify the Network Manager 
      (referred to as 'NetMan' in DPN). This CID matches the CID of 
      any component. Values 1 to 8191 inclusive (equivalent to 'basic 
      CIDs' in DPN) may be assigned to specific customers."
   DEFVAL     { 0 }
::= { mscLpJT2CidDataEntry 1 }

mscLpJT2ProvTable OBJECT-TYPE
   SYNTAX     SEQUENCE OF MscLpJT2ProvEntry
   ACCESS     not-accessible
   STATUS     mandatory
   DESCRIPTION
     "This group contains all of the JT2 specific provisioning data for a 
      JT2 component."
::= { mscLpJT2 11 }

mscLpJT2ProvEntry OBJECT-TYPE
   SYNTAX     MscLpJT2ProvEntry
   ACCESS     not-accessible
   STATUS     mandatory
   DESCRIPTION
     "An entry in the mscLpJT2ProvTable."
   INDEX {
      mscLpIndex,
      mscLpJT2Index }
::= { mscLpJT2ProvTable 1 }

MscLpJT2ProvEntry ::= SEQUENCE {
   mscLpJT2ClockingSource
      INTEGER,
   mscLpJT2LineLength
      Unsigned32,
   mscLpJT2ApplicationFramerName
      Link }

mscLpJT2ClockingSource OBJECT-TYPE
   SYNTAX     INTEGER  {
                 local(0),
                 line(1),
                 module(2),
                 otherPort(4) }
   ACCESS     read-write
   STATUS     mandatory
   DESCRIPTION
     "This attribute defines the source of the transmit clock for the JT2 
      line.
      When the clocking source is selected from local, the oscillator on 
      the port generates the clocking for the line.
      When the clocking source is selected from line, the port 
      synchronizes to the clock recovered from the incoming line signal.
      When the clocking source is selected from module, the port's clock 
      synchronizes to the clock provided by the oscillator on the active 
      CP.
      Note:- that when one port is set to local, the other port must also be 
      set to local, and when one port is set to module, the other port must 
      also be set to module. If one of the ports is set to line, the other port 
      must be set to otherPort.
      Also, if a CP reference clock is available when the JT2 component 
      is added, the clocking source defaults to module, whereas if a CP 
      reference clock is not available when the component is added, the 
      clocking source defaults to local."
::= { mscLpJT2ProvEntry 1 }

mscLpJT2LineLength OBJECT-TYPE
   SYNTAX     Unsigned32 (0..480)
   ACCESS     read-write
   STATUS     mandatory
   DESCRIPTION
     "This attribute defines the line length for equalization calculations 
      for the JT2 line. The range is between 0 and 480 feet (1 metre = 
      3.28 feet)."
   DEFVAL     { 0 }
::= { mscLpJT2ProvEntry 2 }

mscLpJT2ApplicationFramerName OBJECT-TYPE
   SYNTAX     Link 
   ACCESS     read-write
   STATUS     mandatory
   DESCRIPTION
     "This attribute defines the link to the software stack. It defines which 
      application is running on top of the JT2 component."
::= { mscLpJT2ProvEntry 3 }

mscLpJT2IfEntryTable OBJECT-TYPE
   SYNTAX     SEQUENCE OF MscLpJT2IfEntryEntry
   ACCESS     not-accessible
   STATUS     mandatory
   DESCRIPTION
     "This group contains the provisionable attributes for the ifEntry."
::= { mscLpJT2 12 }

mscLpJT2IfEntryEntry OBJECT-TYPE
   SYNTAX     MscLpJT2IfEntryEntry
   ACCESS     not-accessible
   STATUS     mandatory
   DESCRIPTION
     "An entry in the mscLpJT2IfEntryTable."
   INDEX {
      mscLpIndex,
      mscLpJT2Index }
::= { mscLpJT2IfEntryTable 1 }

MscLpJT2IfEntryEntry ::= SEQUENCE {
   mscLpJT2IfAdminStatus
      INTEGER,
   mscLpJT2IfIndex
      InterfaceIndex }

mscLpJT2IfAdminStatus OBJECT-TYPE
   SYNTAX     INTEGER  {
                 up(1),
                 down(2),
                 testing(3) }
   ACCESS     read-write
   STATUS     mandatory
   DESCRIPTION
     "The desired state of the interface. The up state indicates the 
      interface is operational. The down state indicates the interface is not 
      operational. The testing state indicates that no operational packets 
      can be passed."
   DEFVAL     { up }
::= { mscLpJT2IfEntryEntry 1 }

mscLpJT2IfIndex OBJECT-TYPE
   SYNTAX     InterfaceIndex (1..65535)
   ACCESS     read-only
   STATUS     mandatory
   DESCRIPTION
     "This is the index for the IfEntry. Its value is automatically initialized 
      during the provisioning process."
::= { mscLpJT2IfEntryEntry 2 }

mscLpJT2OperStatusTable OBJECT-TYPE
   SYNTAX     SEQUENCE OF MscLpJT2OperStatusEntry
   ACCESS     not-accessible
   STATUS     mandatory
   DESCRIPTION
     "This group includes the Operational Status attribute. This attribute 
      defines the current operational state of this component."
::= { mscLpJT2 13 }

mscLpJT2OperStatusEntry OBJECT-TYPE
   SYNTAX     MscLpJT2OperStatusEntry
   ACCESS     not-accessible
   STATUS     mandatory
   DESCRIPTION
     "An entry in the mscLpJT2OperStatusTable."
   INDEX {
      mscLpIndex,
      mscLpJT2Index }
::= { mscLpJT2OperStatusTable 1 }

MscLpJT2OperStatusEntry ::= SEQUENCE {
   mscLpJT2SnmpOperStatus
      INTEGER }

mscLpJT2SnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { mscLpJT2OperStatusEntry 1 }

mscLpJT2StateTable OBJECT-TYPE
   SYNTAX     SEQUENCE OF MscLpJT2StateEntry
   ACCESS     not-accessible
   STATUS     mandatory
   DESCRIPTION
     "This group contains the three OSI State attributes and the six OSI 
      Status attributes. The descriptions generically indicate what each 
      attribute implies about the component. Note that not all the values 
      and state combinations described here are supported by every 
      component which uses this group. For component-specific 
      information and the valid state combinations, refer to NTP 241-
      7001-150, Passport Operations and Maintenance Guide."
::= { mscLpJT2 14 }

mscLpJT2StateEntry OBJECT-TYPE
   SYNTAX     MscLpJT2StateEntry
   ACCESS     not-accessible
   STATUS     mandatory
   DESCRIPTION
     "An entry in the mscLpJT2StateTable."
   INDEX {
      mscLpIndex,
      mscLpJT2Index }
::= { mscLpJT2StateTable 1 }

MscLpJT2StateEntry ::= SEQUENCE {
   mscLpJT2AdminState
      INTEGER,
   mscLpJT2OperationalState
      INTEGER,
   mscLpJT2UsageState
      INTEGER,
   mscLpJT2AvailabilityStatus
      OCTET STRING,
   mscLpJT2ProceduralStatus
      OCTET STRING,
   mscLpJT2ControlStatus
      OCTET STRING,
   mscLpJT2AlarmStatus
      OCTET STRING,
   mscLpJT2StandbyStatus
      INTEGER,
   mscLpJT2UnknownStatus
      INTEGER }

mscLpJT2AdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component.
      
      The OSI Status attributes, if supported by the component, may 
      provide more details, qualifying the state of the component."
   DEFVAL     { unlocked }
::= { mscLpJT2StateEntry 1 }

mscLpJT2OperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle.
      
      The OSI Status attributes, if supported by the component, may 
      provide more details, qualifying the state of the component."
   DEFVAL     { disabled }
::= { mscLpJT2StateEntry 2 }

mscLpJT2UsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time.
      
      The OSI Status attributes, if supported by the component, may 
      provide more details, qualifying the state of the component."
   DEFVAL     { idle }
::= { mscLpJT2StateEntry 3 }

mscLpJT2AvailabilityStatus OBJECT-TYPE
   SYNTAX     OCTET STRING (SIZE (2))
   ACCESS     read-only
   STATUS     mandatory
   DESCRIPTION
     "If supported by the component, this attribute indicates the OSI 
      Availability status of the component. Note that, even though it is 
      defined as a multi-valued set, at most one value is shown to the user.
      
      When no values are in the set, this indicates that either the attribute 
      is not supported or that none of the status conditions described 
      below are present.
      
      The value inTest indicates that the resource is undergoing a test 
      procedure. If adminState is locked or shuttingDown, the normal 
      users are precluded from using the resource and controlStatus is 
      reservedForTest. Tests that do not exclude additional users can be 
      present in any operational or administrative state but the 
      reservedForTest condition should not be present.
      
      The value failed indicates that the component has an internal fault 
      that prevents it from operating. The operationalState is disabled.
      
      The value dependency indicates that the component cannot operate 
      because some other resource on which it depends is unavailable. 
      The operationalState is disabled.
      
      The value powerOff indicates the resource requires power to be 
      applied and it is not powered on. The operationalState is disabled.
      
      The value offLine indicates the resource requires a routine 
      operation (either manual, automatic, or both) to be performed to 
      place it on-line and make it available for use. The operationalState 
      is disabled.
      
      The value offDuty indicates the resource is inactive in accordance 
      with a predetermined time schedule. In the absence of other 
      disabling conditions, the operationalState is enabled or disabled.
      
      The value degraded indicates the service provided by the 
      component is degraded in some way, such as in speed or operating 
      capacity. However, the resource remains available for service. The 
      operationalState is enabled.
      
      The value notInstalled indicates the resource is not present. The 
      operationalState is disabled.
      
      The value logFull is not used.

      Description of bits:
      inTest(0)
      failed(1)
      powerOff(2)
      offLine(3)
      offDuty(4)
      dependency(5)
      degraded(6)
      notInstalled(7)
      logFull(8)"
::= { mscLpJT2StateEntry 4 }

mscLpJT2ProceduralStatus OBJECT-TYPE
   SYNTAX     OCTET STRING (SIZE (1))
   ACCESS     read-only
   STATUS     mandatory
   DESCRIPTION
     "If supported by the component, this attribute indicates the OSI 
      Procedural status of the component. Note that, even though it is 
      defined as a multi-valued set, at most one value is shown to the user.
      
      When no values are in the set, this indicates that either the attribute 
      is not supported or that none of the status conditions described 
      below are present.
      
      The value initializationRequired indicates (for a resource which 
      doesn't initialize autonomously) that initialization is required before 
      it can perform its normal functions, and this procedure has not been 
      initiated. The operationalState is disabled.
      
      The value notInitialized indicates (for a resource which does 
      initialize autonomously) that initialization is required before it can 
      perform its normal functions, and this procedure has not been 
      initiated. The operationalState may be enabled or disabled.
      
      The value initializing indicates that initialization has been initiated 
      but is not yet complete. The operationalState may be enabled or 
      disabled.
      
      The value reporting indicates the resource has completed some 
      processing operation and is notifying the results. The 
      operationalState is enabled.
      
      The value terminating indicates the component is in a termination 
      phase. If the resource doesn't reinitialize autonomously, 
      operationalState is disabled; otherwise it is enabled or disabled.

      Description of bits:
      initializationRequired(0)
      notInitialized(1)
      initializing(2)
      reporting(3)
      terminating(4)"
::= { mscLpJT2StateEntry 5 }

mscLpJT2ControlStatus OBJECT-TYPE
   SYNTAX     OCTET STRING (SIZE (1))
   ACCESS     read-only
   STATUS     mandatory
   DESCRIPTION
     "If supported by the component, this attribute indicates the OSI 
      Control status of the component. Note that, even though it is defined 
      as a multi-valued set, at most one value is shown to the user.
      
      When no values are in the set, this indicates that either the attribute 
      is not supported or that none of the status conditions described 
      below are present.
      
      The value subjectToTest indicates the resource is available but tests 
      may be conducted simultaneously at unpredictable times, which 
      may cause it to exhibit unusual characteristics.
      
      The value partOfServicesLocked indicates that part of the service is 
      restricted from users of a resource. The adminState is unlocked.
      
      The value reservedForTest indicates that the component is 
      administratively unavailable because it is undergoing a test 
      procedure. The adminState is locked.
      
      The value suspended indicates that the service has been 
      administratively suspended.

      Description of bits:
      subjectToTest(0)
      partOfServicesLocked(1)
      reservedForTest(2)
      suspended(3)"
::= { mscLpJT2StateEntry 6 }

mscLpJT2AlarmStatus OBJECT-TYPE
   SYNTAX     OCTET STRING (SIZE (1))
   ACCESS     read-only
   STATUS     mandatory
   DESCRIPTION
     "If supported by the component, this attribute indicates the OSI 
      Alarm status of the component. Note that, even though it is defined 
      as a multi-valued set, at most one value is shown to the user.
      
      When no values are in the set, this indicates that either the attribute 
      is not supported or that none of the status conditions described 
      below are present.
      
      The value underRepair indicates the component is currently being 
      repaired. The operationalState is enabled or disabled.
      
      The value critical indicates one or more critical alarms are 
      outstanding against the component. Other, less severe, alarms may 
      also be outstanding. The operationalState is enabled or disabled.
      
      The value major indicates one or more major alarms are 
      outstanding against the component. Other, less severe, alarms may 
      also be outstanding. The operationalState is enabled or disabled.
      
      The value minor indicates one or more minor alarms are 
      outstanding against the component. Other, less severe, alarms may 
      also be outstanding. The operationalState is enabled or disabled.
      
      The value alarmOutstanding generically indicates that an alarm of 
      some severity is outstanding against the component.

      Description of bits:
      underRepair(0)
      critical(1)
      major(2)
      minor(3)
      alarmOutstanding(4)"
::= { mscLpJT2StateEntry 7 }

mscLpJT2StandbyStatus OBJECT-TYPE
   SYNTAX     INTEGER  {
                 hotStandby(0),
                 coldStandby(1),
                 providingService(2),
                 notSet(15) }
   ACCESS     read-only
   STATUS     mandatory
   DESCRIPTION
     "If supported by the component, this attribute indicates the OSI 
      Standby status of the component.
      
      The value notSet indicates that either the attribute is not supported 
      or that none of the status conditions described below are present. 
      Note that this is a non-standard value, used because the original 
      specification indicated this attribute was set-valued and thus, did not 
      provide a value to indicate that none of the other three are 
      applicable.
      
      The value hotStandby indicates that the resource is not providing 
      service but will be immediately able to take over the role of the 
      resource to be backed up, without initialization activity, and 
      containing the same information as the resource to be backed up.
      
      The value coldStandby indicates the resource is a backup for 
      another resource but will not be immediately able to take over the 
      role of the backed up resource and will require some initialization 
      activity.
      
      The value providingService indicates that this component, as a 
      backup resource, is currently backing up another resource."
   DEFVAL     { notSet }
::= { mscLpJT2StateEntry 8 }

mscLpJT2UnknownStatus OBJECT-TYPE
   SYNTAX     INTEGER  {
                 false(0),
                 true(1) }
   ACCESS     read-only
   STATUS     mandatory
   DESCRIPTION
     "This attribute indicates the OSI Unknown status of the component.
      
      The value false indicates that all of the other OSI State and Status 
      attribute values can be considered accurate.
      
      The value true indicates that the actual state of the component is not 
      known for sure."
   DEFVAL     { false }
::= { mscLpJT2StateEntry 9 }

mscLpJT2OperTable OBJECT-TYPE
   SYNTAX     SEQUENCE OF MscLpJT2OperEntry
   ACCESS     not-accessible
   STATUS     mandatory
   DESCRIPTION
     "This group contains the JT2 specific operational data for a JT2 
      component in a digital hierarchy interface."
::= { mscLpJT2 15 }

mscLpJT2OperEntry OBJECT-TYPE
   SYNTAX     MscLpJT2OperEntry
   ACCESS     not-accessible
   STATUS     mandatory
   DESCRIPTION
     "An entry in the mscLpJT2OperTable."
   INDEX {
      mscLpIndex,
      mscLpJT2Index }
::= { mscLpJT2OperTable 1 }

MscLpJT2OperEntry ::= SEQUENCE {
   mscLpJT2LosAlarm
      INTEGER,
   mscLpJT2LofAlarm
      INTEGER,
   mscLpJT2RxAisPhysicalAlarm
      INTEGER,
   mscLpJT2RxAisPayloadAlarm
      INTEGER,
   mscLpJT2RxRaiAlarm
      INTEGER,
   mscLpJT2TxAisPhysicalAlarm
      INTEGER,
   mscLpJT2TxRaiAlarm
      INTEGER }

mscLpJT2LosAlarm OBJECT-TYPE
   SYNTAX     INTEGER  {
                 on(0),
                 off(1) }
   ACCESS     read-only
   STATUS     mandatory
   DESCRIPTION
     "This attribute displays whether a LOS (Loss of Signal) alarm state 
      is entered. An LOS alarm state is entered when LOS defects have 
      been observed and accumulated for a period of 2.5 seconds +/- 0.5 
      seconds. An LOS defect is declared at the JT2 line interface when 
      the input data is zero for 20 - 32 clock cycles. If the LOS defects are 
      intermittently occurring, the LOS defect accumulator is 
      decremented at a rate of 1/10 of the incrementing rate (alarm 
      integration ratio of 1/10), with all measurements based on a 200 ms 
      polling cycle.
      An LOS failure alarm is cleared when the LOS defect is absent for a 
      period of 10 seconds +/- 0.5 seconds. The JT2 port goes into an 
      operationalState of disabled for the duration of the LOS alarm 
      condition. While the port is in the LOS alarm state, the port also 
      transmits the far-end RAI defect indicator on the out-going JT2 line."
   DEFVAL     { off }
::= { mscLpJT2OperEntry 1 }

mscLpJT2LofAlarm OBJECT-TYPE
   SYNTAX     INTEGER  {
                 on(0),
                 off(1) }
   ACCESS     read-only
   STATUS     mandatory
   DESCRIPTION
     "This attribute indicates whether a LOF (Loss of Frame) alarm state 
      is entered. A LOF alarm state is entered when LOF defects are 
      observed and accumulated for 2.5 seconds +/- 0.5 seconds or more. 
      A LOF defect occurs when seven or more consecutive incorrect 
      frame alignment patterns (4 multiframes) are received. If the LOF 
      defects are intermittently occurring, the LOF defect accumulator is 
      decremented at a rate of 1/10 of the incrementing rate (alarm 
      integration ratio of 1/10), with all measurements based on a 200 ms 
      polling cycle.
      The LOF alarm is cleared when framing has been achieved for 10 
      seconds +/- 0.5 seconds. The port goes into an operationalState of 
      disabled for the duration of the LOF alarm condition. While the 
      port is in the LOF alarm state, the node also transmits the far-end 
      RAI defect indicator on the out-going JT2 line."
   DEFVAL     { off }
::= { mscLpJT2OperEntry 2 }

mscLpJT2RxAisPhysicalAlarm OBJECT-TYPE
   SYNTAX     INTEGER  {
                 on(0),
                 off(1) }
   ACCESS     read-only
   STATUS     mandatory
   DESCRIPTION
     "This attribute indicates whether a Physical AIS alarm state is 
      entered. A Physical AIS alarm state is entered when a Physical AIS 
      defect is observed and accumulated for a period of 2.5 seconds +/- 
      0.5 seconds. A Physical AIS defect is declared when the incoming 
      signal has two or less zeros in a sequence of 3,156 bits (0.5 ms). If 
      the physical AIS defects are intermittently occurring, the physical 
      AIS defect accumulator is decremented at a rate of 1/10 of the 
      incrementing rate (alarm integration ratio of 1/10), with all 
      measurements based on a 200 ms polling cycle.
      A Physical AIS alarm is cleared when the Physical AIS defect is 
      absent for a period of 10 seconds +/- 0.5 seconds. The port goes 
      into an operationalState of disabled until the AIS alarm condition is 
      cleared. While the port is in the Physical AIS alarm state, the node 
      also transmits the far-end RAI defect indicator on the out-going JT2 
      line."
   DEFVAL     { off }
::= { mscLpJT2OperEntry 3 }

mscLpJT2RxAisPayloadAlarm OBJECT-TYPE
   SYNTAX     INTEGER  {
                 on(0),
                 off(1) }
   ACCESS     read-only
   STATUS     mandatory
   DESCRIPTION
     "This attribute indicates whether a Payload AIS alarm state is 
      entered. A Payload AIS alarm state is entered when a Payload AIS 
      defect persists for a period of 2.5 seconds +/- 0.5 seconds. A 
      Payload AIS defect is declared when the incoming signal of the 
      6312 kbit/s frame payload (TS1 - TS96) has two or less zeros in a 
      sequence of 3,072 bits (0.5 ms). If the payload AIS defects are 
      intermittently occurring, the payload AIS defect accumulator is 
      decremented at a rate of 1/10 of the incrementing rate (alarm 
      integration ratio of 1/10), with all measurements based on a 200 ms 
      polling cycle.
      A Payload AIS failure alarm is cleared when the Payload AIS 
      defect is absent for a period of 10 seconds +/- 0.5 seconds. The port 
      goes into an operationalState of disabled until the AIS alarm 
      condition is cleared. While the port is in the Payload AIS alarm 
      state, the node also transmits the far-end RAI defect indicator on the 
      out-going JT2 line."
   DEFVAL     { off }
::= { mscLpJT2OperEntry 4 }

mscLpJT2RxRaiAlarm OBJECT-TYPE
   SYNTAX     INTEGER  {
                 on(0),
                 off(1) }
   ACCESS     read-only
   STATUS     mandatory
   DESCRIPTION
     "This attribute indicates whether a Received RAI alarm state is 
      entered. A received RAI alarm state is entered when the RAI signal 
      is detected on the incoming JT2 Line (when 16 or more consecutive 
      RAI patterns of 1111111100000000 are received on the 4 kbit/s 
      data channel (m-bits) within the framing bits of the JT2 frame). The 
      JT2 port goes into an operationalState of Disabled until the RAI 
      alarm condition is cleared. The RAI alarm is cleared when four or 
      more consecutive non-RAI patterns (anything other than 
      1111111100000000) are received."
   DEFVAL     { off }
::= { mscLpJT2OperEntry 5 }

mscLpJT2TxAisPhysicalAlarm OBJECT-TYPE
   SYNTAX     INTEGER  {
                 on(0),
                 off(1) }
   ACCESS     read-only
   STATUS     mandatory
   DESCRIPTION
     "This attribute indicates whether an AIS (Alarm Indication Signal) 
      alarm is being transmitted on the outgoing JT2 line. Currently the 
      JT2 port only transmits a Physical AIS (no Payload AIS) on the 
      outgoing JT2 line. 
      Since there is no Idle signal defined for JT2, the AIS signal is 
      transmitted when the JT2 port is in the operationalState of locked. 
      The AIS signal may also be transmitted for diagnostic testing."
   DEFVAL     { off }
::= { mscLpJT2OperEntry 6 }

mscLpJT2TxRaiAlarm OBJECT-TYPE
   SYNTAX     INTEGER  {
                 on(0),
                 off(1) }
   ACCESS     read-only
   STATUS     mandatory
   DESCRIPTION
     "This attribute indicates whether an RAI defect indication pattern is 
      being sent on the out-going JT2 line. The RAI alarm pattern is 
      transmitted in the 4 kbit/s data channel (m-bits) when the port 
      detects a LOS, AIS or LOF alarm condition."
   DEFVAL     { off }
::= { mscLpJT2OperEntry 7 }

mscLpJT2StatsTable OBJECT-TYPE
   SYNTAX     SEQUENCE OF MscLpJT2StatsEntry
   ACCESS     not-accessible
   STATUS     mandatory
   DESCRIPTION
     "This group contains the statistical data for a JT2 component in a 
      digital hierarchy interface."
::= { mscLpJT2 16 }

mscLpJT2StatsEntry OBJECT-TYPE
   SYNTAX     MscLpJT2StatsEntry
   ACCESS     not-accessible
   STATUS     mandatory
   DESCRIPTION
     "An entry in the mscLpJT2StatsTable."
   INDEX {
      mscLpIndex,
      mscLpJT2Index }
::= { mscLpJT2StatsTable 1 }

MscLpJT2StatsEntry ::= SEQUENCE {
   mscLpJT2RunningTime
      Counter32,
   mscLpJT2ErrorFreeSec
      Counter32,
   mscLpJT2ErroredSec
      Counter32,
   mscLpJT2SevErroredSec
      Counter32,
   mscLpJT2SevErroredFrmSec
      Counter32,
   mscLpJT2UnavailSec
      Counter32,
   mscLpJT2BpvErrors
      Counter32,
   mscLpJT2CrcErrors
      Counter32,
   mscLpJT2FrameErrors
      Counter32,
   mscLpJT2LosStateChanges
      Counter32 }

mscLpJT2RunningTime OBJECT-TYPE
   SYNTAX     Counter32 
   ACCESS     read-only
   STATUS     mandatory
   DESCRIPTION
     "This attribute indicates the number of seconds since the JT2 
      component was activated and placed in an unlocked state or used for 
      operational testing. All the other error counts that follow as well as 
      each JT2 subcomponent's error counts can be updated when this 
      count is active."
::= { mscLpJT2StatsEntry 1 }

mscLpJT2ErrorFreeSec OBJECT-TYPE
   SYNTAX     Counter32 
   ACCESS     read-only
   STATUS     mandatory
   DESCRIPTION
     "This attribute indicates the number of seconds that the JT2 port has 
      been in an error free state."
::= { mscLpJT2StatsEntry 2 }

mscLpJT2ErroredSec OBJECT-TYPE
   SYNTAX     Counter32 
   ACCESS     read-only
   STATUS     mandatory
   DESCRIPTION
     "This attribute indicates the total number of errored seconds for the 
      JT2 port. An errored second is declared when a second with one or 
      more Code Violation Error events, or one or more LOF or LOS 
      defects occur. A code violation error may be a cyclic redundancy 
      check (CRC) error or a bipolar violation (BPV) error."
::= { mscLpJT2StatsEntry 3 }

mscLpJT2SevErroredSec OBJECT-TYPE
   SYNTAX     Counter32 
   ACCESS     read-only
   STATUS     mandatory
   DESCRIPTION
     "This attribute indicates the total number of severely errored seconds 
      for the JT2 port. A severely errored second occurs when a second 
      with 255 or more Code Violation Error events or one or more LOF 
      or LOS defects occur."
::= { mscLpJT2StatsEntry 4 }

mscLpJT2SevErroredFrmSec OBJECT-TYPE
   SYNTAX     Counter32 
   ACCESS     read-only
   STATUS     mandatory
   DESCRIPTION
     "This attribute indicates the total number of severely errored framing 
      seconds for the JT2 port. A severely errored framing second occurs 
      when a second with one or more Framing Errors occur."
::= { mscLpJT2StatsEntry 5 }

mscLpJT2UnavailSec OBJECT-TYPE
   SYNTAX     Counter32 
   ACCESS     read-only
   STATUS     mandatory
   DESCRIPTION
     "This attribute indicates the total number of seconds that the 
      interface has been in an unavailable state. An unavailable state 
      occurs at the onset of 10 consecutive Severely Errored Seconds. 
      When the unavailable state is entered, the 10 Severely Errored 
      Seconds are immediately transfered to the count of 
      unavailableSeconds by incrementing the count of unavailSec by 10 
      and decrementing the count of sevErroredSec by 10. Whilst in the 
      unavailable state, an unavailableSecond is counted for each SES or 
      SEFS that occurs, and the count of SES and SEFS are both 
      inhibited. The unavailable state is cleared at the onset of 10 
      consecutive seconds which are not Severely Errored Seconds."
::= { mscLpJT2StatsEntry 6 }

mscLpJT2BpvErrors OBJECT-TYPE
   SYNTAX     Counter32 
   ACCESS     read-only
   STATUS     mandatory
   DESCRIPTION
     "This attribute indicates the total count of bipolar violations (BPV). 
      A bipolar violation is an error in the alternate mark inversion pattern 
      (AMI) on the line. The value of this attribute will wrap to zero when 
      it reaches its maximum value."
::= { mscLpJT2StatsEntry 7 }

mscLpJT2CrcErrors OBJECT-TYPE
   SYNTAX     Counter32 
   ACCESS     read-only
   STATUS     mandatory
   DESCRIPTION
     "This attribute indicates the total number of cyclic redundancy check 
      (CRC-5) errors detected on the incoming JT2 line. The value of this 
      attribute will wrap to 0 when its maximum value is reached."
::= { mscLpJT2StatsEntry 8 }

mscLpJT2FrameErrors OBJECT-TYPE
   SYNTAX     Counter32 
   ACCESS     read-only
   STATUS     mandatory
   DESCRIPTION
     "This attribute indicates the total number of Framing Errors that have 
      occured on the JT2 port. A Framing Error is an error in the framing 
      bits. The value of this attribute will wrap to 0 when its maximum 
      value is reached."
::= { mscLpJT2StatsEntry 9 }

mscLpJT2LosStateChanges OBJECT-TYPE
   SYNTAX     Counter32 
   ACCESS     read-only
   STATUS     mandatory
   DESCRIPTION
     "This attribute indicates the total number of times that the incoming 
      signal on the JT2 line has been lost. The value of this attribute will 
      wrap to 0 when its maximum value is reached."
::= { mscLpJT2StatsEntry 10 }

mscLpJT2AdminInfoTable OBJECT-TYPE
   SYNTAX     SEQUENCE OF MscLpJT2AdminInfoEntry
   ACCESS     not-accessible
   STATUS     mandatory
   DESCRIPTION
     "This group contains the attributes pertaining to the vendor of the 
      equipment."
::= { mscLpJT2 17 }

mscLpJT2AdminInfoEntry OBJECT-TYPE
   SYNTAX     MscLpJT2AdminInfoEntry
   ACCESS     not-accessible
   STATUS     mandatory
   DESCRIPTION
     "An entry in the mscLpJT2AdminInfoTable."
   INDEX {
      mscLpIndex,
      mscLpJT2Index }
::= { mscLpJT2AdminInfoTable 1 }

MscLpJT2AdminInfoEntry ::= SEQUENCE {
   mscLpJT2Vendor
      AsciiString,
   mscLpJT2CommentText
      AsciiString }

mscLpJT2Vendor OBJECT-TYPE
   SYNTAX     AsciiString (SIZE (0..20))
   ACCESS     read-write
   STATUS     mandatory
   DESCRIPTION
     "This is the name of the vendor supplying the facility."
::= { mscLpJT2AdminInfoEntry 1 }

mscLpJT2CommentText OBJECT-TYPE
   SYNTAX     AsciiString (SIZE (0..60))
   ACCESS     read-write
   STATUS     mandatory
   DESCRIPTION
     "Any miscellaneous text about the facility."
::= { mscLpJT2AdminInfoEntry 2 }


-- 
-- The Test component is configured to control a hardware facility test 
-- on a physical (V35, X21, DS1, E1, DS3, E3 etc.) or a logical port.

mscLpJT2Test OBJECT IDENTIFIER ::= { mscLpJT2 2 }



mscLpJT2TestRowStatusTable OBJECT-TYPE
   SYNTAX     SEQUENCE OF MscLpJT2TestRowStatusEntry
   ACCESS     not-accessible
   STATUS     mandatory
   DESCRIPTION
     "This entry controls the addition and deletion of 
      mscLpJT2Test components."
::= { mscLpJT2Test 1 }

mscLpJT2TestRowStatusEntry OBJECT-TYPE
   SYNTAX     MscLpJT2TestRowStatusEntry
   ACCESS     not-accessible
   STATUS     mandatory
   DESCRIPTION
     "A single entry in the table represents a single 
      mscLpJT2Test component."
   INDEX {
      mscLpIndex,
      mscLpJT2Index,
      mscLpJT2TestIndex }
::= { mscLpJT2TestRowStatusTable 1 }

MscLpJT2TestRowStatusEntry ::= SEQUENCE {
   mscLpJT2TestRowStatus
      RowStatus,
   mscLpJT2TestComponentName
      DisplayString,
   mscLpJT2TestStorageType
      StorageType,
   mscLpJT2TestIndex
      NonReplicated }

mscLpJT2TestRowStatus OBJECT-TYPE
   SYNTAX     RowStatus 
   ACCESS     read-only
   STATUS     mandatory
   DESCRIPTION
     "This variable is used as the basis for SNMP naming of
      mscLpJT2Test components.
      These components cannot be added nor deleted."
::= { mscLpJT2TestRowStatusEntry 1 }

mscLpJT2TestComponentName OBJECT-TYPE
   SYNTAX     DisplayString 
   ACCESS     read-only
   STATUS     mandatory
   DESCRIPTION
     "This variable provides the component's string name for
      use with the ASCII Console Interface"
::= { mscLpJT2TestRowStatusEntry 2 }

mscLpJT2TestStorageType OBJECT-TYPE
   SYNTAX     StorageType 
   ACCESS     read-only
   STATUS     mandatory
   DESCRIPTION
     "This variable represents the storage type value for the
      mscLpJT2Test tables."
::= { mscLpJT2TestRowStatusEntry 4 }

mscLpJT2TestIndex OBJECT-TYPE
   SYNTAX     NonReplicated 
   ACCESS     not-accessible
   STATUS     mandatory
   DESCRIPTION
     "This variable represents the index for the mscLpJT2Test tables."
::= { mscLpJT2TestRowStatusEntry 10 }

mscLpJT2TestStateTable OBJECT-TYPE
   SYNTAX     SEQUENCE OF MscLpJT2TestStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscLpJT2Test 10 }

mscLpJT2TestStateEntry OBJECT-TYPE
   SYNTAX     MscLpJT2TestStateEntry
   ACCESS     not-accessible
   STATUS     mandatory
   DESCRIPTION
     "An entry in the mscLpJT2TestStateTable."
   INDEX {
      mscLpIndex,
      mscLpJT2Index,
      mscLpJT2TestIndex }
::= { mscLpJT2TestStateTable 1 }

MscLpJT2TestStateEntry ::= SEQUENCE {
   mscLpJT2TestAdminState
      INTEGER,
   mscLpJT2TestOperationalState
      INTEGER,
   mscLpJT2TestUsageState
      INTEGER }

mscLpJT2TestAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscLpJT2TestStateEntry 1 }

mscLpJT2TestOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscLpJT2TestStateEntry 2 }

mscLpJT2TestUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscLpJT2TestStateEntry 3 }

mscLpJT2TestSetupTable OBJECT-TYPE
   SYNTAX     SEQUENCE OF MscLpJT2TestSetupEntry
   ACCESS     not-accessible
   STATUS     mandatory
   DESCRIPTION
     "This group contains all of the operational data for a Test 
      component."
::= { mscLpJT2Test 11 }

mscLpJT2TestSetupEntry OBJECT-TYPE
   SYNTAX     MscLpJT2TestSetupEntry
   ACCESS     not-accessible
   STATUS     mandatory
   DESCRIPTION
     "An entry in the mscLpJT2TestSetupTable."
   INDEX {
      mscLpIndex,
      mscLpJT2Index,
      mscLpJT2TestIndex }
::= { mscLpJT2TestSetupTable 1 }

MscLpJT2TestSetupEntry ::= SEQUENCE {
   mscLpJT2TestPurpose
      AsciiString,
   mscLpJT2TestType
      INTEGER,
   mscLpJT2TestFrmSize
      Unsigned32,
   mscLpJT2TestFrmPatternType
      INTEGER,
   mscLpJT2TestCustomizedPattern
      Hex,
   mscLpJT2TestDataStartDelay
      Unsigned32,
   mscLpJT2TestDisplayInterval
      Unsigned32,
   mscLpJT2TestDuration
      Unsigned32 }

mscLpJT2TestPurpose OBJECT-TYPE
   SYNTAX     AsciiString (SIZE (0..40))
   ACCESS     read-write
   STATUS     mandatory
   DESCRIPTION
     "This attribute records the purpose of the test so that the test results 
      can be associated and properly analyzed."
::= { mscLpJT2TestSetupEntry 1 }

mscLpJT2TestType OBJECT-TYPE
   SYNTAX     INTEGER  {
                 card(0),
                 manual(1),
                 localLoop(2),
                 remoteLoop(3),
                 externalLoop(4),
                 payloadLoop(5),
                 remoteLoopThisTrib(6),
                 v54RemoteLoop(7),
                 pn127RemoteLoop(8) }
   ACCESS     read-write
   STATUS     mandatory
   DESCRIPTION
     "This attribute is the type of test to be run. The available test types 
      include the following:
      card test sets up an internal loop on the board and runs a bit error 
      rate test.
      manual test assumes the line is looped back externally and a bit 
      error rate test is performed.
      localLoop test loops back the local modem and performs a bit error 
      rate test.
      remoteLoop test loops back the remote modem (or CSU) and 
      performs a bit error rate test.
      externalLoop test loops back the line to the far end.
      payloadLoop test only loops back the payload data received from 
      the incoming line.
      remoteLoopThisTrib loops this particular tributary back at the far 
      end, using services provided by the parent.
      v54RemoteLoop initiates a V.54 Remote Loopback test.
      pn127RemoteLoop initiates a PN127 Remote Loopback test.
      Note that not all test types are not supported by all function 
      processors."
   DEFVAL     { card }
::= { mscLpJT2TestSetupEntry 2 }

mscLpJT2TestFrmSize OBJECT-TYPE
   SYNTAX     Unsigned32 (4..4096)
   ACCESS     read-write
   STATUS     mandatory
   DESCRIPTION
     "This attribute defines the size of the test data frames in number of 
      bytes."
   DEFVAL     { 1024 }
::= { mscLpJT2TestSetupEntry 3 }

mscLpJT2TestFrmPatternType OBJECT-TYPE
   SYNTAX     INTEGER  {
                 ccitt32kBitPattern(0),
                 ccitt8MBitPattern(1),
                 customizedPattern(2) }
   ACCESS     read-write
   STATUS     mandatory
   DESCRIPTION
     "This attribute defines the type of data pattern generation to use. The 
      following lists the available pattern types:
      ccitt32kBitPattern is a pseudo-random sequence of 32 kbit.
      ccitt8MBitPattern is a pseudo-random sequence of 8Mbit.
      customizedPattern is the pattern defined in the customizedPattern 
      attribute."
   DEFVAL     { ccitt32kBitPattern }
::= { mscLpJT2TestSetupEntry 4 }

mscLpJT2TestCustomizedPattern OBJECT-TYPE
   SYNTAX     Hex (0..4294967295)
   ACCESS     read-write
   STATUS     mandatory
   DESCRIPTION
     "This attribute allows a customized 32 bit pattern to be defined for 
      use in the test data frames. This attribute is used when the attribute 
      frmPatternType is set to CustomizedPattern. Note that a 55 hex 
      pattern is an alternating 1 and 0 pattern."
   DEFVAL     { 1431655765 }
::= { mscLpJT2TestSetupEntry 5 }

mscLpJT2TestDataStartDelay OBJECT-TYPE
   SYNTAX     Unsigned32 (0..1814400)
   ACCESS     read-write
   STATUS     mandatory
   DESCRIPTION
     "This attribute specifies the time delay (in seconds) between when 
      the test expects the loop to have been set up, to when the test data 
      actually starts to be transmitted. This attribute is to accommodate 
      some non-standard equipment that requires extra time for setting up 
      a requested loop.
      This attribute is ignored when the test type is set to externalLoop."
   DEFVAL     { 0 }
::= { mscLpJT2TestSetupEntry 6 }

mscLpJT2TestDisplayInterval OBJECT-TYPE
   SYNTAX     Unsigned32 (0..30240)
   ACCESS     read-write
   STATUS     mandatory
   DESCRIPTION
     "This attribute defines the interval (in minutes) between which 
      interim test results are to be displayed. Results are displayed at the 
      operator console at which the test was started. When the test type is 
      set to externalLoop, this attribute is ignored. There will be no 
      display of results if displayInterval is set to 0. This attribute can be 
      changed anytime."
   DEFVAL     { 5 }
::= { mscLpJT2TestSetupEntry 7 }

mscLpJT2TestDuration OBJECT-TYPE
   SYNTAX     Unsigned32 (1..30240)
   ACCESS     read-write
   STATUS     mandatory
   DESCRIPTION
     "This attribute is the duration (in minutes) that test data will be 
      transmitted. In the case of an externalLoop, this is the time that the 
      loop is in effect. Note that dataStartDelay does not apply to the 
      externalLoop."
   DEFVAL     { 1 }
::= { mscLpJT2TestSetupEntry 8 }

mscLpJT2TestResultsTable OBJECT-TYPE
   SYNTAX     SEQUENCE OF MscLpJT2TestResultsEntry
   ACCESS     not-accessible
   STATUS     mandatory
   DESCRIPTION
     "This group contains all the statistics related attributes of the Test 
      component."
::= { mscLpJT2Test 12 }

mscLpJT2TestResultsEntry OBJECT-TYPE
   SYNTAX     MscLpJT2TestResultsEntry
   ACCESS     not-accessible
   STATUS     mandatory
   DESCRIPTION
     "An entry in the mscLpJT2TestResultsTable."
   INDEX {
      mscLpIndex,
      mscLpJT2Index,
      mscLpJT2TestIndex }
::= { mscLpJT2TestResultsTable 1 }

MscLpJT2TestResultsEntry ::= SEQUENCE {
   mscLpJT2TestElapsedTime
      Counter32,
   mscLpJT2TestTimeRemaining
      Unsigned32,
   mscLpJT2TestCauseOfTermination
      INTEGER,
   mscLpJT2TestBitsTx
      PassportCounter64,
   mscLpJT2TestBytesTx
      PassportCounter64,
   mscLpJT2TestFrmTx
      PassportCounter64,
   mscLpJT2TestBitsRx
      PassportCounter64,
   mscLpJT2TestBytesRx
      PassportCounter64,
   mscLpJT2TestFrmRx
      PassportCounter64,
   mscLpJT2TestErroredFrmRx
      PassportCounter64,
   mscLpJT2TestBitErrorRate
      AsciiString }

mscLpJT2TestElapsedTime OBJECT-TYPE
   SYNTAX     Counter32 
   ACCESS     read-only
   STATUS     mandatory
   DESCRIPTION
     "This attribute is the number of minutes elapsed since the test started 
      for an externalLoop test. For a data test, this is the time since test 
      data was first transmitted."
::= { mscLpJT2TestResultsEntry 1 }

mscLpJT2TestTimeRemaining OBJECT-TYPE
   SYNTAX     Unsigned32 (0..4294967295)
   ACCESS     read-only
   STATUS     mandatory
   DESCRIPTION
     "This attribute is the number of minutes remaining before the test is 
      to be stopped according to the duration attribute."
   DEFVAL     { 0 }
::= { mscLpJT2TestResultsEntry 2 }

mscLpJT2TestCauseOfTermination OBJECT-TYPE
   SYNTAX     INTEGER  {
                 testTimeExpired(0),
                 stoppedByOperator(1),
                 unknown(2),
                 neverStarted(3),
                 testRunning(4),
                 hardwareReconfigured(5),
                 loopCodeSyncFailed(6),
                 patternSyncFailed(7),
                 patternSyncLost(8) }
   ACCESS     read-only
   STATUS     mandatory
   DESCRIPTION
     "This attribute indicates either the status of the test or the cause of 
      the test's termination:
      
      neverStarted indicates that the test has not yet been started.
      
      testRunning indicates that the test has been started.
      
      stoppedByOperator indicates that the operator issued a stop 
      command on a test that was running.
      
      testTimeExpired indicates that the test ran for the time specified by 
      the test's duration.
      
      loopCodeSyncFailed indicates that the local end failed to 
      synchronize to the loopCode pattern. The local end transmits the 
      loopCode pattern to cause the remote end to apply a loopback, after 
      which the local end should receive the loopCode pattern. The exact 
      pattern used to request loopCode depends on the test type. This 
      failure indicates a high rate of transmission errors, or that the 
      remote end has failed to apply the loopback.
      
      patternSyncFailed indicates that the local end failed to synchronize 
      to the frmPatternType test pattern, that should have been looped 
      back at the remote end. This failure indicates a high rate of 
      transmission errors or the absence of a loopback.
      
      patternSyncLost indicates that the local end gained and then lost 
      synchronization to the returned frmPatternType test pattern. This 
      failure indicates a sudden increase in transmission errors, frame 
      slippage, or the removal of an existing loopback.
      
      unknown is set when a reason to terminate other than those listed 
      here is encountered.
      
      Note: Only MSA cards support recognition of the failures 
      loopCodeSyncFailed, patternSyncFailed and patternSyncLost. 
      Other cards will not terminate the test under the conditions 
      described by these values."
   DEFVAL     { neverStarted }
::= { mscLpJT2TestResultsEntry 3 }

mscLpJT2TestBitsTx OBJECT-TYPE
   SYNTAX     PassportCounter64 
   ACCESS     read-only
   STATUS     mandatory
   DESCRIPTION
     "This attribute is the total number of bits sent during the test period. 
      As long as the line speed of the hardware interface is less than 
      70 Mbit/s, this counter is not expected to reach the maximum value."
::= { mscLpJT2TestResultsEntry 4 }

mscLpJT2TestBytesTx OBJECT-TYPE
   SYNTAX     PassportCounter64 
   ACCESS     read-only
   STATUS     mandatory
   DESCRIPTION
     "This attribute is the total number of bytes sent during the test 
      period. This counter is not expected to reach its maximum value."
::= { mscLpJT2TestResultsEntry 5 }

mscLpJT2TestFrmTx OBJECT-TYPE
   SYNTAX     PassportCounter64 
   ACCESS     read-only
   STATUS     mandatory
   DESCRIPTION
     "This attribute is the total number of frames sent during the test 
      period. This counter is not expected to reach its maximum value."
::= { mscLpJT2TestResultsEntry 6 }

mscLpJT2TestBitsRx OBJECT-TYPE
   SYNTAX     PassportCounter64 
   ACCESS     read-only
   STATUS     mandatory
   DESCRIPTION
     "This attribute is the total number of bits received during the test 
      period. This counter is not expected to reach its maximum value. 
      The counter will wrap around to 0 if it does reach the maximum 
      value."
::= { mscLpJT2TestResultsEntry 7 }

mscLpJT2TestBytesRx OBJECT-TYPE
   SYNTAX     PassportCounter64 
   ACCESS     read-only
   STATUS     mandatory
   DESCRIPTION
     "This attribute is the total number of bytes received during the test 
      period. This counter is not expected to reach its maximum value. 
      The counter will wrap around to 0 if it does reach its maximum 
      value."
::= { mscLpJT2TestResultsEntry 8 }

mscLpJT2TestFrmRx OBJECT-TYPE
   SYNTAX     PassportCounter64 
   ACCESS     read-only
   STATUS     mandatory
   DESCRIPTION
     "This attribute is the total number of frames received during the test 
      period. This counter is not expected to reach its maximum value. 
      The counter will wrap around to 0 if it does reach its maximum 
      value."
::= { mscLpJT2TestResultsEntry 9 }

mscLpJT2TestErroredFrmRx OBJECT-TYPE
   SYNTAX     PassportCounter64 
   ACCESS     read-only
   STATUS     mandatory
   DESCRIPTION
     "This attribute is not displayed for ATM cards because the physical 
      layer drops all errored frames at the controller interface. 
      
      For all other card types, this attribute is the total number of errored 
      frames received during the test period. This counter is not expected 
      to reach its maximum value. The counter will wrap around to 0 if it 
      does reach its maximum value."
::= { mscLpJT2TestResultsEntry 10 }

mscLpJT2TestBitErrorRate OBJECT-TYPE
   SYNTAX     AsciiString (SIZE (5))
   ACCESS     read-only
   STATUS     mandatory
   DESCRIPTION
     "This attribute is not displayed for ATM cards because the physical 
      layer drops all errored frames at the controller interface. 
      
      For all other card types, this attribute is the calculated bit error rate 
      on the link. Test data are generated and sent in frames of a preset 
      size (frameSize). The Test component will try to estimate the 
      number of bit errors in any errored frame which is identifiable. The 
      statistics will be updated accordingly. A lost frame (may be due to 
      an error on the flag sequence) will be discarded for the bit error rate 
      calculation. The result is presented in the form of xEsyy, where x is 
      the mantissa, syy is the exponent, for example 0E+00, 2E-09.
      Note that the bitErrorRate is an estimate only. For more reliable test 
      results, the test should be done over a long period. Multiple tests 
      would also improve the confidence level of the test results."
::= { mscLpJT2TestResultsEntry 11 }


-- 
-- The AtmCell is a component that contains provisioning and 
-- operational attributes. The provisioning attributes are used to set the 
-- Loss of Cell Deliniation (LCD) alarm activation delay and to turn 
-- cell payload scrambling on or off. The operational attributes are 
-- used to report about the quality of the ATM cells received by the 
-- interface and the cell capacity utilization. The AtmCell component 
-- appears under all port components running on ATM cards.

mscLpJT2Cell OBJECT IDENTIFIER ::= { mscLpJT2 3 }



mscLpJT2CellRowStatusTable OBJECT-TYPE
   SYNTAX     SEQUENCE OF MscLpJT2CellRowStatusEntry
   ACCESS     not-accessible
   STATUS     mandatory
   DESCRIPTION
     "This entry controls the addition and deletion of 
      mscLpJT2Cell components."
::= { mscLpJT2Cell 1 }

mscLpJT2CellRowStatusEntry OBJECT-TYPE
   SYNTAX     MscLpJT2CellRowStatusEntry
   ACCESS     not-accessible
   STATUS     mandatory
   DESCRIPTION
     "A single entry in the table represents a single 
      mscLpJT2Cell component."
   INDEX {
      mscLpIndex,
      mscLpJT2Index,
      mscLpJT2CellIndex }
::= { mscLpJT2CellRowStatusTable 1 }

MscLpJT2CellRowStatusEntry ::= SEQUENCE {
   mscLpJT2CellRowStatus
      RowStatus,
   mscLpJT2CellComponentName
      DisplayString,
   mscLpJT2CellStorageType
      StorageType,
   mscLpJT2CellIndex
      NonReplicated }

mscLpJT2CellRowStatus OBJECT-TYPE
   SYNTAX     RowStatus 
   ACCESS     read-only
   STATUS     mandatory
   DESCRIPTION
     "This variable is used as the basis for SNMP naming of
      mscLpJT2Cell components.
      These components cannot be added nor deleted."
::= { mscLpJT2CellRowStatusEntry 1 }

mscLpJT2CellComponentName OBJECT-TYPE
   SYNTAX     DisplayString 
   ACCESS     read-only
   STATUS     mandatory
   DESCRIPTION
     "This variable provides the component's string name for
      use with the ASCII Console Interface"
::= { mscLpJT2CellRowStatusEntry 2 }

mscLpJT2CellStorageType OBJECT-TYPE
   SYNTAX     StorageType 
   ACCESS     read-only
   STATUS     mandatory
   DESCRIPTION
     "This variable represents the storage type value for the
      mscLpJT2Cell tables."
::= { mscLpJT2CellRowStatusEntry 4 }

mscLpJT2CellIndex OBJECT-TYPE
   SYNTAX     NonReplicated 
   ACCESS     not-accessible
   STATUS     mandatory
   DESCRIPTION
     "This variable represents the index for the mscLpJT2Cell tables."
::= { mscLpJT2CellRowStatusEntry 10 }

mscLpJT2CellProvTable OBJECT-TYPE
   SYNTAX     SEQUENCE OF MscLpJT2CellProvEntry
   ACCESS     not-accessible
   STATUS     mandatory
   DESCRIPTION
     "This group contains the provisioning attributes for the AtmCell 
      component."
::= { mscLpJT2Cell 10 }

mscLpJT2CellProvEntry OBJECT-TYPE
   SYNTAX     MscLpJT2CellProvEntry
   ACCESS     not-accessible
   STATUS     mandatory
   DESCRIPTION
     "An entry in the mscLpJT2CellProvTable."
   INDEX {
      mscLpIndex,
      mscLpJT2Index,
      mscLpJT2CellIndex }
::= { mscLpJT2CellProvTable 1 }

MscLpJT2CellProvEntry ::= SEQUENCE {
   mscLpJT2CellAlarmActDelay
      Unsigned32,
   mscLpJT2CellScrambleCellPayload
      INTEGER,
   mscLpJT2CellCorrectSingleBitHeaderErrors
      INTEGER }

mscLpJT2CellAlarmActDelay OBJECT-TYPE
   SYNTAX     Unsigned32 (0..2000)
   ACCESS     read-write
   STATUS     mandatory
   DESCRIPTION
     "This attribute defines the time during which a Loss of Cell 
      Delineation (LCD) defect should be observed before declaring an 
      LCD alarm (alarm 70115501). The time is specified in milliseconds."
   DEFVAL     { 500 }
::= { mscLpJT2CellProvEntry 1 }

mscLpJT2CellScrambleCellPayload OBJECT-TYPE
   SYNTAX     INTEGER  {
                 off(0),
                 on(1) }
   ACCESS     read-write
   STATUS     mandatory
   DESCRIPTION
     "Cell scrambling, as defined by  ITU-T Recommendation I.432., can 
      provide a solution to the problem of transmission equipment which 
      is sensitive to certain bit patterns in the ATM cell payload. This 
      attribute controls whether or not the cell payload is scrambled.
      It defaults to off for DS1 interfaces, and on for all other interfaces.
      Note that this setting must be the same at both ends of the link."
::= { mscLpJT2CellProvEntry 2 }

mscLpJT2CellCorrectSingleBitHeaderErrors OBJECT-TYPE
   SYNTAX     INTEGER  {
                 off(0),
                 on(1) }
   ACCESS     read-write
   STATUS     mandatory
   DESCRIPTION
     "This attribute specifies whether the port corrects single bit errors 
      detected in the headers of received cells. If single bit errors are 
      corrected, the affected cells are passed up to the ATM layer 
      according to normal operation. If single bit errors are not corrected, 
      these errored cells are discarded by the physical layer. Note that 
      cells containing multiple bit errors in their headers are always 
      discarded.
      
      Single bit HEC error correction must remain off for the following 
      card types: 3pDS1Atm, 8pDS1Atm, 3pE1Atm, 8pE1Atm, 
      2pJ6MAtm, 3pDS3Atm, and 3pE3Atm."
   DEFVAL     { off }
::= { mscLpJT2CellProvEntry 3 }

mscLpJT2CellOperTable OBJECT-TYPE
   SYNTAX     SEQUENCE OF MscLpJT2CellOperEntry
   ACCESS     not-accessible
   STATUS     mandatory
   DESCRIPTION
     "This group contains the common operational attributes for the 
      AtmCell component."
::= { mscLpJT2Cell 11 }

mscLpJT2CellOperEntry OBJECT-TYPE
   SYNTAX     MscLpJT2CellOperEntry
   ACCESS     not-accessible
   STATUS     mandatory
   DESCRIPTION
     "An entry in the mscLpJT2CellOperTable."
   INDEX {
      mscLpIndex,
      mscLpJT2Index,
      mscLpJT2CellIndex }
::= { mscLpJT2CellOperTable 1 }

MscLpJT2CellOperEntry ::= SEQUENCE {
   mscLpJT2CellLcdAlarm
      INTEGER }

mscLpJT2CellLcdAlarm OBJECT-TYPE
   SYNTAX     INTEGER  {
                 on(0),
                 off(1) }
   ACCESS     read-only
   STATUS     mandatory
   DESCRIPTION
     "This attribute displays whether the Loss of Cell Delineation (LCD) 
      failure alarm state has been entered. This state is entered when LCD 
      defects have been observed and accumulated for a period of time 
      specified through the alarmActDelay attribute.
      In ATM cell direct mapping mode, an LCD defect occurs when Out 
      of Cell Delineation (OCD) anomaly persists for x milliseconds, and 
      disappears when the Out of Cell Delineation (OCD) is absent for x 
      msec. An OCD anomaly occurs when 7 consecutive incorrect HECs 
      have been detected. An OCD anomaly terminates when 6 
      consecutive correct HECs have been detected.
      For an AtmCell component located under a DS3 or E3 component 
      with mapping = PLCP, the LCD defect is directly derived from the 
      PLCP LOF defect.
      If LCD defects are intermittently occurring, the LCD defect 
      accumulator is decremented at a rate of 1/10 of the incrementing 
      rate (alarm integration ratio of 1/10), with all measurements based 
      on a 200 ms polling cycle
      The component under which is located the AtmCell component goes 
      into an operational state of disabled until the LCD alarm condition 
      is cleared. The condition is cleared after the LCD defect has not 
      been reported for a period of 10 seconds +/- 0.5 seconds.
      The lcdAlarm attribute is always set to off when the parent of the 
      AtmCell component has been locked and left offline. This can also 
      happen when the Path or Channel component has been suspended 
      since its parent has been locked."
   DEFVAL     { off }
::= { mscLpJT2CellOperEntry 1 }

mscLpJT2CellStatsTable OBJECT-TYPE
   SYNTAX     SEQUENCE OF MscLpJT2CellStatsEntry
   ACCESS     not-accessible
   STATUS     mandatory
   DESCRIPTION
     "This group contains the Statistics attribute for the AtmCell 
      component. Each attribute type is a non-negative integer which 
      monotonically increases until it reaches a maximum value, at which 
      point it wraps around and starts increasing again from zero."
::= { mscLpJT2Cell 12 }

mscLpJT2CellStatsEntry OBJECT-TYPE
   SYNTAX     MscLpJT2CellStatsEntry
   ACCESS     not-accessible
   STATUS     mandatory
   DESCRIPTION
     "An entry in the mscLpJT2CellStatsTable."
   INDEX {
      mscLpIndex,
      mscLpJT2Index,
      mscLpJT2CellIndex }
::= { mscLpJT2CellStatsTable 1 }

MscLpJT2CellStatsEntry ::= SEQUENCE {
   mscLpJT2CellUncorrectableHecErrors
      Counter32,
   mscLpJT2CellSevErroredSec
      Counter32,
   mscLpJT2CellReceiveCellUtilization
      Gauge32,
   mscLpJT2CellTransmitCellUtilization
      Gauge32,
   mscLpJT2CellCorrectableHeaderErrors
      Counter32 }

mscLpJT2CellUncorrectableHecErrors OBJECT-TYPE
   SYNTAX     Counter32 
   ACCESS     read-only
   STATUS     mandatory
   DESCRIPTION
     "This attribute indicates the number of uncorrectable ATM cell 
      header errors that have been detected. Counting of 
      uncorrectableHeaderErrors is inhibited when an Out of Cell 
      Delineation (OCD) defect is present. An OCD defect occurs when 
      seven consecutive incorrect HECs have been detected. An OCD 
      defect terminates when six consecutive correct HECs have been 
      detected."
::= { mscLpJT2CellStatsEntry 1 }

mscLpJT2CellSevErroredSec OBJECT-TYPE
   SYNTAX     Counter32 
   ACCESS     read-only
   STATUS     mandatory
   DESCRIPTION
     "This attribute indicates the total number of ATM Cell Severely 
      Errored Seconds (SESs) that have been counted. 
      
      In direct mapping mode, an ATM Cell SES is declared for second 
      intervals containing one or more Out of Cell Delineation (OCD) 
      defects. An OCD defect occurs when seven consecutive incorrect 
      HECs have been detected. An OCD defect terminates when six 
      consecutive correct HECs have been detected.
      
      In PLCP mapping mode, an ATM Cell SES is declared for second 
      intervals containing one or more PLCP LOF defects.
      
      Counting of uncorrectableHeaderErrors (ucErr) and 
      correctableHeaderErrors (cErr) is inhibited when the OCD defect 
      is present."
::= { mscLpJT2CellStatsEntry 2 }

mscLpJT2CellReceiveCellUtilization OBJECT-TYPE
   SYNTAX     Gauge32 (0..100)
   ACCESS     read-only
   STATUS     mandatory
   DESCRIPTION
     "This attribute is the ratio of the number of valid, assigned cells 
      received on the link to the nominal link capacity. The utilization is 
      calculated over a period of one minute.
      This attribute is always set to 0 when the parent of the AtmCell 
      component has been locked and left offline. This can also happen 
      when the Path or Channel component has been suspended since its 
      parent has been locked."
   DEFVAL     { 0 }
::= { mscLpJT2CellStatsEntry 3 }

mscLpJT2CellTransmitCellUtilization OBJECT-TYPE
   SYNTAX     Gauge32 (0..100)
   ACCESS     read-only
   STATUS     mandatory
   DESCRIPTION
     "This attribute is the ratio of the number of valid, assigned cells 
      transmitted on the link to the nominal link capacity. The utilization 
      is calculated over a period of one minute.
      This attribute is always set to 0 when the parent of the AtmCell 
      component has been locked and left offline. This can also happen 
      when the Path or Channel component has been suspended since its 
      parent has been locked."
   DEFVAL     { 0 }
::= { mscLpJT2CellStatsEntry 4 }

mscLpJT2CellCorrectableHeaderErrors OBJECT-TYPE
   SYNTAX     Counter32 
   ACCESS     read-only
   STATUS     mandatory
   DESCRIPTION
     "This attribute indicates the number of correctable ATM cell header 
      errors that have been detected and corrected. Counting of 
      correctableHeaderErrors is inhibited when an Out of Cell 
      Delineation (OCD) defect is present. An OCD defect occurs when 
      seven consecutive incorrect HECs have been detected. An OCD 
      defect terminates when six consecutive correct HECs have been 
      detected"
::= { mscLpJT2CellStatsEntry 5 }


-- 
-- Lp/m Hssi/0
-- 
-- The Hssi component controls a Passport HSSI interface.

mscLpHssi OBJECT IDENTIFIER ::= { mscLp 17 }



mscLpHssiRowStatusTable OBJECT-TYPE
   SYNTAX     SEQUENCE OF MscLpHssiRowStatusEntry
   ACCESS     not-accessible
   STATUS     mandatory
   DESCRIPTION
     "This entry controls the addition and deletion of 
      mscLpHssi components."
::= { mscLpHssi 1 }

mscLpHssiRowStatusEntry OBJECT-TYPE
   SYNTAX     MscLpHssiRowStatusEntry
   ACCESS     not-accessible
   STATUS     mandatory
   DESCRIPTION
     "A single entry in the table represents a single 
      mscLpHssi component."
   INDEX {
      mscLpIndex,
      mscLpHssiIndex }
::= { mscLpHssiRowStatusTable 1 }

MscLpHssiRowStatusEntry ::= SEQUENCE {
   mscLpHssiRowStatus
      RowStatus,
   mscLpHssiComponentName
      DisplayString,
   mscLpHssiStorageType
      StorageType,
   mscLpHssiIndex
      Integer32 }

mscLpHssiRowStatus OBJECT-TYPE
   SYNTAX     RowStatus 
   ACCESS     read-write
   STATUS     mandatory
   DESCRIPTION
     "This variable is used as the basis for SNMP naming of
      mscLpHssi components.
      These components can be added and deleted."
::= { mscLpHssiRowStatusEntry 1 }

mscLpHssiComponentName OBJECT-TYPE
   SYNTAX     DisplayString 
   ACCESS     read-only
   STATUS     mandatory
   DESCRIPTION
     "This variable provides the component's string name for
      use with the ASCII Console Interface"
::= { mscLpHssiRowStatusEntry 2 }

mscLpHssiStorageType OBJECT-TYPE
   SYNTAX     StorageType 
   ACCESS     read-only
   STATUS     mandatory
   DESCRIPTION
     "This variable represents the storage type value for the
      mscLpHssi tables."
::= { mscLpHssiRowStatusEntry 4 }

mscLpHssiIndex OBJECT-TYPE
   SYNTAX     Integer32 (0..0)
   ACCESS     not-accessible
   STATUS     mandatory
   DESCRIPTION
     "This variable represents the index for the mscLpHssi tables."
::= { mscLpHssiRowStatusEntry 10 }

mscLpHssiProvTable OBJECT-TYPE
   SYNTAX     SEQUENCE OF MscLpHssiProvEntry
   ACCESS     not-accessible
   STATUS     mandatory
   DESCRIPTION
     "This group contains the specific provisioning data for a Hssi 
      component."
::= { mscLpHssi 10 }

mscLpHssiProvEntry OBJECT-TYPE
   SYNTAX     MscLpHssiProvEntry
   ACCESS     not-accessible
   STATUS     mandatory
   DESCRIPTION
     "An entry in the mscLpHssiProvTable."
   INDEX {
      mscLpIndex,
      mscLpHssiIndex }
::= { mscLpHssiProvTable 1 }

MscLpHssiProvEntry ::= SEQUENCE {
   mscLpHssiLinkMode
      INTEGER,
   mscLpHssiReadyLineState
      OCTET STRING,
   mscLpHssiDataTransferLineState
      OCTET STRING,
   mscLpHssiLineSpeed
      Unsigned32,
   mscLpHssiApplicationFramerName
      Link }

mscLpHssiLinkMode OBJECT-TYPE
   SYNTAX     INTEGER  {
                 dte(0),
                 dce(128) }
   ACCESS     read-write
   STATUS     mandatory
   DESCRIPTION
     "This attribute defines the intended gender of the HSSI port. The 
      actual gender of the port is determined by the hardware setup.
      
      In dte mode, the ta line signal is driven as specified by the attribute 
      readyLineState when the HSSI port passes its diagnostics. The ta 
      line signal is then driven as specified by the attribute 
      dataTransferLineState when the application is ready to transfer 
      data. On the other hand, the input line signal ca is compared against 
      those specified in the attributes readyLineState and 
      dataTransferLineState. The application will be notified when the 
      specified input line states are observed. 
      
      In dce mode, the Hssi component behaves similarly as when it is in 
      dte mode. However, it will be driving the dce line signal (ca) and 
      monitoring the dte line signal (ta) as specified by the attributes 
      readyLineState and dataTransferLineState."
   DEFVAL     { dce }
::= { mscLpHssiProvEntry 1 }

mscLpHssiReadyLineState OBJECT-TYPE
   SYNTAX     OCTET STRING (SIZE (1))
   ACCESS     read-write
   STATUS     mandatory
   DESCRIPTION
     "This attribute specifies the line signal originating from the HSSI 
      interface that will always be turned on, provided the HSSI interface 
      passes it diagnostics. This set of signal is generally required for 
      maintaining the connection. Note that both dte and dce signals are 
      specified in this attribute. The appropriate set of specified signals 
      will be turned on or checked according to the operational attribute 
      actualLinkMode. See also linkMode.

      Description of bits:
      ca(0)
      ta(1)"
   DEFVAL     { 'c0'H }
::= { mscLpHssiProvEntry 2 }

mscLpHssiDataTransferLineState OBJECT-TYPE
   SYNTAX     OCTET STRING (SIZE (1))
   ACCESS     read-write
   STATUS     mandatory
   DESCRIPTION
     "This attribute specifies the line signals required to indicate that the 
      external equipment is in a good state (that is, data transfer can 
      proceed). Note that both dte and dce signals are specified in this 
      attribute. The appropriate set of specified signals will be turned on 
      or checked according to the operational attribute actualLinkMode. 
      The value of this attribute must be a superset of that of the 
      readyLineState attribute.
      See also linkMode.

      Description of bits:
      ca(0)
      ta(1)"
   DEFVAL     { 'c0'H }
::= { mscLpHssiProvEntry 3 }

mscLpHssiLineSpeed OBJECT-TYPE
   SYNTAX     Unsigned32 (1000000..50000000)
   ACCESS     read-write
   STATUS     mandatory
   DESCRIPTION
     "This attribute defines the speed of the line for source clocking. This 
      attribute is ignored if the interface is not providing a clock. Note 
      that the actual clock rate are available in the operational attributes 
      actualTxLineSpeed and actualRxLineSpeed."
   DEFVAL     { 45000000 }
::= { mscLpHssiProvEntry 5 }

mscLpHssiApplicationFramerName OBJECT-TYPE
   SYNTAX     Link 
   ACCESS     read-write
   STATUS     mandatory
   DESCRIPTION
     "This attribute contains the component name of a Framer which is 
      associated with the Hssi component."
::= { mscLpHssiProvEntry 7 }

mscLpHssiCidDataTable OBJECT-TYPE
   SYNTAX     SEQUENCE OF MscLpHssiCidDataEntry
   ACCESS     not-accessible
   STATUS     mandatory
   DESCRIPTION
     "This group contains the attribute for a component's Customer 
      Identifier (CID). Refer to the attribute description for a detailed 
      explanation of CIDs."
::= { mscLpHssi 11 }

mscLpHssiCidDataEntry OBJECT-TYPE
   SYNTAX     MscLpHssiCidDataEntry
   ACCESS     not-accessible
   STATUS     mandatory
   DESCRIPTION
     "An entry in the mscLpHssiCidDataTable."
   INDEX {
      mscLpIndex,
      mscLpHssiIndex }
::= { mscLpHssiCidDataTable 1 }

MscLpHssiCidDataEntry ::= SEQUENCE {
   mscLpHssiCustomerIdentifier
      Unsigned32 }

mscLpHssiCustomerIdentifier OBJECT-TYPE
   SYNTAX     Unsigned32 (0 | 1..8191)
   ACCESS     read-write
   STATUS     mandatory
   DESCRIPTION
     "This attribute holds the Customer Identifier (CID).
      
      Every component has a CID. If a component has a cid attribute, the 
      component's CID is the provisioned value of that attribute; 
      otherwise the component inherits the CID of its parent. The top-
      level component has a CID of 0.
      
      Every operator session also has a CID, which is the CID 
      provisioned for the operator's user ID. An operator will see only the 
      stream data for components having a matching CID. Also, the 
      operator will be allowed to issue commands for only those 
      components which have a matching CID.
      
      An operator CID of 0 is used to identify the Network Manager 
      (referred to as 'NetMan' in DPN). This CID matches the CID of 
      any component. Values 1 to 8191 inclusive (equivalent to 'basic 
      CIDs' in DPN) may be assigned to specific customers."
   DEFVAL     { 0 }
::= { mscLpHssiCidDataEntry 1 }

mscLpHssiAdminInfoTable OBJECT-TYPE
   SYNTAX     SEQUENCE OF MscLpHssiAdminInfoEntry
   ACCESS     not-accessible
   STATUS     mandatory
   DESCRIPTION
     "This group contains the attributes pertaining to the vendor of the 
      equipment."
::= { mscLpHssi 12 }

mscLpHssiAdminInfoEntry OBJECT-TYPE
   SYNTAX     MscLpHssiAdminInfoEntry
   ACCESS     not-accessible
   STATUS     mandatory
   DESCRIPTION
     "An entry in the mscLpHssiAdminInfoTable."
   INDEX {
      mscLpIndex,
      mscLpHssiIndex }
::= { mscLpHssiAdminInfoTable 1 }

MscLpHssiAdminInfoEntry ::= SEQUENCE {
   mscLpHssiVendor
      AsciiString,
   mscLpHssiCommentText
      AsciiString }

mscLpHssiVendor OBJECT-TYPE
   SYNTAX     AsciiString (SIZE (0..20))
   ACCESS     read-write
   STATUS     mandatory
   DESCRIPTION
     "This is the name of the vendor supplying the facility."
::= { mscLpHssiAdminInfoEntry 1 }

mscLpHssiCommentText OBJECT-TYPE
   SYNTAX     AsciiString (SIZE (0..60))
   ACCESS     read-write
   STATUS     mandatory
   DESCRIPTION
     "Any miscellaneous text about the facility."
::= { mscLpHssiAdminInfoEntry 2 }

mscLpHssiIfEntryTable OBJECT-TYPE
   SYNTAX     SEQUENCE OF MscLpHssiIfEntryEntry
   ACCESS     not-accessible
   STATUS     mandatory
   DESCRIPTION
     "This group contains the provisionable attributes for the ifEntry."
::= { mscLpHssi 13 }

mscLpHssiIfEntryEntry OBJECT-TYPE
   SYNTAX     MscLpHssiIfEntryEntry
   ACCESS     not-accessible
   STATUS     mandatory
   DESCRIPTION
     "An entry in the mscLpHssiIfEntryTable."
   INDEX {
      mscLpIndex,
      mscLpHssiIndex }
::= { mscLpHssiIfEntryTable 1 }

MscLpHssiIfEntryEntry ::= SEQUENCE {
   mscLpHssiIfAdminStatus
      INTEGER,
   mscLpHssiIfIndex
      InterfaceIndex }

mscLpHssiIfAdminStatus OBJECT-TYPE
   SYNTAX     INTEGER  {
                 up(1),
                 down(2),
                 testing(3) }
   ACCESS     read-write
   STATUS     mandatory
   DESCRIPTION
     "The desired state of the interface. The up state indicates the 
      interface is operational. The down state indicates the interface is not 
      operational. The testing state indicates that no operational packets 
      can be passed."
   DEFVAL     { up }
::= { mscLpHssiIfEntryEntry 1 }

mscLpHssiIfIndex OBJECT-TYPE
   SYNTAX     InterfaceIndex (1..65535)
   ACCESS     read-only
   STATUS     mandatory
   DESCRIPTION
     "This is the index for the IfEntry. Its value is automatically initialized 
      during the provisioning process."
::= { mscLpHssiIfEntryEntry 2 }

mscLpHssiOperStatusTable OBJECT-TYPE
   SYNTAX     SEQUENCE OF MscLpHssiOperStatusEntry
   ACCESS     not-accessible
   STATUS     mandatory
   DESCRIPTION
     "This group includes the Operational Status attribute. This attribute 
      defines the current operational state of this component."
::= { mscLpHssi 14 }

mscLpHssiOperStatusEntry OBJECT-TYPE
   SYNTAX     MscLpHssiOperStatusEntry
   ACCESS     not-accessible
   STATUS     mandatory
   DESCRIPTION
     "An entry in the mscLpHssiOperStatusTable."
   INDEX {
      mscLpIndex,
      mscLpHssiIndex }
::= { mscLpHssiOperStatusTable 1 }

MscLpHssiOperStatusEntry ::= SEQUENCE {
   mscLpHssiSnmpOperStatus
      INTEGER }

mscLpHssiSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { mscLpHssiOperStatusEntry 1 }

mscLpHssiStateTable OBJECT-TYPE
   SYNTAX     SEQUENCE OF MscLpHssiStateEntry
   ACCESS     not-accessible
   STATUS     mandatory
   DESCRIPTION
     "This group contains the three OSI State attributes and the six OSI 
      Status attributes. The descriptions generically indicate what each 
      attribute implies about the component. Note that not all the values 
      and state combinations described here are supported by every 
      component which uses this group. For component-specific 
      information and the valid state combinations, refer to NTP 241-
      7001-150, Passport Operations and Maintenance Guide."
::= { mscLpHssi 15 }

mscLpHssiStateEntry OBJECT-TYPE
   SYNTAX     MscLpHssiStateEntry
   ACCESS     not-accessible
   STATUS     mandatory
   DESCRIPTION
     "An entry in the mscLpHssiStateTable."
   INDEX {
      mscLpIndex,
      mscLpHssiIndex }
::= { mscLpHssiStateTable 1 }

MscLpHssiStateEntry ::= SEQUENCE {
   mscLpHssiAdminState
      INTEGER,
   mscLpHssiOperationalState
      INTEGER,
   mscLpHssiUsageState
      INTEGER,
   mscLpHssiAvailabilityStatus
      OCTET STRING,
   mscLpHssiProceduralStatus
      OCTET STRING,
   mscLpHssiControlStatus
      OCTET STRING,
   mscLpHssiAlarmStatus
      OCTET STRING,
   mscLpHssiStandbyStatus
      INTEGER,
   mscLpHssiUnknownStatus
      INTEGER }

mscLpHssiAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component.
      
      The OSI Status attributes, if supported by the component, may 
      provide more details, qualifying the state of the component."
   DEFVAL     { unlocked }
::= { mscLpHssiStateEntry 1 }

mscLpHssiOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle.
      
      The OSI Status attributes, if supported by the component, may 
      provide more details, qualifying the state of the component."
   DEFVAL     { disabled }
::= { mscLpHssiStateEntry 2 }

mscLpHssiUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time.
      
      The OSI Status attributes, if supported by the component, may 
      provide more details, qualifying the state of the component."
   DEFVAL     { idle }
::= { mscLpHssiStateEntry 3 }

mscLpHssiAvailabilityStatus OBJECT-TYPE
   SYNTAX     OCTET STRING (SIZE (2))
   ACCESS     read-only
   STATUS     mandatory
   DESCRIPTION
     "If supported by the component, this attribute indicates the OSI 
      Availability status of the component. Note that, even though it is 
      defined as a multi-valued set, at most one value is shown to the user.
      
      When no values are in the set, this indicates that either the attribute 
      is not supported or that none of the status conditions described 
      below are present.
      
      The value inTest indicates that the resource is undergoing a test 
      procedure. If adminState is locked or shuttingDown, the normal 
      users are precluded from using the resource and controlStatus is 
      reservedForTest. Tests that do not exclude additional users can be 
      present in any operational or administrative state but the 
      reservedForTest condition should not be present.
      
      The value failed indicates that the component has an internal fault 
      that prevents it from operating. The operationalState is disabled.
      
      The value dependency indicates that the component cannot operate 
      because some other resource on which it depends is unavailable. 
      The operationalState is disabled.
      
      The value powerOff indicates the resource requires power to be 
      applied and it is not powered on. The operationalState is disabled.
      
      The value offLine indicates the resource requires a routine 
      operation (either manual, automatic, or both) to be performed to 
      place it on-line and make it available for use. The operationalState 
      is disabled.
      
      The value offDuty indicates the resource is inactive in accordance 
      with a predetermined time schedule. In the absence of other 
      disabling conditions, the operationalState is enabled or disabled.
      
      The value degraded indicates the service provided by the 
      component is degraded in some way, such as in speed or operating 
      capacity. However, the resource remains available for service. The 
      operationalState is enabled.
      
      The value notInstalled indicates the resource is not present. The 
      operationalState is disabled.
      
      The value logFull is not used.

      Description of bits:
      inTest(0)
      failed(1)
      powerOff(2)
      offLine(3)
      offDuty(4)
      dependency(5)
      degraded(6)
      notInstalled(7)
      logFull(8)"
::= { mscLpHssiStateEntry 4 }

mscLpHssiProceduralStatus OBJECT-TYPE
   SYNTAX     OCTET STRING (SIZE (1))
   ACCESS     read-only
   STATUS     mandatory
   DESCRIPTION
     "If supported by the component, this attribute indicates the OSI 
      Procedural status of the component. Note that, even though it is 
      defined as a multi-valued set, at most one value is shown to the user.
      
      When no values are in the set, this indicates that either the attribute 
      is not supported or that none of the status conditions described 
      below are present.
      
      The value initializationRequired indicates (for a resource which 
      doesn't initialize autonomously) that initialization is required before 
      it can perform its normal functions, and this procedure has not been 
      initiated. The operationalState is disabled.
      
      The value notInitialized indicates (for a resource which does 
      initialize autonomously) that initialization is required before it can 
      perform its normal functions, and this procedure has not been 
      initiated. The operationalState may be enabled or disabled.
      
      The value initializing indicates that initialization has been initiated 
      but is not yet complete. The operationalState may be enabled or 
      disabled.
      
      The value reporting indicates the resource has completed some 
      processing operation and is notifying the results. The 
      operationalState is enabled.
      
      The value terminating indicates the component is in a termination 
      phase. If the resource doesn't reinitialize autonomously, 
      operationalState is disabled; otherwise it is enabled or disabled.

      Description of bits:
      initializationRequired(0)
      notInitialized(1)
      initializing(2)
      reporting(3)
      terminating(4)"
::= { mscLpHssiStateEntry 5 }

mscLpHssiControlStatus OBJECT-TYPE
   SYNTAX     OCTET STRING (SIZE (1))
   ACCESS     read-only
   STATUS     mandatory
   DESCRIPTION
     "If supported by the component, this attribute indicates the OSI 
      Control status of the component. Note that, even though it is defined 
      as a multi-valued set, at most one value is shown to the user.
      
      When no values are in the set, this indicates that either the attribute 
      is not supported or that none of the status conditions described 
      below are present.
      
      The value subjectToTest indicates the resource is available but tests 
      may be conducted simultaneously at unpredictable times, which 
      may cause it to exhibit unusual characteristics.
      
      The value partOfServicesLocked indicates that part of the service is 
      restricted from users of a resource. The adminState is unlocked.
      
      The value reservedForTest indicates that the component is 
      administratively unavailable because it is undergoing a test 
      procedure. The adminState is locked.
      
      The value suspended indicates that the service has been 
      administratively suspended.

      Description of bits:
      subjectToTest(0)
      partOfServicesLocked(1)
      reservedForTest(2)
      suspended(3)"
::= { mscLpHssiStateEntry 6 }

mscLpHssiAlarmStatus OBJECT-TYPE
   SYNTAX     OCTET STRING (SIZE (1))
   ACCESS     read-only
   STATUS     mandatory
   DESCRIPTION
     "If supported by the component, this attribute indicates the OSI 
      Alarm status of the component. Note that, even though it is defined 
      as a multi-valued set, at most one value is shown to the user.
      
      When no values are in the set, this indicates that either the attribute 
      is not supported or that none of the status conditions described 
      below are present.
      
      The value underRepair indicates the component is currently being 
      repaired. The operationalState is enabled or disabled.
      
      The value critical indicates one or more critical alarms are 
      outstanding against the component. Other, less severe, alarms may 
      also be outstanding. The operationalState is enabled or disabled.
      
      The value major indicates one or more major alarms are 
      outstanding against the component. Other, less severe, alarms may 
      also be outstanding. The operationalState is enabled or disabled.
      
      The value minor indicates one or more minor alarms are 
      outstanding against the component. Other, less severe, alarms may 
      also be outstanding. The operationalState is enabled or disabled.
      
      The value alarmOutstanding generically indicates that an alarm of 
      some severity is outstanding against the component.

      Description of bits:
      underRepair(0)
      critical(1)
      major(2)
      minor(3)
      alarmOutstanding(4)"
::= { mscLpHssiStateEntry 7 }

mscLpHssiStandbyStatus OBJECT-TYPE
   SYNTAX     INTEGER  {
                 hotStandby(0),
                 coldStandby(1),
                 providingService(2),
                 notSet(15) }
   ACCESS     read-only
   STATUS     mandatory
   DESCRIPTION
     "If supported by the component, this attribute indicates the OSI 
      Standby status of the component.
      
      The value notSet indicates that either the attribute is not supported 
      or that none of the status conditions described below are present. 
      Note that this is a non-standard value, used because the original 
      specification indicated this attribute was set-valued and thus, did not 
      provide a value to indicate that none of the other three are 
      applicable.
      
      The value hotStandby indicates that the resource is not providing 
      service but will be immediately able to take over the role of the 
      resource to be backed up, without initialization activity, and 
      containing the same information as the resource to be backed up.
      
      The value coldStandby indicates the resource is a backup for 
      another resource but will not be immediately able to take over the 
      role of the backed up resource and will require some initialization 
      activity.
      
      The value providingService indicates that this component, as a 
      backup resource, is currently backing up another resource."
   DEFVAL     { notSet }
::= { mscLpHssiStateEntry 8 }

mscLpHssiUnknownStatus OBJECT-TYPE
   SYNTAX     INTEGER  {
                 false(0),
                 true(1) }
   ACCESS     read-only
   STATUS     mandatory
   DESCRIPTION
     "This attribute indicates the OSI Unknown status of the component.
      
      The value false indicates that all of the other OSI State and Status 
      attribute values can be considered accurate.
      
      The value true indicates that the actual state of the component is not 
      known for sure."
   DEFVAL     { false }
::= { mscLpHssiStateEntry 9 }

mscLpHssiOperTable OBJECT-TYPE
   SYNTAX     SEQUENCE OF MscLpHssiOperEntry
   ACCESS     not-accessible
   STATUS     mandatory
   DESCRIPTION
     "This group contains all specific operational data for a Hssi 
      component."
::= { mscLpHssi 16 }

mscLpHssiOperEntry OBJECT-TYPE
   SYNTAX     MscLpHssiOperEntry
   ACCESS     not-accessible
   STATUS     mandatory
   DESCRIPTION
     "An entry in the mscLpHssiOperTable."
   INDEX {
      mscLpIndex,
      mscLpHssiIndex }
::= { mscLpHssiOperTable 1 }

MscLpHssiOperEntry ::= SEQUENCE {
   mscLpHssiActualLinkMode
      INTEGER,
   mscLpHssiLineState
      OCTET STRING,
   mscLpHssiActualTxLineSpeed
      Gauge32,
   mscLpHssiActualRxLineSpeed
      Gauge32,
   mscLpHssiDataXferStateChanges
      Counter32 }

mscLpHssiActualLinkMode OBJECT-TYPE
   SYNTAX     INTEGER  {
                 dte(0),
                 dce(128) }
   ACCESS     read-only
   STATUS     mandatory
   DESCRIPTION
     "This attribute contains the actual link mode defined by the 
      hardware. Note that the hardware overrides the provisionable data. 
      The port behaves as a dce or dte according to the actualLinkMode."
::= { mscLpHssiOperEntry 1 }

mscLpHssiLineState OBJECT-TYPE
   SYNTAX     OCTET STRING (SIZE (1))
   ACCESS     read-only
   STATUS     mandatory
   DESCRIPTION
     "This attribute contains the state of the interface signals.

      Description of bits:
      ca(0)
      ta(1)
      tm(2)
      la(3)
      lb(4)"
::= { mscLpHssiOperEntry 2 }

mscLpHssiActualTxLineSpeed OBJECT-TYPE
   SYNTAX     Gauge32 (0..4294967295)
   ACCESS     read-only
   STATUS     mandatory
   DESCRIPTION
     "This attribute is the measured speed of the transmit clock. Note the 
      reported transmit speed is in an error of +/- 10000 bit/s"
::= { mscLpHssiOperEntry 3 }

mscLpHssiActualRxLineSpeed OBJECT-TYPE
   SYNTAX     Gauge32 (0..4294967295)
   ACCESS     read-only
   STATUS     mandatory
   DESCRIPTION
     "This attribute is the measured speed of the receive clock. Note the 
      reported receive speed is in an error of +/- 10000 bit/s"
::= { mscLpHssiOperEntry 4 }

mscLpHssiDataXferStateChanges OBJECT-TYPE
   SYNTAX     Counter32 
   ACCESS     read-only
   STATUS     mandatory
   DESCRIPTION
     "This attribute contains the number of times that the line has entered 
      or exited the data transfer state."
::= { mscLpHssiOperEntry 5 }


-- 
-- The Test component is configured to control a hardware facility test 
-- on a physical (V35, X21, DS1, E1, DS3, E3 etc.) or a logical port.

mscLpHssiTest OBJECT IDENTIFIER ::= { mscLpHssi 2 }



mscLpHssiTestRowStatusTable OBJECT-TYPE
   SYNTAX     SEQUENCE OF MscLpHssiTestRowStatusEntry
   ACCESS     not-accessible
   STATUS     mandatory
   DESCRIPTION
     "This entry controls the addition and deletion of 
      mscLpHssiTest components."
::= { mscLpHssiTest 1 }

mscLpHssiTestRowStatusEntry OBJECT-TYPE
   SYNTAX     MscLpHssiTestRowStatusEntry
   ACCESS     not-accessible
   STATUS     mandatory
   DESCRIPTION
     "A single entry in the table represents a single 
      mscLpHssiTest component."
   INDEX {
      mscLpIndex,
      mscLpHssiIndex,
      mscLpHssiTestIndex }
::= { mscLpHssiTestRowStatusTable 1 }

MscLpHssiTestRowStatusEntry ::= SEQUENCE {
   mscLpHssiTestRowStatus
      RowStatus,
   mscLpHssiTestComponentName
      DisplayString,
   mscLpHssiTestStorageType
      StorageType,
   mscLpHssiTestIndex
      NonReplicated }

mscLpHssiTestRowStatus OBJECT-TYPE
   SYNTAX     RowStatus 
   ACCESS     read-only
   STATUS     mandatory
   DESCRIPTION
     "This variable is used as the basis for SNMP naming of
      mscLpHssiTest components.
      These components cannot be added nor deleted."
::= { mscLpHssiTestRowStatusEntry 1 }

mscLpHssiTestComponentName OBJECT-TYPE
   SYNTAX     DisplayString 
   ACCESS     read-only
   STATUS     mandatory
   DESCRIPTION
     "This variable provides the component's string name for
      use with the ASCII Console Interface"
::= { mscLpHssiTestRowStatusEntry 2 }

mscLpHssiTestStorageType OBJECT-TYPE
   SYNTAX     StorageType 
   ACCESS     read-only
   STATUS     mandatory
   DESCRIPTION
     "This variable represents the storage type value for the
      mscLpHssiTest tables."
::= { mscLpHssiTestRowStatusEntry 4 }

mscLpHssiTestIndex OBJECT-TYPE
   SYNTAX     NonReplicated 
   ACCESS     not-accessible
   STATUS     mandatory
   DESCRIPTION
     "This variable represents the index for the mscLpHssiTest tables."
::= { mscLpHssiTestRowStatusEntry 10 }

mscLpHssiTestStateTable OBJECT-TYPE
   SYNTAX     SEQUENCE OF MscLpHssiTestStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscLpHssiTest 10 }

mscLpHssiTestStateEntry OBJECT-TYPE
   SYNTAX     MscLpHssiTestStateEntry
   ACCESS     not-accessible
   STATUS     mandatory
   DESCRIPTION
     "An entry in the mscLpHssiTestStateTable."
   INDEX {
      mscLpIndex,
      mscLpHssiIndex,
      mscLpHssiTestIndex }
::= { mscLpHssiTestStateTable 1 }

MscLpHssiTestStateEntry ::= SEQUENCE {
   mscLpHssiTestAdminState
      INTEGER,
   mscLpHssiTestOperationalState
      INTEGER,
   mscLpHssiTestUsageState
      INTEGER }

mscLpHssiTestAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscLpHssiTestStateEntry 1 }

mscLpHssiTestOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscLpHssiTestStateEntry 2 }

mscLpHssiTestUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscLpHssiTestStateEntry 3 }

mscLpHssiTestSetupTable OBJECT-TYPE
   SYNTAX     SEQUENCE OF MscLpHssiTestSetupEntry
   ACCESS     not-accessible
   STATUS     mandatory
   DESCRIPTION
     "This group contains all of the operational data for a Test 
      component."
::= { mscLpHssiTest 11 }

mscLpHssiTestSetupEntry OBJECT-TYPE
   SYNTAX     MscLpHssiTestSetupEntry
   ACCESS     not-accessible
   STATUS     mandatory
   DESCRIPTION
     "An entry in the mscLpHssiTestSetupTable."
   INDEX {
      mscLpIndex,
      mscLpHssiIndex,
      mscLpHssiTestIndex }
::= { mscLpHssiTestSetupTable 1 }

MscLpHssiTestSetupEntry ::= SEQUENCE {
   mscLpHssiTestPurpose
      AsciiString,
   mscLpHssiTestType
      INTEGER,
   mscLpHssiTestFrmSize
      Unsigned32,
   mscLpHssiTestFrmPatternType
      INTEGER,
   mscLpHssiTestCustomizedPattern
      Hex,
   mscLpHssiTestDataStartDelay
      Unsigned32,
   mscLpHssiTestDisplayInterval
      Unsigned32,
   mscLpHssiTestDuration
      Unsigned32 }

mscLpHssiTestPurpose OBJECT-TYPE
   SYNTAX     AsciiString (SIZE (0..40))
   ACCESS     read-write
   STATUS     mandatory
   DESCRIPTION
     "This attribute records the purpose of the test so that the test results 
      can be associated and properly analyzed."
::= { mscLpHssiTestSetupEntry 1 }

mscLpHssiTestType OBJECT-TYPE
   SYNTAX     INTEGER  {
                 card(0),
                 manual(1),
                 localLoop(2),
                 remoteLoop(3),
                 externalLoop(4),
                 payloadLoop(5),
                 remoteLoopThisTrib(6),
                 v54RemoteLoop(7),
                 pn127RemoteLoop(8) }
   ACCESS     read-write
   STATUS     mandatory
   DESCRIPTION
     "This attribute is the type of test to be run. The available test types 
      include the following:
      card test sets up an internal loop on the board and runs a bit error 
      rate test.
      manual test assumes the line is looped back externally and a bit 
      error rate test is performed.
      localLoop test loops back the local modem and performs a bit error 
      rate test.
      remoteLoop test loops back the remote modem (or CSU) and 
      performs a bit error rate test.
      externalLoop test loops back the line to the far end.
      payloadLoop test only loops back the payload data received from 
      the incoming line.
      remoteLoopThisTrib loops this particular tributary back at the far 
      end, using services provided by the parent.
      v54RemoteLoop initiates a V.54 Remote Loopback test.
      pn127RemoteLoop initiates a PN127 Remote Loopback test.
      Note that not all test types are not supported by all function 
      processors."
   DEFVAL     { card }
::= { mscLpHssiTestSetupEntry 2 }

mscLpHssiTestFrmSize OBJECT-TYPE
   SYNTAX     Unsigned32 (4..4096)
   ACCESS     read-write
   STATUS     mandatory
   DESCRIPTION
     "This attribute defines the size of the test data frames in number of 
      bytes."
   DEFVAL     { 1024 }
::= { mscLpHssiTestSetupEntry 3 }

mscLpHssiTestFrmPatternType OBJECT-TYPE
   SYNTAX     INTEGER  {
                 ccitt32kBitPattern(0),
                 ccitt8MBitPattern(1),
                 customizedPattern(2) }
   ACCESS     read-write
   STATUS     mandatory
   DESCRIPTION
     "This attribute defines the type of data pattern generation to use. The 
      following lists the available pattern types:
      ccitt32kBitPattern is a pseudo-random sequence of 32 kbit.
      ccitt8MBitPattern is a pseudo-random sequence of 8Mbit.
      customizedPattern is the pattern defined in the customizedPattern 
      attribute."
   DEFVAL     { ccitt32kBitPattern }
::= { mscLpHssiTestSetupEntry 4 }

mscLpHssiTestCustomizedPattern OBJECT-TYPE
   SYNTAX     Hex (0..4294967295)
   ACCESS     read-write
   STATUS     mandatory
   DESCRIPTION
     "This attribute allows a customized 32 bit pattern to be defined for 
      use in the test data frames. This attribute is used when the attribute 
      frmPatternType is set to CustomizedPattern. Note that a 55 hex 
      pattern is an alternating 1 and 0 pattern."
   DEFVAL     { 1431655765 }
::= { mscLpHssiTestSetupEntry 5 }

mscLpHssiTestDataStartDelay OBJECT-TYPE
   SYNTAX     Unsigned32 (0..1814400)
   ACCESS     read-write
   STATUS     mandatory
   DESCRIPTION
     "This attribute specifies the time delay (in seconds) between when 
      the test expects the loop to have been set up, to when the test data 
      actually starts to be transmitted. This attribute is to accommodate 
      some non-standard equipment that requires extra time for setting up 
      a requested loop.
      This attribute is ignored when the test type is set to externalLoop."
   DEFVAL     { 0 }
::= { mscLpHssiTestSetupEntry 6 }

mscLpHssiTestDisplayInterval OBJECT-TYPE
   SYNTAX     Unsigned32 (0..30240)
   ACCESS     read-write
   STATUS     mandatory
   DESCRIPTION
     "This attribute defines the interval (in minutes) between which 
      interim test results are to be displayed. Results are displayed at the 
      operator console at which the test was started. When the test type is 
      set to externalLoop, this attribute is ignored. There will be no 
      display of results if displayInterval is set to 0. This attribute can be 
      changed anytime."
   DEFVAL     { 5 }
::= { mscLpHssiTestSetupEntry 7 }

mscLpHssiTestDuration OBJECT-TYPE
   SYNTAX     Unsigned32 (1..30240)
   ACCESS     read-write
   STATUS     mandatory
   DESCRIPTION
     "This attribute is the duration (in minutes) that test data will be 
      transmitted. In the case of an externalLoop, this is the time that the 
      loop is in effect. Note that dataStartDelay does not apply to the 
      externalLoop."
   DEFVAL     { 1 }
::= { mscLpHssiTestSetupEntry 8 }

mscLpHssiTestResultsTable OBJECT-TYPE
   SYNTAX     SEQUENCE OF MscLpHssiTestResultsEntry
   ACCESS     not-accessible
   STATUS     mandatory
   DESCRIPTION
     "This group contains all the statistics related attributes of the Test 
      component."
::= { mscLpHssiTest 12 }

mscLpHssiTestResultsEntry OBJECT-TYPE
   SYNTAX     MscLpHssiTestResultsEntry
   ACCESS     not-accessible
   STATUS     mandatory
   DESCRIPTION
     "An entry in the mscLpHssiTestResultsTable."
   INDEX {
      mscLpIndex,
      mscLpHssiIndex,
      mscLpHssiTestIndex }
::= { mscLpHssiTestResultsTable 1 }

MscLpHssiTestResultsEntry ::= SEQUENCE {
   mscLpHssiTestElapsedTime
      Counter32,
   mscLpHssiTestTimeRemaining
      Unsigned32,
   mscLpHssiTestCauseOfTermination
      INTEGER,
   mscLpHssiTestBitsTx
      PassportCounter64,
   mscLpHssiTestBytesTx
      PassportCounter64,
   mscLpHssiTestFrmTx
      PassportCounter64,
   mscLpHssiTestBitsRx
      PassportCounter64,
   mscLpHssiTestBytesRx
      PassportCounter64,
   mscLpHssiTestFrmRx
      PassportCounter64,
   mscLpHssiTestErroredFrmRx
      PassportCounter64,
   mscLpHssiTestBitErrorRate
      AsciiString }

mscLpHssiTestElapsedTime OBJECT-TYPE
   SYNTAX     Counter32 
   ACCESS     read-only
   STATUS     mandatory
   DESCRIPTION
     "This attribute is the number of minutes elapsed since the test started 
      for an externalLoop test. For a data test, this is the time since test 
      data was first transmitted."
::= { mscLpHssiTestResultsEntry 1 }

mscLpHssiTestTimeRemaining OBJECT-TYPE
   SYNTAX     Unsigned32 (0..4294967295)
   ACCESS     read-only
   STATUS     mandatory
   DESCRIPTION
     "This attribute is the number of minutes remaining before the test is 
      to be stopped according to the duration attribute."
   DEFVAL     { 0 }
::= { mscLpHssiTestResultsEntry 2 }

mscLpHssiTestCauseOfTermination OBJECT-TYPE
   SYNTAX     INTEGER  {
                 testTimeExpired(0),
                 stoppedByOperator(1),
                 unknown(2),
                 neverStarted(3),
                 testRunning(4),
                 hardwareReconfigured(5),
                 loopCodeSyncFailed(6),
                 patternSyncFailed(7),
                 patternSyncLost(8) }
   ACCESS     read-only
   STATUS     mandatory
   DESCRIPTION
     "This attribute indicates either the status of the test or the cause of 
      the test's termination:
      
      neverStarted indicates that the test has not yet been started.
      
      testRunning indicates that the test has been started.
      
      stoppedByOperator indicates that the operator issued a stop 
      command on a test that was running.
      
      testTimeExpired indicates that the test ran for the time specified by 
      the test's duration.
      
      loopCodeSyncFailed indicates that the local end failed to 
      synchronize to the loopCode pattern. The local end transmits the 
      loopCode pattern to cause the remote end to apply a loopback, after 
      which the local end should receive the loopCode pattern. The exact 
      pattern used to request loopCode depends on the test type. This 
      failure indicates a high rate of transmission errors, or that the 
      remote end has failed to apply the loopback.
      
      patternSyncFailed indicates that the local end failed to synchronize 
      to the frmPatternType test pattern, that should have been looped 
      back at the remote end. This failure indicates a high rate of 
      transmission errors or the absence of a loopback.
      
      patternSyncLost indicates that the local end gained and then lost 
      synchronization to the returned frmPatternType test pattern. This 
      failure indicates a sudden increase in transmission errors, frame 
      slippage, or the removal of an existing loopback.
      
      unknown is set when a reason to terminate other than those listed 
      here is encountered.
      
      Note: Only MSA cards support recognition of the failures 
      loopCodeSyncFailed, patternSyncFailed and patternSyncLost. 
      Other cards will not terminate the test under the conditions 
      described by these values."
   DEFVAL     { neverStarted }
::= { mscLpHssiTestResultsEntry 3 }

mscLpHssiTestBitsTx OBJECT-TYPE
   SYNTAX     PassportCounter64 
   ACCESS     read-only
   STATUS     mandatory
   DESCRIPTION
     "This attribute is the total number of bits sent during the test period. 
      As long as the line speed of the hardware interface is less than 
      70 Mbit/s, this counter is not expected to reach the maximum value."
::= { mscLpHssiTestResultsEntry 4 }

mscLpHssiTestBytesTx OBJECT-TYPE
   SYNTAX     PassportCounter64 
   ACCESS     read-only
   STATUS     mandatory
   DESCRIPTION
     "This attribute is the total number of bytes sent during the test 
      period. This counter is not expected to reach its maximum value."
::= { mscLpHssiTestResultsEntry 5 }

mscLpHssiTestFrmTx OBJECT-TYPE
   SYNTAX     PassportCounter64 
   ACCESS     read-only
   STATUS     mandatory
   DESCRIPTION
     "This attribute is the total number of frames sent during the test 
      period. This counter is not expected to reach its maximum value."
::= { mscLpHssiTestResultsEntry 6 }

mscLpHssiTestBitsRx OBJECT-TYPE
   SYNTAX     PassportCounter64 
   ACCESS     read-only
   STATUS     mandatory
   DESCRIPTION
     "This attribute is the total number of bits received during the test 
      period. This counter is not expected to reach its maximum value. 
      The counter will wrap around to 0 if it does reach the maximum 
      value."
::= { mscLpHssiTestResultsEntry 7 }

mscLpHssiTestBytesRx OBJECT-TYPE
   SYNTAX     PassportCounter64 
   ACCESS     read-only
   STATUS     mandatory
   DESCRIPTION
     "This attribute is the total number of bytes received during the test 
      period. This counter is not expected to reach its maximum value. 
      The counter will wrap around to 0 if it does reach its maximum 
      value."
::= { mscLpHssiTestResultsEntry 8 }

mscLpHssiTestFrmRx OBJECT-TYPE
   SYNTAX     PassportCounter64 
   ACCESS     read-only
   STATUS     mandatory
   DESCRIPTION
     "This attribute is the total number of frames received during the test 
      period. This counter is not expected to reach its maximum value. 
      The counter will wrap around to 0 if it does reach its maximum 
      value."
::= { mscLpHssiTestResultsEntry 9 }

mscLpHssiTestErroredFrmRx OBJECT-TYPE
   SYNTAX     PassportCounter64 
   ACCESS     read-only
   STATUS     mandatory
   DESCRIPTION
     "This attribute is not displayed for ATM cards because the physical 
      layer drops all errored frames at the controller interface. 
      
      For all other card types, this attribute is the total number of errored 
      frames received during the test period. This counter is not expected 
      to reach its maximum value. The counter will wrap around to 0 if it 
      does reach its maximum value."
::= { mscLpHssiTestResultsEntry 10 }

mscLpHssiTestBitErrorRate OBJECT-TYPE
   SYNTAX     AsciiString (SIZE (5))
   ACCESS     read-only
   STATUS     mandatory
   DESCRIPTION
     "This attribute is not displayed for ATM cards because the physical 
      layer drops all errored frames at the controller interface. 
      
      For all other card types, this attribute is the calculated bit error rate 
      on the link. Test data are generated and sent in frames of a preset 
      size (frameSize). The Test component will try to estimate the 
      number of bit errors in any errored frame which is identifiable. The 
      statistics will be updated accordingly. A lost frame (may be due to 
      an error on the flag sequence) will be discarded for the bit error rate 
      calculation. The result is presented in the form of xEsyy, where x is 
      the mantissa, syy is the exponent, for example 0E+00, 2E-09.
      Note that the bitErrorRate is an estimate only. For more reliable test 
      results, the test should be done over a long period. Multiple tests 
      would also improve the confidence level of the test results."
::= { mscLpHssiTestResultsEntry 11 }


-- Lp Engineering
-- This component has various subcomponents which hold 
-- engineering/control parameters and corresponding indicator 
-- statistics for this LP. The subcomponents can be defined for selected 
-- services or be common to a number of services.
-- 
-- This component has no data of its own.

mscLpEng OBJECT IDENTIFIER ::= { mscLp 23 }



mscLpEngRowStatusTable OBJECT-TYPE
   SYNTAX     SEQUENCE OF MscLpEngRowStatusEntry
   ACCESS     not-accessible
   STATUS     mandatory
   DESCRIPTION
     "This entry controls the addition and deletion of 
      mscLpEng components."
::= { mscLpEng 1 }

mscLpEngRowStatusEntry OBJECT-TYPE
   SYNTAX     MscLpEngRowStatusEntry
   ACCESS     not-accessible
   STATUS     mandatory
   DESCRIPTION
     "A single entry in the table represents a single 
      mscLpEng component."
   INDEX {
      mscLpIndex,
      mscLpEngIndex }
::= { mscLpEngRowStatusTable 1 }

MscLpEngRowStatusEntry ::= SEQUENCE {
   mscLpEngRowStatus
      RowStatus,
   mscLpEngComponentName
      DisplayString,
   mscLpEngStorageType
      StorageType,
   mscLpEngIndex
      NonReplicated }

mscLpEngRowStatus OBJECT-TYPE
   SYNTAX     RowStatus 
   ACCESS     read-only
   STATUS     mandatory
   DESCRIPTION
     "This variable is used as the basis for SNMP naming of
      mscLpEng components.
      These components cannot be added nor deleted."
::= { mscLpEngRowStatusEntry 1 }

mscLpEngComponentName OBJECT-TYPE
   SYNTAX     DisplayString 
   ACCESS     read-only
   STATUS     mandatory
   DESCRIPTION
     "This variable provides the component's string name for
      use with the ASCII Console Interface"
::= { mscLpEngRowStatusEntry 2 }

mscLpEngStorageType OBJECT-TYPE
   SYNTAX     StorageType 
   ACCESS     read-only
   STATUS     mandatory
   DESCRIPTION
     "This variable represents the storage type value for the
      mscLpEng tables."
::= { mscLpEngRowStatusEntry 4 }

mscLpEngIndex OBJECT-TYPE
   SYNTAX     NonReplicated 
   ACCESS     not-accessible
   STATUS     mandatory
   DESCRIPTION
     "This variable represents the index for the mscLpEng tables."
::= { mscLpEngRowStatusEntry 10 }


-- Lp Eng DataStream/<type>
-- This component holds engineering parameters used by DCS on this 
-- LP for a particular DCS stream.

mscLpEngDs OBJECT IDENTIFIER ::= { mscLpEng 2 }



mscLpEngDsRowStatusTable OBJECT-TYPE
   SYNTAX     SEQUENCE OF MscLpEngDsRowStatusEntry
   ACCESS     not-accessible
   STATUS     mandatory
   DESCRIPTION
     "This entry controls the addition and deletion of 
      mscLpEngDs components."
::= { mscLpEngDs 1 }

mscLpEngDsRowStatusEntry OBJECT-TYPE
   SYNTAX     MscLpEngDsRowStatusEntry
   ACCESS     not-accessible
   STATUS     mandatory
   DESCRIPTION
     "A single entry in the table represents a single 
      mscLpEngDs component."
   INDEX {
      mscLpIndex,
      mscLpEngIndex,
      mscLpEngDsIndex }
::= { mscLpEngDsRowStatusTable 1 }

MscLpEngDsRowStatusEntry ::= SEQUENCE {
   mscLpEngDsRowStatus
      RowStatus,
   mscLpEngDsComponentName
      DisplayString,
   mscLpEngDsStorageType
      StorageType,
   mscLpEngDsIndex
      INTEGER }

mscLpEngDsRowStatus OBJECT-TYPE
   SYNTAX     RowStatus 
   ACCESS     read-write
   STATUS     mandatory
   DESCRIPTION
     "This variable is used as the basis for SNMP naming of
      mscLpEngDs components.
      These components can be added and deleted."
::= { mscLpEngDsRowStatusEntry 1 }

mscLpEngDsComponentName OBJECT-TYPE
   SYNTAX     DisplayString 
   ACCESS     read-only
   STATUS     mandatory
   DESCRIPTION
     "This variable provides the component's string name for
      use with the ASCII Console Interface"
::= { mscLpEngDsRowStatusEntry 2 }

mscLpEngDsStorageType OBJECT-TYPE
   SYNTAX     StorageType 
   ACCESS     read-only
   STATUS     mandatory
   DESCRIPTION
     "This variable represents the storage type value for the
      mscLpEngDs tables."
::= { mscLpEngDsRowStatusEntry 4 }

mscLpEngDsIndex OBJECT-TYPE
   SYNTAX     INTEGER  {
                 accounting(0),
                 alarm(1),
                 log(2),
                 debug(3),
                 scn(4),
                 trap(5),
                 stats(6) }
   ACCESS     not-accessible
   STATUS     mandatory
   DESCRIPTION
     "This variable represents the index for the mscLpEngDs tables."
::= { mscLpEngDsRowStatusEntry 10 }

mscLpEngDsOperTable OBJECT-TYPE
   SYNTAX     SEQUENCE OF MscLpEngDsOperEntry
   ACCESS     not-accessible
   STATUS     mandatory
   DESCRIPTION
     "This group contains operational attributes for the DataStream 
      components under Lp Engineering."
::= { mscLpEngDs 10 }

mscLpEngDsOperEntry OBJECT-TYPE
   SYNTAX     MscLpEngDsOperEntry
   ACCESS     not-accessible
   STATUS     mandatory
   DESCRIPTION
     "An entry in the mscLpEngDsOperTable."
   INDEX {
      mscLpIndex,
      mscLpEngIndex,
      mscLpEngDsIndex }
::= { mscLpEngDsOperTable 1 }

MscLpEngDsOperEntry ::= SEQUENCE {
   mscLpEngDsAgentQueueSize
      Unsigned32 }

mscLpEngDsAgentQueueSize OBJECT-TYPE
   SYNTAX     Unsigned32 (0..4294967295)
   ACCESS     read-only
   STATUS     mandatory
   DESCRIPTION
     "This attribute indicates the maximum size of the DCS Agent queue 
      size maximum for a DCS data stream on the LP. It is the maximum 
      size to which the Agent's currentQueueSize can grow. When the 
      queue is full and more data is offered to the Agent, it will be 
      discarded.
      The following are the system defaults (in number of records):
      - alarm: 100
      - accounting: 10000
      - debug: 0
      - log: 50
      - scn: 200
      - trap: 50
      - stats: 0
      To override the system defaults, see Lp Eng Ds Ov's 
      agentQueueSize attribute."
::= { mscLpEngDsOperEntry 1 }


-- Lp Eng Ds/<type> Override
-- This component holds provisionable engineering parameters used 
-- by DCS on this LP for a particular DCS stream.

mscLpEngDsOv OBJECT IDENTIFIER ::= { mscLpEngDs 2 }



mscLpEngDsOvRowStatusTable OBJECT-TYPE
   SYNTAX     SEQUENCE OF MscLpEngDsOvRowStatusEntry
   ACCESS     not-accessible
   STATUS     mandatory
   DESCRIPTION
     "This entry controls the addition and deletion of 
      mscLpEngDsOv components."
::= { mscLpEngDsOv 1 }

mscLpEngDsOvRowStatusEntry OBJECT-TYPE
   SYNTAX     MscLpEngDsOvRowStatusEntry
   ACCESS     not-accessible
   STATUS     mandatory
   DESCRIPTION
     "A single entry in the table represents a single 
      mscLpEngDsOv component."
   INDEX {
      mscLpIndex,
      mscLpEngIndex,
      mscLpEngDsIndex,
      mscLpEngDsOvIndex }
::= { mscLpEngDsOvRowStatusTable 1 }

MscLpEngDsOvRowStatusEntry ::= SEQUENCE {
   mscLpEngDsOvRowStatus
      RowStatus,
   mscLpEngDsOvComponentName
      DisplayString,
   mscLpEngDsOvStorageType
      StorageType,
   mscLpEngDsOvIndex
      NonReplicated }

mscLpEngDsOvRowStatus OBJECT-TYPE
   SYNTAX     RowStatus 
   ACCESS     read-write
   STATUS     mandatory
   DESCRIPTION
     "This variable is used as the basis for SNMP naming of
      mscLpEngDsOv components.
      These components can be added and deleted."
::= { mscLpEngDsOvRowStatusEntry 1 }

mscLpEngDsOvComponentName OBJECT-TYPE
   SYNTAX     DisplayString 
   ACCESS     read-only
   STATUS     mandatory
   DESCRIPTION
     "This variable provides the component's string name for
      use with the ASCII Console Interface"
::= { mscLpEngDsOvRowStatusEntry 2 }

mscLpEngDsOvStorageType OBJECT-TYPE
   SYNTAX     StorageType 
   ACCESS     read-only
   STATUS     mandatory
   DESCRIPTION
     "This variable represents the storage type value for the
      mscLpEngDsOv tables."
::= { mscLpEngDsOvRowStatusEntry 4 }

mscLpEngDsOvIndex OBJECT-TYPE
   SYNTAX     NonReplicated 
   ACCESS     not-accessible
   STATUS     mandatory
   DESCRIPTION
     "This variable represents the index for the mscLpEngDsOv tables."
::= { mscLpEngDsOvRowStatusEntry 10 }

mscLpEngDsOvProvTable OBJECT-TYPE
   SYNTAX     SEQUENCE OF MscLpEngDsOvProvEntry
   ACCESS     not-accessible
   STATUS     mandatory
   DESCRIPTION
     "This group contains provisionable attributes for the DataStream Ov 
      components under Lp Engineering.
      DESCRIPTION"
::= { mscLpEngDsOv 10 }

mscLpEngDsOvProvEntry OBJECT-TYPE
   SYNTAX     MscLpEngDsOvProvEntry
   ACCESS     not-accessible
   STATUS     mandatory
   DESCRIPTION
     "An entry in the mscLpEngDsOvProvTable."
   INDEX {
      mscLpIndex,
      mscLpEngIndex,
      mscLpEngDsIndex,
      mscLpEngDsOvIndex }
::= { mscLpEngDsOvProvTable 1 }

MscLpEngDsOvProvEntry ::= SEQUENCE {
   mscLpEngDsOvAgentQueueSize
      Unsigned32 }

mscLpEngDsOvAgentQueueSize OBJECT-TYPE
   SYNTAX     Unsigned32 (0..4294967295)
   ACCESS     read-write
   STATUS     mandatory
   DESCRIPTION
     "This attribute specifies the maximum size of the DCS Agent's 
      queue for this data stream on this LP. For more details on the 
      defaults and other information, refer to the parent component's 
      agentQueueSize attribute.
      The size should be set to 0 if absolutely no data is to be accepted 
      from applications. There are threshold alarms based on the value of 
      the Agent's currentQueueSize attribute (a Set when the queue 
      becomes 75% full and a Clear after dropping back to 50% full).
      To properly determine what to set this to, consult the 'Magellan 
      Passport Engineering Notes and Guidelines'."
::= { mscLpEngDsOvProvEntry 1 }




-- 
-- Version and Compliance statements
-- 



-- Object-Group Statement:
-- A list of all current accessible leaf objects.

-- OBJECTS { mscLpDS1ChanOperationalState,
--           mscLpE1ChanUsageState,
--           mscLpSonetFarEndLineFailures,
--           mscLpJT2LosAlarm,
--           mscLpDS3RunningTime,
--           mscLpMemoryUsageAvgValue,
--           mscLpDS3CBitFarEndSevErroredSec,
--           mscLpDS3DS1ChanTestFrmTx,
--           mscLpHssiCommentText,
--           mscLpDS3Mapping,
--           mscLpDS3DS1ChanUnknownStatus,
--           mscLpSonetRowStatus,
--           mscLpDS1ChanTestBitsRx,
--           mscLpStandbyStatus,
--           mscLpDS3DS1ChanTestDataStartDelay,
--           mscLpE3PathCodeViolations,
--           mscLpE3PlcpUnavailSec,
--           mscLpDS1ChanTestStorageType,
--           mscLpHssiControlStatus,
--           mscLpE1ChanCellUncorrectableHecErrors,
--           mscLpE3CellScrambleCellPayload,
--           mscLpE1ChanTestFrmSize,
--           mscLpSonetPathControlStatus,
--           mscLpSdhPathLopAlarm,
--           mscLpX21Vendor,
--           mscLpDS3DS1SevErroredFrmSec,
--           mscLpDS1RunningTime,
--           mscLpJT2CellRowStatus,
--           mscLpJT2RowStatus,
--           mscLpDS3PathErroredSec,
--           mscLpDS3DS1ChanTestFrmRx,
--           mscLpDS3DS1Vendor,
--           mscLpE3CellStorageType,
--           mscLpSonetTxAis,
--           mscLpE3PlcpRowStatus,
--           mscLpE3OperationalState,
--           mscLpDS3CBitFarEndSefAisSec,
--           mscLpDS3DS1ChanCustomerIdentifier,
--           mscLpDS3CellSevErroredSec,
--           mscLpE3PlcpFarEndErrorFreeSec,
--           mscLpE1ChanTcEgressConditioning,
--           mscLpE3TestErroredFrmRx,
--           mscLpJT2TestElapsedTime,
--           mscLpE1ChanTestBitErrorRate,
--           mscLpE3LosAlarm,
--           mscLpE3LinkAlarmScanInterval,
--           mscLpSdhLineFailures,
--           mscLpDS3DS1OperationalState,
--           mscLpSonetTestRowStatus,
--           mscLpHssiLinkMode,
--           mscLpSonetPathFarEndPathSevErroredSec,
--           mscLpE3TestCauseOfTermination,
--           mscLpV35StorageType,
--           mscLpSdhTestBitsRx,
--           mscLpDS3DS1ChanTimeslots,
--           mscLpDS3DS1TestBitsTx,
--           mscLpLocalMsgBlockUsageAvg,
--           mscLpSonetPathPathSevErroredSec,
--           mscLpMemoryCapacityValue,
--           mscLpX21DataXferStateChanges,
--           mscLpE1TestErroredFrmRx,
--           mscLpE1TxRaiAlarm,
--           mscLpDS3PlcpRxRaiAlarm,
--           mscLpE1LosAlarm,
--           mscLpHssiTestBytesTx,
--           mscLpSonetPathSignalLabelMismatch,
--           mscLpJT2AvailabilityStatus,
--           mscLpE3LineCodeViolations,
--           mscLpDS1ChanTestElapsedTime,
--           mscLpSdhSnmpOperStatus,
--           mscLpHssiIfAdminStatus,
--           mscLpDS1ChanActualChannelSpeed,
--           mscLpMemoryUsageValue,
--           mscLpX21TestOperationalState,
--           mscLpE3G832TrailTraceReceived,
--           mscLpSdhPathCellCorrectableHeaderErrors,
--           mscLpDS3DS1TestOperationalState,
--           mscLpSonetPathCellStorageType,
--           mscLpDS1ChanCellCorrectSingleBitHeaderErrors,
--           mscLpE3IfAdminStatus,
--           mscLpDS1IfIndex,
--           mscLpJT2StandbyStatus,
--           mscLpDS1ChanTimeslotDataRate,
--           mscLpSonetPathStorageType,
--           mscLpE1ChanTestType,
--           mscLpV35TestOperationalState,
--           mscLpDS3RowStatus,
--           mscLpDS1TestElapsedTime,
--           mscLpE1RaiClearAlarmTime,
--           mscLpDS1AlarmStatus,
--           mscLpDS3DS1ChanCellScrambleCellPayload,
--           mscLpE3LineErroredSec,
--           mscLpE1ChanTestBytesTx,
--           mscLpE3ControlStatus,
--           mscLpDS1ChanTestCustomizedPattern,
--           mscLpE3TestFrmRx,
--           mscLpV35TestBytesTx,
--           mscLpDS3CBitComponentName,
--           mscLpSonetFarEndLineErroredSec,
--           mscLpDS1RaiAlarmType,
--           mscLpV35TestCustomizedPattern,
--           mscLpE1ChanCommentText,
--           mscLpSdhVendor,
--           mscLpE3LinkAlarmActivationThreshold,
--           mscLpDS3PlcpFarEndErroredSec,
--           mscLpE1ChanTestStorageType,
--           mscLpE1Vendor,
--           mscLpLocalMsgBlockCapacity,
--           mscLpSdhRxAisAlarm,
--           mscLpJT2UnknownStatus,
--           mscLpScheduledSwitchover,
--           mscLpDS1RowStatus,
--           mscLpJT2SevErroredSec,
--           mscLpDS3DS1ChanTestErroredFrmRx,
--           mscLpDS1ChanTestBytesRx,
--           mscLpE1FrmErrors,
--           mscLpSdhPathFarEndPathSevErroredSec,
--           mscLpDS3PlcpErroredSec,
--           mscLpDS3DS1ChanCellLcdAlarm,
--           mscLpE1ControlStatus,
--           mscLpJT2TestBytesTx,
--           mscLpV35TestBytesRx,
--           mscLpE1ChanTestDisplayInterval,
--           mscLpDS3PlcpSevErroredFramingSec,
--           mscLpDS3CellComponentName,
--           mscLpE1SevErroredSec,
--           mscLpDS3DS1ChanTcReplacementData,
--           mscLpLocalMsgBlockUsage,
--           mscLpV35LineSpeed,
--           mscLpDS3DS1ChanTestCauseOfTermination,
--           mscLpDS3DS1TestBitErrorRate,
--           mscLpDS3TestRowStatus,
--           mscLpJT2TxAisPhysicalAlarm,
--           mscLpDS3CBitCbitErrorFreeSec,
--           mscLpE1ChanAdminState,
--           mscLpMainCard,
--           mscLpE3CellCorrectableHeaderErrors,
--           mscLpDS3AvailabilityStatus,
--           mscLpX21TestBytesTx,
--           mscLpSonetUnknownStatus,
--           mscLpSonetCommentText,
--           mscLpDS3DS1AdminState,
--           mscLpDS3TestErroredFrmRx,
--           mscLpX21TestCustomizedPattern,
--           mscLpDS3ClockingSource,
--           mscLpHssiTestTimeRemaining,
--           mscLpDS3DS1TestBytesRx,
--           mscLpSdhTestBitErrorRate,
--           mscLpDS3CBitFarEndCodeViolations,
--           mscLpEngStorageType,
--           mscLpDS3DS1TestCustomizedPattern,
--           mscLpE1AudioComponentName,
--           mscLpDS3CellRowStatus,
--           mscLpDS3PlcpStorageType,
--           mscLpJT2CustomerIdentifier,
--           mscLpDS1TestRowStatus,
--           mscLpSonetSectFailures,
--           mscLpDS3UsageState,
--           mscLpSonetTestFrmRx,
--           mscLpDS1AvailabilityStatus,
--           mscLpV35TestPurpose,
--           mscLpDS1ChanTcSigOneValue,
--           mscLpHssiReadyLineState,
--           mscLpSonetTestDuration,
--           mscLpX21LineSpeed,
--           mscLpSonetCustomerIdentifier,
--           mscLpE1TestElapsedTime,
--           mscLpSdhPathStorageType,
--           mscLpX21IfAdminStatus,
--           mscLpJT2TestFrmTx,
--           mscLpDS1ChanCellTransmitCellUtilization,
--           mscLpE1ChanTestAdminState,
--           mscLpJT2TestFrmRx,
--           mscLpHssiSnmpOperStatus,
--           mscLpHssiApplicationFramerName,
--           mscLpDS3DS1IfAdminStatus,
--           mscLpE1ChanTestTimeRemaining,
--           mscLpDS3PathSevErroredSec,
--           mscLpDS3PathUnavailSec,
--           mscLpDS3DS1ChanControlStatus,
--           mscLpJT2TestDuration,
--           mscLpSdhPathStandbyStatus,
--           mscLpCpuUtilAvgMax,
--           mscLpEngDsAgentQueueSize,
--           mscLpEngDsOvComponentName,
--           mscLpJT2TestBytesRx,
--           mscLpE3TestBitErrorRate,
--           mscLpDS1LineType,
--           mscLpE1ChanAlarmStatus,
--           mscLpE3LofAlarm,
--           mscLpE1ChanFlmHdlcMonitoring,
--           mscLpHssiStorageType,
--           mscLpX21TestPurpose,
--           mscLpX21EnableDynamicSpeed,
--           mscLpDS1ChanTestFrmPatternType,
--           mscLpE3CellAlarmActDelay,
--           mscLpSdhPathFarEndPathFailures,
--           mscLpSonetSectCodeViolations,
--           mscLpDS3DS1TestPurpose,
--           mscLpDS3DS1RxAisAlarm,
--           mscLpE3CellRowStatus,
--           mscLpE1ChanTestPurpose,
--           mscLpSdhPathApplicationFramerName,
--           mscLpV35TestFrmPatternType,
--           mscLpV35ProceduralStatus,
--           mscLpSonetPathCellSevErroredSec,
--           mscLpDS1ChanCellReceiveCellUtilization,
--           mscLpE1ProceduralStatus,
--           mscLpJT2FrameErrors,
--           mscLpOperationalState,
--           mscLpE1LofAlarm,
--           mscLpDS3StandbyStatus,
--           mscLpHssiTestBitsRx,
--           mscLpDS3DS1ChanCellCorrectableHeaderErrors,
--           mscLpDS1ChanComponentName,
--           mscLpDS3TestFrmTx,
--           mscLpX21RowStatus,
--           mscLpSdhPathCustomerIdentifier,
--           mscLpDS3DS1ChanTestElapsedTime,
--           mscLpDS3UnknownStatus,
--           mscLpDS1SevErroredFrmSec,
--           mscLpV35ComponentName,
--           mscLpDS3TestDataStartDelay,
--           mscLpE1ChanTcSigTwoValue,
--           mscLpSonetSectErroredSec,
--           mscLpJT2ErrorFreeSec,
--           mscLpSonetTestDisplayInterval,
--           mscLpE3G832RowStatus,
--           mscLpHssiUsageState,
--           mscLpSonetPathIfIndex,
--           mscLpDS3TestElapsedTime,
--           mscLpHssiTestFrmPatternType,
--           mscLpE1ChanCellSevErroredSec,
--           mscLpE3StandbyStatus,
--           mscLpJT2RxAisPhysicalAlarm,
--           mscLpX21TestFrmPatternType,
--           mscLpHssiVendor,
--           mscLpSdhPathPathFailures,
--           mscLpDS3TestFrmRx,
--           mscLpJT2CellScrambleCellPayload,
--           mscLpDS3DS1TestFrmPatternType,
--           mscLpDS1UnknownStatus,
--           mscLpSonetErrorFreeSec,
--           mscLpSonetTestErroredFrmRx,
--           mscLpDS3TestDuration,
--           mscLpDS3CustomerIdentifier,
--           mscLpSonetLosAlarm,
--           mscLpE3AdminState,
--           mscLpRestartOnCpSwitch,
--           mscLpSonetPathCustomerIdentifier,
--           mscLpDS1ChanTestComponentName,
--           mscLpSdhIfAdminStatus,
--           mscLpSdhTestFrmPatternType,
--           mscLpDS3CBitFarEndErroredSec,
--           mscLpE1StandbyStatus,
--           mscLpE1ChanFlmABitMonitoring,
--           mscLpSonetTestCauseOfTermination,
--           mscLpHssiDataTransferLineState,
--           mscLpV35TestComponentName,
--           mscLpDS1TestFrmRx,
--           mscLpDS3DS1ChanProceduralStatus,
--           mscLpDS3DS1ComponentName,
--           mscLpE1CrcErrors,
--           mscLpJT2TestBitsTx,
--           mscLpLinkToApplicationsValue,
--           mscLpHssiTestAdminState,
--           mscLpSonetFarEndLineCodeViolations,
--           mscLpDS1TestDuration,
--           mscLpDS3TxAis,
--           mscLpLogicalProcessorType,
--           mscLpEngRowStatus,
--           mscLpE3TestBitsTx,
--           mscLpDS3DS1ChanCellAlarmActDelay,
--           mscLpDS3DS1ChanTestBitsTx,
--           mscLpDS1TestDataStartDelay,
--           mscLpE3G832FarEndSevErroredSec,
--           mscLpSdhAdminState,
--           mscLpDS3TxRai,
--           mscLpJT2BpvErrors,
--           mscLpJT2TestComponentName,
--           mscLpV35TestDisplayInterval,
--           mscLpDS3CBitFarEndUnavailSec,
--           mscLpE1ChanRowStatus,
--           mscLpE3PathFailures,
--           mscLpSonetPathCellComponentName,
--           mscLpX21TestComponentName,
--           mscLpE1LosStateChanges,
--           mscLpSdhFarEndLineErrorFreeSec,
--           mscLpDS3CBitStorageType,
--           mscLpHssiStandbyStatus,
--           mscLpSonetAvailabilityStatus,
--           mscLpJT2TestUsageState,
--           mscLpSonetPathFarEndPathErroredSec,
--           mscLpDS3DS1TestComponentName,
--           mscLpSonetPathAvailabilityStatus,
--           mscLpDS3PathCodeViolations,
--           mscLpE3ErrorFreeSec,
--           mscLpSonetRunningTime,
--           mscLpSonetControlStatus,
--           mscLpSonetClockingSource,
--           mscLpDS1ChanCellUncorrectableHecErrors,
--           mscLpDS3CellScrambleCellPayload,
--           mscLpDS1ChanCellLcdAlarm,
--           mscLpHssiComponentName,
--           mscLpSonetPathPathErroredSec,
--           mscLpDS3DS1ChanStandbyStatus,
--           mscLpV35TestFrmSize,
--           mscLpDS3DS1ChanTestBitsRx,
--           mscLpE1TestBitsRx,
--           mscLpDS3CellStorageType,
--           mscLpDS1TestFrmTx,
--           mscLpDS3PlcpRowStatus,
--           mscLpE1ChanCellComponentName,
--           mscLpDS1ChanTestUsageState,
--           mscLpE1ErrorFreeSec,
--           mscLpE1ChanTcIngressConditioning,
--           mscLpE1ChanTestRowStatus,
--           mscLpX21UsageState,
--           mscLpDS3LosAlarm,
--           mscLpE1ChanAvailabilityStatus,
--           mscLpV35TestUsageState,
--           mscLpDS3DS1ChanApplicationFramerName,
--           mscLpDS1TestDisplayInterval,
--           mscLpDS3DS1TxAisAlarm,
--           mscLpX21TestStorageType,
--           mscLpMsgBlockUsageAvgMax,
--           mscLpE1TestCauseOfTermination,
--           mscLpDS3TestCauseOfTermination,
--           mscLpE1AudioStorageType,
--           mscLpCpuUtilAvg,
--           mscLpSonetPathPathUnavailSec,
--           mscLpSdhComponentName,
--           mscLpDS3DS1TxRaiAlarm,
--           mscLpE3CellComponentName,
--           mscLpSonetTestElapsedTime,
--           mscLpX21TestFrmSize,
--           mscLpSdhTestDataStartDelay,
--           mscLpDS1TestErroredFrmRx,
--           mscLpDS1LosAlarm,
--           mscLpX21TestFrmTx,
--           mscLpDS3DS1TestFrmSize,
--           mscLpE3CustomerIdentifier,
--           mscLpJT2CellCorrectableHeaderErrors,
--           mscLpDS3DS1ZeroCoding,
--           mscLpDS3LineCodeViolations,
--           mscLpDS1ErroredSec,
--           mscLpHssiLineState,
--           mscLpMsgBlockUsageAvgMin,
--           mscLpE1ChanIfIndex,
--           mscLpJT2CellAlarmActDelay,
--           mscLpDS1TestCauseOfTermination,
--           mscLpDS3TestBytesRx,
--           mscLpDS1CustomerIdentifier,
--           mscLpX21TestUsageState,
--           mscLpHssiUnknownStatus,
--           mscLpDS3DS1RxRaiAlarm,
--           mscLpDS3DS1TestUsageState,
--           mscLpDS1BpvErrors,
--           mscLpSonetPathFarEndPathUnavailSec,
--           mscLpDS1ChanTestTimeRemaining,
--           mscLpE3G832ComponentName,
--           mscLpSpareCard,
--           mscLpJT2TestBitErrorRate,
--           mscLpDS1ChanTestType,
--           mscLpE1ChanUnknownStatus,
--           mscLpSdhTestComponentName,
--           mscLpV35TestTimeRemaining,
--           mscLpSonetTestBitsRx,
--           mscLpE3PlcpFarEndUnavailableSec,
--           mscLpV35TestType,
--           mscLpDS3CBitCbitSevErroredSec,
--           mscLpDS3ControlStatus,
--           mscLpSonetTestUsageState,
--           mscLpSonetProceduralStatus,
--           mscLpSdhCustomerIdentifier,
--           mscLpDS3TestOperationalState,
--           mscLpJT2AdminState,
--           mscLpSdhTestFrmRx,
--           mscLpSonetLofAlarm,
--           mscLpSdhTestFrmTx,
--           mscLpE1SlipErrors,
--           mscLpDS1ChanCommentText,
--           mscLpX21TestTimeRemaining,
--           mscLpE1SnmpOperStatus,
--           mscLpHssiIfIndex,
--           mscLpJT2IfAdminStatus,
--           mscLpDS3DS1ChanTcSigTwoValue,
--           mscLpDS3DS1ChanCellStorageType,
--           mscLpJT2TestCustomizedPattern,
--           mscLpV35CommentText,
--           mscLpSdhUnusableTxClockRefAlarm,
--           mscLpJT2ProceduralStatus,
--           mscLpDS1FrmErrors,
--           mscLpDS1ChanStorageType,
--           mscLpJT2LofAlarm,
--           mscLpDS1ChanCellRowStatus,
--           mscLpDS1ControlStatus,
--           mscLpE1ChanTestFrmTx,
--           mscLpE3Vendor,
--           mscLpE3TestBytesRx,
--           mscLpE3PlcpLofAlarm,
--           mscLpDS3DS1ChanIfIndex,
--           mscLpV35ClockingSource,
--           mscLpSonetPathLopAlarm,
--           mscLpJT2LosStateChanges,
--           mscLpX21TestType,
--           mscLpE1ChanTestDataStartDelay,
--           mscLpDS1ChanAdminState,
--           mscLpDS3CellCorrectableHeaderErrors,
--           mscLpE3TestBitsRx,
--           mscLpDS3DS1ErroredSec,
--           mscLpComponentName,
--           mscLpX21SnmpOperStatus,
--           mscLpSonetPathTxRdi,
--           mscLpV35AdminState,
--           mscLpE1SevErroredFrmSec,
--           mscLpDS3DS1CustomerIdentifier,
--           mscLpSonetPathCellAlarmActDelay,
--           mscLpDS3DS1ChanTcStorageType,
--           mscLpE1ChanTestFrmRx,
--           mscLpDS3DS1TestFrmTx,
--           mscLpDS3DS1ChanTcSignalOneDuration,
--           mscLpDS1AudioComponentName,
--           mscLpX21CommentText,
--           mscLpSonetStandbyStatus,
--           mscLpE1ChanTestDuration,
--           mscLpSdhPathProceduralStatus,
--           mscLpE1ChanCustomerIdentifier,
--           mscLpDS3DS1CommentText,
--           mscLpSonetPathRxAisAlarm,
--           mscLpCpuUtilAvgMin,
--           mscLpDS1TestAdminState,
--           mscLpX21StorageType,
--           mscLpHssiTestCustomizedPattern,
--           mscLpSdhSectCodeViolations,
--           mscLpE1OperationalState,
--           mscLpDS3DS1ChanSnmpOperStatus,
--           mscLpDS3DS1StorageType,
--           mscLpDS3AdminState,
--           mscLpDS3DS1UnavailSec,
--           mscLpHssiTestFrmSize,
--           mscLpDS3TestTimeRemaining,
--           mscLpDS1ChanTestAdminState,
--           mscLpSonetPathFarEndPathCodeViolations,
--           mscLpHssiOperationalState,
--           mscLpX21AdminState,
--           mscLpJT2TestDisplayInterval,
--           mscLpSonetTestDataStartDelay,
--           mscLpE1MultifrmLofAlarm,
--           mscLpV35TestAdminState,
--           mscLpE3TestOperationalState,
--           mscLpE1ChanTestElapsedTime,
--           mscLpSonetPathPathCodeViolations,
--           mscLpE1TxMultifrmRaiAlarm,
--           mscLpDS3ProceduralStatus,
--           mscLpMsgBlockUsage,
--           mscLpDS1ChanAlarmStatus,
--           mscLpDS3LofAlarm,
--           mscLpX21TestDuration,
--           mscLpSonetTestBitsTx,
--           mscLpDS3TestUsageState,
--           mscLpJT2ApplicationFramerName,
--           mscLpSdhSectSevErroredSec,
--           mscLpV35AlarmStatus,
--           mscLpE3ApplicationFramerName,
--           mscLpDS3CellAlarmActDelay,
--           mscLpE1RaiDeclareAlarmTime,
--           mscLpE1ChanFlmFlmStatus,
--           mscLpSdhTestFrmSize,
--           mscLpDS1ChanTestPurpose,
--           mscLpE1ChanCellLcdAlarm,
--           mscLpSdhPathFarEndPathErrorFreeSec,
--           mscLpE1TestOperationalState,
--           mscLpDS3DS1ChanVendor,
--           mscLpDS3DS1TestStorageType,
--           mscLpDS3TestFrmPatternType,
--           mscLpV35ActualTxLineSpeed,
--           mscLpE1DspComponentName,
--           mscLpUsageState,
--           mscLpDS1UsageState,
--           mscLpX21TestAdminState,
--           mscLpDS3TestBitErrorRate,
--           mscLpSonetLineErroredSec,
--           mscLpE1ChanCellScrambleCellPayload,
--           mscLpE3TestPurpose,
--           mscLpSonetPathCellUncorrectableHecErrors,
--           mscLpDS3DS1TestAdminState,
--           mscLpSdhTestType,
--           mscLpV35IfAdminStatus,
--           mscLpDS1LosStateChanges,
--           mscLpSdhPathTxRdi,
--           mscLpE1AudioRowStatus,
--           mscLpHssiActualLinkMode,
--           mscLpJT2TestTimeRemaining,
--           mscLpDS1ChanTcReplacementData,
--           mscLpE1ChanCellStorageType,
--           mscLpX21AlarmStatus,
--           mscLpE3CellCorrectSingleBitHeaderErrors,
--           mscLpHssiTestErroredFrmRx,
--           mscLpV35ActualRxLineSpeed,
--           mscLpSdhFarEndLineCodeViolations,
--           mscLpJT2CellTransmitCellUtilization,
--           mscLpDS1ChanCellSevErroredSec,
--           mscLpDS3DS1AlarmStatus,
--           mscLpE3G832TimingMarker,
--           mscLpE1ChanTestErroredFrmRx,
--           mscLpDS3DS1ChanCellRowStatus,
--           mscLpE3TestBytesTx,
--           mscLpX21ActualTxLineSpeed,
--           mscLpE1ChanTestBitsTx,
--           mscLpE3PlcpErrorFreeSec,
--           mscLpE3TestCustomizedPattern,
--           mscLpDS3DS1RunningTime,
--           mscLpDS1ChanTcComponentName,
--           mscLpE1ChanTcReplacementData,
--           mscLpSdhStorageType,
--           mscLpE1ChanTestCauseOfTermination,
--           mscLpJT2TestPurpose,
--           mscLpE3PlcpStorageType,
--           mscLpSdhPathPathErrorFreeSec,
--           mscLpE1ChanTcSignalOneDuration,
--           mscLpSdhOperationalState,
--           mscLpDS1ProceduralStatus,
--           mscLpDS3ApplicationFramerName,
--           mscLpDS1StandbyStatus,
--           mscLpDS3DS1ChanTestOperationalState,
--           mscLpE1UsageState,
--           mscLpDS1ChanIfIndex,
--           mscLpSdhFarEndLineSevErroredSec,
--           mscLpX21ActualRxLineSpeed,
--           mscLpDS1CrcErrors,
--           mscLpV35UsageState,
--           mscLpSonetLineFailures,
--           mscLpE1TestCustomizedPattern,
--           mscLpMsgBlockCapacity,
--           mscLpV35IfIndex,
--           mscLpE3ClockingSource,
--           mscLpE1ChanTimeslots,
--           mscLpDS1ZeroCoding,
--           mscLpSdhLineSevErroredSec,
--           mscLpDS3TestBitsTx,
--           mscLpE3G832FarEndUnavailSec,
--           mscLpJT2ControlStatus,
--           mscLpE1ChanTestUsageState,
--           mscLpDS1ChanTestBitErrorRate,
--           mscLpSonetTestOperationalState,
--           mscLpSonetTestTimeRemaining,
--           mscLpX21TestBytesRx,
--           mscLpE3G832StorageType,
--           mscLpE1TestBytesRx,
--           mscLpSdhTestStorageType,
--           mscLpJT2TestType,
--           mscLpDS1ChanRowStatus,
--           mscLpV35ReadyLineState,
--           mscLpE1IfAdminStatus,
--           mscLpSonetSnmpOperStatus,
--           mscLpDS1TestBitsTx,
--           mscLpSdhPathCellReceiveCellUtilization,
--           mscLpDS3DS1ChanActualChannelSpeed,
--           mscLpE1ChanControlStatus,
--           mscLpV35RowStatus,
--           mscLpDS3TestDisplayInterval,
--           mscLpSdhTestAdminState,
--           mscLpJT2UnavailSec,
--           mscLpX21IfIndex,
--           mscLpDS1TestBitErrorRate,
--           mscLpDS3ErrorFreeSec,
--           mscLpJT2ClockingSource,
--           mscLpSdhPathComponentName,
--           mscLpDS3DS1ChanCellCorrectSingleBitHeaderErrors,
--           mscLpDS3PlcpSevErroredSec,
--           mscLpHssiAvailabilityStatus,
--           mscLpDS3DS1IfIndex,
--           mscLpDS3DS1ChanTimeslotDataRate,
--           mscLpJT2SnmpOperStatus,
--           mscLpHssiTestPurpose,
--           mscLpJT2UsageState,
--           mscLpE3PathSefAisSec,
--           mscLpE3CellTransmitCellUtilization,
--           mscLpHssiTestComponentName,
--           mscLpSdhAlarmStatus,
--           mscLpDS3DS1ChanTestBytesTx,
--           mscLpDS1TestBitsRx,
--           mscLpE3G832FarEndSefAisSec,
--           mscLpX21TestFrmRx,
--           mscLpDS1LofAlarm,
--           mscLpX21LineTerminationRequired,
--           mscLpDS3DS1ChanTestCustomizedPattern,
--           mscLpDS1ChanCellComponentName,
--           mscLpSonetTestFrmPatternType,
--           mscLpSonetPathCellCorrectableHeaderErrors,
--           mscLpDS1ErrorFreeSec,
--           mscLpDS1ChanTcIngressConditioning,
--           mscLpDS1ChanTestRowStatus,
--           mscLpE1ChanProceduralStatus,
--           mscLpStorageType,
--           mscLpE1ChanCellCorrectableHeaderErrors,
--           mscLpDS1ChanAvailabilityStatus,
--           mscLpJT2TxRaiAlarm,
--           mscLpV35TestRowStatus,
--           mscLpDS3DS1RowStatus,
--           mscLpDS3DS1ChanTestBytesRx,
--           mscLpTimeInterval,
--           mscLpSdhPathFarEndPathAisLopSec,
--           mscLpDS1AudioStorageType,
--           mscLpJT2RxAisPayloadAlarm,
--           mscLpAdminState,
--           mscLpX21ReadyLineState,
--           mscLpJT2Vendor,
--           mscLpDS3DS1ChanIfAdminStatus,
--           mscLpDS3LineFailures,
--           mscLpE3CellReceiveCellUtilization,
--           mscLpDS3CBitCbitErroredSec,
--           mscLpE1ChanFlmRowStatus,
--           mscLpSonetPathProceduralStatus,
--           mscLpDS1TestBytesRx,
--           mscLpDS3DS1TestDisplayInterval,
--           mscLpSdhPathRxRfiAlarm,
--           mscLpE3TestUsageState,
--           mscLpHssiTestRowStatus,
--           mscLpE1ChanCellAlarmActDelay,
--           mscLpV35DataXferStateChanges,
--           mscLpE3ComponentName,
--           mscLpDS3DS1ChanTcComponentName,
--           mscLpE1ChanTcComponentName,
--           mscLpSonetFarEndLineUnavailSec,
--           mscLpDS1ChanTestOperationalState,
--           mscLpSdhFarEndLineAisSec,
--           mscLpEngDsStorageType,
--           mscLpV35OperationalState,
--           mscLpSonetSectSevErroredSec,
--           mscLpX21TestRowStatus,
--           mscLpSdhTestCauseOfTermination,
--           mscLpE3TestElapsedTime,
--           mscLpEngDsOvStorageType,
--           mscLpJT2TestAdminState,
--           mscLpDS3DS1ChanTestPurpose,
--           mscLpSdhLineAisSec,
--           mscLpSonetLineSevErroredSec,
--           mscLpDS3DS1TestRowStatus,
--           mscLpSdhPathUsageState,
--           mscLpE3G832UnexpectedPayloadType,
--           mscLpDS3SnmpOperStatus,
--           mscLpDS3DS1AvailabilityStatus,
--           mscLpX21ClockingSource,
--           mscLpSdhTestElapsedTime,
--           mscLpDS3DS1ChanTcSigOneValue,
--           mscLpE1ComponentName,
--           mscLpDS3CBitCbitUnavailSec,
--           mscLpSdhTestBytesTx,
--           mscLpDS3PlcpFarEndUnavailableSec,
--           mscLpDS3DS1ClockingSource,
--           mscLpE1ChanStorageType,
--           mscLpDS1TestTimeRemaining,
--           mscLpSonetTestFrmSize,
--           mscLpDS3DS1ChanCellTransmitCellUtilization,
--           mscLpE3G832FarEndErroredSec,
--           mscLpE1TestBitsTx,
--           mscLpSdhPathPathCodeViolations,
--           mscLpE3PlcpFarEndCodingViolations,
--           mscLpDS1SlipErrors,
--           mscLpSdhPathCellUncorrectableHecErrors,
--           mscLpE1TestUsageState,
--           mscLpE3TestComponentName,
--           mscLpAlarmStatus,
--           mscLpDS1SnmpOperStatus,
--           mscLpE3G832FarEndCodeViolations,
--           mscLpE1DspStorageType,
--           mscLpE3PlcpCodingViolations,
--           mscLpJT2CellLcdAlarm,
--           mscLpDS3CBitFarEndFailures,
--           mscLpDS3DS1LineType,
--           mscLpDS1ChanTcStorageType,
--           mscLpSdhPathFarEndPathUnavailSec,
--           mscLpSdhTestDisplayInterval,
--           mscLpHssiTestFrmTx,
--           mscLpDS1ChanTestFrmTx,
--           mscLpDS3Vendor,
--           mscLpDS3LineSevErroredSec,
--           mscLpDS3PlcpLofAlarm,
--           mscLpDS3DS1ChanTestFrmPatternType,
--           mscLpDS1ChanUnknownStatus,
--           mscLpSdhRowStatus,
--           mscLpDS1LineLength,
--           mscLpE1TestComponentName,
--           mscLpV35TestFrmTx,
--           mscLpDS1ChanTestDataStartDelay,
--           mscLpSonetLineCodeViolations,
--           mscLpSonetPathApplicationFramerName,
--           mscLpV35UnknownStatus,
--           mscLpE3LineFailures,
--           mscLpSdhTestBytesRx,
--           mscLpE3SnmpOperStatus,
--           mscLpDS3DS1ChanCellReceiveCellUtilization,
--           mscLpDS3DS1TestBytesTx,
--           mscLpX21OperationalState,
--           mscLpE3TestDataStartDelay,
--           mscLpDS3OperationalState,
--           mscLpE3UsageState,
--           mscLpSonetPathSnmpOperStatus,
--           mscLpDS1ChanTestFrmRx,
--           mscLpDS1Vendor,
--           mscLpDS3DS1ChanComponentName,
--           mscLpSdhCommentText,
--           mscLpDS1ChanTestDuration,
--           mscLpV35TestFrmRx,
--           mscLpDS1ChanCustomerIdentifier,
--           mscLpSonetTestBytesTx,
--           mscLpX21ComponentName,
--           mscLpX21TestBitErrorRate,
--           mscLpDS3PlcpUnavailSec,
--           mscLpV35TestDuration,
--           mscLpJT2CellCorrectSingleBitHeaderErrors,
--           mscLpE3CellUncorrectableHecErrors,
--           mscLpV35CustomerIdentifier,
--           mscLpE3CellLcdAlarm,
--           mscLpE1ChanApplicationFramerName,
--           mscLpDS1OperationalState,
--           mscLpE3RxAisAlarm,
--           mscLpSdhPathRxAisAlarm,
--           mscLpE3G832TrailTraceTransmitted,
--           mscLpSdhTestRowStatus,
--           mscLpSdhPathCellCorrectSingleBitHeaderErrors,
--           mscLpUnknownStatus,
--           mscLpSonetPathAdminState,
--           mscLpX21UnknownStatus,
--           mscLpDS3TxIdle,
--           mscLpSonetPathPathFailures,
--           mscLpMainCardStatus,
--           mscLpSdhPathIfAdminStatus,
--           mscLpX21TestDataStartDelay,
--           mscLpDS3DS1UnknownStatus,
--           mscLpE3RxRaiAlarm,
--           mscLpSdhPathPathSevErroredSec,
--           mscLpSonetTestBytesRx,
--           mscLpDS3DS1TestDataStartDelay,
--           mscLpDS1ClockingSource,
--           mscLpJT2CellStorageType,
--           mscLpE1TestDataStartDelay,
--           mscLpSdhTestUsageState,
--           mscLpE1TestFrmSize,
--           mscLpDS3DS1ChanTestComponentName,
--           mscLpSonetIfAdminStatus,
--           mscLpE1RxAisAlarm,
--           mscLpDS3RxAisAlarm,
--           mscLpHssiRowStatus,
--           mscLpHssiAlarmStatus,
--           mscLpDS3RxIdle,
--           mscLpDS3IfAdminStatus,
--           mscLpDS3DS1TestFrmRx,
--           mscLpX21CustomerIdentifier,
--           mscLpE3LineLosSec,
--           mscLpSdhTestPurpose,
--           mscLpE3PlcpFarEndSevErroredSec,
--           mscLpDS3DS1TestDuration,
--           mscLpDS1TestOperationalState,
--           mscLpE1ChanTestBitsRx,
--           mscLpJT2CellSevErroredSec,
--           mscLpDS3DS1ChanTestAdminState,
--           mscLpSdhTestCustomizedPattern,
--           mscLpSdhErrorFreeSec,
--           mscLpDS3RxRaiAlarm,
--           mscLpDS1DspComponentName,
--           mscLpSonetTestPurpose,
--           mscLpRowStatus,
--           mscLpV35DataTransferLineState,
--           mscLpV35ActualLinkMode,
--           mscLpDS1ChanCellScrambleCellPayload,
--           mscLpDS3DS1TestTimeRemaining,
--           mscLpHssiTestStorageType,
--           mscLpSdhRxRfiAlarm,
--           mscLpDS1ChanTestDisplayInterval,
--           mscLpDS3DS1ChanUsageState,
--           mscLpDS3CBitCbitCodeViolations,
--           mscLpDS1AudioRowStatus,
--           mscLpSdhTestDuration,
--           mscLpSdhFarEndLineErroredSec,
--           mscLpSdhPathUnknownStatus,
--           mscLpDS1ChanCellStorageType,
--           mscLpE1TestFrmTx,
--           mscLpDS3CellCorrectSingleBitHeaderErrors,
--           mscLpSonetFarEndLineErrorFreeSec,
--           mscLpV35TestBitsTx,
--           mscLpSdhPathSignalLabelMismatch,
--           mscLpE3PathSevErroredSec,
--           mscLpDS3PlcpFarEndErrorFreeSec,
--           mscLpSdhLineErroredSec,
--           mscLpE3TestType,
--           mscLpDS1ChanTestErroredFrmRx,
--           mscLpSdhSectSevErroredFrmSec,
--           mscLpDS3TestBytesTx,
--           mscLpDS3DS1ChanCellUncorrectableHecErrors,
--           mscLpE1SendRaiOnAis,
--           mscLpDS3DS1ChanTestFrmSize,
--           mscLpV35AvailabilityStatus,
--           mscLpDS3LineErroredSec,
--           mscLpDS3PlcpErrorFreeSec,
--           mscLpDS3TestCustomizedPattern,
--           mscLpDS3IfIndex,
--           mscLpX21DataTransferLineState,
--           mscLpX21ActualLinkMode,
--           mscLpDS1ChanTestCauseOfTermination,
--           mscLpDS1ChanTestBytesTx,
--           mscLpDS1RxRaiAlarm,
--           mscLpJT2TestFrmSize,
--           mscLpE3CommentText,
--           mscLpSdhClockingSource,
--           mscLpJT2ComponentName,
--           mscLpAvailabilityStatus,
--           mscLpE1ErroredSec,
--           mscLpV35TestCauseOfTermination,
--           mscLpSdhUnknownStatus,
--           mscLpE1TestType,
--           mscLpDS3DS1ChanTestUsageState,
--           mscLpDS3DS1ChanTcEgressConditioning,
--           mscLpX21TestDisplayInterval,
--           mscLpDS1TestBytesTx,
--           mscLpHssiTestBitErrorRate,
--           mscLpE3StorageType,
--           mscLpDS1ChanTcEgressConditioning,
--           mscLpE1ChanTcStorageType,
--           mscLpDS1TestCustomizedPattern,
--           mscLpSdhSectErroredSec,
--           mscLpSdhTestOperationalState,
--           mscLpDS1ChanTimeslots,
--           mscLpJT2LineLength,
--           mscLpJT2TestFrmPatternType,
--           mscLpSdhFarEndLineUnavailSec,
--           mscLpDS1IfAdminStatus,
--           mscLpE1CommentText,
--           mscLpX21TestErroredFrmRx,
--           mscLpE3LineLength,
--           mscLpActiveCard,
--           mscLpDS3DS1TestType,
--           mscLpSdhTxRdi,
--           mscLpJT2CellReceiveCellUtilization,
--           mscLpDS3DS1TestErroredFrmRx,
--           mscLpE1DspRowStatus,
--           mscLpE1ChanSnmpOperStatus,
--           mscLpE1StorageType,
--           mscLpE3LineSevErroredSec,
--           mscLpE1UnavailSec,
--           mscLpX21TestCauseOfTermination,
--           mscLpDS1SevErroredSec,
--           mscLpDS3TestPurpose,
--           mscLpHssiTestElapsedTime,
--           mscLpDS3DS1TestCauseOfTermination,
--           mscLpDS1ChanControlStatus,
--           mscLpHssiLineSpeed,
--           mscLpE3PlcpComponentName,
--           mscLpE1AdminState,
--           mscLpDS3DS1ChanTestBitErrorRate,
--           mscLpE3TestStorageType,
--           mscLpDS3PathFailures,
--           mscLpDS3DS1UsageState,
--           mscLpV35ControlStatus,
--           mscLpSdhTxAis,
--           mscLpSonetTestFrmTx,
--           mscLpDS3DS1ChanTestTimeRemaining,
--           mscLpDS3DS1ChanTestType,
--           mscLpDS3CellTransmitCellUtilization,
--           mscLpSonetTestComponentName,
--           mscLpE3TestAdminState,
--           mscLpE1Crc4Mode,
--           mscLpE1ChanCellRowStatus,
--           mscLpDS1TestPurpose,
--           mscLpHssiTestType,
--           mscLpSdhPathOperationalState,
--           mscLpSdhUsageState,
--           mscLpE1ChanVendor,
--           mscLpSdhPathCellSevErroredSec,
--           mscLpE1TestStorageType,
--           mscLpSonetRxRfiAlarm,
--           mscLpE1ChanFlmStorageType,
--           mscLpSdhSectFailures,
--           mscLpSdhAvailabilityStatus,
--           mscLpDS3DS1ChanCommentText,
--           mscLpE3AlarmStatus,
--           mscLpDS1ChanCellCorrectableHeaderErrors,
--           mscLpDS1ChanTestFrmSize,
--           mscLpE3G832FarEndErrorFreeSec,
--           mscLpSonetSectLosSec,
--           mscLpV35LinkMode,
--           mscLpE1TestAdminState,
--           mscLpSonetUnusableTxClockRefAlarm,
--           mscLpE1ChanOperationalState,
--           mscLpDS3DS1FrmErrors,
--           mscLpSonetPathUnknownStatus,
--           mscLpDS3DS1ChanStorageType,
--           mscLpE3RunningTime,
--           mscLpSonetIfIndex,
--           mscLpDS3DS1ControlStatus,
--           mscLpV35TestElapsedTime,
--           mscLpE3TestFrmSize,
--           mscLpSonetUsageState,
--           mscLpE3Mapping,
--           mscLpDS3CellReceiveCellUtilization,
--           mscLpSdhPathIfIndex,
--           mscLpSonetSectSevErroredFrmSec,
--           mscLpE1AlarmStatus,
--           mscLpSonetPathFarEndPathFailures,
--           mscLpDS3DS1ChanAdminState,
--           mscLpX21ControlStatus,
--           mscLpCpuUtil,
--           mscLpJT2CommentText,
--           mscLpDS3DS1ChanTcRowStatus,
--           mscLpDS3ComponentName,
--           mscLpDS1TestFrmPatternType,
--           mscLpSdhFarEndLineFailures,
--           mscLpV35TestStorageType,
--           mscLpE1RunningTime,
--           mscLpJT2TestCauseOfTermination,
--           mscLpCustomerIdentifier,
--           mscLpSdhLosAlarm,
--           mscLpDS3CBitFarEndAlarm,
--           mscLpX21LinkMode,
--           mscLpSonetFarEndLineAisSec,
--           mscLpDS3DS1ChanOperationalState,
--           mscLpDS3DS1ChanTestStorageType,
--           mscLpDS3TestFrmSize,
--           mscLpDS3CbitParity,
--           mscLpE1ChanTestOperationalState,
--           mscLpE3CellSevErroredSec,
--           mscLpDS3CBitRowStatus,
--           mscLpDS3CBitFarEndErrorFreeSec,
--           mscLpX21TestElapsedTime,
--           mscLpDS1ChanProceduralStatus,
--           mscLpDS1ComponentName,
--           mscLpJT2CellUncorrectableHecErrors,
--           mscLpSdhTestErroredFrmRx,
--           mscLpSonetPathCellRowStatus,
--           mscLpDS3DS1ChanTestDisplayInterval,
--           mscLpDS3DS1TestElapsedTime,
--           mscLpDS3DS1SevErroredSec,
--           mscLpV35TestBitErrorRate,
--           mscLpMemoryUsageAvgMinValue,
--           mscLpSdhRunningTime,
--           mscLpDS1ChanCellAlarmActDelay,
--           mscLpSdhPathControlStatus,
--           mscLpDS3PlcpFarEndCodingViolations,
--           mscLpSdhLineCodeViolations,
--           mscLpSonetPathCellCorrectSingleBitHeaderErrors,
--           mscLpDS3TestComponentName,
--           mscLpJT2RxRaiAlarm,
--           mscLpE3TestFrmPatternType,
--           mscLpDS1DspStorageType,
--           mscLpDS3PlcpCodingViolations,
--           mscLpE3PlcpRxRaiAlarm,
--           mscLpE3IfIndex,
--           mscLpDS1ChanUsageState,
--           mscLpE3ProceduralStatus,
--           mscLpDS3DS1ChanAlarmStatus,
--           mscLpHssiCustomerIdentifier,
--           mscLpSdhPathPathErroredSec,
--           mscLpJT2TestOperationalState,
--           mscLpE1ChanActualChannelSpeed,
--           mscLpSpareCardStatus,
--           mscLpSonetRxAisAlarm,
--           mscLpSdhLineUnavailSec,
--           mscLpSdhTestTimeRemaining,
--           mscLpSdhPathFarEndPathErroredSec,
--           mscLpDS1TestComponentName,
--           mscLpSdhPathPathAisLopSec,
--           mscLpSdhPathAvailabilityStatus,
--           mscLpX21ProceduralStatus,
--           mscLpSonetPathFarEndPathErrorFreeSec,
--           mscLpSdhControlStatus,
--           mscLpE1ChanCellCorrectSingleBitHeaderErrors,
--           mscLpJT2CrcErrors,
--           mscLpE1IfIndex,
--           mscLpE1ChanTimeslotDataRate,
--           mscLpDS1ChanStandbyStatus,
--           mscLpDS3DS1LofAlarm,
--           mscLpSonetPathCellLcdAlarm,
--           mscLpSonetPathPathErrorFreeSec,
--           mscLpE3RowStatus,
--           mscLpSdhPathCellComponentName,
--           mscLpSonetPathOperationalState,
--           mscLpE1ChanTcRowStatus,
--           mscLpJT2StorageType,
--           mscLpSonetPathIfAdminStatus,
--           mscLpV35StandbyStatus,
--           mscLpE3Framing,
--           mscLpJT2TestErroredFrmRx,
--           mscLpSonetPathCellScrambleCellPayload,
--           mscLpSonetTestType,
--           mscLpE1TestFrmPatternType,
--           mscLpE1ChanTestCustomizedPattern,
--           mscLpSonetVendor,
--           mscLpJT2TestBitsRx,
--           mscLpSonetTxRdi,
--           mscLpSdhPathAdminState,
--           mscLpE1TestBitErrorRate,
--           mscLpHssiProceduralStatus,
--           mscLpDS3CellUncorrectableHecErrors,
--           mscLpE3PlcpFarEndErroredSec,
--           mscLpDS3CellLcdAlarm,
--           mscLpDS1ChanApplicationFramerName,
--           mscLpE1RxMultifrmRaiAlarm,
--           mscLpDS1TxAisAlarm,
--           mscLpDS3DS1ChanCellSevErroredSec,
--           mscLpE1RowStatus,
--           mscLpHssiTestBitsTx,
--           mscLpE1ChanTestBytesRx,
--           mscLpV35ApplicationFramerName,
--           mscLpE3PlcpErroredSec,
--           mscLpJT2TestDataStartDelay,
--           mscLpX21AvailabilityStatus,
--           mscLpSdhPathPathUnavailSec,
--           mscLpDS1TxRaiAlarm,
--           mscLpE3PlcpSevErroredFramingSec,
--           mscLpE1ChanIfAdminStatus,
--           mscLpSdhPathAlarmStatus,
--           mscLpMsgBlockUsageAvg,
--           mscLpSonetStorageType,
--           mscLpMemoryUsageAvgMaxValue,
--           mscLpX21StandbyStatus,
--           mscLpE1ChanFlmComponentName,
--           mscLpDS1TestFrmSize,
--           mscLpSonetPathStandbyStatus,
--           mscLpE1BpvErrors,
--           mscLpE3AvailabilityStatus,
--           mscLpDS1RxAisAlarm,
--           mscLpE1TxAisAlarm,
--           mscLpDS3DS1StandbyStatus,
--           mscLpSonetPathCellTransmitCellUtilization,
--           mscLpHssiTestDataStartDelay,
--           mscLpSonetAdminState,
--           mscLpSonetFarEndLineSevErroredSec,
--           mscLpDS3DS1CrcErrors,
--           mscLpEngDsRowStatus,
--           mscLpDS1ChanTcRowStatus,
--           mscLpDS3LineLosSec,
--           mscLpSonetPathTxAis,
--           mscLpDS3PlcpFarEndSevErroredSec,
--           mscLpHssiActualTxLineSpeed,
--           mscLpDS1TestUsageState,
--           mscLpDS1ChanIfAdminStatus,
--           mscLpE3TestDisplayInterval,
--           mscLpX21ApplicationFramerName,
--           mscLpE1TestRowStatus,
--           mscLpHssiTestUsageState,
--           mscLpSonetTestBitErrorRate,
--           mscLpHssiTestFrmRx,
--           mscLpE1AvailabilityStatus,
--           mscLpV35TestBitsRx,
--           mscLpHssiDataXferStateChanges,
--           mscLpE1ChanTcSigOneValue,
--           mscLpE3PlcpSevErroredSec,
--           mscLpHssiTestDuration,
--           mscLpJT2TestRowStatus,
--           mscLpSonetPathRxRfiAlarm,
--           mscLpE1ClockingSource,
--           mscLpSonetTestStorageType,
--           mscLpControlStatus,
--           mscLpE1TestBytesTx,
--           mscLpHssiTestBytesRx,
--           mscLpSdhProceduralStatus,
--           mscLpX21TestBitsTx,
--           mscLpE1ChanCellTransmitCellUtilization,
--           mscLpDS3DS1ChanRowStatus,
--           mscLpSdhLofAlarm,
--           mscLpDS3DS1ChanTestDuration,
--           mscLpE3PathUnavailSec,
--           mscLpSonetPathCellReceiveCellUtilization,
--           mscLpSdhPathCellTransmitCellUtilization,
--           mscLpHssiAdminState,
--           mscLpDS1ChanTcSigTwoValue,
--           mscLpJT2TestStorageType,
--           mscLpDS3TestType,
--           mscLpSdhPathCellLcdAlarm,
--           mscLpE1LineType,
--           mscLpSonetPathComponentName,
--           mscLpHssiTestOperationalState,
--           mscLpSdhPathCellAlarmActDelay,
--           mscLpV35DteDataClockSource,
--           mscLpX21TestBitsRx,
--           mscLpSonetLineUnavailSec,
--           mscLpE1TestDisplayInterval,
--           mscLpJT2SevErroredFrmSec,
--           mscLpE1ChanTestFrmPatternType,
--           mscLpSonetAlarmStatus,
--           mscLpDS3DS1TestBitsRx,
--           mscLpE3G832TrailTraceMismatch,
--           mscLpDS3CommentText,
--           mscLpDS1ChanTestBitsTx,
--           mscLpV35LineStatusTimeOut,
--           mscLpE3TestTimeRemaining,
--           mscLpDS3DS1ChanCellComponentName,
--           mscLpEngDsComponentName,
--           mscLpDS1TestType,
--           mscLpE1ChanCellReceiveCellUtilization,
--           mscLpSonetTestCustomizedPattern,
--           mscLpDS3DS1ErrorFreeSec,
--           mscLpDS3DS1ChanTcIngressConditioning,
--           mscLpDS3DS1ChanTestRowStatus,
--           mscLpDS3PathSefAisSec,
--           mscLpHssiActualRxLineSpeed,
--           mscLpSdhPathCellRowStatus,
--           mscLpDS3StorageType,
--           mscLpDS3DS1ChanAvailabilityStatus,
--           mscLpV35EnableDynamicSpeed,
--           mscLpSdhPathTxAis,
--           mscLpDS1ChanTcSignalOneDuration,
--           mscLpE1ChanComponentName,
--           mscLpE3TestFrmTx,
--           mscLpDS3CBitLoopbackAtFarEndRequested,
--           mscLpDS3CBitLoopedbackToFarEnd,
--           mscLpSdhStandbyStatus,
--           mscLpE1ChanTestComponentName,
--           mscLpE3UnknownStatus,
--           mscLpSonetPathFarEndPathAisLopSec,
--           mscLpDS1CommentText,
--           mscLpV35TestErroredFrmRx,
--           mscLpV35TestDataStartDelay,
--           mscLpX21DteDataClockSource,
--           mscLpDS3LineLength,
--           mscLpJT2AlarmStatus,
--           mscLpEngDsOvRowStatus,
--           mscLpHssiTestDisplayInterval,
--           mscLpDS3TestBitsRx,
--           mscLpSonetPathPathAisLopSec,
--           mscLpDS1DspRowStatus,
--           mscLpDS1ChanSnmpOperStatus,
--           mscLpDS1StorageType,
--           mscLpX21LineStatusTimeOut,
--           mscLpDS1UnavailSec,
--           mscLpV35LineState,
--           mscLpSdhPathFarEndPathCodeViolations,
--           mscLpJT2RunningTime,
--           mscLpV35SnmpOperStatus,
--           mscLpE1UnknownStatus,
--           mscLpE1TestTimeRemaining,
--           mscLpE3G832TrailTraceExpected,
--           mscLpE3TestDuration,
--           mscLpDS3PlcpComponentName,
--           mscLpDS1AdminState,
--           mscLpSonetPathRowStatus,
--           mscLpDS3TestStorageType,
--           mscLpProceduralStatus,
--           mscLpSdhPathCellScrambleCellPayload,
--           mscLpDS3DS1ProceduralStatus,
--           mscLpSonetLineAisSec,
--           mscLpE1RxRaiAlarm,
--           mscLpLocalMsgBlockUsageMax,
--           mscLpSdhTestBitsTx,
--           mscLpJT2ErroredSec,
--           mscLpHssiTestCauseOfTermination,
--           mscLpSonetPathUsageState,
--           mscLpSdhPathSnmpOperStatus,
--           mscLpSonetPathAlarmStatus,
--           mscLpE1TestFrmRx,
--           mscLpE3TestRowStatus,
--           mscLpDS3TestAdminState,
--           mscLpSdhPathCellStorageType,
--           mscLpSonetOperationalState,
--           mscLpE1TestDuration,
--           mscLpE3TxAis,
--           mscLpE1CustomerIdentifier,
--           mscLpDS1ChanVendor,
--           mscLpE1TestPurpose,
--           mscLpDS1TestStorageType,
--           mscLpX21LineState,
--           mscLpEngComponentName,
--           mscLpJT2OperationalState,
--           mscLpE1ChanStandbyStatus,
--           mscLpJT2CellComponentName,
--           mscLpEngDsOvAgentQueueSize,
--           mscLpDS3DS1SlipErrors,
--           mscLpV35Vendor,
--           mscLpLocalMsgBlockUsageMin,
--           mscLpDS3AlarmStatus,
--           mscLpE3TxRai,
--           mscLpDS3DS1SnmpOperStatus,
--           mscLpSdhIfIndex,
--           mscLpSdhSectLosSec,
--           mscLpE3PathErroredSec,
--           mscLpSdhPathRowStatus,
--           mscLpSonetComponentName,
--           mscLpJT2IfIndex,
--           mscLpSonetTestAdminState }
-- STATUS  mandatory
-- DESCRIPTION
--   "A list of all current accessible leaf objects."

logicalProcessorGroup OBJECT IDENTIFIER ::= { logicalProcessorMIB 1 }
logicalProcessorGroupCA OBJECT IDENTIFIER ::= { logicalProcessorGroup 1 }
logicalProcessorGroupCA02 OBJECT IDENTIFIER ::= { logicalProcessorGroupCA 3 }
logicalProcessorGroupCA02A OBJECT IDENTIFIER ::= { logicalProcessorGroupCA02 2 }



-- Agent-Capabilities Statement:

-- PRODUCT-RELEASE "MscPassport Release 1.2 LogicalProcessor."
-- STATUS          mandatory
-- DESCRIPTION     "Carrier Passport LogicalProcessor MIB: MIB Version CA02A,
--                  Software Version CA02S9C."
-- SUPPORTS        Nortel-MsCarrier-MscPassport-LogicalProcessorMIB
--    INCLUDES     { logicalProcessorGroupCA02A }

logicalProcessorCapabilities OBJECT IDENTIFIER ::= { logicalProcessorMIB 3 }
logicalProcessorCapabilitiesCA OBJECT IDENTIFIER ::= { logicalProcessorCapabilities 1 }
logicalProcessorCapabilitiesCA02 OBJECT IDENTIFIER ::= { logicalProcessorCapabilitiesCA 3 }
logicalProcessorCapabilitiesCA02A OBJECT IDENTIFIER ::= { logicalProcessorCapabilitiesCA02 2 }





END
