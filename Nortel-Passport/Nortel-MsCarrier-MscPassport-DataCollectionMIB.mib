Nortel-MsCarrier-MscPassport-DataCollectionMIB
DEFINITIONS ::= BEGIN



IMPORTS

      OBJECT-TYPE
   FROM RFC-1212

      mscPassportMIBs,
      mscComponents
   FROM Nortel-MsCarrier-MscPassport-UsefulDefinitionsMIB

      Counter32,
      DisplayString,
      StorageType,
      RowStatus,
      Gauge32,
      Integer32,
      Unsigned32
   FROM Nortel-MsCarrier-MscPassport-StandardTextualConventionsMIB

      AsciiString,
      NonReplicated,
      EnterpriseDateAndTime
   FROM Nortel-MsCarrier-MscPassport-TextualConventionsMIB;




-- LAST-UPDATED   "9909010000Z"
-- ORGANIZATION   "Nortel Networks"
-- CONTACT-INFO   "
--         Nortel Carrier Data Network Management
--         
--         Postal:       P.O. Box 3511, Station C 
--                       Ottawa, Ontario 
--                       Canada  K1Y 4H7
--         
--         via the WEB:  http://www.nortelnetworks.com  
--                       select 'Contact Us' from the menu
--          
--         via phone:    1-800-4NORTEL"
-- DESCRIPTION
--    "The module describing the Nortel MsCarrier MscPassport
--     DataCollection Enterprise MIB."

dataCollectionMIB OBJECT IDENTIFIER ::= { mscPassportMIBs 14 }










-- Collector/<dataType> 
-- There is a Collector for each data stream. It is a permanent 
-- component which resides on the active CP. Its main function is to 
-- coordinate collection of data from all its Agent subcomponents and 
-- distribute that data to the downstream applications which have 
-- requested it (for example, one or more Sessions or its Spooler 
-- subcomponent). It also coordinates the time-of-day accounting 
-- (TODA) schedules and spooled statistics probes.

mscCol OBJECT IDENTIFIER ::= { mscComponents 21 }



mscColRowStatusTable OBJECT-TYPE
   SYNTAX     SEQUENCE OF MscColRowStatusEntry
   ACCESS     not-accessible
   STATUS     mandatory
   DESCRIPTION
     "This entry controls the addition and deletion of 
      mscCol components."
::= { mscCol 1 }

mscColRowStatusEntry OBJECT-TYPE
   SYNTAX     MscColRowStatusEntry
   ACCESS     not-accessible
   STATUS     mandatory
   DESCRIPTION
     "A single entry in the table represents a single 
      mscCol component."
   INDEX {
      mscColIndex }
::= { mscColRowStatusTable 1 }

MscColRowStatusEntry ::= SEQUENCE {
   mscColRowStatus
      RowStatus,
   mscColComponentName
      DisplayString,
   mscColStorageType
      StorageType,
   mscColIndex
      INTEGER }

mscColRowStatus OBJECT-TYPE
   SYNTAX     RowStatus 
   ACCESS     read-write
   STATUS     mandatory
   DESCRIPTION
     "This variable is used as the basis for SNMP naming of
      mscCol components.
      These components can be added."
::= { mscColRowStatusEntry 1 }

mscColComponentName OBJECT-TYPE
   SYNTAX     DisplayString 
   ACCESS     read-only
   STATUS     mandatory
   DESCRIPTION
     "This variable provides the component's string name for
      use with the ASCII Console Interface"
::= { mscColRowStatusEntry 2 }

mscColStorageType OBJECT-TYPE
   SYNTAX     StorageType 
   ACCESS     read-only
   STATUS     mandatory
   DESCRIPTION
     "This variable represents the storage type value for the
      mscCol tables."
::= { mscColRowStatusEntry 4 }

mscColIndex OBJECT-TYPE
   SYNTAX     INTEGER  {
                 accounting(0),
                 alarm(1),
                 log(2),
                 debug(3),
                 scn(4),
                 trap(5),
                 stats(6) }
   ACCESS     not-accessible
   STATUS     mandatory
   DESCRIPTION
     "This variable represents the index for the mscCol tables."
::= { mscColRowStatusEntry 10 }

mscColProvTable OBJECT-TYPE
   SYNTAX     SEQUENCE OF MscColProvEntry
   ACCESS     not-accessible
   STATUS     mandatory
   DESCRIPTION
     "This group specifies all of the provisioning data for a DCS 
      Collector."
::= { mscCol 10 }

mscColProvEntry OBJECT-TYPE
   SYNTAX     MscColProvEntry
   ACCESS     not-accessible
   STATUS     mandatory
   DESCRIPTION
     "An entry in the mscColProvTable."
   INDEX {
      mscColIndex }
::= { mscColProvTable 1 }

MscColProvEntry ::= SEQUENCE {
   mscColAgentQueueSize
      Unsigned32 }

mscColAgentQueueSize OBJECT-TYPE
   SYNTAX     Unsigned32 (0 | 20..10000)
   ACCESS     read-write
   STATUS     obsolete
   DESCRIPTION
     "This attribute has been replaced with the agentQueueSize attribute 
      in the Lp Engineering DataStream Ov component.
      
      Upon migration, if the existing provisioned value of this attribute is 
      the same as the system default for this type of data, no new 
      components are added because the default is what the DataStream 
      component already would be using. Otherwise, if the value is not 
      the same as the system default, then for each Lp which is 
      provisioned at the time of the migration, a DataStream is 
      provisioned and the Ov's agentQueueSize is set to the non-default 
      value."
::= { mscColProvEntry 1 }

mscColStatsTable OBJECT-TYPE
   SYNTAX     SEQUENCE OF MscColStatsEntry
   ACCESS     not-accessible
   STATUS     mandatory
   DESCRIPTION
     "This group specifies the statistics operational attributes of the DCS 
      Collector, Agent and Spooler components."
::= { mscCol 11 }

mscColStatsEntry OBJECT-TYPE
   SYNTAX     MscColStatsEntry
   ACCESS     not-accessible
   STATUS     mandatory
   DESCRIPTION
     "An entry in the mscColStatsTable."
   INDEX {
      mscColIndex }
::= { mscColStatsTable 1 }

MscColStatsEntry ::= SEQUENCE {
   mscColCurrentQueueSize
      Gauge32,
   mscColRecordsRx
      Counter32,
   mscColRecordsDiscarded
      Counter32 }

mscColCurrentQueueSize OBJECT-TYPE
   SYNTAX     Gauge32 (0..4294967295)
   ACCESS     read-only
   STATUS     mandatory
   DESCRIPTION
     "This gauge contains the current number of records held by this DCS 
      component."
::= { mscColStatsEntry 1 }

mscColRecordsRx OBJECT-TYPE
   SYNTAX     Counter32 
   ACCESS     read-only
   STATUS     mandatory
   DESCRIPTION
     "This counter contains the cumulative number of records received by 
      a DCS component, from applications which send data to it, since 
      the processor last restarted.
      
      This counter wraps to 0 when the maximum value is exceeded."
::= { mscColStatsEntry 2 }

mscColRecordsDiscarded OBJECT-TYPE
   SYNTAX     Counter32 
   ACCESS     read-only
   STATUS     mandatory
   DESCRIPTION
     "This is the cumulative number of records discarded by this DCS 
      component since the processor last restarted.
      
      This counter wraps to 0 when the maximum value is exceeded."
::= { mscColStatsEntry 3 }

mscColTimesTable OBJECT-TYPE
   SYNTAX     SEQUENCE OF MscColTimesEntry
   ACCESS     not-accessible
   STATUS     mandatory
   DESCRIPTION
     "This attribute specifies the scheduled times at which data should be 
      collected. Only accounting applications need the capability to 
      generate data in this way. Setting this attribute for other streams has 
      no effect.
      
      The user can enter the times in any order and duplicates are 
      prevented at data entry. There is a limit of 24 entries, which is 
      imposed at semantic check time. The collection times are triggered 
      in chronological order. A semantic check error is issued if any 2 
      entries are less than 1 hour apart or if any 2 entries are more than 12 
      hours apart (which implies that if any entries are provided, there 
      must be at least 2 entries).
      
      Note that by default (that is, in the absence of a provisioned 
      schedule), a Virtual Circuit (VC) starts its own 12-hour accounting 
      timer. If any collection times are provisioned here, then the Time-
      Of-Day-Accounting (TODA) method is used in place of 12-hour 
      accounting. This is applicable to both Switched VCs and Permanent 
      VCs."
::= { mscCol 266 }

mscColTimesEntry OBJECT-TYPE
   SYNTAX     MscColTimesEntry
   ACCESS     not-accessible
   STATUS     mandatory
   DESCRIPTION
     "An entry in the mscColTimesTable."
   INDEX {
      mscColIndex,
      mscColTimesValue }
::= { mscColTimesTable 1 }

MscColTimesEntry ::= SEQUENCE {
   mscColTimesValue
      EnterpriseDateAndTime,
   mscColTimesRowStatus
      RowStatus }

mscColTimesValue OBJECT-TYPE
   SYNTAX     EnterpriseDateAndTime (SIZE (5))
   ACCESS     read-write
   STATUS     mandatory
   DESCRIPTION
     "This variable represents both the value and the index for the
      mscColTimesTable."
::= { mscColTimesEntry 1 }

mscColTimesRowStatus OBJECT-TYPE
   SYNTAX     RowStatus 
   ACCESS     write-only
   STATUS     mandatory
   DESCRIPTION
     "This variable is used to control the addition and deletion 
      of individual values of the mscColTimesTable."
::= { mscColTimesEntry 2 }

mscColLastTable OBJECT-TYPE
   SYNTAX     SEQUENCE OF MscColLastEntry
   ACCESS     not-accessible
   STATUS     obsolete
   DESCRIPTION
     "Note: This was made obsolete in R4.1 (BD0108A).
      This attribute is used for Collector/stats and Collector/account. 
      For statistics, when collection is turned off, or prior to the very first 
      probe, the value is the empty list. Otherwise, this is the network 
      time at which the last probe was sent out (that is, the last time that 
      statistics were collected from, or at least reset by, the applications 
      providing them).
      For accounting, when no entries exist in collectionTimes, or prior to 
      the very first collection time, the value is the empty list. Otherwise, 
      this is the network time at which the last time-of-day changeover 
      occurred."
::= { mscCol 275 }

mscColLastEntry OBJECT-TYPE
   SYNTAX     MscColLastEntry
   ACCESS     not-accessible
   STATUS     obsolete
   DESCRIPTION
     "An entry in the mscColLastTable."
   INDEX {
      mscColIndex,
      mscColLastValue }
::= { mscColLastTable 1 }

MscColLastEntry ::= SEQUENCE {
   mscColLastValue
      EnterpriseDateAndTime }

mscColLastValue OBJECT-TYPE
   SYNTAX     EnterpriseDateAndTime (SIZE (19))
   ACCESS     read-only
   STATUS     obsolete
   DESCRIPTION
     "This variable represents both the value and the index for the
      mscColLastTable."
::= { mscColLastEntry 1 }

mscColPeakTable OBJECT-TYPE
   SYNTAX     SEQUENCE OF MscColPeakEntry
   ACCESS     not-accessible
   STATUS     mandatory
   DESCRIPTION
     "This attribute specifies the length of the accounting peak water mark 
      interval. It is at least one minute and at most 15 minutes long. An 
      accounting peak water mark within a given accounting interval is 
      the accounting count which occured during a peak water mark 
      interval with the highest traffic. Peak water marks are used to 
      determine traffic bursts. If no value is provisioned for this attribute 
      value of 5 minutes is assumed. Peak water mark is only measured if 
      attribute collectionTimes in Collector/account is provisioned."
::= { mscCol 279 }

mscColPeakEntry OBJECT-TYPE
   SYNTAX     MscColPeakEntry
   ACCESS     not-accessible
   STATUS     mandatory
   DESCRIPTION
     "An entry in the mscColPeakTable."
   INDEX {
      mscColIndex,
      mscColPeakValue }
::= { mscColPeakTable 1 }

MscColPeakEntry ::= SEQUENCE {
   mscColPeakValue
      Integer32,
   mscColPeakRowStatus
      RowStatus }

mscColPeakValue OBJECT-TYPE
   SYNTAX     Integer32 (1..15)
   ACCESS     read-write
   STATUS     mandatory
   DESCRIPTION
     "This variable represents both the value and the index for the
      mscColPeakTable."
::= { mscColPeakEntry 1 }

mscColPeakRowStatus OBJECT-TYPE
   SYNTAX     RowStatus 
   ACCESS     write-only
   STATUS     mandatory
   DESCRIPTION
     "This variable is used to control the addition and deletion 
      of individual values of the mscColPeakTable."
::= { mscColPeakEntry 2 }


-- Col/<dataType> Spooler
-- A Spooler is a required subcomponent of the Collector and also 
-- resides on the active CP, managing all the spooling of a particular 
-- type of data.

mscColSp OBJECT IDENTIFIER ::= { mscCol 2 }



mscColSpRowStatusTable OBJECT-TYPE
   SYNTAX     SEQUENCE OF MscColSpRowStatusEntry
   ACCESS     not-accessible
   STATUS     mandatory
   DESCRIPTION
     "This entry controls the addition and deletion of 
      mscColSp components."
::= { mscColSp 1 }

mscColSpRowStatusEntry OBJECT-TYPE
   SYNTAX     MscColSpRowStatusEntry
   ACCESS     not-accessible
   STATUS     mandatory
   DESCRIPTION
     "A single entry in the table represents a single 
      mscColSp component."
   INDEX {
      mscColIndex,
      mscColSpIndex }
::= { mscColSpRowStatusTable 1 }

MscColSpRowStatusEntry ::= SEQUENCE {
   mscColSpRowStatus
      RowStatus,
   mscColSpComponentName
      DisplayString,
   mscColSpStorageType
      StorageType,
   mscColSpIndex
      NonReplicated }

mscColSpRowStatus OBJECT-TYPE
   SYNTAX     RowStatus 
   ACCESS     read-only
   STATUS     mandatory
   DESCRIPTION
     "This variable is used as the basis for SNMP naming of
      mscColSp components.
      These components cannot be added nor deleted."
::= { mscColSpRowStatusEntry 1 }

mscColSpComponentName OBJECT-TYPE
   SYNTAX     DisplayString 
   ACCESS     read-only
   STATUS     mandatory
   DESCRIPTION
     "This variable provides the component's string name for
      use with the ASCII Console Interface"
::= { mscColSpRowStatusEntry 2 }

mscColSpStorageType OBJECT-TYPE
   SYNTAX     StorageType 
   ACCESS     read-only
   STATUS     mandatory
   DESCRIPTION
     "This variable represents the storage type value for the
      mscColSp tables."
::= { mscColSpRowStatusEntry 4 }

mscColSpIndex OBJECT-TYPE
   SYNTAX     NonReplicated 
   ACCESS     not-accessible
   STATUS     mandatory
   DESCRIPTION
     "This variable represents the index for the mscColSp tables."
::= { mscColSpRowStatusEntry 10 }

mscColSpProvTable OBJECT-TYPE
   SYNTAX     SEQUENCE OF MscColSpProvEntry
   ACCESS     not-accessible
   STATUS     mandatory
   DESCRIPTION
     "This group specifies all of the provisioning data for a DCS Spooler."
::= { mscColSp 10 }

mscColSpProvEntry OBJECT-TYPE
   SYNTAX     MscColSpProvEntry
   ACCESS     not-accessible
   STATUS     mandatory
   DESCRIPTION
     "An entry in the mscColSpProvTable."
   INDEX {
      mscColIndex,
      mscColSpIndex }
::= { mscColSpProvTable 1 }

MscColSpProvEntry ::= SEQUENCE {
   mscColSpSpooling
      INTEGER,
   mscColSpMaximumNumberOfFiles
      Unsigned32 }

mscColSpSpooling OBJECT-TYPE
   SYNTAX     INTEGER  {
                 off(0),
                 on(1) }
   ACCESS     read-write
   STATUS     mandatory
   DESCRIPTION
     "This attribute specifies whether or not this type of data is spooled to 
      the disk. If set to off, it is roughly equivalent to Locking the Spooler 
      (except this will survive processor restarts).
      
      The following defaults are used:
      - alarm: on
      - accounting: on
      - log: on
      - debug: off
      - scn: on
      - trap: off (see Note below)
      - stats: on
      
      Note that SNMP Traps cannot be spooled. A semantic check 
      prevents the user from setting the value to on for the trap stream."
::= { mscColSpProvEntry 1 }

mscColSpMaximumNumberOfFiles OBJECT-TYPE
   SYNTAX     Unsigned32 (0..200)
   ACCESS     read-write
   STATUS     mandatory
   DESCRIPTION
     "This attribute specifies the maximum number of files that should be 
      kept on the disk in the directory containing the closed files of this 
      type. The value 0 is defined to mean 'unlimited'.
      
      A different default for each type of Spooler is defined as follows:
      - alarm: 30
      - accounting: 200
      - debug: 2
      - log: 10
      - scn: 10
      - trap: 2 (this value is meaningless and is ignored)
      - stats: 200"
::= { mscColSpProvEntry 2 }

mscColSpStateTable OBJECT-TYPE
   SYNTAX     SEQUENCE OF MscColSpStateEntry
   ACCESS     not-accessible
   STATUS     mandatory
   DESCRIPTION
     "This group contains the three OSI State attributes and the six OSI 
      Status attributes. The descriptions generically indicate what each 
      attribute implies about the component. Note that not all the values 
      and state combinations described here are supported by every 
      component which uses this group. For component-specific 
      information and the valid state combinations, refer to NTP 241-
      7001-150, Passport Operations and Maintenance Guide."
::= { mscColSp 11 }

mscColSpStateEntry OBJECT-TYPE
   SYNTAX     MscColSpStateEntry
   ACCESS     not-accessible
   STATUS     mandatory
   DESCRIPTION
     "An entry in the mscColSpStateTable."
   INDEX {
      mscColIndex,
      mscColSpIndex }
::= { mscColSpStateTable 1 }

MscColSpStateEntry ::= SEQUENCE {
   mscColSpAdminState
      INTEGER,
   mscColSpOperationalState
      INTEGER,
   mscColSpUsageState
      INTEGER,
   mscColSpAvailabilityStatus
      OCTET STRING,
   mscColSpProceduralStatus
      OCTET STRING,
   mscColSpControlStatus
      OCTET STRING,
   mscColSpAlarmStatus
      OCTET STRING,
   mscColSpStandbyStatus
      INTEGER,
   mscColSpUnknownStatus
      INTEGER }

mscColSpAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component.
      
      The OSI Status attributes, if supported by the component, may 
      provide more details, qualifying the state of the component."
   DEFVAL     { unlocked }
::= { mscColSpStateEntry 1 }

mscColSpOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle.
      
      The OSI Status attributes, if supported by the component, may 
      provide more details, qualifying the state of the component."
   DEFVAL     { disabled }
::= { mscColSpStateEntry 2 }

mscColSpUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time.
      
      The OSI Status attributes, if supported by the component, may 
      provide more details, qualifying the state of the component."
   DEFVAL     { idle }
::= { mscColSpStateEntry 3 }

mscColSpAvailabilityStatus OBJECT-TYPE
   SYNTAX     OCTET STRING (SIZE (2))
   ACCESS     read-only
   STATUS     mandatory
   DESCRIPTION
     "If supported by the component, this attribute indicates the OSI 
      Availability status of the component. Note that, even though it is 
      defined as a multi-valued set, at most one value is shown to the user.
      
      When no values are in the set, this indicates that either the attribute 
      is not supported or that none of the status conditions described 
      below are present.
      
      The value inTest indicates that the resource is undergoing a test 
      procedure. If adminState is locked or shuttingDown, the normal 
      users are precluded from using the resource and controlStatus is 
      reservedForTest. Tests that do not exclude additional users can be 
      present in any operational or administrative state but the 
      reservedForTest condition should not be present.
      
      The value failed indicates that the component has an internal fault 
      that prevents it from operating. The operationalState is disabled.
      
      The value dependency indicates that the component cannot operate 
      because some other resource on which it depends is unavailable. 
      The operationalState is disabled.
      
      The value powerOff indicates the resource requires power to be 
      applied and it is not powered on. The operationalState is disabled.
      
      The value offLine indicates the resource requires a routine 
      operation (either manual, automatic, or both) to be performed to 
      place it on-line and make it available for use. The operationalState 
      is disabled.
      
      The value offDuty indicates the resource is inactive in accordance 
      with a predetermined time schedule. In the absence of other 
      disabling conditions, the operationalState is enabled or disabled.
      
      The value degraded indicates the service provided by the 
      component is degraded in some way, such as in speed or operating 
      capacity. However, the resource remains available for service. The 
      operationalState is enabled.
      
      The value notInstalled indicates the resource is not present. The 
      operationalState is disabled.
      
      The value logFull is not used.

      Description of bits:
      inTest(0)
      failed(1)
      powerOff(2)
      offLine(3)
      offDuty(4)
      dependency(5)
      degraded(6)
      notInstalled(7)
      logFull(8)"
::= { mscColSpStateEntry 4 }

mscColSpProceduralStatus OBJECT-TYPE
   SYNTAX     OCTET STRING (SIZE (1))
   ACCESS     read-only
   STATUS     mandatory
   DESCRIPTION
     "If supported by the component, this attribute indicates the OSI 
      Procedural status of the component. Note that, even though it is 
      defined as a multi-valued set, at most one value is shown to the user.
      
      When no values are in the set, this indicates that either the attribute 
      is not supported or that none of the status conditions described 
      below are present.
      
      The value initializationRequired indicates (for a resource which 
      doesn't initialize autonomously) that initialization is required before 
      it can perform its normal functions, and this procedure has not been 
      initiated. The operationalState is disabled.
      
      The value notInitialized indicates (for a resource which does 
      initialize autonomously) that initialization is required before it can 
      perform its normal functions, and this procedure has not been 
      initiated. The operationalState may be enabled or disabled.
      
      The value initializing indicates that initialization has been initiated 
      but is not yet complete. The operationalState may be enabled or 
      disabled.
      
      The value reporting indicates the resource has completed some 
      processing operation and is notifying the results. The 
      operationalState is enabled.
      
      The value terminating indicates the component is in a termination 
      phase. If the resource doesn't reinitialize autonomously, 
      operationalState is disabled; otherwise it is enabled or disabled.

      Description of bits:
      initializationRequired(0)
      notInitialized(1)
      initializing(2)
      reporting(3)
      terminating(4)"
::= { mscColSpStateEntry 5 }

mscColSpControlStatus OBJECT-TYPE
   SYNTAX     OCTET STRING (SIZE (1))
   ACCESS     read-only
   STATUS     mandatory
   DESCRIPTION
     "If supported by the component, this attribute indicates the OSI 
      Control status of the component. Note that, even though it is defined 
      as a multi-valued set, at most one value is shown to the user.
      
      When no values are in the set, this indicates that either the attribute 
      is not supported or that none of the status conditions described 
      below are present.
      
      The value subjectToTest indicates the resource is available but tests 
      may be conducted simultaneously at unpredictable times, which 
      may cause it to exhibit unusual characteristics.
      
      The value partOfServicesLocked indicates that part of the service is 
      restricted from users of a resource. The adminState is unlocked.
      
      The value reservedForTest indicates that the component is 
      administratively unavailable because it is undergoing a test 
      procedure. The adminState is locked.
      
      The value suspended indicates that the service has been 
      administratively suspended.

      Description of bits:
      subjectToTest(0)
      partOfServicesLocked(1)
      reservedForTest(2)
      suspended(3)"
::= { mscColSpStateEntry 6 }

mscColSpAlarmStatus OBJECT-TYPE
   SYNTAX     OCTET STRING (SIZE (1))
   ACCESS     read-only
   STATUS     mandatory
   DESCRIPTION
     "If supported by the component, this attribute indicates the OSI 
      Alarm status of the component. Note that, even though it is defined 
      as a multi-valued set, at most one value is shown to the user.
      
      When no values are in the set, this indicates that either the attribute 
      is not supported or that none of the status conditions described 
      below are present.
      
      The value underRepair indicates the component is currently being 
      repaired. The operationalState is enabled or disabled.
      
      The value critical indicates one or more critical alarms are 
      outstanding against the component. Other, less severe, alarms may 
      also be outstanding. The operationalState is enabled or disabled.
      
      The value major indicates one or more major alarms are 
      outstanding against the component. Other, less severe, alarms may 
      also be outstanding. The operationalState is enabled or disabled.
      
      The value minor indicates one or more minor alarms are 
      outstanding against the component. Other, less severe, alarms may 
      also be outstanding. The operationalState is enabled or disabled.
      
      The value alarmOutstanding generically indicates that an alarm of 
      some severity is outstanding against the component.

      Description of bits:
      underRepair(0)
      critical(1)
      major(2)
      minor(3)
      alarmOutstanding(4)"
::= { mscColSpStateEntry 7 }

mscColSpStandbyStatus OBJECT-TYPE
   SYNTAX     INTEGER  {
                 hotStandby(0),
                 coldStandby(1),
                 providingService(2),
                 notSet(15) }
   ACCESS     read-only
   STATUS     mandatory
   DESCRIPTION
     "If supported by the component, this attribute indicates the OSI 
      Standby status of the component.
      
      The value notSet indicates that either the attribute is not supported 
      or that none of the status conditions described below are present. 
      Note that this is a non-standard value, used because the original 
      specification indicated this attribute was set-valued and thus, did not 
      provide a value to indicate that none of the other three are 
      applicable.
      
      The value hotStandby indicates that the resource is not providing 
      service but will be immediately able to take over the role of the 
      resource to be backed up, without initialization activity, and 
      containing the same information as the resource to be backed up.
      
      The value coldStandby indicates the resource is a backup for 
      another resource but will not be immediately able to take over the 
      role of the backed up resource and will require some initialization 
      activity.
      
      The value providingService indicates that this component, as a 
      backup resource, is currently backing up another resource."
   DEFVAL     { notSet }
::= { mscColSpStateEntry 8 }

mscColSpUnknownStatus OBJECT-TYPE
   SYNTAX     INTEGER  {
                 false(0),
                 true(1) }
   ACCESS     read-only
   STATUS     mandatory
   DESCRIPTION
     "This attribute indicates the OSI Unknown status of the component.
      
      The value false indicates that all of the other OSI State and Status 
      attribute values can be considered accurate.
      
      The value true indicates that the actual state of the component is not 
      known for sure."
   DEFVAL     { false }
::= { mscColSpStateEntry 9 }

mscColSpOperTable OBJECT-TYPE
   SYNTAX     SEQUENCE OF MscColSpOperEntry
   ACCESS     not-accessible
   STATUS     mandatory
   DESCRIPTION
     "This group contains the operational attributes specific to a DCS 
      Spooler."
::= { mscColSp 12 }

mscColSpOperEntry OBJECT-TYPE
   SYNTAX     MscColSpOperEntry
   ACCESS     not-accessible
   STATUS     mandatory
   DESCRIPTION
     "An entry in the mscColSpOperTable."
   INDEX {
      mscColIndex,
      mscColSpIndex }
::= { mscColSpOperTable 1 }

MscColSpOperEntry ::= SEQUENCE {
   mscColSpSpoolingFileName
      AsciiString }

mscColSpSpoolingFileName OBJECT-TYPE
   SYNTAX     AsciiString (SIZE (0..128))
   ACCESS     read-only
   STATUS     mandatory
   DESCRIPTION
     "When spooling is on, this attribute contains the name of the open 
      file into which data is currently being spooled. When spooling is 
      off, the value of this attribute is the empty string."
::= { mscColSpOperEntry 1 }

mscColSpStatsTable OBJECT-TYPE
   SYNTAX     SEQUENCE OF MscColSpStatsEntry
   ACCESS     not-accessible
   STATUS     mandatory
   DESCRIPTION
     "This group specifies the statistics operational attributes of the DCS 
      Collector, Agent and Spooler components."
::= { mscColSp 13 }

mscColSpStatsEntry OBJECT-TYPE
   SYNTAX     MscColSpStatsEntry
   ACCESS     not-accessible
   STATUS     mandatory
   DESCRIPTION
     "An entry in the mscColSpStatsTable."
   INDEX {
      mscColIndex,
      mscColSpIndex }
::= { mscColSpStatsTable 1 }

MscColSpStatsEntry ::= SEQUENCE {
   mscColSpCurrentQueueSize
      Gauge32,
   mscColSpRecordsRx
      Counter32,
   mscColSpRecordsDiscarded
      Counter32 }

mscColSpCurrentQueueSize OBJECT-TYPE
   SYNTAX     Gauge32 (0..4294967295)
   ACCESS     read-only
   STATUS     mandatory
   DESCRIPTION
     "This gauge contains the current number of records held by this DCS 
      component."
::= { mscColSpStatsEntry 1 }

mscColSpRecordsRx OBJECT-TYPE
   SYNTAX     Counter32 
   ACCESS     read-only
   STATUS     mandatory
   DESCRIPTION
     "This counter contains the cumulative number of records received by 
      a DCS component, from applications which send data to it, since 
      the processor last restarted.
      
      This counter wraps to 0 when the maximum value is exceeded."
::= { mscColSpStatsEntry 2 }

mscColSpRecordsDiscarded OBJECT-TYPE
   SYNTAX     Counter32 
   ACCESS     read-only
   STATUS     mandatory
   DESCRIPTION
     "This is the cumulative number of records discarded by this DCS 
      component since the processor last restarted.
      
      This counter wraps to 0 when the maximum value is exceeded."
::= { mscColSpStatsEntry 3 }

-- 
-- *** THIS SUBTREE CURRENTLY NOT IMPLEMENTED ***
-- 

-- Col/<dataType> Agent/<cardNumber> 
-- A DCS Agent is an operational subcomponent of a Collector. One 
-- Agent instance exists for each Card that is running as active or 
-- standby.

mscColAg OBJECT IDENTIFIER ::= { mscCol 3 }



mscColAgRowStatusTable OBJECT-TYPE
   SYNTAX     SEQUENCE OF MscColAgRowStatusEntry
   ACCESS     not-accessible
   STATUS     mandatory
   DESCRIPTION
     "*** THIS TABLE CURRENTLY NOT IMPLEMENTED ***

      This entry controls the addition and deletion of 
      mscColAg components."
::= { mscColAg 1 }

mscColAgRowStatusEntry OBJECT-TYPE
   SYNTAX     MscColAgRowStatusEntry
   ACCESS     not-accessible
   STATUS     mandatory
   DESCRIPTION
     "A single entry in the table represents a single 
      mscColAg component."
   INDEX {
      mscColIndex,
      mscColAgIndex }
::= { mscColAgRowStatusTable 1 }

MscColAgRowStatusEntry ::= SEQUENCE {
   mscColAgRowStatus
      RowStatus,
   mscColAgComponentName
      DisplayString,
   mscColAgStorageType
      StorageType,
   mscColAgIndex
      Integer32 }

mscColAgRowStatus OBJECT-TYPE
   SYNTAX     RowStatus 
   ACCESS     read-only
   STATUS     mandatory
   DESCRIPTION
     "This variable is used as the basis for SNMP naming of
      mscColAg components.
      These components cannot be added nor deleted."
::= { mscColAgRowStatusEntry 1 }

mscColAgComponentName OBJECT-TYPE
   SYNTAX     DisplayString 
   ACCESS     read-only
   STATUS     mandatory
   DESCRIPTION
     "This variable provides the component's string name for
      use with the ASCII Console Interface"
::= { mscColAgRowStatusEntry 2 }

mscColAgStorageType OBJECT-TYPE
   SYNTAX     StorageType 
   ACCESS     read-only
   STATUS     mandatory
   DESCRIPTION
     "This variable represents the storage type value for the
      mscColAg tables."
::= { mscColAgRowStatusEntry 4 }

mscColAgIndex OBJECT-TYPE
   SYNTAX     Integer32 (0..15)
   ACCESS     not-accessible
   STATUS     mandatory
   DESCRIPTION
     "This variable represents the index for the mscColAg tables."
::= { mscColAgRowStatusEntry 10 }

mscColAgStatsTable OBJECT-TYPE
   SYNTAX     SEQUENCE OF MscColAgStatsEntry
   ACCESS     not-accessible
   STATUS     mandatory
   DESCRIPTION
     "*** THIS TABLE CURRENTLY NOT IMPLEMENTED ***

      This group specifies the statistics operational attributes of the DCS 
      Collector, Agent and Spooler components."
::= { mscColAg 10 }

mscColAgStatsEntry OBJECT-TYPE
   SYNTAX     MscColAgStatsEntry
   ACCESS     not-accessible
   STATUS     mandatory
   DESCRIPTION
     "An entry in the mscColAgStatsTable."
   INDEX {
      mscColIndex,
      mscColAgIndex }
::= { mscColAgStatsTable 1 }

MscColAgStatsEntry ::= SEQUENCE {
   mscColAgCurrentQueueSize
      Gauge32,
   mscColAgRecordsRx
      Counter32,
   mscColAgRecordsDiscarded
      Counter32 }

mscColAgCurrentQueueSize OBJECT-TYPE
   SYNTAX     Gauge32 (0..4294967295)
   ACCESS     read-only
   STATUS     mandatory
   DESCRIPTION
     "This gauge contains the current number of records held by this DCS 
      component."
::= { mscColAgStatsEntry 1 }

mscColAgRecordsRx OBJECT-TYPE
   SYNTAX     Counter32 
   ACCESS     read-only
   STATUS     mandatory
   DESCRIPTION
     "This counter contains the cumulative number of records received by 
      a DCS component, from applications which send data to it, since 
      the processor last restarted.
      
      This counter wraps to 0 when the maximum value is exceeded."
::= { mscColAgStatsEntry 2 }

mscColAgRecordsDiscarded OBJECT-TYPE
   SYNTAX     Counter32 
   ACCESS     read-only
   STATUS     mandatory
   DESCRIPTION
     "This is the cumulative number of records discarded by this DCS 
      component since the processor last restarted.
      
      This counter wraps to 0 when the maximum value is exceeded."
::= { mscColAgStatsEntry 3 }

mscColAgAgentStatsTable OBJECT-TYPE
   SYNTAX     SEQUENCE OF MscColAgAgentStatsEntry
   ACCESS     not-accessible
   STATUS     mandatory
   DESCRIPTION
     "*** THIS TABLE CURRENTLY NOT IMPLEMENTED ***

      This group contains the statistical attributes specific to the DCS 
      Agent components."
::= { mscColAg 11 }

mscColAgAgentStatsEntry OBJECT-TYPE
   SYNTAX     MscColAgAgentStatsEntry
   ACCESS     not-accessible
   STATUS     mandatory
   DESCRIPTION
     "An entry in the mscColAgAgentStatsTable."
   INDEX {
      mscColIndex,
      mscColAgIndex }
::= { mscColAgAgentStatsTable 1 }

MscColAgAgentStatsEntry ::= SEQUENCE {
   mscColAgRecordsNotGenerated
      Counter32 }

mscColAgRecordsNotGenerated OBJECT-TYPE
   SYNTAX     Counter32 
   ACCESS     read-only
   STATUS     mandatory
   DESCRIPTION
     "This attribute counts the records of a particular event type on this 
      Card which could not be generated by some application due to 
      some problem such as insufficient resources. One cannot tell exactly 
      which event could not be generated, nor which application instance 
      tried to generate it, but when this count increases, it is an indicator 
      that some re-engineering may be required and will provide some 
      idea as to why a record is missing.
      
      This counter wraps to 0 when the maximum value is exceeded."
::= { mscColAgAgentStatsEntry 1 }




-- 
-- Version and Compliance statements
-- 



-- Object-Group Statement:
-- A list of all current accessible leaf objects.

-- OBJECTS { mscColTimesValue,
--           mscColAgRowStatus,
--           mscColSpUnknownStatus,
--           mscColTimesRowStatus,
--           mscColSpProceduralStatus,
--           mscColAgRecordsDiscarded,
--           mscColSpAvailabilityStatus,
--           mscColAgStorageType,
--           mscColSpRowStatus,
--           mscColSpSpoolingFileName,
--           mscColSpAlarmStatus,
--           mscColSpUsageState,
--           mscColCurrentQueueSize,
--           mscColRowStatus,
--           mscColSpRecordsDiscarded,
--           mscColSpMaximumNumberOfFiles,
--           mscColSpComponentName,
--           mscColSpStandbyStatus,
--           mscColRecordsDiscarded,
--           mscColSpStorageType,
--           mscColSpRecordsRx,
--           mscColAgRecordsRx,
--           mscColSpSpooling,
--           mscColPeakRowStatus,
--           mscColSpOperationalState,
--           mscColAgComponentName,
--           mscColComponentName,
--           mscColPeakValue,
--           mscColSpControlStatus,
--           mscColSpAdminState,
--           mscColStorageType,
--           mscColRecordsRx,
--           mscColSpCurrentQueueSize,
--           mscColAgCurrentQueueSize,
--           mscColAgRecordsNotGenerated }
-- STATUS  mandatory
-- DESCRIPTION
--   "A list of all current accessible leaf objects."

dataCollectionGroup OBJECT IDENTIFIER ::= { dataCollectionMIB 1 }
dataCollectionGroupCA OBJECT IDENTIFIER ::= { dataCollectionGroup 1 }
dataCollectionGroupCA02 OBJECT IDENTIFIER ::= { dataCollectionGroupCA 3 }
dataCollectionGroupCA02A OBJECT IDENTIFIER ::= { dataCollectionGroupCA02 2 }



-- Agent-Capabilities Statement:

-- PRODUCT-RELEASE "MscPassport Release 1.2 DataCollection."
-- STATUS          mandatory
-- DESCRIPTION     "Carrier Passport DataCollection MIB: MIB Version CA02A,
--                  Software Version CA02S9C."
-- SUPPORTS        Nortel-MsCarrier-MscPassport-DataCollectionMIB
--    INCLUDES     { dataCollectionGroupCA02A }

dataCollectionCapabilities OBJECT IDENTIFIER ::= { dataCollectionMIB 3 }
dataCollectionCapabilitiesCA OBJECT IDENTIFIER ::= { dataCollectionCapabilities 1 }
dataCollectionCapabilitiesCA02 OBJECT IDENTIFIER ::= { dataCollectionCapabilitiesCA 3 }
dataCollectionCapabilitiesCA02A OBJECT IDENTIFIER ::= { dataCollectionCapabilitiesCA02 2 }





END
