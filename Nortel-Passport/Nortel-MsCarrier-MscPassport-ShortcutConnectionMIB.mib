Nortel-MsCarrier-MscPassport-ShortcutConnectionMIB
DEFINITIONS ::= BEGIN



IMPORTS

      OBJECT-TYPE
   FROM RFC-1212

      mscPassportMIBs
   FROM Nortel-MsCarrier-MscPassport-UsefulDefinitionsMIB

      Counter32,
      RowPointer,
      DisplayString,
      StorageType,
      RowStatus,
      Integer32,
      Unsigned32
   FROM Nortel-MsCarrier-MscPassport-StandardTextualConventionsMIB

      NonReplicated,
      HexString
   FROM Nortel-MsCarrier-MscPassport-TextualConventionsMIB

      mscVrIndex,
      mscVrPp,
      mscVrPpIndex
   FROM Nortel-MsCarrier-MscPassport-VirtualRouterMIB;




-- LAST-UPDATED   "9909010000Z"
-- ORGANIZATION   "Nortel Networks"
-- CONTACT-INFO   "
--         Nortel Carrier Data Network Management
--         
--         Postal:       P.O. Box 3511, Station C 
--                       Ottawa, Ontario 
--                       Canada  K1Y 4H7
--         
--         via the WEB:  http://www.nortelnetworks.com  
--                       select 'Contact Us' from the menu
--          
--         via phone:    1-800-4NORTEL"
-- DESCRIPTION
--    "The module describing the Nortel MsCarrier MscPassport
--     ShortcutConnection Enterprise MIB."

shortcutConnectionMIB OBJECT IDENTIFIER ::= { mscPassportMIBs 78 }









-- 
-- *** THIS SUBTREE CURRENTLY NOT IMPLEMENTED ***
-- 

-- Vr/<string> Pp/<string> ShortcutConnection/n
-- This component represents a shortcut connection (SVC) for use by 
-- NHRP.

mscVrPpSc OBJECT IDENTIFIER ::= { mscVrPp 16 }



mscVrPpScRowStatusTable OBJECT-TYPE
   SYNTAX     SEQUENCE OF MscVrPpScRowStatusEntry
   ACCESS     not-accessible
   STATUS     mandatory
   DESCRIPTION
     "*** THIS TABLE CURRENTLY NOT IMPLEMENTED ***

      This entry controls the addition and deletion of 
      mscVrPpSc components."
::= { mscVrPpSc 1 }

mscVrPpScRowStatusEntry OBJECT-TYPE
   SYNTAX     MscVrPpScRowStatusEntry
   ACCESS     not-accessible
   STATUS     mandatory
   DESCRIPTION
     "A single entry in the table represents a single 
      mscVrPpSc component."
   INDEX {
      mscVrIndex,
      mscVrPpIndex,
      mscVrPpScIndex }
::= { mscVrPpScRowStatusTable 1 }

MscVrPpScRowStatusEntry ::= SEQUENCE {
   mscVrPpScRowStatus
      RowStatus,
   mscVrPpScComponentName
      DisplayString,
   mscVrPpScStorageType
      StorageType,
   mscVrPpScIndex
      Integer32 }

mscVrPpScRowStatus OBJECT-TYPE
   SYNTAX     RowStatus 
   ACCESS     read-only
   STATUS     mandatory
   DESCRIPTION
     "This variable is used as the basis for SNMP naming of
      mscVrPpSc components.
      These components cannot be added nor deleted."
::= { mscVrPpScRowStatusEntry 1 }

mscVrPpScComponentName OBJECT-TYPE
   SYNTAX     DisplayString 
   ACCESS     read-only
   STATUS     mandatory
   DESCRIPTION
     "This variable provides the component's string name for
      use with the ASCII Console Interface"
::= { mscVrPpScRowStatusEntry 2 }

mscVrPpScStorageType OBJECT-TYPE
   SYNTAX     StorageType 
   ACCESS     read-only
   STATUS     mandatory
   DESCRIPTION
     "This variable represents the storage type value for the
      mscVrPpSc tables."
::= { mscVrPpScRowStatusEntry 4 }

mscVrPpScIndex OBJECT-TYPE
   SYNTAX     Integer32 (0..1023)
   ACCESS     not-accessible
   STATUS     mandatory
   DESCRIPTION
     "This variable represents the index for the mscVrPpSc tables."
::= { mscVrPpScRowStatusEntry 10 }

mscVrPpScOperTable OBJECT-TYPE
   SYNTAX     SEQUENCE OF MscVrPpScOperEntry
   ACCESS     not-accessible
   STATUS     mandatory
   DESCRIPTION
     "*** THIS TABLE CURRENTLY NOT IMPLEMENTED ***

      This group contains the operational status attributes of the 
      ShortcutConnection component."
::= { mscVrPpSc 10 }

mscVrPpScOperEntry OBJECT-TYPE
   SYNTAX     MscVrPpScOperEntry
   ACCESS     not-accessible
   STATUS     mandatory
   DESCRIPTION
     "An entry in the mscVrPpScOperTable."
   INDEX {
      mscVrIndex,
      mscVrPpIndex,
      mscVrPpScIndex }
::= { mscVrPpScOperTable 1 }

MscVrPpScOperEntry ::= SEQUENCE {
   mscVrPpScRemoteNbmaAddress
      HexString,
   mscVrPpScAge
      Unsigned32,
   mscVrPpScMtu
      Unsigned32,
   mscVrPpScConnSource
      INTEGER,
   mscVrPpScType
      INTEGER }

mscVrPpScRemoteNbmaAddress OBJECT-TYPE
   SYNTAX     HexString (SIZE (0..20))
   ACCESS     read-only
   STATUS     mandatory
   DESCRIPTION
     "This attribute indicates the NBMA address of the far (remote) end."
::= { mscVrPpScOperEntry 1 }

mscVrPpScAge OBJECT-TYPE
   SYNTAX     Unsigned32 (0..4292967295)
   ACCESS     read-only
   STATUS     mandatory
   DESCRIPTION
     "This attribute indicates how long the connection has been up."
::= { mscVrPpScOperEntry 2 }

mscVrPpScMtu OBJECT-TYPE
   SYNTAX     Unsigned32 (0..0 | 576..18944)
   ACCESS     read-only
   STATUS     mandatory
   DESCRIPTION
     "This attribute indicates the Layer 2 MTU (that is, CPCS-SDU for 
      ATM) of this connection."
::= { mscVrPpScOperEntry 3 }

mscVrPpScConnSource OBJECT-TYPE
   SYNTAX     INTEGER  {
                 local(1),
                 remote(2) }
   ACCESS     read-only
   STATUS     mandatory
   DESCRIPTION
     "This attributes indicates which end originated the connect request 
      for this connection."
::= { mscVrPpScOperEntry 4 }

mscVrPpScType OBJECT-TYPE
   SYNTAX     INTEGER  {
                 unidirectional(1),
                 bidirectional(2) }
   ACCESS     read-only
   STATUS     mandatory
   DESCRIPTION
     "This attributes indicates the type of this connection."
::= { mscVrPpScOperEntry 5 }

mscVrPpScStatsTable OBJECT-TYPE
   SYNTAX     SEQUENCE OF MscVrPpScStatsEntry
   ACCESS     not-accessible
   STATUS     mandatory
   DESCRIPTION
     "*** THIS TABLE CURRENTLY NOT IMPLEMENTED ***

      This group contains the statistical attributes of the 
      ShortcutConnection component."
::= { mscVrPpSc 11 }

mscVrPpScStatsEntry OBJECT-TYPE
   SYNTAX     MscVrPpScStatsEntry
   ACCESS     not-accessible
   STATUS     mandatory
   DESCRIPTION
     "An entry in the mscVrPpScStatsTable."
   INDEX {
      mscVrIndex,
      mscVrPpIndex,
      mscVrPpScIndex }
::= { mscVrPpScStatsTable 1 }

MscVrPpScStatsEntry ::= SEQUENCE {
   mscVrPpScTxFrames
      Counter32,
   mscVrPpScRxFrames
      Counter32 }

mscVrPpScTxFrames OBJECT-TYPE
   SYNTAX     Counter32 
   ACCESS     read-only
   STATUS     mandatory
   DESCRIPTION
     "This attribute counts the frames transmitted over this connection.
      This counter wraps to zero when the maximum value is exceeded."
::= { mscVrPpScStatsEntry 1 }

mscVrPpScRxFrames OBJECT-TYPE
   SYNTAX     Counter32 
   ACCESS     read-only
   STATUS     mandatory
   DESCRIPTION
     "This attributes counts the frames received over this connection.
      This counter wraps to zero when the maximum value is exceeded."
::= { mscVrPpScStatsEntry 2 }

-- 
-- *** THIS SUBTREE CURRENTLY NOT IMPLEMENTED ***
-- 

-- An AtmConnection component is created for each ATM connection 
-- established by an application. It shows where the data traffic for this 
-- connection is directed.

mscVrPpScAtmCon OBJECT IDENTIFIER ::= { mscVrPpSc 4 }



mscVrPpScAtmConRowStatusTable OBJECT-TYPE
   SYNTAX     SEQUENCE OF MscVrPpScAtmConRowStatusEntry
   ACCESS     not-accessible
   STATUS     mandatory
   DESCRIPTION
     "*** THIS TABLE CURRENTLY NOT IMPLEMENTED ***

      This entry controls the addition and deletion of 
      mscVrPpScAtmCon components."
::= { mscVrPpScAtmCon 1 }

mscVrPpScAtmConRowStatusEntry OBJECT-TYPE
   SYNTAX     MscVrPpScAtmConRowStatusEntry
   ACCESS     not-accessible
   STATUS     mandatory
   DESCRIPTION
     "A single entry in the table represents a single 
      mscVrPpScAtmCon component."
   INDEX {
      mscVrIndex,
      mscVrPpIndex,
      mscVrPpScIndex,
      mscVrPpScAtmConIndex }
::= { mscVrPpScAtmConRowStatusTable 1 }

MscVrPpScAtmConRowStatusEntry ::= SEQUENCE {
   mscVrPpScAtmConRowStatus
      RowStatus,
   mscVrPpScAtmConComponentName
      DisplayString,
   mscVrPpScAtmConStorageType
      StorageType,
   mscVrPpScAtmConIndex
      NonReplicated }

mscVrPpScAtmConRowStatus OBJECT-TYPE
   SYNTAX     RowStatus 
   ACCESS     read-only
   STATUS     mandatory
   DESCRIPTION
     "This variable is used as the basis for SNMP naming of
      mscVrPpScAtmCon components.
      These components cannot be added nor deleted."
::= { mscVrPpScAtmConRowStatusEntry 1 }

mscVrPpScAtmConComponentName OBJECT-TYPE
   SYNTAX     DisplayString 
   ACCESS     read-only
   STATUS     mandatory
   DESCRIPTION
     "This variable provides the component's string name for
      use with the ASCII Console Interface"
::= { mscVrPpScAtmConRowStatusEntry 2 }

mscVrPpScAtmConStorageType OBJECT-TYPE
   SYNTAX     StorageType 
   ACCESS     read-only
   STATUS     mandatory
   DESCRIPTION
     "This variable represents the storage type value for the
      mscVrPpScAtmCon tables."
::= { mscVrPpScAtmConRowStatusEntry 4 }

mscVrPpScAtmConIndex OBJECT-TYPE
   SYNTAX     NonReplicated 
   ACCESS     not-accessible
   STATUS     mandatory
   DESCRIPTION
     "This variable represents the index for the mscVrPpScAtmCon tables."
::= { mscVrPpScAtmConRowStatusEntry 10 }

mscVrPpScAtmConOperTable OBJECT-TYPE
   SYNTAX     SEQUENCE OF MscVrPpScAtmConOperEntry
   ACCESS     not-accessible
   STATUS     mandatory
   DESCRIPTION
     "*** THIS TABLE CURRENTLY NOT IMPLEMENTED ***

      This attribute group contains the operational attributes for the 
      NapAtmConnection component."
::= { mscVrPpScAtmCon 10 }

mscVrPpScAtmConOperEntry OBJECT-TYPE
   SYNTAX     MscVrPpScAtmConOperEntry
   ACCESS     not-accessible
   STATUS     mandatory
   DESCRIPTION
     "An entry in the mscVrPpScAtmConOperTable."
   INDEX {
      mscVrIndex,
      mscVrPpIndex,
      mscVrPpScIndex,
      mscVrPpScAtmConIndex }
::= { mscVrPpScAtmConOperTable 1 }

MscVrPpScAtmConOperEntry ::= SEQUENCE {
   mscVrPpScAtmConNextHop
      RowPointer }

mscVrPpScAtmConNextHop OBJECT-TYPE
   SYNTAX     RowPointer 
   ACCESS     read-only
   STATUS     mandatory
   DESCRIPTION
     "This attribute shows the component name of the AtmIf Vcc Ep or 
      AtmCon component to which this switched connection is 
      established."
::= { mscVrPpScAtmConOperEntry 1 }




-- 
-- Version and Compliance statements
-- 



-- Object-Group Statement:
-- A list of all current accessible leaf objects.

-- OBJECTS { mscVrPpScConnSource,
--           mscVrPpScType,
--           mscVrPpScAtmConNextHop,
--           mscVrPpScMtu,
--           mscVrPpScTxFrames,
--           mscVrPpScComponentName,
--           mscVrPpScAtmConStorageType,
--           mscVrPpScAtmConRowStatus,
--           mscVrPpScRxFrames,
--           mscVrPpScAge,
--           mscVrPpScStorageType,
--           mscVrPpScRowStatus,
--           mscVrPpScRemoteNbmaAddress,
--           mscVrPpScAtmConComponentName }
-- STATUS  mandatory
-- DESCRIPTION
--   "A list of all current accessible leaf objects."

shortcutConnectionGroup OBJECT IDENTIFIER ::= { shortcutConnectionMIB 1 }
shortcutConnectionGroupCA OBJECT IDENTIFIER ::= { shortcutConnectionGroup 1 }
shortcutConnectionGroupCA02 OBJECT IDENTIFIER ::= { shortcutConnectionGroupCA 3 }
shortcutConnectionGroupCA02A OBJECT IDENTIFIER ::= { shortcutConnectionGroupCA02 2 }



-- Agent-Capabilities Statement:

-- PRODUCT-RELEASE "MscPassport Release 1.2 ShortcutConnection."
-- STATUS          mandatory
-- DESCRIPTION     "Carrier Passport ShortcutConnection MIB: MIB Version CA02A,
--                  Software Version CA02S9C."
-- SUPPORTS        Nortel-MsCarrier-MscPassport-ShortcutConnectionMIB
--    INCLUDES     { shortcutConnectionGroupCA02A }

shortcutConnectionCapabilities OBJECT IDENTIFIER ::= { shortcutConnectionMIB 3 }
shortcutConnectionCapabilitiesCA OBJECT IDENTIFIER ::= { shortcutConnectionCapabilities 1 }
shortcutConnectionCapabilitiesCA02 OBJECT IDENTIFIER ::= { shortcutConnectionCapabilitiesCA 3 }
shortcutConnectionCapabilitiesCA02A OBJECT IDENTIFIER ::= { shortcutConnectionCapabilitiesCA02 2 }





END
