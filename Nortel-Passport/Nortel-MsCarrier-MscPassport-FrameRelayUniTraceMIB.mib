Nortel-MsCarrier-MscPassport-FrameRelayUniTraceMIB
DEFINITIONS ::= BEGIN



IMPORTS

      OBJECT-TYPE
   FROM RFC-1212

      mscPassportMIBs
   FROM Nortel-MsCarrier-MscPassport-UsefulDefinitionsMIB

      RowPointer,
      DisplayString,
      StorageType,
      RowStatus,
      Unsigned32
   FROM Nortel-MsCarrier-MscPassport-StandardTextualConventionsMIB

      AsciiString,
      NonReplicated
   FROM Nortel-MsCarrier-MscPassport-TextualConventionsMIB

      mscFrUniIndex,
      mscFrUni
   FROM Nortel-MsCarrier-MscPassport-FrameRelayUniMIB;




-- LAST-UPDATED   "9909010000Z"
-- ORGANIZATION   "Nortel Networks"
-- CONTACT-INFO   "
--         Nortel Carrier Data Network Management
--         
--         Postal:       P.O. Box 3511, Station C 
--                       Ottawa, Ontario 
--                       Canada  K1Y 4H7
--         
--         via the WEB:  http://www.nortelnetworks.com  
--                       select 'Contact Us' from the menu
--          
--         via phone:    1-800-4NORTEL"
-- DESCRIPTION
--    "The module describing the Nortel MsCarrier MscPassport
--     FrameRelayUniTrace Enterprise MIB."

frameRelayUniTraceMIB OBJECT IDENTIFIER ::= { mscPassportMIBs 105 }










-- FrUni/n Trace
-- FrNni/n Trace
-- The Trace component of the Frame Relay service determines if the 
-- trace capability is allowed on this interface. If it is not provisioned, 
-- then a trace session cannot be started on this service.

mscFrUniTrace OBJECT IDENTIFIER ::= { mscFrUni 7 }



mscFrUniTraceRowStatusTable OBJECT-TYPE
   SYNTAX     SEQUENCE OF MscFrUniTraceRowStatusEntry
   ACCESS     not-accessible
   STATUS     mandatory
   DESCRIPTION
     "This entry controls the addition and deletion of 
      mscFrUniTrace components."
::= { mscFrUniTrace 1 }

mscFrUniTraceRowStatusEntry OBJECT-TYPE
   SYNTAX     MscFrUniTraceRowStatusEntry
   ACCESS     not-accessible
   STATUS     mandatory
   DESCRIPTION
     "A single entry in the table represents a single 
      mscFrUniTrace component."
   INDEX {
      mscFrUniIndex,
      mscFrUniTraceIndex }
::= { mscFrUniTraceRowStatusTable 1 }

MscFrUniTraceRowStatusEntry ::= SEQUENCE {
   mscFrUniTraceRowStatus
      RowStatus,
   mscFrUniTraceComponentName
      DisplayString,
   mscFrUniTraceStorageType
      StorageType,
   mscFrUniTraceIndex
      NonReplicated }

mscFrUniTraceRowStatus OBJECT-TYPE
   SYNTAX     RowStatus 
   ACCESS     read-write
   STATUS     mandatory
   DESCRIPTION
     "This variable is used as the basis for SNMP naming of
      mscFrUniTrace components.
      These components can be added and deleted."
::= { mscFrUniTraceRowStatusEntry 1 }

mscFrUniTraceComponentName OBJECT-TYPE
   SYNTAX     DisplayString 
   ACCESS     read-only
   STATUS     mandatory
   DESCRIPTION
     "This variable provides the component's string name for
      use with the ASCII Console Interface"
::= { mscFrUniTraceRowStatusEntry 2 }

mscFrUniTraceStorageType OBJECT-TYPE
   SYNTAX     StorageType 
   ACCESS     read-only
   STATUS     mandatory
   DESCRIPTION
     "This variable represents the storage type value for the
      mscFrUniTrace tables."
::= { mscFrUniTraceRowStatusEntry 4 }

mscFrUniTraceIndex OBJECT-TYPE
   SYNTAX     NonReplicated 
   ACCESS     not-accessible
   STATUS     mandatory
   DESCRIPTION
     "This variable represents the index for the mscFrUniTrace tables."
::= { mscFrUniTraceRowStatusEntry 10 }

mscFrUniTraceOperationalTable OBJECT-TYPE
   SYNTAX     SEQUENCE OF MscFrUniTraceOperationalEntry
   ACCESS     not-accessible
   STATUS     mandatory
   DESCRIPTION
     "This group provides the operational attributes for the Trace 
      component."
::= { mscFrUniTrace 10 }

mscFrUniTraceOperationalEntry OBJECT-TYPE
   SYNTAX     MscFrUniTraceOperationalEntry
   ACCESS     not-accessible
   STATUS     mandatory
   DESCRIPTION
     "An entry in the mscFrUniTraceOperationalTable."
   INDEX {
      mscFrUniIndex,
      mscFrUniTraceIndex }
::= { mscFrUniTraceOperationalTable 1 }

MscFrUniTraceOperationalEntry ::= SEQUENCE {
   mscFrUniTraceReceiverName
      AsciiString,
   mscFrUniTraceDuration
      Unsigned32,
   mscFrUniTraceQueueLimit
      Unsigned32,
   mscFrUniTraceSession
      RowPointer }

mscFrUniTraceReceiverName OBJECT-TYPE
   SYNTAX     AsciiString (SIZE (0..8))
   ACCESS     read-write
   STATUS     mandatory
   DESCRIPTION
     "This attribute should be set to the name of the desired trace receiver 
      before starting a trace session. All available trace receivers are listed 
      under the Trace Rcvr/<string> component. This attribute cannot be 
      set while a trace is active."
::= { mscFrUniTraceOperationalEntry 2 }

mscFrUniTraceDuration OBJECT-TYPE
   SYNTAX     Unsigned32 (0..9999)
   ACCESS     read-write
   STATUS     mandatory
   DESCRIPTION
     "This attribute specifies the duration, in minutes, of a trace session. 
      A value of 0 indicates unlimited duration in which case a trace 
      session remains active until a stop command is issued. The default 
      duration is 60 minutes. This attribute cannot be set while a trace is 
      active."
   DEFVAL     { 60 }
::= { mscFrUniTraceOperationalEntry 3 }

mscFrUniTraceQueueLimit OBJECT-TYPE
   SYNTAX     Unsigned32 (1..100)
   ACCESS     read-write
   STATUS     mandatory
   DESCRIPTION
     "This attribute specifies the total number of bytes of traced data 
      which may be queued for transmission to the trace receiver. When 
      this limit is exceeded, incoming traced frames are discarded. This 
      attribute can be set while a trace is active and takes effect 
      immediately."
   DEFVAL     { 20 }
::= { mscFrUniTraceOperationalEntry 4 }

mscFrUniTraceSession OBJECT-TYPE
   SYNTAX     RowPointer 
   ACCESS     read-only
   STATUS     mandatory
   DESCRIPTION
     "This attribute is set automatically. It identifies the Trace Session 
      component which is forwarding the trace data. This attribute is 
      empty unless a trace is active."
::= { mscFrUniTraceOperationalEntry 5 }


-- FrUni/n Trace Filter 
-- FrNni/n Trace Filter
-- The Filter component defines the type of traced data that is sent to 
-- the receiver. The Filter component provides default values for all its 
-- attributes which are sufficient to start a trace session. Nonetheless, if 
-- needed, these attributes may be changed before or during a trace 
-- session.

mscFrUniTraceFilter OBJECT IDENTIFIER ::= { mscFrUniTrace 2 }



mscFrUniTraceFilterRowStatusTable OBJECT-TYPE
   SYNTAX     SEQUENCE OF MscFrUniTraceFilterRowStatusEntry
   ACCESS     not-accessible
   STATUS     mandatory
   DESCRIPTION
     "This entry controls the addition and deletion of 
      mscFrUniTraceFilter components."
::= { mscFrUniTraceFilter 1 }

mscFrUniTraceFilterRowStatusEntry OBJECT-TYPE
   SYNTAX     MscFrUniTraceFilterRowStatusEntry
   ACCESS     not-accessible
   STATUS     mandatory
   DESCRIPTION
     "A single entry in the table represents a single 
      mscFrUniTraceFilter component."
   INDEX {
      mscFrUniIndex,
      mscFrUniTraceIndex,
      mscFrUniTraceFilterIndex }
::= { mscFrUniTraceFilterRowStatusTable 1 }

MscFrUniTraceFilterRowStatusEntry ::= SEQUENCE {
   mscFrUniTraceFilterRowStatus
      RowStatus,
   mscFrUniTraceFilterComponentName
      DisplayString,
   mscFrUniTraceFilterStorageType
      StorageType,
   mscFrUniTraceFilterIndex
      NonReplicated }

mscFrUniTraceFilterRowStatus OBJECT-TYPE
   SYNTAX     RowStatus 
   ACCESS     read-only
   STATUS     mandatory
   DESCRIPTION
     "This variable is used as the basis for SNMP naming of
      mscFrUniTraceFilter components.
      These components cannot be added nor deleted."
::= { mscFrUniTraceFilterRowStatusEntry 1 }

mscFrUniTraceFilterComponentName OBJECT-TYPE
   SYNTAX     DisplayString 
   ACCESS     read-only
   STATUS     mandatory
   DESCRIPTION
     "This variable provides the component's string name for
      use with the ASCII Console Interface"
::= { mscFrUniTraceFilterRowStatusEntry 2 }

mscFrUniTraceFilterStorageType OBJECT-TYPE
   SYNTAX     StorageType 
   ACCESS     read-only
   STATUS     mandatory
   DESCRIPTION
     "This variable represents the storage type value for the
      mscFrUniTraceFilter tables."
::= { mscFrUniTraceFilterRowStatusEntry 4 }

mscFrUniTraceFilterIndex OBJECT-TYPE
   SYNTAX     NonReplicated 
   ACCESS     not-accessible
   STATUS     mandatory
   DESCRIPTION
     "This variable represents the index for the mscFrUniTraceFilter tables."
::= { mscFrUniTraceFilterRowStatusEntry 10 }

mscFrUniTraceFilterOperationalTable OBJECT-TYPE
   SYNTAX     SEQUENCE OF MscFrUniTraceFilterOperationalEntry
   ACCESS     not-accessible
   STATUS     mandatory
   DESCRIPTION
     "This group provides the operational attributes for the Frame Relay 
      Trace Filter component."
::= { mscFrUniTraceFilter 10 }

mscFrUniTraceFilterOperationalEntry OBJECT-TYPE
   SYNTAX     MscFrUniTraceFilterOperationalEntry
   ACCESS     not-accessible
   STATUS     mandatory
   DESCRIPTION
     "An entry in the mscFrUniTraceFilterOperationalTable."
   INDEX {
      mscFrUniIndex,
      mscFrUniTraceIndex,
      mscFrUniTraceFilterIndex }
::= { mscFrUniTraceFilterOperationalTable 1 }

MscFrUniTraceFilterOperationalEntry ::= SEQUENCE {
   mscFrUniTraceFilterTraceType
      OCTET STRING,
   mscFrUniTraceFilterTracedDlci
      Unsigned32,
   mscFrUniTraceFilterDirection
      OCTET STRING,
   mscFrUniTraceFilterTracedLength
      Unsigned32 }

mscFrUniTraceFilterTraceType OBJECT-TYPE
   SYNTAX     OCTET STRING (SIZE (1))
   ACCESS     read-write
   STATUS     mandatory
   DESCRIPTION
     "This attribute specifies the level of filtering required for this trace 
      session. A value of lmi indicates that Lmi frames are traced. A 
      value of dlci indicates that frames from the Dlci specified by the 
      tracedDlci attribute are traced. A value of badFrames indicates that 
      bad received frames (overruns, CRC errors, aborts) are traced. The 
      default is to trace all frames. This attribute can be set while a trace 
      is active and takes effect immediately.

      Description of bits:
      lmi(0)
      dlci(1)
      badFrames(2)"
   DEFVAL     { 'e0'H }
::= { mscFrUniTraceFilterOperationalEntry 1 }

mscFrUniTraceFilterTracedDlci OBJECT-TYPE
   SYNTAX     Unsigned32 (0..1007)
   ACCESS     read-write
   STATUS     mandatory
   DESCRIPTION
     "This attribute specifies a particular Dlci to trace. A value of zero 
      specifies that all Dlcis are to be traced. This attribute can be set 
      while a trace is active and takes effect immediately."
   DEFVAL     { 0 }
::= { mscFrUniTraceFilterOperationalEntry 2 }

mscFrUniTraceFilterDirection OBJECT-TYPE
   SYNTAX     OCTET STRING (SIZE (1))
   ACCESS     read-write
   STATUS     mandatory
   DESCRIPTION
     "This attribute specifies the direction of the data to be traced as 
      viewed by the service. The values can be egress, and/or ingress. An 
      egress value indicates frames outbound from the service. An 
      ingress value indicates frames inbound to the service. This attribute 
      can be set while a trace is active and takes effect immediately.

      Description of bits:
      egress(0)
      ingress(1)"
   DEFVAL     { 'c0'H }
::= { mscFrUniTraceFilterOperationalEntry 3 }

mscFrUniTraceFilterTracedLength OBJECT-TYPE
   SYNTAX     Unsigned32 (1..2000)
   ACCESS     read-write
   STATUS     mandatory
   DESCRIPTION
     "This attribute specifies the maximum number of bytes to trace per 
      frame starting from the byte following the frame flag. If the frame 
      length is longer than the value specified by this attribute, then the 
      traced frame is truncated. This attribute can be set while a trace is 
      active and takes effect immediately."
   DEFVAL     { 2000 }
::= { mscFrUniTraceFilterOperationalEntry 4 }




-- 
-- Version and Compliance statements
-- 



-- Object-Group Statement:
-- A list of all current accessible leaf objects.

-- OBJECTS { mscFrUniTraceComponentName,
--           mscFrUniTraceStorageType,
--           mscFrUniTraceRowStatus,
--           mscFrUniTraceDuration,
--           mscFrUniTraceFilterTracedDlci,
--           mscFrUniTraceFilterComponentName,
--           mscFrUniTraceQueueLimit,
--           mscFrUniTraceFilterTraceType,
--           mscFrUniTraceFilterStorageType,
--           mscFrUniTraceFilterRowStatus,
--           mscFrUniTraceFilterDirection,
--           mscFrUniTraceReceiverName,
--           mscFrUniTraceFilterTracedLength,
--           mscFrUniTraceSession }
-- STATUS  mandatory
-- DESCRIPTION
--   "A list of all current accessible leaf objects."

frameRelayUniTraceGroup OBJECT IDENTIFIER ::= { frameRelayUniTraceMIB 1 }
frameRelayUniTraceGroupCA OBJECT IDENTIFIER ::= { frameRelayUniTraceGroup 1 }
frameRelayUniTraceGroupCA02 OBJECT IDENTIFIER ::= { frameRelayUniTraceGroupCA 3 }
frameRelayUniTraceGroupCA02A OBJECT IDENTIFIER ::= { frameRelayUniTraceGroupCA02 2 }



-- Agent-Capabilities Statement:

-- PRODUCT-RELEASE "MscPassport Release 1.2 FrameRelayUniTrace."
-- STATUS          mandatory
-- DESCRIPTION     "Carrier Passport FrameRelayUniTrace MIB: MIB Version CA02A,
--                  Software Version CA02S9C."
-- SUPPORTS        Nortel-MsCarrier-MscPassport-FrameRelayUniTraceMIB
--    INCLUDES     { frameRelayUniTraceGroupCA02A }

frameRelayUniTraceCapabilities OBJECT IDENTIFIER ::= { frameRelayUniTraceMIB 3 }
frameRelayUniTraceCapabilitiesCA OBJECT IDENTIFIER ::= { frameRelayUniTraceCapabilities 1 }
frameRelayUniTraceCapabilitiesCA02 OBJECT IDENTIFIER ::= { frameRelayUniTraceCapabilitiesCA 3 }
frameRelayUniTraceCapabilitiesCA02A OBJECT IDENTIFIER ::= { frameRelayUniTraceCapabilitiesCA02 2 }





END
