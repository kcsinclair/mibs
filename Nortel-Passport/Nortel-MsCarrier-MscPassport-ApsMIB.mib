Nortel-MsCarrier-MscPassport-ApsMIB
DEFINITIONS ::= BEGIN



IMPORTS

      OBJECT-TYPE
   FROM RFC-1212

      mscPassportMIBs,
      mscComponents
   FROM Nortel-MsCarrier-MscPassport-UsefulDefinitionsMIB

      Counter32,
      DisplayString,
      StorageType,
      RowStatus,
      Integer32,
      Unsigned32
   FROM Nortel-MsCarrier-MscPassport-StandardTextualConventionsMIB

      AsciiString,
      Hex,
      NonReplicated,
      PassportCounter64,
      FixedPoint1,
      Link
   FROM Nortel-MsCarrier-MscPassport-TextualConventionsMIB;




-- LAST-UPDATED   "9909010000Z"
-- ORGANIZATION   "Nortel Networks"
-- CONTACT-INFO   "
--         Nortel Carrier Data Network Management
--         
--         Postal:       P.O. Box 3511, Station C 
--                       Ottawa, Ontario 
--                       Canada  K1Y 4H7
--         
--         via the WEB:  http://www.nortelnetworks.com  
--                       select 'Contact Us' from the menu
--          
--         via phone:    1-800-4NORTEL"
-- DESCRIPTION
--    "The module describing the Nortel MsCarrier MscPassport
--     Aps Enterprise MIB."

apsMIB OBJECT IDENTIFIER ::= { mscPassportMIBs 136 }










-- AutomaticProtectionSwitching/n
-- This component manages the line protection of a SONET/SDH 
-- interface. Automatic Protection Switching (APS) can switch traffic 
-- from an active line onto a standby line when a failure or degradation 
-- occurs on the active line.

mscAps OBJECT IDENTIFIER ::= { mscComponents 134 }



mscApsRowStatusTable OBJECT-TYPE
   SYNTAX     SEQUENCE OF MscApsRowStatusEntry
   ACCESS     not-accessible
   STATUS     mandatory
   DESCRIPTION
     "This entry controls the addition and deletion of 
      mscAps components."
::= { mscAps 1 }

mscApsRowStatusEntry OBJECT-TYPE
   SYNTAX     MscApsRowStatusEntry
   ACCESS     not-accessible
   STATUS     mandatory
   DESCRIPTION
     "A single entry in the table represents a single 
      mscAps component."
   INDEX {
      mscApsIndex }
::= { mscApsRowStatusTable 1 }

MscApsRowStatusEntry ::= SEQUENCE {
   mscApsRowStatus
      RowStatus,
   mscApsComponentName
      DisplayString,
   mscApsStorageType
      StorageType,
   mscApsIndex
      Integer32 }

mscApsRowStatus OBJECT-TYPE
   SYNTAX     RowStatus 
   ACCESS     read-write
   STATUS     mandatory
   DESCRIPTION
     "This variable is used as the basis for SNMP naming of
      mscAps components.
      These components can be added and deleted."
::= { mscApsRowStatusEntry 1 }

mscApsComponentName OBJECT-TYPE
   SYNTAX     DisplayString 
   ACCESS     read-only
   STATUS     mandatory
   DESCRIPTION
     "This variable provides the component's string name for
      use with the ASCII Console Interface"
::= { mscApsRowStatusEntry 2 }

mscApsStorageType OBJECT-TYPE
   SYNTAX     StorageType 
   ACCESS     read-only
   STATUS     mandatory
   DESCRIPTION
     "This variable represents the storage type value for the
      mscAps tables."
::= { mscApsRowStatusEntry 4 }

mscApsIndex OBJECT-TYPE
   SYNTAX     Integer32 (0..15999)
   ACCESS     not-accessible
   STATUS     mandatory
   DESCRIPTION
     "This variable represents the index for the mscAps tables."
::= { mscApsRowStatusEntry 10 }

mscApsCidDataTable OBJECT-TYPE
   SYNTAX     SEQUENCE OF MscApsCidDataEntry
   ACCESS     not-accessible
   STATUS     mandatory
   DESCRIPTION
     "This group contains the attribute for a component's Customer 
      Identifier (CID). Refer to the attribute description for a detailed 
      explanation of CIDs."
::= { mscAps 10 }

mscApsCidDataEntry OBJECT-TYPE
   SYNTAX     MscApsCidDataEntry
   ACCESS     not-accessible
   STATUS     mandatory
   DESCRIPTION
     "An entry in the mscApsCidDataTable."
   INDEX {
      mscApsIndex }
::= { mscApsCidDataTable 1 }

MscApsCidDataEntry ::= SEQUENCE {
   mscApsCustomerIdentifier
      Unsigned32 }

mscApsCustomerIdentifier OBJECT-TYPE
   SYNTAX     Unsigned32 (0 | 1..8191)
   ACCESS     read-write
   STATUS     mandatory
   DESCRIPTION
     "This attribute holds the Customer Identifier (CID).
      
      Every component has a CID. If a component has a cid attribute, the 
      component's CID is the provisioned value of that attribute; 
      otherwise the component inherits the CID of its parent. The top-
      level component has a CID of 0.
      
      Every operator session also has a CID, which is the CID 
      provisioned for the operator's user ID. An operator will see only the 
      stream data for components having a matching CID. Also, the 
      operator will be allowed to issue commands for only those 
      components which have a matching CID.
      
      An operator CID of 0 is used to identify the Network Manager 
      (referred to as 'NetMan' in DPN). This CID matches the CID of 
      any component. Values 1 to 8191 inclusive (equivalent to 'basic 
      CIDs' in DPN) may be assigned to specific customers."
   DEFVAL     { 0 }
::= { mscApsCidDataEntry 1 }

mscApsProvTable OBJECT-TYPE
   SYNTAX     SEQUENCE OF MscApsProvEntry
   ACCESS     not-accessible
   STATUS     mandatory
   DESCRIPTION
     "This group contains the provisioned attributes for the Aps 
      component."
::= { mscAps 11 }

mscApsProvEntry OBJECT-TYPE
   SYNTAX     MscApsProvEntry
   ACCESS     not-accessible
   STATUS     mandatory
   DESCRIPTION
     "An entry in the mscApsProvTable."
   INDEX {
      mscApsIndex }
::= { mscApsProvTable 1 }

MscApsProvEntry ::= SEQUENCE {
   mscApsApplicationFramerName
      Link,
   mscApsWorkingLine
      Link,
   mscApsProtectionLine
      Link,
   mscApsMode
      INTEGER,
   mscApsRevertive
      INTEGER,
   mscApsHoldOffTime
      FixedPoint1,
   mscApsWaitToRestorePeriod
      Unsigned32,
   mscApsSignalDegradeRatio
      INTEGER }

mscApsApplicationFramerName OBJECT-TYPE
   SYNTAX     Link 
   ACCESS     read-write
   STATUS     mandatory
   DESCRIPTION
     "This attribute is a link to the service component which utilizes the 
      protected Sonet or Sdh interface managed by the Aps component."
::= { mscApsProvEntry 1 }

mscApsWorkingLine OBJECT-TYPE
   SYNTAX     Link 
   ACCESS     read-write
   STATUS     mandatory
   DESCRIPTION
     "This attribute is a link to the Path component whose parent Sonet or 
      Sdh component provides the Aps' working line. A value must be 
      defined for this component.
      
      The working line must exist under the same Lp as the protection 
      line and must link to a Path component under the same type of port 
      component (Sonet or Sdh) as the protection line.
      
      Valid workingLine and protectionLine pairs must exist. For the 
      1pOC12SmLrAtm card, the workingLine must be lp/n sonet/0 path/
      0. For other APS compatible cards, the workingLine and 
      protectionLine pairs must use port 0 with port 1 and port 2 with port 
      3. For example, if the workingLine is linked to a path on port 0, then 
      the protectionLine must be linked to a path on port 1.
      
      Sonet APS is available on cards of type 2pOC3SmAtm2, 
      2pOC3MmAtm2, 4pOC3SmIrAtm, 4pOC3MmAtm, and 
      1pOC12SmLrAtm."
::= { mscApsProvEntry 2 }

mscApsProtectionLine OBJECT-TYPE
   SYNTAX     Link 
   ACCESS     read-write
   STATUS     mandatory
   DESCRIPTION
     "This attribute is a link to the Path component whose parent Sonet or 
      Sdh component provides the Aps' protection line. A value must be 
      defined for this component. This attribute is critical because the 
      APS process runs on the LP associated with the protectionLine. The 
      protection line must exist under the same Lp as the working line, 
      and must link to a Path component under the same type of port 
      component (Sonet or Sdh) as the protection line.
      
      Valid workingLine and protectionLine pairs must exist. For the 
      1pOC12SmLrAtm, the protectionLine must be lp/n sonet/1 path/0. 
      For other APS compatible cards, the workingLine and 
      protectionLine pairs must use port 0 with port 1 and port 2 with port 
      3. For example, if the workingLine is linked to a path on port 0, then 
      the protectionLine must be linked to a path on port 1.
      
      Sonet APS is available on cards of type 2pOC3SmAtm2, 
      2pOC3MmAtm2, 4pOC3SmIrAtm, 4pOC3MmAtm, and 
      1pOC12SmLrAtm."
::= { mscApsProvEntry 3 }

mscApsMode OBJECT-TYPE
   SYNTAX     INTEGER  {
                 unidirectional(4),
                 bidirectional(5) }
   ACCESS     read-write
   STATUS     mandatory
   DESCRIPTION
     "This attribute specifies the protection mode to use. It has possible 
      values of unidirectional and bidirectional.
      
      The unidirectional mode allows the Aps to decide independently of 
      the far end which channel, either working or protection, will be 
      active for receive.
      
      The bidirectional mode instructs the Aps to decide jointly with the 
      far end which channel, either working or protection, will be active 
      for receive.
      
      Note that while an Aps Test is being run the Aps will operate in 
      unidirectional mode, regardless of the actual provisioned mode."
   DEFVAL     { unidirectional }
::= { mscApsProvEntry 4 }

mscApsRevertive OBJECT-TYPE
   SYNTAX     INTEGER  {
                 no(0),
                 yes(1) }
   ACCESS     read-write
   STATUS     mandatory
   DESCRIPTION
     "This attribute specifies whether revertive switching is to be used. It 
      has possible values of no or yes.
      
      When this attribute is no, the Aps will not revert the receive active 
      line from protection back to working when a working line request is 
      cleared.
      
      When this attribute is yes, the Aps will revert the receive active line 
      from protection back to working when a working line request is 
      cleared, after the provisioned waitToRestorePeriod has expired.
      
      Note that it is acceptable for the near end and far end to be 
      provisioned with a mix of revertive and nonrevertive switching."
   DEFVAL     { no }
::= { mscApsProvEntry 5 }

mscApsHoldOffTime OBJECT-TYPE
   SYNTAX     FixedPoint1 (0..100)
   ACCESS     read-write
   STATUS     mandatory
   DESCRIPTION
     "The hold off time is the delay between the detection of a Signal Fail 
      or Signal Degrade on the active line and the initiation of a 
      switchover."
   DEFVAL     { 0 }
::= { mscApsProvEntry 6 }

mscApsWaitToRestorePeriod OBJECT-TYPE
   SYNTAX     Unsigned32 (5..12)
   ACCESS     read-write
   STATUS     mandatory
   DESCRIPTION
     "This attribute specifies the time during which the protection line 
      will remain the receive active line after the working line recovers 
      from the fault that caused the switch. This attribute is only 
      applicable when the provisionable attribute revertive is yes."
   DEFVAL     { 5 }
::= { mscApsProvEntry 7 }

mscApsSignalDegradeRatio OBJECT-TYPE
   SYNTAX     INTEGER (-9..-5)
   ACCESS     read-write
   STATUS     mandatory
   DESCRIPTION
     "This attribute specifies the minimum bit error ratio (BER) for which 
      a Signal Degrade failure is declared. Its value is the exponent of the 
      BER, with possible values of -5 through -9 inclusive, which 
      correspond to a BER range of 10-5 through 10-9.
      
      The switch initiation time for a Signal Degrade varies depending on 
      the observed BER (not the provisioned signalDegradeRatio), as 
      described in the following table.
      
      Observed BER	Switch Initiation Time
      10-3	10 milliseconds
      10-4	100 milliseconds
      10-5	1 second
      10-6	10 seconds
      10-7	100 seconds
      10-8	16 minutes 40 seconds
      10-9	2 hours 46 minutes 40 seconds
      
      The clearing threshold for a Signal Degrade is one-tenth the 
      signalDegradeRatio; for example, if the provisioned 
      signalDegradeRatio is -5, the corresponding clearing threshold will 
      be 10-6. The clearing time varies depending on the clearing 
      threshold (not the observed BER), and can be determined from the 
      above table."
   DEFVAL     { -5 }
::= { mscApsProvEntry 8 }

mscApsStateTable OBJECT-TYPE
   SYNTAX     SEQUENCE OF MscApsStateEntry
   ACCESS     not-accessible
   STATUS     mandatory
   DESCRIPTION
     "This group contains the three OSI State attributes and the six OSI 
      Status attributes. The descriptions generically indicate what each 
      attribute implies about the component. Note that not all the values 
      and state combinations described here are supported by every 
      component which uses this group. For component-specific 
      information and the valid state combinations, refer to NTP 241-
      7001-150, Passport Operations and Maintenance Guide."
::= { mscAps 12 }

mscApsStateEntry OBJECT-TYPE
   SYNTAX     MscApsStateEntry
   ACCESS     not-accessible
   STATUS     mandatory
   DESCRIPTION
     "An entry in the mscApsStateTable."
   INDEX {
      mscApsIndex }
::= { mscApsStateTable 1 }

MscApsStateEntry ::= SEQUENCE {
   mscApsAdminState
      INTEGER,
   mscApsOperationalState
      INTEGER,
   mscApsUsageState
      INTEGER,
   mscApsAvailabilityStatus
      OCTET STRING,
   mscApsProceduralStatus
      OCTET STRING,
   mscApsControlStatus
      OCTET STRING,
   mscApsAlarmStatus
      OCTET STRING,
   mscApsStandbyStatus
      INTEGER,
   mscApsUnknownStatus
      INTEGER }

mscApsAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component.
      
      The OSI Status attributes, if supported by the component, may 
      provide more details, qualifying the state of the component."
   DEFVAL     { unlocked }
::= { mscApsStateEntry 1 }

mscApsOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle.
      
      The OSI Status attributes, if supported by the component, may 
      provide more details, qualifying the state of the component."
   DEFVAL     { disabled }
::= { mscApsStateEntry 2 }

mscApsUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time.
      
      The OSI Status attributes, if supported by the component, may 
      provide more details, qualifying the state of the component."
   DEFVAL     { idle }
::= { mscApsStateEntry 3 }

mscApsAvailabilityStatus OBJECT-TYPE
   SYNTAX     OCTET STRING (SIZE (2))
   ACCESS     read-only
   STATUS     mandatory
   DESCRIPTION
     "If supported by the component, this attribute indicates the OSI 
      Availability status of the component. Note that, even though it is 
      defined as a multi-valued set, at most one value is shown to the user.
      
      When no values are in the set, this indicates that either the attribute 
      is not supported or that none of the status conditions described 
      below are present.
      
      The value inTest indicates that the resource is undergoing a test 
      procedure. If adminState is locked or shuttingDown, the normal 
      users are precluded from using the resource and controlStatus is 
      reservedForTest. Tests that do not exclude additional users can be 
      present in any operational or administrative state but the 
      reservedForTest condition should not be present.
      
      The value failed indicates that the component has an internal fault 
      that prevents it from operating. The operationalState is disabled.
      
      The value dependency indicates that the component cannot operate 
      because some other resource on which it depends is unavailable. 
      The operationalState is disabled.
      
      The value powerOff indicates the resource requires power to be 
      applied and it is not powered on. The operationalState is disabled.
      
      The value offLine indicates the resource requires a routine 
      operation (either manual, automatic, or both) to be performed to 
      place it on-line and make it available for use. The operationalState 
      is disabled.
      
      The value offDuty indicates the resource is inactive in accordance 
      with a predetermined time schedule. In the absence of other 
      disabling conditions, the operationalState is enabled or disabled.
      
      The value degraded indicates the service provided by the 
      component is degraded in some way, such as in speed or operating 
      capacity. However, the resource remains available for service. The 
      operationalState is enabled.
      
      The value notInstalled indicates the resource is not present. The 
      operationalState is disabled.
      
      The value logFull is not used.

      Description of bits:
      inTest(0)
      failed(1)
      powerOff(2)
      offLine(3)
      offDuty(4)
      dependency(5)
      degraded(6)
      notInstalled(7)
      logFull(8)"
::= { mscApsStateEntry 4 }

mscApsProceduralStatus OBJECT-TYPE
   SYNTAX     OCTET STRING (SIZE (1))
   ACCESS     read-only
   STATUS     mandatory
   DESCRIPTION
     "If supported by the component, this attribute indicates the OSI 
      Procedural status of the component. Note that, even though it is 
      defined as a multi-valued set, at most one value is shown to the user.
      
      When no values are in the set, this indicates that either the attribute 
      is not supported or that none of the status conditions described 
      below are present.
      
      The value initializationRequired indicates (for a resource which 
      doesn't initialize autonomously) that initialization is required before 
      it can perform its normal functions, and this procedure has not been 
      initiated. The operationalState is disabled.
      
      The value notInitialized indicates (for a resource which does 
      initialize autonomously) that initialization is required before it can 
      perform its normal functions, and this procedure has not been 
      initiated. The operationalState may be enabled or disabled.
      
      The value initializing indicates that initialization has been initiated 
      but is not yet complete. The operationalState may be enabled or 
      disabled.
      
      The value reporting indicates the resource has completed some 
      processing operation and is notifying the results. The 
      operationalState is enabled.
      
      The value terminating indicates the component is in a termination 
      phase. If the resource doesn't reinitialize autonomously, 
      operationalState is disabled; otherwise it is enabled or disabled.

      Description of bits:
      initializationRequired(0)
      notInitialized(1)
      initializing(2)
      reporting(3)
      terminating(4)"
::= { mscApsStateEntry 5 }

mscApsControlStatus OBJECT-TYPE
   SYNTAX     OCTET STRING (SIZE (1))
   ACCESS     read-only
   STATUS     mandatory
   DESCRIPTION
     "If supported by the component, this attribute indicates the OSI 
      Control status of the component. Note that, even though it is defined 
      as a multi-valued set, at most one value is shown to the user.
      
      When no values are in the set, this indicates that either the attribute 
      is not supported or that none of the status conditions described 
      below are present.
      
      The value subjectToTest indicates the resource is available but tests 
      may be conducted simultaneously at unpredictable times, which 
      may cause it to exhibit unusual characteristics.
      
      The value partOfServicesLocked indicates that part of the service is 
      restricted from users of a resource. The adminState is unlocked.
      
      The value reservedForTest indicates that the component is 
      administratively unavailable because it is undergoing a test 
      procedure. The adminState is locked.
      
      The value suspended indicates that the service has been 
      administratively suspended.

      Description of bits:
      subjectToTest(0)
      partOfServicesLocked(1)
      reservedForTest(2)
      suspended(3)"
::= { mscApsStateEntry 6 }

mscApsAlarmStatus OBJECT-TYPE
   SYNTAX     OCTET STRING (SIZE (1))
   ACCESS     read-only
   STATUS     mandatory
   DESCRIPTION
     "If supported by the component, this attribute indicates the OSI 
      Alarm status of the component. Note that, even though it is defined 
      as a multi-valued set, at most one value is shown to the user.
      
      When no values are in the set, this indicates that either the attribute 
      is not supported or that none of the status conditions described 
      below are present.
      
      The value underRepair indicates the component is currently being 
      repaired. The operationalState is enabled or disabled.
      
      The value critical indicates one or more critical alarms are 
      outstanding against the component. Other, less severe, alarms may 
      also be outstanding. The operationalState is enabled or disabled.
      
      The value major indicates one or more major alarms are 
      outstanding against the component. Other, less severe, alarms may 
      also be outstanding. The operationalState is enabled or disabled.
      
      The value minor indicates one or more minor alarms are 
      outstanding against the component. Other, less severe, alarms may 
      also be outstanding. The operationalState is enabled or disabled.
      
      The value alarmOutstanding generically indicates that an alarm of 
      some severity is outstanding against the component.

      Description of bits:
      underRepair(0)
      critical(1)
      major(2)
      minor(3)
      alarmOutstanding(4)"
::= { mscApsStateEntry 7 }

mscApsStandbyStatus OBJECT-TYPE
   SYNTAX     INTEGER  {
                 hotStandby(0),
                 coldStandby(1),
                 providingService(2),
                 notSet(15) }
   ACCESS     read-only
   STATUS     mandatory
   DESCRIPTION
     "If supported by the component, this attribute indicates the OSI 
      Standby status of the component.
      
      The value notSet indicates that either the attribute is not supported 
      or that none of the status conditions described below are present. 
      Note that this is a non-standard value, used because the original 
      specification indicated this attribute was set-valued and thus, did not 
      provide a value to indicate that none of the other three are 
      applicable.
      
      The value hotStandby indicates that the resource is not providing 
      service but will be immediately able to take over the role of the 
      resource to be backed up, without initialization activity, and 
      containing the same information as the resource to be backed up.
      
      The value coldStandby indicates the resource is a backup for 
      another resource but will not be immediately able to take over the 
      role of the backed up resource and will require some initialization 
      activity.
      
      The value providingService indicates that this component, as a 
      backup resource, is currently backing up another resource."
   DEFVAL     { notSet }
::= { mscApsStateEntry 8 }

mscApsUnknownStatus OBJECT-TYPE
   SYNTAX     INTEGER  {
                 false(0),
                 true(1) }
   ACCESS     read-only
   STATUS     mandatory
   DESCRIPTION
     "This attribute indicates the OSI Unknown status of the component.
      
      The value false indicates that all of the other OSI State and Status 
      attribute values can be considered accurate.
      
      The value true indicates that the actual state of the component is not 
      known for sure."
   DEFVAL     { false }
::= { mscApsStateEntry 9 }

mscApsOperTable OBJECT-TYPE
   SYNTAX     SEQUENCE OF MscApsOperEntry
   ACCESS     not-accessible
   STATUS     mandatory
   DESCRIPTION
     "This group contains the operational attributes for the Aps 
      component."
::= { mscAps 13 }

mscApsOperEntry OBJECT-TYPE
   SYNTAX     MscApsOperEntry
   ACCESS     not-accessible
   STATUS     mandatory
   DESCRIPTION
     "An entry in the mscApsOperTable."
   INDEX {
      mscApsIndex }
::= { mscApsOperTable 1 }

MscApsOperEntry ::= SEQUENCE {
   mscApsNearEndRxActiveLine
      INTEGER,
   mscApsNearEndRequest
      INTEGER,
   mscApsNearEndRequestChannel
      INTEGER,
   mscApsFarEndRequest
      INTEGER,
   mscApsFarEndRequestChannel
      INTEGER,
   mscApsSdOnLines
      OCTET STRING,
   mscApsSwitchovers
      Counter32,
   mscApsTimeUntilRestore
      Unsigned32,
   mscApsProtocolFailureAlarm
      INTEGER,
   mscApsModeMismatchAlarm
      INTEGER }

mscApsNearEndRxActiveLine OBJECT-TYPE
   SYNTAX     INTEGER  {
                 protection(0),
                 working(1) }
   ACCESS     read-only
   STATUS     mandatory
   DESCRIPTION
     "This attribute indicates which near end line is active for receiving 
      data from the far end."
::= { mscApsOperEntry 1 }

mscApsNearEndRequest OBJECT-TYPE
   SYNTAX     INTEGER  {
                 noRequest(0),
                 doNotRevert(1),
                 reverseRequest(2),
                 waitToRestore(6),
                 manualSwitch(8),
                 signalDegrade(10),
                 signalFail(12),
                 forcedSwitch(14),
                 lockoutOfProtection(15) }
   ACCESS     read-only
   STATUS     mandatory
   DESCRIPTION
     "This attribute indicates the request currently being transmitted to the 
      far end in the SONET/SDH line overhead K1 byte of the protection 
      line. Requests are prioritized so that high priority requests preempt 
      or block those with a lower priority. The possible requests, in order 
      of priority from highest to lowest, are as follows.
      
      lockoutOfProtection  the working line is prevented from 
      switching to the protection line under any circumstances due to an 
      ProtectionLockout command being in effect.
      
      forcedSwitch  the line indicated by attribute 
      nearEndRequestChannel has a Switch -force command in effect 
      against it. Note that a signalFail on the protection line has higher 
      priority than a forcedSwitch.
      
      signalFail  the line indicated by attribute 
      nearEndRequestChannel is experiencing a signal failure (SF). 
      Failures include LOS, LOF, received AIS-L, a signal BER 
      exceeding 10-3, LOP, received AIS-P, LCD, or a locked Sonet, Sdh, 
      or Path component. Note that a signalFail on the protection line 
      has higher priority than a forcedSwitch.
      
      signalDegrade  the line indicated by attribute 
      nearEndRequestChannel is experiencing a signal degradation (SD). 
      For more information on the conditions required to declare and 
      clear an SD please refer to the desription for attribute 
      signalDegradeRatio.
      
      A such that the signal BER exceeds the value provisioned in the 
      signalDegradeRatio attribute, or is still exceeding 
      
      manualSwitch  the line indicated by attribute 
      nearEndRequestChannel has a Switch command in effect against it.
      
      waitToRestore  the protection line is active, provisioned attribute 
      revertive is yes, and the working line has recovered from a Signal 
      Fail or Signal Degrade. After the period defined by attribute 
      waitToRestorePeriod the working line will automatically revert to 
      being the receive active line and the request will change to 
      noRequest.
      
      reverseRequest  the line indicated by attribute 
      nearEndRequestChannel is active due to a request from the far end. 
      This request is only applicable when the provisioned mode is 
      bidirectional.
      
      doNotRevert  the protection line is active, provisioned attribute 
      revertive is no, and either: (1) the working line has recovered from 
      a signalFail or signalDegrade; or (2) a forcedSwitch or 
      manualSwitch request has been cleared. The receive active line will 
      not automatically revert to the working line.
      
      noRequest  the working line is active and no other requests are in 
      effect."
::= { mscApsOperEntry 2 }

mscApsNearEndRequestChannel OBJECT-TYPE
   SYNTAX     INTEGER  {
                 protection(0),
                 working(1) }
   ACCESS     read-only
   STATUS     mandatory
   DESCRIPTION
     "This attribute indicates to which channel the nearEndRequest 
      applies."
::= { mscApsOperEntry 3 }

mscApsFarEndRequest OBJECT-TYPE
   SYNTAX     INTEGER  {
                 noRequest(0),
                 doNotRevert(1),
                 reverseRequest(2),
                 waitToRestore(6),
                 manualSwitch(8),
                 signalDegrade(10),
                 signalFail(12),
                 forcedSwitch(14),
                 lockoutOfProtection(15) }
   ACCESS     read-only
   STATUS     mandatory
   DESCRIPTION
     "This attribute indicates the request currently being received from the 
      far end in the SONET/SDH line overhead K1 byte of the protection 
      line. Requests are prioritized so that high priority requests preempt 
      or block those with a lower priority. The possible requests, in order 
      of priority from highest to lowest, are as follows.
      
      lockoutOfProtection  the working line is prevented from 
      switching to the protection line under any circumstances due to an 
      ProtectionLockout command being in effect.
      
      forcedSwitch  the line indicated by attribute 
      nearEndRequestChannel has a Switch -force command in effect 
      against it. Note that a signalFail on the protection line has higher 
      priority than a forcedSwitch.
      
      signalFail  the line indicated by attribute 
      nearEndRequestChannel is experiencing a signal failure (SF). 
      Failures include LOS, LOF, received AIS-L, a signal BER 
      exceeding 10-3, LOP, received AIS-P, LCD, or a locked Sonet, Sdh, 
      or Path component. Note that a signalFail on the protection line 
      has higher priority than a forcedSwitch.
      
      signalDegrade  the line indicated by attribute 
      nearEndRequestChannel is experiencing a signal degradation (SD). 
      For more information on the conditions required to declare and 
      clear an SD please refer to the desription for attribute 
      signalDegradeRatio.
      
      A such that the signal BER exceeds the value provisioned in the 
      signalDegradeRatio attribute, or is still exceeding 
      
      manualSwitch  the line indicated by attribute 
      nearEndRequestChannel has a Switch command in effect against it.
      
      waitToRestore  the protection line is active, provisioned attribute 
      revertive is yes, and the working line has recovered from a Signal 
      Fail or Signal Degrade. After the period defined by attribute 
      waitToRestorePeriod the working line will automatically revert to 
      being the receive active line and the request will change to 
      noRequest.
      
      reverseRequest  the line indicated by attribute 
      nearEndRequestChannel is active due to a request from the far end. 
      This request is only applicable when the provisioned mode is 
      bidirectional.
      
      doNotRevert  the protection line is active, provisioned attribute 
      revertive is no, and either: (1) the working line has recovered from 
      a signalFail or signalDegrade; or (2) a forcedSwitch or 
      manualSwitch request has been cleared. The receive active line will 
      not automatically revert to the working line.
      
      noRequest  the working line is active and no other requests are in 
      effect.
      DESCRIPTION"
::= { mscApsOperEntry 4 }

mscApsFarEndRequestChannel OBJECT-TYPE
   SYNTAX     INTEGER  {
                 protection(0),
                 working(1) }
   ACCESS     read-only
   STATUS     mandatory
   DESCRIPTION
     "This attribute indicates to which channel the farEndRequest applies."
::= { mscApsOperEntry 5 }

mscApsSdOnLines OBJECT-TYPE
   SYNTAX     OCTET STRING (SIZE (1))
   ACCESS     read-only
   STATUS     mandatory
   DESCRIPTION
     "This attribute indicates which lines (if any) are currently 
      experiencing a Signal Degrade (SD).

      Description of bits:
      protection(0)
      working(1)"
::= { mscApsOperEntry 6 }

mscApsSwitchovers OBJECT-TYPE
   SYNTAX     Counter32 
   ACCESS     read-only
   STATUS     mandatory
   DESCRIPTION
     "This attributes counts the number of times that a switchover of the 
      active line has occurred since the Aps component became active."
::= { mscApsOperEntry 7 }

mscApsTimeUntilRestore OBJECT-TYPE
   SYNTAX     Unsigned32 (0..12)
   ACCESS     read-only
   STATUS     mandatory
   DESCRIPTION
     "This attribute indicates the amount of time in minutes until the 
      receive active line is automatically switched back from the 
      protection line to the working line. It is only applicable for Aps 
      components that are provisioned to be revertive, and which 
      currently have the protection line as the receive active line and a 
      nearEndRequest of waitToRestore."
::= { mscApsOperEntry 8 }

mscApsProtocolFailureAlarm OBJECT-TYPE
   SYNTAX     INTEGER  {
                 on(0),
                 off(1) }
   ACCESS     read-only
   STATUS     mandatory
   DESCRIPTION
     "This attribute indicates whether the Aps component is experiencing 
      an APS protocol failure alarm. Protocol failure alarms include the 
      protection switching byte mismatch alarm (code 7011 5270) and the 
      channel mismatch failure alarm (code 7011 5271)."
::= { mscApsOperEntry 9 }

mscApsModeMismatchAlarm OBJECT-TYPE
   SYNTAX     INTEGER  {
                 on(0),
                 off(1) }
   ACCESS     read-only
   STATUS     mandatory
   DESCRIPTION
     "This attribute indicates whether the Aps component is experiencing 
      an APS mode mismatch alarm (code 7011 5272). This alarm 
      indicates either:
      
      (1) that the far end is operating with a 1:n switching architecture 
      (not supported by Passport), as opposed to 1+1; or
      
      (2) that the far end's provisioned mode is not the same as the nears 
      end's provisioned mode.
      
      When a mode mismatch occurs: (1) if the far end is operating with a 
      1:n switching architecture it will operate as 1+1; and (2) if either 
      end has a provisioned mode of unidirectional then both ends will 
      operate unidirectionally."
::= { mscApsOperEntry 10 }


-- 
-- The Test component is configured to control a hardware facility test 
-- on a physical (V35, X21, DS1, E1, DS3, E3 etc.) or a logical port.

mscApsTest OBJECT IDENTIFIER ::= { mscAps 2 }



mscApsTestRowStatusTable OBJECT-TYPE
   SYNTAX     SEQUENCE OF MscApsTestRowStatusEntry
   ACCESS     not-accessible
   STATUS     mandatory
   DESCRIPTION
     "This entry controls the addition and deletion of 
      mscApsTest components."
::= { mscApsTest 1 }

mscApsTestRowStatusEntry OBJECT-TYPE
   SYNTAX     MscApsTestRowStatusEntry
   ACCESS     not-accessible
   STATUS     mandatory
   DESCRIPTION
     "A single entry in the table represents a single 
      mscApsTest component."
   INDEX {
      mscApsIndex,
      mscApsTestIndex }
::= { mscApsTestRowStatusTable 1 }

MscApsTestRowStatusEntry ::= SEQUENCE {
   mscApsTestRowStatus
      RowStatus,
   mscApsTestComponentName
      DisplayString,
   mscApsTestStorageType
      StorageType,
   mscApsTestIndex
      NonReplicated }

mscApsTestRowStatus OBJECT-TYPE
   SYNTAX     RowStatus 
   ACCESS     read-only
   STATUS     mandatory
   DESCRIPTION
     "This variable is used as the basis for SNMP naming of
      mscApsTest components.
      These components cannot be added nor deleted."
::= { mscApsTestRowStatusEntry 1 }

mscApsTestComponentName OBJECT-TYPE
   SYNTAX     DisplayString 
   ACCESS     read-only
   STATUS     mandatory
   DESCRIPTION
     "This variable provides the component's string name for
      use with the ASCII Console Interface"
::= { mscApsTestRowStatusEntry 2 }

mscApsTestStorageType OBJECT-TYPE
   SYNTAX     StorageType 
   ACCESS     read-only
   STATUS     mandatory
   DESCRIPTION
     "This variable represents the storage type value for the
      mscApsTest tables."
::= { mscApsTestRowStatusEntry 4 }

mscApsTestIndex OBJECT-TYPE
   SYNTAX     NonReplicated 
   ACCESS     not-accessible
   STATUS     mandatory
   DESCRIPTION
     "This variable represents the index for the mscApsTest tables."
::= { mscApsTestRowStatusEntry 10 }

mscApsTestStateTable OBJECT-TYPE
   SYNTAX     SEQUENCE OF MscApsTestStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscApsTest 10 }

mscApsTestStateEntry OBJECT-TYPE
   SYNTAX     MscApsTestStateEntry
   ACCESS     not-accessible
   STATUS     mandatory
   DESCRIPTION
     "An entry in the mscApsTestStateTable."
   INDEX {
      mscApsIndex,
      mscApsTestIndex }
::= { mscApsTestStateTable 1 }

MscApsTestStateEntry ::= SEQUENCE {
   mscApsTestAdminState
      INTEGER,
   mscApsTestOperationalState
      INTEGER,
   mscApsTestUsageState
      INTEGER }

mscApsTestAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscApsTestStateEntry 1 }

mscApsTestOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscApsTestStateEntry 2 }

mscApsTestUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscApsTestStateEntry 3 }

mscApsTestSetupTable OBJECT-TYPE
   SYNTAX     SEQUENCE OF MscApsTestSetupEntry
   ACCESS     not-accessible
   STATUS     mandatory
   DESCRIPTION
     "This group contains all of the operational data for a Test 
      component."
::= { mscApsTest 11 }

mscApsTestSetupEntry OBJECT-TYPE
   SYNTAX     MscApsTestSetupEntry
   ACCESS     not-accessible
   STATUS     mandatory
   DESCRIPTION
     "An entry in the mscApsTestSetupTable."
   INDEX {
      mscApsIndex,
      mscApsTestIndex }
::= { mscApsTestSetupTable 1 }

MscApsTestSetupEntry ::= SEQUENCE {
   mscApsTestPurpose
      AsciiString,
   mscApsTestType
      INTEGER,
   mscApsTestFrmSize
      Unsigned32,
   mscApsTestFrmPatternType
      INTEGER,
   mscApsTestCustomizedPattern
      Hex,
   mscApsTestDataStartDelay
      Unsigned32,
   mscApsTestDisplayInterval
      Unsigned32,
   mscApsTestDuration
      Unsigned32 }

mscApsTestPurpose OBJECT-TYPE
   SYNTAX     AsciiString (SIZE (0..40))
   ACCESS     read-write
   STATUS     mandatory
   DESCRIPTION
     "This attribute records the purpose of the test so that the test results 
      can be associated and properly analyzed."
::= { mscApsTestSetupEntry 1 }

mscApsTestType OBJECT-TYPE
   SYNTAX     INTEGER  {
                 card(0),
                 manual(1),
                 localLoop(2),
                 remoteLoop(3),
                 externalLoop(4),
                 payloadLoop(5),
                 remoteLoopThisTrib(6),
                 v54RemoteLoop(7),
                 pn127RemoteLoop(8) }
   ACCESS     read-write
   STATUS     mandatory
   DESCRIPTION
     "This attribute is the type of test to be run. The available test types 
      include the following:
      card test sets up an internal loop on the board and runs a bit error 
      rate test.
      manual test assumes the line is looped back externally and a bit 
      error rate test is performed.
      localLoop test loops back the local modem and performs a bit error 
      rate test.
      remoteLoop test loops back the remote modem (or CSU) and 
      performs a bit error rate test.
      externalLoop test loops back the line to the far end.
      payloadLoop test only loops back the payload data received from 
      the incoming line.
      remoteLoopThisTrib loops this particular tributary back at the far 
      end, using services provided by the parent.
      v54RemoteLoop initiates a V.54 Remote Loopback test.
      pn127RemoteLoop initiates a PN127 Remote Loopback test.
      Note that not all test types are not supported by all function 
      processors."
   DEFVAL     { card }
::= { mscApsTestSetupEntry 2 }

mscApsTestFrmSize OBJECT-TYPE
   SYNTAX     Unsigned32 (4..4096)
   ACCESS     read-write
   STATUS     mandatory
   DESCRIPTION
     "This attribute defines the size of the test data frames in number of 
      bytes."
   DEFVAL     { 1024 }
::= { mscApsTestSetupEntry 3 }

mscApsTestFrmPatternType OBJECT-TYPE
   SYNTAX     INTEGER  {
                 ccitt32kBitPattern(0),
                 ccitt8MBitPattern(1),
                 customizedPattern(2) }
   ACCESS     read-write
   STATUS     mandatory
   DESCRIPTION
     "This attribute defines the type of data pattern generation to use. The 
      following lists the available pattern types:
      ccitt32kBitPattern is a pseudo-random sequence of 32 kbit.
      ccitt8MBitPattern is a pseudo-random sequence of 8Mbit.
      customizedPattern is the pattern defined in the customizedPattern 
      attribute."
   DEFVAL     { ccitt32kBitPattern }
::= { mscApsTestSetupEntry 4 }

mscApsTestCustomizedPattern OBJECT-TYPE
   SYNTAX     Hex (0..4294967295)
   ACCESS     read-write
   STATUS     mandatory
   DESCRIPTION
     "This attribute allows a customized 32 bit pattern to be defined for 
      use in the test data frames. This attribute is used when the attribute 
      frmPatternType is set to CustomizedPattern. Note that a 55 hex 
      pattern is an alternating 1 and 0 pattern."
   DEFVAL     { 1431655765 }
::= { mscApsTestSetupEntry 5 }

mscApsTestDataStartDelay OBJECT-TYPE
   SYNTAX     Unsigned32 (0..1814400)
   ACCESS     read-write
   STATUS     mandatory
   DESCRIPTION
     "This attribute specifies the time delay (in seconds) between when 
      the test expects the loop to have been set up, to when the test data 
      actually starts to be transmitted. This attribute is to accommodate 
      some non-standard equipment that requires extra time for setting up 
      a requested loop.
      This attribute is ignored when the test type is set to externalLoop."
   DEFVAL     { 0 }
::= { mscApsTestSetupEntry 6 }

mscApsTestDisplayInterval OBJECT-TYPE
   SYNTAX     Unsigned32 (0..30240)
   ACCESS     read-write
   STATUS     mandatory
   DESCRIPTION
     "This attribute defines the interval (in minutes) between which 
      interim test results are to be displayed. Results are displayed at the 
      operator console at which the test was started. When the test type is 
      set to externalLoop, this attribute is ignored. There will be no 
      display of results if displayInterval is set to 0. This attribute can be 
      changed anytime."
   DEFVAL     { 5 }
::= { mscApsTestSetupEntry 7 }

mscApsTestDuration OBJECT-TYPE
   SYNTAX     Unsigned32 (1..30240)
   ACCESS     read-write
   STATUS     mandatory
   DESCRIPTION
     "This attribute is the duration (in minutes) that test data will be 
      transmitted. In the case of an externalLoop, this is the time that the 
      loop is in effect. Note that dataStartDelay does not apply to the 
      externalLoop."
   DEFVAL     { 1 }
::= { mscApsTestSetupEntry 8 }

mscApsTestResultsTable OBJECT-TYPE
   SYNTAX     SEQUENCE OF MscApsTestResultsEntry
   ACCESS     not-accessible
   STATUS     mandatory
   DESCRIPTION
     "This group contains all the statistics related attributes of the Test 
      component."
::= { mscApsTest 12 }

mscApsTestResultsEntry OBJECT-TYPE
   SYNTAX     MscApsTestResultsEntry
   ACCESS     not-accessible
   STATUS     mandatory
   DESCRIPTION
     "An entry in the mscApsTestResultsTable."
   INDEX {
      mscApsIndex,
      mscApsTestIndex }
::= { mscApsTestResultsTable 1 }

MscApsTestResultsEntry ::= SEQUENCE {
   mscApsTestElapsedTime
      Counter32,
   mscApsTestTimeRemaining
      Unsigned32,
   mscApsTestCauseOfTermination
      INTEGER,
   mscApsTestBitsTx
      PassportCounter64,
   mscApsTestBytesTx
      PassportCounter64,
   mscApsTestFrmTx
      PassportCounter64,
   mscApsTestBitsRx
      PassportCounter64,
   mscApsTestBytesRx
      PassportCounter64,
   mscApsTestFrmRx
      PassportCounter64,
   mscApsTestErroredFrmRx
      PassportCounter64,
   mscApsTestBitErrorRate
      AsciiString }

mscApsTestElapsedTime OBJECT-TYPE
   SYNTAX     Counter32 
   ACCESS     read-only
   STATUS     mandatory
   DESCRIPTION
     "This attribute is the number of minutes elapsed since the test started 
      for an externalLoop test. For a data test, this is the time since test 
      data was first transmitted."
::= { mscApsTestResultsEntry 1 }

mscApsTestTimeRemaining OBJECT-TYPE
   SYNTAX     Unsigned32 (0..4294967295)
   ACCESS     read-only
   STATUS     mandatory
   DESCRIPTION
     "This attribute is the number of minutes remaining before the test is 
      to be stopped according to the duration attribute."
   DEFVAL     { 0 }
::= { mscApsTestResultsEntry 2 }

mscApsTestCauseOfTermination OBJECT-TYPE
   SYNTAX     INTEGER  {
                 testTimeExpired(0),
                 stoppedByOperator(1),
                 unknown(2),
                 neverStarted(3),
                 testRunning(4),
                 hardwareReconfigured(5),
                 loopCodeSyncFailed(6),
                 patternSyncFailed(7),
                 patternSyncLost(8) }
   ACCESS     read-only
   STATUS     mandatory
   DESCRIPTION
     "This attribute indicates either the status of the test or the cause of 
      the test's termination:
      
      neverStarted indicates that the test has not yet been started.
      
      testRunning indicates that the test has been started.
      
      stoppedByOperator indicates that the operator issued a stop 
      command on a test that was running.
      
      testTimeExpired indicates that the test ran for the time specified by 
      the test's duration.
      
      loopCodeSyncFailed indicates that the local end failed to 
      synchronize to the loopCode pattern. The local end transmits the 
      loopCode pattern to cause the remote end to apply a loopback, after 
      which the local end should receive the loopCode pattern. The exact 
      pattern used to request loopCode depends on the test type. This 
      failure indicates a high rate of transmission errors, or that the 
      remote end has failed to apply the loopback.
      
      patternSyncFailed indicates that the local end failed to synchronize 
      to the frmPatternType test pattern, that should have been looped 
      back at the remote end. This failure indicates a high rate of 
      transmission errors or the absence of a loopback.
      
      patternSyncLost indicates that the local end gained and then lost 
      synchronization to the returned frmPatternType test pattern. This 
      failure indicates a sudden increase in transmission errors, frame 
      slippage, or the removal of an existing loopback.
      
      unknown is set when a reason to terminate other than those listed 
      here is encountered.
      
      Note: Only MSA cards support recognition of the failures 
      loopCodeSyncFailed, patternSyncFailed and patternSyncLost. 
      Other cards will not terminate the test under the conditions 
      described by these values."
   DEFVAL     { neverStarted }
::= { mscApsTestResultsEntry 3 }

mscApsTestBitsTx OBJECT-TYPE
   SYNTAX     PassportCounter64 
   ACCESS     read-only
   STATUS     mandatory
   DESCRIPTION
     "This attribute is the total number of bits sent during the test period. 
      As long as the line speed of the hardware interface is less than 
      70 Mbit/s, this counter is not expected to reach the maximum value."
::= { mscApsTestResultsEntry 4 }

mscApsTestBytesTx OBJECT-TYPE
   SYNTAX     PassportCounter64 
   ACCESS     read-only
   STATUS     mandatory
   DESCRIPTION
     "This attribute is the total number of bytes sent during the test 
      period. This counter is not expected to reach its maximum value."
::= { mscApsTestResultsEntry 5 }

mscApsTestFrmTx OBJECT-TYPE
   SYNTAX     PassportCounter64 
   ACCESS     read-only
   STATUS     mandatory
   DESCRIPTION
     "This attribute is the total number of frames sent during the test 
      period. This counter is not expected to reach its maximum value."
::= { mscApsTestResultsEntry 6 }

mscApsTestBitsRx OBJECT-TYPE
   SYNTAX     PassportCounter64 
   ACCESS     read-only
   STATUS     mandatory
   DESCRIPTION
     "This attribute is the total number of bits received during the test 
      period. This counter is not expected to reach its maximum value. 
      The counter will wrap around to 0 if it does reach the maximum 
      value."
::= { mscApsTestResultsEntry 7 }

mscApsTestBytesRx OBJECT-TYPE
   SYNTAX     PassportCounter64 
   ACCESS     read-only
   STATUS     mandatory
   DESCRIPTION
     "This attribute is the total number of bytes received during the test 
      period. This counter is not expected to reach its maximum value. 
      The counter will wrap around to 0 if it does reach its maximum 
      value."
::= { mscApsTestResultsEntry 8 }

mscApsTestFrmRx OBJECT-TYPE
   SYNTAX     PassportCounter64 
   ACCESS     read-only
   STATUS     mandatory
   DESCRIPTION
     "This attribute is the total number of frames received during the test 
      period. This counter is not expected to reach its maximum value. 
      The counter will wrap around to 0 if it does reach its maximum 
      value."
::= { mscApsTestResultsEntry 9 }

mscApsTestErroredFrmRx OBJECT-TYPE
   SYNTAX     PassportCounter64 
   ACCESS     read-only
   STATUS     mandatory
   DESCRIPTION
     "This attribute is not displayed for ATM cards because the physical 
      layer drops all errored frames at the controller interface. 
      
      For all other card types, this attribute is the total number of errored 
      frames received during the test period. This counter is not expected 
      to reach its maximum value. The counter will wrap around to 0 if it 
      does reach its maximum value."
::= { mscApsTestResultsEntry 10 }

mscApsTestBitErrorRate OBJECT-TYPE
   SYNTAX     AsciiString (SIZE (5))
   ACCESS     read-only
   STATUS     mandatory
   DESCRIPTION
     "This attribute is not displayed for ATM cards because the physical 
      layer drops all errored frames at the controller interface. 
      
      For all other card types, this attribute is the calculated bit error rate 
      on the link. Test data are generated and sent in frames of a preset 
      size (frameSize). The Test component will try to estimate the 
      number of bit errors in any errored frame which is identifiable. The 
      statistics will be updated accordingly. A lost frame (may be due to 
      an error on the flag sequence) will be discarded for the bit error rate 
      calculation. The result is presented in the form of xEsyy, where x is 
      the mantissa, syy is the exponent, for example 0E+00, 2E-09.
      Note that the bitErrorRate is an estimate only. For more reliable test 
      results, the test should be done over a long period. Multiple tests 
      would also improve the confidence level of the test results."
::= { mscApsTestResultsEntry 11 }




-- 
-- Version and Compliance statements
-- 



-- Object-Group Statement:
-- A list of all current accessible leaf objects.

-- OBJECTS { mscApsTestBitsTx,
--           mscApsModeMismatchAlarm,
--           mscApsOperationalState,
--           mscApsTestStorageType,
--           mscApsSwitchovers,
--           mscApsTestCauseOfTermination,
--           mscApsWaitToRestorePeriod,
--           mscApsApplicationFramerName,
--           mscApsTestPurpose,
--           mscApsTestTimeRemaining,
--           mscApsTestType,
--           mscApsProtocolFailureAlarm,
--           mscApsHoldOffTime,
--           mscApsTestFrmSize,
--           mscApsTestAdminState,
--           mscApsUnknownStatus,
--           mscApsFarEndRequest,
--           mscApsProtectionLine,
--           mscApsTestElapsedTime,
--           mscApsFarEndRequestChannel,
--           mscApsTestBitsRx,
--           mscApsTimeUntilRestore,
--           mscApsAvailabilityStatus,
--           mscApsSignalDegradeRatio,
--           mscApsTestBytesTx,
--           mscApsTestFrmTx,
--           mscApsTestUsageState,
--           mscApsTestCustomizedPattern,
--           mscApsSdOnLines,
--           mscApsTestComponentName,
--           mscApsStandbyStatus,
--           mscApsStorageType,
--           mscApsRevertive,
--           mscApsNearEndRequest,
--           mscApsTestOperationalState,
--           mscApsWorkingLine,
--           mscApsTestDataStartDelay,
--           mscApsTestBytesRx,
--           mscApsTestDisplayInterval,
--           mscApsControlStatus,
--           mscApsAdminState,
--           mscApsTestFrmRx,
--           mscApsTestBitErrorRate,
--           mscApsUsageState,
--           mscApsTestRowStatus,
--           mscApsRowStatus,
--           mscApsTestDuration,
--           mscApsNearEndRxActiveLine,
--           mscApsProceduralStatus,
--           mscApsNearEndRequestChannel,
--           mscApsTestFrmPatternType,
--           mscApsTestErroredFrmRx,
--           mscApsAlarmStatus,
--           mscApsCustomerIdentifier,
--           mscApsMode,
--           mscApsComponentName }
-- STATUS  mandatory
-- DESCRIPTION
--   "A list of all current accessible leaf objects."

apsGroup OBJECT IDENTIFIER ::= { apsMIB 1 }
apsGroupCA OBJECT IDENTIFIER ::= { apsGroup 1 }
apsGroupCA02 OBJECT IDENTIFIER ::= { apsGroupCA 3 }
apsGroupCA02A OBJECT IDENTIFIER ::= { apsGroupCA02 2 }



-- Agent-Capabilities Statement:

-- PRODUCT-RELEASE "MscPassport Release 1.2 Aps."
-- STATUS          mandatory
-- DESCRIPTION     "Carrier Passport Aps MIB: MIB Version CA02A,
--                  Software Version CA02S9C."
-- SUPPORTS        Nortel-MsCarrier-MscPassport-ApsMIB
--    INCLUDES     { apsGroupCA02A }

apsCapabilities OBJECT IDENTIFIER ::= { apsMIB 3 }
apsCapabilitiesCA OBJECT IDENTIFIER ::= { apsCapabilities 1 }
apsCapabilitiesCA02 OBJECT IDENTIFIER ::= { apsCapabilitiesCA 3 }
apsCapabilitiesCA02A OBJECT IDENTIFIER ::= { apsCapabilitiesCA02 2 }





END
