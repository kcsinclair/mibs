Nortel-MsCarrier-MscPassport-TrunksMIB
DEFINITIONS ::= BEGIN



IMPORTS

      OBJECT-TYPE
   FROM RFC-1212

      mscPassportMIBs,
      mscComponents
   FROM Nortel-MsCarrier-MscPassport-UsefulDefinitionsMIB

      Counter32,
      DisplayString,
      StorageType,
      RowStatus,
      InterfaceIndex,
      Gauge32,
      Integer32,
      Unsigned32
   FROM Nortel-MsCarrier-MscPassport-StandardTextualConventionsMIB

      AsciiString,
      NonReplicated,
      PassportCounter64,
      FixedPoint1,
      AsciiStringIndex
   FROM Nortel-MsCarrier-MscPassport-TextualConventionsMIB;




-- LAST-UPDATED   "9909010000Z"
-- ORGANIZATION   "Nortel Networks"
-- CONTACT-INFO   "
--         Nortel Carrier Data Network Management
--         
--         Postal:       P.O. Box 3511, Station C 
--                       Ottawa, Ontario 
--                       Canada  K1Y 4H7
--         
--         via the WEB:  http://www.nortelnetworks.com  
--                       select 'Contact Us' from the menu
--          
--         via phone:    1-800-4NORTEL"
-- DESCRIPTION
--    "The module describing the Nortel MsCarrier MscPassport
--     Trunks Enterprise MIB."

trunksMIB OBJECT IDENTIFIER ::= { mscPassportMIBs 43 }










-- Trunk/n
-- The Trunk component provides a Passport to Passport connection. It 
-- controls a protocol stack associated with a logical port on a function 
-- processor that provides an interconnection to another Passport with 
-- a Trunk component.
-- It requires the existence of the Routing component. Note that 
-- dpnRouting also needs to be included in the featureList of CP's 
-- LogicalProcessorType component.
-- Either an AtmAccess or an Unacknowledged subcomponent must be 
-- added to provide the underlying link protocol and associated 
-- hardware that the Trunk will use. 

mscTrk OBJECT IDENTIFIER ::= { mscComponents 60 }



mscTrkRowStatusTable OBJECT-TYPE
   SYNTAX     SEQUENCE OF MscTrkRowStatusEntry
   ACCESS     not-accessible
   STATUS     mandatory
   DESCRIPTION
     "This entry controls the addition and deletion of 
      mscTrk components."
::= { mscTrk 1 }

mscTrkRowStatusEntry OBJECT-TYPE
   SYNTAX     MscTrkRowStatusEntry
   ACCESS     not-accessible
   STATUS     mandatory
   DESCRIPTION
     "A single entry in the table represents a single 
      mscTrk component."
   INDEX {
      mscTrkIndex }
::= { mscTrkRowStatusTable 1 }

MscTrkRowStatusEntry ::= SEQUENCE {
   mscTrkRowStatus
      RowStatus,
   mscTrkComponentName
      DisplayString,
   mscTrkStorageType
      StorageType,
   mscTrkIndex
      Integer32 }

mscTrkRowStatus OBJECT-TYPE
   SYNTAX     RowStatus 
   ACCESS     read-write
   STATUS     mandatory
   DESCRIPTION
     "This variable is used as the basis for SNMP naming of
      mscTrk components.
      These components can be added and deleted."
::= { mscTrkRowStatusEntry 1 }

mscTrkComponentName OBJECT-TYPE
   SYNTAX     DisplayString 
   ACCESS     read-only
   STATUS     mandatory
   DESCRIPTION
     "This variable provides the component's string name for
      use with the ASCII Console Interface"
::= { mscTrkRowStatusEntry 2 }

mscTrkStorageType OBJECT-TYPE
   SYNTAX     StorageType 
   ACCESS     read-only
   STATUS     mandatory
   DESCRIPTION
     "This variable represents the storage type value for the
      mscTrk tables."
::= { mscTrkRowStatusEntry 4 }

mscTrkIndex OBJECT-TYPE
   SYNTAX     Integer32 (0..65535)
   ACCESS     not-accessible
   STATUS     mandatory
   DESCRIPTION
     "This variable represents the index for the mscTrk tables."
::= { mscTrkRowStatusEntry 10 }

mscTrkIfEntryTable OBJECT-TYPE
   SYNTAX     SEQUENCE OF MscTrkIfEntryEntry
   ACCESS     not-accessible
   STATUS     mandatory
   DESCRIPTION
     "This group contains the provisionable attributes for the ifEntry."
::= { mscTrk 100 }

mscTrkIfEntryEntry OBJECT-TYPE
   SYNTAX     MscTrkIfEntryEntry
   ACCESS     not-accessible
   STATUS     mandatory
   DESCRIPTION
     "An entry in the mscTrkIfEntryTable."
   INDEX {
      mscTrkIndex }
::= { mscTrkIfEntryTable 1 }

MscTrkIfEntryEntry ::= SEQUENCE {
   mscTrkIfAdminStatus
      INTEGER,
   mscTrkIfIndex
      InterfaceIndex }

mscTrkIfAdminStatus OBJECT-TYPE
   SYNTAX     INTEGER  {
                 up(1),
                 down(2),
                 testing(3) }
   ACCESS     read-write
   STATUS     mandatory
   DESCRIPTION
     "The desired state of the interface. The up state indicates the 
      interface is operational. The down state indicates the interface is not 
      operational. The testing state indicates that no operational packets 
      can be passed."
   DEFVAL     { up }
::= { mscTrkIfEntryEntry 1 }

mscTrkIfIndex OBJECT-TYPE
   SYNTAX     InterfaceIndex (1..65535)
   ACCESS     read-only
   STATUS     mandatory
   DESCRIPTION
     "This is the index for the IfEntry. Its value is automatically initialized 
      during the provisioning process."
::= { mscTrkIfEntryEntry 2 }

mscTrkProvTable OBJECT-TYPE
   SYNTAX     SEQUENCE OF MscTrkProvEntry
   ACCESS     not-accessible
   STATUS     mandatory
   DESCRIPTION
     "This group of attributes provides the parameters used by the layer 3 
      Trunk to Trunk staging protocol."
::= { mscTrk 101 }

mscTrkProvEntry OBJECT-TYPE
   SYNTAX     MscTrkProvEntry
   ACCESS     not-accessible
   STATUS     mandatory
   DESCRIPTION
     "An entry in the mscTrkProvTable."
   INDEX {
      mscTrkIndex }
::= { mscTrkProvTable 1 }

MscTrkProvEntry ::= SEQUENCE {
   mscTrkExpectedRemoteNodeName
      AsciiString,
   mscTrkRemoteValidationAction
      INTEGER,
   mscTrkMaximumExpectedRoundTripDelay
      Unsigned32,
   mscTrkIdleTimeOut
      Unsigned32 }

mscTrkExpectedRemoteNodeName OBJECT-TYPE
   SYNTAX     AsciiString (SIZE (0..12))
   ACCESS     read-write
   STATUS     mandatory
   DESCRIPTION
     "This attribute specifies the expected node name of the module to 
      which this Trunk is connected. Once entered, the node name must 
      correspond to the Mod nodeName attribute of the remote node. The 
      Trunk end points exchange their node name through the Trunk 
      staging protocol. The staged value is validated and the 
      remoteValidationAction will be executed for those values not 
      matching the value supplied for this attribute.
      If this attribute is an empty string, then the comparison is always 
      successful."
::= { mscTrkProvEntry 1 }

mscTrkRemoteValidationAction OBJECT-TYPE
   SYNTAX     INTEGER  {
                 continue(0),
                 disable(1) }
   ACCESS     read-write
   STATUS     mandatory
   DESCRIPTION
     "This attribute specifies the action to be taken if there is a mismatch 
      between the expectedRemoteNodeName attribute and the value 
      received from the remote end. The remoteValidationAction 
      determines the action when a value is supplied to the 
      expectedRemoteNodeName attribute. If this attribute is provisioned 
      to continue then upon an unsuccessful validation staging continues, 
      otherwise, if disable is set then the Trunk does not continue to stage 
      but, attempts to stage again after a one minute time out.
      All unsuccessful validation when the expectedRemoteNodeName 
      has been set result in the generation of an alarm."
   DEFVAL     { continue }
::= { mscTrkProvEntry 2 }

mscTrkMaximumExpectedRoundTripDelay OBJECT-TYPE
   SYNTAX     Unsigned32 (1..1500)
   ACCESS     read-write
   STATUS     mandatory
   DESCRIPTION
     "This is the maximum round trip delay value used by the Trunk 
      staging protocol, in conjunction with measuredSpeedToIf, to 
      determine if it has taken too long to successfully stage with a 
      remote Trunk. The value specified must be larger than the 
      measuredRoundTripDelay or the Trunk may not successfully stage."
   DEFVAL     { 1500 }
::= { mscTrkProvEntry 3 }

mscTrkIdleTimeOut OBJECT-TYPE
   SYNTAX     Unsigned32 (2..30)
   ACCESS     read-write
   STATUS     mandatory
   DESCRIPTION
     "This attribute specifies the Trunk protocol idle time out duration in 
      units of seconds. If the local Trunk does not receive any packets 
      from the link for the period specified by this attribute, the Trunk 
      enters Are You There (AYT) mode for up to two seconds. If the 
      Trunk does not receive any packets from the remote during the AYT 
      mode it will restage; otherwise, it exits AYT mode and continues to 
      provide service."
   DEFVAL     { 4 }
::= { mscTrkProvEntry 4 }

mscTrkOverridesTable OBJECT-TYPE
   SYNTAX     SEQUENCE OF MscTrkOverridesEntry
   ACCESS     not-accessible
   STATUS     mandatory
   DESCRIPTION
     "Theses attribute comprise the set of provisionable override 
      parameters supported by both the Trunk and DpnGateway 
      components. The attributes are used when reporting operational 
      attributes (used for metric calculations) to the routing system."
::= { mscTrk 102 }

mscTrkOverridesEntry OBJECT-TYPE
   SYNTAX     MscTrkOverridesEntry
   ACCESS     not-accessible
   STATUS     mandatory
   DESCRIPTION
     "An entry in the mscTrkOverridesTable."
   INDEX {
      mscTrkIndex }
::= { mscTrkOverridesTable 1 }

MscTrkOverridesEntry ::= SEQUENCE {
   mscTrkOverrideTransmitSpeed
      Gauge32,
   mscTrkOldOverrideRoundTripDelay
      Gauge32,
   mscTrkOverrideRoundTripUsec
      FixedPoint1 }

mscTrkOverrideTransmitSpeed OBJECT-TYPE
   SYNTAX     Gauge32 (0 | 1000..4294967295)
   ACCESS     read-write
   STATUS     mandatory
   DESCRIPTION
     "This is the overridden value of link speed (bit/s) that, if staged 
      successfully with the remote, is reported to the routing system for 
      metric calculations. A zero indicates that an override value has not 
      been provided and that only the measured value will be reported to 
      the routing system.
      If this value is changed on a Trunk or DpnGateway that is enabled, 
      the LOCK and UNLOCK commands must be issued to the 
      component to restage the override with the remote."
   DEFVAL     { 0 }
::= { mscTrkOverridesEntry 1 }

mscTrkOldOverrideRoundTripDelay OBJECT-TYPE
   SYNTAX     Gauge32 (0..1500)
   ACCESS     read-write
   STATUS     obsolete
   DESCRIPTION
     "This is the overridden value of link delay (ms) that, if staged 
      successfully with the remote, is reported to the routing system for 
      metric calculations. A zero indicates that an override value has not 
      been provided and that only the measured value will be reported to 
      the routing system. 
      If this value is changed on a Trunk or DpnGateway that is enabled, 
      the LOCK and UNLOCK commands must be issued to the 
      component to restage the override with the remote."
   DEFVAL     { 0 }
::= { mscTrkOverridesEntry 2 }

mscTrkOverrideRoundTripUsec OBJECT-TYPE
   SYNTAX     FixedPoint1 (0..15000)
   ACCESS     read-write
   STATUS     mandatory
   DESCRIPTION
     "This is the overridden value of link delay (ms) that, if staged 
      successfully with the remote, is reported to the routing system for 
      metric calculations. A zero indicates that an override value has not 
      been provided and that only the measured value will be reported to 
      the routing system. 
      If this value is changed on a Trunk or DpnGateway that is enabled, 
      the LOCK and UNLOCK commands must be issued to the 
      component to restage the override with the remote."
   DEFVAL     { 0 }
::= { mscTrkOverridesEntry 3 }

mscTrkStateTable OBJECT-TYPE
   SYNTAX     SEQUENCE OF MscTrkStateEntry
   ACCESS     not-accessible
   STATUS     mandatory
   DESCRIPTION
     "This group contains the three OSI State attributes and the six OSI 
      Status attributes. The descriptions generically indicate what each 
      attribute implies about the component. Note that not all the values 
      and state combinations described here are supported by every 
      component which uses this group. For component-specific 
      information and the valid state combinations, refer to NTP 241-
      7001-150, Passport Operations and Maintenance Guide."
::= { mscTrk 103 }

mscTrkStateEntry OBJECT-TYPE
   SYNTAX     MscTrkStateEntry
   ACCESS     not-accessible
   STATUS     mandatory
   DESCRIPTION
     "An entry in the mscTrkStateTable."
   INDEX {
      mscTrkIndex }
::= { mscTrkStateTable 1 }

MscTrkStateEntry ::= SEQUENCE {
   mscTrkAdminState
      INTEGER,
   mscTrkOperationalState
      INTEGER,
   mscTrkUsageState
      INTEGER,
   mscTrkAvailabilityStatus
      OCTET STRING,
   mscTrkProceduralStatus
      OCTET STRING,
   mscTrkControlStatus
      OCTET STRING,
   mscTrkAlarmStatus
      OCTET STRING,
   mscTrkStandbyStatus
      INTEGER,
   mscTrkUnknownStatus
      INTEGER }

mscTrkAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component.
      
      The OSI Status attributes, if supported by the component, may 
      provide more details, qualifying the state of the component."
   DEFVAL     { unlocked }
::= { mscTrkStateEntry 1 }

mscTrkOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle.
      
      The OSI Status attributes, if supported by the component, may 
      provide more details, qualifying the state of the component."
   DEFVAL     { disabled }
::= { mscTrkStateEntry 2 }

mscTrkUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time.
      
      The OSI Status attributes, if supported by the component, may 
      provide more details, qualifying the state of the component."
   DEFVAL     { idle }
::= { mscTrkStateEntry 3 }

mscTrkAvailabilityStatus OBJECT-TYPE
   SYNTAX     OCTET STRING (SIZE (2))
   ACCESS     read-only
   STATUS     mandatory
   DESCRIPTION
     "If supported by the component, this attribute indicates the OSI 
      Availability status of the component. Note that, even though it is 
      defined as a multi-valued set, at most one value is shown to the user.
      
      When no values are in the set, this indicates that either the attribute 
      is not supported or that none of the status conditions described 
      below are present.
      
      The value inTest indicates that the resource is undergoing a test 
      procedure. If adminState is locked or shuttingDown, the normal 
      users are precluded from using the resource and controlStatus is 
      reservedForTest. Tests that do not exclude additional users can be 
      present in any operational or administrative state but the 
      reservedForTest condition should not be present.
      
      The value failed indicates that the component has an internal fault 
      that prevents it from operating. The operationalState is disabled.
      
      The value dependency indicates that the component cannot operate 
      because some other resource on which it depends is unavailable. 
      The operationalState is disabled.
      
      The value powerOff indicates the resource requires power to be 
      applied and it is not powered on. The operationalState is disabled.
      
      The value offLine indicates the resource requires a routine 
      operation (either manual, automatic, or both) to be performed to 
      place it on-line and make it available for use. The operationalState 
      is disabled.
      
      The value offDuty indicates the resource is inactive in accordance 
      with a predetermined time schedule. In the absence of other 
      disabling conditions, the operationalState is enabled or disabled.
      
      The value degraded indicates the service provided by the 
      component is degraded in some way, such as in speed or operating 
      capacity. However, the resource remains available for service. The 
      operationalState is enabled.
      
      The value notInstalled indicates the resource is not present. The 
      operationalState is disabled.
      
      The value logFull is not used.

      Description of bits:
      inTest(0)
      failed(1)
      powerOff(2)
      offLine(3)
      offDuty(4)
      dependency(5)
      degraded(6)
      notInstalled(7)
      logFull(8)"
::= { mscTrkStateEntry 4 }

mscTrkProceduralStatus OBJECT-TYPE
   SYNTAX     OCTET STRING (SIZE (1))
   ACCESS     read-only
   STATUS     mandatory
   DESCRIPTION
     "If supported by the component, this attribute indicates the OSI 
      Procedural status of the component. Note that, even though it is 
      defined as a multi-valued set, at most one value is shown to the user.
      
      When no values are in the set, this indicates that either the attribute 
      is not supported or that none of the status conditions described 
      below are present.
      
      The value initializationRequired indicates (for a resource which 
      doesn't initialize autonomously) that initialization is required before 
      it can perform its normal functions, and this procedure has not been 
      initiated. The operationalState is disabled.
      
      The value notInitialized indicates (for a resource which does 
      initialize autonomously) that initialization is required before it can 
      perform its normal functions, and this procedure has not been 
      initiated. The operationalState may be enabled or disabled.
      
      The value initializing indicates that initialization has been initiated 
      but is not yet complete. The operationalState may be enabled or 
      disabled.
      
      The value reporting indicates the resource has completed some 
      processing operation and is notifying the results. The 
      operationalState is enabled.
      
      The value terminating indicates the component is in a termination 
      phase. If the resource doesn't reinitialize autonomously, 
      operationalState is disabled; otherwise it is enabled or disabled.

      Description of bits:
      initializationRequired(0)
      notInitialized(1)
      initializing(2)
      reporting(3)
      terminating(4)"
::= { mscTrkStateEntry 5 }

mscTrkControlStatus OBJECT-TYPE
   SYNTAX     OCTET STRING (SIZE (1))
   ACCESS     read-only
   STATUS     mandatory
   DESCRIPTION
     "If supported by the component, this attribute indicates the OSI 
      Control status of the component. Note that, even though it is defined 
      as a multi-valued set, at most one value is shown to the user.
      
      When no values are in the set, this indicates that either the attribute 
      is not supported or that none of the status conditions described 
      below are present.
      
      The value subjectToTest indicates the resource is available but tests 
      may be conducted simultaneously at unpredictable times, which 
      may cause it to exhibit unusual characteristics.
      
      The value partOfServicesLocked indicates that part of the service is 
      restricted from users of a resource. The adminState is unlocked.
      
      The value reservedForTest indicates that the component is 
      administratively unavailable because it is undergoing a test 
      procedure. The adminState is locked.
      
      The value suspended indicates that the service has been 
      administratively suspended.

      Description of bits:
      subjectToTest(0)
      partOfServicesLocked(1)
      reservedForTest(2)
      suspended(3)"
::= { mscTrkStateEntry 6 }

mscTrkAlarmStatus OBJECT-TYPE
   SYNTAX     OCTET STRING (SIZE (1))
   ACCESS     read-only
   STATUS     mandatory
   DESCRIPTION
     "If supported by the component, this attribute indicates the OSI 
      Alarm status of the component. Note that, even though it is defined 
      as a multi-valued set, at most one value is shown to the user.
      
      When no values are in the set, this indicates that either the attribute 
      is not supported or that none of the status conditions described 
      below are present.
      
      The value underRepair indicates the component is currently being 
      repaired. The operationalState is enabled or disabled.
      
      The value critical indicates one or more critical alarms are 
      outstanding against the component. Other, less severe, alarms may 
      also be outstanding. The operationalState is enabled or disabled.
      
      The value major indicates one or more major alarms are 
      outstanding against the component. Other, less severe, alarms may 
      also be outstanding. The operationalState is enabled or disabled.
      
      The value minor indicates one or more minor alarms are 
      outstanding against the component. Other, less severe, alarms may 
      also be outstanding. The operationalState is enabled or disabled.
      
      The value alarmOutstanding generically indicates that an alarm of 
      some severity is outstanding against the component.

      Description of bits:
      underRepair(0)
      critical(1)
      major(2)
      minor(3)
      alarmOutstanding(4)"
::= { mscTrkStateEntry 7 }

mscTrkStandbyStatus OBJECT-TYPE
   SYNTAX     INTEGER  {
                 hotStandby(0),
                 coldStandby(1),
                 providingService(2),
                 notSet(15) }
   ACCESS     read-only
   STATUS     mandatory
   DESCRIPTION
     "If supported by the component, this attribute indicates the OSI 
      Standby status of the component.
      
      The value notSet indicates that either the attribute is not supported 
      or that none of the status conditions described below are present. 
      Note that this is a non-standard value, used because the original 
      specification indicated this attribute was set-valued and thus, did not 
      provide a value to indicate that none of the other three are 
      applicable.
      
      The value hotStandby indicates that the resource is not providing 
      service but will be immediately able to take over the role of the 
      resource to be backed up, without initialization activity, and 
      containing the same information as the resource to be backed up.
      
      The value coldStandby indicates the resource is a backup for 
      another resource but will not be immediately able to take over the 
      role of the backed up resource and will require some initialization 
      activity.
      
      The value providingService indicates that this component, as a 
      backup resource, is currently backing up another resource."
   DEFVAL     { notSet }
::= { mscTrkStateEntry 8 }

mscTrkUnknownStatus OBJECT-TYPE
   SYNTAX     INTEGER  {
                 false(0),
                 true(1) }
   ACCESS     read-only
   STATUS     mandatory
   DESCRIPTION
     "This attribute indicates the OSI Unknown status of the component.
      
      The value false indicates that all of the other OSI State and Status 
      attribute values can be considered accurate.
      
      The value true indicates that the actual state of the component is not 
      known for sure."
   DEFVAL     { false }
::= { mscTrkStateEntry 9 }

mscTrkOperStatusTable OBJECT-TYPE
   SYNTAX     SEQUENCE OF MscTrkOperStatusEntry
   ACCESS     not-accessible
   STATUS     mandatory
   DESCRIPTION
     "This group includes the Operational Status attribute. This attribute 
      defines the current operational state of this component."
::= { mscTrk 104 }

mscTrkOperStatusEntry OBJECT-TYPE
   SYNTAX     MscTrkOperStatusEntry
   ACCESS     not-accessible
   STATUS     mandatory
   DESCRIPTION
     "An entry in the mscTrkOperStatusTable."
   INDEX {
      mscTrkIndex }
::= { mscTrkOperStatusTable 1 }

MscTrkOperStatusEntry ::= SEQUENCE {
   mscTrkSnmpOperStatus
      INTEGER }

mscTrkSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { mscTrkOperStatusEntry 1 }

mscTrkOperTable OBJECT-TYPE
   SYNTAX     SEQUENCE OF MscTrkOperEntry
   ACCESS     not-accessible
   STATUS     mandatory
   DESCRIPTION
     "This is the group of operational attributes supported by the Trunk."
::= { mscTrk 105 }

mscTrkOperEntry OBJECT-TYPE
   SYNTAX     MscTrkOperEntry
   ACCESS     not-accessible
   STATUS     mandatory
   DESCRIPTION
     "An entry in the mscTrkOperTable."
   INDEX {
      mscTrkIndex }
::= { mscTrkOperTable 1 }

MscTrkOperEntry ::= SEQUENCE {
   mscTrkRemoteComponentName
      AsciiString }

mscTrkRemoteComponentName OBJECT-TYPE
   SYNTAX     AsciiString (SIZE (1..27))
   ACCESS     read-only
   STATUS     mandatory
   DESCRIPTION
     "This attribute is the component name of the remote end which it has 
      supplied through the Trunk staging protocol."
::= { mscTrkOperEntry 1 }

mscTrkTransportTable OBJECT-TYPE
   SYNTAX     SEQUENCE OF MscTrkTransportEntry
   ACCESS     not-accessible
   STATUS     mandatory
   DESCRIPTION
     "This group of attributes contains the set of operational parameters 
      measured and maintained by both the Trunk and DpnGateway 
      components."
::= { mscTrk 106 }

mscTrkTransportEntry OBJECT-TYPE
   SYNTAX     MscTrkTransportEntry
   ACCESS     not-accessible
   STATUS     mandatory
   DESCRIPTION
     "An entry in the mscTrkTransportTable."
   INDEX {
      mscTrkIndex }
::= { mscTrkTransportTable 1 }

MscTrkTransportEntry ::= SEQUENCE {
   mscTrkMeasuredSpeedToIf
      Gauge32,
   mscTrkMeasuredRoundTripDelay
      Gauge32,
   mscTrkMaxTxUnit
      Gauge32,
   mscTrkMeasuredRoundTripDelayUsec
      FixedPoint1 }

mscTrkMeasuredSpeedToIf OBJECT-TYPE
   SYNTAX     Gauge32 (0..4294967295)
   ACCESS     read-only
   STATUS     mandatory
   DESCRIPTION
     "This attribute indicates the current 'transmittable' bandwidth of the 
      underlying facility.
      For a Trunk with a Unack subcomponent, and a DpnGateway with a 
      Utp subcomponent, if a serial port is used, the value is the measured 
      transmit speed of the port; if a channelized port (E1/DS1) is used, 
      the value is the measured transmit speed of the Channel. 
      For a Trunk with an AtmAccess subcomponent, the value is 
      calculated by converting the VCC transmit cell rate to an equivalent 
      bit rate. The VCC transmit cell rate is determined based on the 
      vccReportingBw attribute of the Trunk AtmAccess component. If 
      vccReportingBw has a value of pcr and attribute bwElastic of 
      AtmAccess has a value of no, the peak cell rate (PCR) of the VCC, 
      defined in txTrafficDescParm of AtmIf Vcc Vcd, is used. If 
      vccReportingBw has a value of pcr and attribute bwElastic of 
      AtmAccess has a value of yes, the minimum of the PCR, defined in 
      txTrafficDescParm of AtmIf Vcc Vcd, and the current cell rate 
      (CCR) of the VCC is used. If vccReportingBw has a value of acr, 
      the best measurement of the actual cell rate (ACR) of the VCC is 
      used, which is the minimum of the PCR, the CCR and the actual 
      shaping rate (ASR).
      For a DpnGateway with a FrAccess subcomponent, the value 
      indicates the committedInformationRate of FrAccess FrMuxSetup.
      A value of zero is displayed when the underlying facility is disabled 
      or the current 'transmittable' bandwidth is unknown."
   DEFVAL     { 0 }
::= { mscTrkTransportEntry 1 }

mscTrkMeasuredRoundTripDelay OBJECT-TYPE
   SYNTAX     Gauge32 (0..1500)
   ACCESS     read-only
   STATUS     obsolete
   DESCRIPTION
     "This attribute indicates the measured Round Trip Delay (msec) 
      discovered with the remote through the Trunk and DpnGateway 
      staging protocols. The value includes emission, propagation, and 
      queuing delays. A 512 byte data packet is used to perform the 
      measurement. A value of zero is displayed when the link is disabled 
      or the measured Round Trip Delay is unknown."
   DEFVAL     { 0 }
::= { mscTrkTransportEntry 2 }

mscTrkMaxTxUnit OBJECT-TYPE
   SYNTAX     Gauge32 (0..65535)
   ACCESS     read-only
   STATUS     mandatory
   DESCRIPTION
     "This is the maximum transmission unit (byte size) that is supported 
      by the Trunk or DpnGateway component. This size includes the 
      data and routing headers. A value of zero indicates the MTU has not 
      yet been determined."
   DEFVAL     { 0 }
::= { mscTrkTransportEntry 3 }

mscTrkMeasuredRoundTripDelayUsec OBJECT-TYPE
   SYNTAX     FixedPoint1 (0..15000)
   ACCESS     read-only
   STATUS     mandatory
   DESCRIPTION
     "This attribute indicates the measured Round Trip Delay (msec) 
      discovered with the remote through the Trunk and DpnGateway 
      staging protocols. The value includes emission, propagation, and 
      queuing delays. A 512 byte data packet is used to perform the 
      measurement. A value of zero is displayed when the link is disabled 
      or the measured Round Trip Delay is unknown."
   DEFVAL     { 0 }
::= { mscTrkTransportEntry 4 }

mscTrkStatsTable OBJECT-TYPE
   SYNTAX     SEQUENCE OF MscTrkStatsEntry
   ACCESS     not-accessible
   STATUS     mandatory
   DESCRIPTION
     "These attributes comprise the statistics collected by the Trunk 
      component."
::= { mscTrk 107 }

mscTrkStatsEntry OBJECT-TYPE
   SYNTAX     MscTrkStatsEntry
   ACCESS     not-accessible
   STATUS     mandatory
   DESCRIPTION
     "An entry in the mscTrkStatsTable."
   INDEX {
      mscTrkIndex }
::= { mscTrkStatsTable 1 }

MscTrkStatsEntry ::= SEQUENCE {
   mscTrkAreYouThereModeEntries
      Counter32,
   mscTrkPktFromIf
      PassportCounter64,
   mscTrkTrunkPktFromIf
      Counter32,
   mscTrkTrunkPktToIf
      Counter32,
   mscTrkDiscardUnforward
      PassportCounter64,
   mscTrkDiscardTrunkPktFromIf
      Counter32,
   mscTrkIntPktFromIf
      PassportCounter64,
   mscTrkDiscardIntUnforward
      PassportCounter64,
   mscTrkStagingAttempts
      Counter32,
   mscTrkDiscardTrunkPktToIf
      Counter32 }

mscTrkAreYouThereModeEntries OBJECT-TYPE
   SYNTAX     Counter32 
   ACCESS     read-only
   STATUS     mandatory
   DESCRIPTION
     "This attribute counts the number of times that the component has 
      entered Are You There mode. This counter wraps around to zero 
      when the maximum value is exceeded."
::= { mscTrkStatsEntry 1 }

mscTrkPktFromIf OBJECT-TYPE
   SYNTAX     PassportCounter64 
   ACCESS     read-only
   STATUS     mandatory
   DESCRIPTION
     "This attribute counts the number of packets received from the 
      remote module. It does not include the packets received from the 
      interrupting queue. This counter wraps around to zero when the 
      maximum value is exceeded."
::= { mscTrkStatsEntry 2 }

mscTrkTrunkPktFromIf OBJECT-TYPE
   SYNTAX     Counter32 
   ACCESS     read-only
   STATUS     mandatory
   DESCRIPTION
     "This attribute counts the number of internal trunk protocol packets 
      (including those from the interrupting queue) received from the 
      remote module. These packets are forwarded to the Trunk 
      component. This counter wraps around to zero when the maximum 
      value is exceeded."
::= { mscTrkStatsEntry 3 }

mscTrkTrunkPktToIf OBJECT-TYPE
   SYNTAX     Counter32 
   ACCESS     read-only
   STATUS     mandatory
   DESCRIPTION
     "This attribute counts the number of internal trunk protocol packets 
      (including those through the interrupting queue) transmitted to the 
      remote module. This counter wraps around to zero when the 
      maximum value is exceeded."
::= { mscTrkStatsEntry 4 }

mscTrkDiscardUnforward OBJECT-TYPE
   SYNTAX     PassportCounter64 
   ACCESS     read-only
   STATUS     mandatory
   DESCRIPTION
     "This attribute counts the number of packets received from the 
      remote module that have been discarded. It does not include the 
      packets received from the interrupting queue that have been 
      discarded. This counter wraps around to zero when the maximum 
      value is exceeded. Two main reasons that cause this counter to 
      increase are: 
      (1) the remote protocol is not compatible with the local protocol 
      stack or, 
      (2) the packet cannot be forwarded due to a recent loss of 
      connectivity or due to congestion."
::= { mscTrkStatsEntry 5 }

mscTrkDiscardTrunkPktFromIf OBJECT-TYPE
   SYNTAX     Counter32 
   ACCESS     read-only
   STATUS     mandatory
   DESCRIPTION
     "This attribute counts the number of internal trunk protocol packets 
      (including those on the interrupting queue) received from the 
      remote module that have been discarded. This counter wraps around 
      to zero when the maximum value is exceeded. The three main 
      reasons that cause this counter to increase are: 
      (1) the two Trunks are not synchronized, 
      (2) the remote trunk protocol is not the same version as the local 
      protocol, and 
      (3) the remote trunk has restaged."
::= { mscTrkStatsEntry 6 }

mscTrkIntPktFromIf OBJECT-TYPE
   SYNTAX     PassportCounter64 
   ACCESS     read-only
   STATUS     mandatory
   DESCRIPTION
     "This attribute counts the number of packets received on the 
      interrupting queue from the remote module. This counter wraps 
      around to zero when the maximum value is exceeded."
::= { mscTrkStatsEntry 7 }

mscTrkDiscardIntUnforward OBJECT-TYPE
   SYNTAX     PassportCounter64 
   ACCESS     read-only
   STATUS     mandatory
   DESCRIPTION
     "This attribute counts the number of packets received on the 
      interrupting queue from the remote module that have been 
      discarded. This counter wraps around to zero when the maximum 
      value is exceeded. Two main reasons that cause this counter to 
      increment are: 
      (1) the remote protocol is not compatible to the local protocol stack 
      and, 
      (2) the packet cannot be forwarded due to either a recent loss of 
      connectivity or due to congestion."
::= { mscTrkStatsEntry 8 }

mscTrkStagingAttempts OBJECT-TYPE
   SYNTAX     Counter32 
   ACCESS     read-only
   STATUS     mandatory
   DESCRIPTION
     "This attribute counts the number of times that the staging protocol 
      has attempted to stage with the remote module. This counter wraps 
      around to zero when the maximum value is exceeded. The main 
      reason that causes this counter to increment is that the local 
      hardware is up but, the local protocol cannot stage with the remote 
      protocol due to a faulty connection. If the value is zero, then the 
      local hardware has never enabled successfully."
::= { mscTrkStatsEntry 9 }

mscTrkDiscardTrunkPktToIf OBJECT-TYPE
   SYNTAX     Counter32 
   ACCESS     read-only
   STATUS     mandatory
   DESCRIPTION
     "This attribute counts the number of internal trunk protocol packets 
      (including those through the interrupting queue) that have been 
      discarded before being transmitted to the remote module. This 
      counter wraps around to zero when the maximum value is 
      exceeded. The main reason that causes this counter to increment is 
      that the trunk can not get sufficient resources to create an internal 
      trunk protocol packet."
::= { mscTrkStatsEntry 10 }

mscTrkSpeedReportingTable OBJECT-TYPE
   SYNTAX     SEQUENCE OF MscTrkSpeedReportingEntry
   ACCESS     not-accessible
   STATUS     mandatory
   DESCRIPTION
     "This group of provisionable attributes provides the ability to disable 
      or enable the generation of speed change alarms by the Trunk 
      component. It also provides the ability to disable or enable the 
      Dynamic Speed Reporting mechanism."
::= { mscTrk 109 }

mscTrkSpeedReportingEntry OBJECT-TYPE
   SYNTAX     MscTrkSpeedReportingEntry
   ACCESS     not-accessible
   STATUS     mandatory
   DESCRIPTION
     "An entry in the mscTrkSpeedReportingTable."
   INDEX {
      mscTrkIndex }
::= { mscTrkSpeedReportingTable 1 }

MscTrkSpeedReportingEntry ::= SEQUENCE {
   mscTrkSpeedReportingHoldOff
      Unsigned32,
   mscTrkLowSpeedAlarmThreshold
      Unsigned32,
   mscTrkHighSpeedAlarmThreshold
      Unsigned32 }

mscTrkSpeedReportingHoldOff OBJECT-TYPE
   SYNTAX     Unsigned32 (1..1200)
   ACCESS     read-write
   STATUS     mandatory
   DESCRIPTION
     "This attribute specifies the hold off time for reporting speed 
      increases. When the measuredSpeedToIf reaches a level specified 
      by the speedReportingThresholds attribute, the value specifies the 
      duration (in units of seconds) for which the measuredSpeedToIf 
      must maintain that level before it will be reported."
   DEFVAL     { 30 }
::= { mscTrkSpeedReportingEntry 2 }

mscTrkLowSpeedAlarmThreshold OBJECT-TYPE
   SYNTAX     Unsigned32 (0 | 1..4294967295)
   ACCESS     read-write
   STATUS     mandatory
   DESCRIPTION
     "This attribute specifies the lower end of the range of normal speeds 
      for this Trunk. If the measuredSpeedToIf drops below this value the 
      Trunk component generates a SET alarm. When the 
      measuredSpeedToIf reaches or exceeds the value of this attribute, 
      the Trunk component will generate a CLEAR alarm."
   DEFVAL     { 0 }
::= { mscTrkSpeedReportingEntry 3 }

mscTrkHighSpeedAlarmThreshold OBJECT-TYPE
   SYNTAX     Unsigned32 (1..4294967295)
   ACCESS     read-write
   STATUS     mandatory
   DESCRIPTION
     "This attribute specifies the upper end of the range of normal speeds 
      for this Trunk. If the measuredSpeedToIf exceeds this value the 
      Trunk component generates a SET alarm. When the 
      measuredSpeedToIf returns to or falls below the value of this 
      attribute, the Trunk component will generate a CLEAR alarm."
   DEFVAL     { 4294967295 }
::= { mscTrkSpeedReportingEntry 4 }

mscTrkSpdThTable OBJECT-TYPE
   SYNTAX     SEQUENCE OF MscTrkSpdThEntry
   ACCESS     not-accessible
   STATUS     mandatory
   DESCRIPTION
     "This attribute controls the behavior of the Dynamic Speed 
      Reporting mechanism. If its value is empty then the mechanism is 
      disabled and neither increases nor decreases are reported. 
      Otherwise, the attribute may contain up to seven threshold levels 
      which are used to control the reporting of speed increases. Speed 
      decreases are always reported immediately. If the 
      measuredSpeedToIf increases such that it reaches one of the 
      threshold levels which is greater than the last reported speed, the 
      Trunk starts the speedReportingHoldOff timer. If the speed remains 
      above this threshold until the timer expires, the Trunk component 
      then reports the measuredSpeedToIf; otherwise the increase is not 
      reported."
::= { mscTrk 318 }

mscTrkSpdThEntry OBJECT-TYPE
   SYNTAX     MscTrkSpdThEntry
   ACCESS     not-accessible
   STATUS     mandatory
   DESCRIPTION
     "An entry in the mscTrkSpdThTable."
   INDEX {
      mscTrkIndex,
      mscTrkSpdThValue }
::= { mscTrkSpdThTable 1 }

MscTrkSpdThEntry ::= SEQUENCE {
   mscTrkSpdThValue
      Integer32,
   mscTrkSpdThRowStatus
      RowStatus }

mscTrkSpdThValue OBJECT-TYPE
   SYNTAX     Integer32 (0..268435455)
   ACCESS     read-write
   STATUS     mandatory
   DESCRIPTION
     "This variable represents both the value and the index for the
      mscTrkSpdThTable."
::= { mscTrkSpdThEntry 1 }

mscTrkSpdThRowStatus OBJECT-TYPE
   SYNTAX     RowStatus 
   ACCESS     write-only
   STATUS     mandatory
   DESCRIPTION
     "This variable is used to control the addition and deletion 
      of individual values of the mscTrkSpdThTable."
::= { mscTrkSpdThEntry 2 }

mscTrkPktBpTable OBJECT-TYPE
   SYNTAX     SEQUENCE OF MscTrkPktBpEntry
   ACCESS     not-accessible
   STATUS     mandatory
   DESCRIPTION
     "This attribute counts the number of packets received by the Trunk. 
      It is a vector indexed by the emission priorities (ep0, ep1, and ep2) 
      of the packets. The highest emission priority is ep0. These counters 
      wrap around to zero when the maximum value is exceeded."
::= { mscTrk 368 }

mscTrkPktBpEntry OBJECT-TYPE
   SYNTAX     MscTrkPktBpEntry
   ACCESS     not-accessible
   STATUS     mandatory
   DESCRIPTION
     "An entry in the mscTrkPktBpTable."
   INDEX {
      mscTrkIndex,
      mscTrkPktBpIndex }
::= { mscTrkPktBpTable 1 }

MscTrkPktBpEntry ::= SEQUENCE {
   mscTrkPktBpIndex
      INTEGER,
   mscTrkPktBpValue
      PassportCounter64 }

mscTrkPktBpIndex OBJECT-TYPE
   SYNTAX     INTEGER  {
                 ep0(0),
                 ep1(1),
                 ep2(2) }
   ACCESS     not-accessible
   STATUS     mandatory
   DESCRIPTION
     "This variable represents the mscTrkPktBpTable
      specific index for the mscTrkPktBpTable."
::= { mscTrkPktBpEntry 1 }

mscTrkPktBpValue OBJECT-TYPE
   SYNTAX     PassportCounter64 
   ACCESS     read-only
   STATUS     mandatory
   DESCRIPTION
     "This variable represents an individual value for the
      mscTrkPktBpTable."
::= { mscTrkPktBpEntry 2 }

mscTrkDiscBpTable OBJECT-TYPE
   SYNTAX     SEQUENCE OF MscTrkDiscBpEntry
   ACCESS     not-accessible
   STATUS     mandatory
   DESCRIPTION
     "This attribute counts the number of packets received from the 
      remote module that have been discarded. It is a vector indexed by 
      the emission priorities (ep0, ep1 and ep2) of the packets. The 
      highest emission priority is ep0. These counters wrap around to zero 
      when the maximum value is exceeded.
      Two main reasons that cause this counter to increment are: 
      (1) the remote protocol is not compatible to the local protocol stack 
      and, 
      (2) the packet cannot be forwarded due to either a recent loss of 
      connectivity or due to congestion.
      DESCRIPTION"
::= { mscTrk 369 }

mscTrkDiscBpEntry OBJECT-TYPE
   SYNTAX     MscTrkDiscBpEntry
   ACCESS     not-accessible
   STATUS     mandatory
   DESCRIPTION
     "An entry in the mscTrkDiscBpTable."
   INDEX {
      mscTrkIndex,
      mscTrkDiscBpIndex }
::= { mscTrkDiscBpTable 1 }

MscTrkDiscBpEntry ::= SEQUENCE {
   mscTrkDiscBpIndex
      INTEGER,
   mscTrkDiscBpValue
      PassportCounter64 }

mscTrkDiscBpIndex OBJECT-TYPE
   SYNTAX     INTEGER  {
                 ep0(0),
                 ep1(1),
                 ep2(2) }
   ACCESS     not-accessible
   STATUS     mandatory
   DESCRIPTION
     "This variable represents the mscTrkDiscBpTable
      specific index for the mscTrkDiscBpTable."
::= { mscTrkDiscBpEntry 1 }

mscTrkDiscBpValue OBJECT-TYPE
   SYNTAX     PassportCounter64 
   ACCESS     read-only
   STATUS     mandatory
   DESCRIPTION
     "This variable represents an individual value for the
      mscTrkDiscBpTable."
::= { mscTrkDiscBpEntry 2 }

mscTrkOctBpTable OBJECT-TYPE
   SYNTAX     SEQUENCE OF MscTrkOctBpEntry
   ACCESS     not-accessible
   STATUS     mandatory
   DESCRIPTION
     "This attribute counts the octets coming from the remote module 
      which are received by the Trunk. It is a vector indexed by the 
      emission priorities (ep0, ep1 and ep2) of the packets. The highest 
      emission priority is ep0. These counters wrap around to zero when 
      the maximum value is exceeded."
::= { mscTrk 370 }

mscTrkOctBpEntry OBJECT-TYPE
   SYNTAX     MscTrkOctBpEntry
   ACCESS     not-accessible
   STATUS     mandatory
   DESCRIPTION
     "An entry in the mscTrkOctBpTable."
   INDEX {
      mscTrkIndex,
      mscTrkOctBpIndex }
::= { mscTrkOctBpTable 1 }

MscTrkOctBpEntry ::= SEQUENCE {
   mscTrkOctBpIndex
      INTEGER,
   mscTrkOctBpValue
      PassportCounter64 }

mscTrkOctBpIndex OBJECT-TYPE
   SYNTAX     INTEGER  {
                 ep0(0),
                 ep1(1),
                 ep2(2) }
   ACCESS     not-accessible
   STATUS     mandatory
   DESCRIPTION
     "This variable represents the mscTrkOctBpTable
      specific index for the mscTrkOctBpTable."
::= { mscTrkOctBpEntry 1 }

mscTrkOctBpValue OBJECT-TYPE
   SYNTAX     PassportCounter64 
   ACCESS     read-only
   STATUS     mandatory
   DESCRIPTION
     "This variable represents an individual value for the
      mscTrkOctBpTable."
::= { mscTrkOctBpEntry 2 }


-- Trunk/n PorsStatistics
-- This is a dynamic subcomponent of a Trunk which appears when a 
-- PathAdmin component is provisioned under the Trunk supporting 
-- interrupting priority queue. It contains statistics associated with 
-- PORS traffic for a Trunk component.

mscTrkPorsStats OBJECT IDENTIFIER ::= { mscTrk 6 }



mscTrkPorsStatsRowStatusTable OBJECT-TYPE
   SYNTAX     SEQUENCE OF MscTrkPorsStatsRowStatusEntry
   ACCESS     not-accessible
   STATUS     mandatory
   DESCRIPTION
     "This entry controls the addition and deletion of 
      mscTrkPorsStats components."
::= { mscTrkPorsStats 1 }

mscTrkPorsStatsRowStatusEntry OBJECT-TYPE
   SYNTAX     MscTrkPorsStatsRowStatusEntry
   ACCESS     not-accessible
   STATUS     mandatory
   DESCRIPTION
     "A single entry in the table represents a single 
      mscTrkPorsStats component."
   INDEX {
      mscTrkIndex,
      mscTrkPorsStatsIndex }
::= { mscTrkPorsStatsRowStatusTable 1 }

MscTrkPorsStatsRowStatusEntry ::= SEQUENCE {
   mscTrkPorsStatsRowStatus
      RowStatus,
   mscTrkPorsStatsComponentName
      DisplayString,
   mscTrkPorsStatsStorageType
      StorageType,
   mscTrkPorsStatsIndex
      NonReplicated }

mscTrkPorsStatsRowStatus OBJECT-TYPE
   SYNTAX     RowStatus 
   ACCESS     read-only
   STATUS     mandatory
   DESCRIPTION
     "This variable is used as the basis for SNMP naming of
      mscTrkPorsStats components.
      These components cannot be added nor deleted."
::= { mscTrkPorsStatsRowStatusEntry 1 }

mscTrkPorsStatsComponentName OBJECT-TYPE
   SYNTAX     DisplayString 
   ACCESS     read-only
   STATUS     mandatory
   DESCRIPTION
     "This variable provides the component's string name for
      use with the ASCII Console Interface"
::= { mscTrkPorsStatsRowStatusEntry 2 }

mscTrkPorsStatsStorageType OBJECT-TYPE
   SYNTAX     StorageType 
   ACCESS     read-only
   STATUS     mandatory
   DESCRIPTION
     "This variable represents the storage type value for the
      mscTrkPorsStats tables."
::= { mscTrkPorsStatsRowStatusEntry 4 }

mscTrkPorsStatsIndex OBJECT-TYPE
   SYNTAX     NonReplicated 
   ACCESS     not-accessible
   STATUS     mandatory
   DESCRIPTION
     "This variable represents the index for the mscTrkPorsStats tables."
::= { mscTrkPorsStatsRowStatusEntry 10 }

mscTrkPorsStatsOperTable OBJECT-TYPE
   SYNTAX     SEQUENCE OF MscTrkPorsStatsOperEntry
   ACCESS     not-accessible
   STATUS     mandatory
   DESCRIPTION
     "This operational group provides the PORS Trunks interrupting and 
      normal traffic statistics for operator console display."
::= { mscTrkPorsStats 10 }

mscTrkPorsStatsOperEntry OBJECT-TYPE
   SYNTAX     MscTrkPorsStatsOperEntry
   ACCESS     not-accessible
   STATUS     mandatory
   DESCRIPTION
     "An entry in the mscTrkPorsStatsOperTable."
   INDEX {
      mscTrkIndex,
      mscTrkPorsStatsIndex }
::= { mscTrkPorsStatsOperTable 1 }

MscTrkPorsStatsOperEntry ::= SEQUENCE {
   mscTrkPorsStatsPorsNormPktFromIf
      PassportCounter64,
   mscTrkPorsStatsPorsNormDiscUnforwardFromIf
      PassportCounter64,
   mscTrkPorsStatsPorsNormOctetFromIf
      PassportCounter64,
   mscTrkPorsStatsPorsIntPktFromIf
      PassportCounter64,
   mscTrkPorsStatsPorsIntDiscUnforwardFromIf
      PassportCounter64,
   mscTrkPorsStatsPorsIntOctetFromIf
      PassportCounter64 }

mscTrkPorsStatsPorsNormPktFromIf OBJECT-TYPE
   SYNTAX     PassportCounter64 
   ACCESS     read-only
   STATUS     mandatory
   DESCRIPTION
     "This attribute counts the number of normal priority packets received 
      on the PORS Trunk normal priority queue. This counter wraps 
      around to zero when the maximum value is exceeded."
::= { mscTrkPorsStatsOperEntry 1 }

mscTrkPorsStatsPorsNormDiscUnforwardFromIf OBJECT-TYPE
   SYNTAX     PassportCounter64 
   ACCESS     read-only
   STATUS     mandatory
   DESCRIPTION
     "This attribute counts the number of normal priority packets 
      discarded from the PORS Trunk normal priority queue. This 
      counter wraps around to zero when the maximum value is 
      exceeded."
::= { mscTrkPorsStatsOperEntry 2 }

mscTrkPorsStatsPorsNormOctetFromIf OBJECT-TYPE
   SYNTAX     PassportCounter64 
   ACCESS     read-only
   STATUS     mandatory
   DESCRIPTION
     "This attribute counts the number of normal priority bytes received 
      on the PORS Trunk normal priority queue.This counter wraps 
      around to zero when the maximum value is exceeded."
::= { mscTrkPorsStatsOperEntry 3 }

mscTrkPorsStatsPorsIntPktFromIf OBJECT-TYPE
   SYNTAX     PassportCounter64 
   ACCESS     read-only
   STATUS     mandatory
   DESCRIPTION
     "This attribute counts the number of interrupting priority packets 
      received on the PORS Trunk interrupting priority queue. This 
      counter wraps around to zero when the maximum value is 
      exceeded."
::= { mscTrkPorsStatsOperEntry 4 }

mscTrkPorsStatsPorsIntDiscUnforwardFromIf OBJECT-TYPE
   SYNTAX     PassportCounter64 
   ACCESS     read-only
   STATUS     mandatory
   DESCRIPTION
     "This attribute counts the number of interrupting priority packets 
      discarded from the PORS Trunk interrupting priority queue. This 
      counter wraps around to zero when the maximum value is 
      exceeded."
::= { mscTrkPorsStatsOperEntry 5 }

mscTrkPorsStatsPorsIntOctetFromIf OBJECT-TYPE
   SYNTAX     PassportCounter64 
   ACCESS     read-only
   STATUS     mandatory
   DESCRIPTION
     "This attribute counts the number of interrupting priority bytes 
      received on the PORS Trunk interrupting priority queue. This 
      counter wraps around to zero when the maximum value is 
      exceeded."
::= { mscTrkPorsStatsOperEntry 6 }

mscTrkPorsStatsPktBpTable OBJECT-TYPE
   SYNTAX     SEQUENCE OF MscTrkPorsStatsPktBpEntry
   ACCESS     not-accessible
   STATUS     mandatory
   DESCRIPTION
     "This attribute counts the number of PORS packets received by the 
      Trunk. It is an array indexed by the emission priorities (ep0, ep1 and 
      ep2) and discard priorities (dp0, dp1, dp2 and dp3) of the packets. 
      The highest emission priority is ep0 and the least discardable 
      priority is dp0. These counters wrap around to zero when the 
      maximum value is exceeded."
::= { mscTrkPorsStats 371 }

mscTrkPorsStatsPktBpEntry OBJECT-TYPE
   SYNTAX     MscTrkPorsStatsPktBpEntry
   ACCESS     not-accessible
   STATUS     mandatory
   DESCRIPTION
     "An entry in the mscTrkPorsStatsPktBpTable."
   INDEX {
      mscTrkIndex,
      mscTrkPorsStatsIndex,
      mscTrkPorsStatsPktBpEpIndex,
      mscTrkPorsStatsPktBpDpIndex }
::= { mscTrkPorsStatsPktBpTable 1 }

MscTrkPorsStatsPktBpEntry ::= SEQUENCE {
   mscTrkPorsStatsPktBpEpIndex
      INTEGER,
   mscTrkPorsStatsPktBpDpIndex
      INTEGER,
   mscTrkPorsStatsPktBpValue
      PassportCounter64 }

mscTrkPorsStatsPktBpEpIndex OBJECT-TYPE
   SYNTAX     INTEGER  {
                 ep0(0),
                 ep1(1),
                 ep2(2) }
   ACCESS     not-accessible
   STATUS     mandatory
   DESCRIPTION
     "This variable represents the next to last index for the 
      mscTrkPorsStatsPktBpTable."
::= { mscTrkPorsStatsPktBpEntry 1 }

mscTrkPorsStatsPktBpDpIndex OBJECT-TYPE
   SYNTAX     INTEGER  {
                 dp0(0),
                 dp1(1),
                 dp2(2),
                 dp3(3) }
   ACCESS     not-accessible
   STATUS     mandatory
   DESCRIPTION
     "This variable represents the final index for the 
      mscTrkPorsStatsPktBpTable."
::= { mscTrkPorsStatsPktBpEntry 2 }

mscTrkPorsStatsPktBpValue OBJECT-TYPE
   SYNTAX     PassportCounter64 
   ACCESS     read-only
   STATUS     mandatory
   DESCRIPTION
     "This variable represents an individual value for the
      mscTrkPorsStatsPktBpTable."
::= { mscTrkPorsStatsPktBpEntry 3 }

mscTrkPorsStatsDiscBpTable OBJECT-TYPE
   SYNTAX     SEQUENCE OF MscTrkPorsStatsDiscBpEntry
   ACCESS     not-accessible
   STATUS     mandatory
   DESCRIPTION
     "This attribute counts the number of PORS packets received from the 
      remote module that have been discarded. It is an array indexed by 
      the emission priorities (ep0, ep1 and ep2) and discard priorities (dp0, 
      dp1, dp2 and dp3) of the packets. The highest emission priority is 
      ep0 and the least discardable priority is dp0. These counters wrap 
      around to zero when the maximum value is exceeded."
::= { mscTrkPorsStats 372 }

mscTrkPorsStatsDiscBpEntry OBJECT-TYPE
   SYNTAX     MscTrkPorsStatsDiscBpEntry
   ACCESS     not-accessible
   STATUS     mandatory
   DESCRIPTION
     "An entry in the mscTrkPorsStatsDiscBpTable."
   INDEX {
      mscTrkIndex,
      mscTrkPorsStatsIndex,
      mscTrkPorsStatsDiscBpEpIndex,
      mscTrkPorsStatsDiscBpDpIndex }
::= { mscTrkPorsStatsDiscBpTable 1 }

MscTrkPorsStatsDiscBpEntry ::= SEQUENCE {
   mscTrkPorsStatsDiscBpEpIndex
      INTEGER,
   mscTrkPorsStatsDiscBpDpIndex
      INTEGER,
   mscTrkPorsStatsDiscBpValue
      PassportCounter64 }

mscTrkPorsStatsDiscBpEpIndex OBJECT-TYPE
   SYNTAX     INTEGER  {
                 ep0(0),
                 ep1(1),
                 ep2(2) }
   ACCESS     not-accessible
   STATUS     mandatory
   DESCRIPTION
     "This variable represents the next to last index for the 
      mscTrkPorsStatsDiscBpTable."
::= { mscTrkPorsStatsDiscBpEntry 1 }

mscTrkPorsStatsDiscBpDpIndex OBJECT-TYPE
   SYNTAX     INTEGER  {
                 dp0(0),
                 dp1(1),
                 dp2(2),
                 dp3(3) }
   ACCESS     not-accessible
   STATUS     mandatory
   DESCRIPTION
     "This variable represents the final index for the 
      mscTrkPorsStatsDiscBpTable."
::= { mscTrkPorsStatsDiscBpEntry 2 }

mscTrkPorsStatsDiscBpValue OBJECT-TYPE
   SYNTAX     PassportCounter64 
   ACCESS     read-only
   STATUS     mandatory
   DESCRIPTION
     "This variable represents an individual value for the
      mscTrkPorsStatsDiscBpTable."
::= { mscTrkPorsStatsDiscBpEntry 3 }

mscTrkPorsStatsOctBpTable OBJECT-TYPE
   SYNTAX     SEQUENCE OF MscTrkPorsStatsOctBpEntry
   ACCESS     not-accessible
   STATUS     mandatory
   DESCRIPTION
     "This attribute counts the number of PORS octets received by the 
      Trunk. It is an array indexed by the emission priorities (ep0, ep1 and 
      ep2) and discard priorities (dp0, dp1, dp2 and dp3) of the packets. 
      The highest emission priority is ep0 and the least discardable 
      priority is dp0. These counters wrap around to zero when the 
      maximum value is exceeded."
::= { mscTrkPorsStats 373 }

mscTrkPorsStatsOctBpEntry OBJECT-TYPE
   SYNTAX     MscTrkPorsStatsOctBpEntry
   ACCESS     not-accessible
   STATUS     mandatory
   DESCRIPTION
     "An entry in the mscTrkPorsStatsOctBpTable."
   INDEX {
      mscTrkIndex,
      mscTrkPorsStatsIndex,
      mscTrkPorsStatsOctBpEpIndex,
      mscTrkPorsStatsOctBpDpIndex }
::= { mscTrkPorsStatsOctBpTable 1 }

MscTrkPorsStatsOctBpEntry ::= SEQUENCE {
   mscTrkPorsStatsOctBpEpIndex
      INTEGER,
   mscTrkPorsStatsOctBpDpIndex
      INTEGER,
   mscTrkPorsStatsOctBpValue
      PassportCounter64 }

mscTrkPorsStatsOctBpEpIndex OBJECT-TYPE
   SYNTAX     INTEGER  {
                 ep0(0),
                 ep1(1),
                 ep2(2) }
   ACCESS     not-accessible
   STATUS     mandatory
   DESCRIPTION
     "This variable represents the next to last index for the 
      mscTrkPorsStatsOctBpTable."
::= { mscTrkPorsStatsOctBpEntry 1 }

mscTrkPorsStatsOctBpDpIndex OBJECT-TYPE
   SYNTAX     INTEGER  {
                 dp0(0),
                 dp1(1),
                 dp2(2),
                 dp3(3) }
   ACCESS     not-accessible
   STATUS     mandatory
   DESCRIPTION
     "This variable represents the final index for the 
      mscTrkPorsStatsOctBpTable."
::= { mscTrkPorsStatsOctBpEntry 2 }

mscTrkPorsStatsOctBpValue OBJECT-TYPE
   SYNTAX     PassportCounter64 
   ACCESS     read-only
   STATUS     mandatory
   DESCRIPTION
     "This variable represents an individual value for the
      mscTrkPorsStatsOctBpTable."
::= { mscTrkPorsStatsOctBpEntry 3 }


-- Trunk/n ForwardingStatistics
-- This is a dynamic subcomponent of a Trunk or DpnGateway which 
-- appears when packet forwarding traffic is used over the Trunk or 
-- DpnGateway. It contains statistics associated with packet 
-- forwarding traffic for Trunks and DpnGateways.

mscTrkFwdStats OBJECT IDENTIFIER ::= { mscTrk 7 }



mscTrkFwdStatsRowStatusTable OBJECT-TYPE
   SYNTAX     SEQUENCE OF MscTrkFwdStatsRowStatusEntry
   ACCESS     not-accessible
   STATUS     mandatory
   DESCRIPTION
     "This entry controls the addition and deletion of 
      mscTrkFwdStats components."
::= { mscTrkFwdStats 1 }

mscTrkFwdStatsRowStatusEntry OBJECT-TYPE
   SYNTAX     MscTrkFwdStatsRowStatusEntry
   ACCESS     not-accessible
   STATUS     mandatory
   DESCRIPTION
     "A single entry in the table represents a single 
      mscTrkFwdStats component."
   INDEX {
      mscTrkIndex,
      mscTrkFwdStatsIndex }
::= { mscTrkFwdStatsRowStatusTable 1 }

MscTrkFwdStatsRowStatusEntry ::= SEQUENCE {
   mscTrkFwdStatsRowStatus
      RowStatus,
   mscTrkFwdStatsComponentName
      DisplayString,
   mscTrkFwdStatsStorageType
      StorageType,
   mscTrkFwdStatsIndex
      NonReplicated }

mscTrkFwdStatsRowStatus OBJECT-TYPE
   SYNTAX     RowStatus 
   ACCESS     read-only
   STATUS     mandatory
   DESCRIPTION
     "This variable is used as the basis for SNMP naming of
      mscTrkFwdStats components.
      These components cannot be added nor deleted."
::= { mscTrkFwdStatsRowStatusEntry 1 }

mscTrkFwdStatsComponentName OBJECT-TYPE
   SYNTAX     DisplayString 
   ACCESS     read-only
   STATUS     mandatory
   DESCRIPTION
     "This variable provides the component's string name for
      use with the ASCII Console Interface"
::= { mscTrkFwdStatsRowStatusEntry 2 }

mscTrkFwdStatsStorageType OBJECT-TYPE
   SYNTAX     StorageType 
   ACCESS     read-only
   STATUS     mandatory
   DESCRIPTION
     "This variable represents the storage type value for the
      mscTrkFwdStats tables."
::= { mscTrkFwdStatsRowStatusEntry 4 }

mscTrkFwdStatsIndex OBJECT-TYPE
   SYNTAX     NonReplicated 
   ACCESS     not-accessible
   STATUS     mandatory
   DESCRIPTION
     "This variable represents the index for the mscTrkFwdStats tables."
::= { mscTrkFwdStatsRowStatusEntry 10 }

mscTrkFwdStatsOperTable OBJECT-TYPE
   SYNTAX     SEQUENCE OF MscTrkFwdStatsOperEntry
   ACCESS     not-accessible
   STATUS     mandatory
   DESCRIPTION
     "This operational group counts the Trunk or DpnGateway packet 
      forwarding traffic statistics for operator console display."
::= { mscTrkFwdStats 10 }

mscTrkFwdStatsOperEntry OBJECT-TYPE
   SYNTAX     MscTrkFwdStatsOperEntry
   ACCESS     not-accessible
   STATUS     mandatory
   DESCRIPTION
     "An entry in the mscTrkFwdStatsOperTable."
   INDEX {
      mscTrkIndex,
      mscTrkFwdStatsIndex }
::= { mscTrkFwdStatsOperTable 1 }

MscTrkFwdStatsOperEntry ::= SEQUENCE {
   mscTrkFwdStatsFwdPktFromIf
      PassportCounter64,
   mscTrkFwdStatsFwdDiscUnforwardFromIf
      PassportCounter64,
   mscTrkFwdStatsFwdOctetFromIf
      PassportCounter64 }

mscTrkFwdStatsFwdPktFromIf OBJECT-TYPE
   SYNTAX     PassportCounter64 
   ACCESS     read-only
   STATUS     mandatory
   DESCRIPTION
     "This attribute counts the number of forwarding packets received by 
      the Trunk or DpnGateway. This counter wraps around to zero when 
      the maximum value is exceeded."
::= { mscTrkFwdStatsOperEntry 1 }

mscTrkFwdStatsFwdDiscUnforwardFromIf OBJECT-TYPE
   SYNTAX     PassportCounter64 
   ACCESS     read-only
   STATUS     mandatory
   DESCRIPTION
     "This attribute counts the number of forwarding packets discarded by 
      the Trunk or DpnGateway. This counter wraps around to zero when 
      the maximum value is exceeded."
::= { mscTrkFwdStatsOperEntry 2 }

mscTrkFwdStatsFwdOctetFromIf OBJECT-TYPE
   SYNTAX     PassportCounter64 
   ACCESS     read-only
   STATUS     mandatory
   DESCRIPTION
     "This attribute counts the number of forwarding bytes received by 
      the Trunk or DpnGateway. This counter wraps around to zero when 
      the maximum value is exceeded."
::= { mscTrkFwdStatsOperEntry 3 }


-- Trunk/n VirtualNetworkStatistics
-- This is a dynamic subcomponent of a Trunk which appears when 
-- virtual networking system (VNS) traffic is used over the Trunk. It 
-- contains statistics associated with virtual traffic network for the 
-- Trunk.

mscTrkVnsStats OBJECT IDENTIFIER ::= { mscTrk 8 }



mscTrkVnsStatsRowStatusTable OBJECT-TYPE
   SYNTAX     SEQUENCE OF MscTrkVnsStatsRowStatusEntry
   ACCESS     not-accessible
   STATUS     mandatory
   DESCRIPTION
     "This entry controls the addition and deletion of 
      mscTrkVnsStats components."
::= { mscTrkVnsStats 1 }

mscTrkVnsStatsRowStatusEntry OBJECT-TYPE
   SYNTAX     MscTrkVnsStatsRowStatusEntry
   ACCESS     not-accessible
   STATUS     mandatory
   DESCRIPTION
     "A single entry in the table represents a single 
      mscTrkVnsStats component."
   INDEX {
      mscTrkIndex,
      mscTrkVnsStatsIndex }
::= { mscTrkVnsStatsRowStatusTable 1 }

MscTrkVnsStatsRowStatusEntry ::= SEQUENCE {
   mscTrkVnsStatsRowStatus
      RowStatus,
   mscTrkVnsStatsComponentName
      DisplayString,
   mscTrkVnsStatsStorageType
      StorageType,
   mscTrkVnsStatsIndex
      NonReplicated }

mscTrkVnsStatsRowStatus OBJECT-TYPE
   SYNTAX     RowStatus 
   ACCESS     read-only
   STATUS     mandatory
   DESCRIPTION
     "This variable is used as the basis for SNMP naming of
      mscTrkVnsStats components.
      These components cannot be added nor deleted."
::= { mscTrkVnsStatsRowStatusEntry 1 }

mscTrkVnsStatsComponentName OBJECT-TYPE
   SYNTAX     DisplayString 
   ACCESS     read-only
   STATUS     mandatory
   DESCRIPTION
     "This variable provides the component's string name for
      use with the ASCII Console Interface"
::= { mscTrkVnsStatsRowStatusEntry 2 }

mscTrkVnsStatsStorageType OBJECT-TYPE
   SYNTAX     StorageType 
   ACCESS     read-only
   STATUS     mandatory
   DESCRIPTION
     "This variable represents the storage type value for the
      mscTrkVnsStats tables."
::= { mscTrkVnsStatsRowStatusEntry 4 }

mscTrkVnsStatsIndex OBJECT-TYPE
   SYNTAX     NonReplicated 
   ACCESS     not-accessible
   STATUS     mandatory
   DESCRIPTION
     "This variable represents the index for the mscTrkVnsStats tables."
::= { mscTrkVnsStatsRowStatusEntry 10 }

mscTrkVnsStatsOperTable OBJECT-TYPE
   SYNTAX     SEQUENCE OF MscTrkVnsStatsOperEntry
   ACCESS     not-accessible
   STATUS     mandatory
   DESCRIPTION
     "This operational group counts the Trunk virtual network traffic 
      statistics for operator console display."
::= { mscTrkVnsStats 10 }

mscTrkVnsStatsOperEntry OBJECT-TYPE
   SYNTAX     MscTrkVnsStatsOperEntry
   ACCESS     not-accessible
   STATUS     mandatory
   DESCRIPTION
     "An entry in the mscTrkVnsStatsOperTable."
   INDEX {
      mscTrkIndex,
      mscTrkVnsStatsIndex }
::= { mscTrkVnsStatsOperTable 1 }

MscTrkVnsStatsOperEntry ::= SEQUENCE {
   mscTrkVnsStatsVnsPktFromIf
      PassportCounter64,
   mscTrkVnsStatsVnsDiscUnforwardFromIf
      PassportCounter64,
   mscTrkVnsStatsVnsOctetFromIf
      PassportCounter64 }

mscTrkVnsStatsVnsPktFromIf OBJECT-TYPE
   SYNTAX     PassportCounter64 
   ACCESS     read-only
   STATUS     mandatory
   DESCRIPTION
     "This attribute counts the number of virtual network packets received 
      by a Trunk component handling virtual network traffic. This counter 
      wraps around to zero when the maximum value is exceeded."
::= { mscTrkVnsStatsOperEntry 1 }

mscTrkVnsStatsVnsDiscUnforwardFromIf OBJECT-TYPE
   SYNTAX     PassportCounter64 
   ACCESS     read-only
   STATUS     mandatory
   DESCRIPTION
     "This attribute counts the number of virtual network packets 
      discarded by a Trunk component handling virtual network traffic. 
      This counter wraps around to zero when the maximum value is 
      exceeded."
::= { mscTrkVnsStatsOperEntry 2 }

mscTrkVnsStatsVnsOctetFromIf OBJECT-TYPE
   SYNTAX     PassportCounter64 
   ACCESS     read-only
   STATUS     mandatory
   DESCRIPTION
     "This attribute counts the number of virtual network bytes received 
      by a Trunk component handling virtual network traffic. This counter 
      wraps around to zero when the maximum value is exceeded."
::= { mscTrkVnsStatsOperEntry 3 }

mscTrkVnsStatsPktBpTable OBJECT-TYPE
   SYNTAX     SEQUENCE OF MscTrkVnsStatsPktBpEntry
   ACCESS     not-accessible
   STATUS     mandatory
   DESCRIPTION
     "This attribute counts the number of Virtual Network packets 
      received by the Trunk. It is an array indexed by the emission 
      priorities (ep0, ep1 and ep2) and discard priorities (dp0, dp1, dp2 
      and dp3) of the packets. The highest emission priority is ep0 and the 
      least discardable priority is dp0. These counters wrap around to zero 
      when the maximum value is exceeded."
::= { mscTrkVnsStats 377 }

mscTrkVnsStatsPktBpEntry OBJECT-TYPE
   SYNTAX     MscTrkVnsStatsPktBpEntry
   ACCESS     not-accessible
   STATUS     mandatory
   DESCRIPTION
     "An entry in the mscTrkVnsStatsPktBpTable."
   INDEX {
      mscTrkIndex,
      mscTrkVnsStatsIndex,
      mscTrkVnsStatsPktBpEpIndex,
      mscTrkVnsStatsPktBpDpIndex }
::= { mscTrkVnsStatsPktBpTable 1 }

MscTrkVnsStatsPktBpEntry ::= SEQUENCE {
   mscTrkVnsStatsPktBpEpIndex
      INTEGER,
   mscTrkVnsStatsPktBpDpIndex
      INTEGER,
   mscTrkVnsStatsPktBpValue
      PassportCounter64 }

mscTrkVnsStatsPktBpEpIndex OBJECT-TYPE
   SYNTAX     INTEGER  {
                 ep0(0),
                 ep1(1),
                 ep2(2) }
   ACCESS     not-accessible
   STATUS     mandatory
   DESCRIPTION
     "This variable represents the next to last index for the 
      mscTrkVnsStatsPktBpTable."
::= { mscTrkVnsStatsPktBpEntry 1 }

mscTrkVnsStatsPktBpDpIndex OBJECT-TYPE
   SYNTAX     INTEGER  {
                 dp0(0),
                 dp1(1),
                 dp2(2),
                 dp3(3) }
   ACCESS     not-accessible
   STATUS     mandatory
   DESCRIPTION
     "This variable represents the final index for the 
      mscTrkVnsStatsPktBpTable."
::= { mscTrkVnsStatsPktBpEntry 2 }

mscTrkVnsStatsPktBpValue OBJECT-TYPE
   SYNTAX     PassportCounter64 
   ACCESS     read-only
   STATUS     mandatory
   DESCRIPTION
     "This variable represents an individual value for the
      mscTrkVnsStatsPktBpTable."
::= { mscTrkVnsStatsPktBpEntry 3 }

mscTrkVnsStatsDiscBpTable OBJECT-TYPE
   SYNTAX     SEQUENCE OF MscTrkVnsStatsDiscBpEntry
   ACCESS     not-accessible
   STATUS     mandatory
   DESCRIPTION
     "This attribute counts the number of Virtual Network packets 
      received from the remote module that have been discarded by the 
      Trunk. It is an array indexed by the emission priorities (ep0, ep1 and 
      ep2) and discard priorities (dp0, dp1, dp2 and dp3) of the packets. 
      The highest emission priority is ep0 and the least discardable 
      priority is dp0. These counters wrap around to zero when the 
      maximum value is exceeded."
::= { mscTrkVnsStats 378 }

mscTrkVnsStatsDiscBpEntry OBJECT-TYPE
   SYNTAX     MscTrkVnsStatsDiscBpEntry
   ACCESS     not-accessible
   STATUS     mandatory
   DESCRIPTION
     "An entry in the mscTrkVnsStatsDiscBpTable."
   INDEX {
      mscTrkIndex,
      mscTrkVnsStatsIndex,
      mscTrkVnsStatsDiscBpEpIndex,
      mscTrkVnsStatsDiscBpDpIndex }
::= { mscTrkVnsStatsDiscBpTable 1 }

MscTrkVnsStatsDiscBpEntry ::= SEQUENCE {
   mscTrkVnsStatsDiscBpEpIndex
      INTEGER,
   mscTrkVnsStatsDiscBpDpIndex
      INTEGER,
   mscTrkVnsStatsDiscBpValue
      PassportCounter64 }

mscTrkVnsStatsDiscBpEpIndex OBJECT-TYPE
   SYNTAX     INTEGER  {
                 ep0(0),
                 ep1(1),
                 ep2(2) }
   ACCESS     not-accessible
   STATUS     mandatory
   DESCRIPTION
     "This variable represents the next to last index for the 
      mscTrkVnsStatsDiscBpTable."
::= { mscTrkVnsStatsDiscBpEntry 1 }

mscTrkVnsStatsDiscBpDpIndex OBJECT-TYPE
   SYNTAX     INTEGER  {
                 dp0(0),
                 dp1(1),
                 dp2(2),
                 dp3(3) }
   ACCESS     not-accessible
   STATUS     mandatory
   DESCRIPTION
     "This variable represents the final index for the 
      mscTrkVnsStatsDiscBpTable."
::= { mscTrkVnsStatsDiscBpEntry 2 }

mscTrkVnsStatsDiscBpValue OBJECT-TYPE
   SYNTAX     PassportCounter64 
   ACCESS     read-only
   STATUS     mandatory
   DESCRIPTION
     "This variable represents an individual value for the
      mscTrkVnsStatsDiscBpTable."
::= { mscTrkVnsStatsDiscBpEntry 3 }

mscTrkVnsStatsOctBpTable OBJECT-TYPE
   SYNTAX     SEQUENCE OF MscTrkVnsStatsOctBpEntry
   ACCESS     not-accessible
   STATUS     mandatory
   DESCRIPTION
     "This attribute counts the number of Virtual Network octets received 
      by the Trunk. It is an array indexed by the emission priorities (ep0, 
      ep1 and ep2) and discard priorities (dp0, dp1, dp2 and dp3) of the 
      packets. The highest emission priority is ep0 and the least 
      discardable priority is dp0. These counters wrap around to zero 
      when the maximum value is exceeded."
::= { mscTrkVnsStats 379 }

mscTrkVnsStatsOctBpEntry OBJECT-TYPE
   SYNTAX     MscTrkVnsStatsOctBpEntry
   ACCESS     not-accessible
   STATUS     mandatory
   DESCRIPTION
     "An entry in the mscTrkVnsStatsOctBpTable."
   INDEX {
      mscTrkIndex,
      mscTrkVnsStatsIndex,
      mscTrkVnsStatsOctBpEpIndex,
      mscTrkVnsStatsOctBpDpIndex }
::= { mscTrkVnsStatsOctBpTable 1 }

MscTrkVnsStatsOctBpEntry ::= SEQUENCE {
   mscTrkVnsStatsOctBpEpIndex
      INTEGER,
   mscTrkVnsStatsOctBpDpIndex
      INTEGER,
   mscTrkVnsStatsOctBpValue
      PassportCounter64 }

mscTrkVnsStatsOctBpEpIndex OBJECT-TYPE
   SYNTAX     INTEGER  {
                 ep0(0),
                 ep1(1),
                 ep2(2) }
   ACCESS     not-accessible
   STATUS     mandatory
   DESCRIPTION
     "This variable represents the next to last index for the 
      mscTrkVnsStatsOctBpTable."
::= { mscTrkVnsStatsOctBpEntry 1 }

mscTrkVnsStatsOctBpDpIndex OBJECT-TYPE
   SYNTAX     INTEGER  {
                 dp0(0),
                 dp1(1),
                 dp2(2),
                 dp3(3) }
   ACCESS     not-accessible
   STATUS     mandatory
   DESCRIPTION
     "This variable represents the final index for the 
      mscTrkVnsStatsOctBpTable."
::= { mscTrkVnsStatsOctBpEntry 2 }

mscTrkVnsStatsOctBpValue OBJECT-TYPE
   SYNTAX     PassportCounter64 
   ACCESS     read-only
   STATUS     mandatory
   DESCRIPTION
     "This variable represents an individual value for the
      mscTrkVnsStatsOctBpTable."
::= { mscTrkVnsStatsOctBpEntry 3 }


-- Trunk/n DprsStatistics
-- This is a dynamic subcomponent of a Trunk which appears when 
-- DPRS traffic is used over the Trunk. It contains statistics associated 
-- with packet forwarding traffic for Trunks.

mscTrkDprsStats OBJECT IDENTIFIER ::= { mscTrk 10 }



mscTrkDprsStatsRowStatusTable OBJECT-TYPE
   SYNTAX     SEQUENCE OF MscTrkDprsStatsRowStatusEntry
   ACCESS     not-accessible
   STATUS     mandatory
   DESCRIPTION
     "This entry controls the addition and deletion of 
      mscTrkDprsStats components."
::= { mscTrkDprsStats 1 }

mscTrkDprsStatsRowStatusEntry OBJECT-TYPE
   SYNTAX     MscTrkDprsStatsRowStatusEntry
   ACCESS     not-accessible
   STATUS     mandatory
   DESCRIPTION
     "A single entry in the table represents a single 
      mscTrkDprsStats component."
   INDEX {
      mscTrkIndex,
      mscTrkDprsStatsIndex }
::= { mscTrkDprsStatsRowStatusTable 1 }

MscTrkDprsStatsRowStatusEntry ::= SEQUENCE {
   mscTrkDprsStatsRowStatus
      RowStatus,
   mscTrkDprsStatsComponentName
      DisplayString,
   mscTrkDprsStatsStorageType
      StorageType,
   mscTrkDprsStatsIndex
      NonReplicated }

mscTrkDprsStatsRowStatus OBJECT-TYPE
   SYNTAX     RowStatus 
   ACCESS     read-only
   STATUS     mandatory
   DESCRIPTION
     "This variable is used as the basis for SNMP naming of
      mscTrkDprsStats components.
      These components cannot be added nor deleted."
::= { mscTrkDprsStatsRowStatusEntry 1 }

mscTrkDprsStatsComponentName OBJECT-TYPE
   SYNTAX     DisplayString 
   ACCESS     read-only
   STATUS     mandatory
   DESCRIPTION
     "This variable provides the component's string name for
      use with the ASCII Console Interface"
::= { mscTrkDprsStatsRowStatusEntry 2 }

mscTrkDprsStatsStorageType OBJECT-TYPE
   SYNTAX     StorageType 
   ACCESS     read-only
   STATUS     mandatory
   DESCRIPTION
     "This variable represents the storage type value for the
      mscTrkDprsStats tables."
::= { mscTrkDprsStatsRowStatusEntry 4 }

mscTrkDprsStatsIndex OBJECT-TYPE
   SYNTAX     NonReplicated 
   ACCESS     not-accessible
   STATUS     mandatory
   DESCRIPTION
     "This variable represents the index for the mscTrkDprsStats tables."
::= { mscTrkDprsStatsRowStatusEntry 10 }

mscTrkDprsStatsPktBpTable OBJECT-TYPE
   SYNTAX     SEQUENCE OF MscTrkDprsStatsPktBpEntry
   ACCESS     not-accessible
   STATUS     mandatory
   DESCRIPTION
     "This attribute counts the number of DPRS packets received by the 
      Trunk. It is an array indexed by the emission priorities (ep0, ep1 and 
      ep2) and discard priorities (dp0, dp1, dp2 and dp3) of the packets. 
      The highest emission priority is ep0 and the least discardable 
      priority is dp0. These counters wrap around to zero when the 
      maximum value is exceeded."
::= { mscTrkDprsStats 374 }

mscTrkDprsStatsPktBpEntry OBJECT-TYPE
   SYNTAX     MscTrkDprsStatsPktBpEntry
   ACCESS     not-accessible
   STATUS     mandatory
   DESCRIPTION
     "An entry in the mscTrkDprsStatsPktBpTable."
   INDEX {
      mscTrkIndex,
      mscTrkDprsStatsIndex,
      mscTrkDprsStatsPktBpEpIndex,
      mscTrkDprsStatsPktBpDpIndex }
::= { mscTrkDprsStatsPktBpTable 1 }

MscTrkDprsStatsPktBpEntry ::= SEQUENCE {
   mscTrkDprsStatsPktBpEpIndex
      INTEGER,
   mscTrkDprsStatsPktBpDpIndex
      INTEGER,
   mscTrkDprsStatsPktBpValue
      PassportCounter64 }

mscTrkDprsStatsPktBpEpIndex OBJECT-TYPE
   SYNTAX     INTEGER  {
                 ep0(0),
                 ep1(1),
                 ep2(2) }
   ACCESS     not-accessible
   STATUS     mandatory
   DESCRIPTION
     "This variable represents the next to last index for the 
      mscTrkDprsStatsPktBpTable."
::= { mscTrkDprsStatsPktBpEntry 1 }

mscTrkDprsStatsPktBpDpIndex OBJECT-TYPE
   SYNTAX     INTEGER  {
                 dp0(0),
                 dp1(1),
                 dp2(2),
                 dp3(3) }
   ACCESS     not-accessible
   STATUS     mandatory
   DESCRIPTION
     "This variable represents the final index for the 
      mscTrkDprsStatsPktBpTable."
::= { mscTrkDprsStatsPktBpEntry 2 }

mscTrkDprsStatsPktBpValue OBJECT-TYPE
   SYNTAX     PassportCounter64 
   ACCESS     read-only
   STATUS     mandatory
   DESCRIPTION
     "This variable represents an individual value for the
      mscTrkDprsStatsPktBpTable."
::= { mscTrkDprsStatsPktBpEntry 3 }

mscTrkDprsStatsDiscBpTable OBJECT-TYPE
   SYNTAX     SEQUENCE OF MscTrkDprsStatsDiscBpEntry
   ACCESS     not-accessible
   STATUS     mandatory
   DESCRIPTION
     "This attribute counts the number of DPRS packets received from the 
      remote module that have been discarded by the Trunk. It is an array 
      indexed by the emission priorities (ep0, ep1 and ep2) and discard 
      priorities (dp0, dp1, dp2 and dp3) of the packets. The highest 
      emission priority is ep0 and the least discardable priority is dp0. 
      These counters wrap around to zero when the maximum value is 
      exceeded."
::= { mscTrkDprsStats 375 }

mscTrkDprsStatsDiscBpEntry OBJECT-TYPE
   SYNTAX     MscTrkDprsStatsDiscBpEntry
   ACCESS     not-accessible
   STATUS     mandatory
   DESCRIPTION
     "An entry in the mscTrkDprsStatsDiscBpTable."
   INDEX {
      mscTrkIndex,
      mscTrkDprsStatsIndex,
      mscTrkDprsStatsDiscBpEpIndex,
      mscTrkDprsStatsDiscBpDpIndex }
::= { mscTrkDprsStatsDiscBpTable 1 }

MscTrkDprsStatsDiscBpEntry ::= SEQUENCE {
   mscTrkDprsStatsDiscBpEpIndex
      INTEGER,
   mscTrkDprsStatsDiscBpDpIndex
      INTEGER,
   mscTrkDprsStatsDiscBpValue
      PassportCounter64 }

mscTrkDprsStatsDiscBpEpIndex OBJECT-TYPE
   SYNTAX     INTEGER  {
                 ep0(0),
                 ep1(1),
                 ep2(2) }
   ACCESS     not-accessible
   STATUS     mandatory
   DESCRIPTION
     "This variable represents the next to last index for the 
      mscTrkDprsStatsDiscBpTable."
::= { mscTrkDprsStatsDiscBpEntry 1 }

mscTrkDprsStatsDiscBpDpIndex OBJECT-TYPE
   SYNTAX     INTEGER  {
                 dp0(0),
                 dp1(1),
                 dp2(2),
                 dp3(3) }
   ACCESS     not-accessible
   STATUS     mandatory
   DESCRIPTION
     "This variable represents the final index for the 
      mscTrkDprsStatsDiscBpTable."
::= { mscTrkDprsStatsDiscBpEntry 2 }

mscTrkDprsStatsDiscBpValue OBJECT-TYPE
   SYNTAX     PassportCounter64 
   ACCESS     read-only
   STATUS     mandatory
   DESCRIPTION
     "This variable represents an individual value for the
      mscTrkDprsStatsDiscBpTable."
::= { mscTrkDprsStatsDiscBpEntry 3 }

mscTrkDprsStatsOctBpTable OBJECT-TYPE
   SYNTAX     SEQUENCE OF MscTrkDprsStatsOctBpEntry
   ACCESS     not-accessible
   STATUS     mandatory
   DESCRIPTION
     "This attribute counts the number of DPRS octets received by the 
      Trunk. It is an array indexed by the emission priorities (ep0, ep1 and 
      ep2) and discard priorities (dp0, dp1, dp2 and dp3) of the packets. 
      The highest emission priority is ep0 and the least discardable 
      priority is dp0. These counters wrap around to zero when the 
      maximum value is exceeded."
::= { mscTrkDprsStats 376 }

mscTrkDprsStatsOctBpEntry OBJECT-TYPE
   SYNTAX     MscTrkDprsStatsOctBpEntry
   ACCESS     not-accessible
   STATUS     mandatory
   DESCRIPTION
     "An entry in the mscTrkDprsStatsOctBpTable."
   INDEX {
      mscTrkIndex,
      mscTrkDprsStatsIndex,
      mscTrkDprsStatsOctBpEpIndex,
      mscTrkDprsStatsOctBpDpIndex }
::= { mscTrkDprsStatsOctBpTable 1 }

MscTrkDprsStatsOctBpEntry ::= SEQUENCE {
   mscTrkDprsStatsOctBpEpIndex
      INTEGER,
   mscTrkDprsStatsOctBpDpIndex
      INTEGER,
   mscTrkDprsStatsOctBpValue
      PassportCounter64 }

mscTrkDprsStatsOctBpEpIndex OBJECT-TYPE
   SYNTAX     INTEGER  {
                 ep0(0),
                 ep1(1),
                 ep2(2) }
   ACCESS     not-accessible
   STATUS     mandatory
   DESCRIPTION
     "This variable represents the next to last index for the 
      mscTrkDprsStatsOctBpTable."
::= { mscTrkDprsStatsOctBpEntry 1 }

mscTrkDprsStatsOctBpDpIndex OBJECT-TYPE
   SYNTAX     INTEGER  {
                 dp0(0),
                 dp1(1),
                 dp2(2),
                 dp3(3) }
   ACCESS     not-accessible
   STATUS     mandatory
   DESCRIPTION
     "This variable represents the final index for the 
      mscTrkDprsStatsOctBpTable."
::= { mscTrkDprsStatsOctBpEntry 2 }

mscTrkDprsStatsOctBpValue OBJECT-TYPE
   SYNTAX     PassportCounter64 
   ACCESS     read-only
   STATUS     mandatory
   DESCRIPTION
     "This variable represents an individual value for the
      mscTrkDprsStatsOctBpTable."
::= { mscTrkDprsStatsOctBpEntry 3 }


-- Trunk/n Address
-- This subcomponent is optionally added to the Trunk component to 
-- specify an NSAP address of a single destination that can be reached 
-- through that trunk, or to specify an NSAP address prefix which 
-- describes a set of destinations that can be reached through that 
-- trunk. 

mscTrkAddr OBJECT IDENTIFIER ::= { mscTrk 11 }



mscTrkAddrRowStatusTable OBJECT-TYPE
   SYNTAX     SEQUENCE OF MscTrkAddrRowStatusEntry
   ACCESS     not-accessible
   STATUS     mandatory
   DESCRIPTION
     "This entry controls the addition and deletion of 
      mscTrkAddr components."
::= { mscTrkAddr 1 }

mscTrkAddrRowStatusEntry OBJECT-TYPE
   SYNTAX     MscTrkAddrRowStatusEntry
   ACCESS     not-accessible
   STATUS     mandatory
   DESCRIPTION
     "A single entry in the table represents a single 
      mscTrkAddr component."
   INDEX {
      mscTrkIndex,
      mscTrkAddrAddressIndex }
::= { mscTrkAddrRowStatusTable 1 }

MscTrkAddrRowStatusEntry ::= SEQUENCE {
   mscTrkAddrRowStatus
      RowStatus,
   mscTrkAddrComponentName
      DisplayString,
   mscTrkAddrStorageType
      StorageType,
   mscTrkAddrAddressIndex
      AsciiStringIndex }

mscTrkAddrRowStatus OBJECT-TYPE
   SYNTAX     RowStatus 
   ACCESS     read-write
   STATUS     mandatory
   DESCRIPTION
     "This variable is used as the basis for SNMP naming of
      mscTrkAddr components.
      These components can be added and deleted."
::= { mscTrkAddrRowStatusEntry 1 }

mscTrkAddrComponentName OBJECT-TYPE
   SYNTAX     DisplayString 
   ACCESS     read-only
   STATUS     mandatory
   DESCRIPTION
     "This variable provides the component's string name for
      use with the ASCII Console Interface"
::= { mscTrkAddrRowStatusEntry 2 }

mscTrkAddrStorageType OBJECT-TYPE
   SYNTAX     StorageType 
   ACCESS     read-only
   STATUS     mandatory
   DESCRIPTION
     "This variable represents the storage type value for the
      mscTrkAddr tables."
::= { mscTrkAddrRowStatusEntry 4 }

mscTrkAddrAddressIndex OBJECT-TYPE
   SYNTAX     AsciiStringIndex (SIZE (1..40))
   ACCESS     not-accessible
   STATUS     mandatory
   DESCRIPTION
     "This variable represents the index for the mscTrkAddr tables."
::= { mscTrkAddrRowStatusEntry 10 }

mscTrkAddrProvTable OBJECT-TYPE
   SYNTAX     SEQUENCE OF MscTrkAddrProvEntry
   ACCESS     not-accessible
   STATUS     mandatory
   DESCRIPTION
     "This group of attributes specifies the provisionable characteristics of 
      the TrkReachableAddress component."
::= { mscTrkAddr 10 }

mscTrkAddrProvEntry OBJECT-TYPE
   SYNTAX     MscTrkAddrProvEntry
   ACCESS     not-accessible
   STATUS     mandatory
   DESCRIPTION
     "An entry in the mscTrkAddrProvTable."
   INDEX {
      mscTrkIndex,
      mscTrkAddrAddressIndex }
::= { mscTrkAddrProvTable 1 }

MscTrkAddrProvEntry ::= SEQUENCE {
   mscTrkAddrCost
      Unsigned32 }

mscTrkAddrCost OBJECT-TYPE
   SYNTAX     Unsigned32 (0..65435)
   ACCESS     read-write
   STATUS     mandatory
   DESCRIPTION
     "This attribute specifies a cost of using the trunk to reach a 
      destination or destinations described by TrkReachableAddress 
      component. The value is assigned by the network administrator to 
      represent the network cost of using this trunk. It can be related to 
      distance, speed, dollars, or any other factor that could be taken into 
      consideration."
   DEFVAL     { 200 }
::= { mscTrkAddrProvEntry 2 }




-- 
-- Version and Compliance statements
-- 



-- Object-Group Statement:
-- A list of all current accessible leaf objects.

-- OBJECTS { mscTrkDiscardTrunkPktToIf,
--           mscTrkUsageState,
--           mscTrkStandbyStatus,
--           mscTrkDiscardTrunkPktFromIf,
--           mscTrkDiscardUnforward,
--           mscTrkPorsStatsPktBpValue,
--           mscTrkComponentName,
--           mscTrkAddrComponentName,
--           mscTrkRemoteValidationAction,
--           mscTrkPorsStatsOctBpValue,
--           mscTrkPktFromIf,
--           mscTrkVnsStatsPktBpValue,
--           mscTrkPorsStatsDiscBpValue,
--           mscTrkTrunkPktFromIf,
--           mscTrkHighSpeedAlarmThreshold,
--           mscTrkStorageType,
--           mscTrkOctBpValue,
--           mscTrkVnsStatsComponentName,
--           mscTrkOperationalState,
--           mscTrkDprsStatsRowStatus,
--           mscTrkVnsStatsDiscBpValue,
--           mscTrkDiscardIntUnforward,
--           mscTrkFwdStatsRowStatus,
--           mscTrkVnsStatsVnsOctetFromIf,
--           mscTrkRowStatus,
--           mscTrkIdleTimeOut,
--           mscTrkPorsStatsStorageType,
--           mscTrkMaxTxUnit,
--           mscTrkDprsStatsComponentName,
--           mscTrkDprsStatsStorageType,
--           mscTrkFwdStatsFwdPktFromIf,
--           mscTrkPorsStatsPorsNormOctetFromIf,
--           mscTrkDprsStatsDiscBpValue,
--           mscTrkSpdThRowStatus,
--           mscTrkPorsStatsPorsIntOctetFromIf,
--           mscTrkFwdStatsFwdDiscUnforwardFromIf,
--           mscTrkSnmpOperStatus,
--           mscTrkDprsStatsOctBpValue,
--           mscTrkIfIndex,
--           mscTrkAlarmStatus,
--           mscTrkAddrCost,
--           mscTrkVnsStatsVnsDiscUnforwardFromIf,
--           mscTrkSpdThValue,
--           mscTrkExpectedRemoteNodeName,
--           mscTrkPorsStatsRowStatus,
--           mscTrkUnknownStatus,
--           mscTrkMeasuredSpeedToIf,
--           mscTrkOverrideTransmitSpeed,
--           mscTrkDiscBpValue,
--           mscTrkAddrStorageType,
--           mscTrkOverrideRoundTripUsec,
--           mscTrkMeasuredRoundTripDelayUsec,
--           mscTrkDprsStatsPktBpValue,
--           mscTrkTrunkPktToIf,
--           mscTrkStagingAttempts,
--           mscTrkAvailabilityStatus,
--           mscTrkFwdStatsFwdOctetFromIf,
--           mscTrkPorsStatsPorsNormPktFromIf,
--           mscTrkVnsStatsStorageType,
--           mscTrkPorsStatsComponentName,
--           mscTrkAreYouThereModeEntries,
--           mscTrkPorsStatsPorsNormDiscUnforwardFromIf,
--           mscTrkFwdStatsStorageType,
--           mscTrkPorsStatsPorsIntDiscUnforwardFromIf,
--           mscTrkControlStatus,
--           mscTrkAdminState,
--           mscTrkPorsStatsPorsIntPktFromIf,
--           mscTrkPktBpValue,
--           mscTrkFwdStatsComponentName,
--           mscTrkIntPktFromIf,
--           mscTrkSpeedReportingHoldOff,
--           mscTrkAddrRowStatus,
--           mscTrkIfAdminStatus,
--           mscTrkMaximumExpectedRoundTripDelay,
--           mscTrkProceduralStatus,
--           mscTrkVnsStatsOctBpValue,
--           mscTrkVnsStatsVnsPktFromIf,
--           mscTrkLowSpeedAlarmThreshold,
--           mscTrkVnsStatsRowStatus,
--           mscTrkRemoteComponentName }
-- STATUS  mandatory
-- DESCRIPTION
--   "A list of all current accessible leaf objects."

trunksGroup OBJECT IDENTIFIER ::= { trunksMIB 1 }
trunksGroupCA OBJECT IDENTIFIER ::= { trunksGroup 1 }
trunksGroupCA02 OBJECT IDENTIFIER ::= { trunksGroupCA 3 }
trunksGroupCA02A OBJECT IDENTIFIER ::= { trunksGroupCA02 2 }



-- Agent-Capabilities Statement:

-- PRODUCT-RELEASE "MscPassport Release 1.2 Trunks."
-- STATUS          mandatory
-- DESCRIPTION     "Carrier Passport Trunks MIB: MIB Version CA02A,
--                  Software Version CA02S9C."
-- SUPPORTS        Nortel-MsCarrier-MscPassport-TrunksMIB
--    INCLUDES     { trunksGroupCA02A }

trunksCapabilities OBJECT IDENTIFIER ::= { trunksMIB 3 }
trunksCapabilitiesCA OBJECT IDENTIFIER ::= { trunksCapabilities 1 }
trunksCapabilitiesCA02 OBJECT IDENTIFIER ::= { trunksCapabilitiesCA 3 }
trunksCapabilitiesCA02A OBJECT IDENTIFIER ::= { trunksCapabilitiesCA02 2 }





END
