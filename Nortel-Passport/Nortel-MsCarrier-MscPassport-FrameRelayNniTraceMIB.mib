Nortel-MsCarrier-MscPassport-FrameRelayNniTraceMIB
DEFINITIONS ::= BEGIN



IMPORTS

      OBJECT-TYPE
   FROM RFC-1212

      mscPassportMIBs
   FROM Nortel-MsCarrier-MscPassport-UsefulDefinitionsMIB

      RowPointer,
      DisplayString,
      StorageType,
      RowStatus,
      Unsigned32
   FROM Nortel-MsCarrier-MscPassport-StandardTextualConventionsMIB

      AsciiString,
      NonReplicated
   FROM Nortel-MsCarrier-MscPassport-TextualConventionsMIB

      mscFrNni,
      mscFrNniIndex
   FROM Nortel-MsCarrier-MscPassport-FrameRelayNniMIB;




-- LAST-UPDATED   "9909010000Z"
-- ORGANIZATION   "Nortel Networks"
-- CONTACT-INFO   "
--         Nortel Carrier Data Network Management
--         
--         Postal:       P.O. Box 3511, Station C 
--                       Ottawa, Ontario 
--                       Canada  K1Y 4H7
--         
--         via the WEB:  http://www.nortelnetworks.com  
--                       select 'Contact Us' from the menu
--          
--         via phone:    1-800-4NORTEL"
-- DESCRIPTION
--    "The module describing the Nortel MsCarrier MscPassport
--     FrameRelayNniTrace Enterprise MIB."

frameRelayNniTraceMIB OBJECT IDENTIFIER ::= { mscPassportMIBs 106 }










-- FrUni/n Trace
-- FrNni/n Trace
-- The Trace component of the Frame Relay service determines if the 
-- trace capability is allowed on this interface. If it is not provisioned, 
-- then a trace session cannot be started on this service.

mscFrNniTrace OBJECT IDENTIFIER ::= { mscFrNni 7 }



mscFrNniTraceRowStatusTable OBJECT-TYPE
   SYNTAX     SEQUENCE OF MscFrNniTraceRowStatusEntry
   ACCESS     not-accessible
   STATUS     mandatory
   DESCRIPTION
     "This entry controls the addition and deletion of 
      mscFrNniTrace components."
::= { mscFrNniTrace 1 }

mscFrNniTraceRowStatusEntry OBJECT-TYPE
   SYNTAX     MscFrNniTraceRowStatusEntry
   ACCESS     not-accessible
   STATUS     mandatory
   DESCRIPTION
     "A single entry in the table represents a single 
      mscFrNniTrace component."
   INDEX {
      mscFrNniIndex,
      mscFrNniTraceIndex }
::= { mscFrNniTraceRowStatusTable 1 }

MscFrNniTraceRowStatusEntry ::= SEQUENCE {
   mscFrNniTraceRowStatus
      RowStatus,
   mscFrNniTraceComponentName
      DisplayString,
   mscFrNniTraceStorageType
      StorageType,
   mscFrNniTraceIndex
      NonReplicated }

mscFrNniTraceRowStatus OBJECT-TYPE
   SYNTAX     RowStatus 
   ACCESS     read-write
   STATUS     mandatory
   DESCRIPTION
     "This variable is used as the basis for SNMP naming of
      mscFrNniTrace components.
      These components can be added and deleted."
::= { mscFrNniTraceRowStatusEntry 1 }

mscFrNniTraceComponentName OBJECT-TYPE
   SYNTAX     DisplayString 
   ACCESS     read-only
   STATUS     mandatory
   DESCRIPTION
     "This variable provides the component's string name for
      use with the ASCII Console Interface"
::= { mscFrNniTraceRowStatusEntry 2 }

mscFrNniTraceStorageType OBJECT-TYPE
   SYNTAX     StorageType 
   ACCESS     read-only
   STATUS     mandatory
   DESCRIPTION
     "This variable represents the storage type value for the
      mscFrNniTrace tables."
::= { mscFrNniTraceRowStatusEntry 4 }

mscFrNniTraceIndex OBJECT-TYPE
   SYNTAX     NonReplicated 
   ACCESS     not-accessible
   STATUS     mandatory
   DESCRIPTION
     "This variable represents the index for the mscFrNniTrace tables."
::= { mscFrNniTraceRowStatusEntry 10 }

mscFrNniTraceOperationalTable OBJECT-TYPE
   SYNTAX     SEQUENCE OF MscFrNniTraceOperationalEntry
   ACCESS     not-accessible
   STATUS     mandatory
   DESCRIPTION
     "This group provides the operational attributes for the Trace 
      component."
::= { mscFrNniTrace 10 }

mscFrNniTraceOperationalEntry OBJECT-TYPE
   SYNTAX     MscFrNniTraceOperationalEntry
   ACCESS     not-accessible
   STATUS     mandatory
   DESCRIPTION
     "An entry in the mscFrNniTraceOperationalTable."
   INDEX {
      mscFrNniIndex,
      mscFrNniTraceIndex }
::= { mscFrNniTraceOperationalTable 1 }

MscFrNniTraceOperationalEntry ::= SEQUENCE {
   mscFrNniTraceReceiverName
      AsciiString,
   mscFrNniTraceDuration
      Unsigned32,
   mscFrNniTraceQueueLimit
      Unsigned32,
   mscFrNniTraceSession
      RowPointer }

mscFrNniTraceReceiverName OBJECT-TYPE
   SYNTAX     AsciiString (SIZE (0..8))
   ACCESS     read-write
   STATUS     mandatory
   DESCRIPTION
     "This attribute should be set to the name of the desired trace receiver 
      before starting a trace session. All available trace receivers are listed 
      under the Trace Rcvr/<string> component. This attribute cannot be 
      set while a trace is active."
::= { mscFrNniTraceOperationalEntry 2 }

mscFrNniTraceDuration OBJECT-TYPE
   SYNTAX     Unsigned32 (0..9999)
   ACCESS     read-write
   STATUS     mandatory
   DESCRIPTION
     "This attribute specifies the duration, in minutes, of a trace session. 
      A value of 0 indicates unlimited duration in which case a trace 
      session remains active until a stop command is issued. The default 
      duration is 60 minutes. This attribute cannot be set while a trace is 
      active."
   DEFVAL     { 60 }
::= { mscFrNniTraceOperationalEntry 3 }

mscFrNniTraceQueueLimit OBJECT-TYPE
   SYNTAX     Unsigned32 (1..100)
   ACCESS     read-write
   STATUS     mandatory
   DESCRIPTION
     "This attribute specifies the total number of bytes of traced data 
      which may be queued for transmission to the trace receiver. When 
      this limit is exceeded, incoming traced frames are discarded. This 
      attribute can be set while a trace is active and takes effect 
      immediately."
   DEFVAL     { 20 }
::= { mscFrNniTraceOperationalEntry 4 }

mscFrNniTraceSession OBJECT-TYPE
   SYNTAX     RowPointer 
   ACCESS     read-only
   STATUS     mandatory
   DESCRIPTION
     "This attribute is set automatically. It identifies the Trace Session 
      component which is forwarding the trace data. This attribute is 
      empty unless a trace is active."
::= { mscFrNniTraceOperationalEntry 5 }


-- FrUni/n Trace Filter 
-- FrNni/n Trace Filter
-- The Filter component defines the type of traced data that is sent to 
-- the receiver. The Filter component provides default values for all its 
-- attributes which are sufficient to start a trace session. Nonetheless, if 
-- needed, these attributes may be changed before or during a trace 
-- session.

mscFrNniTraceFilter OBJECT IDENTIFIER ::= { mscFrNniTrace 2 }



mscFrNniTraceFilterRowStatusTable OBJECT-TYPE
   SYNTAX     SEQUENCE OF MscFrNniTraceFilterRowStatusEntry
   ACCESS     not-accessible
   STATUS     mandatory
   DESCRIPTION
     "This entry controls the addition and deletion of 
      mscFrNniTraceFilter components."
::= { mscFrNniTraceFilter 1 }

mscFrNniTraceFilterRowStatusEntry OBJECT-TYPE
   SYNTAX     MscFrNniTraceFilterRowStatusEntry
   ACCESS     not-accessible
   STATUS     mandatory
   DESCRIPTION
     "A single entry in the table represents a single 
      mscFrNniTraceFilter component."
   INDEX {
      mscFrNniIndex,
      mscFrNniTraceIndex,
      mscFrNniTraceFilterIndex }
::= { mscFrNniTraceFilterRowStatusTable 1 }

MscFrNniTraceFilterRowStatusEntry ::= SEQUENCE {
   mscFrNniTraceFilterRowStatus
      RowStatus,
   mscFrNniTraceFilterComponentName
      DisplayString,
   mscFrNniTraceFilterStorageType
      StorageType,
   mscFrNniTraceFilterIndex
      NonReplicated }

mscFrNniTraceFilterRowStatus OBJECT-TYPE
   SYNTAX     RowStatus 
   ACCESS     read-only
   STATUS     mandatory
   DESCRIPTION
     "This variable is used as the basis for SNMP naming of
      mscFrNniTraceFilter components.
      These components cannot be added nor deleted."
::= { mscFrNniTraceFilterRowStatusEntry 1 }

mscFrNniTraceFilterComponentName OBJECT-TYPE
   SYNTAX     DisplayString 
   ACCESS     read-only
   STATUS     mandatory
   DESCRIPTION
     "This variable provides the component's string name for
      use with the ASCII Console Interface"
::= { mscFrNniTraceFilterRowStatusEntry 2 }

mscFrNniTraceFilterStorageType OBJECT-TYPE
   SYNTAX     StorageType 
   ACCESS     read-only
   STATUS     mandatory
   DESCRIPTION
     "This variable represents the storage type value for the
      mscFrNniTraceFilter tables."
::= { mscFrNniTraceFilterRowStatusEntry 4 }

mscFrNniTraceFilterIndex OBJECT-TYPE
   SYNTAX     NonReplicated 
   ACCESS     not-accessible
   STATUS     mandatory
   DESCRIPTION
     "This variable represents the index for the mscFrNniTraceFilter tables."
::= { mscFrNniTraceFilterRowStatusEntry 10 }

mscFrNniTraceFilterOperationalTable OBJECT-TYPE
   SYNTAX     SEQUENCE OF MscFrNniTraceFilterOperationalEntry
   ACCESS     not-accessible
   STATUS     mandatory
   DESCRIPTION
     "This group provides the operational attributes for the Frame Relay 
      Trace Filter component."
::= { mscFrNniTraceFilter 10 }

mscFrNniTraceFilterOperationalEntry OBJECT-TYPE
   SYNTAX     MscFrNniTraceFilterOperationalEntry
   ACCESS     not-accessible
   STATUS     mandatory
   DESCRIPTION
     "An entry in the mscFrNniTraceFilterOperationalTable."
   INDEX {
      mscFrNniIndex,
      mscFrNniTraceIndex,
      mscFrNniTraceFilterIndex }
::= { mscFrNniTraceFilterOperationalTable 1 }

MscFrNniTraceFilterOperationalEntry ::= SEQUENCE {
   mscFrNniTraceFilterTraceType
      OCTET STRING,
   mscFrNniTraceFilterTracedDlci
      Unsigned32,
   mscFrNniTraceFilterDirection
      OCTET STRING,
   mscFrNniTraceFilterTracedLength
      Unsigned32 }

mscFrNniTraceFilterTraceType OBJECT-TYPE
   SYNTAX     OCTET STRING (SIZE (1))
   ACCESS     read-write
   STATUS     mandatory
   DESCRIPTION
     "This attribute specifies the level of filtering required for this trace 
      session. A value of lmi indicates that Lmi frames are traced. A 
      value of dlci indicates that frames from the Dlci specified by the 
      tracedDlci attribute are traced. A value of badFrames indicates that 
      bad received frames (overruns, CRC errors, aborts) are traced. The 
      default is to trace all frames. This attribute can be set while a trace 
      is active and takes effect immediately.

      Description of bits:
      lmi(0)
      dlci(1)
      badFrames(2)"
   DEFVAL     { 'e0'H }
::= { mscFrNniTraceFilterOperationalEntry 1 }

mscFrNniTraceFilterTracedDlci OBJECT-TYPE
   SYNTAX     Unsigned32 (0..1007)
   ACCESS     read-write
   STATUS     mandatory
   DESCRIPTION
     "This attribute specifies a particular Dlci to trace. A value of zero 
      specifies that all Dlcis are to be traced. This attribute can be set 
      while a trace is active and takes effect immediately."
   DEFVAL     { 0 }
::= { mscFrNniTraceFilterOperationalEntry 2 }

mscFrNniTraceFilterDirection OBJECT-TYPE
   SYNTAX     OCTET STRING (SIZE (1))
   ACCESS     read-write
   STATUS     mandatory
   DESCRIPTION
     "This attribute specifies the direction of the data to be traced as 
      viewed by the service. The values can be egress, and/or ingress. An 
      egress value indicates frames outbound from the service. An 
      ingress value indicates frames inbound to the service. This attribute 
      can be set while a trace is active and takes effect immediately.

      Description of bits:
      egress(0)
      ingress(1)"
   DEFVAL     { 'c0'H }
::= { mscFrNniTraceFilterOperationalEntry 3 }

mscFrNniTraceFilterTracedLength OBJECT-TYPE
   SYNTAX     Unsigned32 (1..2000)
   ACCESS     read-write
   STATUS     mandatory
   DESCRIPTION
     "This attribute specifies the maximum number of bytes to trace per 
      frame starting from the byte following the frame flag. If the frame 
      length is longer than the value specified by this attribute, then the 
      traced frame is truncated. This attribute can be set while a trace is 
      active and takes effect immediately."
   DEFVAL     { 2000 }
::= { mscFrNniTraceFilterOperationalEntry 4 }




-- 
-- Version and Compliance statements
-- 



-- Object-Group Statement:
-- A list of all current accessible leaf objects.

-- OBJECTS { mscFrNniTraceSession,
--           mscFrNniTraceReceiverName,
--           mscFrNniTraceFilterTracedLength,
--           mscFrNniTraceComponentName,
--           mscFrNniTraceFilterTraceType,
--           mscFrNniTraceStorageType,
--           mscFrNniTraceRowStatus,
--           mscFrNniTraceDuration,
--           mscFrNniTraceFilterTracedDlci,
--           mscFrNniTraceFilterComponentName,
--           mscFrNniTraceQueueLimit,
--           mscFrNniTraceFilterStorageType,
--           mscFrNniTraceFilterRowStatus,
--           mscFrNniTraceFilterDirection }
-- STATUS  mandatory
-- DESCRIPTION
--   "A list of all current accessible leaf objects."

frameRelayNniTraceGroup OBJECT IDENTIFIER ::= { frameRelayNniTraceMIB 1 }
frameRelayNniTraceGroupCA OBJECT IDENTIFIER ::= { frameRelayNniTraceGroup 1 }
frameRelayNniTraceGroupCA02 OBJECT IDENTIFIER ::= { frameRelayNniTraceGroupCA 3 }
frameRelayNniTraceGroupCA02A OBJECT IDENTIFIER ::= { frameRelayNniTraceGroupCA02 2 }



-- Agent-Capabilities Statement:

-- PRODUCT-RELEASE "MscPassport Release 1.2 FrameRelayNniTrace."
-- STATUS          mandatory
-- DESCRIPTION     "Carrier Passport FrameRelayNniTrace MIB: MIB Version CA02A,
--                  Software Version CA02S9C."
-- SUPPORTS        Nortel-MsCarrier-MscPassport-FrameRelayNniTraceMIB
--    INCLUDES     { frameRelayNniTraceGroupCA02A }

frameRelayNniTraceCapabilities OBJECT IDENTIFIER ::= { frameRelayNniTraceMIB 3 }
frameRelayNniTraceCapabilitiesCA OBJECT IDENTIFIER ::= { frameRelayNniTraceCapabilities 1 }
frameRelayNniTraceCapabilitiesCA02 OBJECT IDENTIFIER ::= { frameRelayNniTraceCapabilitiesCA 3 }
frameRelayNniTraceCapabilitiesCA02A OBJECT IDENTIFIER ::= { frameRelayNniTraceCapabilitiesCA02 2 }





END
