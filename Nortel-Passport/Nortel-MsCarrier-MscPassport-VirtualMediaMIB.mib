Nortel-MsCarrier-MscPassport-VirtualMediaMIB
DEFINITIONS ::= BEGIN



IMPORTS

      OBJECT-TYPE
   FROM RFC-1212

      mscPassportMIBs,
      mscComponents
   FROM Nortel-MsCarrier-MscPassport-UsefulDefinitionsMIB

      DisplayString,
      StorageType,
      RowStatus,
      InterfaceIndex,
      Integer32,
      Unsigned32
   FROM Nortel-MsCarrier-MscPassport-StandardTextualConventionsMIB

      Link
   FROM Nortel-MsCarrier-MscPassport-TextualConventionsMIB;




-- LAST-UPDATED   "9909010000Z"
-- ORGANIZATION   "Nortel Networks"
-- CONTACT-INFO   "
--         Nortel Carrier Data Network Management
--         
--         Postal:       P.O. Box 3511, Station C 
--                       Ottawa, Ontario 
--                       Canada  K1Y 4H7
--         
--         via the WEB:  http://www.nortelnetworks.com  
--                       select 'Contact Us' from the menu
--          
--         via phone:    1-800-4NORTEL"
-- DESCRIPTION
--    "The module describing the Nortel MsCarrier MscPassport
--     VirtualMedia Enterprise MIB."

virtualMediaMIB OBJECT IDENTIFIER ::= { mscPassportMIBs 135 }










-- VirtualMedia/n
-- The VirtualMedia component represents an instance of a logical 
-- media. VirtualMedia provides IP connectivity between virtual 
-- routers on the same module, and supports an 'always-up IP 
-- interface' concept; i.e interface stays up unless it is administratively 
-- disabled or the hardware goes down.
-- VirtualMedia can be used to support inter-VR communication, or 
-- by BGP-4 to establish an 'always-up IP interface'.

mscVm OBJECT IDENTIFIER ::= { mscComponents 133 }



mscVmRowStatusTable OBJECT-TYPE
   SYNTAX     SEQUENCE OF MscVmRowStatusEntry
   ACCESS     not-accessible
   STATUS     mandatory
   DESCRIPTION
     "This entry controls the addition and deletion of 
      mscVm components."
::= { mscVm 1 }

mscVmRowStatusEntry OBJECT-TYPE
   SYNTAX     MscVmRowStatusEntry
   ACCESS     not-accessible
   STATUS     mandatory
   DESCRIPTION
     "A single entry in the table represents a single 
      mscVm component."
   INDEX {
      mscVmIndex }
::= { mscVmRowStatusTable 1 }

MscVmRowStatusEntry ::= SEQUENCE {
   mscVmRowStatus
      RowStatus,
   mscVmComponentName
      DisplayString,
   mscVmStorageType
      StorageType,
   mscVmIndex
      Integer32 }

mscVmRowStatus OBJECT-TYPE
   SYNTAX     RowStatus 
   ACCESS     read-write
   STATUS     mandatory
   DESCRIPTION
     "This variable is used as the basis for SNMP naming of
      mscVm components.
      These components can be added and deleted."
::= { mscVmRowStatusEntry 1 }

mscVmComponentName OBJECT-TYPE
   SYNTAX     DisplayString 
   ACCESS     read-only
   STATUS     mandatory
   DESCRIPTION
     "This variable provides the component's string name for
      use with the ASCII Console Interface"
::= { mscVmRowStatusEntry 2 }

mscVmStorageType OBJECT-TYPE
   SYNTAX     StorageType 
   ACCESS     read-only
   STATUS     mandatory
   DESCRIPTION
     "This variable represents the storage type value for the
      mscVm tables."
::= { mscVmRowStatusEntry 4 }

mscVmIndex OBJECT-TYPE
   SYNTAX     Integer32 (0..15)
   ACCESS     not-accessible
   STATUS     mandatory
   DESCRIPTION
     "This variable represents the index for the mscVm tables."
::= { mscVmRowStatusEntry 10 }


-- Vm/n Interface/n
-- This component represents a logical interface to the VirtualMedia. 
-- The given VirtualMedia instance can have at most one Interface 
-- linked to a ProtocolPort of a given VirtualRouter.

mscVmIf OBJECT IDENTIFIER ::= { mscVm 2 }



mscVmIfRowStatusTable OBJECT-TYPE
   SYNTAX     SEQUENCE OF MscVmIfRowStatusEntry
   ACCESS     not-accessible
   STATUS     mandatory
   DESCRIPTION
     "This entry controls the addition and deletion of 
      mscVmIf components."
::= { mscVmIf 1 }

mscVmIfRowStatusEntry OBJECT-TYPE
   SYNTAX     MscVmIfRowStatusEntry
   ACCESS     not-accessible
   STATUS     mandatory
   DESCRIPTION
     "A single entry in the table represents a single 
      mscVmIf component."
   INDEX {
      mscVmIndex,
      mscVmIfIndex }
::= { mscVmIfRowStatusTable 1 }

MscVmIfRowStatusEntry ::= SEQUENCE {
   mscVmIfRowStatus
      RowStatus,
   mscVmIfComponentName
      DisplayString,
   mscVmIfStorageType
      StorageType,
   mscVmIfIndex
      Integer32 }

mscVmIfRowStatus OBJECT-TYPE
   SYNTAX     RowStatus 
   ACCESS     read-write
   STATUS     mandatory
   DESCRIPTION
     "This variable is used as the basis for SNMP naming of
      mscVmIf components.
      These components can be added and deleted."
::= { mscVmIfRowStatusEntry 1 }

mscVmIfComponentName OBJECT-TYPE
   SYNTAX     DisplayString 
   ACCESS     read-only
   STATUS     mandatory
   DESCRIPTION
     "This variable provides the component's string name for
      use with the ASCII Console Interface"
::= { mscVmIfRowStatusEntry 2 }

mscVmIfStorageType OBJECT-TYPE
   SYNTAX     StorageType 
   ACCESS     read-only
   STATUS     mandatory
   DESCRIPTION
     "This variable represents the storage type value for the
      mscVmIf tables."
::= { mscVmIfRowStatusEntry 4 }

mscVmIfIndex OBJECT-TYPE
   SYNTAX     Integer32 (0..15)
   ACCESS     not-accessible
   STATUS     mandatory
   DESCRIPTION
     "This variable represents the index for the mscVmIf tables."
::= { mscVmIfRowStatusEntry 10 }

mscVmIfMpTable OBJECT-TYPE
   SYNTAX     SEQUENCE OF MscVmIfMpEntry
   ACCESS     not-accessible
   STATUS     mandatory
   DESCRIPTION
     "This group contains the base provisioning data for the media base 
      component."
::= { mscVmIf 10 }

mscVmIfMpEntry OBJECT-TYPE
   SYNTAX     MscVmIfMpEntry
   ACCESS     not-accessible
   STATUS     mandatory
   DESCRIPTION
     "An entry in the mscVmIfMpTable."
   INDEX {
      mscVmIndex,
      mscVmIfIndex }
::= { mscVmIfMpTable 1 }

MscVmIfMpEntry ::= SEQUENCE {
   mscVmIfLinkToProtocolPort
      Link }

mscVmIfLinkToProtocolPort OBJECT-TYPE
   SYNTAX     Link 
   ACCESS     read-write
   STATUS     mandatory
   DESCRIPTION
     "This attribute specifies the ProtocolPort to which this interface is 
      linked to. The protocol port is the logical interface to the network. 
      The protocol port component describes the logical characteristics of 
      this interface."
::= { mscVmIfMpEntry 1 }

mscVmIfCidDataTable OBJECT-TYPE
   SYNTAX     SEQUENCE OF MscVmIfCidDataEntry
   ACCESS     not-accessible
   STATUS     mandatory
   DESCRIPTION
     "This group contains the attribute for a component's Customer 
      Identifier (CID). Refer to the attribute description for a detailed 
      explanation of CIDs."
::= { mscVmIf 11 }

mscVmIfCidDataEntry OBJECT-TYPE
   SYNTAX     MscVmIfCidDataEntry
   ACCESS     not-accessible
   STATUS     mandatory
   DESCRIPTION
     "An entry in the mscVmIfCidDataTable."
   INDEX {
      mscVmIndex,
      mscVmIfIndex }
::= { mscVmIfCidDataTable 1 }

MscVmIfCidDataEntry ::= SEQUENCE {
   mscVmIfCustomerIdentifier
      Unsigned32 }

mscVmIfCustomerIdentifier OBJECT-TYPE
   SYNTAX     Unsigned32 (0 | 1..8191)
   ACCESS     read-write
   STATUS     mandatory
   DESCRIPTION
     "This attribute holds the Customer Identifier (CID).
      
      Every component has a CID. If a component has a cid attribute, the 
      component's CID is the provisioned value of that attribute; 
      otherwise the component inherits the CID of its parent. The top-
      level component has a CID of 0.
      
      Every operator session also has a CID, which is the CID 
      provisioned for the operator's user ID. An operator will see only the 
      stream data for components having a matching CID. Also, the 
      operator will be allowed to issue commands for only those 
      components which have a matching CID.
      
      An operator CID of 0 is used to identify the Network Manager 
      (referred to as 'NetMan' in DPN). This CID matches the CID of 
      any component. Values 1 to 8191 inclusive (equivalent to 'basic 
      CIDs' in DPN) may be assigned to specific customers."
   DEFVAL     { 0 }
::= { mscVmIfCidDataEntry 1 }

mscVmIfIfEntryTable OBJECT-TYPE
   SYNTAX     SEQUENCE OF MscVmIfIfEntryEntry
   ACCESS     not-accessible
   STATUS     mandatory
   DESCRIPTION
     "This group contains the provisionable attributes for the ifEntry."
::= { mscVmIf 12 }

mscVmIfIfEntryEntry OBJECT-TYPE
   SYNTAX     MscVmIfIfEntryEntry
   ACCESS     not-accessible
   STATUS     mandatory
   DESCRIPTION
     "An entry in the mscVmIfIfEntryTable."
   INDEX {
      mscVmIndex,
      mscVmIfIndex }
::= { mscVmIfIfEntryTable 1 }

MscVmIfIfEntryEntry ::= SEQUENCE {
   mscVmIfIfAdminStatus
      INTEGER,
   mscVmIfIfIndex
      InterfaceIndex }

mscVmIfIfAdminStatus OBJECT-TYPE
   SYNTAX     INTEGER  {
                 up(1),
                 down(2),
                 testing(3) }
   ACCESS     read-write
   STATUS     mandatory
   DESCRIPTION
     "The desired state of the interface. The up state indicates the 
      interface is operational. The down state indicates the interface is not 
      operational. The testing state indicates that no operational packets 
      can be passed."
   DEFVAL     { up }
::= { mscVmIfIfEntryEntry 1 }

mscVmIfIfIndex OBJECT-TYPE
   SYNTAX     InterfaceIndex (1..65535)
   ACCESS     read-only
   STATUS     mandatory
   DESCRIPTION
     "This is the index for the IfEntry. Its value is automatically initialized 
      during the provisioning process."
::= { mscVmIfIfEntryEntry 2 }

mscVmIfOperStatusTable OBJECT-TYPE
   SYNTAX     SEQUENCE OF MscVmIfOperStatusEntry
   ACCESS     not-accessible
   STATUS     mandatory
   DESCRIPTION
     "This group includes the Operational Status attribute. This attribute 
      defines the current operational state of this component."
::= { mscVmIf 13 }

mscVmIfOperStatusEntry OBJECT-TYPE
   SYNTAX     MscVmIfOperStatusEntry
   ACCESS     not-accessible
   STATUS     mandatory
   DESCRIPTION
     "An entry in the mscVmIfOperStatusTable."
   INDEX {
      mscVmIndex,
      mscVmIfIndex }
::= { mscVmIfOperStatusTable 1 }

MscVmIfOperStatusEntry ::= SEQUENCE {
   mscVmIfSnmpOperStatus
      INTEGER }

mscVmIfSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { mscVmIfOperStatusEntry 1 }

mscVmIfStateTable OBJECT-TYPE
   SYNTAX     SEQUENCE OF MscVmIfStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscVmIf 14 }

mscVmIfStateEntry OBJECT-TYPE
   SYNTAX     MscVmIfStateEntry
   ACCESS     not-accessible
   STATUS     mandatory
   DESCRIPTION
     "An entry in the mscVmIfStateTable."
   INDEX {
      mscVmIndex,
      mscVmIfIndex }
::= { mscVmIfStateTable 1 }

MscVmIfStateEntry ::= SEQUENCE {
   mscVmIfAdminState
      INTEGER,
   mscVmIfOperationalState
      INTEGER,
   mscVmIfUsageState
      INTEGER }

mscVmIfAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscVmIfStateEntry 1 }

mscVmIfOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscVmIfStateEntry 2 }

mscVmIfUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscVmIfStateEntry 3 }

mscVmIfProvTable OBJECT-TYPE
   SYNTAX     SEQUENCE OF MscVmIfProvEntry
   ACCESS     not-accessible
   STATUS     mandatory
   DESCRIPTION
     "This group contains the provisionable attributes for the If 
      component."
::= { mscVmIf 15 }

mscVmIfProvEntry OBJECT-TYPE
   SYNTAX     MscVmIfProvEntry
   ACCESS     not-accessible
   STATUS     mandatory
   DESCRIPTION
     "An entry in the mscVmIfProvTable."
   INDEX {
      mscVmIndex,
      mscVmIfIndex }
::= { mscVmIfProvTable 1 }

MscVmIfProvEntry ::= SEQUENCE {
   mscVmIfMode
      INTEGER }

mscVmIfMode OBJECT-TYPE
   SYNTAX     INTEGER  {
                 alwaysUpInterface(0),
                 interVrConnection(1) }
   ACCESS     read-write
   STATUS     mandatory
   DESCRIPTION
     "This attribute specifies the mode of operation of the Vm If. Two 
      modes are supported: alwaysUpInterface and interVrConnection.
      
      alwaysUpInterface: This mode limits the Vm If to provide the 
      functionality of an 'always up interface' only. Inter-VR 
      communcation is not possible when this mode is selected. Memory 
      consumption by the Vm If is significantly less on FP when this 
      mode is selected. Hence this mode should be used when the sole 
      purpose of the Vm If is to provide an always up interface for 
      application like BGP4.
      
      interVrConnection: This mode provides the full capability of 
      VirtualMedia, i.e. 'always up interface' and inter-VR 
      communication."
   DEFVAL     { alwaysUpInterface }
::= { mscVmIfProvEntry 1 }




-- 
-- Version and Compliance statements
-- 



-- Object-Group Statement:
-- A list of all current accessible leaf objects.

-- OBJECTS { mscVmIfCustomerIdentifier,
--           mscVmIfIfAdminStatus,
--           mscVmIfMode,
--           mscVmIfSnmpOperStatus,
--           mscVmIfIfIndex,
--           mscVmIfUsageState,
--           mscVmIfOperationalState,
--           mscVmComponentName,
--           mscVmIfAdminState,
--           mscVmIfComponentName,
--           mscVmStorageType,
--           mscVmRowStatus,
--           mscVmIfStorageType,
--           mscVmIfRowStatus,
--           mscVmIfLinkToProtocolPort }
-- STATUS  mandatory
-- DESCRIPTION
--   "A list of all current accessible leaf objects."

virtualMediaGroup OBJECT IDENTIFIER ::= { virtualMediaMIB 1 }
virtualMediaGroupCA OBJECT IDENTIFIER ::= { virtualMediaGroup 1 }
virtualMediaGroupCA02 OBJECT IDENTIFIER ::= { virtualMediaGroupCA 3 }
virtualMediaGroupCA02A OBJECT IDENTIFIER ::= { virtualMediaGroupCA02 2 }



-- Agent-Capabilities Statement:

-- PRODUCT-RELEASE "MscPassport Release 1.2 VirtualMedia."
-- STATUS          mandatory
-- DESCRIPTION     "Carrier Passport VirtualMedia MIB: MIB Version CA02A,
--                  Software Version CA02S9C."
-- SUPPORTS        Nortel-MsCarrier-MscPassport-VirtualMediaMIB
--    INCLUDES     { virtualMediaGroupCA02A }

virtualMediaCapabilities OBJECT IDENTIFIER ::= { virtualMediaMIB 3 }
virtualMediaCapabilitiesCA OBJECT IDENTIFIER ::= { virtualMediaCapabilities 1 }
virtualMediaCapabilitiesCA02 OBJECT IDENTIFIER ::= { virtualMediaCapabilitiesCA 3 }
virtualMediaCapabilitiesCA02A OBJECT IDENTIFIER ::= { virtualMediaCapabilitiesCA02 2 }





END
