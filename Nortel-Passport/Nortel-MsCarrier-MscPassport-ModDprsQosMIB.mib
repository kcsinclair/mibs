Nortel-MsCarrier-MscPassport-ModDprsQosMIB
DEFINITIONS ::= BEGIN



IMPORTS

      OBJECT-TYPE
   FROM RFC-1212

      mscPassportMIBs
   FROM Nortel-MsCarrier-MscPassport-UsefulDefinitionsMIB

      DisplayString,
      StorageType,
      RowStatus,
      Integer32,
      Unsigned32
   FROM Nortel-MsCarrier-MscPassport-StandardTextualConventionsMIB

      NonReplicated
   FROM Nortel-MsCarrier-MscPassport-TextualConventionsMIB

      mscModFrsIndex,
      mscModFrs
   FROM Nortel-MsCarrier-MscPassport-ModCommonMIB

      mscModIndex
   FROM Nortel-MsCarrier-MscPassport-BaseShelfMIB;




-- LAST-UPDATED   "9909010000Z"
-- ORGANIZATION   "Nortel Networks"
-- CONTACT-INFO   "
--         Nortel Carrier Data Network Management
--         
--         Postal:       P.O. Box 3511, Station C 
--                       Ottawa, Ontario 
--                       Canada  K1Y 4H7
--         
--         via the WEB:  http://www.nortelnetworks.com  
--                       select 'Contact Us' from the menu
--          
--         via phone:    1-800-4NORTEL"
-- DESCRIPTION
--    "The module describing the Nortel MsCarrier MscPassport
--     ModDprsQos Enterprise MIB."

modDprsQosMIB OBJECT IDENTIFIER ::= { mscPassportMIBs 76 }










-- Mod Frs DprsNetworking
-- DprsNetworking is used to define a number of general 
-- characteristics for all Frame Relay connections using DPRS 
-- networking. All the modules in the network should have identical 
-- DprsNetworking attributes. If these attributes are not consistent 
-- across the network, then the service may be degraded. 

mscModFrsDprsNet OBJECT IDENTIFIER ::= { mscModFrs 3 }



mscModFrsDprsNetRowStatusTable OBJECT-TYPE
   SYNTAX     SEQUENCE OF MscModFrsDprsNetRowStatusEntry
   ACCESS     not-accessible
   STATUS     mandatory
   DESCRIPTION
     "This entry controls the addition and deletion of 
      mscModFrsDprsNet components."
::= { mscModFrsDprsNet 1 }

mscModFrsDprsNetRowStatusEntry OBJECT-TYPE
   SYNTAX     MscModFrsDprsNetRowStatusEntry
   ACCESS     not-accessible
   STATUS     mandatory
   DESCRIPTION
     "A single entry in the table represents a single 
      mscModFrsDprsNet component."
   INDEX {
      mscModIndex,
      mscModFrsIndex,
      mscModFrsDprsNetIndex }
::= { mscModFrsDprsNetRowStatusTable 1 }

MscModFrsDprsNetRowStatusEntry ::= SEQUENCE {
   mscModFrsDprsNetRowStatus
      RowStatus,
   mscModFrsDprsNetComponentName
      DisplayString,
   mscModFrsDprsNetStorageType
      StorageType,
   mscModFrsDprsNetIndex
      NonReplicated }

mscModFrsDprsNetRowStatus OBJECT-TYPE
   SYNTAX     RowStatus 
   ACCESS     read-only
   STATUS     mandatory
   DESCRIPTION
     "This variable is used as the basis for SNMP naming of
      mscModFrsDprsNet components.
      These components cannot be added nor deleted."
::= { mscModFrsDprsNetRowStatusEntry 1 }

mscModFrsDprsNetComponentName OBJECT-TYPE
   SYNTAX     DisplayString 
   ACCESS     read-only
   STATUS     mandatory
   DESCRIPTION
     "This variable provides the component's string name for
      use with the ASCII Console Interface"
::= { mscModFrsDprsNetRowStatusEntry 2 }

mscModFrsDprsNetStorageType OBJECT-TYPE
   SYNTAX     StorageType 
   ACCESS     read-only
   STATUS     mandatory
   DESCRIPTION
     "This variable represents the storage type value for the
      mscModFrsDprsNet tables."
::= { mscModFrsDprsNetRowStatusEntry 4 }

mscModFrsDprsNetIndex OBJECT-TYPE
   SYNTAX     NonReplicated 
   ACCESS     not-accessible
   STATUS     mandatory
   DESCRIPTION
     "This variable represents the index for the mscModFrsDprsNet tables."
::= { mscModFrsDprsNetRowStatusEntry 10 }


-- Mod Frs DprsNet TransferPriorityMappingDprsNet/n
-- This component represents default transfer priority mappings for 
-- Frame Relay connections using DPRS networking.

mscModFrsDprsNetTpm OBJECT IDENTIFIER ::= { mscModFrsDprsNet 2 }



mscModFrsDprsNetTpmRowStatusTable OBJECT-TYPE
   SYNTAX     SEQUENCE OF MscModFrsDprsNetTpmRowStatusEntry
   ACCESS     not-accessible
   STATUS     mandatory
   DESCRIPTION
     "This entry controls the addition and deletion of 
      mscModFrsDprsNetTpm components."
::= { mscModFrsDprsNetTpm 1 }

mscModFrsDprsNetTpmRowStatusEntry OBJECT-TYPE
   SYNTAX     MscModFrsDprsNetTpmRowStatusEntry
   ACCESS     not-accessible
   STATUS     mandatory
   DESCRIPTION
     "A single entry in the table represents a single 
      mscModFrsDprsNetTpm component."
   INDEX {
      mscModIndex,
      mscModFrsIndex,
      mscModFrsDprsNetIndex,
      mscModFrsDprsNetTpmIndex }
::= { mscModFrsDprsNetTpmRowStatusTable 1 }

MscModFrsDprsNetTpmRowStatusEntry ::= SEQUENCE {
   mscModFrsDprsNetTpmRowStatus
      RowStatus,
   mscModFrsDprsNetTpmComponentName
      DisplayString,
   mscModFrsDprsNetTpmStorageType
      StorageType,
   mscModFrsDprsNetTpmIndex
      Integer32 }

mscModFrsDprsNetTpmRowStatus OBJECT-TYPE
   SYNTAX     RowStatus 
   ACCESS     read-write
   STATUS     mandatory
   DESCRIPTION
     "This variable is used as the basis for SNMP naming of
      mscModFrsDprsNetTpm components.
      These components can be added."
::= { mscModFrsDprsNetTpmRowStatusEntry 1 }

mscModFrsDprsNetTpmComponentName OBJECT-TYPE
   SYNTAX     DisplayString 
   ACCESS     read-only
   STATUS     mandatory
   DESCRIPTION
     "This variable provides the component's string name for
      use with the ASCII Console Interface"
::= { mscModFrsDprsNetTpmRowStatusEntry 2 }

mscModFrsDprsNetTpmStorageType OBJECT-TYPE
   SYNTAX     StorageType 
   ACCESS     read-only
   STATUS     mandatory
   DESCRIPTION
     "This variable represents the storage type value for the
      mscModFrsDprsNetTpm tables."
::= { mscModFrsDprsNetTpmRowStatusEntry 4 }

mscModFrsDprsNetTpmIndex OBJECT-TYPE
   SYNTAX     Integer32 (0..15)
   ACCESS     not-accessible
   STATUS     mandatory
   DESCRIPTION
     "This variable represents the index for the mscModFrsDprsNetTpm tables."
::= { mscModFrsDprsNetTpmRowStatusEntry 10 }

mscModFrsDprsNetTpmProvTable OBJECT-TYPE
   SYNTAX     SEQUENCE OF MscModFrsDprsNetTpmProvEntry
   ACCESS     not-accessible
   STATUS     mandatory
   DESCRIPTION
     "This group specifies the mapping from the defined transfer priority 
      to the egress emission priority and routing class of service.
      The mapping of transfer priority to egress emission priority and  
      routing class of service may be modified by the user. Any changes 
      to transfer priority mappings take effect on new  calls. Existing 
      connections are not affected by changes to transfer priority 
      mappings unless the service is reset by locking and unlocking the 
      connection or resetting the card where the service resides."
::= { mscModFrsDprsNetTpm 10 }

mscModFrsDprsNetTpmProvEntry OBJECT-TYPE
   SYNTAX     MscModFrsDprsNetTpmProvEntry
   ACCESS     not-accessible
   STATUS     mandatory
   DESCRIPTION
     "An entry in the mscModFrsDprsNetTpmProvTable."
   INDEX {
      mscModIndex,
      mscModFrsIndex,
      mscModFrsDprsNetIndex,
      mscModFrsDprsNetTpmIndex }
::= { mscModFrsDprsNetTpmProvTable 1 }

MscModFrsDprsNetTpmProvEntry ::= SEQUENCE {
   mscModFrsDprsNetTpmEmissionPriority
      Unsigned32,
   mscModFrsDprsNetTpmRoutingClassOfService
      INTEGER,
   mscModFrsDprsNetTpmAssignedIngressBandwidthPool
      Unsigned32,
   mscModFrsDprsNetTpmAssignedEgressBandwidthPool
      Unsigned32 }

mscModFrsDprsNetTpmEmissionPriority OBJECT-TYPE
   SYNTAX     Unsigned32 (0..3)
   ACCESS     read-write
   STATUS     mandatory
   DESCRIPTION
     "This attribute specifies the egress emission priority at the Frame 
      Relay interface. A value of 3 specifies the highest priority, whereas 
      a value of 0 specifies the lowest priority."
   DEFVAL     { 0 }
::= { mscModFrsDprsNetTpmProvEntry 1 }

mscModFrsDprsNetTpmRoutingClassOfService OBJECT-TYPE
   SYNTAX     INTEGER  {
                 throughput(0),
                 delay(1),
                 multimedia(2) }
   ACCESS     read-write
   STATUS     mandatory
   DESCRIPTION
     "This attribute specifies the routing class of service value to be used 
      on a transport connection. A value of multimedia specifies the 
      highest class of service and a value of throughput specifies the 
      lowest class of service."
   DEFVAL     { throughput }
::= { mscModFrsDprsNetTpmProvEntry 2 }

mscModFrsDprsNetTpmAssignedIngressBandwidthPool OBJECT-TYPE
   SYNTAX     Unsigned32 (0..15)
   ACCESS     read-write
   STATUS     mandatory
   DESCRIPTION
     "This attribute specifies the bandwidth pool which is used to support 
      this transfer priority at this interface. For FrNni, this pool is defined 
      by provisioning attribute ingressBandwidthPool under the FrNni Ca 
      component. For FrNni, the value of this attribute can be overridden 
      at the interface level by provisioning attribute 
      assignedIngressBandwidthPool under the FrNni Ca Tpm/n 
      component"
   DEFVAL     { 0 }
::= { mscModFrsDprsNetTpmProvEntry 3 }

mscModFrsDprsNetTpmAssignedEgressBandwidthPool OBJECT-TYPE
   SYNTAX     Unsigned32 (0..15)
   ACCESS     read-write
   STATUS     mandatory
   DESCRIPTION
     "This attribute specifies the bandwidth pool which is used to support 
      this transfer priority at this interface. For FrNni, this pool is defined 
      by provisioning attribute egressBandwidthPool under the FrNni Ca 
      component. For FrNni, the value of this attribute can be overridden 
      at the interface level by provisioning attribute 
      assignedEgressBandwidthPool under the FrNni Ca Tpm/n 
      component"
   DEFVAL     { 0 }
::= { mscModFrsDprsNetTpmProvEntry 4 }




-- 
-- Version and Compliance statements
-- 



-- Object-Group Statement:
-- A list of all current accessible leaf objects.

-- OBJECTS { mscModFrsDprsNetStorageType,
--           mscModFrsDprsNetRowStatus,
--           mscModFrsDprsNetTpmRoutingClassOfService,
--           mscModFrsDprsNetTpmEmissionPriority,
--           mscModFrsDprsNetTpmAssignedIngressBandwidthPool,
--           mscModFrsDprsNetTpmAssignedEgressBandwidthPool,
--           mscModFrsDprsNetTpmComponentName,
--           mscModFrsDprsNetComponentName,
--           mscModFrsDprsNetTpmStorageType,
--           mscModFrsDprsNetTpmRowStatus }
-- STATUS  mandatory
-- DESCRIPTION
--   "A list of all current accessible leaf objects."

modDprsQosGroup OBJECT IDENTIFIER ::= { modDprsQosMIB 1 }
modDprsQosGroupCA OBJECT IDENTIFIER ::= { modDprsQosGroup 1 }
modDprsQosGroupCA02 OBJECT IDENTIFIER ::= { modDprsQosGroupCA 3 }
modDprsQosGroupCA02A OBJECT IDENTIFIER ::= { modDprsQosGroupCA02 2 }



-- Agent-Capabilities Statement:

-- PRODUCT-RELEASE "MscPassport Release 1.2 ModDprsQos."
-- STATUS          mandatory
-- DESCRIPTION     "Carrier Passport ModDprsQos MIB: MIB Version CA02A,
--                  Software Version CA02S9C."
-- SUPPORTS        Nortel-MsCarrier-MscPassport-ModDprsQosMIB
--    INCLUDES     { modDprsQosGroupCA02A }

modDprsQosCapabilities OBJECT IDENTIFIER ::= { modDprsQosMIB 3 }
modDprsQosCapabilitiesCA OBJECT IDENTIFIER ::= { modDprsQosCapabilities 1 }
modDprsQosCapabilitiesCA02 OBJECT IDENTIFIER ::= { modDprsQosCapabilitiesCA 3 }
modDprsQosCapabilitiesCA02A OBJECT IDENTIFIER ::= { modDprsQosCapabilitiesCA02 2 }





END
