Nortel-MsCarrier-MscPassport-AtmNetworkingMIB
DEFINITIONS ::= BEGIN



IMPORTS

      OBJECT-TYPE
   FROM RFC-1212

      mscPassportMIBs,
      mscComponents
   FROM Nortel-MsCarrier-MscPassport-UsefulDefinitionsMIB

      Counter32,
      RowPointer,
      DisplayString,
      StorageType,
      RowStatus,
      Gauge32,
      Integer32,
      Unsigned32
   FROM Nortel-MsCarrier-MscPassport-StandardTextualConventionsMIB

      AsciiString,
      NonReplicated,
      HexString,
      FixedPoint1,
      AsciiStringIndex,
      IntegerSequence
   FROM Nortel-MsCarrier-MscPassport-TextualConventionsMIB

      mscAtmIfVptVcc,
      mscAtmIfVccIndex,
      mscAtmIfVptIndex,
      mscAtmIfVcc,
      mscAtmIfVpcIndex,
      mscAtmIfVpc,
      mscAtmIfVptVccIndex,
      mscAtmIfIndex
   FROM Nortel-MsCarrier-MscPassport-AtmCoreMIB;




-- LAST-UPDATED   "9909010000Z"
-- ORGANIZATION   "Nortel Networks"
-- CONTACT-INFO   "
--         Nortel Carrier Data Network Management
--         
--         Postal:       P.O. Box 3511, Station C 
--                       Ottawa, Ontario 
--                       Canada  K1Y 4H7
--         
--         via the WEB:  http://www.nortelnetworks.com  
--                       select 'Contact Us' from the menu
--          
--         via phone:    1-800-4NORTEL"
-- DESCRIPTION
--    "The module describing the Nortel MsCarrier MscPassport
--     AtmNetworking Enterprise MIB."

atmNetworkingMIB OBJECT IDENTIFIER ::= { mscPassportMIBs 42 }










-- AtmRouting
-- This component contains the provisionable and operational 
-- attributes related to ATM PNNI routing. 
-- 
-- The Dna subcomponents can be listed to view all the provisioned 
-- and registered ATM end system addresses and prefixes stored 
-- against any of the Uni, Iisp or Pnni interfaces.
-- 
-- The Pnni subcomponent can be provisioned to identify that this 
-- Passport node participates in a PNNI hierarchy. 
-- 
-- The ConfiguredNode subcomponents are indexed by level in the 
-- PNNI hierarchy (a value between 0 and 104), and define 
-- configuration information.

mscARtg OBJECT IDENTIFIER ::= { mscComponents 95 }



mscARtgRowStatusTable OBJECT-TYPE
   SYNTAX     SEQUENCE OF MscARtgRowStatusEntry
   ACCESS     not-accessible
   STATUS     mandatory
   DESCRIPTION
     "This entry controls the addition and deletion of 
      mscARtg components."
::= { mscARtg 1 }

mscARtgRowStatusEntry OBJECT-TYPE
   SYNTAX     MscARtgRowStatusEntry
   ACCESS     not-accessible
   STATUS     mandatory
   DESCRIPTION
     "A single entry in the table represents a single 
      mscARtg component."
   INDEX {
      mscARtgIndex }
::= { mscARtgRowStatusTable 1 }

MscARtgRowStatusEntry ::= SEQUENCE {
   mscARtgRowStatus
      RowStatus,
   mscARtgComponentName
      DisplayString,
   mscARtgStorageType
      StorageType,
   mscARtgIndex
      NonReplicated }

mscARtgRowStatus OBJECT-TYPE
   SYNTAX     RowStatus 
   ACCESS     read-write
   STATUS     mandatory
   DESCRIPTION
     "This variable is used as the basis for SNMP naming of
      mscARtg components.
      These components can be added and deleted."
::= { mscARtgRowStatusEntry 1 }

mscARtgComponentName OBJECT-TYPE
   SYNTAX     DisplayString 
   ACCESS     read-only
   STATUS     mandatory
   DESCRIPTION
     "This variable provides the component's string name for
      use with the ASCII Console Interface"
::= { mscARtgRowStatusEntry 2 }

mscARtgStorageType OBJECT-TYPE
   SYNTAX     StorageType 
   ACCESS     read-only
   STATUS     mandatory
   DESCRIPTION
     "This variable represents the storage type value for the
      mscARtg tables."
::= { mscARtgRowStatusEntry 4 }

mscARtgIndex OBJECT-TYPE
   SYNTAX     NonReplicated 
   ACCESS     not-accessible
   STATUS     mandatory
   DESCRIPTION
     "This variable represents the index for the mscARtg tables."
::= { mscARtgRowStatusEntry 10 }

mscARtgStatsTable OBJECT-TYPE
   SYNTAX     SEQUENCE OF MscARtgStatsEntry
   ACCESS     not-accessible
   STATUS     mandatory
   DESCRIPTION
     "This group contains the statistical operational attributes of an ARtg 
      component."
::= { mscARtg 10 }

mscARtgStatsEntry OBJECT-TYPE
   SYNTAX     MscARtgStatsEntry
   ACCESS     not-accessible
   STATUS     mandatory
   DESCRIPTION
     "An entry in the mscARtgStatsTable."
   INDEX {
      mscARtgIndex }
::= { mscARtgStatsTable 1 }

MscARtgStatsEntry ::= SEQUENCE {
   mscARtgRoutingAttempts
      Counter32,
   mscARtgFailedRoutingAttempts
      Counter32 }

mscARtgRoutingAttempts OBJECT-TYPE
   SYNTAX     Counter32 
   ACCESS     read-only
   STATUS     mandatory
   DESCRIPTION
     "This attribute counts the total number of calls routed. The counter 
      wraps when it exceeds the maximum value."
::= { mscARtgStatsEntry 1 }

mscARtgFailedRoutingAttempts OBJECT-TYPE
   SYNTAX     Counter32 
   ACCESS     read-only
   STATUS     mandatory
   DESCRIPTION
     "This attribute counts the total number of calls which were not 
      successfully routed.The counter wraps when it exceeds the 
      maximum value."
::= { mscARtgStatsEntry 2 }

-- 
-- *** THIS SUBTREE CURRENTLY NOT IMPLEMENTED ***
-- 

-- ARtg Dna/<ATM address>
-- This component represents an ATM NSAP address that has been 
-- provisioned or dynamically registered through ILMI.

mscARtgDna OBJECT IDENTIFIER ::= { mscARtg 2 }



mscARtgDnaRowStatusTable OBJECT-TYPE
   SYNTAX     SEQUENCE OF MscARtgDnaRowStatusEntry
   ACCESS     not-accessible
   STATUS     mandatory
   DESCRIPTION
     "*** THIS TABLE CURRENTLY NOT IMPLEMENTED ***

      This entry controls the addition and deletion of 
      mscARtgDna components."
::= { mscARtgDna 1 }

mscARtgDnaRowStatusEntry OBJECT-TYPE
   SYNTAX     MscARtgDnaRowStatusEntry
   ACCESS     not-accessible
   STATUS     mandatory
   DESCRIPTION
     "A single entry in the table represents a single 
      mscARtgDna component."
   INDEX {
      mscARtgIndex,
      mscARtgDnaIndex }
::= { mscARtgDnaRowStatusTable 1 }

MscARtgDnaRowStatusEntry ::= SEQUENCE {
   mscARtgDnaRowStatus
      RowStatus,
   mscARtgDnaComponentName
      DisplayString,
   mscARtgDnaStorageType
      StorageType,
   mscARtgDnaIndex
      AsciiStringIndex }

mscARtgDnaRowStatus OBJECT-TYPE
   SYNTAX     RowStatus 
   ACCESS     read-only
   STATUS     mandatory
   DESCRIPTION
     "This variable is used as the basis for SNMP naming of
      mscARtgDna components.
      These components cannot be added nor deleted."
::= { mscARtgDnaRowStatusEntry 1 }

mscARtgDnaComponentName OBJECT-TYPE
   SYNTAX     DisplayString 
   ACCESS     read-only
   STATUS     mandatory
   DESCRIPTION
     "This variable provides the component's string name for
      use with the ASCII Console Interface"
::= { mscARtgDnaRowStatusEntry 2 }

mscARtgDnaStorageType OBJECT-TYPE
   SYNTAX     StorageType 
   ACCESS     read-only
   STATUS     mandatory
   DESCRIPTION
     "This variable represents the storage type value for the
      mscARtgDna tables."
::= { mscARtgDnaRowStatusEntry 4 }

mscARtgDnaIndex OBJECT-TYPE
   SYNTAX     AsciiStringIndex (SIZE (1..40))
   ACCESS     not-accessible
   STATUS     mandatory
   DESCRIPTION
     "This variable represents the index for the mscARtgDna tables."
::= { mscARtgDnaRowStatusEntry 10 }

-- 
-- *** THIS SUBTREE CURRENTLY NOT IMPLEMENTED ***
-- 

-- ARtg Dna/<ATM address> DestInfo/<n>
-- This component represents a destination associated with the parent 
-- Dna.

mscARtgDnaDestInfo OBJECT IDENTIFIER ::= { mscARtgDna 2 }



mscARtgDnaDestInfoRowStatusTable OBJECT-TYPE
   SYNTAX     SEQUENCE OF MscARtgDnaDestInfoRowStatusEntry
   ACCESS     not-accessible
   STATUS     mandatory
   DESCRIPTION
     "*** THIS TABLE CURRENTLY NOT IMPLEMENTED ***

      This entry controls the addition and deletion of 
      mscARtgDnaDestInfo components."
::= { mscARtgDnaDestInfo 1 }

mscARtgDnaDestInfoRowStatusEntry OBJECT-TYPE
   SYNTAX     MscARtgDnaDestInfoRowStatusEntry
   ACCESS     not-accessible
   STATUS     mandatory
   DESCRIPTION
     "A single entry in the table represents a single 
      mscARtgDnaDestInfo component."
   INDEX {
      mscARtgIndex,
      mscARtgDnaIndex,
      mscARtgDnaDestInfoIndex }
::= { mscARtgDnaDestInfoRowStatusTable 1 }

MscARtgDnaDestInfoRowStatusEntry ::= SEQUENCE {
   mscARtgDnaDestInfoRowStatus
      RowStatus,
   mscARtgDnaDestInfoComponentName
      DisplayString,
   mscARtgDnaDestInfoStorageType
      StorageType,
   mscARtgDnaDestInfoIndex
      Integer32 }

mscARtgDnaDestInfoRowStatus OBJECT-TYPE
   SYNTAX     RowStatus 
   ACCESS     read-only
   STATUS     mandatory
   DESCRIPTION
     "This variable is used as the basis for SNMP naming of
      mscARtgDnaDestInfo components.
      These components cannot be added nor deleted."
::= { mscARtgDnaDestInfoRowStatusEntry 1 }

mscARtgDnaDestInfoComponentName OBJECT-TYPE
   SYNTAX     DisplayString 
   ACCESS     read-only
   STATUS     mandatory
   DESCRIPTION
     "This variable provides the component's string name for
      use with the ASCII Console Interface"
::= { mscARtgDnaDestInfoRowStatusEntry 2 }

mscARtgDnaDestInfoStorageType OBJECT-TYPE
   SYNTAX     StorageType 
   ACCESS     read-only
   STATUS     mandatory
   DESCRIPTION
     "This variable represents the storage type value for the
      mscARtgDnaDestInfo tables."
::= { mscARtgDnaDestInfoRowStatusEntry 4 }

mscARtgDnaDestInfoIndex OBJECT-TYPE
   SYNTAX     Integer32 (0..50)
   ACCESS     not-accessible
   STATUS     mandatory
   DESCRIPTION
     "This variable represents the index for the mscARtgDnaDestInfo tables."
::= { mscARtgDnaDestInfoRowStatusEntry 10 }

mscARtgDnaDestInfoOperTable OBJECT-TYPE
   SYNTAX     SEQUENCE OF MscARtgDnaDestInfoOperEntry
   ACCESS     not-accessible
   STATUS     mandatory
   DESCRIPTION
     "*** THIS TABLE CURRENTLY NOT IMPLEMENTED ***

      This group contains the operational attributes for the DestInfo 
      component."
::= { mscARtgDnaDestInfo 10 }

mscARtgDnaDestInfoOperEntry OBJECT-TYPE
   SYNTAX     MscARtgDnaDestInfoOperEntry
   ACCESS     not-accessible
   STATUS     mandatory
   DESCRIPTION
     "An entry in the mscARtgDnaDestInfoOperTable."
   INDEX {
      mscARtgIndex,
      mscARtgDnaIndex,
      mscARtgDnaDestInfoIndex }
::= { mscARtgDnaDestInfoOperTable 1 }

MscARtgDnaDestInfoOperEntry ::= SEQUENCE {
   mscARtgDnaDestInfoType
      INTEGER,
   mscARtgDnaDestInfoScope
      INTEGER,
   mscARtgDnaDestInfoStdComponentName
      RowPointer,
   mscARtgDnaDestInfoReachability
      INTEGER }

mscARtgDnaDestInfoType OBJECT-TYPE
   SYNTAX     INTEGER  {
                 primary(0),
                 alternate(1),
                 registered(2),
                 default(3),
                 ebr(4) }
   ACCESS     read-only
   STATUS     mandatory
   DESCRIPTION
     "This attribute indicates the type of the address at the destination 
      interface. Provisioned addresses are assigned a type of  primary or  
      alternate; ATM routing will try primary routes and then the 
      alternate routes if none of the primary routes succeed. The type 
      registered is used for dynamic addresses registered through ILMI. 
      The type default is  used for Soft PVC addresses. The type ebr 	
      indicates addresses used by Edge Based Rerouting."
::= { mscARtgDnaDestInfoOperEntry 1 }

mscARtgDnaDestInfoScope OBJECT-TYPE
   SYNTAX     INTEGER (-1..104)
   ACCESS     read-only
   STATUS     mandatory
   DESCRIPTION
     "This attribute indicates the highest level (meaning the lowest level 
      number) in the hierarchy that the address will be advertised to.
      
      A value of -1 indicates that the scope is not applicable since this 
      node has not been configured as a PNNI node."
::= { mscARtgDnaDestInfoOperEntry 2 }

mscARtgDnaDestInfoStdComponentName OBJECT-TYPE
   SYNTAX     RowPointer 
   ACCESS     read-only
   STATUS     mandatory
   DESCRIPTION
     "This attribute represents a component name of the interface through 
      which the address can be reached."
::= { mscARtgDnaDestInfoOperEntry 3 }

mscARtgDnaDestInfoReachability OBJECT-TYPE
   SYNTAX     INTEGER  {
                 internal(0),
                 exterior(1) }
   ACCESS     read-only
   STATUS     mandatory
   DESCRIPTION
     "This attribute indicates whether the address is internal or exterior."
::= { mscARtgDnaDestInfoOperEntry 4 }


-- ARtg Pnni
-- This component contains the provisionable and operational 
-- attributes for a PNNI node. Provisioning the Pnni component under 
-- the ARtg component indicates that this switch has PNNI routing 
-- capability. 
-- The Pnni component must have one and only one ConfiguredNode 
-- subcomponent.

mscARtgPnni OBJECT IDENTIFIER ::= { mscARtg 3 }



mscARtgPnniRowStatusTable OBJECT-TYPE
   SYNTAX     SEQUENCE OF MscARtgPnniRowStatusEntry
   ACCESS     not-accessible
   STATUS     mandatory
   DESCRIPTION
     "This entry controls the addition and deletion of 
      mscARtgPnni components."
::= { mscARtgPnni 1 }

mscARtgPnniRowStatusEntry OBJECT-TYPE
   SYNTAX     MscARtgPnniRowStatusEntry
   ACCESS     not-accessible
   STATUS     mandatory
   DESCRIPTION
     "A single entry in the table represents a single 
      mscARtgPnni component."
   INDEX {
      mscARtgIndex,
      mscARtgPnniIndex }
::= { mscARtgPnniRowStatusTable 1 }

MscARtgPnniRowStatusEntry ::= SEQUENCE {
   mscARtgPnniRowStatus
      RowStatus,
   mscARtgPnniComponentName
      DisplayString,
   mscARtgPnniStorageType
      StorageType,
   mscARtgPnniIndex
      NonReplicated }

mscARtgPnniRowStatus OBJECT-TYPE
   SYNTAX     RowStatus 
   ACCESS     read-write
   STATUS     mandatory
   DESCRIPTION
     "This variable is used as the basis for SNMP naming of
      mscARtgPnni components.
      These components can be added and deleted."
::= { mscARtgPnniRowStatusEntry 1 }

mscARtgPnniComponentName OBJECT-TYPE
   SYNTAX     DisplayString 
   ACCESS     read-only
   STATUS     mandatory
   DESCRIPTION
     "This variable provides the component's string name for
      use with the ASCII Console Interface"
::= { mscARtgPnniRowStatusEntry 2 }

mscARtgPnniStorageType OBJECT-TYPE
   SYNTAX     StorageType 
   ACCESS     read-only
   STATUS     mandatory
   DESCRIPTION
     "This variable represents the storage type value for the
      mscARtgPnni tables."
::= { mscARtgPnniRowStatusEntry 4 }

mscARtgPnniIndex OBJECT-TYPE
   SYNTAX     NonReplicated 
   ACCESS     not-accessible
   STATUS     mandatory
   DESCRIPTION
     "This variable represents the index for the mscARtgPnni tables."
::= { mscARtgPnniRowStatusEntry 10 }

mscARtgPnniProvTable OBJECT-TYPE
   SYNTAX     SEQUENCE OF MscARtgPnniProvEntry
   ACCESS     not-accessible
   STATUS     mandatory
   DESCRIPTION
     "This group contains the generic provisionable attributes of a Pnni 
      component."
::= { mscARtgPnni 10 }

mscARtgPnniProvEntry OBJECT-TYPE
   SYNTAX     MscARtgPnniProvEntry
   ACCESS     not-accessible
   STATUS     mandatory
   DESCRIPTION
     "An entry in the mscARtgPnniProvTable."
   INDEX {
      mscARtgIndex,
      mscARtgPnniIndex }
::= { mscARtgPnniProvTable 1 }

MscARtgPnniProvEntry ::= SEQUENCE {
   mscARtgPnniNodeAddressPrefix
      HexString,
   mscARtgPnniDefaultScope
      Unsigned32,
   mscARtgPnniDomain
      AsciiString,
   mscARtgPnniRestrictTransit
      INTEGER,
   mscARtgPnniMaxAlternateRoutesOnCrankback
      Unsigned32 }

mscARtgPnniNodeAddressPrefix OBJECT-TYPE
   SYNTAX     HexString (SIZE (0..19))
   ACCESS     read-write
   STATUS     mandatory
   DESCRIPTION
     "This attribute specifies the ATM address of this node. It allows the 
      default node address to be overridden. If this attribute is set to the 
      null string, then the default node address prefix is assumed, and 
      computed as follows: the value provisioned for the ModuleData 
      component's nodePrefix attribute, followed by a unique MAC 
      address (6 octets)."
::= { mscARtgPnniProvEntry 1 }

mscARtgPnniDefaultScope OBJECT-TYPE
   SYNTAX     Unsigned32 (0..104)
   ACCESS     read-write
   STATUS     mandatory
   DESCRIPTION
     "This attribute specifies the default PNNI scope for ATM addresses 
      associated with this node. The PNNI scope determines the level to 
      which the address will be advertised within the PNNI routing 
      domain. A provisioned Addr component may override the default 
      scope in a PnniInfo subcomponent.
      
      A value of 0 means that all addresses which do not have 
      provisioned scopes will be advertised globally within the PNNI 
      routing domain.
      
      The value specified must be numerically smaller than or equal to 
      that of the lowest level at which this node is configured in the PNNI 
      hierarchy."
   DEFVAL     { 0 }
::= { mscARtgPnniProvEntry 2 }

mscARtgPnniDomain OBJECT-TYPE
   SYNTAX     AsciiString (SIZE (1..32))
   ACCESS     read-write
   STATUS     mandatory
   DESCRIPTION
     "This attribute specifies the routing domain name. This attribute 
      should be set identically for all nodes in the same routing domain."
   DEFVAL     { '31'H }  -- "1"
::= { mscARtgPnniProvEntry 3 }

mscARtgPnniRestrictTransit OBJECT-TYPE
   SYNTAX     INTEGER  {
                 false(0),
                 true(1) }
   ACCESS     read-write
   STATUS     mandatory
   DESCRIPTION
     "This attribute specifies if the node should restrict tandeming of 
      SVCs. 
      
      If this attribute is set to true, then other lowest level nodes in the 
      PNNI hierarchy will avoid traversing this node during route 
      computation."
   DEFVAL     { false }
::= { mscARtgPnniProvEntry 4 }

mscARtgPnniMaxAlternateRoutesOnCrankback OBJECT-TYPE
   SYNTAX     Unsigned32 (0..20)
   ACCESS     read-write
   STATUS     mandatory
   DESCRIPTION
     "This attribute specifies the number of alternate routing attempts 
      before a call requiring crank back is rejected."
   DEFVAL     { 1 }
::= { mscARtgPnniProvEntry 5 }

mscARtgPnniPglParmsTable OBJECT-TYPE
   SYNTAX     SEQUENCE OF MscARtgPnniPglParmsEntry
   ACCESS     not-accessible
   STATUS     mandatory
   DESCRIPTION
     "This group contains the provisionable attributes for the peer group 
      leader election timer parameters of a Pnni component."
::= { mscARtgPnni 11 }

mscARtgPnniPglParmsEntry OBJECT-TYPE
   SYNTAX     MscARtgPnniPglParmsEntry
   ACCESS     not-accessible
   STATUS     mandatory
   DESCRIPTION
     "An entry in the mscARtgPnniPglParmsTable."
   INDEX {
      mscARtgIndex,
      mscARtgPnniIndex }
::= { mscARtgPnniPglParmsTable 1 }

MscARtgPnniPglParmsEntry ::= SEQUENCE {
   mscARtgPnniPglInitTime
      Unsigned32,
   mscARtgPnniOverrideDelay
      Unsigned32,
   mscARtgPnniReElectionInterval
      Unsigned32 }

mscARtgPnniPglInitTime OBJECT-TYPE
   SYNTAX     Unsigned32 (0..65535)
   ACCESS     read-write
   STATUS     mandatory
   DESCRIPTION
     "This attribute specifies how long this node will delay advertising its 
      choice of preferred peer group leader after having initialized 
      operation and reached the full peer state with at least one neighbor 
      in the peer group."
   DEFVAL     { 15 }
::= { mscARtgPnniPglParmsEntry 1 }

mscARtgPnniOverrideDelay OBJECT-TYPE
   SYNTAX     Unsigned32 (1..65535)
   ACCESS     read-write
   STATUS     mandatory
   DESCRIPTION
     "This attribute specifies how long a node will wait for itself to be 
      declared the preferred peer group leader by unanimous agreement 
      among its peers."
   DEFVAL     { 30 }
::= { mscARtgPnniPglParmsEntry 2 }

mscARtgPnniReElectionInterval OBJECT-TYPE
   SYNTAX     Unsigned32 (1..65535)
   ACCESS     read-write
   STATUS     mandatory
   DESCRIPTION
     "This attribute specifies how long this node will wait after losing 
      connectivity to the current peer group leader before re-starting the 
      process of electing a new peer group leader."
   DEFVAL     { 15 }
::= { mscARtgPnniPglParmsEntry 3 }

mscARtgPnniHlParmsTable OBJECT-TYPE
   SYNTAX     SEQUENCE OF MscARtgPnniHlParmsEntry
   ACCESS     not-accessible
   STATUS     mandatory
   DESCRIPTION
     "This group contains the default provisionable Hello protocol 
      parameters."
::= { mscARtgPnni 12 }

mscARtgPnniHlParmsEntry OBJECT-TYPE
   SYNTAX     MscARtgPnniHlParmsEntry
   ACCESS     not-accessible
   STATUS     mandatory
   DESCRIPTION
     "An entry in the mscARtgPnniHlParmsTable."
   INDEX {
      mscARtgIndex,
      mscARtgPnniIndex }
::= { mscARtgPnniHlParmsTable 1 }

MscARtgPnniHlParmsEntry ::= SEQUENCE {
   mscARtgPnniHelloHoldDown
      FixedPoint1,
   mscARtgPnniHelloInterval
      Unsigned32,
   mscARtgPnniHelloInactivityFactor
      Unsigned32 }

mscARtgPnniHelloHoldDown OBJECT-TYPE
   SYNTAX     FixedPoint1 (1..655350)
   ACCESS     read-write
   STATUS     mandatory
   DESCRIPTION
     "This attribute is used to limit the rate at which this node sends out 
      Hello packets. Specifically, it specifies the default minimum amount 
      of time between successive Hellos used by routing control channels 
      on this node."
   DEFVAL     { 10 }
::= { mscARtgPnniHlParmsEntry 1 }

mscARtgPnniHelloInterval OBJECT-TYPE
   SYNTAX     Unsigned32 (1..65535)
   ACCESS     read-write
   STATUS     mandatory
   DESCRIPTION
     "This attribute specifies the default duration of the Hello Timer in 
      seconds for routing control channels on this node. Every 
      helloInterval seconds, this node will send out a Hello packet to the 
      neighbor node, subject to the helloHoldDown timer having expired 
      at least once since the last Hello packet was sent."
   DEFVAL     { 15 }
::= { mscARtgPnniHlParmsEntry 2 }

mscARtgPnniHelloInactivityFactor OBJECT-TYPE
   SYNTAX     Unsigned32 (1..65535)
   ACCESS     read-write
   STATUS     mandatory
   DESCRIPTION
     "This attribute specifies the default number of Hello intervals 
      allowed to pass without receiving a Hello from the neighbor node, 
      before an attempt is made to re-stage, for routing control channels 
      on this node. The hello inactivity timer is enabled in the 
      oneWayInside, twoWayInside, oneWayOutside, twoWayOutside 
      and commonOutside (see the helloState attribute on the Rcc 
      component for a description of these states). Note that the value for 
      the Hello interval used in the calculation is the one specified in the 
      Hello packet from the neighbor node."
   DEFVAL     { 5 }
::= { mscARtgPnniHlParmsEntry 3 }

mscARtgPnniPtseParmsTable OBJECT-TYPE
   SYNTAX     SEQUENCE OF MscARtgPnniPtseParmsEntry
   ACCESS     not-accessible
   STATUS     mandatory
   DESCRIPTION
     "This group contains the provisionable attributes for the PTSE timer 
      values of a Pnni component."
::= { mscARtgPnni 13 }

mscARtgPnniPtseParmsEntry OBJECT-TYPE
   SYNTAX     MscARtgPnniPtseParmsEntry
   ACCESS     not-accessible
   STATUS     mandatory
   DESCRIPTION
     "An entry in the mscARtgPnniPtseParmsTable."
   INDEX {
      mscARtgIndex,
      mscARtgPnniIndex }
::= { mscARtgPnniPtseParmsTable 1 }

MscARtgPnniPtseParmsEntry ::= SEQUENCE {
   mscARtgPnniPtseHoldDown
      FixedPoint1,
   mscARtgPnniPtseRefreshInterval
      Unsigned32,
   mscARtgPnniPtseLifetimeFactor
      Unsigned32,
   mscARtgPnniRequestRxmtInterval
      Unsigned32,
   mscARtgPnniPeerDelayedAckInterval
      FixedPoint1 }

mscARtgPnniPtseHoldDown OBJECT-TYPE
   SYNTAX     FixedPoint1 (1..655350)
   ACCESS     read-write
   STATUS     mandatory
   DESCRIPTION
     "This attribute is used to limit the rate at which this node sends out 
      PTSE packets. Specifically, it specifies the minimum amount of 
      time in seconds that this node must wait between sending 
      successive PTSE packets."
   DEFVAL     { 10 }
::= { mscARtgPnniPtseParmsEntry 1 }

mscARtgPnniPtseRefreshInterval OBJECT-TYPE
   SYNTAX     Unsigned32 (300..65535)
   ACCESS     read-write
   STATUS     mandatory
   DESCRIPTION
     "This attribute specifies the duration of the PTSE Timer. Every 
      ptseRefreshInterval seconds, this node will send out a self-
      originated PTSE packet to the neighbor node, subject to the 
      ptseHoldDown timer having expired at least once since the last 
      PTSE packet was sent."
   DEFVAL     { 1800 }
::= { mscARtgPnniPtseParmsEntry 2 }

mscARtgPnniPtseLifetimeFactor OBJECT-TYPE
   SYNTAX     Unsigned32 (101..1000)
   ACCESS     read-write
   STATUS     mandatory
   DESCRIPTION
     "This attribute specifies the lifetime multiplier. The result of 
      multiplying the ptseRefreshInterval by this value is used as the 
      initial lifetime that this node places into PTSEs."
   DEFVAL     { 200 }
::= { mscARtgPnniPtseParmsEntry 3 }

mscARtgPnniRequestRxmtInterval OBJECT-TYPE
   SYNTAX     Unsigned32 (1..65535)
   ACCESS     read-write
   STATUS     mandatory
   DESCRIPTION
     "This attribute specifies the period between retransmissions of 
      unacknowledged Database Summary packets, PTSE Request 
      packets and PTSPs."
   DEFVAL     { 5 }
::= { mscARtgPnniPtseParmsEntry 4 }

mscARtgPnniPeerDelayedAckInterval OBJECT-TYPE
   SYNTAX     FixedPoint1 (1..655350)
   ACCESS     read-write
   STATUS     mandatory
   DESCRIPTION
     "This attribute specifies the minimum amount of time between 
      transmissions of delayed PTSE acknowledgment packets."
   DEFVAL     { 1 }
::= { mscARtgPnniPtseParmsEntry 5 }

mscARtgPnniThreshParmsTable OBJECT-TYPE
   SYNTAX     SEQUENCE OF MscARtgPnniThreshParmsEntry
   ACCESS     not-accessible
   STATUS     mandatory
   DESCRIPTION
     "This group contains the provisionable attributes for the change 
      thresholds of a ARtg Pnni component."
::= { mscARtgPnni 14 }

mscARtgPnniThreshParmsEntry OBJECT-TYPE
   SYNTAX     MscARtgPnniThreshParmsEntry
   ACCESS     not-accessible
   STATUS     mandatory
   DESCRIPTION
     "An entry in the mscARtgPnniThreshParmsTable."
   INDEX {
      mscARtgIndex,
      mscARtgPnniIndex }
::= { mscARtgPnniThreshParmsTable 1 }

MscARtgPnniThreshParmsEntry ::= SEQUENCE {
   mscARtgPnniAvcrMt
      Unsigned32,
   mscARtgPnniAvcrPm
      Unsigned32 }

mscARtgPnniAvcrMt OBJECT-TYPE
   SYNTAX     Unsigned32 (1..99)
   ACCESS     read-write
   STATUS     mandatory
   DESCRIPTION
     "This attribute when multiplied by the Maximum Cell Rate specifies 
      the minimum threshold used in the algorithms that determine 
      significant change for average cell rate parameters."
   DEFVAL     { 3 }
::= { mscARtgPnniThreshParmsEntry 1 }

mscARtgPnniAvcrPm OBJECT-TYPE
   SYNTAX     Unsigned32 (1..99)
   ACCESS     read-write
   STATUS     mandatory
   DESCRIPTION
     "This attribute when multiplied by the current Available Cell Rate 
      specifies the threshold used in the algorithms that determine 
      significant change for AvCR parameters. If the resulting threshold is 
      lower than minimum threshold, minimum threshold will be used.
      
      Increasing the value of the attribute increases the range of 
      insignificance and reduces the amount of PTSP flooding due to 
      changes in resource availability."
   DEFVAL     { 50 }
::= { mscARtgPnniThreshParmsEntry 2 }

mscARtgPnniOperTable OBJECT-TYPE
   SYNTAX     SEQUENCE OF MscARtgPnniOperEntry
   ACCESS     not-accessible
   STATUS     mandatory
   DESCRIPTION
     "This group contains the generic operational attributes of an ARtg 
      Pnni component."
::= { mscARtgPnni 15 }

mscARtgPnniOperEntry OBJECT-TYPE
   SYNTAX     MscARtgPnniOperEntry
   ACCESS     not-accessible
   STATUS     mandatory
   DESCRIPTION
     "An entry in the mscARtgPnniOperTable."
   INDEX {
      mscARtgIndex,
      mscARtgPnniIndex }
::= { mscARtgPnniOperTable 1 }

MscARtgPnniOperEntry ::= SEQUENCE {
   mscARtgPnniTopologyMemoryExhaustion
      INTEGER }

mscARtgPnniTopologyMemoryExhaustion OBJECT-TYPE
   SYNTAX     INTEGER  {
                 false(0),
                 true(1) }
   ACCESS     read-only
   STATUS     mandatory
   DESCRIPTION
     "This attribute indicates if the topology database is overloaded. 
      A node goes into a database overload state when it fails to store the 
      complete topology database due to insufficient memory in the node. 
      A node in this state performs resynchronization periodically by 
      restarting all its Neighbor Peer Finite State Machines. The node will 
      stay in this state until it synchronizes with all of its neighbors 
      without any overload problems. When this attribute is set an alarm 
      will be issued."
::= { mscARtgPnniOperEntry 2 }

mscARtgPnniStatsTable OBJECT-TYPE
   SYNTAX     SEQUENCE OF MscARtgPnniStatsEntry
   ACCESS     not-accessible
   STATUS     mandatory
   DESCRIPTION
     "This group contains the statistical operational attributes of a ARtg 
      Pnni component."
::= { mscARtgPnni 16 }

mscARtgPnniStatsEntry OBJECT-TYPE
   SYNTAX     MscARtgPnniStatsEntry
   ACCESS     not-accessible
   STATUS     mandatory
   DESCRIPTION
     "An entry in the mscARtgPnniStatsTable."
   INDEX {
      mscARtgIndex,
      mscARtgPnniIndex }
::= { mscARtgPnniStatsTable 1 }

MscARtgPnniStatsEntry ::= SEQUENCE {
   mscARtgPnniSuccessfulRoutingAttempts
      Counter32,
   mscARtgPnniFailedRoutingAttempts
      Counter32,
   mscARtgPnniAlternateRoutingAttempts
      Counter32 }

mscARtgPnniSuccessfulRoutingAttempts OBJECT-TYPE
   SYNTAX     Counter32 
   ACCESS     read-only
   STATUS     mandatory
   DESCRIPTION
     "This attribute counts successful PNNI routing attempts. The counter 
      wraps when it exceeds the maximum value."
::= { mscARtgPnniStatsEntry 1 }

mscARtgPnniFailedRoutingAttempts OBJECT-TYPE
   SYNTAX     Counter32 
   ACCESS     read-only
   STATUS     mandatory
   DESCRIPTION
     "This attribute counts failed PNNI routing attempts. The counter 
      wraps when it exceeds the maximum value."
::= { mscARtgPnniStatsEntry 2 }

mscARtgPnniAlternateRoutingAttempts OBJECT-TYPE
   SYNTAX     Counter32 
   ACCESS     read-only
   STATUS     mandatory
   DESCRIPTION
     "This attribute counts successful PNNI alternate routing attempts. 
      The counter wraps when it exceeds the maximum value."
::= { mscARtgPnniStatsEntry 3 }

mscARtgPnniOptMetricTable OBJECT-TYPE
   SYNTAX     SEQUENCE OF MscARtgPnniOptMetricEntry
   ACCESS     not-accessible
   STATUS     mandatory
   DESCRIPTION
     "This attribute is a vector that specifies the optimization metric for 
      each ATM service category. The optimization metric is used during 
      Generic Connection Admission Control (GCAC) route 
      computation.
      
      Setting the value to cdv for a particular service category will cause 
      GCAC to optimize for cell delay variation on call setups requiring 
      that service category.
      
      Setting the value to maxCtd for a particular service category will 
      cause GCAC to optimize for maximum cell transfer delay on call 
      setups requiring that service category.
      
      Setting the value to aw for a particular service category will cause 
      GCAC to optimize for administrative weight on call setups 
      requiring that service category."
::= { mscARtgPnni 386 }

mscARtgPnniOptMetricEntry OBJECT-TYPE
   SYNTAX     MscARtgPnniOptMetricEntry
   ACCESS     not-accessible
   STATUS     mandatory
   DESCRIPTION
     "An entry in the mscARtgPnniOptMetricTable."
   INDEX {
      mscARtgIndex,
      mscARtgPnniIndex,
      mscARtgPnniOptMetricIndex }
::= { mscARtgPnniOptMetricTable 1 }

MscARtgPnniOptMetricEntry ::= SEQUENCE {
   mscARtgPnniOptMetricIndex
      INTEGER,
   mscARtgPnniOptMetricValue
      INTEGER }

mscARtgPnniOptMetricIndex OBJECT-TYPE
   SYNTAX     INTEGER  {
                 cbr(1),
                 rtVbr(2),
                 nrtVbr(3),
                 ubr(4) }
   ACCESS     not-accessible
   STATUS     mandatory
   DESCRIPTION
     "This variable represents the mscARtgPnniOptMetricTable
      specific index for the mscARtgPnniOptMetricTable."
::= { mscARtgPnniOptMetricEntry 1 }

mscARtgPnniOptMetricValue OBJECT-TYPE
   SYNTAX     INTEGER  {
                 cdv(0),
                 maxCtd(1),
                 aw(2) }
   ACCESS     read-write
   STATUS     mandatory
   DESCRIPTION
     "This variable represents an individual value for the
      mscARtgPnniOptMetricTable."
::= { mscARtgPnniOptMetricEntry 2 }


-- ARtg Pnni RouteFinder
-- This component is used to compute a list of routes to a specified 
-- destination which satisfy certain traffic and routing requirements.
-- 
-- To display a list of computed routes:
-- - set the route computation criteria
-- - issue the Run command

mscARtgPnniRf OBJECT IDENTIFIER ::= { mscARtgPnni 2 }



mscARtgPnniRfRowStatusTable OBJECT-TYPE
   SYNTAX     SEQUENCE OF MscARtgPnniRfRowStatusEntry
   ACCESS     not-accessible
   STATUS     mandatory
   DESCRIPTION
     "This entry controls the addition and deletion of 
      mscARtgPnniRf components."
::= { mscARtgPnniRf 1 }

mscARtgPnniRfRowStatusEntry OBJECT-TYPE
   SYNTAX     MscARtgPnniRfRowStatusEntry
   ACCESS     not-accessible
   STATUS     mandatory
   DESCRIPTION
     "A single entry in the table represents a single 
      mscARtgPnniRf component."
   INDEX {
      mscARtgIndex,
      mscARtgPnniIndex,
      mscARtgPnniRfIndex }
::= { mscARtgPnniRfRowStatusTable 1 }

MscARtgPnniRfRowStatusEntry ::= SEQUENCE {
   mscARtgPnniRfRowStatus
      RowStatus,
   mscARtgPnniRfComponentName
      DisplayString,
   mscARtgPnniRfStorageType
      StorageType,
   mscARtgPnniRfIndex
      NonReplicated }

mscARtgPnniRfRowStatus OBJECT-TYPE
   SYNTAX     RowStatus 
   ACCESS     read-only
   STATUS     mandatory
   DESCRIPTION
     "This variable is used as the basis for SNMP naming of
      mscARtgPnniRf components.
      These components cannot be added nor deleted."
::= { mscARtgPnniRfRowStatusEntry 1 }

mscARtgPnniRfComponentName OBJECT-TYPE
   SYNTAX     DisplayString 
   ACCESS     read-only
   STATUS     mandatory
   DESCRIPTION
     "This variable provides the component's string name for
      use with the ASCII Console Interface"
::= { mscARtgPnniRfRowStatusEntry 2 }

mscARtgPnniRfStorageType OBJECT-TYPE
   SYNTAX     StorageType 
   ACCESS     read-only
   STATUS     mandatory
   DESCRIPTION
     "This variable represents the storage type value for the
      mscARtgPnniRf tables."
::= { mscARtgPnniRfRowStatusEntry 4 }

mscARtgPnniRfIndex OBJECT-TYPE
   SYNTAX     NonReplicated 
   ACCESS     not-accessible
   STATUS     mandatory
   DESCRIPTION
     "This variable represents the index for the mscARtgPnniRf tables."
::= { mscARtgPnniRfRowStatusEntry 10 }

mscARtgPnniRfCriteriaTable OBJECT-TYPE
   SYNTAX     SEQUENCE OF MscARtgPnniRfCriteriaEntry
   ACCESS     not-accessible
   STATUS     mandatory
   DESCRIPTION
     "This group contains the attributes specifying the routing criteria for 
      the route computation."
::= { mscARtgPnniRf 10 }

mscARtgPnniRfCriteriaEntry OBJECT-TYPE
   SYNTAX     MscARtgPnniRfCriteriaEntry
   ACCESS     not-accessible
   STATUS     mandatory
   DESCRIPTION
     "An entry in the mscARtgPnniRfCriteriaTable."
   INDEX {
      mscARtgIndex,
      mscARtgPnniIndex,
      mscARtgPnniRfIndex }
::= { mscARtgPnniRfCriteriaTable 1 }

MscARtgPnniRfCriteriaEntry ::= SEQUENCE {
   mscARtgPnniRfDestinationAddress
      HexString,
   mscARtgPnniRfMaxRoutes
      Unsigned32,
   mscARtgPnniRfTxTrafficDescType
      INTEGER,
   mscARtgPnniRfRxTrafficDescType
      INTEGER,
   mscARtgPnniRfAtmServiceCategory
      INTEGER,
   mscARtgPnniRfFwdQosClass
      INTEGER,
   mscARtgPnniRfBwdQosClass
      INTEGER,
   mscARtgPnniRfBearerClassBbc
      INTEGER,
   mscARtgPnniRfTransferCapabilityBbc
      INTEGER,
   mscARtgPnniRfClippingBbc
      INTEGER,
   mscARtgPnniRfBestEffort
      INTEGER,
   mscARtgPnniRfOptimizationMetric
      INTEGER }

mscARtgPnniRfDestinationAddress OBJECT-TYPE
   SYNTAX     HexString (SIZE (1..20))
   ACCESS     read-write
   STATUS     mandatory
   DESCRIPTION
     "This attribute specifies the destination NSAP address to be used for 
      the computation. If this attribute specifies an invalid address then no 
      routes will be found."
::= { mscARtgPnniRfCriteriaEntry 1 }

mscARtgPnniRfMaxRoutes OBJECT-TYPE
   SYNTAX     Unsigned32 (1..15)
   ACCESS     read-write
   STATUS     mandatory
   DESCRIPTION
     "This attribute specifies a ceiling on the number of routes to be 
      computed."
   DEFVAL     { 1 }
::= { mscARtgPnniRfCriteriaEntry 2 }

mscARtgPnniRfTxTrafficDescType OBJECT-TYPE
   SYNTAX     INTEGER  {
                 n1(1),
                 n2(2),
                 n3(3),
                 n4(4),
                 n5(5),
                 n6(6),
                 n7(7),
                 n8(8) }
   ACCESS     read-write
   STATUS     mandatory
   DESCRIPTION
     "This attribute specifies the type of traffic management which is 
      applied to the transmit direction as defined in the ATM Forum. The 
      txTrafficDescType determines the number and meaning of the 
      parameters in the txTrafficDescParm attribute."
   DEFVAL     { n1 }
::= { mscARtgPnniRfCriteriaEntry 3 }

mscARtgPnniRfRxTrafficDescType OBJECT-TYPE
   SYNTAX     INTEGER  {
                 n1(1),
                 n2(2),
                 n3(3),
                 n4(4),
                 n5(5),
                 n6(6),
                 n7(7),
                 n8(8),
                 sameAsTx(15) }
   ACCESS     read-write
   STATUS     mandatory
   DESCRIPTION
     "This attribute specifies the type of traffic management which is 
      applied to the receive direction of this connection as defined in the 
      ATM Forum. The rxTrafficDescType determines the number and 
      meaning of the parameters in the rxTrafficDescParm attribute
      
      When sameAsTx is selected, the rxTrafficDescType as well as the 
      rxTrafficDescParm are taken from the transmit values."
   DEFVAL     { sameAsTx }
::= { mscARtgPnniRfCriteriaEntry 5 }

mscARtgPnniRfAtmServiceCategory OBJECT-TYPE
   SYNTAX     INTEGER  {
                 unspecifiedBitRate(0),
                 constantBitRate(1),
                 rtVariableBitRate(2),
                 nrtVariableBitRate(3),
                 derivedFromBBC(15) }
   ACCESS     read-write
   STATUS     mandatory
   DESCRIPTION
     "This attribute specifies the ATM service category for both directions 
      of the connection. 
      
      If this attribute is set to derivedFromBBC, the Broadband Bearer 
      Capability (BBC) and bestEffort attributes are used to determine the 
      atmServiceCategory of this connection. 
      
      If this attribute is set to other than derivedFromBBC, the value of 
      this attribute is used to override the provisioned BBC IE parameters. 
      In those cases, the BBC attributes are not used. 
      
      The constantBitRate service category is intended for real time 
      applications, that is those requiring tightly constrained delay and 
      delay variation, as would be appropriate for voice and video 
      applications. The consistent availability of a fixed quantity of 
      bandwidth is considered appropriate for CBR service. Cells which 
      are delayed beyond the value specified by CellTransfer Delay are 
      assumed to be of significantly reduce value to the application.
      
      The rtVariableBitRate service category is intended for real time 
      applications, that is those requiring tightly constrained delay and 
      delay variation, as would be appropriate for voice and video 
      applications. Sources are expected to transmit at a rate which varies 
      with time. Equivalently, the source can be described as 'bursty'. 
      Cells which are delayed beyond the value specified by CTD are 
      assumed to be of significantly reduced value to the application. 
      VBR real time service may support statistical multiplexing of real 
      time sources.
      
      The nrtVariableBitRate service category is intended for non-real 
      time applications which have bursty traffic characteristics and which 
      can be characterized in terms of a PCR, SCR, and MBS. For those 
      cells which are transferred within the traffic contract, the application 
      expects a low cell loss ratio. For all connections, it expects a bound 
      on the mean cell transfer delay. VBR non-real time service may 
      support statistical multiplexing of connections.
      
      The unspecifiedBitRate service is intended for non-real time 
      applications; that is, those not requiring tightly constrained delay 
      and delay variation. UBR sources are expected to be bursty. UBR 
      service supports a high degree of statistical multiplexing among 
      sources. UBR service does not specify traffic related service 
      guarantees. No numerical commitments are made with respect to 
      the cell loss ratio experienced by a UBR connection, or as to the 
      cell transfer delay experienced by cells on the connection."
   DEFVAL     { unspecifiedBitRate }
::= { mscARtgPnniRfCriteriaEntry 6 }

mscARtgPnniRfFwdQosClass OBJECT-TYPE
   SYNTAX     INTEGER  {
                 n0(0),
                 n1(1),
                 n2(2),
                 n3(3),
                 n4(4) }
   ACCESS     read-write
   STATUS     mandatory
   DESCRIPTION
     "This attribute specifies the quality of service for the forward 
      direction for this connection. 
      
      Class 1 supports a QOS that will meet Service Class A performance 
      requirements (Circuit emulation, constant bit rate video).
      
      Class 2 supports a QOS that will meet Service Class B performance 
      requirements (Variable bit rate audio and video).
      
      Class 3 supports a QOS that will meet Service Class C performance 
      requirements (Connection-Oriented Data Transfer).
      
      Class 4 supports a QOS that will meet Service Class D performance 
      requirements (Connectionless Data Transfer).
      
      Class 0 is the unspecified bit rate QOS class; no objective is 
      specified for the performance parameters."
   DEFVAL     { n0 }
::= { mscARtgPnniRfCriteriaEntry 10 }

mscARtgPnniRfBwdQosClass OBJECT-TYPE
   SYNTAX     INTEGER  {
                 n0(0),
                 n1(1),
                 n2(2),
                 n3(3),
                 n4(4),
                 sameAsFwd(15) }
   ACCESS     read-write
   STATUS     mandatory
   DESCRIPTION
     "This attribute specifies the quality of service for the backward 
      direction for this connection.
      
      Class 1 supports a QOS that will meet Service Class A performance 
      requirements (Circuit emulation, constant bit rate video).
      
      Class 2 supports a QOS that will meet Service Class B performance 
      requirements (Variable bit rate audio and video).
      
      Class 3 supports a QOS that will meet Service Class C performance 
      requirements (Connection-Oriented Data Transfer).
      
      Class 4 supports a QOS that will meet Service Class D performance 
      requirements (Connectionless Data Transfer).
      
      Class 0 is the unspecified bit rate QOS class; no objective is 
      specified for the performance parameters.
      
      The sameAsFwd selection sets the backward quality of service to 
      be the same as the forward quality of service."
   DEFVAL     { sameAsFwd }
::= { mscARtgPnniRfCriteriaEntry 11 }

mscARtgPnniRfBearerClassBbc OBJECT-TYPE
   SYNTAX     INTEGER  {
                 a(1),
                 c(3),
                 x(16),
                 derivedFromServiceCategory(31) }
   ACCESS     read-write
   STATUS     mandatory
   DESCRIPTION
     "This attribute specifies the bearer capability. It is one of the 
      Broadband Bearer Capability (BBC) attributes. The purpose of the 
      BBC information element is to indicate a requested broadband 
      connection-oriented bearer service to be provided by the network.
      
      The value derivedFromServiceCategory specifies that the actual 
      value which is used for this connection is derived from the value of 
      the atmServiceCategory. Either, this attribute must be set to 
      derivedFromServiceCategory, or the atmServiceCategory attribute 
      must be set to derivedFromBBC, but not both.
      
      Class a service is a connection-oriented, constant bit rate ATM 
      transport service. Class a service has end to end timing 
      requirements and may require stringent cell loss, cell delay and cell 
      delay variation performance.When a is set, the user is requesting 
      more than an ATM only service. The network may look at the AAL 
      to provide interworking based upon its contents. 
      
      Class c service is a connection-oriented, variable bit rate ATM 
      transport service. Class c service has no end-to-end timing 
      requirements. When c is set, the user is requesting more than an 
      ATM only service. The network interworking function may look at 
      the AAL and provide service based on it.
      
      Class x service is a connection-oriented ATM transport service 
      where the AAL, trafficType (vbr or cbr) and timing requirements 
      are user defined (that is, transparent to the network).When x is set 
      the user is requesting an ATM only service from the network. In this 
      case, the network shall not process any higher layer protocol."
   DEFVAL     { derivedFromServiceCategory }
::= { mscARtgPnniRfCriteriaEntry 12 }

mscARtgPnniRfTransferCapabilityBbc OBJECT-TYPE
   SYNTAX     INTEGER  {
                 n0(0),
                 n1(1),
                 n2(2),
                 n5(5),
                 n8(8),
                 n9(9),
                 n10(10),
                 notApplicable(30),
                 derivedFromServiceCategory(31) }
   ACCESS     read-write
   STATUS     mandatory
   DESCRIPTION
     "This attribute specifies the transfer capability for this connection. 
      Uni 3.0/3.1 traffic type and end-to-end timing parameters are 
      mapped into this parameter as follows:
      <transferCapability : TrafficType, Timing>
      0 : NoIndication, NoIndication
      1 : NoIndication, yes
      2 : NoIndication, no
      5 : CBR, yes
      8 : VBR, NoIndication
      9 : VBR, yes
      10: VBR, no
      
      NotApplicable specifies that the user does not want to specify the 
      transfer capability.
      
      The CBR traffic type refers to traffic offered on services such as a 
      constant bit rate video service or a circuit emulation.
      
      The VBR traffic type refers to traffic offered on services such as 
      packetized audio and video, or data.
      
      The value NoIndication for traffic type is used if the user has not set 
      the traffic type; this is also the case for end-to-end timing.
      
      The value yes for end-to-end timing indicates that end-to-end 
      timing is required.
      
      The value no for end-to-end timing indicates that end-to-end timing 
      is not required.
      
      The value derivedFromServiceCategory specifies that the actual 
      value which is used for this connection is derived from the value of 
      the atmServiceCategory. Either, this attribute must be set to 
      derivedFromServiceCategory, or the atmServiceCategory attribute 
      must be set to derivedFromBBC, but not both."
   DEFVAL     { derivedFromServiceCategory }
::= { mscARtgPnniRfCriteriaEntry 13 }

mscARtgPnniRfClippingBbc OBJECT-TYPE
   SYNTAX     INTEGER  {
                 no(0),
                 yes(1) }
   ACCESS     read-write
   STATUS     mandatory
   DESCRIPTION
     "This attribute specifies the value for the clipping susceptibility 
      parameter in the BBC IE. This attribute is only used for SPVC 
      connections. It is one of the Broadband Bearer Capability attributes.
      
      Clipping is an impairment in which the first fraction of a second of 
      information to be transferred is lost. It occurs after a call is 
      answered and before an associated connection is switched through."
   DEFVAL     { no }
::= { mscARtgPnniRfCriteriaEntry 14 }

mscARtgPnniRfBestEffort OBJECT-TYPE
   SYNTAX     INTEGER  {
                 indicated(0),
                 notIndicated(1),
                 derivedFromServiceCategory(15) }
   ACCESS     read-write
   STATUS     mandatory
   DESCRIPTION
     "This attribute specifies the value of the best effort parameter in the 
      ATM Traffic Descriptor IE. It is one of the Broadband Bearer 
      Capability attributes.
      
      The value indicated implies that the quality of service for this 
      connection is not guaranteed.
      
      The value notIndicated implies that the quality of service for this 
      connection is guaranteed.
      
      The value derivedFromServiceCategory specifies that the actual 
      value which is used for this connection is derived from the value of 
      the atmServiceCategory. Either, this attribute must be set to 
      derivedFromServiceCategory, or the atmServiceCategory attribute 
      must be set to derivedFromBBC, but not both.
      DESCRIPTION"
   DEFVAL     { derivedFromServiceCategory }
::= { mscARtgPnniRfCriteriaEntry 15 }

mscARtgPnniRfOptimizationMetric OBJECT-TYPE
   SYNTAX     INTEGER  {
                 cdv(0),
                 maxCtd(1),
                 aw(2) }
   ACCESS     read-write
   STATUS     mandatory
   DESCRIPTION
     "This attribute specifies the optimization metric to be used in the 
      route computation; one of cell delay variation (cdv), maximum cell 
      transfer delay (maxCtd), or administrative weight (aw)."
   DEFVAL     { aw }
::= { mscARtgPnniRfCriteriaEntry 16 }

mscARtgPnniRfRxTdpTable OBJECT-TYPE
   SYNTAX     SEQUENCE OF MscARtgPnniRfRxTdpEntry
   ACCESS     not-accessible
   STATUS     mandatory
   DESCRIPTION
     "This attribute is a vector of four traffic parameters whose meanings 
      are defined by the rxTrafficDescType attribute. The values of peak 
      cell rate (PCR) and sustained cell rate (SCR) are expressed in 
      cell/s. Maximum burst size (MBS) is expressed in cells. The value 
      of CDVT is expressed in microseconds. The values of PCR, SCR, 
      MBS and CDVT are used for usage parameter control (UPC).
      
      When rxTrafficDescType is 1 or 2, all of the parameters must be set 
      to zero (unused).
      
      When rxTrafficDescType is 3, parameter 1 represents the PCR for 
      CLP equal to 0 and 1 traffic. Parameter 1 must be non-zero. 
      Parameters 2 and 3 must be set to zero (unused).
      
      When rxTrafficDescType is 4, parameter 1 represents the PCR for 
      CLP equal to 0 and 1 traffic; parameter 2 represents the PCR for 
      CLP equal to 0 traffic with cell discard. Parameters 1 and 2 must be 
      non-zero. Parameter 3 must be set to zero (unused). Parameter 1 
      must be greater than or equal to parameter 2.
      
      When rxTrafficDescType is 5, parameter 1 represents the PCR for 
      CLP equal to 0 and 1 traffic; parameter 2 represents the PCR for 
      CLP equal to 0 traffic with cell tagging. Parameters 1 and 2 must be 
      non-zero. Parameter 3 must be set to zero (unused). Parameter 1 
      must be greater than or equal to parameter 2.
      
      When rxTrafficDescType is a 6, parameter 1 represents the PCR for 
      CLP equal to 0 and 1 traffic; parameter 2 represents the SCR for 
      CLP equal to 0 and 1 traffic; parameter 3 represents the MBS for 
      CLP equal to 0 and 1 traffic. Parameters 1, 2 and 3 must be non-
      zero. Parameter 1 must be greater than or equal to Parameter 2. 
      
      When rxTrafficDescType is 7, parameter 1 represents the PCR for 
      CLP equal to 0 and 1 traffic; parameter 2 represents the SCR for 
      CLP equal to 0 traffic with cell discard; parameter 3 represents the 
      MBS for CLP equal to 0 traffic. Parameters 1, 2 and 3 must be non-
      zero. Parameter 1 must be greater than or equal to parameter 2. 
      
      When rxTrafficDescType is 8, parameter 1 represents the PCR for 
      CLP equal to 0 and 1 traffic; parameter 2 represents the SCR for 
      CLP equal to 0 traffic with cell tagging; parameter 3 represents the 
      MBS for CLP equal to 0 traffic. Parameter 1, 2 and 3 must be non-
      zero. Parameter 1 must be greater than or equal to parameter 2.
      
      When rxTrafficDescType is any value from 3 through 8, parameter 
      4 represents the CDVT. If this value is zero, the CDVT is taken 
      from the ConnectionAdministrator defaults for the particular 
      atmServiceCategory of this connection.
      
      When rxTrafficDescriptorType is 3 through 8, there are certain 
      extreme combinations of rxTrafficDescParm which are outside the 
      capabilities of the UPC hardware. 
      
      To calculate the limits, use the following formulae:
      I1 = 1 000 000 000 / PCR
      L1 = CDVT * 1000
      I2 = 1 000 000 000 / SCR
      L2 = CDVT + (MBS - 1) * (I2 - I1)
      I1 and I2 must be less than or equal to 335 523 840. I1 + L1 must 
      be less than or equal to 1 342 156 800. I2 + L2 must be less than or 
      equal to 1 342 156 800. Note that I2 and L2 only apply when the 
      rxTrafficDescriptorType is 6 through 8.
      
      If the values of I1, L1, I2 or L2 are closer to the limits described 
      above, a further restriction applies. Specifically, if either:
      I1 > 41 940 480 or
      I2 > 41 940 480 or
      I1 + L1 > 167 769 600 or
      I2 + L2 > 167 769 600
      then both I1 and I2 must be greater than 20 480. 
      
      Parameter 5 of the rxTrafficDescParm is always unused. 
      
      If the rxTrafficDescType is sameAsTx, the values in this attribute 
      will be taken from the txTrafficDescParm."
::= { mscARtgPnniRf 388 }

mscARtgPnniRfRxTdpEntry OBJECT-TYPE
   SYNTAX     MscARtgPnniRfRxTdpEntry
   ACCESS     not-accessible
   STATUS     mandatory
   DESCRIPTION
     "An entry in the mscARtgPnniRfRxTdpTable."
   INDEX {
      mscARtgIndex,
      mscARtgPnniIndex,
      mscARtgPnniRfIndex,
      mscARtgPnniRfRxTdpIndex }
::= { mscARtgPnniRfRxTdpTable 1 }

MscARtgPnniRfRxTdpEntry ::= SEQUENCE {
   mscARtgPnniRfRxTdpIndex
      Integer32,
   mscARtgPnniRfRxTdpValue
      Unsigned32 }

mscARtgPnniRfRxTdpIndex OBJECT-TYPE
   SYNTAX     Integer32 (1..5)
   ACCESS     not-accessible
   STATUS     mandatory
   DESCRIPTION
     "This variable represents the mscARtgPnniRfRxTdpTable
      specific index for the mscARtgPnniRfRxTdpTable."
::= { mscARtgPnniRfRxTdpEntry 1 }

mscARtgPnniRfRxTdpValue OBJECT-TYPE
   SYNTAX     Unsigned32 (0..2147483647)
   ACCESS     read-write
   STATUS     mandatory
   DESCRIPTION
     "This variable represents an individual value for the
      mscARtgPnniRfRxTdpTable."
::= { mscARtgPnniRfRxTdpEntry 2 }

mscARtgPnniRfTxTdpTable OBJECT-TYPE
   SYNTAX     SEQUENCE OF MscARtgPnniRfTxTdpEntry
   ACCESS     not-accessible
   STATUS     mandatory
   DESCRIPTION
     "This attribute is a vector of five traffic parameters whose meanings 
      are defined by the txTrafficDescType attribute. The values of peak 
      cell rate (PCR), sustained cell rate (SCR) and requested shaping rate 
      are expressed in cell/s. Maximum burst size (MBS) is expressed in 
      cells. CDVT is expressed in microseconds. The values of PCR, 
      SCR, MBS and CDVT are used for connection admission control 
      (CAC). The value of CDVT is only used for connections where the 
      atmServiceCategory is constantBitRate. For all other values of 
      atmServiceCategory, CDVT is ignored. The values of PCR, SCR 
      and requested shaping rate are used to determine the actual shaping 
      rate where traffic shaping is enabled.
      
      When txTrafficDescType is 1 or 2, all of the parameters must be set 
      to zero.
      
      When txTrafficDescType is 3, parameter 1 represents the PCR for 
      CLP equal to 0 and 1 traffic; parameter 4 represents the CDVT; and 
      parameter 5 represents the requested shaping rate. A non-zero value 
      in parameter 5 overrides any value in parameter 1. This result is 
      used as the PCR. Parameter 1 must be non-zero. Parameters 2 and 3 
      must be zero.
      
      When txTrafficDescType is 4, parameter 1 represents the PCR for 
      CLP equal to 0 and 1 traffic with cell discard; parameter 2 
      represents the PCR for CLP equal to 0 traffic; parameter 4 
      represents the CDVT; and parameter 5 represents the requested 
      shaping rate. A non-zero value in parameter 5 overrides any value in 
      parameter 1. This result is used as the PCR. Parameter 1 must be 
      greater than or equal to parameter 2. Parameters 1 and 2 must be 
      non-zero. Parameter 3 must be zero.
      
      When txTrafficDescType is 5, parameter 1 represents the PCR for 
      CLP equal to 0 and 1 traffic with cell tagging; parameter 2 
      represents the PCR for CLP equal to 0 traffic; parameter 4 
      represents the CDVT; and parameter 5 represents the requested 
      shaping rate. A non-zero value in parameter 5 overrides any value in 
      parameter 1. This result is used as the PCR. Parameter 1 must be 
      greater than or equal to parameter 2. Parameters 1 and 2 must be 
      non-zero. Parameter 3 must be zero.
      
      When txTrafficDescType is 6, parameter 1 represents the PCR for 
      CLP equal to 0 and 1 traffic; parameter 2 represents the SCR for 
      CLP equal to 0 and 1 traffic; parameter 3 represents the MBS for 
      CLP equal to 0 and 1 traffic; parameter 4 represents the CDVT; and 
      parameter 5 represents the requested shaping rate. A non-zero value 
      in parameter 5 overrides any value in parameter 1. This result is 
      used as the PCR. Parameters 1, 2 and 3 must be non-zero. 
      Parameter 1 must be greater than or equal to parameter 2. Parameter 
      5, must either be zero (unused) or greater than or equal to parameter 
      2.
      
      When txTrafficDescType is 7, parameter 1 represents the PCR for 
      CLP equal to 0 and 1 traffic; parameter 2 represents the SCR for 
      CLP equal to 0 with cell discard; parameter 3 represents the MBS 
      for CLP equal to 0 traffic; parameter 4 represents the CDVT; and 
      parameter 5 represents the requested shaping rate. A non-zero value 
      in parameter 5 overrides any value in parameter 1. This result is 
      used as the PCR. Parameters 1, 2 and 3 must be non-zero. 
      Parameter 1 must be greater than or equal to parameter 2. Parameter 
      5, must either be zero (unused) or greater than or equal to parameter 
      2.
      
      When txTrafficDescType is 8, parameter 1 represents the PCR for 
      CLP equal to 0 and 1 traffic; parameter 2 represents the SCR for 
      CLP equal to 0 traffic with cell tagging; parameter 3 represents the 
      MBS for CLP equal to 0 traffic; parameter 4 represents the CDVT; 
      and parameter 5 represents the requested shaping rate. A non-zero 
      value in parameter 5 overrides any value in parameter 1. This result 
      is used as the PCR. Parameters 1, 2 and 3 must be non-zero. 
      Parameter 1 must be greater than or equal to parameter 2. Parameter 
      5, must either be zero (unused) or greater than or equal to parameter 
      2.
      
      Whenever it is valid for PCR to be specified, parameter 5 may also 
      be used to specify a requested shaping rate. A non-zero value in 
      parameter 5 overrides the value in parameter 1 and is used as the 
      peak cell rate in calculations of CAC and shaping rate.
      
      For txTrafficDescType 3, 4 and 5, the transmit traffic will be shaped 
      at the next rate less than the PCR. 
      
      For txTrafficDescType 6, 7 and 8, the transmit traffic will be shaped 
      at the highest available rate which is between PCR and SCR. 
      However, if there is no available shaping rate between PCR and 
      SCR, traffic will be shaped at the next rate above the PCR."
::= { mscARtgPnniRf 389 }

mscARtgPnniRfTxTdpEntry OBJECT-TYPE
   SYNTAX     MscARtgPnniRfTxTdpEntry
   ACCESS     not-accessible
   STATUS     mandatory
   DESCRIPTION
     "An entry in the mscARtgPnniRfTxTdpTable."
   INDEX {
      mscARtgIndex,
      mscARtgPnniIndex,
      mscARtgPnniRfIndex,
      mscARtgPnniRfTxTdpIndex }
::= { mscARtgPnniRfTxTdpTable 1 }

MscARtgPnniRfTxTdpEntry ::= SEQUENCE {
   mscARtgPnniRfTxTdpIndex
      Integer32,
   mscARtgPnniRfTxTdpValue
      Unsigned32 }

mscARtgPnniRfTxTdpIndex OBJECT-TYPE
   SYNTAX     Integer32 (1..5)
   ACCESS     not-accessible
   STATUS     mandatory
   DESCRIPTION
     "This variable represents the mscARtgPnniRfTxTdpTable
      specific index for the mscARtgPnniRfTxTdpTable."
::= { mscARtgPnniRfTxTdpEntry 1 }

mscARtgPnniRfTxTdpValue OBJECT-TYPE
   SYNTAX     Unsigned32 (0..2147483647)
   ACCESS     read-write
   STATUS     mandatory
   DESCRIPTION
     "This variable represents an individual value for the
      mscARtgPnniRfTxTdpTable."
::= { mscARtgPnniRfTxTdpEntry 2 }

mscARtgPnniRfFqpTable OBJECT-TYPE
   SYNTAX     SEQUENCE OF MscARtgPnniRfFqpEntry
   ACCESS     not-accessible
   STATUS     mandatory
   DESCRIPTION
     "This attribute is a vector of three elements that specify the quality of 
      service parameters for the forward direction for this connection. 
      This attribute is used for SPVC connections.
      
      The cdv element specifies the acceptable peak-to-peak Cell Delay 
      Variation (CDV) of real-time connections (CBR, and rt-VBR). It is 
      signalled through the extended QoS information element.
      
      The ctd specifies the acceptable maximum Cell Transfer Delay 
      (maxCtd) of real-time connections (CBR, and rt-VBR). 
      It is signalled through the end to end transit delay information 
      element.
      
      The clr specifies the acceptable Cell Loss Ratio (CLR) of CBR, rt-
      VBR, and nrt-VBR connections. It is signalled through the extended 
      QoS information element."
::= { mscARtgPnniRf 390 }

mscARtgPnniRfFqpEntry OBJECT-TYPE
   SYNTAX     MscARtgPnniRfFqpEntry
   ACCESS     not-accessible
   STATUS     mandatory
   DESCRIPTION
     "An entry in the mscARtgPnniRfFqpTable."
   INDEX {
      mscARtgIndex,
      mscARtgPnniIndex,
      mscARtgPnniRfIndex,
      mscARtgPnniRfFqpIndex }
::= { mscARtgPnniRfFqpTable 1 }

MscARtgPnniRfFqpEntry ::= SEQUENCE {
   mscARtgPnniRfFqpIndex
      INTEGER,
   mscARtgPnniRfFqpValue
      Unsigned32 }

mscARtgPnniRfFqpIndex OBJECT-TYPE
   SYNTAX     INTEGER  {
                 cdv(0),
                 ctd(1),
                 clr(2) }
   ACCESS     not-accessible
   STATUS     mandatory
   DESCRIPTION
     "This variable represents the mscARtgPnniRfFqpTable
      specific index for the mscARtgPnniRfFqpTable."
::= { mscARtgPnniRfFqpEntry 1 }

mscARtgPnniRfFqpValue OBJECT-TYPE
   SYNTAX     Unsigned32 (0..2147483647)
   ACCESS     read-write
   STATUS     mandatory
   DESCRIPTION
     "This variable represents an individual value for the
      mscARtgPnniRfFqpTable."
::= { mscARtgPnniRfFqpEntry 2 }

mscARtgPnniRfBqpTable OBJECT-TYPE
   SYNTAX     SEQUENCE OF MscARtgPnniRfBqpEntry
   ACCESS     not-accessible
   STATUS     mandatory
   DESCRIPTION
     "This attribute is a vector of three elements that specify the quality of 
      service parameters for the backward direction for this connection. 
      This attribute is used for SPVC connections.
      
      The cdv element specifies the acceptable peak-to-peak Cell Delay 
      Variation (CDV) of real-time connections (CBR, and rt-VBR). 
      
      It is signalled through the extended QoS information element.
      
      The ctd specifies the acceptable maximum Cell Transfer Delay 
      (maxCtd) of real-time connections (CBR, and rt-VBR). It is 
      signalled through the end to end transit delay information element.
      
      The clr specifies the acceptable Cell Loss Ratio (CLR) of CBR, rt-
      VBR, and nrt-VBR connections. It is signalled through the extended 
      QoS information element."
::= { mscARtgPnniRf 393 }

mscARtgPnniRfBqpEntry OBJECT-TYPE
   SYNTAX     MscARtgPnniRfBqpEntry
   ACCESS     not-accessible
   STATUS     mandatory
   DESCRIPTION
     "An entry in the mscARtgPnniRfBqpTable."
   INDEX {
      mscARtgIndex,
      mscARtgPnniIndex,
      mscARtgPnniRfIndex,
      mscARtgPnniRfBqpIndex }
::= { mscARtgPnniRfBqpTable 1 }

MscARtgPnniRfBqpEntry ::= SEQUENCE {
   mscARtgPnniRfBqpIndex
      INTEGER,
   mscARtgPnniRfBqpValue
      Unsigned32 }

mscARtgPnniRfBqpIndex OBJECT-TYPE
   SYNTAX     INTEGER  {
                 cdv(0),
                 ctd(1),
                 clr(2) }
   ACCESS     not-accessible
   STATUS     mandatory
   DESCRIPTION
     "This variable represents the mscARtgPnniRfBqpTable
      specific index for the mscARtgPnniRfBqpTable."
::= { mscARtgPnniRfBqpEntry 1 }

mscARtgPnniRfBqpValue OBJECT-TYPE
   SYNTAX     Unsigned32 (0..2147483647)
   ACCESS     read-write
   STATUS     mandatory
   DESCRIPTION
     "This variable represents an individual value for the
      mscARtgPnniRfBqpTable."
::= { mscARtgPnniRfBqpEntry 2 }


-- ARtg Pnni ConfiguredNode/<level>
-- This component represents the participation of this node at one level 
-- in the PNNI hierarchy.

mscARtgPnniCfgNode OBJECT IDENTIFIER ::= { mscARtgPnni 3 }



mscARtgPnniCfgNodeRowStatusTable OBJECT-TYPE
   SYNTAX     SEQUENCE OF MscARtgPnniCfgNodeRowStatusEntry
   ACCESS     not-accessible
   STATUS     mandatory
   DESCRIPTION
     "This entry controls the addition and deletion of 
      mscARtgPnniCfgNode components."
::= { mscARtgPnniCfgNode 1 }

mscARtgPnniCfgNodeRowStatusEntry OBJECT-TYPE
   SYNTAX     MscARtgPnniCfgNodeRowStatusEntry
   ACCESS     not-accessible
   STATUS     mandatory
   DESCRIPTION
     "A single entry in the table represents a single 
      mscARtgPnniCfgNode component."
   INDEX {
      mscARtgIndex,
      mscARtgPnniIndex,
      mscARtgPnniCfgNodeIndex }
::= { mscARtgPnniCfgNodeRowStatusTable 1 }

MscARtgPnniCfgNodeRowStatusEntry ::= SEQUENCE {
   mscARtgPnniCfgNodeRowStatus
      RowStatus,
   mscARtgPnniCfgNodeComponentName
      DisplayString,
   mscARtgPnniCfgNodeStorageType
      StorageType,
   mscARtgPnniCfgNodeIndex
      Integer32 }

mscARtgPnniCfgNodeRowStatus OBJECT-TYPE
   SYNTAX     RowStatus 
   ACCESS     read-write
   STATUS     mandatory
   DESCRIPTION
     "This variable is used as the basis for SNMP naming of
      mscARtgPnniCfgNode components.
      These components can be added and deleted."
::= { mscARtgPnniCfgNodeRowStatusEntry 1 }

mscARtgPnniCfgNodeComponentName OBJECT-TYPE
   SYNTAX     DisplayString 
   ACCESS     read-only
   STATUS     mandatory
   DESCRIPTION
     "This variable provides the component's string name for
      use with the ASCII Console Interface"
::= { mscARtgPnniCfgNodeRowStatusEntry 2 }

mscARtgPnniCfgNodeStorageType OBJECT-TYPE
   SYNTAX     StorageType 
   ACCESS     read-only
   STATUS     mandatory
   DESCRIPTION
     "This variable represents the storage type value for the
      mscARtgPnniCfgNode tables."
::= { mscARtgPnniCfgNodeRowStatusEntry 4 }

mscARtgPnniCfgNodeIndex OBJECT-TYPE
   SYNTAX     Integer32 (0..104)
   ACCESS     not-accessible
   STATUS     mandatory
   DESCRIPTION
     "This variable represents the index for the mscARtgPnniCfgNode tables."
::= { mscARtgPnniCfgNodeRowStatusEntry 10 }

mscARtgPnniCfgNodeProvTable OBJECT-TYPE
   SYNTAX     SEQUENCE OF MscARtgPnniCfgNodeProvEntry
   ACCESS     not-accessible
   STATUS     mandatory
   DESCRIPTION
     "This group contains the provisionable attributes of a 
      ConfiguredNode component."
::= { mscARtgPnniCfgNode 10 }

mscARtgPnniCfgNodeProvEntry OBJECT-TYPE
   SYNTAX     MscARtgPnniCfgNodeProvEntry
   ACCESS     not-accessible
   STATUS     mandatory
   DESCRIPTION
     "An entry in the mscARtgPnniCfgNodeProvTable."
   INDEX {
      mscARtgIndex,
      mscARtgPnniIndex,
      mscARtgPnniCfgNodeIndex }
::= { mscARtgPnniCfgNodeProvTable 1 }

MscARtgPnniCfgNodeProvEntry ::= SEQUENCE {
   mscARtgPnniCfgNodeNodeId
      HexString,
   mscARtgPnniCfgNodePeerGroupId
      HexString }

mscARtgPnniCfgNodeNodeId OBJECT-TYPE
   SYNTAX     HexString (SIZE (0..22))
   ACCESS     read-write
   STATUS     mandatory
   DESCRIPTION
     "This attribute specifies the node id of the configured node. If this 
      attribute is set to null, then the node id is computed as follows:
      
      If this is the lowest configured node, then the node id is computed 
      as the level (one octet), followed by the integer value 160 (one 
      octet), followed by the node address (20 octets).
      
      If this is not the lowest configured node, then the node id is 
      computed as the level (one octet), followed by the 14 octet peer 
      group id of the child peer group which the LGN represents, 
      followed by the ESI specified in the node address (6 octets), 
      followed by the integer value 0 (one octet)."
::= { mscARtgPnniCfgNodeProvEntry 2 }

mscARtgPnniCfgNodePeerGroupId OBJECT-TYPE
   SYNTAX     HexString (SIZE (0..14))
   ACCESS     read-write
   STATUS     mandatory
   DESCRIPTION
     "This attribute allows the peer group id of the Logical Group Node 
      (LGN) to be set. The peer group id is specified by 28 hex digits 
      where the first octet represents the level of the node and the 
      remaining 13 octets form the End System Address. If this attribute 
      is set to the null string then the peer group id is computed as 
      follows:
      
      The peer group id for a lowest level node is computed to be the 
      node's level (one octet), followed by the first <level> bits of the 
      node's address, followed by zero or more padding 0 bits.
      
      The peer group id for an LGN is computed to be the LGN's level 
      (one octet), followed by the first <level> bits of the id of the peer 
      group which this LGN represents."
::= { mscARtgPnniCfgNodeProvEntry 3 }

mscARtgPnniCfgNodeOperTable OBJECT-TYPE
   SYNTAX     SEQUENCE OF MscARtgPnniCfgNodeOperEntry
   ACCESS     not-accessible
   STATUS     mandatory
   DESCRIPTION
     "This group contains the generic operational attributes of a 
      ConfiguredNode component."
::= { mscARtgPnniCfgNode 11 }

mscARtgPnniCfgNodeOperEntry OBJECT-TYPE
   SYNTAX     MscARtgPnniCfgNodeOperEntry
   ACCESS     not-accessible
   STATUS     mandatory
   DESCRIPTION
     "An entry in the mscARtgPnniCfgNodeOperTable."
   INDEX {
      mscARtgIndex,
      mscARtgPnniIndex,
      mscARtgPnniCfgNodeIndex }
::= { mscARtgPnniCfgNodeOperTable 1 }

MscARtgPnniCfgNodeOperEntry ::= SEQUENCE {
   mscARtgPnniCfgNodeNodeAddress
      HexString,
   mscARtgPnniCfgNodeOpNodeId
      HexString,
   mscARtgPnniCfgNodeOpPeerGroupId
      HexString,
   mscARtgPnniCfgNodeNumNeighbors
      Unsigned32,
   mscARtgPnniCfgNodeNumRccs
      Unsigned32,
   mscARtgPnniCfgNodeCurrentLeadershipPriority
      Unsigned32,
   mscARtgPnniCfgNodePglElectionState
      INTEGER }

mscARtgPnniCfgNodeNodeAddress OBJECT-TYPE
   SYNTAX     HexString (SIZE (20))
   ACCESS     read-only
   STATUS     mandatory
   DESCRIPTION
     "This attribute indicates the address of the node at this level.
      
      At the lowest level, the nodeAddress is determined by the value of 
      the nodeAddressPrefix attribute for the ARtg Pnni component 
      followed by the level of this CfgNode.
      
      For LGNs, the nodeAddress is the same as the nodeAddress of the 
      node at the lowest level, with the selector field set to the level of the 
      peer group containing the LGN."
::= { mscARtgPnniCfgNodeOperEntry 1 }

mscARtgPnniCfgNodeOpNodeId OBJECT-TYPE
   SYNTAX     HexString (SIZE (22))
   ACCESS     read-only
   STATUS     mandatory
   DESCRIPTION
     "This attribute indicates the node id of the node at this level. The 
      default node id is computed as follows:
      
      If this is the lowest level node, then the default node id is computed 
      as the level (one octet), followed by the integer value 160 (one 
      octet), followed by the node address (20 octets).
      
      If this is not the lowest level node, then the default node id is 
      computed as the level (one octet), followed by the 14 octet peer 
      group id of the child peer group which the LGN represents, 
      followed by the ESI specified in the node address (6 octets), 
      followed by the integer value 0 (one octet)."
::= { mscARtgPnniCfgNodeOperEntry 2 }

mscARtgPnniCfgNodeOpPeerGroupId OBJECT-TYPE
   SYNTAX     HexString (SIZE (14))
   ACCESS     read-only
   STATUS     mandatory
   DESCRIPTION
     "This attribute indicates the peer group id of the node at this level. 
      The value is determined by the provisioned peerGroupId attribute."
::= { mscARtgPnniCfgNodeOperEntry 3 }

mscARtgPnniCfgNodeNumNeighbors OBJECT-TYPE
   SYNTAX     Unsigned32 (0..65535)
   ACCESS     read-only
   STATUS     mandatory
   DESCRIPTION
     "This attribute indicates the number of PNNI nodes which are 
      neighbors of this node at this level."
::= { mscARtgPnniCfgNodeOperEntry 4 }

mscARtgPnniCfgNodeNumRccs OBJECT-TYPE
   SYNTAX     Unsigned32 (0..65535)
   ACCESS     read-only
   STATUS     mandatory
   DESCRIPTION
     "This attribute indicates the number of Routing Control Channels to 
      this node's neighbors at this level."
::= { mscARtgPnniCfgNodeOperEntry 5 }

mscARtgPnniCfgNodeCurrentLeadershipPriority OBJECT-TYPE
   SYNTAX     Unsigned32 (0..205)
   ACCESS     read-only
   STATUS     mandatory
   DESCRIPTION
     "This attribute indicates the leadership priority of the node that this 
      node believes should be the peer group leader at this point in time."
::= { mscARtgPnniCfgNodeOperEntry 6 }

mscARtgPnniCfgNodePglElectionState OBJECT-TYPE
   SYNTAX     INTEGER  {
                 starting(0),
                 awaiting(1),
                 awaitingFull(2),
                 initialDelay(3),
                 calculating(4),
                 operNotPgl(5),
                 operPgl(6),
                 awaitUnanimity(7),
                 hungElection(8),
                 awaitReElection(9) }
   ACCESS     read-only
   STATUS     mandatory
   DESCRIPTION
     "This attribute indicates the current state of the peer group leader 
      election process. The following are the possible values for this 
      attribute:
      
      starting: the initial state of the state machine.
      
      awaiting: the node has started the Hello Finite State Machine on at 
      least one link, and no peer has been found yet.
      
      awaitingFull: no database synchronization process has been 
      completed yet but at least one neighboring peer has been found.
      
      initialDelay: Database synchronization has been completed with at 
      least one neighboring peer. The node must wait pglInitTime second 
      before it can select and advertise its preferred Peer Group Leader 
      (PGL).
      
      calculating: the node is in the process of calculating what its new 
      choice for preferred PGL will be.
      
      operNotPgl: a non PGL node is in the process of determining which 
      node has the highest priority to be PGL by examining PTSEs sent 
      by other nodes.
      
      operPgl: a PGL node is in the process of determining if another 
      node has a higher priority than itself by examining PTSEs sent by 
      other nodes.
      
      awaitUnanimity: the node has chosen itself as PGL. If the node has 
      been elected unanimously, it generates a Unanimity event. It waits 
      for unanimity or expiration of the overrideDelay timer before 
      declaring itself peer group leader.
      
      hungElection: the node has chosen itself as PGL with less than 2/3 
      of the other nodes advertising it as their preferred PGL. In this case 
      either this node should change its choice of preferred PGL, or the 
      other nodes are going to accept it as PGL.
      
      awaitReElection: the node has lost connectivity to the current PGL. 
      The connectivity must be reestablished before the 
      reElectionInterval timer fires, otherwise the election is redone."
::= { mscARtgPnniCfgNodeOperEntry 7 }


-- ARtg Pnni CfgNode/<level> SummaryAddress/<address>, 
-- <prefixLength>, <reachability>
-- A summary address is an abbreviation of a set of addresses, 
-- represented by an address prefix that all of the summarized 
-- addresses have in common.
-- A suppressed summary address is used to suppress the 
-- advertisement of addresses which match this prefix, regardless of 
-- scope.
-- 
-- The prefixLength specifies the number of prefix bits of the address 
-- and reachability specifies whether the address is to summarize 
-- internal or exterior addresses.
-- 
-- An internal address is an address of a destination that is directly 
-- attached to the logical node. An exterior address is an address of a 
-- destination that is located outside of the PNNI routing domain but 
-- can be reached through a port attached to the logical node.

mscARtgPnniCfgNodeSAddr OBJECT IDENTIFIER ::= { mscARtgPnniCfgNode 2 }



mscARtgPnniCfgNodeSAddrRowStatusTable OBJECT-TYPE
   SYNTAX     SEQUENCE OF MscARtgPnniCfgNodeSAddrRowStatusEntry
   ACCESS     not-accessible
   STATUS     mandatory
   DESCRIPTION
     "This entry controls the addition and deletion of 
      mscARtgPnniCfgNodeSAddr components."
::= { mscARtgPnniCfgNodeSAddr 1 }

mscARtgPnniCfgNodeSAddrRowStatusEntry OBJECT-TYPE
   SYNTAX     MscARtgPnniCfgNodeSAddrRowStatusEntry
   ACCESS     not-accessible
   STATUS     mandatory
   DESCRIPTION
     "A single entry in the table represents a single 
      mscARtgPnniCfgNodeSAddr component."
   INDEX {
      mscARtgIndex,
      mscARtgPnniIndex,
      mscARtgPnniCfgNodeIndex,
      mscARtgPnniCfgNodeSAddrAddressIndex,
      mscARtgPnniCfgNodeSAddrPrefixLengthIndex,
      mscARtgPnniCfgNodeSAddrReachabilityIndex }
::= { mscARtgPnniCfgNodeSAddrRowStatusTable 1 }

MscARtgPnniCfgNodeSAddrRowStatusEntry ::= SEQUENCE {
   mscARtgPnniCfgNodeSAddrRowStatus
      RowStatus,
   mscARtgPnniCfgNodeSAddrComponentName
      DisplayString,
   mscARtgPnniCfgNodeSAddrStorageType
      StorageType,
   mscARtgPnniCfgNodeSAddrAddressIndex
      HexString,
   mscARtgPnniCfgNodeSAddrPrefixLengthIndex
      Integer32,
   mscARtgPnniCfgNodeSAddrReachabilityIndex
      INTEGER }

mscARtgPnniCfgNodeSAddrRowStatus OBJECT-TYPE
   SYNTAX     RowStatus 
   ACCESS     read-write
   STATUS     mandatory
   DESCRIPTION
     "This variable is used as the basis for SNMP naming of
      mscARtgPnniCfgNodeSAddr components.
      These components can be added and deleted."
::= { mscARtgPnniCfgNodeSAddrRowStatusEntry 1 }

mscARtgPnniCfgNodeSAddrComponentName OBJECT-TYPE
   SYNTAX     DisplayString 
   ACCESS     read-only
   STATUS     mandatory
   DESCRIPTION
     "This variable provides the component's string name for
      use with the ASCII Console Interface"
::= { mscARtgPnniCfgNodeSAddrRowStatusEntry 2 }

mscARtgPnniCfgNodeSAddrStorageType OBJECT-TYPE
   SYNTAX     StorageType 
   ACCESS     read-only
   STATUS     mandatory
   DESCRIPTION
     "This variable represents the storage type value for the
      mscARtgPnniCfgNodeSAddr tables."
::= { mscARtgPnniCfgNodeSAddrRowStatusEntry 4 }

mscARtgPnniCfgNodeSAddrAddressIndex OBJECT-TYPE
   SYNTAX     HexString (SIZE (19))
   ACCESS     not-accessible
   STATUS     mandatory
   DESCRIPTION
     "This variable represents an index for the mscARtgPnniCfgNodeSAddr tables."
::= { mscARtgPnniCfgNodeSAddrRowStatusEntry 10 }

mscARtgPnniCfgNodeSAddrPrefixLengthIndex OBJECT-TYPE
   SYNTAX     Integer32 (1..152)
   ACCESS     not-accessible
   STATUS     mandatory
   DESCRIPTION
     "This variable represents an index for the mscARtgPnniCfgNodeSAddr tables."
::= { mscARtgPnniCfgNodeSAddrRowStatusEntry 11 }

mscARtgPnniCfgNodeSAddrReachabilityIndex OBJECT-TYPE
   SYNTAX     INTEGER  {
                 internal(0),
                 exterior(1) }
   ACCESS     not-accessible
   STATUS     mandatory
   DESCRIPTION
     "This variable represents an index for the mscARtgPnniCfgNodeSAddr tables."
::= { mscARtgPnniCfgNodeSAddrRowStatusEntry 12 }

mscARtgPnniCfgNodeSAddrProvTable OBJECT-TYPE
   SYNTAX     SEQUENCE OF MscARtgPnniCfgNodeSAddrProvEntry
   ACCESS     not-accessible
   STATUS     mandatory
   DESCRIPTION
     "This group contains the provisionable attributes of a 
      SummaryAddress component. 
      
      A summary address is an abbreviation of a set of addresses, 
      represented by an address prefix that all of the summarized 
      addresses have in common.
      A suppressed summary address is used to suppress the 
      advertisement of addresses which match this prefix, regardless of 
      scope."
::= { mscARtgPnniCfgNodeSAddr 10 }

mscARtgPnniCfgNodeSAddrProvEntry OBJECT-TYPE
   SYNTAX     MscARtgPnniCfgNodeSAddrProvEntry
   ACCESS     not-accessible
   STATUS     mandatory
   DESCRIPTION
     "An entry in the mscARtgPnniCfgNodeSAddrProvTable."
   INDEX {
      mscARtgIndex,
      mscARtgPnniIndex,
      mscARtgPnniCfgNodeIndex,
      mscARtgPnniCfgNodeSAddrAddressIndex,
      mscARtgPnniCfgNodeSAddrPrefixLengthIndex,
      mscARtgPnniCfgNodeSAddrReachabilityIndex }
::= { mscARtgPnniCfgNodeSAddrProvTable 1 }

MscARtgPnniCfgNodeSAddrProvEntry ::= SEQUENCE {
   mscARtgPnniCfgNodeSAddrSuppress
      INTEGER }

mscARtgPnniCfgNodeSAddrSuppress OBJECT-TYPE
   SYNTAX     INTEGER  {
                 false(0),
                 true(1) }
   ACCESS     read-write
   STATUS     mandatory
   DESCRIPTION
     "This attribute specifies whether or not the address should be 
      suppressed. If this attribute is set to true, then all addresses 
      matching that prefix will not be advertised above this level."
   DEFVAL     { false }
::= { mscARtgPnniCfgNodeSAddrProvEntry 2 }

mscARtgPnniCfgNodeSAddrOperTable OBJECT-TYPE
   SYNTAX     SEQUENCE OF MscARtgPnniCfgNodeSAddrOperEntry
   ACCESS     not-accessible
   STATUS     mandatory
   DESCRIPTION
     "This group contains the operational attributes of a SummaryAddress 
      component."
::= { mscARtgPnniCfgNodeSAddr 11 }

mscARtgPnniCfgNodeSAddrOperEntry OBJECT-TYPE
   SYNTAX     MscARtgPnniCfgNodeSAddrOperEntry
   ACCESS     not-accessible
   STATUS     mandatory
   DESCRIPTION
     "An entry in the mscARtgPnniCfgNodeSAddrOperTable."
   INDEX {
      mscARtgIndex,
      mscARtgPnniIndex,
      mscARtgPnniCfgNodeIndex,
      mscARtgPnniCfgNodeSAddrAddressIndex,
      mscARtgPnniCfgNodeSAddrPrefixLengthIndex,
      mscARtgPnniCfgNodeSAddrReachabilityIndex }
::= { mscARtgPnniCfgNodeSAddrOperTable 1 }

MscARtgPnniCfgNodeSAddrOperEntry ::= SEQUENCE {
   mscARtgPnniCfgNodeSAddrState
      INTEGER,
   mscARtgPnniCfgNodeSAddrScope
      INTEGER }

mscARtgPnniCfgNodeSAddrState OBJECT-TYPE
   SYNTAX     INTEGER  {
                 advertising(0),
                 suppressing(1),
                 inactive(2) }
   ACCESS     read-only
   STATUS     mandatory
   DESCRIPTION
     "This attribute indicates the state of the address: one of advertising, 
      suppressing or inactive.
      inactive: the summary address has been configured but is not 
      suppressing or summarizing any ATM addresses. 
      suppressing: the summary address has suppressed at least one ATM 
      address on the node.
      advertising: the summary address is summarizing at least one ATM 
      address on the node."
::= { mscARtgPnniCfgNodeSAddrOperEntry 1 }

mscARtgPnniCfgNodeSAddrScope OBJECT-TYPE
   SYNTAX     INTEGER (-1..104)
   ACCESS     read-only
   STATUS     mandatory
   DESCRIPTION
     "This attribute indicates the scope of the summary address. The 
      scope corresponds to the scope of the underlying summarized 
      address with the highest advertised scope. A value of -1 means the 
      scope is unknown."
::= { mscARtgPnniCfgNodeSAddrOperEntry 2 }

-- 
-- *** THIS SUBTREE CURRENTLY NOT IMPLEMENTED ***
-- 

-- ARtg Pnni CfgNode/n Neighbor/<node id>
-- This component represents the operational attributes for a neighbor 
-- node at this level. 

mscARtgPnniCfgNodeNbr OBJECT IDENTIFIER ::= { mscARtgPnniCfgNode 3 }



mscARtgPnniCfgNodeNbrRowStatusTable OBJECT-TYPE
   SYNTAX     SEQUENCE OF MscARtgPnniCfgNodeNbrRowStatusEntry
   ACCESS     not-accessible
   STATUS     mandatory
   DESCRIPTION
     "*** THIS TABLE CURRENTLY NOT IMPLEMENTED ***

      This entry controls the addition and deletion of 
      mscARtgPnniCfgNodeNbr components."
::= { mscARtgPnniCfgNodeNbr 1 }

mscARtgPnniCfgNodeNbrRowStatusEntry OBJECT-TYPE
   SYNTAX     MscARtgPnniCfgNodeNbrRowStatusEntry
   ACCESS     not-accessible
   STATUS     mandatory
   DESCRIPTION
     "A single entry in the table represents a single 
      mscARtgPnniCfgNodeNbr component."
   INDEX {
      mscARtgIndex,
      mscARtgPnniIndex,
      mscARtgPnniCfgNodeIndex,
      mscARtgPnniCfgNodeNbrIndex }
::= { mscARtgPnniCfgNodeNbrRowStatusTable 1 }

MscARtgPnniCfgNodeNbrRowStatusEntry ::= SEQUENCE {
   mscARtgPnniCfgNodeNbrRowStatus
      RowStatus,
   mscARtgPnniCfgNodeNbrComponentName
      DisplayString,
   mscARtgPnniCfgNodeNbrStorageType
      StorageType,
   mscARtgPnniCfgNodeNbrIndex
      HexString }

mscARtgPnniCfgNodeNbrRowStatus OBJECT-TYPE
   SYNTAX     RowStatus 
   ACCESS     read-only
   STATUS     mandatory
   DESCRIPTION
     "This variable is used as the basis for SNMP naming of
      mscARtgPnniCfgNodeNbr components.
      These components cannot be added nor deleted."
::= { mscARtgPnniCfgNodeNbrRowStatusEntry 1 }

mscARtgPnniCfgNodeNbrComponentName OBJECT-TYPE
   SYNTAX     DisplayString 
   ACCESS     read-only
   STATUS     mandatory
   DESCRIPTION
     "This variable provides the component's string name for
      use with the ASCII Console Interface"
::= { mscARtgPnniCfgNodeNbrRowStatusEntry 2 }

mscARtgPnniCfgNodeNbrStorageType OBJECT-TYPE
   SYNTAX     StorageType 
   ACCESS     read-only
   STATUS     mandatory
   DESCRIPTION
     "This variable represents the storage type value for the
      mscARtgPnniCfgNodeNbr tables."
::= { mscARtgPnniCfgNodeNbrRowStatusEntry 4 }

mscARtgPnniCfgNodeNbrIndex OBJECT-TYPE
   SYNTAX     HexString (SIZE (22))
   ACCESS     not-accessible
   STATUS     mandatory
   DESCRIPTION
     "This variable represents the index for the mscARtgPnniCfgNodeNbr tables."
::= { mscARtgPnniCfgNodeNbrRowStatusEntry 10 }

mscARtgPnniCfgNodeNbrOperTable OBJECT-TYPE
   SYNTAX     SEQUENCE OF MscARtgPnniCfgNodeNbrOperEntry
   ACCESS     not-accessible
   STATUS     mandatory
   DESCRIPTION
     "*** THIS TABLE CURRENTLY NOT IMPLEMENTED ***

      This group contains the operational attributes of a Neighbor 
      component."
::= { mscARtgPnniCfgNodeNbr 10 }

mscARtgPnniCfgNodeNbrOperEntry OBJECT-TYPE
   SYNTAX     MscARtgPnniCfgNodeNbrOperEntry
   ACCESS     not-accessible
   STATUS     mandatory
   DESCRIPTION
     "An entry in the mscARtgPnniCfgNodeNbrOperTable."
   INDEX {
      mscARtgIndex,
      mscARtgPnniIndex,
      mscARtgPnniCfgNodeIndex,
      mscARtgPnniCfgNodeNbrIndex }
::= { mscARtgPnniCfgNodeNbrOperTable 1 }

MscARtgPnniCfgNodeNbrOperEntry ::= SEQUENCE {
   mscARtgPnniCfgNodeNbrPeerState
      INTEGER }

mscARtgPnniCfgNodeNbrPeerState OBJECT-TYPE
   SYNTAX     INTEGER  {
                 npDown(0),
                 negotiating(1),
                 exchanging(2),
                 loading(3),
                 full(4) }
   ACCESS     read-only
   STATUS     mandatory
   DESCRIPTION
     "This attribute indicates the state of the routing database exchange 
      with the peer node.
      
      npDown: there are no active links (i.e. in the twoWayInside Hello 
      state) to the neighboring peer.
      
      negotiating: the first step in creating an adjacency between the two 
      neighboring peers; this step determines which node is the master, 
      and what the initial DS sequence number will be.
      
      exchanging: the node describes its topology database by sending 
      Database Summary packets to the neighboring peer. 
      
      loading: a full sequence of Database Summary packets has been 
      exchanged with the neighboring peer, and the required PTSEs are 
      requested and at least one has not yet been received.
      
      full: All PTSEs known to be available have been received from the 
      neighboring peer. At this point the all ports leading to the neighbor 
      node will be flooded in PTSEs within the peer group."
::= { mscARtgPnniCfgNodeNbrOperEntry 2 }

mscARtgPnniCfgNodeNbrStatsTable OBJECT-TYPE
   SYNTAX     SEQUENCE OF MscARtgPnniCfgNodeNbrStatsEntry
   ACCESS     not-accessible
   STATUS     mandatory
   DESCRIPTION
     "*** THIS TABLE CURRENTLY NOT IMPLEMENTED ***

      This group contains the statistical operational attributes of a 
      Neighbor component."
::= { mscARtgPnniCfgNodeNbr 11 }

mscARtgPnniCfgNodeNbrStatsEntry OBJECT-TYPE
   SYNTAX     MscARtgPnniCfgNodeNbrStatsEntry
   ACCESS     not-accessible
   STATUS     mandatory
   DESCRIPTION
     "An entry in the mscARtgPnniCfgNodeNbrStatsTable."
   INDEX {
      mscARtgIndex,
      mscARtgPnniIndex,
      mscARtgPnniCfgNodeIndex,
      mscARtgPnniCfgNodeNbrIndex }
::= { mscARtgPnniCfgNodeNbrStatsTable 1 }

MscARtgPnniCfgNodeNbrStatsEntry ::= SEQUENCE {
   mscARtgPnniCfgNodeNbrPtspRx
      Counter32,
   mscARtgPnniCfgNodeNbrPtspTx
      Counter32,
   mscARtgPnniCfgNodeNbrPtseRx
      Counter32,
   mscARtgPnniCfgNodeNbrPtseTx
      Counter32,
   mscARtgPnniCfgNodeNbrPtseReqRx
      Counter32,
   mscARtgPnniCfgNodeNbrPtseReqTx
      Counter32,
   mscARtgPnniCfgNodeNbrPtseAcksRx
      Counter32,
   mscARtgPnniCfgNodeNbrPtseAcksTx
      Counter32,
   mscARtgPnniCfgNodeNbrDbSummariesRx
      Counter32,
   mscARtgPnniCfgNodeNbrDbSummariesTx
      Counter32,
   mscARtgPnniCfgNodeNbrBadPtspRx
      Counter32,
   mscARtgPnniCfgNodeNbrBadPtseRx
      Counter32,
   mscARtgPnniCfgNodeNbrBadPtseReqRx
      Counter32,
   mscARtgPnniCfgNodeNbrBadPtseAckRx
      Counter32,
   mscARtgPnniCfgNodeNbrBadDbSummariesRx
      Counter32 }

mscARtgPnniCfgNodeNbrPtspRx OBJECT-TYPE
   SYNTAX     Counter32 
   ACCESS     read-only
   STATUS     mandatory
   DESCRIPTION
     "This attribute counts the PNNI Topology State Packets received 
      from the neighbor node. The counter wraps when it exceeds the 
      maximum value."
::= { mscARtgPnniCfgNodeNbrStatsEntry 1 }

mscARtgPnniCfgNodeNbrPtspTx OBJECT-TYPE
   SYNTAX     Counter32 
   ACCESS     read-only
   STATUS     mandatory
   DESCRIPTION
     "This attribute counts the total number of PTSPs send to the 
      neighbor node.The counter wraps when it exceeds the maximum 
      value."
::= { mscARtgPnniCfgNodeNbrStatsEntry 2 }

mscARtgPnniCfgNodeNbrPtseRx OBJECT-TYPE
   SYNTAX     Counter32 
   ACCESS     read-only
   STATUS     mandatory
   DESCRIPTION
     "This attribute counts the total number of PTSEs received from the 
      neighbor node. The counter wraps when it exceeds the maximum 
      value."
::= { mscARtgPnniCfgNodeNbrStatsEntry 3 }

mscARtgPnniCfgNodeNbrPtseTx OBJECT-TYPE
   SYNTAX     Counter32 
   ACCESS     read-only
   STATUS     mandatory
   DESCRIPTION
     "This attribute counts the total number of PTSEs sent to the neighbor 
      node. The counter wraps when it exceeds the maximum value."
::= { mscARtgPnniCfgNodeNbrStatsEntry 4 }

mscARtgPnniCfgNodeNbrPtseReqRx OBJECT-TYPE
   SYNTAX     Counter32 
   ACCESS     read-only
   STATUS     mandatory
   DESCRIPTION
     "This attribute counts the total number of PTSE requests received 
      from the neighbor node. The counter wraps when it exceeds the 
      maximum value."
::= { mscARtgPnniCfgNodeNbrStatsEntry 5 }

mscARtgPnniCfgNodeNbrPtseReqTx OBJECT-TYPE
   SYNTAX     Counter32 
   ACCESS     read-only
   STATUS     mandatory
   DESCRIPTION
     "This attribute counts the total number of PTSE requests sent to the 
      neighbor node. The counter wraps when it exceeds the maximum 
      value."
::= { mscARtgPnniCfgNodeNbrStatsEntry 6 }

mscARtgPnniCfgNodeNbrPtseAcksRx OBJECT-TYPE
   SYNTAX     Counter32 
   ACCESS     read-only
   STATUS     mandatory
   DESCRIPTION
     "This attribute counts the total number of PTSE acknowledgments 
      received from the neighbor node. The counter wraps when it 
      exceeds the maximum value."
::= { mscARtgPnniCfgNodeNbrStatsEntry 7 }

mscARtgPnniCfgNodeNbrPtseAcksTx OBJECT-TYPE
   SYNTAX     Counter32 
   ACCESS     read-only
   STATUS     mandatory
   DESCRIPTION
     "This attribute counts the total number of PTSE acknowledgments 
      sent to the neighbor node. The counter wraps when it exceeds the 
      maximum value."
::= { mscARtgPnniCfgNodeNbrStatsEntry 8 }

mscARtgPnniCfgNodeNbrDbSummariesRx OBJECT-TYPE
   SYNTAX     Counter32 
   ACCESS     read-only
   STATUS     mandatory
   DESCRIPTION
     "This attribute counts the number of database summary packets 
      received from the neighbor. The counter wraps when it exceeds the 
      maximum value."
::= { mscARtgPnniCfgNodeNbrStatsEntry 9 }

mscARtgPnniCfgNodeNbrDbSummariesTx OBJECT-TYPE
   SYNTAX     Counter32 
   ACCESS     read-only
   STATUS     mandatory
   DESCRIPTION
     "This attribute counts the number of database summary packets 
      transmitted to the neighbor. The counter wraps when it exceeds the 
      maximum value."
::= { mscARtgPnniCfgNodeNbrStatsEntry 10 }

mscARtgPnniCfgNodeNbrBadPtspRx OBJECT-TYPE
   SYNTAX     Counter32 
   ACCESS     read-only
   STATUS     mandatory
   DESCRIPTION
     "This attribute counts the total number of invalid PTSP packets 
      received from the neighbor node. The counter wraps when it 
      exceeds the maximum value."
::= { mscARtgPnniCfgNodeNbrStatsEntry 11 }

mscARtgPnniCfgNodeNbrBadPtseRx OBJECT-TYPE
   SYNTAX     Counter32 
   ACCESS     read-only
   STATUS     mandatory
   DESCRIPTION
     "This attribute counts the total number of invalid PTSE packets 
      received to the neighbor node. The counter wraps when it exceeds 
      the maximum value."
::= { mscARtgPnniCfgNodeNbrStatsEntry 12 }

mscARtgPnniCfgNodeNbrBadPtseReqRx OBJECT-TYPE
   SYNTAX     Counter32 
   ACCESS     read-only
   STATUS     mandatory
   DESCRIPTION
     "This attribute counts the total number of invalid PTSE requests 
      received from the neighbor node. The counter wraps when it 
      exceeds the maximum value."
::= { mscARtgPnniCfgNodeNbrStatsEntry 13 }

mscARtgPnniCfgNodeNbrBadPtseAckRx OBJECT-TYPE
   SYNTAX     Counter32 
   ACCESS     read-only
   STATUS     mandatory
   DESCRIPTION
     "This attribute counts the total number of invalid PTSE 
      acknowledgments received from the neighbor node. The counter 
      wraps when it exceeds the maximum value."
::= { mscARtgPnniCfgNodeNbrStatsEntry 14 }

mscARtgPnniCfgNodeNbrBadDbSummariesRx OBJECT-TYPE
   SYNTAX     Counter32 
   ACCESS     read-only
   STATUS     mandatory
   DESCRIPTION
     "This attribute counts the total number of invalid database summary 
      packets received from the neighbor. The counter wraps when it 
      exceeds the maximum value."
::= { mscARtgPnniCfgNodeNbrStatsEntry 15 }

mscARtgPnniCfgNodeNbrRccListTable OBJECT-TYPE
   SYNTAX     SEQUENCE OF MscARtgPnniCfgNodeNbrRccListEntry
   ACCESS     not-accessible
   STATUS     mandatory
   DESCRIPTION
     "*** THIS TABLE CURRENTLY NOT IMPLEMENTED ***

      This attribute indicates the component names of all Routing Control 
      Channels to the neighbor PNNI node."
::= { mscARtgPnniCfgNodeNbr 385 }

mscARtgPnniCfgNodeNbrRccListEntry OBJECT-TYPE
   SYNTAX     MscARtgPnniCfgNodeNbrRccListEntry
   ACCESS     not-accessible
   STATUS     mandatory
   DESCRIPTION
     "An entry in the mscARtgPnniCfgNodeNbrRccListTable."
   INDEX {
      mscARtgIndex,
      mscARtgPnniIndex,
      mscARtgPnniCfgNodeIndex,
      mscARtgPnniCfgNodeNbrIndex,
      mscARtgPnniCfgNodeNbrRccListValue }
::= { mscARtgPnniCfgNodeNbrRccListTable 1 }

MscARtgPnniCfgNodeNbrRccListEntry ::= SEQUENCE {
   mscARtgPnniCfgNodeNbrRccListValue
      RowPointer }

mscARtgPnniCfgNodeNbrRccListValue OBJECT-TYPE
   SYNTAX     RowPointer 
   ACCESS     read-only
   STATUS     mandatory
   DESCRIPTION
     "This variable represents both the value and the index for the
      mscARtgPnniCfgNodeNbrRccListTable."
::= { mscARtgPnniCfgNodeNbrRccListEntry 1 }


-- ARtg Pnni CfgNode/<level> DefSAddr
-- A default summary address is an internal summary address 
-- computed for every logical group node as follows:
-- If this is not the lowest configured node, then the default summary 
-- address is identical to the peer group id that this logical group 
-- represents.
-- If this is the lowest configured node but not at level 104, then the 
-- default summary address is the 13-octet prefix of the node's 
-- address.
-- A node at level 104 has no default summary address.

mscARtgPnniCfgNodeDefSAddr OBJECT IDENTIFIER ::= { mscARtgPnniCfgNode 4 }



mscARtgPnniCfgNodeDefSAddrRowStatusTable OBJECT-TYPE
   SYNTAX     SEQUENCE OF MscARtgPnniCfgNodeDefSAddrRowStatusEntry
   ACCESS     not-accessible
   STATUS     mandatory
   DESCRIPTION
     "This entry controls the addition and deletion of 
      mscARtgPnniCfgNodeDefSAddr components."
::= { mscARtgPnniCfgNodeDefSAddr 1 }

mscARtgPnniCfgNodeDefSAddrRowStatusEntry OBJECT-TYPE
   SYNTAX     MscARtgPnniCfgNodeDefSAddrRowStatusEntry
   ACCESS     not-accessible
   STATUS     mandatory
   DESCRIPTION
     "A single entry in the table represents a single 
      mscARtgPnniCfgNodeDefSAddr component."
   INDEX {
      mscARtgIndex,
      mscARtgPnniIndex,
      mscARtgPnniCfgNodeIndex,
      mscARtgPnniCfgNodeDefSAddrIndex }
::= { mscARtgPnniCfgNodeDefSAddrRowStatusTable 1 }

MscARtgPnniCfgNodeDefSAddrRowStatusEntry ::= SEQUENCE {
   mscARtgPnniCfgNodeDefSAddrRowStatus
      RowStatus,
   mscARtgPnniCfgNodeDefSAddrComponentName
      DisplayString,
   mscARtgPnniCfgNodeDefSAddrStorageType
      StorageType,
   mscARtgPnniCfgNodeDefSAddrIndex
      NonReplicated }

mscARtgPnniCfgNodeDefSAddrRowStatus OBJECT-TYPE
   SYNTAX     RowStatus 
   ACCESS     read-only
   STATUS     mandatory
   DESCRIPTION
     "This variable is used as the basis for SNMP naming of
      mscARtgPnniCfgNodeDefSAddr components.
      These components cannot be added nor deleted."
::= { mscARtgPnniCfgNodeDefSAddrRowStatusEntry 1 }

mscARtgPnniCfgNodeDefSAddrComponentName OBJECT-TYPE
   SYNTAX     DisplayString 
   ACCESS     read-only
   STATUS     mandatory
   DESCRIPTION
     "This variable provides the component's string name for
      use with the ASCII Console Interface"
::= { mscARtgPnniCfgNodeDefSAddrRowStatusEntry 2 }

mscARtgPnniCfgNodeDefSAddrStorageType OBJECT-TYPE
   SYNTAX     StorageType 
   ACCESS     read-only
   STATUS     mandatory
   DESCRIPTION
     "This variable represents the storage type value for the
      mscARtgPnniCfgNodeDefSAddr tables."
::= { mscARtgPnniCfgNodeDefSAddrRowStatusEntry 4 }

mscARtgPnniCfgNodeDefSAddrIndex OBJECT-TYPE
   SYNTAX     NonReplicated 
   ACCESS     not-accessible
   STATUS     mandatory
   DESCRIPTION
     "This variable represents the index for the mscARtgPnniCfgNodeDefSAddr tables."
::= { mscARtgPnniCfgNodeDefSAddrRowStatusEntry 10 }

mscARtgPnniCfgNodeDefSAddrDefAddrTable OBJECT-TYPE
   SYNTAX     SEQUENCE OF MscARtgPnniCfgNodeDefSAddrDefAddrEntry
   ACCESS     not-accessible
   STATUS     mandatory
   DESCRIPTION
     "This group contains the operational attributes of a 
      DefSummaryAddress component."
::= { mscARtgPnniCfgNodeDefSAddr 10 }

mscARtgPnniCfgNodeDefSAddrDefAddrEntry OBJECT-TYPE
   SYNTAX     MscARtgPnniCfgNodeDefSAddrDefAddrEntry
   ACCESS     not-accessible
   STATUS     mandatory
   DESCRIPTION
     "An entry in the mscARtgPnniCfgNodeDefSAddrDefAddrTable."
   INDEX {
      mscARtgIndex,
      mscARtgPnniIndex,
      mscARtgPnniCfgNodeIndex,
      mscARtgPnniCfgNodeDefSAddrIndex }
::= { mscARtgPnniCfgNodeDefSAddrDefAddrTable 1 }

MscARtgPnniCfgNodeDefSAddrDefAddrEntry ::= SEQUENCE {
   mscARtgPnniCfgNodeDefSAddrAddress
      HexString }

mscARtgPnniCfgNodeDefSAddrAddress OBJECT-TYPE
   SYNTAX     HexString (SIZE (13))
   ACCESS     read-only
   STATUS     mandatory
   DESCRIPTION
     "This attribute indicates the default summary address of the node at 
      this level."
::= { mscARtgPnniCfgNodeDefSAddrDefAddrEntry 1 }

mscARtgPnniCfgNodeDefSAddrOperTable OBJECT-TYPE
   SYNTAX     SEQUENCE OF MscARtgPnniCfgNodeDefSAddrOperEntry
   ACCESS     not-accessible
   STATUS     mandatory
   DESCRIPTION
     "This group contains the operational attributes of a SummaryAddress 
      component."
::= { mscARtgPnniCfgNodeDefSAddr 11 }

mscARtgPnniCfgNodeDefSAddrOperEntry OBJECT-TYPE
   SYNTAX     MscARtgPnniCfgNodeDefSAddrOperEntry
   ACCESS     not-accessible
   STATUS     mandatory
   DESCRIPTION
     "An entry in the mscARtgPnniCfgNodeDefSAddrOperTable."
   INDEX {
      mscARtgIndex,
      mscARtgPnniIndex,
      mscARtgPnniCfgNodeIndex,
      mscARtgPnniCfgNodeDefSAddrIndex }
::= { mscARtgPnniCfgNodeDefSAddrOperTable 1 }

MscARtgPnniCfgNodeDefSAddrOperEntry ::= SEQUENCE {
   mscARtgPnniCfgNodeDefSAddrState
      INTEGER,
   mscARtgPnniCfgNodeDefSAddrScope
      INTEGER }

mscARtgPnniCfgNodeDefSAddrState OBJECT-TYPE
   SYNTAX     INTEGER  {
                 advertising(0),
                 suppressing(1),
                 inactive(2) }
   ACCESS     read-only
   STATUS     mandatory
   DESCRIPTION
     "This attribute indicates the state of the address: one of advertising, 
      suppressing or inactive.
      inactive: the summary address has been configured but is not 
      suppressing or summarizing any ATM addresses. 
      suppressing: the summary address has suppressed at least one ATM 
      address on the node.
      advertising: the summary address is summarizing at least one ATM 
      address on the node."
::= { mscARtgPnniCfgNodeDefSAddrOperEntry 1 }

mscARtgPnniCfgNodeDefSAddrScope OBJECT-TYPE
   SYNTAX     INTEGER (-1..104)
   ACCESS     read-only
   STATUS     mandatory
   DESCRIPTION
     "This attribute indicates the scope of the summary address. The 
      scope corresponds to the scope of the underlying summarized 
      address with the highest advertised scope. A value of -1 means the 
      scope is unknown."
::= { mscARtgPnniCfgNodeDefSAddrOperEntry 2 }

-- 
-- *** THIS SUBTREE CURRENTLY NOT IMPLEMENTED ***
-- 

-- ARtg Pnni Topology/<level>
-- 
-- The Topology component provides access to information in this 
-- node's PNNI topology database for a particular level in the PNNI 
-- hierarchy.

mscARtgPnniTop OBJECT IDENTIFIER ::= { mscARtgPnni 4 }



mscARtgPnniTopRowStatusTable OBJECT-TYPE
   SYNTAX     SEQUENCE OF MscARtgPnniTopRowStatusEntry
   ACCESS     not-accessible
   STATUS     mandatory
   DESCRIPTION
     "*** THIS TABLE CURRENTLY NOT IMPLEMENTED ***

      This entry controls the addition and deletion of 
      mscARtgPnniTop components."
::= { mscARtgPnniTop 1 }

mscARtgPnniTopRowStatusEntry OBJECT-TYPE
   SYNTAX     MscARtgPnniTopRowStatusEntry
   ACCESS     not-accessible
   STATUS     mandatory
   DESCRIPTION
     "A single entry in the table represents a single 
      mscARtgPnniTop component."
   INDEX {
      mscARtgIndex,
      mscARtgPnniIndex,
      mscARtgPnniTopIndex }
::= { mscARtgPnniTopRowStatusTable 1 }

MscARtgPnniTopRowStatusEntry ::= SEQUENCE {
   mscARtgPnniTopRowStatus
      RowStatus,
   mscARtgPnniTopComponentName
      DisplayString,
   mscARtgPnniTopStorageType
      StorageType,
   mscARtgPnniTopIndex
      Integer32 }

mscARtgPnniTopRowStatus OBJECT-TYPE
   SYNTAX     RowStatus 
   ACCESS     read-only
   STATUS     mandatory
   DESCRIPTION
     "This variable is used as the basis for SNMP naming of
      mscARtgPnniTop components.
      These components cannot be added nor deleted."
::= { mscARtgPnniTopRowStatusEntry 1 }

mscARtgPnniTopComponentName OBJECT-TYPE
   SYNTAX     DisplayString 
   ACCESS     read-only
   STATUS     mandatory
   DESCRIPTION
     "This variable provides the component's string name for
      use with the ASCII Console Interface"
::= { mscARtgPnniTopRowStatusEntry 2 }

mscARtgPnniTopStorageType OBJECT-TYPE
   SYNTAX     StorageType 
   ACCESS     read-only
   STATUS     mandatory
   DESCRIPTION
     "This variable represents the storage type value for the
      mscARtgPnniTop tables."
::= { mscARtgPnniTopRowStatusEntry 4 }

mscARtgPnniTopIndex OBJECT-TYPE
   SYNTAX     Integer32 (0..104)
   ACCESS     not-accessible
   STATUS     mandatory
   DESCRIPTION
     "This variable represents the index for the mscARtgPnniTop tables."
::= { mscARtgPnniTopRowStatusEntry 10 }

mscARtgPnniTopOperTable OBJECT-TYPE
   SYNTAX     SEQUENCE OF MscARtgPnniTopOperEntry
   ACCESS     not-accessible
   STATUS     mandatory
   DESCRIPTION
     "*** THIS TABLE CURRENTLY NOT IMPLEMENTED ***

      This group contains the operational attributes of a Topology 
      component."
::= { mscARtgPnniTop 10 }

mscARtgPnniTopOperEntry OBJECT-TYPE
   SYNTAX     MscARtgPnniTopOperEntry
   ACCESS     not-accessible
   STATUS     mandatory
   DESCRIPTION
     "An entry in the mscARtgPnniTopOperTable."
   INDEX {
      mscARtgIndex,
      mscARtgPnniIndex,
      mscARtgPnniTopIndex }
::= { mscARtgPnniTopOperTable 1 }

MscARtgPnniTopOperEntry ::= SEQUENCE {
   mscARtgPnniTopPtsesInDatabase
      Gauge32,
   mscARtgPnniTopPglNodeId
      HexString,
   mscARtgPnniTopActiveParentNodeId
      HexString,
   mscARtgPnniTopPreferredPglNodeId
      HexString }

mscARtgPnniTopPtsesInDatabase OBJECT-TYPE
   SYNTAX     Gauge32 (0..4294967295)
   ACCESS     read-only
   STATUS     mandatory
   DESCRIPTION
     "This attribute indicates the number of PTSEs in storage in this 
      node's topology database for this level."
::= { mscARtgPnniTopOperEntry 1 }

mscARtgPnniTopPglNodeId OBJECT-TYPE
   SYNTAX     HexString (SIZE (0..22))
   ACCESS     read-only
   STATUS     mandatory
   DESCRIPTION
     "This attribute indicates the node id of the peer group leader. If this 
      attribute is empty, it indicates the Peer Group Level node id is 
      unknown."
::= { mscARtgPnniTopOperEntry 2 }

mscARtgPnniTopActiveParentNodeId OBJECT-TYPE
   SYNTAX     HexString (SIZE (0..22))
   ACCESS     read-only
   STATUS     mandatory
   DESCRIPTION
     "This attribute indicates the node identifier being used by the LGN 
      representing this peer group at the next higher level peer group."
::= { mscARtgPnniTopOperEntry 3 }

mscARtgPnniTopPreferredPglNodeId OBJECT-TYPE
   SYNTAX     HexString (SIZE (0..22))
   ACCESS     read-only
   STATUS     mandatory
   DESCRIPTION
     "This attribute represents the node in database with the highest Peer 
      Group Level (PGL) priority. If this attribute is empty, it indicates 
      the preferred PGL node id is unknown."
::= { mscARtgPnniTopOperEntry 4 }

-- 
-- *** THIS SUBTREE CURRENTLY NOT IMPLEMENTED ***
-- 

-- ARtg Pnni Top/<level> Node/<node id>
-- This component represents the nodal information stored in this 
-- node's topology database.
-- 
-- The reachable ATM end system addresses (both interior and 
-- exterior reachable addresses) advertised by the node can be listed 
-- through the Addr subcomponent instances.
-- 
-- All advertised links associated with the node can be listed through 
-- the Link subcomponent instances which are indexed by their port id.

mscARtgPnniTopNode OBJECT IDENTIFIER ::= { mscARtgPnniTop 2 }



mscARtgPnniTopNodeRowStatusTable OBJECT-TYPE
   SYNTAX     SEQUENCE OF MscARtgPnniTopNodeRowStatusEntry
   ACCESS     not-accessible
   STATUS     mandatory
   DESCRIPTION
     "*** THIS TABLE CURRENTLY NOT IMPLEMENTED ***

      This entry controls the addition and deletion of 
      mscARtgPnniTopNode components."
::= { mscARtgPnniTopNode 1 }

mscARtgPnniTopNodeRowStatusEntry OBJECT-TYPE
   SYNTAX     MscARtgPnniTopNodeRowStatusEntry
   ACCESS     not-accessible
   STATUS     mandatory
   DESCRIPTION
     "A single entry in the table represents a single 
      mscARtgPnniTopNode component."
   INDEX {
      mscARtgIndex,
      mscARtgPnniIndex,
      mscARtgPnniTopIndex,
      mscARtgPnniTopNodeIndex }
::= { mscARtgPnniTopNodeRowStatusTable 1 }

MscARtgPnniTopNodeRowStatusEntry ::= SEQUENCE {
   mscARtgPnniTopNodeRowStatus
      RowStatus,
   mscARtgPnniTopNodeComponentName
      DisplayString,
   mscARtgPnniTopNodeStorageType
      StorageType,
   mscARtgPnniTopNodeIndex
      HexString }

mscARtgPnniTopNodeRowStatus OBJECT-TYPE
   SYNTAX     RowStatus 
   ACCESS     read-only
   STATUS     mandatory
   DESCRIPTION
     "This variable is used as the basis for SNMP naming of
      mscARtgPnniTopNode components.
      These components cannot be added nor deleted."
::= { mscARtgPnniTopNodeRowStatusEntry 1 }

mscARtgPnniTopNodeComponentName OBJECT-TYPE
   SYNTAX     DisplayString 
   ACCESS     read-only
   STATUS     mandatory
   DESCRIPTION
     "This variable provides the component's string name for
      use with the ASCII Console Interface"
::= { mscARtgPnniTopNodeRowStatusEntry 2 }

mscARtgPnniTopNodeStorageType OBJECT-TYPE
   SYNTAX     StorageType 
   ACCESS     read-only
   STATUS     mandatory
   DESCRIPTION
     "This variable represents the storage type value for the
      mscARtgPnniTopNode tables."
::= { mscARtgPnniTopNodeRowStatusEntry 4 }

mscARtgPnniTopNodeIndex OBJECT-TYPE
   SYNTAX     HexString (SIZE (22))
   ACCESS     not-accessible
   STATUS     mandatory
   DESCRIPTION
     "This variable represents the index for the mscARtgPnniTopNode tables."
::= { mscARtgPnniTopNodeRowStatusEntry 10 }

-- 
-- *** THIS SUBTREE CURRENTLY NOT IMPLEMENTED ***
-- 

-- ARtg Pnni Top Node/<node id> Address/<address>, 
-- <prefixLength>, <reachability>
-- This component represents an address advertised by the parent 
-- node. The instance value is a 38 hex digit string. 
-- 
-- The prefixLength specifies the number of significant bits in the 
-- address. 
-- 
-- The reachability specifies whether the address is internal or 
-- exterior.
-- An internal reachable address is an address of a destination that is 
-- directly attached to the logical node advertising the address. An 
-- exterior reachable address is an address that can be reached 
-- through a PNNI routing domain, but which is not located in that 
-- PNNI routing domain.

mscARtgPnniTopNodeAddr OBJECT IDENTIFIER ::= { mscARtgPnniTopNode 2 }



mscARtgPnniTopNodeAddrRowStatusTable OBJECT-TYPE
   SYNTAX     SEQUENCE OF MscARtgPnniTopNodeAddrRowStatusEntry
   ACCESS     not-accessible
   STATUS     mandatory
   DESCRIPTION
     "*** THIS TABLE CURRENTLY NOT IMPLEMENTED ***

      This entry controls the addition and deletion of 
      mscARtgPnniTopNodeAddr components."
::= { mscARtgPnniTopNodeAddr 1 }

mscARtgPnniTopNodeAddrRowStatusEntry OBJECT-TYPE
   SYNTAX     MscARtgPnniTopNodeAddrRowStatusEntry
   ACCESS     not-accessible
   STATUS     mandatory
   DESCRIPTION
     "A single entry in the table represents a single 
      mscARtgPnniTopNodeAddr component."
   INDEX {
      mscARtgIndex,
      mscARtgPnniIndex,
      mscARtgPnniTopIndex,
      mscARtgPnniTopNodeIndex,
      mscARtgPnniTopNodeAddrAddressIndex,
      mscARtgPnniTopNodeAddrPrefixLengthIndex,
      mscARtgPnniTopNodeAddrReachabilityIndex }
::= { mscARtgPnniTopNodeAddrRowStatusTable 1 }

MscARtgPnniTopNodeAddrRowStatusEntry ::= SEQUENCE {
   mscARtgPnniTopNodeAddrRowStatus
      RowStatus,
   mscARtgPnniTopNodeAddrComponentName
      DisplayString,
   mscARtgPnniTopNodeAddrStorageType
      StorageType,
   mscARtgPnniTopNodeAddrAddressIndex
      HexString,
   mscARtgPnniTopNodeAddrPrefixLengthIndex
      Integer32,
   mscARtgPnniTopNodeAddrReachabilityIndex
      INTEGER }

mscARtgPnniTopNodeAddrRowStatus OBJECT-TYPE
   SYNTAX     RowStatus 
   ACCESS     read-only
   STATUS     mandatory
   DESCRIPTION
     "This variable is used as the basis for SNMP naming of
      mscARtgPnniTopNodeAddr components.
      These components cannot be added nor deleted."
::= { mscARtgPnniTopNodeAddrRowStatusEntry 1 }

mscARtgPnniTopNodeAddrComponentName OBJECT-TYPE
   SYNTAX     DisplayString 
   ACCESS     read-only
   STATUS     mandatory
   DESCRIPTION
     "This variable provides the component's string name for
      use with the ASCII Console Interface"
::= { mscARtgPnniTopNodeAddrRowStatusEntry 2 }

mscARtgPnniTopNodeAddrStorageType OBJECT-TYPE
   SYNTAX     StorageType 
   ACCESS     read-only
   STATUS     mandatory
   DESCRIPTION
     "This variable represents the storage type value for the
      mscARtgPnniTopNodeAddr tables."
::= { mscARtgPnniTopNodeAddrRowStatusEntry 4 }

mscARtgPnniTopNodeAddrAddressIndex OBJECT-TYPE
   SYNTAX     HexString (SIZE (19))
   ACCESS     not-accessible
   STATUS     mandatory
   DESCRIPTION
     "This variable represents an index for the mscARtgPnniTopNodeAddr tables."
::= { mscARtgPnniTopNodeAddrRowStatusEntry 10 }

mscARtgPnniTopNodeAddrPrefixLengthIndex OBJECT-TYPE
   SYNTAX     Integer32 (1..152)
   ACCESS     not-accessible
   STATUS     mandatory
   DESCRIPTION
     "This variable represents an index for the mscARtgPnniTopNodeAddr tables."
::= { mscARtgPnniTopNodeAddrRowStatusEntry 11 }

mscARtgPnniTopNodeAddrReachabilityIndex OBJECT-TYPE
   SYNTAX     INTEGER  {
                 internal(0),
                 exterior(1) }
   ACCESS     not-accessible
   STATUS     mandatory
   DESCRIPTION
     "This variable represents an index for the mscARtgPnniTopNodeAddr tables."
::= { mscARtgPnniTopNodeAddrRowStatusEntry 12 }

mscARtgPnniTopNodeAddrOperTable OBJECT-TYPE
   SYNTAX     SEQUENCE OF MscARtgPnniTopNodeAddrOperEntry
   ACCESS     not-accessible
   STATUS     mandatory
   DESCRIPTION
     "*** THIS TABLE CURRENTLY NOT IMPLEMENTED ***

      This attribute group contains the operational attributes for the 
      Address component."
::= { mscARtgPnniTopNodeAddr 10 }

mscARtgPnniTopNodeAddrOperEntry OBJECT-TYPE
   SYNTAX     MscARtgPnniTopNodeAddrOperEntry
   ACCESS     not-accessible
   STATUS     mandatory
   DESCRIPTION
     "An entry in the mscARtgPnniTopNodeAddrOperTable."
   INDEX {
      mscARtgIndex,
      mscARtgPnniIndex,
      mscARtgPnniTopIndex,
      mscARtgPnniTopNodeIndex,
      mscARtgPnniTopNodeAddrAddressIndex,
      mscARtgPnniTopNodeAddrPrefixLengthIndex,
      mscARtgPnniTopNodeAddrReachabilityIndex }
::= { mscARtgPnniTopNodeAddrOperTable 1 }

MscARtgPnniTopNodeAddrOperEntry ::= SEQUENCE {
   mscARtgPnniTopNodeAddrScope
      Unsigned32 }

mscARtgPnniTopNodeAddrScope OBJECT-TYPE
   SYNTAX     Unsigned32 (0..104)
   ACCESS     read-only
   STATUS     mandatory
   DESCRIPTION
     "This attribute specifies the scope of the ATM address, which is the 
      highest level to which this address will be advertised in the PNNI 
      hierarchy."
::= { mscARtgPnniTopNodeAddrOperEntry 1 }

-- 
-- *** THIS SUBTREE CURRENTLY NOT IMPLEMENTED ***
-- 

-- ARtg Pnni Top/<level> Node/<node id> Link/<port id>
-- This component represents the link information stored in this node's 
-- topology database.
-- 
-- All advertised links associated with the node can be listed through 
-- the Link subcomponent instances which are indexed by their port id.

mscARtgPnniTopNodeLink OBJECT IDENTIFIER ::= { mscARtgPnniTopNode 3 }



mscARtgPnniTopNodeLinkRowStatusTable OBJECT-TYPE
   SYNTAX     SEQUENCE OF MscARtgPnniTopNodeLinkRowStatusEntry
   ACCESS     not-accessible
   STATUS     mandatory
   DESCRIPTION
     "*** THIS TABLE CURRENTLY NOT IMPLEMENTED ***

      This entry controls the addition and deletion of 
      mscARtgPnniTopNodeLink components."
::= { mscARtgPnniTopNodeLink 1 }

mscARtgPnniTopNodeLinkRowStatusEntry OBJECT-TYPE
   SYNTAX     MscARtgPnniTopNodeLinkRowStatusEntry
   ACCESS     not-accessible
   STATUS     mandatory
   DESCRIPTION
     "A single entry in the table represents a single 
      mscARtgPnniTopNodeLink component."
   INDEX {
      mscARtgIndex,
      mscARtgPnniIndex,
      mscARtgPnniTopIndex,
      mscARtgPnniTopNodeIndex,
      mscARtgPnniTopNodeLinkIndex }
::= { mscARtgPnniTopNodeLinkRowStatusTable 1 }

MscARtgPnniTopNodeLinkRowStatusEntry ::= SEQUENCE {
   mscARtgPnniTopNodeLinkRowStatus
      RowStatus,
   mscARtgPnniTopNodeLinkComponentName
      DisplayString,
   mscARtgPnniTopNodeLinkStorageType
      StorageType,
   mscARtgPnniTopNodeLinkIndex
      Integer32 }

mscARtgPnniTopNodeLinkRowStatus OBJECT-TYPE
   SYNTAX     RowStatus 
   ACCESS     read-only
   STATUS     mandatory
   DESCRIPTION
     "This variable is used as the basis for SNMP naming of
      mscARtgPnniTopNodeLink components.
      These components cannot be added nor deleted."
::= { mscARtgPnniTopNodeLinkRowStatusEntry 1 }

mscARtgPnniTopNodeLinkComponentName OBJECT-TYPE
   SYNTAX     DisplayString 
   ACCESS     read-only
   STATUS     mandatory
   DESCRIPTION
     "This variable provides the component's string name for
      use with the ASCII Console Interface"
::= { mscARtgPnniTopNodeLinkRowStatusEntry 2 }

mscARtgPnniTopNodeLinkStorageType OBJECT-TYPE
   SYNTAX     StorageType 
   ACCESS     read-only
   STATUS     mandatory
   DESCRIPTION
     "This variable represents the storage type value for the
      mscARtgPnniTopNodeLink tables."
::= { mscARtgPnniTopNodeLinkRowStatusEntry 4 }

mscARtgPnniTopNodeLinkIndex OBJECT-TYPE
   SYNTAX     Integer32 (0..268435455)
   ACCESS     not-accessible
   STATUS     mandatory
   DESCRIPTION
     "This variable represents the index for the mscARtgPnniTopNodeLink tables."
::= { mscARtgPnniTopNodeLinkRowStatusEntry 10 }

mscARtgPnniTopNodeLinkOperTable OBJECT-TYPE
   SYNTAX     SEQUENCE OF MscARtgPnniTopNodeLinkOperEntry
   ACCESS     not-accessible
   STATUS     mandatory
   DESCRIPTION
     "*** THIS TABLE CURRENTLY NOT IMPLEMENTED ***

      This group contains the operational attributes of a Link component."
::= { mscARtgPnniTopNodeLink 10 }

mscARtgPnniTopNodeLinkOperEntry OBJECT-TYPE
   SYNTAX     MscARtgPnniTopNodeLinkOperEntry
   ACCESS     not-accessible
   STATUS     mandatory
   DESCRIPTION
     "An entry in the mscARtgPnniTopNodeLinkOperTable."
   INDEX {
      mscARtgIndex,
      mscARtgPnniIndex,
      mscARtgPnniTopIndex,
      mscARtgPnniTopNodeIndex,
      mscARtgPnniTopNodeLinkIndex }
::= { mscARtgPnniTopNodeLinkOperTable 1 }

MscARtgPnniTopNodeLinkOperEntry ::= SEQUENCE {
   mscARtgPnniTopNodeLinkRemoteNodeId
      HexString,
   mscARtgPnniTopNodeLinkRemotePortId
      Unsigned32 }

mscARtgPnniTopNodeLinkRemoteNodeId OBJECT-TYPE
   SYNTAX     HexString (SIZE (22))
   ACCESS     read-only
   STATUS     mandatory
   DESCRIPTION
     "This attribute indicates the id of the node at the far end of this link."
::= { mscARtgPnniTopNodeLinkOperEntry 1 }

mscARtgPnniTopNodeLinkRemotePortId OBJECT-TYPE
   SYNTAX     Unsigned32 (0..4294967295)
   ACCESS     read-only
   STATUS     mandatory
   DESCRIPTION
     "This attribute indicates the node's port id at the far end of this link."
::= { mscARtgPnniTopNodeLinkOperEntry 2 }

-- 
-- *** THIS SUBTREE CURRENTLY NOT IMPLEMENTED ***
-- 

-- ARtg Pnni Port/<n>
-- This component represents a port advertised within the PNNI 
-- routing domain.

mscARtgPnniPort OBJECT IDENTIFIER ::= { mscARtgPnni 5 }



mscARtgPnniPortRowStatusTable OBJECT-TYPE
   SYNTAX     SEQUENCE OF MscARtgPnniPortRowStatusEntry
   ACCESS     not-accessible
   STATUS     mandatory
   DESCRIPTION
     "*** THIS TABLE CURRENTLY NOT IMPLEMENTED ***

      This entry controls the addition and deletion of 
      mscARtgPnniPort components."
::= { mscARtgPnniPort 1 }

mscARtgPnniPortRowStatusEntry OBJECT-TYPE
   SYNTAX     MscARtgPnniPortRowStatusEntry
   ACCESS     not-accessible
   STATUS     mandatory
   DESCRIPTION
     "A single entry in the table represents a single 
      mscARtgPnniPort component."
   INDEX {
      mscARtgIndex,
      mscARtgPnniIndex,
      mscARtgPnniPortIndex }
::= { mscARtgPnniPortRowStatusTable 1 }

MscARtgPnniPortRowStatusEntry ::= SEQUENCE {
   mscARtgPnniPortRowStatus
      RowStatus,
   mscARtgPnniPortComponentName
      DisplayString,
   mscARtgPnniPortStorageType
      StorageType,
   mscARtgPnniPortIndex
      Integer32 }

mscARtgPnniPortRowStatus OBJECT-TYPE
   SYNTAX     RowStatus 
   ACCESS     read-only
   STATUS     mandatory
   DESCRIPTION
     "This variable is used as the basis for SNMP naming of
      mscARtgPnniPort components.
      These components cannot be added nor deleted."
::= { mscARtgPnniPortRowStatusEntry 1 }

mscARtgPnniPortComponentName OBJECT-TYPE
   SYNTAX     DisplayString 
   ACCESS     read-only
   STATUS     mandatory
   DESCRIPTION
     "This variable provides the component's string name for
      use with the ASCII Console Interface"
::= { mscARtgPnniPortRowStatusEntry 2 }

mscARtgPnniPortStorageType OBJECT-TYPE
   SYNTAX     StorageType 
   ACCESS     read-only
   STATUS     mandatory
   DESCRIPTION
     "This variable represents the storage type value for the
      mscARtgPnniPort tables."
::= { mscARtgPnniPortRowStatusEntry 4 }

mscARtgPnniPortIndex OBJECT-TYPE
   SYNTAX     Integer32 (0..268435455)
   ACCESS     not-accessible
   STATUS     mandatory
   DESCRIPTION
     "This variable represents the index for the mscARtgPnniPort tables."
::= { mscARtgPnniPortRowStatusEntry 10 }

mscARtgPnniPortOperTable OBJECT-TYPE
   SYNTAX     SEQUENCE OF MscARtgPnniPortOperEntry
   ACCESS     not-accessible
   STATUS     mandatory
   DESCRIPTION
     "*** THIS TABLE CURRENTLY NOT IMPLEMENTED ***

      This group contains the operational attributes of a Port component."
::= { mscARtgPnniPort 10 }

mscARtgPnniPortOperEntry OBJECT-TYPE
   SYNTAX     MscARtgPnniPortOperEntry
   ACCESS     not-accessible
   STATUS     mandatory
   DESCRIPTION
     "An entry in the mscARtgPnniPortOperTable."
   INDEX {
      mscARtgIndex,
      mscARtgPnniIndex,
      mscARtgPnniPortIndex }
::= { mscARtgPnniPortOperTable 1 }

MscARtgPnniPortOperEntry ::= SEQUENCE {
   mscARtgPnniPortStdComponentName
      RowPointer }

mscARtgPnniPortStdComponentName OBJECT-TYPE
   SYNTAX     RowPointer 
   ACCESS     read-only
   STATUS     mandatory
   DESCRIPTION
     "This attribute indicates the component name of the port."
::= { mscARtgPnniPortOperEntry 1 }


-- AtmCallRouter
-- This component represents the database that contains all the static 
-- (provisioned) DNAs and dynamically registered DNAs (via ILMI) 
-- used for source call routing for ATM switched connection setups..

mscAtmCR OBJECT IDENTIFIER ::= { mscComponents 113 }



mscAtmCRRowStatusTable OBJECT-TYPE
   SYNTAX     SEQUENCE OF MscAtmCRRowStatusEntry
   ACCESS     not-accessible
   STATUS     mandatory
   DESCRIPTION
     "This entry controls the addition and deletion of 
      mscAtmCR components."
::= { mscAtmCR 1 }

mscAtmCRRowStatusEntry OBJECT-TYPE
   SYNTAX     MscAtmCRRowStatusEntry
   ACCESS     not-accessible
   STATUS     mandatory
   DESCRIPTION
     "A single entry in the table represents a single 
      mscAtmCR component."
   INDEX {
      mscAtmCRIndex }
::= { mscAtmCRRowStatusTable 1 }

MscAtmCRRowStatusEntry ::= SEQUENCE {
   mscAtmCRRowStatus
      RowStatus,
   mscAtmCRComponentName
      DisplayString,
   mscAtmCRStorageType
      StorageType,
   mscAtmCRIndex
      NonReplicated }

mscAtmCRRowStatus OBJECT-TYPE
   SYNTAX     RowStatus 
   ACCESS     read-write
   STATUS     mandatory
   DESCRIPTION
     "This variable is used as the basis for SNMP naming of
      mscAtmCR components.
      These components can be added and deleted."
::= { mscAtmCRRowStatusEntry 1 }

mscAtmCRComponentName OBJECT-TYPE
   SYNTAX     DisplayString 
   ACCESS     read-only
   STATUS     mandatory
   DESCRIPTION
     "This variable provides the component's string name for
      use with the ASCII Console Interface"
::= { mscAtmCRRowStatusEntry 2 }

mscAtmCRStorageType OBJECT-TYPE
   SYNTAX     StorageType 
   ACCESS     read-only
   STATUS     mandatory
   DESCRIPTION
     "This variable represents the storage type value for the
      mscAtmCR tables."
::= { mscAtmCRRowStatusEntry 4 }

mscAtmCRIndex OBJECT-TYPE
   SYNTAX     NonReplicated 
   ACCESS     not-accessible
   STATUS     mandatory
   DESCRIPTION
     "This variable represents the index for the mscAtmCR tables."
::= { mscAtmCRRowStatusEntry 10 }

mscAtmCRProvTable OBJECT-TYPE
   SYNTAX     SEQUENCE OF MscAtmCRProvEntry
   ACCESS     not-accessible
   STATUS     mandatory
   DESCRIPTION
     "This group represents the provisioned attributes for the 
      AtmCallRouter component."
::= { mscAtmCR 10 }

mscAtmCRProvEntry OBJECT-TYPE
   SYNTAX     MscAtmCRProvEntry
   ACCESS     not-accessible
   STATUS     mandatory
   DESCRIPTION
     "An entry in the mscAtmCRProvTable."
   INDEX {
      mscAtmCRIndex }
::= { mscAtmCRProvTable 1 }

MscAtmCRProvEntry ::= SEQUENCE {
   mscAtmCRNodeAddress
      AsciiString }

mscAtmCRNodeAddress OBJECT-TYPE
   SYNTAX     AsciiString (SIZE (26))
   ACCESS     read-write
   STATUS     obsolete
   DESCRIPTION
     "This attribute specifies the NSAP address prefix used for ILMI 
      purposes."
::= { mscAtmCRProvEntry 1 }

mscAtmCRStatsTable OBJECT-TYPE
   SYNTAX     SEQUENCE OF MscAtmCRStatsEntry
   ACCESS     not-accessible
   STATUS     obsolete
   DESCRIPTION
     "This group represents the operational attributes for the 
      AtmCallRouter component."
::= { mscAtmCR 11 }

mscAtmCRStatsEntry OBJECT-TYPE
   SYNTAX     MscAtmCRStatsEntry
   ACCESS     not-accessible
   STATUS     obsolete
   DESCRIPTION
     "An entry in the mscAtmCRStatsTable."
   INDEX {
      mscAtmCRIndex }
::= { mscAtmCRStatsTable 1 }

MscAtmCRStatsEntry ::= SEQUENCE {
   mscAtmCRCallsRouted
      Counter32,
   mscAtmCRCallsFailed
      Counter32 }

mscAtmCRCallsRouted OBJECT-TYPE
   SYNTAX     Counter32 
   ACCESS     read-only
   STATUS     obsolete
   DESCRIPTION
     "This attribute counts the total number of calls routed."
::= { mscAtmCRStatsEntry 1 }

mscAtmCRCallsFailed OBJECT-TYPE
   SYNTAX     Counter32 
   ACCESS     read-only
   STATUS     obsolete
   DESCRIPTION
     "This attribute specifies the number of calls that failed to route."
::= { mscAtmCRStatsEntry 2 }

-- 
-- *** THIS SUBTREE CURRENTLY NOT IMPLEMENTED ***
-- 

-- AtmCallRouter AtmDna/<STRING(1..40)>
-- This component represents an ATM NSAP address that has been 
-- provisioned or dynamically registered via ILMI.

mscAtmCRDna OBJECT IDENTIFIER ::= { mscAtmCR 2 }



mscAtmCRDnaRowStatusTable OBJECT-TYPE
   SYNTAX     SEQUENCE OF MscAtmCRDnaRowStatusEntry
   ACCESS     not-accessible
   STATUS     mandatory
   DESCRIPTION
     "*** THIS TABLE CURRENTLY NOT IMPLEMENTED ***

      This entry controls the addition and deletion of 
      mscAtmCRDna components."
::= { mscAtmCRDna 1 }

mscAtmCRDnaRowStatusEntry OBJECT-TYPE
   SYNTAX     MscAtmCRDnaRowStatusEntry
   ACCESS     not-accessible
   STATUS     mandatory
   DESCRIPTION
     "A single entry in the table represents a single 
      mscAtmCRDna component."
   INDEX {
      mscAtmCRIndex,
      mscAtmCRDnaIndex }
::= { mscAtmCRDnaRowStatusTable 1 }

MscAtmCRDnaRowStatusEntry ::= SEQUENCE {
   mscAtmCRDnaRowStatus
      RowStatus,
   mscAtmCRDnaComponentName
      DisplayString,
   mscAtmCRDnaStorageType
      StorageType,
   mscAtmCRDnaIndex
      AsciiStringIndex }

mscAtmCRDnaRowStatus OBJECT-TYPE
   SYNTAX     RowStatus 
   ACCESS     read-only
   STATUS     mandatory
   DESCRIPTION
     "This variable is used as the basis for SNMP naming of
      mscAtmCRDna components.
      These components cannot be added nor deleted."
::= { mscAtmCRDnaRowStatusEntry 1 }

mscAtmCRDnaComponentName OBJECT-TYPE
   SYNTAX     DisplayString 
   ACCESS     read-only
   STATUS     mandatory
   DESCRIPTION
     "This variable provides the component's string name for
      use with the ASCII Console Interface"
::= { mscAtmCRDnaRowStatusEntry 2 }

mscAtmCRDnaStorageType OBJECT-TYPE
   SYNTAX     StorageType 
   ACCESS     read-only
   STATUS     mandatory
   DESCRIPTION
     "This variable represents the storage type value for the
      mscAtmCRDna tables."
::= { mscAtmCRDnaRowStatusEntry 4 }

mscAtmCRDnaIndex OBJECT-TYPE
   SYNTAX     AsciiStringIndex (SIZE (1..40))
   ACCESS     not-accessible
   STATUS     mandatory
   DESCRIPTION
     "This variable represents the index for the mscAtmCRDna tables."
::= { mscAtmCRDnaRowStatusEntry 10 }

mscAtmCRDnaDestinationNameTable OBJECT-TYPE
   SYNTAX     SEQUENCE OF MscAtmCRDnaDestinationNameEntry
   ACCESS     not-accessible
   STATUS     obsolete
   DESCRIPTION
     "*** THIS TABLE CURRENTLY NOT IMPLEMENTED ***

      This attribute indicates which components have this address 
      provisioned or dynamically registered via ILMI."
::= { mscAtmCRDna 289 }

mscAtmCRDnaDestinationNameEntry OBJECT-TYPE
   SYNTAX     MscAtmCRDnaDestinationNameEntry
   ACCESS     not-accessible
   STATUS     obsolete
   DESCRIPTION
     "An entry in the mscAtmCRDnaDestinationNameTable."
   INDEX {
      mscAtmCRIndex,
      mscAtmCRDnaIndex,
      mscAtmCRDnaDestinationNameValue }
::= { mscAtmCRDnaDestinationNameTable 1 }

MscAtmCRDnaDestinationNameEntry ::= SEQUENCE {
   mscAtmCRDnaDestinationNameValue
      RowPointer }

mscAtmCRDnaDestinationNameValue OBJECT-TYPE
   SYNTAX     RowPointer 
   ACCESS     read-only
   STATUS     obsolete
   DESCRIPTION
     "This variable represents both the value and the index for the
      mscAtmCRDnaDestinationNameTable."
::= { mscAtmCRDnaDestinationNameEntry 1 }


-- AtmIf/n Vpc/vpi SourcePvp
-- This component represents the source end of a soft PVP.

mscAtmIfVpcSrc OBJECT IDENTIFIER ::= { mscAtmIfVpc 6 }



mscAtmIfVpcSrcRowStatusTable OBJECT-TYPE
   SYNTAX     SEQUENCE OF MscAtmIfVpcSrcRowStatusEntry
   ACCESS     not-accessible
   STATUS     mandatory
   DESCRIPTION
     "This entry controls the addition and deletion of 
      mscAtmIfVpcSrc components."
::= { mscAtmIfVpcSrc 1 }

mscAtmIfVpcSrcRowStatusEntry OBJECT-TYPE
   SYNTAX     MscAtmIfVpcSrcRowStatusEntry
   ACCESS     not-accessible
   STATUS     mandatory
   DESCRIPTION
     "A single entry in the table represents a single 
      mscAtmIfVpcSrc component."
   INDEX {
      mscAtmIfIndex,
      mscAtmIfVpcIndex,
      mscAtmIfVpcSrcIndex }
::= { mscAtmIfVpcSrcRowStatusTable 1 }

MscAtmIfVpcSrcRowStatusEntry ::= SEQUENCE {
   mscAtmIfVpcSrcRowStatus
      RowStatus,
   mscAtmIfVpcSrcComponentName
      DisplayString,
   mscAtmIfVpcSrcStorageType
      StorageType,
   mscAtmIfVpcSrcIndex
      NonReplicated }

mscAtmIfVpcSrcRowStatus OBJECT-TYPE
   SYNTAX     RowStatus 
   ACCESS     read-write
   STATUS     mandatory
   DESCRIPTION
     "This variable is used as the basis for SNMP naming of
      mscAtmIfVpcSrc components.
      These components can be added and deleted."
::= { mscAtmIfVpcSrcRowStatusEntry 1 }

mscAtmIfVpcSrcComponentName OBJECT-TYPE
   SYNTAX     DisplayString 
   ACCESS     read-only
   STATUS     mandatory
   DESCRIPTION
     "This variable provides the component's string name for
      use with the ASCII Console Interface"
::= { mscAtmIfVpcSrcRowStatusEntry 2 }

mscAtmIfVpcSrcStorageType OBJECT-TYPE
   SYNTAX     StorageType 
   ACCESS     read-only
   STATUS     mandatory
   DESCRIPTION
     "This variable represents the storage type value for the
      mscAtmIfVpcSrc tables."
::= { mscAtmIfVpcSrcRowStatusEntry 4 }

mscAtmIfVpcSrcIndex OBJECT-TYPE
   SYNTAX     NonReplicated 
   ACCESS     not-accessible
   STATUS     mandatory
   DESCRIPTION
     "This variable represents the index for the mscAtmIfVpcSrc tables."
::= { mscAtmIfVpcSrcRowStatusEntry 10 }

mscAtmIfVpcSrcProvTable OBJECT-TYPE
   SYNTAX     SEQUENCE OF MscAtmIfVpcSrcProvEntry
   ACCESS     not-accessible
   STATUS     mandatory
   DESCRIPTION
     "This attribute group contains the provisionable attributes of the 
      AtmIf/n Vpc/vpi SrcPvp component."
::= { mscAtmIfVpcSrc 10 }

mscAtmIfVpcSrcProvEntry OBJECT-TYPE
   SYNTAX     MscAtmIfVpcSrcProvEntry
   ACCESS     not-accessible
   STATUS     mandatory
   DESCRIPTION
     "An entry in the mscAtmIfVpcSrcProvTable."
   INDEX {
      mscAtmIfIndex,
      mscAtmIfVpcIndex,
      mscAtmIfVpcSrcIndex }
::= { mscAtmIfVpcSrcProvTable 1 }

MscAtmIfVpcSrcProvEntry ::= SEQUENCE {
   mscAtmIfVpcSrcCallingAddress
      HexString,
   mscAtmIfVpcSrcCalledAddress
      HexString,
   mscAtmIfVpcSrcCalledVpi
      Unsigned32 }

mscAtmIfVpcSrcCallingAddress OBJECT-TYPE
   SYNTAX     HexString (SIZE (0..20))
   ACCESS     read-write
   STATUS     mandatory
   DESCRIPTION
     "This attribute specifies the calling address of the soft PVP. If it is a 
      null string, then the calling address is the address of the current 
      interface (that is, where the soft PVC originates)."
   DEFVAL     { ''H }  -- ""
::= { mscAtmIfVpcSrcProvEntry 1 }

mscAtmIfVpcSrcCalledAddress OBJECT-TYPE
   SYNTAX     HexString (SIZE (20))
   ACCESS     read-write
   STATUS     mandatory
   DESCRIPTION
     "This attribute specifies the called (remote) address of the soft PVP."
::= { mscAtmIfVpcSrcProvEntry 2 }

mscAtmIfVpcSrcCalledVpi OBJECT-TYPE
   SYNTAX     Unsigned32 (1..4095)
   ACCESS     read-write
   STATUS     mandatory
   DESCRIPTION
     "This attribute specifies the called VPI of the soft PVP."
::= { mscAtmIfVpcSrcProvEntry 3 }

mscAtmIfVpcSrcOperTable OBJECT-TYPE
   SYNTAX     SEQUENCE OF MscAtmIfVpcSrcOperEntry
   ACCESS     not-accessible
   STATUS     mandatory
   DESCRIPTION
     "This attribute group contains the operational attributes associated 
      with the SrcPvp or SrcPvc component."
::= { mscAtmIfVpcSrc 11 }

mscAtmIfVpcSrcOperEntry OBJECT-TYPE
   SYNTAX     MscAtmIfVpcSrcOperEntry
   ACCESS     not-accessible
   STATUS     mandatory
   DESCRIPTION
     "An entry in the mscAtmIfVpcSrcOperTable."
   INDEX {
      mscAtmIfIndex,
      mscAtmIfVpcIndex,
      mscAtmIfVpcSrcIndex }
::= { mscAtmIfVpcSrcOperTable 1 }

MscAtmIfVpcSrcOperEntry ::= SEQUENCE {
   mscAtmIfVpcSrcState
      INTEGER,
   mscAtmIfVpcSrcRetryCount
      Counter32,
   mscAtmIfVpcSrcLastFailureCauseCode
      Unsigned32,
   mscAtmIfVpcSrcLastFailureDiagCode
      AsciiString }

mscAtmIfVpcSrcState OBJECT-TYPE
   SYNTAX     INTEGER  {
                 active(0),
                 inactive(1) }
   ACCESS     read-only
   STATUS     mandatory
   DESCRIPTION
     "This attribute indicates the state of the soft PVP or soft PVC."
::= { mscAtmIfVpcSrcOperEntry 1 }

mscAtmIfVpcSrcRetryCount OBJECT-TYPE
   SYNTAX     Counter32 
   ACCESS     read-only
   STATUS     mandatory
   DESCRIPTION
     "This attribute indicates the number of failed attempts to set up the 
      soft PVP or soft PVC since the last time the connection failed."
::= { mscAtmIfVpcSrcOperEntry 2 }

mscAtmIfVpcSrcLastFailureCauseCode OBJECT-TYPE
   SYNTAX     Unsigned32 (0..255)
   ACCESS     read-only
   STATUS     mandatory
   DESCRIPTION
     "This attribute contains the cause code in the last transmitted 
      signalling message that contains the CAUSE information element. 
      The cause code is used to describe the reason for generating certain 
      signalling messages. 
      The default value for this attribute is set to 0."
::= { mscAtmIfVpcSrcOperEntry 3 }

mscAtmIfVpcSrcLastFailureDiagCode OBJECT-TYPE
   SYNTAX     AsciiString (SIZE (0..8))
   ACCESS     read-only
   STATUS     mandatory
   DESCRIPTION
     "This attribute contains the diagnostic code in the last transmitted 
      signalling message. The diagnostic code is contained in the CAUSE 
      information element and identifies an information element type or 
      timer type. The diagnostic code is present only if a procedural error 
      is detected by the signalling protocol. A diagnostic code is always 
      accompanied by the cause code. If there is no failure, this attribute 
      is set to NULL."
::= { mscAtmIfVpcSrcOperEntry 4 }


-- AtmIf/n Vpc/vpi Rp
-- AtmIf/n Vcc/vpi.vci Rp
-- AtmIf/n Vpt/vpi Vcc/vci Rp
-- 
-- The RelayPoint component is used to establish a single hop of a 
-- Switched connection. When linked together, two Rps within a 
-- module, the associated connections are configured to relay ATM 
-- cells to one another. 

mscAtmIfVpcRp OBJECT IDENTIFIER ::= { mscAtmIfVpc 7 }



mscAtmIfVpcRpRowStatusTable OBJECT-TYPE
   SYNTAX     SEQUENCE OF MscAtmIfVpcRpRowStatusEntry
   ACCESS     not-accessible
   STATUS     mandatory
   DESCRIPTION
     "This entry controls the addition and deletion of 
      mscAtmIfVpcRp components."
::= { mscAtmIfVpcRp 1 }

mscAtmIfVpcRpRowStatusEntry OBJECT-TYPE
   SYNTAX     MscAtmIfVpcRpRowStatusEntry
   ACCESS     not-accessible
   STATUS     mandatory
   DESCRIPTION
     "A single entry in the table represents a single 
      mscAtmIfVpcRp component."
   INDEX {
      mscAtmIfIndex,
      mscAtmIfVpcIndex,
      mscAtmIfVpcRpIndex }
::= { mscAtmIfVpcRpRowStatusTable 1 }

MscAtmIfVpcRpRowStatusEntry ::= SEQUENCE {
   mscAtmIfVpcRpRowStatus
      RowStatus,
   mscAtmIfVpcRpComponentName
      DisplayString,
   mscAtmIfVpcRpStorageType
      StorageType,
   mscAtmIfVpcRpIndex
      NonReplicated }

mscAtmIfVpcRpRowStatus OBJECT-TYPE
   SYNTAX     RowStatus 
   ACCESS     read-only
   STATUS     mandatory
   DESCRIPTION
     "This variable is used as the basis for SNMP naming of
      mscAtmIfVpcRp components.
      These components cannot be added nor deleted."
::= { mscAtmIfVpcRpRowStatusEntry 1 }

mscAtmIfVpcRpComponentName OBJECT-TYPE
   SYNTAX     DisplayString 
   ACCESS     read-only
   STATUS     mandatory
   DESCRIPTION
     "This variable provides the component's string name for
      use with the ASCII Console Interface"
::= { mscAtmIfVpcRpRowStatusEntry 2 }

mscAtmIfVpcRpStorageType OBJECT-TYPE
   SYNTAX     StorageType 
   ACCESS     read-only
   STATUS     mandatory
   DESCRIPTION
     "This variable represents the storage type value for the
      mscAtmIfVpcRp tables."
::= { mscAtmIfVpcRpRowStatusEntry 4 }

mscAtmIfVpcRpIndex OBJECT-TYPE
   SYNTAX     NonReplicated 
   ACCESS     not-accessible
   STATUS     mandatory
   DESCRIPTION
     "This variable represents the index for the mscAtmIfVpcRp tables."
::= { mscAtmIfVpcRpRowStatusEntry 10 }

mscAtmIfVpcRpOperTable OBJECT-TYPE
   SYNTAX     SEQUENCE OF MscAtmIfVpcRpOperEntry
   ACCESS     not-accessible
   STATUS     mandatory
   DESCRIPTION
     "This attribute group contains the operational attributes for the 
      AtmRelayPoint component."
::= { mscAtmIfVpcRp 10 }

mscAtmIfVpcRpOperEntry OBJECT-TYPE
   SYNTAX     MscAtmIfVpcRpOperEntry
   ACCESS     not-accessible
   STATUS     mandatory
   DESCRIPTION
     "An entry in the mscAtmIfVpcRpOperTable."
   INDEX {
      mscAtmIfIndex,
      mscAtmIfVpcIndex,
      mscAtmIfVpcRpIndex }
::= { mscAtmIfVpcRpOperTable 1 }

MscAtmIfVpcRpOperEntry ::= SEQUENCE {
   mscAtmIfVpcRpNextHop
      RowPointer }

mscAtmIfVpcRpNextHop OBJECT-TYPE
   SYNTAX     RowPointer 
   ACCESS     read-only
   STATUS     obsolete
   DESCRIPTION
     "This attribute indicates the component name of the Rp component 
      with which this Rp component is associated."
::= { mscAtmIfVpcRpOperEntry 1 }

mscAtmIfVpcRpNextHopsTable OBJECT-TYPE
   SYNTAX     SEQUENCE OF MscAtmIfVpcRpNextHopsEntry
   ACCESS     not-accessible
   STATUS     mandatory
   DESCRIPTION
     "This attribute indicates the component name(s) of the Rp 
      component(s) with which this Rp component is associated. This 
      attribute can have more than one component name only when the 
      Vcc distributionType is pointToMultipoint and the callDirection is 
      fromLink."
::= { mscAtmIfVpcRp 430 }

mscAtmIfVpcRpNextHopsEntry OBJECT-TYPE
   SYNTAX     MscAtmIfVpcRpNextHopsEntry
   ACCESS     not-accessible
   STATUS     mandatory
   DESCRIPTION
     "An entry in the mscAtmIfVpcRpNextHopsTable."
   INDEX {
      mscAtmIfIndex,
      mscAtmIfVpcIndex,
      mscAtmIfVpcRpIndex,
      mscAtmIfVpcRpNextHopsValue }
::= { mscAtmIfVpcRpNextHopsTable 1 }

MscAtmIfVpcRpNextHopsEntry ::= SEQUENCE {
   mscAtmIfVpcRpNextHopsValue
      RowPointer }

mscAtmIfVpcRpNextHopsValue OBJECT-TYPE
   SYNTAX     RowPointer 
   ACCESS     read-only
   STATUS     mandatory
   DESCRIPTION
     "This variable represents both the value and the index for the
      mscAtmIfVpcRpNextHopsTable."
::= { mscAtmIfVpcRpNextHopsEntry 1 }


-- AtmIf/n Vpc/vpi DestinationPvp
-- This component represents the destination end of a soft PVP.

mscAtmIfVpcDst OBJECT IDENTIFIER ::= { mscAtmIfVpc 8 }



mscAtmIfVpcDstRowStatusTable OBJECT-TYPE
   SYNTAX     SEQUENCE OF MscAtmIfVpcDstRowStatusEntry
   ACCESS     not-accessible
   STATUS     mandatory
   DESCRIPTION
     "This entry controls the addition and deletion of 
      mscAtmIfVpcDst components."
::= { mscAtmIfVpcDst 1 }

mscAtmIfVpcDstRowStatusEntry OBJECT-TYPE
   SYNTAX     MscAtmIfVpcDstRowStatusEntry
   ACCESS     not-accessible
   STATUS     mandatory
   DESCRIPTION
     "A single entry in the table represents a single 
      mscAtmIfVpcDst component."
   INDEX {
      mscAtmIfIndex,
      mscAtmIfVpcIndex,
      mscAtmIfVpcDstIndex }
::= { mscAtmIfVpcDstRowStatusTable 1 }

MscAtmIfVpcDstRowStatusEntry ::= SEQUENCE {
   mscAtmIfVpcDstRowStatus
      RowStatus,
   mscAtmIfVpcDstComponentName
      DisplayString,
   mscAtmIfVpcDstStorageType
      StorageType,
   mscAtmIfVpcDstIndex
      NonReplicated }

mscAtmIfVpcDstRowStatus OBJECT-TYPE
   SYNTAX     RowStatus 
   ACCESS     read-only
   STATUS     mandatory
   DESCRIPTION
     "This variable is used as the basis for SNMP naming of
      mscAtmIfVpcDst components.
      These components cannot be added nor deleted."
::= { mscAtmIfVpcDstRowStatusEntry 1 }

mscAtmIfVpcDstComponentName OBJECT-TYPE
   SYNTAX     DisplayString 
   ACCESS     read-only
   STATUS     mandatory
   DESCRIPTION
     "This variable provides the component's string name for
      use with the ASCII Console Interface"
::= { mscAtmIfVpcDstRowStatusEntry 2 }

mscAtmIfVpcDstStorageType OBJECT-TYPE
   SYNTAX     StorageType 
   ACCESS     read-only
   STATUS     mandatory
   DESCRIPTION
     "This variable represents the storage type value for the
      mscAtmIfVpcDst tables."
::= { mscAtmIfVpcDstRowStatusEntry 4 }

mscAtmIfVpcDstIndex OBJECT-TYPE
   SYNTAX     NonReplicated 
   ACCESS     not-accessible
   STATUS     mandatory
   DESCRIPTION
     "This variable represents the index for the mscAtmIfVpcDst tables."
::= { mscAtmIfVpcDstRowStatusEntry 10 }

mscAtmIfVpcDstOperTable OBJECT-TYPE
   SYNTAX     SEQUENCE OF MscAtmIfVpcDstOperEntry
   ACCESS     not-accessible
   STATUS     mandatory
   DESCRIPTION
     "This attribute group contains the operational attributes for the 
      AtmIf/n Vpc/vpi DstPvp component."
::= { mscAtmIfVpcDst 10 }

mscAtmIfVpcDstOperEntry OBJECT-TYPE
   SYNTAX     MscAtmIfVpcDstOperEntry
   ACCESS     not-accessible
   STATUS     mandatory
   DESCRIPTION
     "An entry in the mscAtmIfVpcDstOperTable."
   INDEX {
      mscAtmIfIndex,
      mscAtmIfVpcIndex,
      mscAtmIfVpcDstIndex }
::= { mscAtmIfVpcDstOperTable 1 }

MscAtmIfVpcDstOperEntry ::= SEQUENCE {
   mscAtmIfVpcDstCalledAddress
      HexString,
   mscAtmIfVpcDstCallingAddress
      AsciiString,
   mscAtmIfVpcDstCallingVpi
      AsciiString }

mscAtmIfVpcDstCalledAddress OBJECT-TYPE
   SYNTAX     HexString (SIZE (20))
   ACCESS     read-only
   STATUS     mandatory
   DESCRIPTION
     "This attribute indicates the called address of the soft PVP."
::= { mscAtmIfVpcDstOperEntry 1 }

mscAtmIfVpcDstCallingAddress OBJECT-TYPE
   SYNTAX     AsciiString (SIZE (7..40))
   ACCESS     read-only
   STATUS     mandatory
   DESCRIPTION
     "This attribute indicates the calling (remote) address of the soft PVP. 
      If the address in not known, then the value of this address is 
      Unknown."
::= { mscAtmIfVpcDstOperEntry 2 }

mscAtmIfVpcDstCallingVpi OBJECT-TYPE
   SYNTAX     AsciiString (SIZE (1..7))
   ACCESS     read-only
   STATUS     mandatory
   DESCRIPTION
     "This attribute represents the calling (remote) VPI of the soft PVP. If 
      the VPI value is not known, the attribute value is set to Unknown."
::= { mscAtmIfVpcDstOperEntry 3 }


-- AtmIf/n Vcc/vpi.vci SrcPvc
-- AtmIf/n Vpt/vpi Vcc/vci SrcPvc
-- 
-- This component represents the source end of a soft PVC.

mscAtmIfVccSrc OBJECT IDENTIFIER ::= { mscAtmIfVcc 8 }



mscAtmIfVccSrcRowStatusTable OBJECT-TYPE
   SYNTAX     SEQUENCE OF MscAtmIfVccSrcRowStatusEntry
   ACCESS     not-accessible
   STATUS     mandatory
   DESCRIPTION
     "This entry controls the addition and deletion of 
      mscAtmIfVccSrc components."
::= { mscAtmIfVccSrc 1 }

mscAtmIfVccSrcRowStatusEntry OBJECT-TYPE
   SYNTAX     MscAtmIfVccSrcRowStatusEntry
   ACCESS     not-accessible
   STATUS     mandatory
   DESCRIPTION
     "A single entry in the table represents a single 
      mscAtmIfVccSrc component."
   INDEX {
      mscAtmIfIndex,
      mscAtmIfVccIndex,
      mscAtmIfVccSrcIndex }
::= { mscAtmIfVccSrcRowStatusTable 1 }

MscAtmIfVccSrcRowStatusEntry ::= SEQUENCE {
   mscAtmIfVccSrcRowStatus
      RowStatus,
   mscAtmIfVccSrcComponentName
      DisplayString,
   mscAtmIfVccSrcStorageType
      StorageType,
   mscAtmIfVccSrcIndex
      NonReplicated }

mscAtmIfVccSrcRowStatus OBJECT-TYPE
   SYNTAX     RowStatus 
   ACCESS     read-write
   STATUS     mandatory
   DESCRIPTION
     "This variable is used as the basis for SNMP naming of
      mscAtmIfVccSrc components.
      These components can be added and deleted."
::= { mscAtmIfVccSrcRowStatusEntry 1 }

mscAtmIfVccSrcComponentName OBJECT-TYPE
   SYNTAX     DisplayString 
   ACCESS     read-only
   STATUS     mandatory
   DESCRIPTION
     "This variable provides the component's string name for
      use with the ASCII Console Interface"
::= { mscAtmIfVccSrcRowStatusEntry 2 }

mscAtmIfVccSrcStorageType OBJECT-TYPE
   SYNTAX     StorageType 
   ACCESS     read-only
   STATUS     mandatory
   DESCRIPTION
     "This variable represents the storage type value for the
      mscAtmIfVccSrc tables."
::= { mscAtmIfVccSrcRowStatusEntry 4 }

mscAtmIfVccSrcIndex OBJECT-TYPE
   SYNTAX     NonReplicated 
   ACCESS     not-accessible
   STATUS     mandatory
   DESCRIPTION
     "This variable represents the index for the mscAtmIfVccSrc tables."
::= { mscAtmIfVccSrcRowStatusEntry 10 }

mscAtmIfVccSrcProvTable OBJECT-TYPE
   SYNTAX     SEQUENCE OF MscAtmIfVccSrcProvEntry
   ACCESS     not-accessible
   STATUS     mandatory
   DESCRIPTION
     "This attribute group contains the provisionable attributes of the 
      SourcePvc component."
::= { mscAtmIfVccSrc 10 }

mscAtmIfVccSrcProvEntry OBJECT-TYPE
   SYNTAX     MscAtmIfVccSrcProvEntry
   ACCESS     not-accessible
   STATUS     mandatory
   DESCRIPTION
     "An entry in the mscAtmIfVccSrcProvTable."
   INDEX {
      mscAtmIfIndex,
      mscAtmIfVccIndex,
      mscAtmIfVccSrcIndex }
::= { mscAtmIfVccSrcProvTable 1 }

MscAtmIfVccSrcProvEntry ::= SEQUENCE {
   mscAtmIfVccSrcRemoteAddress
      HexString,
   mscAtmIfVccSrcRemoteVpiVci
      IntegerSequence,
   mscAtmIfVccSrcCallingAddress
      HexString,
   mscAtmIfVccSrcCalledAddress
      HexString,
   mscAtmIfVccSrcCalledVpiVci
      IntegerSequence }

mscAtmIfVccSrcRemoteAddress OBJECT-TYPE
   SYNTAX     HexString (SIZE (20))
   ACCESS     read-write
   STATUS     obsolete
   DESCRIPTION
     "This attribute represents the remote address of the soft PVC."
::= { mscAtmIfVccSrcProvEntry 1 }

mscAtmIfVccSrcRemoteVpiVci OBJECT-TYPE
   SYNTAX     IntegerSequence (SIZE (3..9))
   ACCESS     read-write
   STATUS     obsolete
   DESCRIPTION
     "This attribute represents the remote VPI and VCI of the soft PVC."
::= { mscAtmIfVccSrcProvEntry 2 }

mscAtmIfVccSrcCallingAddress OBJECT-TYPE
   SYNTAX     HexString (SIZE (0..20))
   ACCESS     read-write
   STATUS     mandatory
   DESCRIPTION
     "This attribute represents the calling address of the soft PVC. If it is 
      a null string, then the calling address is the address of the current 
      interface (that is, where the soft PVC originates)."
   DEFVAL     { ''H }  -- ""
::= { mscAtmIfVccSrcProvEntry 3 }

mscAtmIfVccSrcCalledAddress OBJECT-TYPE
   SYNTAX     HexString (SIZE (20))
   ACCESS     read-write
   STATUS     mandatory
   DESCRIPTION
     "This attribute represents the called (remote) address of the soft 
      PVC."
::= { mscAtmIfVccSrcProvEntry 4 }

mscAtmIfVccSrcCalledVpiVci OBJECT-TYPE
   SYNTAX     IntegerSequence (SIZE (3..10))
   ACCESS     read-write
   STATUS     mandatory
   DESCRIPTION
     "This attribute represents the remote VPI and VCI of the soft PVC."
::= { mscAtmIfVccSrcProvEntry 5 }

mscAtmIfVccSrcOperTable OBJECT-TYPE
   SYNTAX     SEQUENCE OF MscAtmIfVccSrcOperEntry
   ACCESS     not-accessible
   STATUS     mandatory
   DESCRIPTION
     "This attribute group contains the operational attributes associated 
      with the SrcPvp or SrcPvc component."
::= { mscAtmIfVccSrc 11 }

mscAtmIfVccSrcOperEntry OBJECT-TYPE
   SYNTAX     MscAtmIfVccSrcOperEntry
   ACCESS     not-accessible
   STATUS     mandatory
   DESCRIPTION
     "An entry in the mscAtmIfVccSrcOperTable."
   INDEX {
      mscAtmIfIndex,
      mscAtmIfVccIndex,
      mscAtmIfVccSrcIndex }
::= { mscAtmIfVccSrcOperTable 1 }

MscAtmIfVccSrcOperEntry ::= SEQUENCE {
   mscAtmIfVccSrcState
      INTEGER,
   mscAtmIfVccSrcRetryCount
      Counter32,
   mscAtmIfVccSrcLastFailureCauseCode
      Unsigned32,
   mscAtmIfVccSrcLastFailureDiagCode
      AsciiString }

mscAtmIfVccSrcState OBJECT-TYPE
   SYNTAX     INTEGER  {
                 active(0),
                 inactive(1) }
   ACCESS     read-only
   STATUS     mandatory
   DESCRIPTION
     "This attribute indicates the state of the soft PVP or soft PVC."
::= { mscAtmIfVccSrcOperEntry 1 }

mscAtmIfVccSrcRetryCount OBJECT-TYPE
   SYNTAX     Counter32 
   ACCESS     read-only
   STATUS     mandatory
   DESCRIPTION
     "This attribute indicates the number of failed attempts to set up the 
      soft PVP or soft PVC since the last time the connection failed."
::= { mscAtmIfVccSrcOperEntry 2 }

mscAtmIfVccSrcLastFailureCauseCode OBJECT-TYPE
   SYNTAX     Unsigned32 (0..255)
   ACCESS     read-only
   STATUS     mandatory
   DESCRIPTION
     "This attribute contains the cause code in the last transmitted 
      signalling message that contains the CAUSE information element. 
      The cause code is used to describe the reason for generating certain 
      signalling messages. 
      The default value for this attribute is set to 0."
::= { mscAtmIfVccSrcOperEntry 3 }

mscAtmIfVccSrcLastFailureDiagCode OBJECT-TYPE
   SYNTAX     AsciiString (SIZE (0..8))
   ACCESS     read-only
   STATUS     mandatory
   DESCRIPTION
     "This attribute contains the diagnostic code in the last transmitted 
      signalling message. The diagnostic code is contained in the CAUSE 
      information element and identifies an information element type or 
      timer type. The diagnostic code is present only if a procedural error 
      is detected by the signalling protocol. A diagnostic code is always 
      accompanied by the cause code. If there is no failure, this attribute 
      is set to NULL."
::= { mscAtmIfVccSrcOperEntry 4 }


-- AtmIf/n Vcc/vpi.vci Ep
-- AtmIf/n Vpt/vpi Vcc/vci Ep
-- 
-- The EndPoint component of the application associated with the 
-- VCC is used to link a switched VCC to an application that sends 
-- and receives frames using the connection. 

mscAtmIfVccEp OBJECT IDENTIFIER ::= { mscAtmIfVcc 9 }



mscAtmIfVccEpRowStatusTable OBJECT-TYPE
   SYNTAX     SEQUENCE OF MscAtmIfVccEpRowStatusEntry
   ACCESS     not-accessible
   STATUS     mandatory
   DESCRIPTION
     "This entry controls the addition and deletion of 
      mscAtmIfVccEp components."
::= { mscAtmIfVccEp 1 }

mscAtmIfVccEpRowStatusEntry OBJECT-TYPE
   SYNTAX     MscAtmIfVccEpRowStatusEntry
   ACCESS     not-accessible
   STATUS     mandatory
   DESCRIPTION
     "A single entry in the table represents a single 
      mscAtmIfVccEp component."
   INDEX {
      mscAtmIfIndex,
      mscAtmIfVccIndex,
      mscAtmIfVccEpIndex }
::= { mscAtmIfVccEpRowStatusTable 1 }

MscAtmIfVccEpRowStatusEntry ::= SEQUENCE {
   mscAtmIfVccEpRowStatus
      RowStatus,
   mscAtmIfVccEpComponentName
      DisplayString,
   mscAtmIfVccEpStorageType
      StorageType,
   mscAtmIfVccEpIndex
      NonReplicated }

mscAtmIfVccEpRowStatus OBJECT-TYPE
   SYNTAX     RowStatus 
   ACCESS     read-only
   STATUS     mandatory
   DESCRIPTION
     "This variable is used as the basis for SNMP naming of
      mscAtmIfVccEp components.
      These components cannot be added nor deleted."
::= { mscAtmIfVccEpRowStatusEntry 1 }

mscAtmIfVccEpComponentName OBJECT-TYPE
   SYNTAX     DisplayString 
   ACCESS     read-only
   STATUS     mandatory
   DESCRIPTION
     "This variable provides the component's string name for
      use with the ASCII Console Interface"
::= { mscAtmIfVccEpRowStatusEntry 2 }

mscAtmIfVccEpStorageType OBJECT-TYPE
   SYNTAX     StorageType 
   ACCESS     read-only
   STATUS     mandatory
   DESCRIPTION
     "This variable represents the storage type value for the
      mscAtmIfVccEp tables."
::= { mscAtmIfVccEpRowStatusEntry 4 }

mscAtmIfVccEpIndex OBJECT-TYPE
   SYNTAX     NonReplicated 
   ACCESS     not-accessible
   STATUS     mandatory
   DESCRIPTION
     "This variable represents the index for the mscAtmIfVccEp tables."
::= { mscAtmIfVccEpRowStatusEntry 10 }

mscAtmIfVccEpOperTable OBJECT-TYPE
   SYNTAX     SEQUENCE OF MscAtmIfVccEpOperEntry
   ACCESS     not-accessible
   STATUS     mandatory
   DESCRIPTION
     "This attribute group contains the operational attributes for the 
      AtmEndPoint component."
::= { mscAtmIfVccEp 10 }

mscAtmIfVccEpOperEntry OBJECT-TYPE
   SYNTAX     MscAtmIfVccEpOperEntry
   ACCESS     not-accessible
   STATUS     mandatory
   DESCRIPTION
     "An entry in the mscAtmIfVccEpOperTable."
   INDEX {
      mscAtmIfIndex,
      mscAtmIfVccIndex,
      mscAtmIfVccEpIndex }
::= { mscAtmIfVccEpOperTable 1 }

MscAtmIfVccEpOperEntry ::= SEQUENCE {
   mscAtmIfVccEpApplicationName
      RowPointer }

mscAtmIfVccEpApplicationName OBJECT-TYPE
   SYNTAX     RowPointer 
   ACCESS     read-only
   STATUS     mandatory
   DESCRIPTION
     "This attribute indicates the component name associated with the 
      application associated with the switched VCC."
::= { mscAtmIfVccEpOperEntry 1 }


-- AtmIf/n Vpc/vpi Rp
-- AtmIf/n Vcc/vpi.vci Rp
-- AtmIf/n Vpt/vpi Vcc/vci Rp
-- 
-- The RelayPoint component is used to establish a single hop of a 
-- Switched connection. When linked together, two Rps within a 
-- module, the associated connections are configured to relay ATM 
-- cells to one another. 

mscAtmIfVccRp OBJECT IDENTIFIER ::= { mscAtmIfVcc 10 }



mscAtmIfVccRpRowStatusTable OBJECT-TYPE
   SYNTAX     SEQUENCE OF MscAtmIfVccRpRowStatusEntry
   ACCESS     not-accessible
   STATUS     mandatory
   DESCRIPTION
     "This entry controls the addition and deletion of 
      mscAtmIfVccRp components."
::= { mscAtmIfVccRp 1 }

mscAtmIfVccRpRowStatusEntry OBJECT-TYPE
   SYNTAX     MscAtmIfVccRpRowStatusEntry
   ACCESS     not-accessible
   STATUS     mandatory
   DESCRIPTION
     "A single entry in the table represents a single 
      mscAtmIfVccRp component."
   INDEX {
      mscAtmIfIndex,
      mscAtmIfVccIndex,
      mscAtmIfVccRpIndex }
::= { mscAtmIfVccRpRowStatusTable 1 }

MscAtmIfVccRpRowStatusEntry ::= SEQUENCE {
   mscAtmIfVccRpRowStatus
      RowStatus,
   mscAtmIfVccRpComponentName
      DisplayString,
   mscAtmIfVccRpStorageType
      StorageType,
   mscAtmIfVccRpIndex
      NonReplicated }

mscAtmIfVccRpRowStatus OBJECT-TYPE
   SYNTAX     RowStatus 
   ACCESS     read-only
   STATUS     mandatory
   DESCRIPTION
     "This variable is used as the basis for SNMP naming of
      mscAtmIfVccRp components.
      These components cannot be added nor deleted."
::= { mscAtmIfVccRpRowStatusEntry 1 }

mscAtmIfVccRpComponentName OBJECT-TYPE
   SYNTAX     DisplayString 
   ACCESS     read-only
   STATUS     mandatory
   DESCRIPTION
     "This variable provides the component's string name for
      use with the ASCII Console Interface"
::= { mscAtmIfVccRpRowStatusEntry 2 }

mscAtmIfVccRpStorageType OBJECT-TYPE
   SYNTAX     StorageType 
   ACCESS     read-only
   STATUS     mandatory
   DESCRIPTION
     "This variable represents the storage type value for the
      mscAtmIfVccRp tables."
::= { mscAtmIfVccRpRowStatusEntry 4 }

mscAtmIfVccRpIndex OBJECT-TYPE
   SYNTAX     NonReplicated 
   ACCESS     not-accessible
   STATUS     mandatory
   DESCRIPTION
     "This variable represents the index for the mscAtmIfVccRp tables."
::= { mscAtmIfVccRpRowStatusEntry 10 }

mscAtmIfVccRpOperTable OBJECT-TYPE
   SYNTAX     SEQUENCE OF MscAtmIfVccRpOperEntry
   ACCESS     not-accessible
   STATUS     mandatory
   DESCRIPTION
     "This attribute group contains the operational attributes for the 
      AtmRelayPoint component."
::= { mscAtmIfVccRp 10 }

mscAtmIfVccRpOperEntry OBJECT-TYPE
   SYNTAX     MscAtmIfVccRpOperEntry
   ACCESS     not-accessible
   STATUS     mandatory
   DESCRIPTION
     "An entry in the mscAtmIfVccRpOperTable."
   INDEX {
      mscAtmIfIndex,
      mscAtmIfVccIndex,
      mscAtmIfVccRpIndex }
::= { mscAtmIfVccRpOperTable 1 }

MscAtmIfVccRpOperEntry ::= SEQUENCE {
   mscAtmIfVccRpNextHop
      RowPointer }

mscAtmIfVccRpNextHop OBJECT-TYPE
   SYNTAX     RowPointer 
   ACCESS     read-only
   STATUS     obsolete
   DESCRIPTION
     "This attribute indicates the component name of the Rp component 
      with which this Rp component is associated."
::= { mscAtmIfVccRpOperEntry 1 }

mscAtmIfVccRpNextHopsTable OBJECT-TYPE
   SYNTAX     SEQUENCE OF MscAtmIfVccRpNextHopsEntry
   ACCESS     not-accessible
   STATUS     mandatory
   DESCRIPTION
     "This attribute indicates the component name(s) of the Rp 
      component(s) with which this Rp component is associated. This 
      attribute can have more than one component name only when the 
      Vcc distributionType is pointToMultipoint and the callDirection is 
      fromLink."
::= { mscAtmIfVccRp 430 }

mscAtmIfVccRpNextHopsEntry OBJECT-TYPE
   SYNTAX     MscAtmIfVccRpNextHopsEntry
   ACCESS     not-accessible
   STATUS     mandatory
   DESCRIPTION
     "An entry in the mscAtmIfVccRpNextHopsTable."
   INDEX {
      mscAtmIfIndex,
      mscAtmIfVccIndex,
      mscAtmIfVccRpIndex,
      mscAtmIfVccRpNextHopsValue }
::= { mscAtmIfVccRpNextHopsTable 1 }

MscAtmIfVccRpNextHopsEntry ::= SEQUENCE {
   mscAtmIfVccRpNextHopsValue
      RowPointer }

mscAtmIfVccRpNextHopsValue OBJECT-TYPE
   SYNTAX     RowPointer 
   ACCESS     read-only
   STATUS     mandatory
   DESCRIPTION
     "This variable represents both the value and the index for the
      mscAtmIfVccRpNextHopsTable."
::= { mscAtmIfVccRpNextHopsEntry 1 }


-- AtmIf/n Vcc/vpi.vci DstPvc
-- AtmIf/n Vpt/vpi Vcc/vci DstPvc
-- 
-- This component represents the destination end of a soft PVC.

mscAtmIfVccDst OBJECT IDENTIFIER ::= { mscAtmIfVcc 11 }



mscAtmIfVccDstRowStatusTable OBJECT-TYPE
   SYNTAX     SEQUENCE OF MscAtmIfVccDstRowStatusEntry
   ACCESS     not-accessible
   STATUS     mandatory
   DESCRIPTION
     "This entry controls the addition and deletion of 
      mscAtmIfVccDst components."
::= { mscAtmIfVccDst 1 }

mscAtmIfVccDstRowStatusEntry OBJECT-TYPE
   SYNTAX     MscAtmIfVccDstRowStatusEntry
   ACCESS     not-accessible
   STATUS     mandatory
   DESCRIPTION
     "A single entry in the table represents a single 
      mscAtmIfVccDst component."
   INDEX {
      mscAtmIfIndex,
      mscAtmIfVccIndex,
      mscAtmIfVccDstIndex }
::= { mscAtmIfVccDstRowStatusTable 1 }

MscAtmIfVccDstRowStatusEntry ::= SEQUENCE {
   mscAtmIfVccDstRowStatus
      RowStatus,
   mscAtmIfVccDstComponentName
      DisplayString,
   mscAtmIfVccDstStorageType
      StorageType,
   mscAtmIfVccDstIndex
      NonReplicated }

mscAtmIfVccDstRowStatus OBJECT-TYPE
   SYNTAX     RowStatus 
   ACCESS     read-only
   STATUS     mandatory
   DESCRIPTION
     "This variable is used as the basis for SNMP naming of
      mscAtmIfVccDst components.
      These components cannot be added nor deleted."
::= { mscAtmIfVccDstRowStatusEntry 1 }

mscAtmIfVccDstComponentName OBJECT-TYPE
   SYNTAX     DisplayString 
   ACCESS     read-only
   STATUS     mandatory
   DESCRIPTION
     "This variable provides the component's string name for
      use with the ASCII Console Interface"
::= { mscAtmIfVccDstRowStatusEntry 2 }

mscAtmIfVccDstStorageType OBJECT-TYPE
   SYNTAX     StorageType 
   ACCESS     read-only
   STATUS     mandatory
   DESCRIPTION
     "This variable represents the storage type value for the
      mscAtmIfVccDst tables."
::= { mscAtmIfVccDstRowStatusEntry 4 }

mscAtmIfVccDstIndex OBJECT-TYPE
   SYNTAX     NonReplicated 
   ACCESS     not-accessible
   STATUS     mandatory
   DESCRIPTION
     "This variable represents the index for the mscAtmIfVccDst tables."
::= { mscAtmIfVccDstRowStatusEntry 10 }

mscAtmIfVccDstOperTable OBJECT-TYPE
   SYNTAX     SEQUENCE OF MscAtmIfVccDstOperEntry
   ACCESS     not-accessible
   STATUS     mandatory
   DESCRIPTION
     "This attribute group contains the operational attributes for the 
      DestinationPvc component."
::= { mscAtmIfVccDst 10 }

mscAtmIfVccDstOperEntry OBJECT-TYPE
   SYNTAX     MscAtmIfVccDstOperEntry
   ACCESS     not-accessible
   STATUS     mandatory
   DESCRIPTION
     "An entry in the mscAtmIfVccDstOperTable."
   INDEX {
      mscAtmIfIndex,
      mscAtmIfVccIndex,
      mscAtmIfVccDstIndex }
::= { mscAtmIfVccDstOperTable 1 }

MscAtmIfVccDstOperEntry ::= SEQUENCE {
   mscAtmIfVccDstCalledAddress
      HexString,
   mscAtmIfVccDstCallingAddress
      AsciiString,
   mscAtmIfVccDstCallingVpiVci
      AsciiString }

mscAtmIfVccDstCalledAddress OBJECT-TYPE
   SYNTAX     HexString (SIZE (20))
   ACCESS     read-only
   STATUS     mandatory
   DESCRIPTION
     "This attribute represents the called address of the soft PVC."
::= { mscAtmIfVccDstOperEntry 3 }

mscAtmIfVccDstCallingAddress OBJECT-TYPE
   SYNTAX     AsciiString (SIZE (7..40))
   ACCESS     read-only
   STATUS     mandatory
   DESCRIPTION
     "This attribute represents the remote address of the soft PVC. If the 
      address in not known, then the value of this address is Unknown."
::= { mscAtmIfVccDstOperEntry 4 }

mscAtmIfVccDstCallingVpiVci OBJECT-TYPE
   SYNTAX     AsciiString (SIZE (7..9))
   ACCESS     read-only
   STATUS     mandatory
   DESCRIPTION
     "This attribute represents the remote VPI and VCI of the soft PVC. If 
      the VPI and VCI values are not known, this attribute is set to 
      Unknown."
::= { mscAtmIfVccDstOperEntry 5 }


-- AtmIf/n Vcc/vpi.vci SrcPvc
-- AtmIf/n Vpt/vpi Vcc/vci SrcPvc
-- 
-- This component represents the source end of a soft PVC.

mscAtmIfVptVccSrc OBJECT IDENTIFIER ::= { mscAtmIfVptVcc 8 }



mscAtmIfVptVccSrcRowStatusTable OBJECT-TYPE
   SYNTAX     SEQUENCE OF MscAtmIfVptVccSrcRowStatusEntry
   ACCESS     not-accessible
   STATUS     mandatory
   DESCRIPTION
     "This entry controls the addition and deletion of 
      mscAtmIfVptVccSrc components."
::= { mscAtmIfVptVccSrc 1 }

mscAtmIfVptVccSrcRowStatusEntry OBJECT-TYPE
   SYNTAX     MscAtmIfVptVccSrcRowStatusEntry
   ACCESS     not-accessible
   STATUS     mandatory
   DESCRIPTION
     "A single entry in the table represents a single 
      mscAtmIfVptVccSrc component."
   INDEX {
      mscAtmIfIndex,
      mscAtmIfVptIndex,
      mscAtmIfVptVccIndex,
      mscAtmIfVptVccSrcIndex }
::= { mscAtmIfVptVccSrcRowStatusTable 1 }

MscAtmIfVptVccSrcRowStatusEntry ::= SEQUENCE {
   mscAtmIfVptVccSrcRowStatus
      RowStatus,
   mscAtmIfVptVccSrcComponentName
      DisplayString,
   mscAtmIfVptVccSrcStorageType
      StorageType,
   mscAtmIfVptVccSrcIndex
      NonReplicated }

mscAtmIfVptVccSrcRowStatus OBJECT-TYPE
   SYNTAX     RowStatus 
   ACCESS     read-write
   STATUS     mandatory
   DESCRIPTION
     "This variable is used as the basis for SNMP naming of
      mscAtmIfVptVccSrc components.
      These components can be added and deleted."
::= { mscAtmIfVptVccSrcRowStatusEntry 1 }

mscAtmIfVptVccSrcComponentName OBJECT-TYPE
   SYNTAX     DisplayString 
   ACCESS     read-only
   STATUS     mandatory
   DESCRIPTION
     "This variable provides the component's string name for
      use with the ASCII Console Interface"
::= { mscAtmIfVptVccSrcRowStatusEntry 2 }

mscAtmIfVptVccSrcStorageType OBJECT-TYPE
   SYNTAX     StorageType 
   ACCESS     read-only
   STATUS     mandatory
   DESCRIPTION
     "This variable represents the storage type value for the
      mscAtmIfVptVccSrc tables."
::= { mscAtmIfVptVccSrcRowStatusEntry 4 }

mscAtmIfVptVccSrcIndex OBJECT-TYPE
   SYNTAX     NonReplicated 
   ACCESS     not-accessible
   STATUS     mandatory
   DESCRIPTION
     "This variable represents the index for the mscAtmIfVptVccSrc tables."
::= { mscAtmIfVptVccSrcRowStatusEntry 10 }

mscAtmIfVptVccSrcProvTable OBJECT-TYPE
   SYNTAX     SEQUENCE OF MscAtmIfVptVccSrcProvEntry
   ACCESS     not-accessible
   STATUS     mandatory
   DESCRIPTION
     "This attribute group contains the provisionable attributes of the 
      SourcePvc component."
::= { mscAtmIfVptVccSrc 10 }

mscAtmIfVptVccSrcProvEntry OBJECT-TYPE
   SYNTAX     MscAtmIfVptVccSrcProvEntry
   ACCESS     not-accessible
   STATUS     mandatory
   DESCRIPTION
     "An entry in the mscAtmIfVptVccSrcProvTable."
   INDEX {
      mscAtmIfIndex,
      mscAtmIfVptIndex,
      mscAtmIfVptVccIndex,
      mscAtmIfVptVccSrcIndex }
::= { mscAtmIfVptVccSrcProvTable 1 }

MscAtmIfVptVccSrcProvEntry ::= SEQUENCE {
   mscAtmIfVptVccSrcRemoteAddress
      HexString,
   mscAtmIfVptVccSrcRemoteVpiVci
      IntegerSequence,
   mscAtmIfVptVccSrcCallingAddress
      HexString,
   mscAtmIfVptVccSrcCalledAddress
      HexString,
   mscAtmIfVptVccSrcCalledVpiVci
      IntegerSequence }

mscAtmIfVptVccSrcRemoteAddress OBJECT-TYPE
   SYNTAX     HexString (SIZE (20))
   ACCESS     read-write
   STATUS     obsolete
   DESCRIPTION
     "This attribute represents the remote address of the soft PVC."
::= { mscAtmIfVptVccSrcProvEntry 1 }

mscAtmIfVptVccSrcRemoteVpiVci OBJECT-TYPE
   SYNTAX     IntegerSequence (SIZE (3..9))
   ACCESS     read-write
   STATUS     obsolete
   DESCRIPTION
     "This attribute represents the remote VPI and VCI of the soft PVC."
::= { mscAtmIfVptVccSrcProvEntry 2 }

mscAtmIfVptVccSrcCallingAddress OBJECT-TYPE
   SYNTAX     HexString (SIZE (0..20))
   ACCESS     read-write
   STATUS     mandatory
   DESCRIPTION
     "This attribute represents the calling address of the soft PVC. If it is 
      a null string, then the calling address is the address of the current 
      interface (that is, where the soft PVC originates)."
   DEFVAL     { ''H }  -- ""
::= { mscAtmIfVptVccSrcProvEntry 3 }

mscAtmIfVptVccSrcCalledAddress OBJECT-TYPE
   SYNTAX     HexString (SIZE (20))
   ACCESS     read-write
   STATUS     mandatory
   DESCRIPTION
     "This attribute represents the called (remote) address of the soft 
      PVC."
::= { mscAtmIfVptVccSrcProvEntry 4 }

mscAtmIfVptVccSrcCalledVpiVci OBJECT-TYPE
   SYNTAX     IntegerSequence (SIZE (3..10))
   ACCESS     read-write
   STATUS     mandatory
   DESCRIPTION
     "This attribute represents the remote VPI and VCI of the soft PVC."
::= { mscAtmIfVptVccSrcProvEntry 5 }

mscAtmIfVptVccSrcOperTable OBJECT-TYPE
   SYNTAX     SEQUENCE OF MscAtmIfVptVccSrcOperEntry
   ACCESS     not-accessible
   STATUS     mandatory
   DESCRIPTION
     "This attribute group contains the operational attributes associated 
      with the SrcPvp or SrcPvc component."
::= { mscAtmIfVptVccSrc 11 }

mscAtmIfVptVccSrcOperEntry OBJECT-TYPE
   SYNTAX     MscAtmIfVptVccSrcOperEntry
   ACCESS     not-accessible
   STATUS     mandatory
   DESCRIPTION
     "An entry in the mscAtmIfVptVccSrcOperTable."
   INDEX {
      mscAtmIfIndex,
      mscAtmIfVptIndex,
      mscAtmIfVptVccIndex,
      mscAtmIfVptVccSrcIndex }
::= { mscAtmIfVptVccSrcOperTable 1 }

MscAtmIfVptVccSrcOperEntry ::= SEQUENCE {
   mscAtmIfVptVccSrcState
      INTEGER,
   mscAtmIfVptVccSrcRetryCount
      Counter32,
   mscAtmIfVptVccSrcLastFailureCauseCode
      Unsigned32,
   mscAtmIfVptVccSrcLastFailureDiagCode
      AsciiString }

mscAtmIfVptVccSrcState OBJECT-TYPE
   SYNTAX     INTEGER  {
                 active(0),
                 inactive(1) }
   ACCESS     read-only
   STATUS     mandatory
   DESCRIPTION
     "This attribute indicates the state of the soft PVP or soft PVC."
::= { mscAtmIfVptVccSrcOperEntry 1 }

mscAtmIfVptVccSrcRetryCount OBJECT-TYPE
   SYNTAX     Counter32 
   ACCESS     read-only
   STATUS     mandatory
   DESCRIPTION
     "This attribute indicates the number of failed attempts to set up the 
      soft PVP or soft PVC since the last time the connection failed."
::= { mscAtmIfVptVccSrcOperEntry 2 }

mscAtmIfVptVccSrcLastFailureCauseCode OBJECT-TYPE
   SYNTAX     Unsigned32 (0..255)
   ACCESS     read-only
   STATUS     mandatory
   DESCRIPTION
     "This attribute contains the cause code in the last transmitted 
      signalling message that contains the CAUSE information element. 
      The cause code is used to describe the reason for generating certain 
      signalling messages. 
      The default value for this attribute is set to 0."
::= { mscAtmIfVptVccSrcOperEntry 3 }

mscAtmIfVptVccSrcLastFailureDiagCode OBJECT-TYPE
   SYNTAX     AsciiString (SIZE (0..8))
   ACCESS     read-only
   STATUS     mandatory
   DESCRIPTION
     "This attribute contains the diagnostic code in the last transmitted 
      signalling message. The diagnostic code is contained in the CAUSE 
      information element and identifies an information element type or 
      timer type. The diagnostic code is present only if a procedural error 
      is detected by the signalling protocol. A diagnostic code is always 
      accompanied by the cause code. If there is no failure, this attribute 
      is set to NULL."
::= { mscAtmIfVptVccSrcOperEntry 4 }


-- AtmIf/n Vcc/vpi.vci Ep
-- AtmIf/n Vpt/vpi Vcc/vci Ep
-- 
-- The EndPoint component of the application associated with the 
-- VCC is used to link a switched VCC to an application that sends 
-- and receives frames using the connection. 

mscAtmIfVptVccEp OBJECT IDENTIFIER ::= { mscAtmIfVptVcc 9 }



mscAtmIfVptVccEpRowStatusTable OBJECT-TYPE
   SYNTAX     SEQUENCE OF MscAtmIfVptVccEpRowStatusEntry
   ACCESS     not-accessible
   STATUS     mandatory
   DESCRIPTION
     "This entry controls the addition and deletion of 
      mscAtmIfVptVccEp components."
::= { mscAtmIfVptVccEp 1 }

mscAtmIfVptVccEpRowStatusEntry OBJECT-TYPE
   SYNTAX     MscAtmIfVptVccEpRowStatusEntry
   ACCESS     not-accessible
   STATUS     mandatory
   DESCRIPTION
     "A single entry in the table represents a single 
      mscAtmIfVptVccEp component."
   INDEX {
      mscAtmIfIndex,
      mscAtmIfVptIndex,
      mscAtmIfVptVccIndex,
      mscAtmIfVptVccEpIndex }
::= { mscAtmIfVptVccEpRowStatusTable 1 }

MscAtmIfVptVccEpRowStatusEntry ::= SEQUENCE {
   mscAtmIfVptVccEpRowStatus
      RowStatus,
   mscAtmIfVptVccEpComponentName
      DisplayString,
   mscAtmIfVptVccEpStorageType
      StorageType,
   mscAtmIfVptVccEpIndex
      NonReplicated }

mscAtmIfVptVccEpRowStatus OBJECT-TYPE
   SYNTAX     RowStatus 
   ACCESS     read-only
   STATUS     mandatory
   DESCRIPTION
     "This variable is used as the basis for SNMP naming of
      mscAtmIfVptVccEp components.
      These components cannot be added nor deleted."
::= { mscAtmIfVptVccEpRowStatusEntry 1 }

mscAtmIfVptVccEpComponentName OBJECT-TYPE
   SYNTAX     DisplayString 
   ACCESS     read-only
   STATUS     mandatory
   DESCRIPTION
     "This variable provides the component's string name for
      use with the ASCII Console Interface"
::= { mscAtmIfVptVccEpRowStatusEntry 2 }

mscAtmIfVptVccEpStorageType OBJECT-TYPE
   SYNTAX     StorageType 
   ACCESS     read-only
   STATUS     mandatory
   DESCRIPTION
     "This variable represents the storage type value for the
      mscAtmIfVptVccEp tables."
::= { mscAtmIfVptVccEpRowStatusEntry 4 }

mscAtmIfVptVccEpIndex OBJECT-TYPE
   SYNTAX     NonReplicated 
   ACCESS     not-accessible
   STATUS     mandatory
   DESCRIPTION
     "This variable represents the index for the mscAtmIfVptVccEp tables."
::= { mscAtmIfVptVccEpRowStatusEntry 10 }

mscAtmIfVptVccEpOperTable OBJECT-TYPE
   SYNTAX     SEQUENCE OF MscAtmIfVptVccEpOperEntry
   ACCESS     not-accessible
   STATUS     mandatory
   DESCRIPTION
     "This attribute group contains the operational attributes for the 
      AtmEndPoint component."
::= { mscAtmIfVptVccEp 10 }

mscAtmIfVptVccEpOperEntry OBJECT-TYPE
   SYNTAX     MscAtmIfVptVccEpOperEntry
   ACCESS     not-accessible
   STATUS     mandatory
   DESCRIPTION
     "An entry in the mscAtmIfVptVccEpOperTable."
   INDEX {
      mscAtmIfIndex,
      mscAtmIfVptIndex,
      mscAtmIfVptVccIndex,
      mscAtmIfVptVccEpIndex }
::= { mscAtmIfVptVccEpOperTable 1 }

MscAtmIfVptVccEpOperEntry ::= SEQUENCE {
   mscAtmIfVptVccEpApplicationName
      RowPointer }

mscAtmIfVptVccEpApplicationName OBJECT-TYPE
   SYNTAX     RowPointer 
   ACCESS     read-only
   STATUS     mandatory
   DESCRIPTION
     "This attribute indicates the component name associated with the 
      application associated with the switched VCC."
::= { mscAtmIfVptVccEpOperEntry 1 }


-- AtmIf/n Vpc/vpi Rp
-- AtmIf/n Vcc/vpi.vci Rp
-- AtmIf/n Vpt/vpi Vcc/vci Rp
-- 
-- The RelayPoint component is used to establish a single hop of a 
-- Switched connection. When linked together, two Rps within a 
-- module, the associated connections are configured to relay ATM 
-- cells to one another. 

mscAtmIfVptVccRp OBJECT IDENTIFIER ::= { mscAtmIfVptVcc 10 }



mscAtmIfVptVccRpRowStatusTable OBJECT-TYPE
   SYNTAX     SEQUENCE OF MscAtmIfVptVccRpRowStatusEntry
   ACCESS     not-accessible
   STATUS     mandatory
   DESCRIPTION
     "This entry controls the addition and deletion of 
      mscAtmIfVptVccRp components."
::= { mscAtmIfVptVccRp 1 }

mscAtmIfVptVccRpRowStatusEntry OBJECT-TYPE
   SYNTAX     MscAtmIfVptVccRpRowStatusEntry
   ACCESS     not-accessible
   STATUS     mandatory
   DESCRIPTION
     "A single entry in the table represents a single 
      mscAtmIfVptVccRp component."
   INDEX {
      mscAtmIfIndex,
      mscAtmIfVptIndex,
      mscAtmIfVptVccIndex,
      mscAtmIfVptVccRpIndex }
::= { mscAtmIfVptVccRpRowStatusTable 1 }

MscAtmIfVptVccRpRowStatusEntry ::= SEQUENCE {
   mscAtmIfVptVccRpRowStatus
      RowStatus,
   mscAtmIfVptVccRpComponentName
      DisplayString,
   mscAtmIfVptVccRpStorageType
      StorageType,
   mscAtmIfVptVccRpIndex
      NonReplicated }

mscAtmIfVptVccRpRowStatus OBJECT-TYPE
   SYNTAX     RowStatus 
   ACCESS     read-only
   STATUS     mandatory
   DESCRIPTION
     "This variable is used as the basis for SNMP naming of
      mscAtmIfVptVccRp components.
      These components cannot be added nor deleted."
::= { mscAtmIfVptVccRpRowStatusEntry 1 }

mscAtmIfVptVccRpComponentName OBJECT-TYPE
   SYNTAX     DisplayString 
   ACCESS     read-only
   STATUS     mandatory
   DESCRIPTION
     "This variable provides the component's string name for
      use with the ASCII Console Interface"
::= { mscAtmIfVptVccRpRowStatusEntry 2 }

mscAtmIfVptVccRpStorageType OBJECT-TYPE
   SYNTAX     StorageType 
   ACCESS     read-only
   STATUS     mandatory
   DESCRIPTION
     "This variable represents the storage type value for the
      mscAtmIfVptVccRp tables."
::= { mscAtmIfVptVccRpRowStatusEntry 4 }

mscAtmIfVptVccRpIndex OBJECT-TYPE
   SYNTAX     NonReplicated 
   ACCESS     not-accessible
   STATUS     mandatory
   DESCRIPTION
     "This variable represents the index for the mscAtmIfVptVccRp tables."
::= { mscAtmIfVptVccRpRowStatusEntry 10 }

mscAtmIfVptVccRpOperTable OBJECT-TYPE
   SYNTAX     SEQUENCE OF MscAtmIfVptVccRpOperEntry
   ACCESS     not-accessible
   STATUS     mandatory
   DESCRIPTION
     "This attribute group contains the operational attributes for the 
      AtmRelayPoint component."
::= { mscAtmIfVptVccRp 10 }

mscAtmIfVptVccRpOperEntry OBJECT-TYPE
   SYNTAX     MscAtmIfVptVccRpOperEntry
   ACCESS     not-accessible
   STATUS     mandatory
   DESCRIPTION
     "An entry in the mscAtmIfVptVccRpOperTable."
   INDEX {
      mscAtmIfIndex,
      mscAtmIfVptIndex,
      mscAtmIfVptVccIndex,
      mscAtmIfVptVccRpIndex }
::= { mscAtmIfVptVccRpOperTable 1 }

MscAtmIfVptVccRpOperEntry ::= SEQUENCE {
   mscAtmIfVptVccRpNextHop
      RowPointer }

mscAtmIfVptVccRpNextHop OBJECT-TYPE
   SYNTAX     RowPointer 
   ACCESS     read-only
   STATUS     obsolete
   DESCRIPTION
     "This attribute indicates the component name of the Rp component 
      with which this Rp component is associated."
::= { mscAtmIfVptVccRpOperEntry 1 }

mscAtmIfVptVccRpNextHopsTable OBJECT-TYPE
   SYNTAX     SEQUENCE OF MscAtmIfVptVccRpNextHopsEntry
   ACCESS     not-accessible
   STATUS     mandatory
   DESCRIPTION
     "This attribute indicates the component name(s) of the Rp 
      component(s) with which this Rp component is associated. This 
      attribute can have more than one component name only when the 
      Vcc distributionType is pointToMultipoint and the callDirection is 
      fromLink."
::= { mscAtmIfVptVccRp 430 }

mscAtmIfVptVccRpNextHopsEntry OBJECT-TYPE
   SYNTAX     MscAtmIfVptVccRpNextHopsEntry
   ACCESS     not-accessible
   STATUS     mandatory
   DESCRIPTION
     "An entry in the mscAtmIfVptVccRpNextHopsTable."
   INDEX {
      mscAtmIfIndex,
      mscAtmIfVptIndex,
      mscAtmIfVptVccIndex,
      mscAtmIfVptVccRpIndex,
      mscAtmIfVptVccRpNextHopsValue }
::= { mscAtmIfVptVccRpNextHopsTable 1 }

MscAtmIfVptVccRpNextHopsEntry ::= SEQUENCE {
   mscAtmIfVptVccRpNextHopsValue
      RowPointer }

mscAtmIfVptVccRpNextHopsValue OBJECT-TYPE
   SYNTAX     RowPointer 
   ACCESS     read-only
   STATUS     mandatory
   DESCRIPTION
     "This variable represents both the value and the index for the
      mscAtmIfVptVccRpNextHopsTable."
::= { mscAtmIfVptVccRpNextHopsEntry 1 }


-- AtmIf/n Vcc/vpi.vci DstPvc
-- AtmIf/n Vpt/vpi Vcc/vci DstPvc
-- 
-- This component represents the destination end of a soft PVC.

mscAtmIfVptVccDst OBJECT IDENTIFIER ::= { mscAtmIfVptVcc 11 }



mscAtmIfVptVccDstRowStatusTable OBJECT-TYPE
   SYNTAX     SEQUENCE OF MscAtmIfVptVccDstRowStatusEntry
   ACCESS     not-accessible
   STATUS     mandatory
   DESCRIPTION
     "This entry controls the addition and deletion of 
      mscAtmIfVptVccDst components."
::= { mscAtmIfVptVccDst 1 }

mscAtmIfVptVccDstRowStatusEntry OBJECT-TYPE
   SYNTAX     MscAtmIfVptVccDstRowStatusEntry
   ACCESS     not-accessible
   STATUS     mandatory
   DESCRIPTION
     "A single entry in the table represents a single 
      mscAtmIfVptVccDst component."
   INDEX {
      mscAtmIfIndex,
      mscAtmIfVptIndex,
      mscAtmIfVptVccIndex,
      mscAtmIfVptVccDstIndex }
::= { mscAtmIfVptVccDstRowStatusTable 1 }

MscAtmIfVptVccDstRowStatusEntry ::= SEQUENCE {
   mscAtmIfVptVccDstRowStatus
      RowStatus,
   mscAtmIfVptVccDstComponentName
      DisplayString,
   mscAtmIfVptVccDstStorageType
      StorageType,
   mscAtmIfVptVccDstIndex
      NonReplicated }

mscAtmIfVptVccDstRowStatus OBJECT-TYPE
   SYNTAX     RowStatus 
   ACCESS     read-only
   STATUS     mandatory
   DESCRIPTION
     "This variable is used as the basis for SNMP naming of
      mscAtmIfVptVccDst components.
      These components cannot be added nor deleted."
::= { mscAtmIfVptVccDstRowStatusEntry 1 }

mscAtmIfVptVccDstComponentName OBJECT-TYPE
   SYNTAX     DisplayString 
   ACCESS     read-only
   STATUS     mandatory
   DESCRIPTION
     "This variable provides the component's string name for
      use with the ASCII Console Interface"
::= { mscAtmIfVptVccDstRowStatusEntry 2 }

mscAtmIfVptVccDstStorageType OBJECT-TYPE
   SYNTAX     StorageType 
   ACCESS     read-only
   STATUS     mandatory
   DESCRIPTION
     "This variable represents the storage type value for the
      mscAtmIfVptVccDst tables."
::= { mscAtmIfVptVccDstRowStatusEntry 4 }

mscAtmIfVptVccDstIndex OBJECT-TYPE
   SYNTAX     NonReplicated 
   ACCESS     not-accessible
   STATUS     mandatory
   DESCRIPTION
     "This variable represents the index for the mscAtmIfVptVccDst tables."
::= { mscAtmIfVptVccDstRowStatusEntry 10 }

mscAtmIfVptVccDstOperTable OBJECT-TYPE
   SYNTAX     SEQUENCE OF MscAtmIfVptVccDstOperEntry
   ACCESS     not-accessible
   STATUS     mandatory
   DESCRIPTION
     "This attribute group contains the operational attributes for the 
      DestinationPvc component."
::= { mscAtmIfVptVccDst 10 }

mscAtmIfVptVccDstOperEntry OBJECT-TYPE
   SYNTAX     MscAtmIfVptVccDstOperEntry
   ACCESS     not-accessible
   STATUS     mandatory
   DESCRIPTION
     "An entry in the mscAtmIfVptVccDstOperTable."
   INDEX {
      mscAtmIfIndex,
      mscAtmIfVptIndex,
      mscAtmIfVptVccIndex,
      mscAtmIfVptVccDstIndex }
::= { mscAtmIfVptVccDstOperTable 1 }

MscAtmIfVptVccDstOperEntry ::= SEQUENCE {
   mscAtmIfVptVccDstCalledAddress
      HexString,
   mscAtmIfVptVccDstCallingAddress
      AsciiString,
   mscAtmIfVptVccDstCallingVpiVci
      AsciiString }

mscAtmIfVptVccDstCalledAddress OBJECT-TYPE
   SYNTAX     HexString (SIZE (20))
   ACCESS     read-only
   STATUS     mandatory
   DESCRIPTION
     "This attribute represents the called address of the soft PVC."
::= { mscAtmIfVptVccDstOperEntry 3 }

mscAtmIfVptVccDstCallingAddress OBJECT-TYPE
   SYNTAX     AsciiString (SIZE (7..40))
   ACCESS     read-only
   STATUS     mandatory
   DESCRIPTION
     "This attribute represents the remote address of the soft PVC. If the 
      address in not known, then the value of this address is Unknown."
::= { mscAtmIfVptVccDstOperEntry 4 }

mscAtmIfVptVccDstCallingVpiVci OBJECT-TYPE
   SYNTAX     AsciiString (SIZE (7..9))
   ACCESS     read-only
   STATUS     mandatory
   DESCRIPTION
     "This attribute represents the remote VPI and VCI of the soft PVC. If 
      the VPI and VCI values are not known, this attribute is set to 
      Unknown."
::= { mscAtmIfVptVccDstOperEntry 5 }




-- 
-- Version and Compliance statements
-- 



-- Object-Group Statement:
-- A list of all current accessible leaf objects.

-- OBJECTS { mscARtgComponentName,
--           mscARtgPnniCfgNodeNbrRccListValue,
--           mscARtgPnniTopPtsesInDatabase,
--           mscAtmIfVccSrcCalledVpiVci,
--           mscAtmIfVpcSrcRowStatus,
--           mscAtmIfVptVccRpRowStatus,
--           mscARtgPnniRfFwdQosClass,
--           mscARtgPnniTopComponentName,
--           mscARtgPnniCfgNodeNbrComponentName,
--           mscAtmIfVptVccSrcState,
--           mscAtmIfVccEpRowStatus,
--           mscARtgPnniCfgNodeSAddrRowStatus,
--           mscARtgFailedRoutingAttempts,
--           mscARtgPnniRfStorageType,
--           mscARtgPnniComponentName,
--           mscARtgDnaDestInfoStdComponentName,
--           mscARtgPnniTopNodeLinkStorageType,
--           mscARtgPnniCfgNodeNbrBadPtseRx,
--           mscARtgPnniCfgNodeStorageType,
--           mscAtmIfVpcSrcState,
--           mscARtgPnniRfFqpValue,
--           mscAtmIfVccSrcLastFailureCauseCode,
--           mscARtgPnniTopNodeLinkRemoteNodeId,
--           mscARtgPnniCfgNodeNbrRowStatus,
--           mscARtgPnniCfgNodeNbrBadPtspRx,
--           mscAtmIfVpcRpRowStatus,
--           mscAtmIfVpcSrcLastFailureCauseCode,
--           mscARtgPnniFailedRoutingAttempts,
--           mscARtgPnniCfgNodeDefSAddrScope,
--           mscARtgPnniHelloHoldDown,
--           mscARtgPnniDomain,
--           mscARtgPnniCfgNodeNbrPtseTx,
--           mscAtmIfVccRpNextHopsValue,
--           mscAtmIfVptVccEpStorageType,
--           mscAtmIfVptVccSrcStorageType,
--           mscARtgPnniRfDestinationAddress,
--           mscAtmIfVptVccDstComponentName,
--           mscARtgPnniPortComponentName,
--           mscARtgDnaDestInfoScope,
--           mscAtmCRDnaStorageType,
--           mscARtgPnniTopNodeLinkRowStatus,
--           mscARtgPnniTopNodeAddrComponentName,
--           mscARtgPnniTopNodeComponentName,
--           mscARtgPnniCfgNodeRowStatus,
--           mscARtgPnniRfTransferCapabilityBbc,
--           mscARtgPnniPortStorageType,
--           mscAtmIfVptVccSrcComponentName,
--           mscARtgPnniCfgNodeNbrBadDbSummariesRx,
--           mscARtgPnniTopActiveParentNodeId,
--           mscAtmIfVpcDstCallingAddress,
--           mscAtmIfVccRpComponentName,
--           mscARtgPnniNodeAddressPrefix,
--           mscAtmIfVpcSrcCallingAddress,
--           mscARtgPnniRfTxTdpValue,
--           mscAtmIfVpcSrcCalledVpi,
--           mscARtgPnniPeerDelayedAckInterval,
--           mscARtgPnniCfgNodeNodeAddress,
--           mscARtgPnniCfgNodeNodeId,
--           mscAtmIfVccDstCallingVpiVci,
--           mscAtmIfVccDstStorageType,
--           mscAtmIfVpcDstComponentName,
--           mscARtgPnniCfgNodeNbrPtseRx,
--           mscAtmIfVccDstCalledAddress,
--           mscARtgRoutingAttempts,
--           mscARtgPnniPtseHoldDown,
--           mscARtgPnniCfgNodeNbrStorageType,
--           mscARtgPnniRfBwdQosClass,
--           mscAtmCRDnaRowStatus,
--           mscARtgPnniCfgNodeNbrPtseReqTx,
--           mscAtmIfVpcDstCalledAddress,
--           mscARtgDnaComponentName,
--           mscARtgPnniStorageType,
--           mscARtgPnniCfgNodePeerGroupId,
--           mscARtgPnniPortRowStatus,
--           mscAtmIfVptVccDstCalledAddress,
--           mscAtmIfVptVccSrcRetryCount,
--           mscAtmIfVptVccSrcCallingAddress,
--           mscARtgPnniRfClippingBbc,
--           mscARtgPnniSuccessfulRoutingAttempts,
--           mscARtgPnniDefaultScope,
--           mscAtmIfVptVccDstRowStatus,
--           mscARtgPnniRfBqpValue,
--           mscAtmIfVptVccRpStorageType,
--           mscARtgRowStatus,
--           mscARtgPnniRfBestEffort,
--           mscARtgPnniRfRxTdpValue,
--           mscAtmIfVptVccSrcLastFailureDiagCode,
--           mscAtmIfVpcRpNextHopsValue,
--           mscARtgPnniOverrideDelay,
--           mscARtgPnniCfgNodeDefSAddrState,
--           mscARtgPnniMaxAlternateRoutesOnCrankback,
--           mscARtgPnniCfgNodeOpNodeId,
--           mscARtgPnniTopRowStatus,
--           mscAtmIfVpcSrcCalledAddress,
--           mscARtgPnniRowStatus,
--           mscARtgPnniCfgNodeNbrPtseReqRx,
--           mscARtgPnniTopNodeAddrStorageType,
--           mscARtgPnniTopNodeStorageType,
--           mscAtmIfVptVccEpRowStatus,
--           mscARtgPnniAlternateRoutingAttempts,
--           mscARtgPnniPortStdComponentName,
--           mscARtgPnniRfAtmServiceCategory,
--           mscARtgDnaDestInfoComponentName,
--           mscAtmIfVpcSrcComponentName,
--           mscAtmIfVpcRpStorageType,
--           mscAtmIfVccDstComponentName,
--           mscARtgPnniCfgNodeSAddrScope,
--           mscARtgPnniCfgNodeNumRccs,
--           mscARtgPnniCfgNodeOpPeerGroupId,
--           mscARtgPnniCfgNodeNbrDbSummariesTx,
--           mscAtmIfVptVccRpNextHopsValue,
--           mscARtgPnniCfgNodeDefSAddrStorageType,
--           mscAtmIfVccRpRowStatus,
--           mscARtgPnniCfgNodeNbrBadPtseAckRx,
--           mscARtgPnniCfgNodeDefSAddrAddress,
--           mscARtgPnniRfOptimizationMetric,
--           mscAtmCRComponentName,
--           mscARtgPnniAvcrMt,
--           mscARtgPnniCfgNodeCurrentLeadershipPriority,
--           mscARtgPnniPglInitTime,
--           mscAtmIfVptVccDstStorageType,
--           mscARtgPnniTopNodeAddrRowStatus,
--           mscARtgDnaStorageType,
--           mscARtgPnniCfgNodeDefSAddrComponentName,
--           mscAtmIfVptVccSrcLastFailureCauseCode,
--           mscARtgPnniRfTxTrafficDescType,
--           mscARtgPnniTopPglNodeId,
--           mscAtmCRStorageType,
--           mscAtmIfVccSrcState,
--           mscARtgPnniCfgNodeSAddrComponentName,
--           mscAtmIfVpcSrcLastFailureDiagCode,
--           mscAtmIfVptVccDstCallingVpiVci,
--           mscAtmIfVccSrcComponentName,
--           mscAtmIfVccEpApplicationName,
--           mscAtmIfVptVccRpComponentName,
--           mscAtmIfVccSrcCalledAddress,
--           mscARtgPnniRfMaxRoutes,
--           mscARtgStorageType,
--           mscAtmIfVccDstRowStatus,
--           mscARtgPnniRfRowStatus,
--           mscARtgPnniCfgNodeSAddrSuppress,
--           mscARtgPnniRequestRxmtInterval,
--           mscARtgPnniCfgNodeNbrDbSummariesRx,
--           mscARtgPnniCfgNodeNbrPtseAcksTx,
--           mscAtmIfVccEpComponentName,
--           mscARtgPnniCfgNodeNbrBadPtseReqRx,
--           mscARtgPnniHelloInactivityFactor,
--           mscARtgPnniHelloInterval,
--           mscARtgPnniTopNodeRowStatus,
--           mscARtgPnniCfgNodeNbrPtspTx,
--           mscARtgPnniPtseRefreshInterval,
--           mscARtgPnniRestrictTransit,
--           mscARtgDnaRowStatus,
--           mscAtmIfVccSrcStorageType,
--           mscARtgPnniAvcrPm,
--           mscAtmIfVptVccEpComponentName,
--           mscARtgPnniRfRxTrafficDescType,
--           mscARtgPnniCfgNodeNumNeighbors,
--           mscARtgPnniRfComponentName,
--           mscARtgDnaDestInfoStorageType,
--           mscAtmIfVpcSrcStorageType,
--           mscARtgPnniTopNodeLinkComponentName,
--           mscARtgPnniCfgNodeSAddrState,
--           mscARtgPnniCfgNodeComponentName,
--           mscAtmIfVccSrcCallingAddress,
--           mscAtmIfVpcDstRowStatus,
--           mscARtgPnniTopNodeLinkRemotePortId,
--           mscARtgPnniTopologyMemoryExhaustion,
--           mscARtgDnaDestInfoType,
--           mscARtgPnniTopPreferredPglNodeId,
--           mscAtmIfVpcDstCallingVpi,
--           mscARtgPnniCfgNodeNbrPtseAcksRx,
--           mscARtgPnniRfBearerClassBbc,
--           mscARtgDnaDestInfoReachability,
--           mscAtmIfVpcDstStorageType,
--           mscARtgPnniTopStorageType,
--           mscAtmIfVptVccSrcRowStatus,
--           mscARtgPnniCfgNodeNbrPtspRx,
--           mscARtgPnniTopNodeAddrScope,
--           mscAtmIfVptVccEpApplicationName,
--           mscAtmIfVptVccSrcCalledVpiVci,
--           mscAtmIfVccSrcLastFailureDiagCode,
--           mscAtmIfVccSrcRetryCount,
--           mscARtgDnaDestInfoRowStatus,
--           mscARtgPnniCfgNodeSAddrStorageType,
--           mscAtmIfVccSrcRowStatus,
--           mscARtgPnniCfgNodeNbrPeerState,
--           mscAtmIfVpcRpComponentName,
--           mscARtgPnniReElectionInterval,
--           mscARtgPnniOptMetricValue,
--           mscARtgPnniPtseLifetimeFactor,
--           mscAtmIfVpcSrcRetryCount,
--           mscAtmIfVccRpStorageType,
--           mscARtgPnniCfgNodeDefSAddrRowStatus,
--           mscARtgPnniCfgNodePglElectionState,
--           mscAtmIfVptVccDstCallingAddress,
--           mscAtmIfVptVccSrcCalledAddress,
--           mscAtmIfVccEpStorageType,
--           mscAtmCRDnaComponentName,
--           mscAtmCRRowStatus,
--           mscAtmIfVccDstCallingAddress }
-- STATUS  mandatory
-- DESCRIPTION
--   "A list of all current accessible leaf objects."

atmNetworkingGroup OBJECT IDENTIFIER ::= { atmNetworkingMIB 1 }
atmNetworkingGroupCA OBJECT IDENTIFIER ::= { atmNetworkingGroup 1 }
atmNetworkingGroupCA02 OBJECT IDENTIFIER ::= { atmNetworkingGroupCA 3 }
atmNetworkingGroupCA02A OBJECT IDENTIFIER ::= { atmNetworkingGroupCA02 2 }



-- Agent-Capabilities Statement:

-- PRODUCT-RELEASE "MscPassport Release 1.2 AtmNetworking."
-- STATUS          mandatory
-- DESCRIPTION     "Carrier Passport AtmNetworking MIB: MIB Version CA02A,
--                  Software Version CA02S9C."
-- SUPPORTS        Nortel-MsCarrier-MscPassport-AtmNetworkingMIB
--    INCLUDES     { atmNetworkingGroupCA02A }

atmNetworkingCapabilities OBJECT IDENTIFIER ::= { atmNetworkingMIB 3 }
atmNetworkingCapabilitiesCA OBJECT IDENTIFIER ::= { atmNetworkingCapabilities 1 }
atmNetworkingCapabilitiesCA02 OBJECT IDENTIFIER ::= { atmNetworkingCapabilitiesCA 3 }
atmNetworkingCapabilitiesCA02A OBJECT IDENTIFIER ::= { atmNetworkingCapabilitiesCA02 2 }





END
