Nortel-MsCarrier-MscPassport-VnetEuroIsdnMIB
DEFINITIONS ::= BEGIN



IMPORTS

      OBJECT-TYPE
   FROM RFC-1212

      mscPassportMIBs
   FROM Nortel-MsCarrier-MscPassport-UsefulDefinitionsMIB

      Counter32,
      DisplayString,
      StorageType,
      RowStatus,
      Gauge32,
      Unsigned32
   FROM Nortel-MsCarrier-MscPassport-StandardTextualConventionsMIB

      NonReplicated,
      Link
   FROM Nortel-MsCarrier-MscPassport-TextualConventionsMIB

      mscSigChan,
      mscSigChanIndex
   FROM Nortel-MsCarrier-MscPassport-VoiceNetworkingMIB;




-- LAST-UPDATED   "9909010000Z"
-- ORGANIZATION   "Nortel Networks"
-- CONTACT-INFO   "
--         Nortel Carrier Data Network Management
--         
--         Postal:       P.O. Box 3511, Station C 
--                       Ottawa, Ontario 
--                       Canada  K1Y 4H7
--         
--         via the WEB:  http://www.nortelnetworks.com  
--                       select 'Contact Us' from the menu
--          
--         via phone:    1-800-4NORTEL"
-- DESCRIPTION
--    "The module describing the Nortel MsCarrier MscPassport
--     VnetEuroIsdn Enterprise MIB."

vnetEuroIsdnMIB OBJECT IDENTIFIER ::= { mscPassportMIBs 138 }










-- SigChan/n EuroIsdn
-- The EuroIsdn component defines the characteristics of the 
-- signalling channel's connection to the external equipment on the 
-- Euro ISDN UNI (ETSI-T Interface).

mscSigChanEIsdn OBJECT IDENTIFIER ::= { mscSigChan 14 }



mscSigChanEIsdnRowStatusTable OBJECT-TYPE
   SYNTAX     SEQUENCE OF MscSigChanEIsdnRowStatusEntry
   ACCESS     not-accessible
   STATUS     mandatory
   DESCRIPTION
     "This entry controls the addition and deletion of 
      mscSigChanEIsdn components."
::= { mscSigChanEIsdn 1 }

mscSigChanEIsdnRowStatusEntry OBJECT-TYPE
   SYNTAX     MscSigChanEIsdnRowStatusEntry
   ACCESS     not-accessible
   STATUS     mandatory
   DESCRIPTION
     "A single entry in the table represents a single 
      mscSigChanEIsdn component."
   INDEX {
      mscSigChanIndex,
      mscSigChanEIsdnIndex }
::= { mscSigChanEIsdnRowStatusTable 1 }

MscSigChanEIsdnRowStatusEntry ::= SEQUENCE {
   mscSigChanEIsdnRowStatus
      RowStatus,
   mscSigChanEIsdnComponentName
      DisplayString,
   mscSigChanEIsdnStorageType
      StorageType,
   mscSigChanEIsdnIndex
      NonReplicated }

mscSigChanEIsdnRowStatus OBJECT-TYPE
   SYNTAX     RowStatus 
   ACCESS     read-write
   STATUS     mandatory
   DESCRIPTION
     "This variable is used as the basis for SNMP naming of
      mscSigChanEIsdn components.
      These components can be added and deleted."
::= { mscSigChanEIsdnRowStatusEntry 1 }

mscSigChanEIsdnComponentName OBJECT-TYPE
   SYNTAX     DisplayString 
   ACCESS     read-only
   STATUS     mandatory
   DESCRIPTION
     "This variable provides the component's string name for
      use with the ASCII Console Interface"
::= { mscSigChanEIsdnRowStatusEntry 2 }

mscSigChanEIsdnStorageType OBJECT-TYPE
   SYNTAX     StorageType 
   ACCESS     read-only
   STATUS     mandatory
   DESCRIPTION
     "This variable represents the storage type value for the
      mscSigChanEIsdn tables."
::= { mscSigChanEIsdnRowStatusEntry 4 }

mscSigChanEIsdnIndex OBJECT-TYPE
   SYNTAX     NonReplicated 
   ACCESS     not-accessible
   STATUS     mandatory
   DESCRIPTION
     "This variable represents the index for the mscSigChanEIsdn tables."
::= { mscSigChanEIsdnRowStatusEntry 10 }

mscSigChanEIsdnL2Table OBJECT-TYPE
   SYNTAX     SEQUENCE OF MscSigChanEIsdnL2Entry
   ACCESS     not-accessible
   STATUS     mandatory
   DESCRIPTION
     "This group specifies the provisionable layer 2 attributes of the Euro 
      ISDN (ETSI-T) protocol."
::= { mscSigChanEIsdn 11 }

mscSigChanEIsdnL2Entry OBJECT-TYPE
   SYNTAX     MscSigChanEIsdnL2Entry
   ACCESS     not-accessible
   STATUS     mandatory
   DESCRIPTION
     "An entry in the mscSigChanEIsdnL2Table."
   INDEX {
      mscSigChanIndex,
      mscSigChanEIsdnIndex }
::= { mscSigChanEIsdnL2Table 1 }

MscSigChanEIsdnL2Entry ::= SEQUENCE {
   mscSigChanEIsdnT23
      Unsigned32,
   mscSigChanEIsdnT200
      Unsigned32,
   mscSigChanEIsdnN200
      Unsigned32,
   mscSigChanEIsdnT203
      Unsigned32,
   mscSigChanEIsdnCircuitSwitchedK
      Unsigned32 }

mscSigChanEIsdnT23 OBJECT-TYPE
   SYNTAX     Unsigned32 (1..15)
   ACCESS     read-write
   STATUS     mandatory
   DESCRIPTION
     "This attribute specifies duration of the layer 2 enable request timer."
   DEFVAL     { 10 }
::= { mscSigChanEIsdnL2Entry 1 }

mscSigChanEIsdnT200 OBJECT-TYPE
   SYNTAX     Unsigned32 (1..20)
   ACCESS     read-write
   STATUS     mandatory
   DESCRIPTION
     "This attribute specifies the maximum elapsed time between a layer 
      2 frame and its acknowledgment."
   DEFVAL     { 1 }
::= { mscSigChanEIsdnL2Entry 2 }

mscSigChanEIsdnN200 OBJECT-TYPE
   SYNTAX     Unsigned32 (1..8)
   ACCESS     read-write
   STATUS     mandatory
   DESCRIPTION
     "This attribute specifies the maximum number of re-transmissions of 
      a layer 2 frame."
   DEFVAL     { 3 }
::= { mscSigChanEIsdnL2Entry 3 }

mscSigChanEIsdnT203 OBJECT-TYPE
   SYNTAX     Unsigned32 (2..40)
   ACCESS     read-write
   STATUS     mandatory
   DESCRIPTION
     "This attribute specifies the maximum time during which layer 2 
      frames may be absent. Expiry triggers a check on whether the far 
      end is alive."
   DEFVAL     { 10 }
::= { mscSigChanEIsdnL2Entry 4 }

mscSigChanEIsdnCircuitSwitchedK OBJECT-TYPE
   SYNTAX     Unsigned32 (1..127)
   ACCESS     read-write
   STATUS     mandatory
   DESCRIPTION
     "This attribute specifies the maximum number of sequentially 
      numbered I frames (that is, window size (k)) that may be 
      unacknowledged at any given time for a SAP supporting primary 
      rate (64kbit/sec) signalling."
   DEFVAL     { 7 }
::= { mscSigChanEIsdnL2Entry 6 }

mscSigChanEIsdnL3Table OBJECT-TYPE
   SYNTAX     SEQUENCE OF MscSigChanEIsdnL3Entry
   ACCESS     not-accessible
   STATUS     mandatory
   DESCRIPTION
     "This group represents the provisionable Layer 3 timer attributes of a 
      the Euro ISDN (ETSI-T) protocol."
::= { mscSigChanEIsdn 12 }

mscSigChanEIsdnL3Entry OBJECT-TYPE
   SYNTAX     MscSigChanEIsdnL3Entry
   ACCESS     not-accessible
   STATUS     mandatory
   DESCRIPTION
     "An entry in the mscSigChanEIsdnL3Table."
   INDEX {
      mscSigChanIndex,
      mscSigChanEIsdnIndex }
::= { mscSigChanEIsdnL3Table 1 }

MscSigChanEIsdnL3Entry ::= SEQUENCE {
   mscSigChanEIsdnT310
      Unsigned32 }

mscSigChanEIsdnT310 OBJECT-TYPE
   SYNTAX     Unsigned32 (10..120)
   ACCESS     read-write
   STATUS     mandatory
   DESCRIPTION
     "This attribute specifies duration of the call proceeding state timer."
   DEFVAL     { 30 }
::= { mscSigChanEIsdnL3Entry 4 }

mscSigChanEIsdnProvTable OBJECT-TYPE
   SYNTAX     SEQUENCE OF MscSigChanEIsdnProvEntry
   ACCESS     not-accessible
   STATUS     mandatory
   DESCRIPTION
     "This group defines the general options of the D-channel signalling 
      link."
::= { mscSigChanEIsdn 13 }

mscSigChanEIsdnProvEntry OBJECT-TYPE
   SYNTAX     MscSigChanEIsdnProvEntry
   ACCESS     not-accessible
   STATUS     mandatory
   DESCRIPTION
     "An entry in the mscSigChanEIsdnProvTable."
   INDEX {
      mscSigChanIndex,
      mscSigChanEIsdnIndex }
::= { mscSigChanEIsdnProvTable 1 }

MscSigChanEIsdnProvEntry ::= SEQUENCE {
   mscSigChanEIsdnSide
      INTEGER,
   mscSigChanEIsdnMaxNonCallConcurrent
      Unsigned32,
   mscSigChanEIsdnOverlapSending
      INTEGER,
   mscSigChanEIsdnOverlapReceiving
      INTEGER }

mscSigChanEIsdnSide OBJECT-TYPE
   SYNTAX     INTEGER  {
                 network(1),
                 user(2) }
   ACCESS     read-write
   STATUS     mandatory
   DESCRIPTION
     "This attribute specifies whether the interface is the network or user 
      side of the connection. The parameter applies to both the layer 2 
      and layer 3 of the interface. In addition, if this attribute is set to 
      network, then the interface is master during channel negotiation. If 
      this attribute is set to user, then the interface is slave during channel 
      negotiation."
   DEFVAL     { network }
::= { mscSigChanEIsdnProvEntry 1 }

mscSigChanEIsdnMaxNonCallConcurrent OBJECT-TYPE
   SYNTAX     Unsigned32 (0..30)
   ACCESS     read-write
   STATUS     mandatory
   DESCRIPTION
     "This attribute specifies the maximum number of simultaneous active 
      non call-associated sessions that are allowed. Reduction of the value 
      does not impact NCAS sessions already in progress."
   DEFVAL     { 30 }
::= { mscSigChanEIsdnProvEntry 2 }

mscSigChanEIsdnOverlapSending OBJECT-TYPE
   SYNTAX     INTEGER  {
                 enabled(0),
                 disabled(1) }
   ACCESS     read-write
   STATUS     mandatory
   DESCRIPTION
     "This attribute specifies whether overlap sending to the PBX is 
      enabled."
   DEFVAL     { enabled }
::= { mscSigChanEIsdnProvEntry 3 }

mscSigChanEIsdnOverlapReceiving OBJECT-TYPE
   SYNTAX     INTEGER  {
                 enabled(0),
                 disabled(1) }
   ACCESS     read-write
   STATUS     mandatory
   DESCRIPTION
     "This attribute specifies whether overlap receiving from the PBX is 
      enabled."
   DEFVAL     { enabled }
::= { mscSigChanEIsdnProvEntry 4 }

mscSigChanEIsdnStateTable OBJECT-TYPE
   SYNTAX     SEQUENCE OF MscSigChanEIsdnStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscSigChanEIsdn 14 }

mscSigChanEIsdnStateEntry OBJECT-TYPE
   SYNTAX     MscSigChanEIsdnStateEntry
   ACCESS     not-accessible
   STATUS     mandatory
   DESCRIPTION
     "An entry in the mscSigChanEIsdnStateTable."
   INDEX {
      mscSigChanIndex,
      mscSigChanEIsdnIndex }
::= { mscSigChanEIsdnStateTable 1 }

MscSigChanEIsdnStateEntry ::= SEQUENCE {
   mscSigChanEIsdnAdminState
      INTEGER,
   mscSigChanEIsdnOperationalState
      INTEGER,
   mscSigChanEIsdnUsageState
      INTEGER }

mscSigChanEIsdnAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscSigChanEIsdnStateEntry 1 }

mscSigChanEIsdnOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscSigChanEIsdnStateEntry 2 }

mscSigChanEIsdnUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscSigChanEIsdnStateEntry 3 }

mscSigChanEIsdnStatsTable OBJECT-TYPE
   SYNTAX     SEQUENCE OF MscSigChanEIsdnStatsEntry
   ACCESS     not-accessible
   STATUS     mandatory
   DESCRIPTION
     "This group provides the statistical attributes for the SigChan/x 
      EuroIsdn component."
::= { mscSigChanEIsdn 15 }

mscSigChanEIsdnStatsEntry OBJECT-TYPE
   SYNTAX     MscSigChanEIsdnStatsEntry
   ACCESS     not-accessible
   STATUS     mandatory
   DESCRIPTION
     "An entry in the mscSigChanEIsdnStatsTable."
   INDEX {
      mscSigChanIndex,
      mscSigChanEIsdnIndex }
::= { mscSigChanEIsdnStatsTable 1 }

MscSigChanEIsdnStatsEntry ::= SEQUENCE {
   mscSigChanEIsdnTotalCallsToIf
      Counter32,
   mscSigChanEIsdnTotalCallsFromIf
      Counter32,
   mscSigChanEIsdnNonCallAssocSessionsToIf
      Counter32,
   mscSigChanEIsdnNonCallAssocSessionsFromIf
      Counter32 }

mscSigChanEIsdnTotalCallsToIf OBJECT-TYPE
   SYNTAX     Counter32 
   ACCESS     read-only
   STATUS     mandatory
   DESCRIPTION
     "This attribute counts the total number of calls that have been made 
      to the interface. The value wraps to zero when it exceeds its 
      maximum."
::= { mscSigChanEIsdnStatsEntry 2 }

mscSigChanEIsdnTotalCallsFromIf OBJECT-TYPE
   SYNTAX     Counter32 
   ACCESS     read-only
   STATUS     mandatory
   DESCRIPTION
     "This attribute counts the total number of calls that have been made 
      from the interface. The value wraps to zero when it exceeds its 
      maximum."
::= { mscSigChanEIsdnStatsEntry 3 }

mscSigChanEIsdnNonCallAssocSessionsToIf OBJECT-TYPE
   SYNTAX     Counter32 
   ACCESS     read-only
   STATUS     mandatory
   DESCRIPTION
     "This attribute counts the total number of non call-associated 
      sessions that have been made to the interface. The value wraps to 
      zero when it exceeds its maximum."
::= { mscSigChanEIsdnStatsEntry 4 }

mscSigChanEIsdnNonCallAssocSessionsFromIf OBJECT-TYPE
   SYNTAX     Counter32 
   ACCESS     read-only
   STATUS     mandatory
   DESCRIPTION
     "This attribute counts the total number of non call-associated 
      sessions that have been made from the interface. The value wraps to 
      zero when it exceeds its maximum."
::= { mscSigChanEIsdnStatsEntry 5 }

mscSigChanEIsdnOperTable OBJECT-TYPE
   SYNTAX     SEQUENCE OF MscSigChanEIsdnOperEntry
   ACCESS     not-accessible
   STATUS     mandatory
   DESCRIPTION
     "This group provides the operational attributes for the SigChan/x 
      EuroIsdn component."
::= { mscSigChanEIsdn 16 }

mscSigChanEIsdnOperEntry OBJECT-TYPE
   SYNTAX     MscSigChanEIsdnOperEntry
   ACCESS     not-accessible
   STATUS     mandatory
   DESCRIPTION
     "An entry in the mscSigChanEIsdnOperTable."
   INDEX {
      mscSigChanIndex,
      mscSigChanEIsdnIndex }
::= { mscSigChanEIsdnOperTable 1 }

MscSigChanEIsdnOperEntry ::= SEQUENCE {
   mscSigChanEIsdnActiveChannels
      Gauge32,
   mscSigChanEIsdnActiveVoiceChannels
      Gauge32,
   mscSigChanEIsdnActiveDataChannels
      Gauge32,
   mscSigChanEIsdnPeakActiveChannels
      Gauge32,
   mscSigChanEIsdnPeakActiveVoiceChannels
      Gauge32,
   mscSigChanEIsdnPeakActiveDataChannels
      Gauge32,
   mscSigChanEIsdnDChanStatus
      INTEGER }

mscSigChanEIsdnActiveChannels OBJECT-TYPE
   SYNTAX     Gauge32 (0..128)
   ACCESS     read-only
   STATUS     mandatory
   DESCRIPTION
     "This attribute indicates the number of currently active channels. 
      This includes channels used by both, data and voice calls."
   DEFVAL     { 0 }
::= { mscSigChanEIsdnOperEntry 1 }

mscSigChanEIsdnActiveVoiceChannels OBJECT-TYPE
   SYNTAX     Gauge32 (0..128)
   ACCESS     read-only
   STATUS     mandatory
   DESCRIPTION
     "This attribute indicates the number of channels that are currently 
      used by voice calls. This includes modem calls."
   DEFVAL     { 0 }
::= { mscSigChanEIsdnOperEntry 2 }

mscSigChanEIsdnActiveDataChannels OBJECT-TYPE
   SYNTAX     Gauge32 (0..128)
   ACCESS     read-only
   STATUS     mandatory
   DESCRIPTION
     "This attribute indicates the number of channels that are currently 
      used by data calls. This does not include modem data."
   DEFVAL     { 0 }
::= { mscSigChanEIsdnOperEntry 3 }

mscSigChanEIsdnPeakActiveChannels OBJECT-TYPE
   SYNTAX     Gauge32 (0..128)
   ACCESS     read-only
   STATUS     mandatory
   DESCRIPTION
     "This attribute indicates the maximum value of the activeChannels 
      attribute during the last polling period."
   DEFVAL     { 0 }
::= { mscSigChanEIsdnOperEntry 4 }

mscSigChanEIsdnPeakActiveVoiceChannels OBJECT-TYPE
   SYNTAX     Gauge32 (0..128)
   ACCESS     read-only
   STATUS     mandatory
   DESCRIPTION
     "This attribute indicates the maximum value of the 
      activeVoiceChannels attribute during the last polling period."
   DEFVAL     { 0 }
::= { mscSigChanEIsdnOperEntry 5 }

mscSigChanEIsdnPeakActiveDataChannels OBJECT-TYPE
   SYNTAX     Gauge32 (0..128)
   ACCESS     read-only
   STATUS     mandatory
   DESCRIPTION
     "This attribute indicates the maximum value of the 
      activeDataChannels attribute during the last polling period."
   DEFVAL     { 0 }
::= { mscSigChanEIsdnOperEntry 6 }

mscSigChanEIsdnDChanStatus OBJECT-TYPE
   SYNTAX     INTEGER  {
                 outOfService(0),
                 establishing(1),
                 established(2),
                 enabling(3),
                 inService(4),
                 restarting(5) }
   ACCESS     read-only
   STATUS     mandatory
   DESCRIPTION
     "This attribute indicates the state of the D-channel. 
      outOfService means that there is no layer 2 or layer 3 connectivity 
      to the PBX.
      establishing means that the signalling channel is attempting to stage 
      the layer 2.
      established means that the layer 2 is enabled. If the signalling 
      channel stays in the established state, then it is waiting for a restart 
      from the PBX.
      enabling means that the resources for processing calls are being 
      initialized. If the signalling channel stays in the enabling state then 
      it is waiting for a restart acknowledgment from the PBX. 
      inService means that the resources for processing calls are 
      available. 
      restarting means that the resources for call processing are being 
      initialized."
::= { mscSigChanEIsdnOperEntry 7 }

mscSigChanEIsdnToolsTable OBJECT-TYPE
   SYNTAX     SEQUENCE OF MscSigChanEIsdnToolsEntry
   ACCESS     not-accessible
   STATUS     mandatory
   DESCRIPTION
     "This contains a series of operational attributes which turn on and off 
      several kinds of tracing."
::= { mscSigChanEIsdn 17 }

mscSigChanEIsdnToolsEntry OBJECT-TYPE
   SYNTAX     MscSigChanEIsdnToolsEntry
   ACCESS     not-accessible
   STATUS     mandatory
   DESCRIPTION
     "An entry in the mscSigChanEIsdnToolsTable."
   INDEX {
      mscSigChanIndex,
      mscSigChanEIsdnIndex }
::= { mscSigChanEIsdnToolsTable 1 }

MscSigChanEIsdnToolsEntry ::= SEQUENCE {
   mscSigChanEIsdnTracing
      OCTET STRING }

mscSigChanEIsdnTracing OBJECT-TYPE
   SYNTAX     OCTET STRING (SIZE (1))
   ACCESS     read-write
   STATUS     mandatory
   DESCRIPTION
     "This attribute defines which types of tracing are active on the 
      signalling channel. The tracing messages are sent to the debug 
      stream. To see the messages the agentQueueSize attribute of the 
      Lp/x Eng Ds/debug component must be greater than 0 and the 
      operator's NMIS session must have the debug stream included in its 
      data stream list (for example: set Nmis Telnet Session/1 
      dataStreams deb). Several types of tracing can be enabled 
      simultaneously. 
      Note that tracing consumes additional CPU resources and slows 
      down call processing on a heavily loaded card. If there is message 
      block exhaustion tracing is suspended for a period of time and then 
      automatically re-enabled. An alarm is generated on tracing 
      suspension and resumption. This mechanism protects the function 
      processor against excessive numbers of tracing messages.
      Types of tracing include: 
      protocolErrors - get details of any protocol errors which are 
      occurring. Protocol errors are also reported in summary form as 
      alarms. 
      q931Summary - summary of the Q.931 messages on the signalling 
      link. 
      q931Hex - Q.931 messages displayed in hex format. Useful to 
      determine protocol compliance in case of errors reported on local or 
      remote ends.
      q931Symbolic - Q.931 messages parsed to give maximum detail. 
      Useful for understanding content of messages flowing on the link.
      portHex - Q.921 messages in hex format being sent and received on 
      the link.

      Description of bits:
      protocolErrors(0)
      q931Summary(1)
      q931Hex(2)
      q931Symbolic(3)
      portHex(4)"
::= { mscSigChanEIsdnToolsEntry 1 }

mscSigChanEIsdnOptTable OBJECT-TYPE
   SYNTAX     SEQUENCE OF MscSigChanEIsdnOptEntry
   ACCESS     not-accessible
   STATUS     mandatory
   DESCRIPTION
     "This group specifies the provisionable attributes specific to the Euro 
      ISDN (ETSI-T) protocol."
::= { mscSigChanEIsdn 18 }

mscSigChanEIsdnOptEntry OBJECT-TYPE
   SYNTAX     MscSigChanEIsdnOptEntry
   ACCESS     not-accessible
   STATUS     mandatory
   DESCRIPTION
     "An entry in the mscSigChanEIsdnOptTable."
   INDEX {
      mscSigChanIndex,
      mscSigChanEIsdnIndex }
::= { mscSigChanEIsdnOptTable 1 }

MscSigChanEIsdnOptEntry ::= SEQUENCE {
   mscSigChanEIsdnVariant
      INTEGER,
   mscSigChanEIsdnConnectServiceTimer
      Unsigned32,
   mscSigChanEIsdnResponseServiceTimer
      Unsigned32,
   mscSigChanEIsdnLifetimeServiceTimer
      Unsigned32 }

mscSigChanEIsdnVariant OBJECT-TYPE
   SYNTAX     INTEGER  {
                 etsiGeneric(0),
                 austria(1),
                 germany(2) }
   ACCESS     read-write
   STATUS     mandatory
   DESCRIPTION
     "This attribute specifies the specific variant of the Euro ISDN (ETSI-
      T) protocol. Supported variants are:
      etsiGeneric - provides generic ETSI-T protocol. Only proxy of the 
      NETWORK side of the protocol is implemented,
      austria - provides ETSI-T protocol variant as per the Austrian 
      national specification. Only the USER side of the protocol is 
      implemented,
      germany - provides ETSI-T protocol variant as per the German 
      national specification. Only the USER side of the protocol is 
      implemented."
   DEFVAL     { etsiGeneric }
::= { mscSigChanEIsdnOptEntry 1 }

mscSigChanEIsdnConnectServiceTimer OBJECT-TYPE
   SYNTAX     Unsigned32 (1..10)
   ACCESS     read-write
   STATUS     mandatory
   DESCRIPTION
     "This attribute specifies duration of the 'await connection' 
      supervisory timer which applies to non call-associated sessions 
      providing bearer-independent connection-oriented transport for 
      supplementary services. The timer is started at the ingress Passport 
      when a REGISTER message is received from the source PBX and 
      stopped when a virtual circuit with the egress Passport is 
      established. If the timer expires, the non call-associated session is 
      cleared.
      The 'await connection' timer (attribute connectServiceTimer) 
      together with 'await response' timer (attribute 
      responseServiceTimer) provide equivalent of the T-ACTIVATE 
      timer described in the relevant supplementary service specifications.
      A change of the timer value does not apply to timers already 
      running."
   DEFVAL     { 8 }
::= { mscSigChanEIsdnOptEntry 2 }

mscSigChanEIsdnResponseServiceTimer OBJECT-TYPE
   SYNTAX     Unsigned32 (1..10)
   ACCESS     read-write
   STATUS     mandatory
   DESCRIPTION
     "This attribute specifies duration of the 'await response' supervisory 
      timer which applies to non call-associated sessions providing 
      bearer-independent connection-oriented transport for supplementary 
      services. The timer is started at the ingress Passport when creation 
      of a virtual circuit with the egress Passport is confirmed and stopped 
      when the first message from the destination PBX is received. If the 
      timer expires, the non call-associated session is cleared.
      The 'await connection' timer (attribute connectServiceTimer) 
      together with 'await response' timer (attribute 
      responseServiceTimer) provide equivalent of the T-ACTIVATE 
      timer described in the relevant supplementary service specifications.
      A change of the timer value does not apply to timers already 
      running."
   DEFVAL     { 8 }
::= { mscSigChanEIsdnOptEntry 3 }

mscSigChanEIsdnLifetimeServiceTimer OBJECT-TYPE
   SYNTAX     Unsigned32 (1..200)
   ACCESS     read-write
   STATUS     mandatory
   DESCRIPTION
     "This attribute specifies duration of the service lifetime supervisory 
      timer which applies to non call-associated sessions providing 
      bearer-independent connection-oriented transport for supplementary 
      services. The timer limits the duration of a virtual call. It is started 
      at the ingress Passport at the moment the first response message 
      from the destination PBX has been received and stopped when the 
      non call-associated session is released. If the timer expires, the non 
      call-associated session is cleared.
      This timer is equivalent to the T-CCBS6 timer described in the 
      relevant supplementary service specifications.
      A change of the timer value does not apply to timers already 
      running."
   DEFVAL     { 60 }
::= { mscSigChanEIsdnOptEntry 4 }


-- SigChan/n EuroIsdn Framer
-- 
-- The Framer component controls link layer framing for application 
-- components sending and receiving data on a link interface. It is also 
-- through Framer, that an application component is associated with a 
-- specific hardware link interface.
-- 
-- The Framer component provides provisionable attributes related to 
-- data path aspects of the hardware interface (such as CRC and frame 
-- length). The Framer component also provides a provisionable 
-- attribute which binds the application component to a specific 
-- hardware component.
-- 
-- The Framer component contains operational attributes for link 
-- interface data path statistics (such as frame counts and aborts).

mscSigChanEIsdnFramer OBJECT IDENTIFIER ::= { mscSigChanEIsdn 2 }



mscSigChanEIsdnFramerRowStatusTable OBJECT-TYPE
   SYNTAX     SEQUENCE OF MscSigChanEIsdnFramerRowStatusEntry
   ACCESS     not-accessible
   STATUS     mandatory
   DESCRIPTION
     "This entry controls the addition and deletion of 
      mscSigChanEIsdnFramer components."
::= { mscSigChanEIsdnFramer 1 }

mscSigChanEIsdnFramerRowStatusEntry OBJECT-TYPE
   SYNTAX     MscSigChanEIsdnFramerRowStatusEntry
   ACCESS     not-accessible
   STATUS     mandatory
   DESCRIPTION
     "A single entry in the table represents a single 
      mscSigChanEIsdnFramer component."
   INDEX {
      mscSigChanIndex,
      mscSigChanEIsdnIndex,
      mscSigChanEIsdnFramerIndex }
::= { mscSigChanEIsdnFramerRowStatusTable 1 }

MscSigChanEIsdnFramerRowStatusEntry ::= SEQUENCE {
   mscSigChanEIsdnFramerRowStatus
      RowStatus,
   mscSigChanEIsdnFramerComponentName
      DisplayString,
   mscSigChanEIsdnFramerStorageType
      StorageType,
   mscSigChanEIsdnFramerIndex
      NonReplicated }

mscSigChanEIsdnFramerRowStatus OBJECT-TYPE
   SYNTAX     RowStatus 
   ACCESS     read-only
   STATUS     mandatory
   DESCRIPTION
     "This variable is used as the basis for SNMP naming of
      mscSigChanEIsdnFramer components.
      These components cannot be added nor deleted."
::= { mscSigChanEIsdnFramerRowStatusEntry 1 }

mscSigChanEIsdnFramerComponentName OBJECT-TYPE
   SYNTAX     DisplayString 
   ACCESS     read-only
   STATUS     mandatory
   DESCRIPTION
     "This variable provides the component's string name for
      use with the ASCII Console Interface"
::= { mscSigChanEIsdnFramerRowStatusEntry 2 }

mscSigChanEIsdnFramerStorageType OBJECT-TYPE
   SYNTAX     StorageType 
   ACCESS     read-only
   STATUS     mandatory
   DESCRIPTION
     "This variable represents the storage type value for the
      mscSigChanEIsdnFramer tables."
::= { mscSigChanEIsdnFramerRowStatusEntry 4 }

mscSigChanEIsdnFramerIndex OBJECT-TYPE
   SYNTAX     NonReplicated 
   ACCESS     not-accessible
   STATUS     mandatory
   DESCRIPTION
     "This variable represents the index for the mscSigChanEIsdnFramer tables."
::= { mscSigChanEIsdnFramerRowStatusEntry 10 }

mscSigChanEIsdnFramerProvTable OBJECT-TYPE
   SYNTAX     SEQUENCE OF MscSigChanEIsdnFramerProvEntry
   ACCESS     not-accessible
   STATUS     mandatory
   DESCRIPTION
     "This group contains the base provisioning data for the Framer 
      component. Application or hardware interface specific provisioning 
      data is contained in other provisionable Framer groups."
::= { mscSigChanEIsdnFramer 10 }

mscSigChanEIsdnFramerProvEntry OBJECT-TYPE
   SYNTAX     MscSigChanEIsdnFramerProvEntry
   ACCESS     not-accessible
   STATUS     mandatory
   DESCRIPTION
     "An entry in the mscSigChanEIsdnFramerProvTable."
   INDEX {
      mscSigChanIndex,
      mscSigChanEIsdnIndex,
      mscSigChanEIsdnFramerIndex }
::= { mscSigChanEIsdnFramerProvTable 1 }

MscSigChanEIsdnFramerProvEntry ::= SEQUENCE {
   mscSigChanEIsdnFramerInterfaceName
      Link }

mscSigChanEIsdnFramerInterfaceName OBJECT-TYPE
   SYNTAX     Link 
   ACCESS     read-write
   STATUS     mandatory
   DESCRIPTION
     "This attribute contains a hardware component name.
      
      The attribute associates the application with a specific link. This 
      defines the module processor on which Framer's parent component 
      (as well as Framer itself) will run."
::= { mscSigChanEIsdnFramerProvEntry 1 }

mscSigChanEIsdnFramerStateTable OBJECT-TYPE
   SYNTAX     SEQUENCE OF MscSigChanEIsdnFramerStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscSigChanEIsdnFramer 12 }

mscSigChanEIsdnFramerStateEntry OBJECT-TYPE
   SYNTAX     MscSigChanEIsdnFramerStateEntry
   ACCESS     not-accessible
   STATUS     mandatory
   DESCRIPTION
     "An entry in the mscSigChanEIsdnFramerStateTable."
   INDEX {
      mscSigChanIndex,
      mscSigChanEIsdnIndex,
      mscSigChanEIsdnFramerIndex }
::= { mscSigChanEIsdnFramerStateTable 1 }

MscSigChanEIsdnFramerStateEntry ::= SEQUENCE {
   mscSigChanEIsdnFramerAdminState
      INTEGER,
   mscSigChanEIsdnFramerOperationalState
      INTEGER,
   mscSigChanEIsdnFramerUsageState
      INTEGER }

mscSigChanEIsdnFramerAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscSigChanEIsdnFramerStateEntry 1 }

mscSigChanEIsdnFramerOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscSigChanEIsdnFramerStateEntry 2 }

mscSigChanEIsdnFramerUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscSigChanEIsdnFramerStateEntry 3 }

mscSigChanEIsdnFramerStatsTable OBJECT-TYPE
   SYNTAX     SEQUENCE OF MscSigChanEIsdnFramerStatsEntry
   ACCESS     not-accessible
   STATUS     mandatory
   DESCRIPTION
     "This group contains the operational statistics data for a Framer 
      component."
::= { mscSigChanEIsdnFramer 13 }

mscSigChanEIsdnFramerStatsEntry OBJECT-TYPE
   SYNTAX     MscSigChanEIsdnFramerStatsEntry
   ACCESS     not-accessible
   STATUS     mandatory
   DESCRIPTION
     "An entry in the mscSigChanEIsdnFramerStatsTable."
   INDEX {
      mscSigChanIndex,
      mscSigChanEIsdnIndex,
      mscSigChanEIsdnFramerIndex }
::= { mscSigChanEIsdnFramerStatsTable 1 }

MscSigChanEIsdnFramerStatsEntry ::= SEQUENCE {
   mscSigChanEIsdnFramerFrmToIf
      Counter32,
   mscSigChanEIsdnFramerFrmFromIf
      Counter32,
   mscSigChanEIsdnFramerOctetFromIf
      Counter32,
   mscSigChanEIsdnFramerAborts
      Counter32,
   mscSigChanEIsdnFramerCrcErrors
      Counter32,
   mscSigChanEIsdnFramerLrcErrors
      Counter32,
   mscSigChanEIsdnFramerNonOctetErrors
      Counter32,
   mscSigChanEIsdnFramerOverruns
      Counter32,
   mscSigChanEIsdnFramerUnderruns
      Counter32,
   mscSigChanEIsdnFramerLargeFrmErrors
      Counter32 }

mscSigChanEIsdnFramerFrmToIf OBJECT-TYPE
   SYNTAX     Counter32 
   ACCESS     read-only
   STATUS     mandatory
   DESCRIPTION
     "This attribute counts the number of frames transmitted to the link 
      interface by the Framer.
      This count wraps to zero after exceeding its maximum value."
::= { mscSigChanEIsdnFramerStatsEntry 1 }

mscSigChanEIsdnFramerFrmFromIf OBJECT-TYPE
   SYNTAX     Counter32 
   ACCESS     read-only
   STATUS     mandatory
   DESCRIPTION
     "This attribute counts the number of frames received from the link 
      interface by the Framer.
      This count wraps to zero after exceeding its maximum value."
::= { mscSigChanEIsdnFramerStatsEntry 2 }

mscSigChanEIsdnFramerOctetFromIf OBJECT-TYPE
   SYNTAX     Counter32 
   ACCESS     read-only
   STATUS     mandatory
   DESCRIPTION
     "This attribute counts the number of bytes received from the link 
      interface by the Framer.
      This count wraps to zero after exceeding its maximum value."
::= { mscSigChanEIsdnFramerStatsEntry 3 }

mscSigChanEIsdnFramerAborts OBJECT-TYPE
   SYNTAX     Counter32 
   ACCESS     read-only
   STATUS     mandatory
   DESCRIPTION
     "This attribute counts the total number of aborts received.
      This count wraps to zero after exceeding its maximum value."
::= { mscSigChanEIsdnFramerStatsEntry 4 }

mscSigChanEIsdnFramerCrcErrors OBJECT-TYPE
   SYNTAX     Counter32 
   ACCESS     read-only
   STATUS     mandatory
   DESCRIPTION
     "This attribute counts the total number of frames with CRC errors.
      This count wraps to zero after exceeding its maximum value."
::= { mscSigChanEIsdnFramerStatsEntry 5 }

mscSigChanEIsdnFramerLrcErrors OBJECT-TYPE
   SYNTAX     Counter32 
   ACCESS     read-only
   STATUS     mandatory
   DESCRIPTION
     "This attribute counts the total number of frames with LRC errors.
      This count wraps to zero after exceeding its maximum value."
::= { mscSigChanEIsdnFramerStatsEntry 6 }

mscSigChanEIsdnFramerNonOctetErrors OBJECT-TYPE
   SYNTAX     Counter32 
   ACCESS     read-only
   STATUS     mandatory
   DESCRIPTION
     "This attribute counts the total number of frames that were non octet 
      aligned.
      This count wraps to zero after exceeding its maximum value."
::= { mscSigChanEIsdnFramerStatsEntry 7 }

mscSigChanEIsdnFramerOverruns OBJECT-TYPE
   SYNTAX     Counter32 
   ACCESS     read-only
   STATUS     mandatory
   DESCRIPTION
     "This attribute counts the total number of frames received from the 
      link for which overruns occurred.
      This count wraps to zero after exceeding its maximum value."
::= { mscSigChanEIsdnFramerStatsEntry 8 }

mscSigChanEIsdnFramerUnderruns OBJECT-TYPE
   SYNTAX     Counter32 
   ACCESS     read-only
   STATUS     mandatory
   DESCRIPTION
     "This attribute counts the total number of frames transmitted to the 
      link for which underruns occurred.
      This count wraps to zero after exceeding its maximum value."
::= { mscSigChanEIsdnFramerStatsEntry 9 }

mscSigChanEIsdnFramerLargeFrmErrors OBJECT-TYPE
   SYNTAX     Counter32 
   ACCESS     read-only
   STATUS     mandatory
   DESCRIPTION
     "This attribute counts the total number of frames received which 
      were too large (longer than 500 bytes).
      This count wraps to zero after exceeding its maximum value."
::= { mscSigChanEIsdnFramerStatsEntry 10 }




-- 
-- Version and Compliance statements
-- 



-- Object-Group Statement:
-- A list of all current accessible leaf objects.

-- OBJECTS { mscSigChanEIsdnRowStatus,
--           mscSigChanEIsdnResponseServiceTimer,
--           mscSigChanEIsdnTracing,
--           mscSigChanEIsdnFramerFrmToIf,
--           mscSigChanEIsdnMaxNonCallConcurrent,
--           mscSigChanEIsdnVariant,
--           mscSigChanEIsdnNonCallAssocSessionsFromIf,
--           mscSigChanEIsdnPeakActiveVoiceChannels,
--           mscSigChanEIsdnFramerNonOctetErrors,
--           mscSigChanEIsdnPeakActiveChannels,
--           mscSigChanEIsdnFramerLrcErrors,
--           mscSigChanEIsdnFramerUsageState,
--           mscSigChanEIsdnFramerOverruns,
--           mscSigChanEIsdnActiveDataChannels,
--           mscSigChanEIsdnFramerAborts,
--           mscSigChanEIsdnFramerComponentName,
--           mscSigChanEIsdnTotalCallsFromIf,
--           mscSigChanEIsdnN200,
--           mscSigChanEIsdnTotalCallsToIf,
--           mscSigChanEIsdnFramerInterfaceName,
--           mscSigChanEIsdnComponentName,
--           mscSigChanEIsdnCircuitSwitchedK,
--           mscSigChanEIsdnPeakActiveDataChannels,
--           mscSigChanEIsdnFramerCrcErrors,
--           mscSigChanEIsdnStorageType,
--           mscSigChanEIsdnFramerOperationalState,
--           mscSigChanEIsdnOverlapSending,
--           mscSigChanEIsdnT200,
--           mscSigChanEIsdnFramerStorageType,
--           mscSigChanEIsdnFramerLargeFrmErrors,
--           mscSigChanEIsdnOverlapReceiving,
--           mscSigChanEIsdnConnectServiceTimer,
--           mscSigChanEIsdnOperationalState,
--           mscSigChanEIsdnLifetimeServiceTimer,
--           mscSigChanEIsdnT203,
--           mscSigChanEIsdnFramerFrmFromIf,
--           mscSigChanEIsdnT310,
--           mscSigChanEIsdnDChanStatus,
--           mscSigChanEIsdnFramerAdminState,
--           mscSigChanEIsdnFramerOctetFromIf,
--           mscSigChanEIsdnNonCallAssocSessionsToIf,
--           mscSigChanEIsdnT23,
--           mscSigChanEIsdnSide,
--           mscSigChanEIsdnAdminState,
--           mscSigChanEIsdnFramerUnderruns,
--           mscSigChanEIsdnFramerRowStatus,
--           mscSigChanEIsdnActiveVoiceChannels,
--           mscSigChanEIsdnUsageState,
--           mscSigChanEIsdnActiveChannels }
-- STATUS  mandatory
-- DESCRIPTION
--   "A list of all current accessible leaf objects."

vnetEuroIsdnGroup OBJECT IDENTIFIER ::= { vnetEuroIsdnMIB 1 }
vnetEuroIsdnGroupCA OBJECT IDENTIFIER ::= { vnetEuroIsdnGroup 1 }
vnetEuroIsdnGroupCA02 OBJECT IDENTIFIER ::= { vnetEuroIsdnGroupCA 3 }
vnetEuroIsdnGroupCA02A OBJECT IDENTIFIER ::= { vnetEuroIsdnGroupCA02 2 }



-- Agent-Capabilities Statement:

-- PRODUCT-RELEASE "MscPassport Release 1.2 VnetEuroIsdn."
-- STATUS          mandatory
-- DESCRIPTION     "Carrier Passport VnetEuroIsdn MIB: MIB Version CA02A,
--                  Software Version CA02S9C."
-- SUPPORTS        Nortel-MsCarrier-MscPassport-VnetEuroIsdnMIB
--    INCLUDES     { vnetEuroIsdnGroupCA02A }

vnetEuroIsdnCapabilities OBJECT IDENTIFIER ::= { vnetEuroIsdnMIB 3 }
vnetEuroIsdnCapabilitiesCA OBJECT IDENTIFIER ::= { vnetEuroIsdnCapabilities 1 }
vnetEuroIsdnCapabilitiesCA02 OBJECT IDENTIFIER ::= { vnetEuroIsdnCapabilitiesCA 3 }
vnetEuroIsdnCapabilitiesCA02A OBJECT IDENTIFIER ::= { vnetEuroIsdnCapabilitiesCA02 2 }





END
