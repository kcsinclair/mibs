Nortel-MsCarrier-MscPassport-IpiVcMIB
DEFINITIONS ::= BEGIN



IMPORTS

      OBJECT-TYPE
   FROM RFC-1212

      IpAddress
   FROM RFC1155-SMI

      mscPassportMIBs,
      mscComponents
   FROM Nortel-MsCarrier-MscPassport-UsefulDefinitionsMIB

      Counter32,
      DisplayString,
      StorageType,
      RowStatus,
      Integer32,
      Unsigned32
   FROM Nortel-MsCarrier-MscPassport-StandardTextualConventionsMIB

      Hex,
      NonReplicated,
      EnterpriseDateAndTime,
      DigitString
   FROM Nortel-MsCarrier-MscPassport-TextualConventionsMIB;




-- LAST-UPDATED   "9909010000Z"
-- ORGANIZATION   "Nortel Networks"
-- CONTACT-INFO   "
--         Nortel Carrier Data Network Management
--         
--         Postal:       P.O. Box 3511, Station C 
--                       Ottawa, Ontario 
--                       Canada  K1Y 4H7
--         
--         via the WEB:  http://www.nortelnetworks.com  
--                       select 'Contact Us' from the menu
--          
--         via phone:    1-800-4NORTEL"
-- DESCRIPTION
--    "The module describing the Nortel MsCarrier MscPassport
--     IpiVc Enterprise MIB."

ipiVcMIB OBJECT IDENTIFIER ::= { mscPassportMIBs 53 }










-- 
-- IpiVc
-- 
-- The IP interface over VC allows access to the module for external 
-- network management.

mscIpivc OBJECT IDENTIFIER ::= { mscComponents 51 }



mscIpivcRowStatusTable OBJECT-TYPE
   SYNTAX     SEQUENCE OF MscIpivcRowStatusEntry
   ACCESS     not-accessible
   STATUS     mandatory
   DESCRIPTION
     "This entry controls the addition and deletion of 
      mscIpivc components."
::= { mscIpivc 1 }

mscIpivcRowStatusEntry OBJECT-TYPE
   SYNTAX     MscIpivcRowStatusEntry
   ACCESS     not-accessible
   STATUS     mandatory
   DESCRIPTION
     "A single entry in the table represents a single 
      mscIpivc component."
   INDEX {
      mscIpivcIndex }
::= { mscIpivcRowStatusTable 1 }

MscIpivcRowStatusEntry ::= SEQUENCE {
   mscIpivcRowStatus
      RowStatus,
   mscIpivcComponentName
      DisplayString,
   mscIpivcStorageType
      StorageType,
   mscIpivcIndex
      NonReplicated }

mscIpivcRowStatus OBJECT-TYPE
   SYNTAX     RowStatus 
   ACCESS     read-write
   STATUS     mandatory
   DESCRIPTION
     "This variable is used as the basis for SNMP naming of
      mscIpivc components.
      These components can be added and deleted."
::= { mscIpivcRowStatusEntry 1 }

mscIpivcComponentName OBJECT-TYPE
   SYNTAX     DisplayString 
   ACCESS     read-only
   STATUS     mandatory
   DESCRIPTION
     "This variable provides the component's string name for
      use with the ASCII Console Interface"
::= { mscIpivcRowStatusEntry 2 }

mscIpivcStorageType OBJECT-TYPE
   SYNTAX     StorageType 
   ACCESS     read-only
   STATUS     mandatory
   DESCRIPTION
     "This variable represents the storage type value for the
      mscIpivc tables."
::= { mscIpivcRowStatusEntry 4 }

mscIpivcIndex OBJECT-TYPE
   SYNTAX     NonReplicated 
   ACCESS     not-accessible
   STATUS     mandatory
   DESCRIPTION
     "This variable represents the index for the mscIpivc tables."
::= { mscIpivcRowStatusEntry 10 }

mscIpivcProvTable OBJECT-TYPE
   SYNTAX     SEQUENCE OF MscIpivcProvEntry
   ACCESS     not-accessible
   STATUS     mandatory
   DESCRIPTION
     "This group contains the provisionable attributes for the IpiVc 
      component."
::= { mscIpivc 10 }

mscIpivcProvEntry OBJECT-TYPE
   SYNTAX     MscIpivcProvEntry
   ACCESS     not-accessible
   STATUS     mandatory
   DESCRIPTION
     "An entry in the mscIpivcProvTable."
   INDEX {
      mscIpivcIndex }
::= { mscIpivcProvTable 1 }

MscIpivcProvEntry ::= SEQUENCE {
   mscIpivcIpAddress
      IpAddress,
   mscIpivcMaximumNumberOfLcn
      Unsigned32 }

mscIpivcIpAddress OBJECT-TYPE
   SYNTAX     IpAddress 
   ACCESS     read-write
   STATUS     mandatory
   DESCRIPTION
     "This IP Address represents the IP address of the IP interface."
   DEFVAL     { '00000000'H }  -- "0.0.0.0"
::= { mscIpivcProvEntry 1 }

mscIpivcMaximumNumberOfLcn OBJECT-TYPE
   SYNTAX     Unsigned32 (24)
   ACCESS     read-only
   STATUS     mandatory
   DESCRIPTION
     "This attribute contains the maximum number of LCNs that can be 
      setup to the IP Interface over Vc. It defines the maximum number of 
      calls that the external network management systems can setup to 
      IpiVc simultaneously."
   DEFVAL     { 24 }
::= { mscIpivcProvEntry 2 }


-- IpiVc Dna
-- This is the description of the generic Vc Dna Component. It 
-- includes the superset of all attributes which may apply to a VC. 
-- Particular applications will typically offer only a subset of these 
-- attributes by providing a definition of their own Dna subcomponent. 

mscIpivcDna OBJECT IDENTIFIER ::= { mscIpivc 2 }



mscIpivcDnaRowStatusTable OBJECT-TYPE
   SYNTAX     SEQUENCE OF MscIpivcDnaRowStatusEntry
   ACCESS     not-accessible
   STATUS     mandatory
   DESCRIPTION
     "This entry controls the addition and deletion of 
      mscIpivcDna components."
::= { mscIpivcDna 1 }

mscIpivcDnaRowStatusEntry OBJECT-TYPE
   SYNTAX     MscIpivcDnaRowStatusEntry
   ACCESS     not-accessible
   STATUS     mandatory
   DESCRIPTION
     "A single entry in the table represents a single 
      mscIpivcDna component."
   INDEX {
      mscIpivcIndex,
      mscIpivcDnaIndex }
::= { mscIpivcDnaRowStatusTable 1 }

MscIpivcDnaRowStatusEntry ::= SEQUENCE {
   mscIpivcDnaRowStatus
      RowStatus,
   mscIpivcDnaComponentName
      DisplayString,
   mscIpivcDnaStorageType
      StorageType,
   mscIpivcDnaIndex
      NonReplicated }

mscIpivcDnaRowStatus OBJECT-TYPE
   SYNTAX     RowStatus 
   ACCESS     read-only
   STATUS     mandatory
   DESCRIPTION
     "This variable is used as the basis for SNMP naming of
      mscIpivcDna components.
      These components cannot be added nor deleted."
::= { mscIpivcDnaRowStatusEntry 1 }

mscIpivcDnaComponentName OBJECT-TYPE
   SYNTAX     DisplayString 
   ACCESS     read-only
   STATUS     mandatory
   DESCRIPTION
     "This variable provides the component's string name for
      use with the ASCII Console Interface"
::= { mscIpivcDnaRowStatusEntry 2 }

mscIpivcDnaStorageType OBJECT-TYPE
   SYNTAX     StorageType 
   ACCESS     read-only
   STATUS     mandatory
   DESCRIPTION
     "This variable represents the storage type value for the
      mscIpivcDna tables."
::= { mscIpivcDnaRowStatusEntry 4 }

mscIpivcDnaIndex OBJECT-TYPE
   SYNTAX     NonReplicated 
   ACCESS     not-accessible
   STATUS     mandatory
   DESCRIPTION
     "This variable represents the index for the mscIpivcDna tables."
::= { mscIpivcDnaRowStatusEntry 10 }

mscIpivcDnaAddressTable OBJECT-TYPE
   SYNTAX     SEQUENCE OF MscIpivcDnaAddressEntry
   ACCESS     not-accessible
   STATUS     mandatory
   DESCRIPTION
     "DnaAddress group contains attributes common to all Dna's. Every 
      Dna used in the network is defined with this group 0f 2 attributes. 
      String of address digits is complemented by type of address and 
      Npi. These attributes are used to interpret format of the address 
      digits."
::= { mscIpivcDna 10 }

mscIpivcDnaAddressEntry OBJECT-TYPE
   SYNTAX     MscIpivcDnaAddressEntry
   ACCESS     not-accessible
   STATUS     mandatory
   DESCRIPTION
     "An entry in the mscIpivcDnaAddressTable."
   INDEX {
      mscIpivcIndex,
      mscIpivcDnaIndex }
::= { mscIpivcDnaAddressTable 1 }

MscIpivcDnaAddressEntry ::= SEQUENCE {
   mscIpivcDnaNumberingPlanIndicator
      INTEGER,
   mscIpivcDnaDataNetworkAddress
      DigitString }

mscIpivcDnaNumberingPlanIndicator OBJECT-TYPE
   SYNTAX     INTEGER  {
                 x121(0),
                 e164(1) }
   ACCESS     read-write
   STATUS     mandatory
   DESCRIPTION
     "This attribute indicates the Numbering Plan Indicator (NPI) of the 
      Dna that is entered. Address may belong to X.121 or E.164 plans. 
      X.121 is used in packet svitched data networks."
   DEFVAL     { x121 }
::= { mscIpivcDnaAddressEntry 1 }

mscIpivcDnaDataNetworkAddress OBJECT-TYPE
   SYNTAX     DigitString (SIZE (1..15))
   ACCESS     read-write
   STATUS     mandatory
   DESCRIPTION
     "Dna attribute contains digits which form unique identifier of the 
      customer. It is the equivalent of the telephone number in the 
      telephone network. MaximumLenOfDna is 15digits."
::= { mscIpivcDnaAddressEntry 2 }

mscIpivcDnaOutgoingOptionsTable OBJECT-TYPE
   SYNTAX     SEQUENCE OF MscIpivcDnaOutgoingOptionsEntry
   ACCESS     not-accessible
   STATUS     mandatory
   DESCRIPTION
     "DnaOutOptionsProv group defines call options of a Dna for calls 
      which are made out of the interface represented by Dna. All these 
      options are not used for calls arriving to the interface represented by 
      Dna."
::= { mscIpivcDna 11 }

mscIpivcDnaOutgoingOptionsEntry OBJECT-TYPE
   SYNTAX     MscIpivcDnaOutgoingOptionsEntry
   ACCESS     not-accessible
   STATUS     mandatory
   DESCRIPTION
     "An entry in the mscIpivcDnaOutgoingOptionsTable."
   INDEX {
      mscIpivcIndex,
      mscIpivcDnaIndex }
::= { mscIpivcDnaOutgoingOptionsTable 1 }

MscIpivcDnaOutgoingOptionsEntry ::= SEQUENCE {
   mscIpivcDnaOutCalls
      INTEGER,
   mscIpivcDnaOutDefaultPathSensitivity
      INTEGER,
   mscIpivcDnaOutPathSensitivityOverRide
      INTEGER,
   mscIpivcDnaDefaultTransferPriority
      INTEGER,
   mscIpivcDnaTransferPriorityOverRide
      INTEGER }

mscIpivcDnaOutCalls OBJECT-TYPE
   SYNTAX     INTEGER  {
                 disallowed(0),
                 allowed(1) }
   ACCESS     read-only
   STATUS     mandatory
   DESCRIPTION
     "This attribute, if set to a value of allowed indicates that outgoing 
      calls (from the DTE to the network) can be made using this 
      particular DNA. If set to a value of disallowed, then outgoing calls 
      cannot be made using this DNA - such calls will be cleared by the 
      local DCE. This attribute corresponds to the CCITT 'Outgoing Calls 
      Barred' feature for DNAs in that outgoing calls are barred if this 
      attribute is set to a value of disallowed. Either outCalls, or incCalls 
      (or both) must be set to a value of allowed for this DNA to be 
      useable."
   DEFVAL     { disallowed }
::= { mscIpivcDnaOutgoingOptionsEntry 1 }

mscIpivcDnaOutDefaultPathSensitivity OBJECT-TYPE
   SYNTAX     INTEGER  {
                 throughput(0),
                 delay(1) }
   ACCESS     read-write
   STATUS     obsolete
   DESCRIPTION
     "This attribute specifies the default class of path sensitivity to 
      network for all outgoing calls using this particular Dna. The chosen 
      default class of path sensitivity applies to all outgoing calls 
      established using this Dna. 
      
      This attribute, if set to a value of throughput, indicates that the 
      default class is throughput sensitive. If set to a value of delay, then 
      the default class is delay sensitive. The default of 
      outDefaultPathSensitivity is throughput."
   DEFVAL     { throughput }
::= { mscIpivcDnaOutgoingOptionsEntry 11 }

mscIpivcDnaOutPathSensitivityOverRide OBJECT-TYPE
   SYNTAX     INTEGER  {
                 no(0),
                 yes(1) }
   ACCESS     read-write
   STATUS     obsolete
   DESCRIPTION
     "If this attribute is set to in the call request, the called end will use 
      the calling end provisioning data on path sensitivity to override its 
      own provisioning data.
      
      The default of outPathSensitivityOverRide is no."
   DEFVAL     { no }
::= { mscIpivcDnaOutgoingOptionsEntry 12 }

mscIpivcDnaDefaultTransferPriority OBJECT-TYPE
   SYNTAX     INTEGER  {
                 normal(0),
                 high(9) }
   ACCESS     read-write
   STATUS     mandatory
   DESCRIPTION
     "This attribute specifies the default transfer priority to network for 
      all outgoing calls using this particular Dna. It is overRidden by 
      the transferPriority provisioned in the DLCI Direct Call sub-
      component.
      
      The transfer priority is a preference specified by an application 
      according to its delay-sensitivity requirement. Frames with high
      transfer priority are served by the network before the frames with 
      normal priority. 
      
      Each transfer priority contains a predetermined setting for trunk 
      queue (interrupting, delay or throughput), routing metric (delay or 
      throughput). 
      
      When the transfer priority is set at high, the trunk queue is set to 
      high, the routing metric is set to delay.
      
      When the transfer priority is set at normal, the trunk queue is set to 
      normal, the routing metric is set to throughput.
      
      The default of defaultTransferPriority is normal."
   DEFVAL     { normal }
::= { mscIpivcDnaOutgoingOptionsEntry 18 }

mscIpivcDnaTransferPriorityOverRide OBJECT-TYPE
   SYNTAX     INTEGER  {
                 no(0),
                 yes(1) }
   ACCESS     read-write
   STATUS     mandatory
   DESCRIPTION
     "When this attribute is set to yes, the called end will use the calling 
      end provisioning data on transfer priority to override its own 
      provisioning data. If it is set no, the called end will use its own 
      provisioning data on transfer priority.
      
      For more information about transfer priority, please refer to the 
      previous attribute defaultTransferPriority.
      
      The default of transferPriorityOverRide is no."
   DEFVAL     { no }
::= { mscIpivcDnaOutgoingOptionsEntry 19 }

mscIpivcDnaIncomingOptionsTable OBJECT-TYPE
   SYNTAX     SEQUENCE OF MscIpivcDnaIncomingOptionsEntry
   ACCESS     not-accessible
   STATUS     mandatory
   DESCRIPTION
     "DnaIncOptions defines set of options for incoming calls. These 
      options are used for calls arriving to the interface represented by 
      Dna. For calls originated from the interfasce, IncomingOptions 
      attributes are not used."
::= { mscIpivcDna 12 }

mscIpivcDnaIncomingOptionsEntry OBJECT-TYPE
   SYNTAX     MscIpivcDnaIncomingOptionsEntry
   ACCESS     not-accessible
   STATUS     mandatory
   DESCRIPTION
     "An entry in the mscIpivcDnaIncomingOptionsTable."
   INDEX {
      mscIpivcIndex,
      mscIpivcDnaIndex }
::= { mscIpivcDnaIncomingOptionsTable 1 }

MscIpivcDnaIncomingOptionsEntry ::= SEQUENCE {
   mscIpivcDnaIncCalls
      INTEGER,
   mscIpivcDnaIncHighPriorityReverseCharge
      INTEGER,
   mscIpivcDnaIncNormalPriorityReverseCharge
      INTEGER,
   mscIpivcDnaIncIntlNormalCharge
      INTEGER,
   mscIpivcDnaIncIntlReverseCharge
      INTEGER,
   mscIpivcDnaIncFastSelect
      INTEGER,
   mscIpivcDnaIncSameService
      INTEGER,
   mscIpivcDnaIncChargeTransfer
      INTEGER,
   mscIpivcDnaIncAccess
      INTEGER }

mscIpivcDnaIncCalls OBJECT-TYPE
   SYNTAX     INTEGER  {
                 disallowed(0),
                 allowed(1) }
   ACCESS     read-only
   STATUS     mandatory
   DESCRIPTION
     "This attribute, if set to a value of allowed  indicates that incoming 
      calls (from the network to the DTE) can be made to this DNA. If set 
      to a value of disallowed, then incoming calls cannot be made to this 
      DNA - such calls will be cleared by the local DCE. This attribute 
      corresponds to the CCITT 'Incoming Calls Barred' feature for 
      DNAs in that incoming calls are barred if this attribute is set to a 
      value of disallowed.
      
      Either outCalls, or incCalls (or both) must be set to a value of 
      allowed for this DNA to be useable."
   DEFVAL     { allowed }
::= { mscIpivcDnaIncomingOptionsEntry 1 }

mscIpivcDnaIncHighPriorityReverseCharge OBJECT-TYPE
   SYNTAX     INTEGER  {
                 disallowed(0),
                 allowed(1) }
   ACCESS     read-only
   STATUS     mandatory
   DESCRIPTION
     "This attribute, if set to a value of allowed indicates that incoming 
      high priority, reverse charged calls (from the network to the DTE) 
      can be made to this DNA. If set to a value of disallowed, then such 
      calls cannot be made to this DNA - such calls will be cleared by the 
      local DCE.
      This attribute, together with the 
      incNormalPriorityReverseChargeCalls attribute corresponds to the 
      CCITT 'Reverse Charging Acceptance' feature for DNAs in that 
      reverse charged calls are accepted if both attributes are set to a 
      value of allowed.
      This attribute is ignored if the corresponding attribute, incCalls is 
      set to a value of disallowed."
   DEFVAL     { allowed }
::= { mscIpivcDnaIncomingOptionsEntry 2 }

mscIpivcDnaIncNormalPriorityReverseCharge OBJECT-TYPE
   SYNTAX     INTEGER  {
                 disallowed(0),
                 allowed(1) }
   ACCESS     read-only
   STATUS     mandatory
   DESCRIPTION
     "This attribute, if set to a value of allowed indicates that incoming 
      normal priority, reverse charged calls (from the network to the 
      DTE) can be made to this DNA. If set to a value of disallowed, then 
      such calls cannot be made to this DNA - such calls will be cleared 
      by the local DCE. 
      This attribute, together with the 
      incHighPriorityReverseChargeCalls attribute corresponds to the 
      CCITT 'Reverse Charging Acceptance' feature for DNAs in that 
      reverse charged calls are accepted if both attributes are set to a 
      value of allowed.
      This attribute is ignored if the corresponding attribute, incCalls is 
      set to a value of disallowed."
   DEFVAL     { allowed }
::= { mscIpivcDnaIncomingOptionsEntry 3 }

mscIpivcDnaIncIntlNormalCharge OBJECT-TYPE
   SYNTAX     INTEGER  {
                 disallowed(0),
                 allowed(1) }
   ACCESS     read-only
   STATUS     mandatory
   DESCRIPTION
     "This attribute, if set to a value of allowed indicates that incoming 
      international normal charged calls (from the network to the DTE) 
      can be made to this DNA. If set to a value of disallowed, then such 
      calls cannot be made to this DNA - such calls will be cleared by the 
      local DCE.
      This attribute also currently controls access to/from the E.164 
      numbering plan, and if set to a value of allowed, then cross-
      numbering plan calls (also normal charged) are allowed. 
      This attribute is ignored if the corresponding attribute, incCalls is 
      set to a value of disallowed."
   DEFVAL     { allowed }
::= { mscIpivcDnaIncomingOptionsEntry 4 }

mscIpivcDnaIncIntlReverseCharge OBJECT-TYPE
   SYNTAX     INTEGER  {
                 disallowed(0),
                 allowed(1) }
   ACCESS     read-only
   STATUS     mandatory
   DESCRIPTION
     "This attribute, if set to a value of allowed indicates that incoming 
      international reverse charged calls (from the network to the DTE) 
      can be made to this DNA. If set to a value of disallowed, then such 
      calls cannot be made to this DNA - such calls will be cleared by the 
      local DCE.
      This attribute also currently controls access to/from the E.164 
      numbering plan, and if set to a value of allowed, then cross-
      numbering plan calls (also normal charged) are allowed.
      This attribute is ignored if the corresponding attribute, incCalls is 
      set to a value of disallowed."
   DEFVAL     { allowed }
::= { mscIpivcDnaIncomingOptionsEntry 5 }

mscIpivcDnaIncFastSelect OBJECT-TYPE
   SYNTAX     INTEGER  {
                 disallowed(0),
                 allowed(1) }
   ACCESS     read-only
   STATUS     mandatory
   DESCRIPTION
     "This attribute specifies whether fast select calls may be received.
      This attribute, if set to a value of allowed indicates that incoming 
      fast select calls (from the network to the DTE) can be made to this 
      DNA. If set to a value of disallowed, then such calls cannot be 
      made to this DNA - such calls will be cleared by the local DCE.
      This attribute corresponds to the CCITT 'Fast Select Acceptance' 
      feature for DNAs in that incoming fast select calls are accepted if 
      this attribute is set to a value of allowed.
      This attribute is ignored if the corresponding attribute, incCalls is 
      set to a value of disallowed."
   DEFVAL     { disallowed }
::= { mscIpivcDnaIncomingOptionsEntry 6 }

mscIpivcDnaIncSameService OBJECT-TYPE
   SYNTAX     INTEGER  {
                 disallowed(0),
                 allowed(1) }
   ACCESS     read-only
   STATUS     mandatory
   DESCRIPTION
     "This attribute, if set to a value of allowed indicates that incoming 
      calls from the same service type (eg: X.25, ITI, SNA) (from the 
      network to the DTE) can be made to this DNA. If set to a value of 
      disallowed, then such calls cannot be made to this DNA - such calls 
      will be cleared by the local DCE.
      This attribute is ignored if the corresponding attribute, incCalls is 
      set to a value of disallowed."
   DEFVAL     { allowed }
::= { mscIpivcDnaIncomingOptionsEntry 7 }

mscIpivcDnaIncChargeTransfer OBJECT-TYPE
   SYNTAX     INTEGER  {
                 no(0),
                 yes(1) }
   ACCESS     read-only
   STATUS     mandatory
   DESCRIPTION
     "This attribute, if set to a value of yes indicates that the charges for 
      incoming normal charged calls from a DTE with the same NIC 
      (calls from the network to the DTE) will be transferred to the called 
      DTE. If set to a value of no, then charges will not be transferred.
      This attribute is ignored if the corresponding attribute, incCalls is 
      set to a value of disallowed."
   DEFVAL     { no }
::= { mscIpivcDnaIncomingOptionsEntry 8 }

mscIpivcDnaIncAccess OBJECT-TYPE
   SYNTAX     INTEGER  {
                 disallowed(0),
                 allowed(1) }
   ACCESS     read-only
   STATUS     mandatory
   DESCRIPTION
     "This attribute is an extension of the Closed User Group (CUG) 
      facility, as follows:
      This attribute, if set to a value of allowed indicates that incoming 
      calls (from the network to the DTE) from the open (non-CUG) part 
      of the network are permitted. It also permits incoming calls from 
      DTEs that have Outgoing Access capabilities. If set to a value of 
      disallowed, then such calls cannot be made to this DNA - such calls 
      will be cleared by the local DCE.
      This attribute corresponds to the CCITT 'Closed User Group with 
      Incoming Access' feature for DNAs in that incoming access is 
      granted if this attribute is set to a value of allowed."
   DEFVAL     { disallowed }
::= { mscIpivcDnaIncomingOptionsEntry 9 }

mscIpivcDnaCallOptionsTable OBJECT-TYPE
   SYNTAX     SEQUENCE OF MscIpivcDnaCallOptionsEntry
   ACCESS     not-accessible
   STATUS     mandatory
   DESCRIPTION
     "DnaCallOptions group defines additional options for calls not 
      related directly to direction of a call."
::= { mscIpivcDna 13 }

mscIpivcDnaCallOptionsEntry OBJECT-TYPE
   SYNTAX     MscIpivcDnaCallOptionsEntry
   ACCESS     not-accessible
   STATUS     mandatory
   DESCRIPTION
     "An entry in the mscIpivcDnaCallOptionsTable."
   INDEX {
      mscIpivcIndex,
      mscIpivcDnaIndex }
::= { mscIpivcDnaCallOptionsTable 1 }

MscIpivcDnaCallOptionsEntry ::= SEQUENCE {
   mscIpivcDnaServiceCategory
      INTEGER,
   mscIpivcDnaPacketSizes
      OCTET STRING,
   mscIpivcDnaDefaultRecvFrmNetworkPacketSize
      INTEGER,
   mscIpivcDnaDefaultSendToNetworkPacketSize
      INTEGER,
   mscIpivcDnaDefaultRecvFrmNetworkThruputClass
      Unsigned32,
   mscIpivcDnaDefaultSendToNetworkThruputClass
      Unsigned32,
   mscIpivcDnaDefaultRecvFrmNetworkWindowSize
      Unsigned32,
   mscIpivcDnaDefaultSendToNetworkWindowSize
      Unsigned32,
   mscIpivcDnaPacketSizeNegotiation
      INTEGER,
   mscIpivcDnaAccountClass
      Unsigned32,
   mscIpivcDnaServiceExchange
      Unsigned32,
   mscIpivcDnaCugFormat
      INTEGER,
   mscIpivcDnaCug0AsNonCugCall
      INTEGER,
   mscIpivcDnaFastSelectCallsOnly
      INTEGER }

mscIpivcDnaServiceCategory OBJECT-TYPE
   SYNTAX     INTEGER  {
                 gsp(0),
                 x25(1),
                 enhancedIti(2),
                 ncs(3),
                 mlti(4),
                 sm(5),
                 ici(6),
                 dsp3270(7),
                 iam(8),
                 mlhi(9),
                 term3270(10),
                 iti(11),
                 bsi(13),
                 hostIti(14),
                 x75(15),
                 hdsp3270(16),
                 api3201(20),
                 sdlc(21),
                 snaMultiHost(22),
                 redirectionServ(23),
                 trSnaTpad(24),
                 offnetNui(25),
                 gasServer(26),
                 vapServer(28),
                 vapAgent(29),
                 frameRelay(30),
                 ipiVc(31) }
   ACCESS     read-only
   STATUS     mandatory
   DESCRIPTION
     "This attribute is computed based on the type of service within which 
      this DNA is configured. It is placed into the Service Category 
      attributes in the accounting record by both ends of the VC."
   DEFVAL     { ipiVc }
::= { mscIpivcDnaCallOptionsEntry 1 }

mscIpivcDnaPacketSizes OBJECT-TYPE
   SYNTAX     OCTET STRING (SIZE (2))
   ACCESS     read-only
   STATUS     mandatory
   DESCRIPTION
     "This attribute indicates the allowable packet sizes supported for 
      calls setup using this DNA.  To set a given packet size to be allowed 
      on the DNA, the packet size is entered, and the corresponding bit in 
      the structure is set to a value of 1.  To set a given packet size to be 
      disallowed on the DNA, the packet size is entered preceeded with 
      the '~' character, and the corresponding bit in the structure is set to a 
      value of 0. CCITT recommends that packet size 128 always be 
      supported.

      Description of bits:
      n16(0)
      n32(1)
      n64(2)
      n128(3)
      n256(4)
      n512(5)
      n1024(6)
      n2048(7)
      n4096(8)"
   DEFVAL     { '0100'H }
::= { mscIpivcDnaCallOptionsEntry 2 }

mscIpivcDnaDefaultRecvFrmNetworkPacketSize OBJECT-TYPE
   SYNTAX     INTEGER  {
                 n16(4),
                 n32(5),
                 n64(6),
                 n128(7),
                 n256(8),
                 n512(9),
                 n1024(10),
                 n2048(11),
                 n4096(12) }
   ACCESS     read-only
   STATUS     mandatory
   DESCRIPTION
     "This attribute indicates the default local receive packet size from 
      network to DTE for all calls using this particular DNA."
   DEFVAL     { n2048 }
::= { mscIpivcDnaCallOptionsEntry 3 }

mscIpivcDnaDefaultSendToNetworkPacketSize OBJECT-TYPE
   SYNTAX     INTEGER  {
                 n16(4),
                 n32(5),
                 n64(6),
                 n128(7),
                 n256(8),
                 n512(9),
                 n1024(10),
                 n2048(11),
                 n4096(12) }
   ACCESS     read-only
   STATUS     mandatory
   DESCRIPTION
     "This attribute indicates the default local send packet size from DTE 
      to network for all calls using this particular DNA."
   DEFVAL     { n2048 }
::= { mscIpivcDnaCallOptionsEntry 4 }

mscIpivcDnaDefaultRecvFrmNetworkThruputClass OBJECT-TYPE
   SYNTAX     Unsigned32 (0..15)
   ACCESS     read-only
   STATUS     mandatory
   DESCRIPTION
     "This attribute indicates the default receive throughput class for all 
      calls using this particular DNA."
   DEFVAL     { 10 }
::= { mscIpivcDnaCallOptionsEntry 5 }

mscIpivcDnaDefaultSendToNetworkThruputClass OBJECT-TYPE
   SYNTAX     Unsigned32 (0..15)
   ACCESS     read-only
   STATUS     mandatory
   DESCRIPTION
     "This attribute indicates the default send throughput class for all calls 
      using this particular DNA."
   DEFVAL     { 10 }
::= { mscIpivcDnaCallOptionsEntry 6 }

mscIpivcDnaDefaultRecvFrmNetworkWindowSize OBJECT-TYPE
   SYNTAX     Unsigned32 (1..7)
   ACCESS     read-only
   STATUS     mandatory
   DESCRIPTION
     "This attribute indicates the default number of data packets that can 
      be received by the DTE from the DCE before more packets can be 
      received. This view is oriented with respect to the DTE."
   DEFVAL     { 2 }
::= { mscIpivcDnaCallOptionsEntry 7 }

mscIpivcDnaDefaultSendToNetworkWindowSize OBJECT-TYPE
   SYNTAX     Unsigned32 (1..7)
   ACCESS     read-only
   STATUS     mandatory
   DESCRIPTION
     "This attribute indicates the number of data packets that can be 
      transmitted from the DTE to the DCE and must be acknowledged 
      before more packets can be transmitted."
   DEFVAL     { 2 }
::= { mscIpivcDnaCallOptionsEntry 8 }

mscIpivcDnaPacketSizeNegotiation OBJECT-TYPE
   SYNTAX     INTEGER  {
                 endToEnd(0),
                 local(1) }
   ACCESS     read-only
   STATUS     mandatory
   DESCRIPTION
     "This attribute, if set to a value of local indicates that packet sizes 
      can be negotiated locally at the interface irrespective of the remote 
      interface. If set to a value of endtoEnd, then local negotiation is not 
      permitted and packet sizes are negotiated between 2 ends of Vc."
   DEFVAL     { local }
::= { mscIpivcDnaCallOptionsEntry 9 }

mscIpivcDnaAccountClass OBJECT-TYPE
   SYNTAX     Unsigned32 (0..255)
   ACCESS     read-write
   STATUS     mandatory
   DESCRIPTION
     "This attribute specifies the accounting class which is reserved for 
      network operations usage. Its value is returned in the accounting 
      record in the local and remote service type attributes. Use of this 
      attribute is decided by network operator.
      This attribute is returned by the local VC in the accounting record 
      for all calls setup using this particular DNA."
   DEFVAL     { 0 }
::= { mscIpivcDnaCallOptionsEntry 10 }

mscIpivcDnaServiceExchange OBJECT-TYPE
   SYNTAX     Unsigned32 (0..255)
   ACCESS     read-write
   STATUS     mandatory
   DESCRIPTION
     "This attribute is an arbitrary number, Data Service Exchange, as 
      entered by the network operator and reported in accounting record. 
      It is converted into an internal 8-bit integer value for use in the 
      accounting record as well as in various X.25 and X.75 Tariff 
      utilities."
   DEFVAL     { 0 }
::= { mscIpivcDnaCallOptionsEntry 12 }

mscIpivcDnaCugFormat OBJECT-TYPE
   SYNTAX     INTEGER  {
                 basic(0),
                 extended(1) }
   ACCESS     read-only
   STATUS     mandatory
   DESCRIPTION
     "This attribute specifies which cug format is used when DTE signals 
      CUG indices, basic or extended.
      This attribute, if set to a value of extended indicates that the DTE 
      signals and receives CUG indices in extended CUG format.  If set 
      to a value of basic, then the DTE signals and receives CUG indices 
      in the basic CUG format."
   DEFVAL     { basic }
::= { mscIpivcDnaCallOptionsEntry 13 }

mscIpivcDnaCug0AsNonCugCall OBJECT-TYPE
   SYNTAX     INTEGER  {
                 disallowed(0),
                 allowed(1) }
   ACCESS     read-only
   STATUS     mandatory
   DESCRIPTION
     "This attribute, if set to a value of allowed indicates that when a 
      CUG index of 0 is signalled in a call request packet, the call is 
      treated as a non-CUG call.  If this attribute is set to a value of 
      disallowed, then a CUG index of 0 is treated as an index, and an 
      attempt is made to find the particular CUG corresponding with the 
      DNA."
   DEFVAL     { disallowed }
::= { mscIpivcDnaCallOptionsEntry 14 }

mscIpivcDnaFastSelectCallsOnly OBJECT-TYPE
   SYNTAX     INTEGER  {
                 no(0),
                 yes(1) }
   ACCESS     read-only
   STATUS     mandatory
   DESCRIPTION
     "This attribute, if set to a value of yes, indicates that the service is 
      permitted restricted fast select calls only in both the incoming and 
      the outgoing directions using this DNA. If set to a value of no, then 
      non fast select calls are permitted as well."
   DEFVAL     { no }
::= { mscIpivcDnaCallOptionsEntry 17 }


-- IpiVc Dna Cug
-- ClosedUserGroup options defines options associated with national 
-- or international Cug Identifier. Other Dna's in the network can have 
-- Cug's defined which groups these Dna's by Cug InterlockCode. If 
-- Dna's are defined with Cugs, calls from Dna's which do not have 
-- the same interlockCode defined are refused. Attributes incAccess 
-- and outAccess can override this rule.

mscIpivcDnaCug OBJECT IDENTIFIER ::= { mscIpivcDna 2 }



mscIpivcDnaCugRowStatusTable OBJECT-TYPE
   SYNTAX     SEQUENCE OF MscIpivcDnaCugRowStatusEntry
   ACCESS     not-accessible
   STATUS     mandatory
   DESCRIPTION
     "This entry controls the addition and deletion of 
      mscIpivcDnaCug components."
::= { mscIpivcDnaCug 1 }

mscIpivcDnaCugRowStatusEntry OBJECT-TYPE
   SYNTAX     MscIpivcDnaCugRowStatusEntry
   ACCESS     not-accessible
   STATUS     mandatory
   DESCRIPTION
     "A single entry in the table represents a single 
      mscIpivcDnaCug component."
   INDEX {
      mscIpivcIndex,
      mscIpivcDnaIndex,
      mscIpivcDnaCugIndex }
::= { mscIpivcDnaCugRowStatusTable 1 }

MscIpivcDnaCugRowStatusEntry ::= SEQUENCE {
   mscIpivcDnaCugRowStatus
      RowStatus,
   mscIpivcDnaCugComponentName
      DisplayString,
   mscIpivcDnaCugStorageType
      StorageType,
   mscIpivcDnaCugIndex
      NonReplicated }

mscIpivcDnaCugRowStatus OBJECT-TYPE
   SYNTAX     RowStatus 
   ACCESS     read-only
   STATUS     mandatory
   DESCRIPTION
     "This variable is used as the basis for SNMP naming of
      mscIpivcDnaCug components.
      These components cannot be added nor deleted."
::= { mscIpivcDnaCugRowStatusEntry 1 }

mscIpivcDnaCugComponentName OBJECT-TYPE
   SYNTAX     DisplayString 
   ACCESS     read-only
   STATUS     mandatory
   DESCRIPTION
     "This variable provides the component's string name for
      use with the ASCII Console Interface"
::= { mscIpivcDnaCugRowStatusEntry 2 }

mscIpivcDnaCugStorageType OBJECT-TYPE
   SYNTAX     StorageType 
   ACCESS     read-only
   STATUS     mandatory
   DESCRIPTION
     "This variable represents the storage type value for the
      mscIpivcDnaCug tables."
::= { mscIpivcDnaCugRowStatusEntry 4 }

mscIpivcDnaCugIndex OBJECT-TYPE
   SYNTAX     NonReplicated 
   ACCESS     not-accessible
   STATUS     mandatory
   DESCRIPTION
     "This variable represents the index for the mscIpivcDnaCug tables."
::= { mscIpivcDnaCugRowStatusEntry 10 }

mscIpivcDnaCugCugOptionsTable OBJECT-TYPE
   SYNTAX     SEQUENCE OF MscIpivcDnaCugCugOptionsEntry
   ACCESS     not-accessible
   STATUS     mandatory
   DESCRIPTION
     "This group defines options for Dna closed user group. Attributes in 
      this group define options associated with interlockCode. Dna's with 
      the same Cug (interlockCode) can make calls within this group. 
      Various combinations which permit or prevent calls in the same Cug 
      group are defined here."
::= { mscIpivcDnaCug 10 }

mscIpivcDnaCugCugOptionsEntry OBJECT-TYPE
   SYNTAX     MscIpivcDnaCugCugOptionsEntry
   ACCESS     not-accessible
   STATUS     mandatory
   DESCRIPTION
     "An entry in the mscIpivcDnaCugCugOptionsTable."
   INDEX {
      mscIpivcIndex,
      mscIpivcDnaIndex,
      mscIpivcDnaCugIndex }
::= { mscIpivcDnaCugCugOptionsTable 1 }

MscIpivcDnaCugCugOptionsEntry ::= SEQUENCE {
   mscIpivcDnaCugType
      INTEGER,
   mscIpivcDnaCugDnic
      DigitString,
   mscIpivcDnaCugInterlockCode
      Unsigned32,
   mscIpivcDnaCugOutCalls
      INTEGER,
   mscIpivcDnaCugIncCalls
      INTEGER,
   mscIpivcDnaCugPrivileged
      INTEGER }

mscIpivcDnaCugType OBJECT-TYPE
   SYNTAX     INTEGER  {
                 national(0),
                 international(1) }
   ACCESS     read-write
   STATUS     mandatory
   DESCRIPTION
     "This attribute specifies the CUG type - the CUG is either a national 
      CUG, or an international CUG.  International closed user groups are 
      usually established between DTEs for which there is an X.75 
      Gateway between; whereas national closed user groups are usually 
      established between DTEs for which there is no X.75 Gateway 
      between.  (National CUGs cannot normally traverse an X.75 
      Gateway).
      If this attribute is set to national, then the CUG is a national CUG, 
      in which case, the DNIC should be left at its default value of 
      BCD.0000 since it is not part of a national CUG.  If this attribute is 
      set to international, then the CUG is an international CUG, in 
      which case, the DNIC should be set appropriately as part of the 
      CUG interlock code."
   DEFVAL     { national }
::= { mscIpivcDnaCugCugOptionsEntry 1 }

mscIpivcDnaCugDnic OBJECT-TYPE
   SYNTAX     DigitString (SIZE (4))
   ACCESS     read-write
   STATUS     mandatory
   DESCRIPTION
     "This attribute specifies the DNIC (Data Network ID Code) of the 
      Cug by which packet networks are identified if the Cug is an 
      International Cug - it is specified as 4 BCD digits. This attribute is 
      not applicable if the Cug is a National Cug, as specified by the Cug 
      TYPE attribute. There are usually 1 or 2 DNICs assigned per 
      country, for public networks. The U.S. is an exception where each 
      BOC has a DNIC. Also, a group of private networks can have its 
      own DNIC.
      
      DNIC value is not an arbitrary number. It is assigned by 
      international aggreement and controlled by CCITT."
   DEFVAL     { '30303030'H }  -- "0000"
::= { mscIpivcDnaCugCugOptionsEntry 2 }

mscIpivcDnaCugInterlockCode OBJECT-TYPE
   SYNTAX     Unsigned32 (0..65535)
   ACCESS     read-write
   STATUS     mandatory
   DESCRIPTION
     "This attribute specifies the Cug Identifier of a national or 
      international Cug call. It is an arbitrary number and it also can be 
      called Cug in some descriptions. Interfaces (Dna's) defined with 
      this number can make calls to Dna's with the same interlockCode."
   DEFVAL     { 0 }
::= { mscIpivcDnaCugCugOptionsEntry 3 }

mscIpivcDnaCugOutCalls OBJECT-TYPE
   SYNTAX     INTEGER  {
                 disallowed(0),
                 allowed(1) }
   ACCESS     read-only
   STATUS     mandatory
   DESCRIPTION
     "This attribute, if set to a value of allowed indicates that outgoing 
      calls (from the DTE into the network) can be made using this 
      particular CUG. If set to a value of disallowed, then outgoing calls 
      cannot be made using this CUG - such calls will be cleared by the 
      local DCE.
      This attribute corresponds to the CCITT 'Outgoing Calls Barred' 
      feature for CUGs in that outgoing calls are barred if this attribute is 
      set to a value of disallowed."
   DEFVAL     { disallowed }
::= { mscIpivcDnaCugCugOptionsEntry 5 }

mscIpivcDnaCugIncCalls OBJECT-TYPE
   SYNTAX     INTEGER  {
                 disallowed(0),
                 allowed(1) }
   ACCESS     read-only
   STATUS     mandatory
   DESCRIPTION
     "This attribute, if set to a value of allowed indicates that incoming 
      calls (from the network to the DTE) can be made using this 
      particular CUG. If set to a value of disallowed, then incoming calls 
      cannot be made using this CUG - such calls will be cleared by the 
      local DCE.
      This attribute corresponds to the CCITT 'Incoming Calls Barred' 
      feature for CUGs in that incoming calls are barred if this attribute is 
      set to a value of disallowed."
   DEFVAL     { allowed }
::= { mscIpivcDnaCugCugOptionsEntry 6 }

mscIpivcDnaCugPrivileged OBJECT-TYPE
   SYNTAX     INTEGER  {
                 no(0),
                 yes(1) }
   ACCESS     read-write
   STATUS     mandatory
   DESCRIPTION
     "This attribute, if set to a value of yes indicates that this CUG is a 
      privileged CUG.  In DPN, at least one side of a call setup within a 
      CUG must have the CUG as a privileged CUG.  If set to a value of 
      no, then the CUG is not privileged.
      If both the local DTE and the remote DTE subscribe to the CUG, 
      but it is not privileged, then the call will be cleared.  This attribute is 
      typically used for a host DTE which must accept calls from many 
      other DTEs in which case the other DTEs cannot call one another, 
      but can call the host.  In this example, the host would have the 
      privileged CUG, and the other DTEs would belong to the same 
      CUG, but it would not be privileged."
   DEFVAL     { yes }
::= { mscIpivcDnaCugCugOptionsEntry 7 }


-- 
-- IpiVc DefaultRoute
-- 
-- This component contains information for setting up a default route 
-- on the IpiVc service.The default route feature permits establishment 
-- of a TCP/IP connection to the Software Distribution (SDS).
-- 

mscIpivcDr OBJECT IDENTIFIER ::= { mscIpivc 3 }



mscIpivcDrRowStatusTable OBJECT-TYPE
   SYNTAX     SEQUENCE OF MscIpivcDrRowStatusEntry
   ACCESS     not-accessible
   STATUS     mandatory
   DESCRIPTION
     "This entry controls the addition and deletion of 
      mscIpivcDr components."
::= { mscIpivcDr 1 }

mscIpivcDrRowStatusEntry OBJECT-TYPE
   SYNTAX     MscIpivcDrRowStatusEntry
   ACCESS     not-accessible
   STATUS     mandatory
   DESCRIPTION
     "A single entry in the table represents a single 
      mscIpivcDr component."
   INDEX {
      mscIpivcIndex,
      mscIpivcDrIndex }
::= { mscIpivcDrRowStatusTable 1 }

MscIpivcDrRowStatusEntry ::= SEQUENCE {
   mscIpivcDrRowStatus
      RowStatus,
   mscIpivcDrComponentName
      DisplayString,
   mscIpivcDrStorageType
      StorageType,
   mscIpivcDrIndex
      NonReplicated }

mscIpivcDrRowStatus OBJECT-TYPE
   SYNTAX     RowStatus 
   ACCESS     read-write
   STATUS     mandatory
   DESCRIPTION
     "This variable is used as the basis for SNMP naming of
      mscIpivcDr components.
      These components can be added and deleted."
::= { mscIpivcDrRowStatusEntry 1 }

mscIpivcDrComponentName OBJECT-TYPE
   SYNTAX     DisplayString 
   ACCESS     read-only
   STATUS     mandatory
   DESCRIPTION
     "This variable provides the component's string name for
      use with the ASCII Console Interface"
::= { mscIpivcDrRowStatusEntry 2 }

mscIpivcDrStorageType OBJECT-TYPE
   SYNTAX     StorageType 
   ACCESS     read-only
   STATUS     mandatory
   DESCRIPTION
     "This variable represents the storage type value for the
      mscIpivcDr tables."
::= { mscIpivcDrRowStatusEntry 4 }

mscIpivcDrIndex OBJECT-TYPE
   SYNTAX     NonReplicated 
   ACCESS     not-accessible
   STATUS     mandatory
   DESCRIPTION
     "This variable represents the index for the mscIpivcDr tables."
::= { mscIpivcDrRowStatusEntry 10 }

mscIpivcDrProvTable OBJECT-TYPE
   SYNTAX     SEQUENCE OF MscIpivcDrProvEntry
   ACCESS     not-accessible
   STATUS     mandatory
   DESCRIPTION
     "This group contains the provisionable attributes for setting up a 
      default route on the IpiVc service."
::= { mscIpivcDr 10 }

mscIpivcDrProvEntry OBJECT-TYPE
   SYNTAX     MscIpivcDrProvEntry
   ACCESS     not-accessible
   STATUS     mandatory
   DESCRIPTION
     "An entry in the mscIpivcDrProvTable."
   INDEX {
      mscIpivcIndex,
      mscIpivcDrIndex }
::= { mscIpivcDrProvTable 1 }

MscIpivcDrProvEntry ::= SEQUENCE {
   mscIpivcDrCallingIpAddress
      IpAddress,
   mscIpivcDrCallingNumberingPlanIndicator
      INTEGER,
   mscIpivcDrCallingDataNetworkAddress
      DigitString }

mscIpivcDrCallingIpAddress OBJECT-TYPE
   SYNTAX     IpAddress 
   ACCESS     read-write
   STATUS     mandatory
   DESCRIPTION
     "The field specifies the IP Address of the remote end, which issues 
      the X.25 call."
   DEFVAL     { '00000000'H }  -- "0.0.0.0"
::= { mscIpivcDrProvEntry 1 }

mscIpivcDrCallingNumberingPlanIndicator OBJECT-TYPE
   SYNTAX     INTEGER  {
                 x121(0),
                 e164(1) }
   ACCESS     read-write
   STATUS     mandatory
   DESCRIPTION
     "This field specifies the numbering plan of the address."
   DEFVAL     { x121 }
::= { mscIpivcDrProvEntry 2 }

mscIpivcDrCallingDataNetworkAddress OBJECT-TYPE
   SYNTAX     DigitString (SIZE (1..15))
   ACCESS     read-write
   STATUS     mandatory
   DESCRIPTION
     "This field specifies the address (in Binary Coded Decimal BCD 
      format) assigned to the remote end."
::= { mscIpivcDrProvEntry 3 }

-- 
-- *** THIS SUBTREE CURRENTLY NOT IMPLEMENTED ***
-- 

-- 
-- IpiVc Lcn/<n>
-- 
-- The Logical Channel Number responsible for the logical connection 
-- with the VC. There can be up to 24 instances of Lcn on the IpiVc 
-- component.

mscIpivcLcn OBJECT IDENTIFIER ::= { mscIpivc 4 }



mscIpivcLcnRowStatusTable OBJECT-TYPE
   SYNTAX     SEQUENCE OF MscIpivcLcnRowStatusEntry
   ACCESS     not-accessible
   STATUS     mandatory
   DESCRIPTION
     "*** THIS TABLE CURRENTLY NOT IMPLEMENTED ***

      This entry controls the addition and deletion of 
      mscIpivcLcn components."
::= { mscIpivcLcn 1 }

mscIpivcLcnRowStatusEntry OBJECT-TYPE
   SYNTAX     MscIpivcLcnRowStatusEntry
   ACCESS     not-accessible
   STATUS     mandatory
   DESCRIPTION
     "A single entry in the table represents a single 
      mscIpivcLcn component."
   INDEX {
      mscIpivcIndex,
      mscIpivcLcnIndex }
::= { mscIpivcLcnRowStatusTable 1 }

MscIpivcLcnRowStatusEntry ::= SEQUENCE {
   mscIpivcLcnRowStatus
      RowStatus,
   mscIpivcLcnComponentName
      DisplayString,
   mscIpivcLcnStorageType
      StorageType,
   mscIpivcLcnIndex
      Integer32 }

mscIpivcLcnRowStatus OBJECT-TYPE
   SYNTAX     RowStatus 
   ACCESS     read-only
   STATUS     mandatory
   DESCRIPTION
     "This variable is used as the basis for SNMP naming of
      mscIpivcLcn components.
      These components cannot be added nor deleted."
::= { mscIpivcLcnRowStatusEntry 1 }

mscIpivcLcnComponentName OBJECT-TYPE
   SYNTAX     DisplayString 
   ACCESS     read-only
   STATUS     mandatory
   DESCRIPTION
     "This variable provides the component's string name for
      use with the ASCII Console Interface"
::= { mscIpivcLcnRowStatusEntry 2 }

mscIpivcLcnStorageType OBJECT-TYPE
   SYNTAX     StorageType 
   ACCESS     read-only
   STATUS     mandatory
   DESCRIPTION
     "This variable represents the storage type value for the
      mscIpivcLcn tables."
::= { mscIpivcLcnRowStatusEntry 4 }

mscIpivcLcnIndex OBJECT-TYPE
   SYNTAX     Integer32 (16..39)
   ACCESS     not-accessible
   STATUS     mandatory
   DESCRIPTION
     "This variable represents the index for the mscIpivcLcn tables."
::= { mscIpivcLcnRowStatusEntry 10 }

mscIpivcLcnStateTable OBJECT-TYPE
   SYNTAX     SEQUENCE OF MscIpivcLcnStateEntry
   ACCESS     not-accessible
   STATUS     mandatory
   DESCRIPTION
     "*** THIS TABLE CURRENTLY NOT IMPLEMENTED ***

      This group contains the three OSI State attributes and the six OSI 
      Status attributes. The descriptions generically indicate what each 
      attribute implies about the component. Note that not all the values 
      and state combinations described here are supported by every 
      component which uses this group. For component-specific 
      information and the valid state combinations, refer to NTP 241-
      7001-150, Passport Operations and Maintenance Guide."
::= { mscIpivcLcn 10 }

mscIpivcLcnStateEntry OBJECT-TYPE
   SYNTAX     MscIpivcLcnStateEntry
   ACCESS     not-accessible
   STATUS     mandatory
   DESCRIPTION
     "An entry in the mscIpivcLcnStateTable."
   INDEX {
      mscIpivcIndex,
      mscIpivcLcnIndex }
::= { mscIpivcLcnStateTable 1 }

MscIpivcLcnStateEntry ::= SEQUENCE {
   mscIpivcLcnAdminState
      INTEGER,
   mscIpivcLcnOperationalState
      INTEGER,
   mscIpivcLcnUsageState
      INTEGER,
   mscIpivcLcnAvailabilityStatus
      OCTET STRING,
   mscIpivcLcnProceduralStatus
      OCTET STRING,
   mscIpivcLcnControlStatus
      OCTET STRING,
   mscIpivcLcnAlarmStatus
      OCTET STRING,
   mscIpivcLcnStandbyStatus
      INTEGER,
   mscIpivcLcnUnknownStatus
      INTEGER }

mscIpivcLcnAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component.
      
      The OSI Status attributes, if supported by the component, may 
      provide more details, qualifying the state of the component."
   DEFVAL     { unlocked }
::= { mscIpivcLcnStateEntry 1 }

mscIpivcLcnOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle.
      
      The OSI Status attributes, if supported by the component, may 
      provide more details, qualifying the state of the component."
   DEFVAL     { disabled }
::= { mscIpivcLcnStateEntry 2 }

mscIpivcLcnUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time.
      
      The OSI Status attributes, if supported by the component, may 
      provide more details, qualifying the state of the component."
   DEFVAL     { idle }
::= { mscIpivcLcnStateEntry 3 }

mscIpivcLcnAvailabilityStatus OBJECT-TYPE
   SYNTAX     OCTET STRING (SIZE (2))
   ACCESS     read-only
   STATUS     mandatory
   DESCRIPTION
     "If supported by the component, this attribute indicates the OSI 
      Availability status of the component. Note that, even though it is 
      defined as a multi-valued set, at most one value is shown to the user.
      
      When no values are in the set, this indicates that either the attribute 
      is not supported or that none of the status conditions described 
      below are present.
      
      The value inTest indicates that the resource is undergoing a test 
      procedure. If adminState is locked or shuttingDown, the normal 
      users are precluded from using the resource and controlStatus is 
      reservedForTest. Tests that do not exclude additional users can be 
      present in any operational or administrative state but the 
      reservedForTest condition should not be present.
      
      The value failed indicates that the component has an internal fault 
      that prevents it from operating. The operationalState is disabled.
      
      The value dependency indicates that the component cannot operate 
      because some other resource on which it depends is unavailable. 
      The operationalState is disabled.
      
      The value powerOff indicates the resource requires power to be 
      applied and it is not powered on. The operationalState is disabled.
      
      The value offLine indicates the resource requires a routine 
      operation (either manual, automatic, or both) to be performed to 
      place it on-line and make it available for use. The operationalState 
      is disabled.
      
      The value offDuty indicates the resource is inactive in accordance 
      with a predetermined time schedule. In the absence of other 
      disabling conditions, the operationalState is enabled or disabled.
      
      The value degraded indicates the service provided by the 
      component is degraded in some way, such as in speed or operating 
      capacity. However, the resource remains available for service. The 
      operationalState is enabled.
      
      The value notInstalled indicates the resource is not present. The 
      operationalState is disabled.
      
      The value logFull is not used.

      Description of bits:
      inTest(0)
      failed(1)
      powerOff(2)
      offLine(3)
      offDuty(4)
      dependency(5)
      degraded(6)
      notInstalled(7)
      logFull(8)"
::= { mscIpivcLcnStateEntry 4 }

mscIpivcLcnProceduralStatus OBJECT-TYPE
   SYNTAX     OCTET STRING (SIZE (1))
   ACCESS     read-only
   STATUS     mandatory
   DESCRIPTION
     "If supported by the component, this attribute indicates the OSI 
      Procedural status of the component. Note that, even though it is 
      defined as a multi-valued set, at most one value is shown to the user.
      
      When no values are in the set, this indicates that either the attribute 
      is not supported or that none of the status conditions described 
      below are present.
      
      The value initializationRequired indicates (for a resource which 
      doesn't initialize autonomously) that initialization is required before 
      it can perform its normal functions, and this procedure has not been 
      initiated. The operationalState is disabled.
      
      The value notInitialized indicates (for a resource which does 
      initialize autonomously) that initialization is required before it can 
      perform its normal functions, and this procedure has not been 
      initiated. The operationalState may be enabled or disabled.
      
      The value initializing indicates that initialization has been initiated 
      but is not yet complete. The operationalState may be enabled or 
      disabled.
      
      The value reporting indicates the resource has completed some 
      processing operation and is notifying the results. The 
      operationalState is enabled.
      
      The value terminating indicates the component is in a termination 
      phase. If the resource doesn't reinitialize autonomously, 
      operationalState is disabled; otherwise it is enabled or disabled.

      Description of bits:
      initializationRequired(0)
      notInitialized(1)
      initializing(2)
      reporting(3)
      terminating(4)"
::= { mscIpivcLcnStateEntry 5 }

mscIpivcLcnControlStatus OBJECT-TYPE
   SYNTAX     OCTET STRING (SIZE (1))
   ACCESS     read-only
   STATUS     mandatory
   DESCRIPTION
     "If supported by the component, this attribute indicates the OSI 
      Control status of the component. Note that, even though it is defined 
      as a multi-valued set, at most one value is shown to the user.
      
      When no values are in the set, this indicates that either the attribute 
      is not supported or that none of the status conditions described 
      below are present.
      
      The value subjectToTest indicates the resource is available but tests 
      may be conducted simultaneously at unpredictable times, which 
      may cause it to exhibit unusual characteristics.
      
      The value partOfServicesLocked indicates that part of the service is 
      restricted from users of a resource. The adminState is unlocked.
      
      The value reservedForTest indicates that the component is 
      administratively unavailable because it is undergoing a test 
      procedure. The adminState is locked.
      
      The value suspended indicates that the service has been 
      administratively suspended.

      Description of bits:
      subjectToTest(0)
      partOfServicesLocked(1)
      reservedForTest(2)
      suspended(3)"
::= { mscIpivcLcnStateEntry 6 }

mscIpivcLcnAlarmStatus OBJECT-TYPE
   SYNTAX     OCTET STRING (SIZE (1))
   ACCESS     read-only
   STATUS     mandatory
   DESCRIPTION
     "If supported by the component, this attribute indicates the OSI 
      Alarm status of the component. Note that, even though it is defined 
      as a multi-valued set, at most one value is shown to the user.
      
      When no values are in the set, this indicates that either the attribute 
      is not supported or that none of the status conditions described 
      below are present.
      
      The value underRepair indicates the component is currently being 
      repaired. The operationalState is enabled or disabled.
      
      The value critical indicates one or more critical alarms are 
      outstanding against the component. Other, less severe, alarms may 
      also be outstanding. The operationalState is enabled or disabled.
      
      The value major indicates one or more major alarms are 
      outstanding against the component. Other, less severe, alarms may 
      also be outstanding. The operationalState is enabled or disabled.
      
      The value minor indicates one or more minor alarms are 
      outstanding against the component. Other, less severe, alarms may 
      also be outstanding. The operationalState is enabled or disabled.
      
      The value alarmOutstanding generically indicates that an alarm of 
      some severity is outstanding against the component.

      Description of bits:
      underRepair(0)
      critical(1)
      major(2)
      minor(3)
      alarmOutstanding(4)"
::= { mscIpivcLcnStateEntry 7 }

mscIpivcLcnStandbyStatus OBJECT-TYPE
   SYNTAX     INTEGER  {
                 hotStandby(0),
                 coldStandby(1),
                 providingService(2),
                 notSet(15) }
   ACCESS     read-only
   STATUS     mandatory
   DESCRIPTION
     "If supported by the component, this attribute indicates the OSI 
      Standby status of the component.
      
      The value notSet indicates that either the attribute is not supported 
      or that none of the status conditions described below are present. 
      Note that this is a non-standard value, used because the original 
      specification indicated this attribute was set-valued and thus, did not 
      provide a value to indicate that none of the other three are 
      applicable.
      
      The value hotStandby indicates that the resource is not providing 
      service but will be immediately able to take over the role of the 
      resource to be backed up, without initialization activity, and 
      containing the same information as the resource to be backed up.
      
      The value coldStandby indicates the resource is a backup for 
      another resource but will not be immediately able to take over the 
      role of the backed up resource and will require some initialization 
      activity.
      
      The value providingService indicates that this component, as a 
      backup resource, is currently backing up another resource."
   DEFVAL     { notSet }
::= { mscIpivcLcnStateEntry 8 }

mscIpivcLcnUnknownStatus OBJECT-TYPE
   SYNTAX     INTEGER  {
                 false(0),
                 true(1) }
   ACCESS     read-only
   STATUS     mandatory
   DESCRIPTION
     "This attribute indicates the OSI Unknown status of the component.
      
      The value false indicates that all of the other OSI State and Status 
      attribute values can be considered accurate.
      
      The value true indicates that the actual state of the component is not 
      known for sure."
   DEFVAL     { false }
::= { mscIpivcLcnStateEntry 9 }

mscIpivcLcnOperTable OBJECT-TYPE
   SYNTAX     SEQUENCE OF MscIpivcLcnOperEntry
   ACCESS     not-accessible
   STATUS     mandatory
   DESCRIPTION
     "*** THIS TABLE CURRENTLY NOT IMPLEMENTED ***

      This group contains status of the internal IP network interface."
::= { mscIpivcLcn 11 }

mscIpivcLcnOperEntry OBJECT-TYPE
   SYNTAX     MscIpivcLcnOperEntry
   ACCESS     not-accessible
   STATUS     mandatory
   DESCRIPTION
     "An entry in the mscIpivcLcnOperTable."
   INDEX {
      mscIpivcIndex,
      mscIpivcLcnIndex }
::= { mscIpivcLcnOperTable 1 }

MscIpivcLcnOperEntry ::= SEQUENCE {
   mscIpivcLcnIpInterfaceDevice
      INTEGER,
   mscIpivcLcnDestinationIpAddress
      IpAddress,
   mscIpivcLcnPacketsSent
      Counter32,
   mscIpivcLcnPacketsReceived
      Counter32,
   mscIpivcLcnDiscardTxPackets
      Counter32,
   mscIpivcLcnDiscardRcvPackets
      Counter32 }

mscIpivcLcnIpInterfaceDevice OBJECT-TYPE
   SYNTAX     INTEGER  {
                 inactive(0),
                 active(1) }
   ACCESS     read-only
   STATUS     mandatory
   DESCRIPTION
     "The status of the internal IP network interface is inactive until an IP 
      packet is exchanged between a Network Management Station and 
      the internal IP network interface (via the LCN). At this point, the 
      status changes to active."
   DEFVAL     { inactive }
::= { mscIpivcLcnOperEntry 1 }

mscIpivcLcnDestinationIpAddress OBJECT-TYPE
   SYNTAX     IpAddress 
   ACCESS     read-only
   STATUS     mandatory
   DESCRIPTION
     "This attribute specifies the IP address of the remote network device 
      connected to this interface. The destinationIpAddress default is 
      0.0.0.0, until the first data packet is received from the remote end."
   DEFVAL     { '00000000'H }  -- "0.0.0.0"
::= { mscIpivcLcnOperEntry 2 }

mscIpivcLcnPacketsSent OBJECT-TYPE
   SYNTAX     Counter32 
   ACCESS     read-only
   STATUS     mandatory
   DESCRIPTION
     "This attribute counts the number of IP packets sent from this 
      interface."
::= { mscIpivcLcnOperEntry 3 }

mscIpivcLcnPacketsReceived OBJECT-TYPE
   SYNTAX     Counter32 
   ACCESS     read-only
   STATUS     mandatory
   DESCRIPTION
     "This attribute counts the number of IP packets received from the 
      remote network device."
::= { mscIpivcLcnOperEntry 4 }

mscIpivcLcnDiscardTxPackets OBJECT-TYPE
   SYNTAX     Counter32 
   ACCESS     read-only
   STATUS     mandatory
   DESCRIPTION
     "This attribute counts the number of IP packets destined to the 
      remote end which were discarded by the interface."
::= { mscIpivcLcnOperEntry 5 }

mscIpivcLcnDiscardRcvPackets OBJECT-TYPE
   SYNTAX     Counter32 
   ACCESS     read-only
   STATUS     mandatory
   DESCRIPTION
     "This attribute counts number of IP packets received from the remote 
      end which were discarded by this interface."
::= { mscIpivcLcnOperEntry 6 }

-- 
-- *** THIS SUBTREE CURRENTLY NOT IMPLEMENTED ***
-- 

-- ... Vc()
-- This component defines display of general Vc dynamic attributes

mscIpivcLcnVc OBJECT IDENTIFIER ::= { mscIpivcLcn 2 }



mscIpivcLcnVcRowStatusTable OBJECT-TYPE
   SYNTAX     SEQUENCE OF MscIpivcLcnVcRowStatusEntry
   ACCESS     not-accessible
   STATUS     mandatory
   DESCRIPTION
     "*** THIS TABLE CURRENTLY NOT IMPLEMENTED ***

      This entry controls the addition and deletion of 
      mscIpivcLcnVc components."
::= { mscIpivcLcnVc 1 }

mscIpivcLcnVcRowStatusEntry OBJECT-TYPE
   SYNTAX     MscIpivcLcnVcRowStatusEntry
   ACCESS     not-accessible
   STATUS     mandatory
   DESCRIPTION
     "A single entry in the table represents a single 
      mscIpivcLcnVc component."
   INDEX {
      mscIpivcIndex,
      mscIpivcLcnIndex,
      mscIpivcLcnVcIndex }
::= { mscIpivcLcnVcRowStatusTable 1 }

MscIpivcLcnVcRowStatusEntry ::= SEQUENCE {
   mscIpivcLcnVcRowStatus
      RowStatus,
   mscIpivcLcnVcComponentName
      DisplayString,
   mscIpivcLcnVcStorageType
      StorageType,
   mscIpivcLcnVcIndex
      NonReplicated }

mscIpivcLcnVcRowStatus OBJECT-TYPE
   SYNTAX     RowStatus 
   ACCESS     read-only
   STATUS     mandatory
   DESCRIPTION
     "This variable is used as the basis for SNMP naming of
      mscIpivcLcnVc components.
      These components cannot be added nor deleted."
::= { mscIpivcLcnVcRowStatusEntry 1 }

mscIpivcLcnVcComponentName OBJECT-TYPE
   SYNTAX     DisplayString 
   ACCESS     read-only
   STATUS     mandatory
   DESCRIPTION
     "This variable provides the component's string name for
      use with the ASCII Console Interface"
::= { mscIpivcLcnVcRowStatusEntry 2 }

mscIpivcLcnVcStorageType OBJECT-TYPE
   SYNTAX     StorageType 
   ACCESS     read-only
   STATUS     mandatory
   DESCRIPTION
     "This variable represents the storage type value for the
      mscIpivcLcnVc tables."
::= { mscIpivcLcnVcRowStatusEntry 4 }

mscIpivcLcnVcIndex OBJECT-TYPE
   SYNTAX     NonReplicated 
   ACCESS     not-accessible
   STATUS     mandatory
   DESCRIPTION
     "This variable represents the index for the mscIpivcLcnVc tables."
::= { mscIpivcLcnVcRowStatusEntry 10 }

mscIpivcLcnVcCadTable OBJECT-TYPE
   SYNTAX     SEQUENCE OF MscIpivcLcnVcCadEntry
   ACCESS     not-accessible
   STATUS     mandatory
   DESCRIPTION
     "*** THIS TABLE CURRENTLY NOT IMPLEMENTED ***

      This group represents operational call data related to General Vc. It 
      can be displayed only for General Vc which is created by 
      application."
::= { mscIpivcLcnVc 10 }

mscIpivcLcnVcCadEntry OBJECT-TYPE
   SYNTAX     MscIpivcLcnVcCadEntry
   ACCESS     not-accessible
   STATUS     mandatory
   DESCRIPTION
     "An entry in the mscIpivcLcnVcCadTable."
   INDEX {
      mscIpivcIndex,
      mscIpivcLcnIndex,
      mscIpivcLcnVcIndex }
::= { mscIpivcLcnVcCadTable 1 }

MscIpivcLcnVcCadEntry ::= SEQUENCE {
   mscIpivcLcnVcType
      INTEGER,
   mscIpivcLcnVcState
      INTEGER,
   mscIpivcLcnVcPreviousState
      INTEGER,
   mscIpivcLcnVcDiagnosticCode
      Unsigned32,
   mscIpivcLcnVcPreviousDiagnosticCode
      Unsigned32,
   mscIpivcLcnVcCalledNpi
      INTEGER,
   mscIpivcLcnVcCalledDna
      DigitString,
   mscIpivcLcnVcCalledLcn
      Unsigned32,
   mscIpivcLcnVcCallingNpi
      INTEGER,
   mscIpivcLcnVcCallingDna
      DigitString,
   mscIpivcLcnVcCallingLcn
      Unsigned32,
   mscIpivcLcnVcAccountingEnabled
      INTEGER,
   mscIpivcLcnVcFastSelectCall
      INTEGER,
   mscIpivcLcnVcLocalRxPktSize
      INTEGER,
   mscIpivcLcnVcLocalTxPktSize
      INTEGER,
   mscIpivcLcnVcLocalTxWindowSize
      Unsigned32,
   mscIpivcLcnVcLocalRxWindowSize
      Unsigned32,
   mscIpivcLcnVcPathReliability
      INTEGER,
   mscIpivcLcnVcAccountingEnd
      INTEGER,
   mscIpivcLcnVcPriority
      INTEGER,
   mscIpivcLcnVcSegmentSize
      Unsigned32,
   mscIpivcLcnVcSubnetTxPktSize
      INTEGER,
   mscIpivcLcnVcSubnetTxWindowSize
      Unsigned32,
   mscIpivcLcnVcSubnetRxPktSize
      INTEGER,
   mscIpivcLcnVcSubnetRxWindowSize
      Unsigned32,
   mscIpivcLcnVcMaxSubnetPktSize
      Unsigned32,
   mscIpivcLcnVcTransferPriorityToNetwork
      INTEGER,
   mscIpivcLcnVcTransferPriorityFromNetwork
      INTEGER }

mscIpivcLcnVcType OBJECT-TYPE
   SYNTAX     INTEGER  {
                 svc(0),
                 pvc(1) }
   ACCESS     read-only
   STATUS     mandatory
   DESCRIPTION
     "This attribute displays the type of call, pvc or svc. type is provided 
      at provisioning time."
::= { mscIpivcLcnVcCadEntry 1 }

mscIpivcLcnVcState OBJECT-TYPE
   SYNTAX     INTEGER  {
                 creating(0),
                 readyP1(1),
                 dteWaitingP2(2),
                 dceWaitingP3(3),
                 dataTransferP4(4),
                 unsupportedP5(5),
                 dteClearRequestP6(6),
                 dceClearIndicationP7(7),
                 termination(8) }
   ACCESS     read-only
   STATUS     mandatory
   DESCRIPTION
     "This attribute displays the state of call control. P5 state is not 
      supported but is listed for completness. Transitions from one state to 
      another take very short time. state most often displayed is 
      dataTransferP4."
::= { mscIpivcLcnVcCadEntry 2 }

mscIpivcLcnVcPreviousState OBJECT-TYPE
   SYNTAX     INTEGER  {
                 creating(0),
                 readyP1(1),
                 dteWaitingP2(2),
                 dceWaitingP3(3),
                 dataTransferP4(4),
                 unsupportedP5(5),
                 dteClearRequestP6(6),
                 dceClearIndicationP7(7),
                 termination(8) }
   ACCESS     read-only
   STATUS     mandatory
   DESCRIPTION
     "This attribute displays the previous state of call control. This is a 
      valuable field to determine how the processing is progressing."
::= { mscIpivcLcnVcCadEntry 3 }

mscIpivcLcnVcDiagnosticCode OBJECT-TYPE
   SYNTAX     Unsigned32 (0..255)
   ACCESS     read-only
   STATUS     mandatory
   DESCRIPTION
     "This attribute displays the internal substate of call control. It is used 
      to further refine state of call processing."
::= { mscIpivcLcnVcCadEntry 4 }

mscIpivcLcnVcPreviousDiagnosticCode OBJECT-TYPE
   SYNTAX     Unsigned32 (0..255)
   ACCESS     read-only
   STATUS     mandatory
   DESCRIPTION
     "This attribute displays the internal substate of call control. It is used 
      to further refine state of call processing."
::= { mscIpivcLcnVcCadEntry 5 }

mscIpivcLcnVcCalledNpi OBJECT-TYPE
   SYNTAX     INTEGER  {
                 x121(0),
                 e164(1) }
   ACCESS     read-only
   STATUS     mandatory
   DESCRIPTION
     "This attribute displays the Numbering Plan Indicator (NPI) of the 
      called end."
::= { mscIpivcLcnVcCadEntry 6 }

mscIpivcLcnVcCalledDna OBJECT-TYPE
   SYNTAX     DigitString (SIZE (1..15))
   ACCESS     read-only
   STATUS     mandatory
   DESCRIPTION
     "This attribute displays the Data Network Address (Dna) of the 
      called (destination) DTE to which this call is sent. This address if 
      defined at recieving end will complete Vc connection."
::= { mscIpivcLcnVcCadEntry 7 }

mscIpivcLcnVcCalledLcn OBJECT-TYPE
   SYNTAX     Unsigned32 (1..65535)
   ACCESS     read-only
   STATUS     mandatory
   DESCRIPTION
     "This attribute displays the Logical Channel Number of the called 
      end. It is valid only after both ends of Vc exchanged relevant 
      information."
::= { mscIpivcLcnVcCadEntry 8 }

mscIpivcLcnVcCallingNpi OBJECT-TYPE
   SYNTAX     INTEGER  {
                 x121(0),
                 e164(1) }
   ACCESS     read-only
   STATUS     mandatory
   DESCRIPTION
     "This attribute displays the Numbering Plan Indicator (NPI) of the 
      calling end."
::= { mscIpivcLcnVcCadEntry 9 }

mscIpivcLcnVcCallingDna OBJECT-TYPE
   SYNTAX     DigitString (SIZE (1..15))
   ACCESS     read-only
   STATUS     mandatory
   DESCRIPTION
     "This attribute displays the Data Network Address (Dna) of the 
      calling end."
::= { mscIpivcLcnVcCadEntry 10 }

mscIpivcLcnVcCallingLcn OBJECT-TYPE
   SYNTAX     Unsigned32 (1..65535)
   ACCESS     read-only
   STATUS     mandatory
   DESCRIPTION
     "This attribute displays the Logical Channel Number of the calling 
      end."
::= { mscIpivcLcnVcCadEntry 11 }

mscIpivcLcnVcAccountingEnabled OBJECT-TYPE
   SYNTAX     INTEGER  {
                 yes(0),
                 no(1) }
   ACCESS     read-only
   STATUS     mandatory
   DESCRIPTION
     "This attribute indicates that this optional section of accounting 
      record is suppressed or permitted. If accountingEnabled is yes, 
      conditions for generation of accounting record were met. These 
      conditions include billing options, vc recovery conditions and 
      Module wide accounting data options."
::= { mscIpivcLcnVcCadEntry 12 }

mscIpivcLcnVcFastSelectCall OBJECT-TYPE
   SYNTAX     INTEGER  {
                 no(0),
                 yes(1) }
   ACCESS     read-only
   STATUS     mandatory
   DESCRIPTION
     "This attribute displays that this is a fast select call."
::= { mscIpivcLcnVcCadEntry 13 }

mscIpivcLcnVcLocalRxPktSize OBJECT-TYPE
   SYNTAX     INTEGER  {
                 unknown(0),
                 n16(4),
                 n32(5),
                 n64(6),
                 n128(7),
                 n256(8),
                 n512(9),
                 n1024(10),
                 n2048(11),
                 n4096(12) }
   ACCESS     read-only
   STATUS     mandatory
   DESCRIPTION
     "This attribute displays the locally negotiated size of send packets."
::= { mscIpivcLcnVcCadEntry 14 }

mscIpivcLcnVcLocalTxPktSize OBJECT-TYPE
   SYNTAX     INTEGER  {
                 unknown(0),
                 n16(4),
                 n32(5),
                 n64(6),
                 n128(7),
                 n256(8),
                 n512(9),
                 n1024(10),
                 n2048(11),
                 n4096(12) }
   ACCESS     read-only
   STATUS     mandatory
   DESCRIPTION
     "This attribute displays the locally negotiated size of send packets."
::= { mscIpivcLcnVcCadEntry 15 }

mscIpivcLcnVcLocalTxWindowSize OBJECT-TYPE
   SYNTAX     Unsigned32 (0..127)
   ACCESS     read-only
   STATUS     mandatory
   DESCRIPTION
     "This attribute displays the send window size provided on incoming 
      call packets or the default when a call request packet does not 
      explicitly provide the window size."
::= { mscIpivcLcnVcCadEntry 16 }

mscIpivcLcnVcLocalRxWindowSize OBJECT-TYPE
   SYNTAX     Unsigned32 (0..127)
   ACCESS     read-only
   STATUS     mandatory
   DESCRIPTION
     "This attribute displays the receive window size provided on 
      incoming call packets or the default when a call request does not 
      explicitly provide the window sizes."
::= { mscIpivcLcnVcCadEntry 17 }

mscIpivcLcnVcPathReliability OBJECT-TYPE
   SYNTAX     INTEGER  {
                 high(0),
                 normal(1) }
   ACCESS     read-only
   STATUS     mandatory
   DESCRIPTION
     "This attribute displays the path reliability."
::= { mscIpivcLcnVcCadEntry 19 }

mscIpivcLcnVcAccountingEnd OBJECT-TYPE
   SYNTAX     INTEGER  {
                 callingEnd(0),
                 calledEnd(1) }
   ACCESS     read-only
   STATUS     mandatory
   DESCRIPTION
     "This attribute indicates if this end should generate an accounting 
      record. Normally, callingEnd is the end to generate an accounting 
      record."
::= { mscIpivcLcnVcCadEntry 20 }

mscIpivcLcnVcPriority OBJECT-TYPE
   SYNTAX     INTEGER  {
                 normal(0),
                 high(1) }
   ACCESS     read-only
   STATUS     mandatory
   DESCRIPTION
     "This attribute displays whether the call is a normal or a high 
      priority call."
::= { mscIpivcLcnVcCadEntry 21 }

mscIpivcLcnVcSegmentSize OBJECT-TYPE
   SYNTAX     Unsigned32 (0..4096)
   ACCESS     read-only
   STATUS     mandatory
   DESCRIPTION
     "This attribute displays the segment size (in bytes) used on the call. 
      It is used to calculate the number of segments transmitted and 
      received."
::= { mscIpivcLcnVcCadEntry 22 }

mscIpivcLcnVcSubnetTxPktSize OBJECT-TYPE
   SYNTAX     INTEGER  {
                 unknown(0),
                 n16(4),
                 n32(5),
                 n64(6),
                 n128(7),
                 n256(8),
                 n512(9),
                 n1024(10),
                 n2048(11),
                 n4096(12) }
   ACCESS     read-only
   STATUS     mandatory
   DESCRIPTION
     "This attribute displays the locally negotiated size of the data packets 
      on this Vc."
::= { mscIpivcLcnVcCadEntry 23 }

mscIpivcLcnVcSubnetTxWindowSize OBJECT-TYPE
   SYNTAX     Unsigned32 (0..4096)
   ACCESS     read-only
   STATUS     mandatory
   DESCRIPTION
     "This attribute displays the current send window size of Vc."
::= { mscIpivcLcnVcCadEntry 24 }

mscIpivcLcnVcSubnetRxPktSize OBJECT-TYPE
   SYNTAX     INTEGER  {
                 unknown(0),
                 n16(4),
                 n32(5),
                 n64(6),
                 n128(7),
                 n256(8),
                 n512(9),
                 n1024(10),
                 n2048(11),
                 n4096(12) }
   ACCESS     read-only
   STATUS     mandatory
   DESCRIPTION
     "This attribute displays the locally negotiated size of receive packets."
::= { mscIpivcLcnVcCadEntry 25 }

mscIpivcLcnVcSubnetRxWindowSize OBJECT-TYPE
   SYNTAX     Unsigned32 (0..4096)
   ACCESS     read-only
   STATUS     mandatory
   DESCRIPTION
     "This attribute displays the receive window size provided on 
      incoming call packets and to the default when a call request does 
      not explicitly provide the window sizes."
::= { mscIpivcLcnVcCadEntry 26 }

mscIpivcLcnVcMaxSubnetPktSize OBJECT-TYPE
   SYNTAX     Unsigned32 (0..4096)
   ACCESS     read-only
   STATUS     mandatory
   DESCRIPTION
     "This attribute displays the maximum packet size allowed on Vc."
::= { mscIpivcLcnVcCadEntry 27 }

mscIpivcLcnVcTransferPriorityToNetwork OBJECT-TYPE
   SYNTAX     INTEGER  {
                 normal(0),
                 high(9) }
   ACCESS     read-only
   STATUS     mandatory
   DESCRIPTION
     "This attribute displays the priority in which data is transferred to the 
      network.
      
      The transfer priority is a preference specified by an application 
      according to its delay-sensitivity requirement. Frames with high
      transfer priority are served by the network before the frames with 
      normal priority. 
      
      Each transfer priority contains a predetermined setting for trunk 
      queue (interrupting, delay or throughput), and routing metric (delay 
      or throughput).
      
      When the transfer priority is set at high, the trunk queue is set to 
      high, the routing metric is set to delay.
      
      When the transfer priority is set at normal, the trunk queue is set to 
      normal, the routing metric is set to throughput."
::= { mscIpivcLcnVcCadEntry 28 }

mscIpivcLcnVcTransferPriorityFromNetwork OBJECT-TYPE
   SYNTAX     INTEGER  {
                 normal(0),
                 high(9) }
   ACCESS     read-only
   STATUS     mandatory
   DESCRIPTION
     "This attribute displays the priority in which data is transferred from 
      the network.
      
      The transfer priority is a preference specified by an application 
      according to its delay-sensitivity requirement. Frames with high
      transfer priority are served by the network before the frames with 
      normal priority. 
      
      Each transfer priority contains a predetermined setting for trunk 
      queue (interrupting, delay or throughput), and routing metric (delay 
      or throughput). 
      
      When the transfer priority is set at high, and the trunk queue is set 
      to high, the routing metric is set to delay.
      
      When the transfer priority is set at normal, the trunk queue is set to 
      normal, and the routing metric is set to throughput."
::= { mscIpivcLcnVcCadEntry 29 }

mscIpivcLcnVcIntdTable OBJECT-TYPE
   SYNTAX     SEQUENCE OF MscIpivcLcnVcIntdEntry
   ACCESS     not-accessible
   STATUS     mandatory
   DESCRIPTION
     "*** THIS TABLE CURRENTLY NOT IMPLEMENTED ***

      This group defines display of interval data collected by Vc. Data in 
      this group is variable and may depend on time when this display 
      command is issued."
::= { mscIpivcLcnVc 11 }

mscIpivcLcnVcIntdEntry OBJECT-TYPE
   SYNTAX     MscIpivcLcnVcIntdEntry
   ACCESS     not-accessible
   STATUS     mandatory
   DESCRIPTION
     "An entry in the mscIpivcLcnVcIntdTable."
   INDEX {
      mscIpivcIndex,
      mscIpivcLcnIndex,
      mscIpivcLcnVcIndex }
::= { mscIpivcLcnVcIntdTable 1 }

MscIpivcLcnVcIntdEntry ::= SEQUENCE {
   mscIpivcLcnVcCallReferenceNumber
      Hex,
   mscIpivcLcnVcElapsedTimeTillNow
      Unsigned32,
   mscIpivcLcnVcSegmentsRx
      Unsigned32,
   mscIpivcLcnVcSegmentsSent
      Unsigned32,
   mscIpivcLcnVcStartTime
      EnterpriseDateAndTime,
   mscIpivcLcnVcCallReferenceNumberDecimal
      Unsigned32 }

mscIpivcLcnVcCallReferenceNumber OBJECT-TYPE
   SYNTAX     Hex (0..16777215)
   ACCESS     read-only
   STATUS     obsolete
   DESCRIPTION
     "This attribute is obsolete. It is replaced by the callReferenceNumber 
      attribute to display the call reference number in decimal. The 
      SNMP reference for the callReferenceNumber attribute is 
      callReferenceNumberDecimal."
::= { mscIpivcLcnVcIntdEntry 1 }

mscIpivcLcnVcElapsedTimeTillNow OBJECT-TYPE
   SYNTAX     Unsigned32 (0..16777215)
   ACCESS     read-only
   STATUS     mandatory
   DESCRIPTION
     "This attribute displays the elapsed time representing the period of 
      this interval data. It is elapsed time in 0.1 second increments since 
      Vc started."
::= { mscIpivcLcnVcIntdEntry 2 }

mscIpivcLcnVcSegmentsRx OBJECT-TYPE
   SYNTAX     Unsigned32 (0..16777215)
   ACCESS     read-only
   STATUS     mandatory
   DESCRIPTION
     "This attribute displays the number of segments received at the time 
      command was issued. This is the segment received count 
      maintained by accounting at each end of the Vc. This counter is 
      updated only when the packet cannot be successfully delivered out 
      of the sink Vc and to the sink AP Conditions in which packets may 
      be discarded by the sink Vc include: missing packets due to subnet 
      discards, segmentation protocol violations due to subnet discard, 
      duplicated and out-of-ranged packets and packets that arrive while 
      Vc is in path recovery state."
::= { mscIpivcLcnVcIntdEntry 3 }

mscIpivcLcnVcSegmentsSent OBJECT-TYPE
   SYNTAX     Unsigned32 (0..16777215)
   ACCESS     read-only
   STATUS     mandatory
   DESCRIPTION
     "This attribute displays the number of segments sent at the time 
      command was issued. This is the segment sent count maintained by 
      accounting at the source Vc. Vc only counts packets that Vc thinks 
      can be delivered successfully into the subnet. In reality, these 
      packets may be dropped by trunking, for instance. This counter is 
      not updated when splitting fails, when Vc is in a path recovery state, 
      when packet forwarding fails to forward this packet and when 
      subsequent packets have to be discarded as we want to minimize the 
      chance of out-of-sequence and do not intentionally send out-of-
      sequenced packets into the subnet."
::= { mscIpivcLcnVcIntdEntry 4 }

mscIpivcLcnVcStartTime OBJECT-TYPE
   SYNTAX     EnterpriseDateAndTime (SIZE (0 | 19))
   ACCESS     read-only
   STATUS     mandatory
   DESCRIPTION
     "This attribute displays the start time of this interval period. If Vc 
      spans 12 hour time or time of day change startTime reflects new 
      time as recorded at 12 hour periods or time of day changes."
::= { mscIpivcLcnVcIntdEntry 5 }

mscIpivcLcnVcCallReferenceNumberDecimal OBJECT-TYPE
   SYNTAX     Unsigned32 (0..4294967295)
   ACCESS     read-only
   STATUS     mandatory
   DESCRIPTION
     "This attribute displays the call reference number which is a unique 
      number generated by the switch.The same Call Reference Number 
      is stored in the interval data (accounting record) at both ends of the 
      call. It can be used as one of the attributes in matching duplicate 
      records generated at each end of the call."
::= { mscIpivcLcnVcIntdEntry 7 }

mscIpivcLcnVcStatsTable OBJECT-TYPE
   SYNTAX     SEQUENCE OF MscIpivcLcnVcStatsEntry
   ACCESS     not-accessible
   STATUS     mandatory
   DESCRIPTION
     "*** THIS TABLE CURRENTLY NOT IMPLEMENTED ***

      ... Statistics(Stats)
      This group defines general attributes collected by general Vc.
      The purpose of Vc attributes is to aid end users and verification 
      people to understand the Vc internal behavior. This is particularly 
      useful when the network has experienced abnormality and we want 
      to isolate problems and pinpoint trouble spots. 
      Attributes are collected on a per Vc basis. Until a need is identified, 
      statistics are not collected at a processor level. Each attribute is 
      stored in a 32 bit field and is initialized to zero when a Vc enters 
      into the data transfer state. When a PVC is disconnected and then 
      connected again, the attributes will be reset. Attributes cannot be 
      reset through other methods."
::= { mscIpivcLcnVc 12 }

mscIpivcLcnVcStatsEntry OBJECT-TYPE
   SYNTAX     MscIpivcLcnVcStatsEntry
   ACCESS     not-accessible
   STATUS     mandatory
   DESCRIPTION
     "An entry in the mscIpivcLcnVcStatsTable."
   INDEX {
      mscIpivcIndex,
      mscIpivcLcnIndex,
      mscIpivcLcnVcIndex }
::= { mscIpivcLcnVcStatsTable 1 }

MscIpivcLcnVcStatsEntry ::= SEQUENCE {
   mscIpivcLcnVcAckStackingTimeouts
      Unsigned32,
   mscIpivcLcnVcOutOfRangeFrmFromSubnet
      Unsigned32,
   mscIpivcLcnVcDuplicatesFromSubnet
      Unsigned32,
   mscIpivcLcnVcFrmRetryTimeouts
      Unsigned32,
   mscIpivcLcnVcPeakRetryQueueSize
      Unsigned32,
   mscIpivcLcnVcPeakOoSeqQueueSize
      Unsigned32,
   mscIpivcLcnVcPeakOoSeqFrmForwarded
      Unsigned32,
   mscIpivcLcnVcPeakStackedAcksRx
      Unsigned32,
   mscIpivcLcnVcSubnetRecoveries
      Unsigned32,
   mscIpivcLcnVcWindowClosuresToSubnet
      Unsigned32,
   mscIpivcLcnVcWindowClosuresFromSubnet
      Unsigned32,
   mscIpivcLcnVcWrTriggers
      Unsigned32 }

mscIpivcLcnVcAckStackingTimeouts OBJECT-TYPE
   SYNTAX     Unsigned32 (0..5000)
   ACCESS     read-only
   STATUS     mandatory
   DESCRIPTION
     "This attribute counts the number of ack stacking timer expiries.
      It is used as an indicator of the acknowledgment behavior across the 
      subnet when ack stacking is in effect. If it expires often, usually this 
      means end users will experience longer delay.
      The ack stacking timer specifies how long the Vc will wait before 
      finally sending the subnet acknowledgment. if this attribute is set to 
      a value of 0, then the Vc will automatically return acknowledgment 
      packets without delay. If this attribute is set to a value other than 
      zero, then the Vc will wait for this amount of time in an attempt to 
      piggyback the acknowledgment packet on another credit or data 
      packet. If the Vc cannot piggyback the acknowledgment packet 
      within this time, then the packet is returned without piggybacking."
::= { mscIpivcLcnVcStatsEntry 1 }

mscIpivcLcnVcOutOfRangeFrmFromSubnet OBJECT-TYPE
   SYNTAX     Unsigned32 (0..5000)
   ACCESS     read-only
   STATUS     mandatory
   DESCRIPTION
     "This attribute counts the number of subnet frames discarded due to 
      the sequence number being out of range.
      Two Categories apply for the General Vc
      1) lost Acks (previous Range)
      2) unexpected Packets (next Range)
      Vc internally maintains its own sequence number of packet order 
      and sequencing. Due to packet retransmission, Vc may receive 
      duplicate packets that have the same Vc internal sequence number. 
      Only 1 copy is accepted by the Vc and other copies of the same 
      packets are detected through this count. This attribute can be used to 
      record the frequency of packet retransmission due to Vc and other 
      part of the subnet."
::= { mscIpivcLcnVcStatsEntry 2 }

mscIpivcLcnVcDuplicatesFromSubnet OBJECT-TYPE
   SYNTAX     Unsigned32 (0..5000)
   ACCESS     read-only
   STATUS     mandatory
   DESCRIPTION
     "This attribute counts the number of subnet packets discarded due to 
      duplication. It is used to detect software error fault or duplication 
      caused by retransmitting."
::= { mscIpivcLcnVcStatsEntry 3 }

mscIpivcLcnVcFrmRetryTimeouts OBJECT-TYPE
   SYNTAX     Unsigned32 (0..5000)
   ACCESS     read-only
   STATUS     mandatory
   DESCRIPTION
     "This attribute counts the number of frames which have 
      retransmission time-out.
      If packets from Vc into the subnet are discarded by the subnet, the 
      source Vc will not receive any acknowledgment. The retransmission 
      timer then expires and packets will be retransmitted again. Note that 
      the Vc idle probe may be retransmitted and is included in this count. 
      This statistics does not show the distribution of how many times 
      packets are retransmitted (e.g. first retransmission results in 
      successful packet forwarding)."
::= { mscIpivcLcnVcStatsEntry 4 }

mscIpivcLcnVcPeakRetryQueueSize OBJECT-TYPE
   SYNTAX     Unsigned32 (0..5000)
   ACCESS     read-only
   STATUS     mandatory
   DESCRIPTION
     "This attribute indicates the peak size of the retransmission queue.
      This attribute is used as an indicator of the acknowledgment 
      behavior across the subnet. It records the largest body of 
      unacknowledged packets."
::= { mscIpivcLcnVcStatsEntry 5 }

mscIpivcLcnVcPeakOoSeqQueueSize OBJECT-TYPE
   SYNTAX     Unsigned32 (0..5000)
   ACCESS     read-only
   STATUS     mandatory
   DESCRIPTION
     "This attribute indicates the peak size of the out of sequence queue.
      This attribute is used as an indicator of the sequencing behavior 
      across the subnet. It records the largest body of out of sequence 
      packets."
::= { mscIpivcLcnVcStatsEntry 6 }

mscIpivcLcnVcPeakOoSeqFrmForwarded OBJECT-TYPE
   SYNTAX     Unsigned32 (0..5000)
   ACCESS     read-only
   STATUS     mandatory
   DESCRIPTION
     "This attribute indicates the peak size of the sequence packet queue.
      This attribute is used as an indicator of the sequencing behavior 
      across the subnet. It records the largest body of out of sequence 
      packets, which by the receipt of an expected packet have been 
      transformed to expected packets. The number of times this peak is 
      reached is not recorded as it is traffic dependent."
::= { mscIpivcLcnVcStatsEntry 7 }

mscIpivcLcnVcPeakStackedAcksRx OBJECT-TYPE
   SYNTAX     Unsigned32 (0..5000)
   ACCESS     read-only
   STATUS     mandatory
   DESCRIPTION
     "This attribute indicates the peak size of wait acks.
      This attribute is used as an indicator of the acknowledgment 
      behavior across the subnet. It records the largest collective 
      acknowledgment."
::= { mscIpivcLcnVcStatsEntry 8 }

mscIpivcLcnVcSubnetRecoveries OBJECT-TYPE
   SYNTAX     Unsigned32 (0..5000)
   ACCESS     read-only
   STATUS     mandatory
   DESCRIPTION
     "This attribute counts the number of successful Vc recovery attempts.
      This attribute is used as an indicator of how many times the Vc path 
      is broken but can be recovered. This attribute is useful to record the 
      number of network path failures."
::= { mscIpivcLcnVcStatsEntry 9 }

mscIpivcLcnVcWindowClosuresToSubnet OBJECT-TYPE
   SYNTAX     Unsigned32 (0..5000)
   ACCESS     read-only
   STATUS     mandatory
   DESCRIPTION
     "This attribute counts the number of window closures to subnet.
      A packet may have been sent into the subnet but its 
      acknowledgment from the remote Vc has not yet been received. 
      This is a 8 bit sequence number.This number is useful in detecting 
      whether the Vc is sending any packet into the subnet."
::= { mscIpivcLcnVcStatsEntry 10 }

mscIpivcLcnVcWindowClosuresFromSubnet OBJECT-TYPE
   SYNTAX     Unsigned32 (0..5000)
   ACCESS     read-only
   STATUS     mandatory
   DESCRIPTION
     "This attribute counts the number of window closures from subnet.
      This attribute is useful in detecting whether the Vc is receiving any 
      packet from the subnet."
::= { mscIpivcLcnVcStatsEntry 11 }

mscIpivcLcnVcWrTriggers OBJECT-TYPE
   SYNTAX     Unsigned32 (0..5000)
   ACCESS     read-only
   STATUS     mandatory
   DESCRIPTION
     "This attribute displays the number of times the Vc stays within the 
      W-R region. The W-R region is a value used to determined the 
      timing of credit transmission. Should the current window size be 
      beneath this value, the credits will be transmitted immediately. 
      Otherwise, they will be transmitted later with actual data. The 
      wrTriggers statistic is therefore used to analyze the flow control and 
      credit mechanism."
::= { mscIpivcLcnVcStatsEntry 12 }




-- 
-- Version and Compliance statements
-- 



-- Object-Group Statement:
-- A list of all current accessible leaf objects.

-- OBJECTS { mscIpivcDnaDataNetworkAddress,
--           mscIpivcLcnVcAckStackingTimeouts,
--           mscIpivcLcnVcSubnetRxPktSize,
--           mscIpivcDnaRowStatus,
--           mscIpivcLcnVcCallingDna,
--           mscIpivcDnaIncChargeTransfer,
--           mscIpivcLcnVcPeakOoSeqFrmForwarded,
--           mscIpivcDnaCugComponentName,
--           mscIpivcLcnVcFrmRetryTimeouts,
--           mscIpivcLcnVcPriority,
--           mscIpivcDnaTransferPriorityOverRide,
--           mscIpivcDrCallingNumberingPlanIndicator,
--           mscIpivcDnaIncSameService,
--           mscIpivcDnaDefaultRecvFrmNetworkThruputClass,
--           mscIpivcDnaPacketSizes,
--           mscIpivcDnaCugInterlockCode,
--           mscIpivcDnaNumberingPlanIndicator,
--           mscIpivcDnaServiceExchange,
--           mscIpivcLcnUnknownStatus,
--           mscIpivcLcnStandbyStatus,
--           mscIpivcLcnVcTransferPriorityFromNetwork,
--           mscIpivcLcnVcLocalTxWindowSize,
--           mscIpivcDrComponentName,
--           mscIpivcLcnStorageType,
--           mscIpivcDnaCugOutCalls,
--           mscIpivcLcnAvailabilityStatus,
--           mscIpivcIpAddress,
--           mscIpivcLcnVcDuplicatesFromSubnet,
--           mscIpivcLcnVcStartTime,
--           mscIpivcDnaDefaultSendToNetworkWindowSize,
--           mscIpivcLcnAdminState,
--           mscIpivcDnaServiceCategory,
--           mscIpivcLcnVcDiagnosticCode,
--           mscIpivcDnaDefaultRecvFrmNetworkPacketSize,
--           mscIpivcComponentName,
--           mscIpivcLcnRowStatus,
--           mscIpivcLcnVcLocalRxWindowSize,
--           mscIpivcLcnVcCallingLcn,
--           mscIpivcLcnVcWindowClosuresToSubnet,
--           mscIpivcLcnVcOutOfRangeFrmFromSubnet,
--           mscIpivcDnaCugStorageType,
--           mscIpivcLcnVcCalledDna,
--           mscIpivcLcnUsageState,
--           mscIpivcLcnVcType,
--           mscIpivcDnaCugPrivileged,
--           mscIpivcLcnVcAccountingEnabled,
--           mscIpivcLcnVcSegmentsSent,
--           mscIpivcDnaCugIncCalls,
--           mscIpivcDnaIncIntlReverseCharge,
--           mscIpivcLcnVcPreviousState,
--           mscIpivcMaximumNumberOfLcn,
--           mscIpivcLcnVcSubnetRecoveries,
--           mscIpivcDrStorageType,
--           mscIpivcLcnVcLocalTxPktSize,
--           mscIpivcLcnOperationalState,
--           mscIpivcDnaDefaultSendToNetworkThruputClass,
--           mscIpivcDnaIncHighPriorityReverseCharge,
--           mscIpivcLcnVcSegmentSize,
--           mscIpivcLcnDiscardTxPackets,
--           mscIpivcStorageType,
--           mscIpivcLcnPacketsSent,
--           mscIpivcDnaPacketSizeNegotiation,
--           mscIpivcDnaCugRowStatus,
--           mscIpivcDnaIncFastSelect,
--           mscIpivcLcnVcFastSelectCall,
--           mscIpivcLcnVcComponentName,
--           mscIpivcDrCallingIpAddress,
--           mscIpivcLcnIpInterfaceDevice,
--           mscIpivcLcnVcPeakOoSeqQueueSize,
--           mscIpivcLcnVcWindowClosuresFromSubnet,
--           mscIpivcDnaFastSelectCallsOnly,
--           mscIpivcLcnVcCallingNpi,
--           mscIpivcDnaCug0AsNonCugCall,
--           mscIpivcLcnVcSubnetTxWindowSize,
--           mscIpivcDnaCugDnic,
--           mscIpivcLcnVcLocalRxPktSize,
--           mscIpivcLcnPacketsReceived,
--           mscIpivcLcnAlarmStatus,
--           mscIpivcLcnVcSegmentsRx,
--           mscIpivcLcnVcCalledLcn,
--           mscIpivcLcnVcPathReliability,
--           mscIpivcDnaDefaultSendToNetworkPacketSize,
--           mscIpivcDnaComponentName,
--           mscIpivcLcnVcWrTriggers,
--           mscIpivcDnaAccountClass,
--           mscIpivcLcnVcState,
--           mscIpivcRowStatus,
--           mscIpivcLcnVcMaxSubnetPktSize,
--           mscIpivcDnaOutCalls,
--           mscIpivcLcnVcSubnetRxWindowSize,
--           mscIpivcLcnVcPeakStackedAcksRx,
--           mscIpivcLcnVcTransferPriorityToNetwork,
--           mscIpivcLcnControlStatus,
--           mscIpivcLcnDiscardRcvPackets,
--           mscIpivcLcnProceduralStatus,
--           mscIpivcLcnVcPeakRetryQueueSize,
--           mscIpivcDnaIncNormalPriorityReverseCharge,
--           mscIpivcDnaDefaultRecvFrmNetworkWindowSize,
--           mscIpivcDrCallingDataNetworkAddress,
--           mscIpivcDnaDefaultTransferPriority,
--           mscIpivcDnaIncIntlNormalCharge,
--           mscIpivcLcnVcAccountingEnd,
--           mscIpivcLcnVcSubnetTxPktSize,
--           mscIpivcLcnVcCalledNpi,
--           mscIpivcLcnVcStorageType,
--           mscIpivcLcnVcElapsedTimeTillNow,
--           mscIpivcLcnComponentName,
--           mscIpivcDnaCugFormat,
--           mscIpivcDnaStorageType,
--           mscIpivcDnaCugType,
--           mscIpivcLcnVcCallReferenceNumberDecimal,
--           mscIpivcLcnDestinationIpAddress,
--           mscIpivcLcnVcRowStatus,
--           mscIpivcDnaIncCalls,
--           mscIpivcDnaIncAccess,
--           mscIpivcLcnVcPreviousDiagnosticCode,
--           mscIpivcDrRowStatus }
-- STATUS  mandatory
-- DESCRIPTION
--   "A list of all current accessible leaf objects."

ipiVcGroup OBJECT IDENTIFIER ::= { ipiVcMIB 1 }
ipiVcGroupCA OBJECT IDENTIFIER ::= { ipiVcGroup 1 }
ipiVcGroupCA02 OBJECT IDENTIFIER ::= { ipiVcGroupCA 3 }
ipiVcGroupCA02A OBJECT IDENTIFIER ::= { ipiVcGroupCA02 2 }



-- Agent-Capabilities Statement:

-- PRODUCT-RELEASE "MscPassport Release 1.2 IpiVc."
-- STATUS          mandatory
-- DESCRIPTION     "Carrier Passport IpiVc MIB: MIB Version CA02A,
--                  Software Version CA02S9C."
-- SUPPORTS        Nortel-MsCarrier-MscPassport-IpiVcMIB
--    INCLUDES     { ipiVcGroupCA02A }

ipiVcCapabilities OBJECT IDENTIFIER ::= { ipiVcMIB 3 }
ipiVcCapabilitiesCA OBJECT IDENTIFIER ::= { ipiVcCapabilities 1 }
ipiVcCapabilitiesCA02 OBJECT IDENTIFIER ::= { ipiVcCapabilitiesCA 3 }
ipiVcCapabilitiesCA02A OBJECT IDENTIFIER ::= { ipiVcCapabilitiesCA02 2 }





END
