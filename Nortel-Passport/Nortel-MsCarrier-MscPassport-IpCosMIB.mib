Nortel-MsCarrier-MscPassport-IpCosMIB
DEFINITIONS ::= BEGIN



IMPORTS

      OBJECT-TYPE
   FROM RFC-1212

      IpAddress
   FROM RFC1155-SMI

      mscPassportMIBs
   FROM Nortel-MsCarrier-MscPassport-UsefulDefinitionsMIB

      DisplayString,
      StorageType,
      RowStatus,
      Integer32,
      Unsigned32
   FROM Nortel-MsCarrier-MscPassport-StandardTextualConventionsMIB

      Hex,
      NonReplicated,
      Link,
      AsciiStringIndex
   FROM Nortel-MsCarrier-MscPassport-TextualConventionsMIB

      mscVrIpIndex,
      mscVrIp
   FROM Nortel-MsCarrier-MscPassport-IpMIB

      mscVrIndex
   FROM Nortel-MsCarrier-MscPassport-VirtualRouterMIB;




-- LAST-UPDATED   "9909010000Z"
-- ORGANIZATION   "Nortel Networks"
-- CONTACT-INFO   "
--         Nortel Carrier Data Network Management
--         
--         Postal:       P.O. Box 3511, Station C 
--                       Ottawa, Ontario 
--                       Canada  K1Y 4H7
--         
--         via the WEB:  http://www.nortelnetworks.com  
--                       select 'Contact Us' from the menu
--          
--         via phone:    1-800-4NORTEL"
-- DESCRIPTION
--    "The module describing the Nortel MsCarrier MscPassport
--     IpCos Enterprise MIB."

ipCosMIB OBJECT IDENTIFIER ::= { mscPassportMIBs 161 }










-- Vr/<string> Ip CosPolicyGroup/<string>
-- The CosPolicyGroup component represents a set of policies, which 
-- may be associated with a specific IpPort or may be used as the 
-- default policy of the Virtual Router.
-- 
-- The instance value is represented by an arbitrary text string of at 
-- most 20 characters. The intention is to allow the operator to assign a 
-- meaningful name for easier reference.

mscVrIpPg OBJECT IDENTIFIER ::= { mscVrIp 20 }



mscVrIpPgRowStatusTable OBJECT-TYPE
   SYNTAX     SEQUENCE OF MscVrIpPgRowStatusEntry
   ACCESS     not-accessible
   STATUS     mandatory
   DESCRIPTION
     "This entry controls the addition and deletion of 
      mscVrIpPg components."
::= { mscVrIpPg 1 }

mscVrIpPgRowStatusEntry OBJECT-TYPE
   SYNTAX     MscVrIpPgRowStatusEntry
   ACCESS     not-accessible
   STATUS     mandatory
   DESCRIPTION
     "A single entry in the table represents a single 
      mscVrIpPg component."
   INDEX {
      mscVrIndex,
      mscVrIpIndex,
      mscVrIpPgIndex }
::= { mscVrIpPgRowStatusTable 1 }

MscVrIpPgRowStatusEntry ::= SEQUENCE {
   mscVrIpPgRowStatus
      RowStatus,
   mscVrIpPgComponentName
      DisplayString,
   mscVrIpPgStorageType
      StorageType,
   mscVrIpPgIndex
      AsciiStringIndex }

mscVrIpPgRowStatus OBJECT-TYPE
   SYNTAX     RowStatus 
   ACCESS     read-write
   STATUS     mandatory
   DESCRIPTION
     "This variable is used as the basis for SNMP naming of
      mscVrIpPg components.
      These components can be added and deleted."
::= { mscVrIpPgRowStatusEntry 1 }

mscVrIpPgComponentName OBJECT-TYPE
   SYNTAX     DisplayString 
   ACCESS     read-only
   STATUS     mandatory
   DESCRIPTION
     "This variable provides the component's string name for
      use with the ASCII Console Interface"
::= { mscVrIpPgRowStatusEntry 2 }

mscVrIpPgStorageType OBJECT-TYPE
   SYNTAX     StorageType 
   ACCESS     read-only
   STATUS     mandatory
   DESCRIPTION
     "This variable represents the storage type value for the
      mscVrIpPg tables."
::= { mscVrIpPgRowStatusEntry 4 }

mscVrIpPgIndex OBJECT-TYPE
   SYNTAX     AsciiStringIndex (SIZE (1..20))
   ACCESS     not-accessible
   STATUS     mandatory
   DESCRIPTION
     "This variable represents the index for the mscVrIpPg tables."
::= { mscVrIpPgRowStatusEntry 10 }

mscVrIpPgUsersTable OBJECT-TYPE
   SYNTAX     SEQUENCE OF MscVrIpPgUsersEntry
   ACCESS     not-accessible
   STATUS     mandatory
   DESCRIPTION
     "This attribute specifies a list of components that are using this 
      CosPolicyGroup."
::= { mscVrIpPg 432 }

mscVrIpPgUsersEntry OBJECT-TYPE
   SYNTAX     MscVrIpPgUsersEntry
   ACCESS     not-accessible
   STATUS     mandatory
   DESCRIPTION
     "An entry in the mscVrIpPgUsersTable."
   INDEX {
      mscVrIndex,
      mscVrIpIndex,
      mscVrIpPgIndex,
      mscVrIpPgUsersValue }
::= { mscVrIpPgUsersTable 1 }

MscVrIpPgUsersEntry ::= SEQUENCE {
   mscVrIpPgUsersValue
      Link,
   mscVrIpPgUsersRowStatus
      RowStatus }

mscVrIpPgUsersValue OBJECT-TYPE
   SYNTAX     Link 
   ACCESS     read-write
   STATUS     mandatory
   DESCRIPTION
     "This variable represents both the value and the index for the
      mscVrIpPgUsersTable."
::= { mscVrIpPgUsersEntry 1 }

mscVrIpPgUsersRowStatus OBJECT-TYPE
   SYNTAX     RowStatus 
   ACCESS     write-only
   STATUS     mandatory
   DESCRIPTION
     "This variable is used to control the addition and deletion 
      of individual values of the mscVrIpPgUsersTable."
::= { mscVrIpPgUsersEntry 2 }


-- Vr/<string> Ip Pg/<string> Policy/<string>
-- The Policy component defines a policy to be applied on a per virtual 
-- router or per IpPort basis. A policy is defined by two sets of 
-- parameters:
-- 
-- 1. The criteria specifying when the policy is to be applied. These 
-- criteria are defined by the Policy subcomponents: TosMap and 
-- IpAddrLayer4Flow.
-- 
-- 2. The actions or results when the policy is applied. These actions 
-- or results are defined as subcomponents of CosPolicyGroup, and 
-- are referenced by attributes under the Policy component. Currently 
-- the CosTreatment component is the only component of this type.
-- 
-- The instance value is represented by an arbitrary text string of at 
-- most 20 characters. The intention is to allow operator to assign 
-- meaningful name for easier reference.

mscVrIpPgPolicy OBJECT IDENTIFIER ::= { mscVrIpPg 2 }



mscVrIpPgPolicyRowStatusTable OBJECT-TYPE
   SYNTAX     SEQUENCE OF MscVrIpPgPolicyRowStatusEntry
   ACCESS     not-accessible
   STATUS     mandatory
   DESCRIPTION
     "This entry controls the addition and deletion of 
      mscVrIpPgPolicy components."
::= { mscVrIpPgPolicy 1 }

mscVrIpPgPolicyRowStatusEntry OBJECT-TYPE
   SYNTAX     MscVrIpPgPolicyRowStatusEntry
   ACCESS     not-accessible
   STATUS     mandatory
   DESCRIPTION
     "A single entry in the table represents a single 
      mscVrIpPgPolicy component."
   INDEX {
      mscVrIndex,
      mscVrIpIndex,
      mscVrIpPgIndex,
      mscVrIpPgPolicyIndex }
::= { mscVrIpPgPolicyRowStatusTable 1 }

MscVrIpPgPolicyRowStatusEntry ::= SEQUENCE {
   mscVrIpPgPolicyRowStatus
      RowStatus,
   mscVrIpPgPolicyComponentName
      DisplayString,
   mscVrIpPgPolicyStorageType
      StorageType,
   mscVrIpPgPolicyIndex
      AsciiStringIndex }

mscVrIpPgPolicyRowStatus OBJECT-TYPE
   SYNTAX     RowStatus 
   ACCESS     read-write
   STATUS     mandatory
   DESCRIPTION
     "This variable is used as the basis for SNMP naming of
      mscVrIpPgPolicy components.
      These components can be added and deleted."
::= { mscVrIpPgPolicyRowStatusEntry 1 }

mscVrIpPgPolicyComponentName OBJECT-TYPE
   SYNTAX     DisplayString 
   ACCESS     read-only
   STATUS     mandatory
   DESCRIPTION
     "This variable provides the component's string name for
      use with the ASCII Console Interface"
::= { mscVrIpPgPolicyRowStatusEntry 2 }

mscVrIpPgPolicyStorageType OBJECT-TYPE
   SYNTAX     StorageType 
   ACCESS     read-only
   STATUS     mandatory
   DESCRIPTION
     "This variable represents the storage type value for the
      mscVrIpPgPolicy tables."
::= { mscVrIpPgPolicyRowStatusEntry 4 }

mscVrIpPgPolicyIndex OBJECT-TYPE
   SYNTAX     AsciiStringIndex (SIZE (1..20))
   ACCESS     not-accessible
   STATUS     mandatory
   DESCRIPTION
     "This variable represents the index for the mscVrIpPgPolicy tables."
::= { mscVrIpPgPolicyRowStatusEntry 10 }

mscVrIpPgPolicyProvTable OBJECT-TYPE
   SYNTAX     SEQUENCE OF MscVrIpPgPolicyProvEntry
   ACCESS     not-accessible
   STATUS     mandatory
   DESCRIPTION
     "This group contains the provisionable attributes for the Policy 
      component."
::= { mscVrIpPgPolicy 10 }

mscVrIpPgPolicyProvEntry OBJECT-TYPE
   SYNTAX     MscVrIpPgPolicyProvEntry
   ACCESS     not-accessible
   STATUS     mandatory
   DESCRIPTION
     "An entry in the mscVrIpPgPolicyProvTable."
   INDEX {
      mscVrIndex,
      mscVrIpIndex,
      mscVrIpPgIndex,
      mscVrIpPgPolicyIndex }
::= { mscVrIpPgPolicyProvTable 1 }

MscVrIpPgPolicyProvEntry ::= SEQUENCE {
   mscVrIpPgPolicyCosTreatmentIndex
      Unsigned32 }

mscVrIpPgPolicyCosTreatmentIndex OBJECT-TYPE
   SYNTAX     Unsigned32 (0..3)
   ACCESS     read-write
   STATUS     mandatory
   DESCRIPTION
     "This attribute specifies the Class Of Service (COS) treatment a 
      packet receives if this policy applies. If the value of this attribute is 
      set to n, then the COS treatment is defined by the CosTreatment/n 
      component of the same CosPolicyGroup."
   DEFVAL     { 0 }
::= { mscVrIpPgPolicyProvEntry 1 }


-- Vr/<string> Ip Pg/<string> Policy/<string> TosMap
-- The TosMap component is one of several ways to define the 
-- matching criteria for which a Policy is deemed applicable.
-- 
-- The TosMap component allows the operator to provision a list of 
-- Type Of service (TOS) byte values. Incoming packets are deemed to 
-- match this policy if the TOS byte matches any one of those in the 
-- list.
-- 
-- The operator is provided with the flexibility to define which bits in 
-- the TOS byte are to be matched by setting the tosMask attribute 
-- under the CosTreatment component.

mscVrIpPgPolicyTosMap OBJECT IDENTIFIER ::= { mscVrIpPgPolicy 2 }



mscVrIpPgPolicyTosMapRowStatusTable OBJECT-TYPE
   SYNTAX     SEQUENCE OF MscVrIpPgPolicyTosMapRowStatusEntry
   ACCESS     not-accessible
   STATUS     mandatory
   DESCRIPTION
     "This entry controls the addition and deletion of 
      mscVrIpPgPolicyTosMap components."
::= { mscVrIpPgPolicyTosMap 1 }

mscVrIpPgPolicyTosMapRowStatusEntry OBJECT-TYPE
   SYNTAX     MscVrIpPgPolicyTosMapRowStatusEntry
   ACCESS     not-accessible
   STATUS     mandatory
   DESCRIPTION
     "A single entry in the table represents a single 
      mscVrIpPgPolicyTosMap component."
   INDEX {
      mscVrIndex,
      mscVrIpIndex,
      mscVrIpPgIndex,
      mscVrIpPgPolicyIndex,
      mscVrIpPgPolicyTosMapIndex }
::= { mscVrIpPgPolicyTosMapRowStatusTable 1 }

MscVrIpPgPolicyTosMapRowStatusEntry ::= SEQUENCE {
   mscVrIpPgPolicyTosMapRowStatus
      RowStatus,
   mscVrIpPgPolicyTosMapComponentName
      DisplayString,
   mscVrIpPgPolicyTosMapStorageType
      StorageType,
   mscVrIpPgPolicyTosMapIndex
      NonReplicated }

mscVrIpPgPolicyTosMapRowStatus OBJECT-TYPE
   SYNTAX     RowStatus 
   ACCESS     read-write
   STATUS     mandatory
   DESCRIPTION
     "This variable is used as the basis for SNMP naming of
      mscVrIpPgPolicyTosMap components.
      These components can be added and deleted."
::= { mscVrIpPgPolicyTosMapRowStatusEntry 1 }

mscVrIpPgPolicyTosMapComponentName OBJECT-TYPE
   SYNTAX     DisplayString 
   ACCESS     read-only
   STATUS     mandatory
   DESCRIPTION
     "This variable provides the component's string name for
      use with the ASCII Console Interface"
::= { mscVrIpPgPolicyTosMapRowStatusEntry 2 }

mscVrIpPgPolicyTosMapStorageType OBJECT-TYPE
   SYNTAX     StorageType 
   ACCESS     read-only
   STATUS     mandatory
   DESCRIPTION
     "This variable represents the storage type value for the
      mscVrIpPgPolicyTosMap tables."
::= { mscVrIpPgPolicyTosMapRowStatusEntry 4 }

mscVrIpPgPolicyTosMapIndex OBJECT-TYPE
   SYNTAX     NonReplicated 
   ACCESS     not-accessible
   STATUS     mandatory
   DESCRIPTION
     "This variable represents the index for the mscVrIpPgPolicyTosMap tables."
::= { mscVrIpPgPolicyTosMapRowStatusEntry 10 }

mscVrIpPgPolicyTosMapOperTable OBJECT-TYPE
   SYNTAX     SEQUENCE OF MscVrIpPgPolicyTosMapOperEntry
   ACCESS     not-accessible
   STATUS     mandatory
   DESCRIPTION
     "This group contains the operational attributes for the TosMap and 
      the IpAddrLayer4Flow component."
::= { mscVrIpPgPolicyTosMap 11 }

mscVrIpPgPolicyTosMapOperEntry OBJECT-TYPE
   SYNTAX     MscVrIpPgPolicyTosMapOperEntry
   ACCESS     not-accessible
   STATUS     mandatory
   DESCRIPTION
     "An entry in the mscVrIpPgPolicyTosMapOperTable."
   INDEX {
      mscVrIndex,
      mscVrIpIndex,
      mscVrIpPgIndex,
      mscVrIpPgPolicyIndex,
      mscVrIpPgPolicyTosMapIndex }
::= { mscVrIpPgPolicyTosMapOperTable 1 }

MscVrIpPgPolicyTosMapOperEntry ::= SEQUENCE {
   mscVrIpPgPolicyTosMapCos
      Unsigned32 }

mscVrIpPgPolicyTosMapCos OBJECT-TYPE
   SYNTAX     Unsigned32 (0..3)
   ACCESS     read-only
   STATUS     mandatory
   DESCRIPTION
     "This attribute indicates the Class Of Service (COS) with which a 
      packet receives if this policy applies. The value of this attribute is 
      derived from the cos attribute of the referenced CosTreatment of the 
      Policy."
::= { mscVrIpPgPolicyTosMapOperEntry 1 }

mscVrIpPgPolicyTosMapTosTable OBJECT-TYPE
   SYNTAX     SEQUENCE OF MscVrIpPgPolicyTosMapTosEntry
   ACCESS     not-accessible
   STATUS     mandatory
   DESCRIPTION
     "This attribute specifies a list of TOS byte values. An incoming 
      packet is considered to match this policy if its masked TOS byte 
      matches a value in the list. A bit-wise and operation is performed 
      with the TOS byte of the incoming packet and the tosMask attribute 
      of the referenced CosTreatment component before the comparison 
      is done.
      
      This attribute must contain at least one TOS byte value, otherwise a 
      semantic check error is generated."
::= { mscVrIpPgPolicyTosMap 434 }

mscVrIpPgPolicyTosMapTosEntry OBJECT-TYPE
   SYNTAX     MscVrIpPgPolicyTosMapTosEntry
   ACCESS     not-accessible
   STATUS     mandatory
   DESCRIPTION
     "An entry in the mscVrIpPgPolicyTosMapTosTable."
   INDEX {
      mscVrIndex,
      mscVrIpIndex,
      mscVrIpPgIndex,
      mscVrIpPgPolicyIndex,
      mscVrIpPgPolicyTosMapIndex,
      mscVrIpPgPolicyTosMapTosValue }
::= { mscVrIpPgPolicyTosMapTosTable 1 }

MscVrIpPgPolicyTosMapTosEntry ::= SEQUENCE {
   mscVrIpPgPolicyTosMapTosValue
      Integer32,
   mscVrIpPgPolicyTosMapTosRowStatus
      RowStatus }

mscVrIpPgPolicyTosMapTosValue OBJECT-TYPE
   SYNTAX     Integer32 (0..255)
   ACCESS     read-write
   STATUS     mandatory
   DESCRIPTION
     "This variable represents both the value and the index for the
      mscVrIpPgPolicyTosMapTosTable."
::= { mscVrIpPgPolicyTosMapTosEntry 1 }

mscVrIpPgPolicyTosMapTosRowStatus OBJECT-TYPE
   SYNTAX     RowStatus 
   ACCESS     write-only
   STATUS     mandatory
   DESCRIPTION
     "This variable is used to control the addition and deletion 
      of individual values of the mscVrIpPgPolicyTosMapTosTable."
::= { mscVrIpPgPolicyTosMapTosEntry 2 }


-- Vr/<string> Ip Pg/<string> Policy/<string> IpAddrLayer4Flow/n
-- The IpAddrLayer4Flow component is one of several ways to define 
-- the matching criteria for which a Policy is deemed applicable.
-- 
-- The IpAddrLayer4Flow component allows the operator to 
-- distinguish a flow based on:
-- 1. IP address or range of IP addresses; and/or
-- 2. Layer 4 (transport) protocol; and
-- 3. Optionally for TCP and UDP, one can further specify the port 
-- number or range of port numbers.
-- 
-- When both IP address and port number are defined, the matching is 
-- as follows:
-- 1. The provisioned IP address and port number is matched against 
-- the destination IP address and destination TCP/UDP port number of 
-- the incoming packet. If the match fails, then
-- 2. The provisioned IP address and port number is matched against 
-- the source IP address and source TCP/UDP port number.

mscVrIpPgPolicyIpAddrLayer4Flow OBJECT IDENTIFIER ::= { mscVrIpPgPolicy 3 }



mscVrIpPgPolicyIpAddrLayer4FlowRowStatusTable OBJECT-TYPE
   SYNTAX     SEQUENCE OF MscVrIpPgPolicyIpAddrLayer4FlowRowStatusEntry
   ACCESS     not-accessible
   STATUS     mandatory
   DESCRIPTION
     "This entry controls the addition and deletion of 
      mscVrIpPgPolicyIpAddrLayer4Flow components."
::= { mscVrIpPgPolicyIpAddrLayer4Flow 1 }

mscVrIpPgPolicyIpAddrLayer4FlowRowStatusEntry OBJECT-TYPE
   SYNTAX     MscVrIpPgPolicyIpAddrLayer4FlowRowStatusEntry
   ACCESS     not-accessible
   STATUS     mandatory
   DESCRIPTION
     "A single entry in the table represents a single 
      mscVrIpPgPolicyIpAddrLayer4Flow component."
   INDEX {
      mscVrIndex,
      mscVrIpIndex,
      mscVrIpPgIndex,
      mscVrIpPgPolicyIndex,
      mscVrIpPgPolicyIpAddrLayer4FlowIndex }
::= { mscVrIpPgPolicyIpAddrLayer4FlowRowStatusTable 1 }

MscVrIpPgPolicyIpAddrLayer4FlowRowStatusEntry ::= SEQUENCE {
   mscVrIpPgPolicyIpAddrLayer4FlowRowStatus
      RowStatus,
   mscVrIpPgPolicyIpAddrLayer4FlowComponentName
      DisplayString,
   mscVrIpPgPolicyIpAddrLayer4FlowStorageType
      StorageType,
   mscVrIpPgPolicyIpAddrLayer4FlowIndex
      Integer32 }

mscVrIpPgPolicyIpAddrLayer4FlowRowStatus OBJECT-TYPE
   SYNTAX     RowStatus 
   ACCESS     read-write
   STATUS     mandatory
   DESCRIPTION
     "This variable is used as the basis for SNMP naming of
      mscVrIpPgPolicyIpAddrLayer4Flow components.
      These components can be added and deleted."
::= { mscVrIpPgPolicyIpAddrLayer4FlowRowStatusEntry 1 }

mscVrIpPgPolicyIpAddrLayer4FlowComponentName OBJECT-TYPE
   SYNTAX     DisplayString 
   ACCESS     read-only
   STATUS     mandatory
   DESCRIPTION
     "This variable provides the component's string name for
      use with the ASCII Console Interface"
::= { mscVrIpPgPolicyIpAddrLayer4FlowRowStatusEntry 2 }

mscVrIpPgPolicyIpAddrLayer4FlowStorageType OBJECT-TYPE
   SYNTAX     StorageType 
   ACCESS     read-only
   STATUS     mandatory
   DESCRIPTION
     "This variable represents the storage type value for the
      mscVrIpPgPolicyIpAddrLayer4Flow tables."
::= { mscVrIpPgPolicyIpAddrLayer4FlowRowStatusEntry 4 }

mscVrIpPgPolicyIpAddrLayer4FlowIndex OBJECT-TYPE
   SYNTAX     Integer32 (0..1023)
   ACCESS     not-accessible
   STATUS     mandatory
   DESCRIPTION
     "This variable represents the index for the mscVrIpPgPolicyIpAddrLayer4Flow tables."
::= { mscVrIpPgPolicyIpAddrLayer4FlowRowStatusEntry 10 }

mscVrIpPgPolicyIpAddrLayer4FlowProvTable OBJECT-TYPE
   SYNTAX     SEQUENCE OF MscVrIpPgPolicyIpAddrLayer4FlowProvEntry
   ACCESS     not-accessible
   STATUS     mandatory
   DESCRIPTION
     "This group contains the provisionable attributes for any flow related 
      component which has prefix and prefix length as its parameters."
::= { mscVrIpPgPolicyIpAddrLayer4Flow 10 }

mscVrIpPgPolicyIpAddrLayer4FlowProvEntry OBJECT-TYPE
   SYNTAX     MscVrIpPgPolicyIpAddrLayer4FlowProvEntry
   ACCESS     not-accessible
   STATUS     mandatory
   DESCRIPTION
     "An entry in the mscVrIpPgPolicyIpAddrLayer4FlowProvTable."
   INDEX {
      mscVrIndex,
      mscVrIpIndex,
      mscVrIpPgIndex,
      mscVrIpPgPolicyIndex,
      mscVrIpPgPolicyIpAddrLayer4FlowIndex }
::= { mscVrIpPgPolicyIpAddrLayer4FlowProvTable 1 }

MscVrIpPgPolicyIpAddrLayer4FlowProvEntry ::= SEQUENCE {
   mscVrIpPgPolicyIpAddrLayer4FlowPrefix
      IpAddress,
   mscVrIpPgPolicyIpAddrLayer4FlowPrefixLength
      Unsigned32 }

mscVrIpPgPolicyIpAddrLayer4FlowPrefix OBJECT-TYPE
   SYNTAX     IpAddress 
   ACCESS     read-write
   STATUS     mandatory
   DESCRIPTION
     "This attribute specifies the IP address prefix, source or destination 
      IP address, of which the policy applies. The matching of actual 
      address to the prefix is done in conjunction with the prefixLength 
      attribute. A prefix length of 0 means any IP address."
   DEFVAL     { '00000000'H }  -- "0.0.0.0"
::= { mscVrIpPgPolicyIpAddrLayer4FlowProvEntry 1 }

mscVrIpPgPolicyIpAddrLayer4FlowPrefixLength OBJECT-TYPE
   SYNTAX     Unsigned32 (0..32)
   ACCESS     read-write
   STATUS     mandatory
   DESCRIPTION
     "This attribute specifies the number of most significant bits of the IP 
      address that are to be matched with the prefix. A prefix length of 0 
      means any IP address."
   DEFVAL     { 0 }
::= { mscVrIpPgPolicyIpAddrLayer4FlowProvEntry 2 }

mscVrIpPgPolicyIpAddrLayer4FlowProtoProvisionedTable OBJECT-TYPE
   SYNTAX     SEQUENCE OF MscVrIpPgPolicyIpAddrLayer4FlowProtoProvisionedEntry
   ACCESS     not-accessible
   STATUS     mandatory
   DESCRIPTION
     "This group contains the provisionable attributes for any flow related 
      component which has layer 4 (transport) protocol and port number 
      as its parameters."
::= { mscVrIpPgPolicyIpAddrLayer4Flow 11 }

mscVrIpPgPolicyIpAddrLayer4FlowProtoProvisionedEntry OBJECT-TYPE
   SYNTAX     MscVrIpPgPolicyIpAddrLayer4FlowProtoProvisionedEntry
   ACCESS     not-accessible
   STATUS     mandatory
   DESCRIPTION
     "An entry in the mscVrIpPgPolicyIpAddrLayer4FlowProtoProvisionedTable."
   INDEX {
      mscVrIndex,
      mscVrIpIndex,
      mscVrIpPgIndex,
      mscVrIpPgPolicyIndex,
      mscVrIpPgPolicyIpAddrLayer4FlowIndex }
::= { mscVrIpPgPolicyIpAddrLayer4FlowProtoProvisionedTable 1 }

MscVrIpPgPolicyIpAddrLayer4FlowProtoProvisionedEntry ::= SEQUENCE {
   mscVrIpPgPolicyIpAddrLayer4FlowProtocol
      INTEGER }

mscVrIpPgPolicyIpAddrLayer4FlowProtocol OBJECT-TYPE
   SYNTAX     INTEGER  {
                 icmp(1),
                 tcp(6),
                 udp(17) }
   ACCESS     read-write
   STATUS     mandatory
   DESCRIPTION
     "This attribute specifies the layer 4 (transport) protocol to which the 
      policy applies."
   DEFVAL     { tcp }
::= { mscVrIpPgPolicyIpAddrLayer4FlowProtoProvisionedEntry 1 }

mscVrIpPgPolicyIpAddrLayer4FlowOperTable OBJECT-TYPE
   SYNTAX     SEQUENCE OF MscVrIpPgPolicyIpAddrLayer4FlowOperEntry
   ACCESS     not-accessible
   STATUS     mandatory
   DESCRIPTION
     "This group contains the operational attributes for the TosMap and 
      the IpAddrLayer4Flow component."
::= { mscVrIpPgPolicyIpAddrLayer4Flow 12 }

mscVrIpPgPolicyIpAddrLayer4FlowOperEntry OBJECT-TYPE
   SYNTAX     MscVrIpPgPolicyIpAddrLayer4FlowOperEntry
   ACCESS     not-accessible
   STATUS     mandatory
   DESCRIPTION
     "An entry in the mscVrIpPgPolicyIpAddrLayer4FlowOperTable."
   INDEX {
      mscVrIndex,
      mscVrIpIndex,
      mscVrIpPgIndex,
      mscVrIpPgPolicyIndex,
      mscVrIpPgPolicyIpAddrLayer4FlowIndex }
::= { mscVrIpPgPolicyIpAddrLayer4FlowOperTable 1 }

MscVrIpPgPolicyIpAddrLayer4FlowOperEntry ::= SEQUENCE {
   mscVrIpPgPolicyIpAddrLayer4FlowCos
      Unsigned32 }

mscVrIpPgPolicyIpAddrLayer4FlowCos OBJECT-TYPE
   SYNTAX     Unsigned32 (0..3)
   ACCESS     read-only
   STATUS     mandatory
   DESCRIPTION
     "This attribute indicates the Class Of Service (COS) with which a 
      packet receives if this policy applies. The value of this attribute is 
      derived from the cos attribute of the referenced CosTreatment of the 
      Policy."
::= { mscVrIpPgPolicyIpAddrLayer4FlowOperEntry 1 }

mscVrIpPgPolicyIpAddrLayer4FlowPortNumberRangeTable OBJECT-TYPE
   SYNTAX     SEQUENCE OF MscVrIpPgPolicyIpAddrLayer4FlowPortNumberRangeEntry
   ACCESS     not-accessible
   STATUS     mandatory
   DESCRIPTION
     "This attribute specifies the TCP or UDP port number or range of 
      port numbers of which the policy applies. The port numbers 
      specified here are used to match the source or destination port 
      number of any incoming packet. The exact matching algorithm is 
      defined by the flow component that uses this attribute group.
      
      To specify a port number to match, just enter the value. To specify a 
      range of port numbers to match, enter the lower and upper bound of 
      the range. The order in which the lower and upper bound are 
      entered does not matter.
      
      Not setting this attribute or setting the port number to 0 means any 
      port number."
::= { mscVrIpPgPolicyIpAddrLayer4Flow 435 }

mscVrIpPgPolicyIpAddrLayer4FlowPortNumberRangeEntry OBJECT-TYPE
   SYNTAX     MscVrIpPgPolicyIpAddrLayer4FlowPortNumberRangeEntry
   ACCESS     not-accessible
   STATUS     mandatory
   DESCRIPTION
     "An entry in the mscVrIpPgPolicyIpAddrLayer4FlowPortNumberRangeTable."
   INDEX {
      mscVrIndex,
      mscVrIpIndex,
      mscVrIpPgIndex,
      mscVrIpPgPolicyIndex,
      mscVrIpPgPolicyIpAddrLayer4FlowIndex,
      mscVrIpPgPolicyIpAddrLayer4FlowPortNumberRangeValue }
::= { mscVrIpPgPolicyIpAddrLayer4FlowPortNumberRangeTable 1 }

MscVrIpPgPolicyIpAddrLayer4FlowPortNumberRangeEntry ::= SEQUENCE {
   mscVrIpPgPolicyIpAddrLayer4FlowPortNumberRangeValue
      Integer32,
   mscVrIpPgPolicyIpAddrLayer4FlowPortNumberRangeRowStatus
      RowStatus }

mscVrIpPgPolicyIpAddrLayer4FlowPortNumberRangeValue OBJECT-TYPE
   SYNTAX     Integer32 (0..65535)
   ACCESS     read-write
   STATUS     mandatory
   DESCRIPTION
     "This variable represents both the value and the index for the
      mscVrIpPgPolicyIpAddrLayer4FlowPortNumberRangeTable."
::= { mscVrIpPgPolicyIpAddrLayer4FlowPortNumberRangeEntry 1 }

mscVrIpPgPolicyIpAddrLayer4FlowPortNumberRangeRowStatus OBJECT-TYPE
   SYNTAX     RowStatus 
   ACCESS     write-only
   STATUS     mandatory
   DESCRIPTION
     "This variable is used to control the addition and deletion 
      of individual values of the mscVrIpPgPolicyIpAddrLayer4FlowPortNumberRangeTable."
::= { mscVrIpPgPolicyIpAddrLayer4FlowPortNumberRangeEntry 2 }


-- Vr/<string> Ip Pg/<string> CosTreatment/n
-- The CosTreatment represents a Class of Service (CoS) treatment a 
-- packet receives when any Policy referencing it is deemed 
-- applicable. A Policy is referencing this component if its 
-- cosTreatmentIndex attribute contains the instance value of this 
-- component.
-- 
-- Four instances of this component, index 0, 1, 2 and 3 respectively, 
-- are created automatically when the parent CosPolicyGroup 
-- component is added. These 4 CosTreatment component represents 
-- the 4 CoS values that are currently supported.
-- 
-- When multiple policies, such as TosMap and IpAddrLayer4Flow 
-- are deemed applicable to a packet, the ultimate CoS treatment the 
-- packet receives is determined in the following fashion:
-- 
-- 1. The packet's CoS is initialized to be the media's assigned CoS. 
-- For media type FrameRelayDte, the media CoS is based on the 
-- receiving DLCI's ipCos. For Vns, the media CoS is based on the 
-- mapping from discard and emission priority in the Vns header to 
-- QosP. For all other media, the media CoS is the linked IpPort 
-- assignedQos.
-- 
-- 2. Subsequently, if the IpPort has a TosMap policy provisioned, the 
-- packet's CoS is updated if there is a match.
-- 
-- 3. Finally, if the IpPort has one or more IpAddrLayer4Flow policies 
-- provisioned, the packet's CoS is updated if there is a match.

mscVrIpPgCosTreatment OBJECT IDENTIFIER ::= { mscVrIpPg 3 }



mscVrIpPgCosTreatmentRowStatusTable OBJECT-TYPE
   SYNTAX     SEQUENCE OF MscVrIpPgCosTreatmentRowStatusEntry
   ACCESS     not-accessible
   STATUS     mandatory
   DESCRIPTION
     "This entry controls the addition and deletion of 
      mscVrIpPgCosTreatment components."
::= { mscVrIpPgCosTreatment 1 }

mscVrIpPgCosTreatmentRowStatusEntry OBJECT-TYPE
   SYNTAX     MscVrIpPgCosTreatmentRowStatusEntry
   ACCESS     not-accessible
   STATUS     mandatory
   DESCRIPTION
     "A single entry in the table represents a single 
      mscVrIpPgCosTreatment component."
   INDEX {
      mscVrIndex,
      mscVrIpIndex,
      mscVrIpPgIndex,
      mscVrIpPgCosTreatmentIndex }
::= { mscVrIpPgCosTreatmentRowStatusTable 1 }

MscVrIpPgCosTreatmentRowStatusEntry ::= SEQUENCE {
   mscVrIpPgCosTreatmentRowStatus
      RowStatus,
   mscVrIpPgCosTreatmentComponentName
      DisplayString,
   mscVrIpPgCosTreatmentStorageType
      StorageType,
   mscVrIpPgCosTreatmentIndex
      Integer32 }

mscVrIpPgCosTreatmentRowStatus OBJECT-TYPE
   SYNTAX     RowStatus 
   ACCESS     read-write
   STATUS     mandatory
   DESCRIPTION
     "This variable is used as the basis for SNMP naming of
      mscVrIpPgCosTreatment components.
      These components can be added."
::= { mscVrIpPgCosTreatmentRowStatusEntry 1 }

mscVrIpPgCosTreatmentComponentName OBJECT-TYPE
   SYNTAX     DisplayString 
   ACCESS     read-only
   STATUS     mandatory
   DESCRIPTION
     "This variable provides the component's string name for
      use with the ASCII Console Interface"
::= { mscVrIpPgCosTreatmentRowStatusEntry 2 }

mscVrIpPgCosTreatmentStorageType OBJECT-TYPE
   SYNTAX     StorageType 
   ACCESS     read-only
   STATUS     mandatory
   DESCRIPTION
     "This variable represents the storage type value for the
      mscVrIpPgCosTreatment tables."
::= { mscVrIpPgCosTreatmentRowStatusEntry 4 }

mscVrIpPgCosTreatmentIndex OBJECT-TYPE
   SYNTAX     Integer32 (0..3)
   ACCESS     not-accessible
   STATUS     mandatory
   DESCRIPTION
     "This variable represents the index for the mscVrIpPgCosTreatment tables."
::= { mscVrIpPgCosTreatmentRowStatusEntry 10 }

mscVrIpPgCosTreatmentProvTable OBJECT-TYPE
   SYNTAX     SEQUENCE OF MscVrIpPgCosTreatmentProvEntry
   ACCESS     not-accessible
   STATUS     mandatory
   DESCRIPTION
     "This group contains the provisionable attributes for the 
      CosTreatment component."
::= { mscVrIpPgCosTreatment 10 }

mscVrIpPgCosTreatmentProvEntry OBJECT-TYPE
   SYNTAX     MscVrIpPgCosTreatmentProvEntry
   ACCESS     not-accessible
   STATUS     mandatory
   DESCRIPTION
     "An entry in the mscVrIpPgCosTreatmentProvTable."
   INDEX {
      mscVrIndex,
      mscVrIpIndex,
      mscVrIpPgIndex,
      mscVrIpPgCosTreatmentIndex }
::= { mscVrIpPgCosTreatmentProvTable 1 }

MscVrIpPgCosTreatmentProvEntry ::= SEQUENCE {
   mscVrIpPgCosTreatmentCos
      Unsigned32,
   mscVrIpPgCosTreatmentSetTosByte
      INTEGER,
   mscVrIpPgCosTreatmentTos
      Hex,
   mscVrIpPgCosTreatmentTosMask
      Hex }

mscVrIpPgCosTreatmentCos OBJECT-TYPE
   SYNTAX     Unsigned32 (0..3)
   ACCESS     read-only
   STATUS     mandatory
   DESCRIPTION
     "This attribute specifies the Class Of Service (COS) with which a 
      packet would be forwarded when this COS treatment is selected."
::= { mscVrIpPgCosTreatmentProvEntry 1 }

mscVrIpPgCosTreatmentSetTosByte OBJECT-TYPE
   SYNTAX     INTEGER  {
                 no(0),
                 yes(1) }
   ACCESS     read-write
   STATUS     mandatory
   DESCRIPTION
     "This attribute specifies whether the router would change the Type 
      Of Service (TOS) byte of packets when this COS treatment is 
      selected. If set to yes, the TOS byte is changed based on the value of 
      tos and tosMask."
   DEFVAL     { no }
::= { mscVrIpPgCosTreatmentProvEntry 3 }

mscVrIpPgCosTreatmentTos OBJECT-TYPE
   SYNTAX     Hex (0..255)
   ACCESS     read-write
   STATUS     mandatory
   DESCRIPTION
     "This attribute specifies the value of the Type Of Service (TOS) byte 
      with which packets are updated when this COS treatment is 
      selected. This attribute is ignored if setTosByte is set to no. The 
      actual TOS byte of the packet is updated based on the tos and 
      tosMask attribute using the following formula:
      
      New TOS = ( Original TOS & ~tosMask ) | ( tos & tosMask )
      
      For example:
      
      Original TOS byte: hex 8A (10001010 in binary)
      tos attribute: hex 12 (00010010 in binary)
      tosMask attribute: hex 3F (00111111 in binary)
      
      The changed TOS byte would be: hex 92 (10010010 in binary)."
   DEFVAL     { 0 }
::= { mscVrIpPgCosTreatmentProvEntry 4 }

mscVrIpPgCosTreatmentTosMask OBJECT-TYPE
   SYNTAX     Hex (1..255)
   ACCESS     read-write
   STATUS     mandatory
   DESCRIPTION
     "This attribute specifies the Type Of Service (TOS) bit mask with 
      which the packets are examined and updated when this COS 
      treatment is selected. The mask specifies which bits within the 
      original TOS byte are to be examined or updated by the router.
      
      When the setTosByte is set to yes, this attribute is used in 
      conjunction with the tos attribute to determine how the TOS byte is 
      updated using the following formula:
      
      New TOS = ( Original TOS & ~tosMask ) | ( tos & tosMask )
      
      For example:
      
      Original TOS byte: hex 8A (10001010 in binary)
      tos attribute: hex 12 (00010010 in binary)
      tosMask attribute: hex 3F (00111111 in binary)
      
      The changed TOS byte would be: hex 92 (10010010 in binary).
      
      When the TosMap component is provisioned under this Policy, this 
      attribute is used in conjunction with the tos attribute of the TosMap 
      component when packets are examined for matching TOS bits.
      
      By default, this attribute is set to the value of hex E0, i.e. bit 0, 1 
      and 2 of the TOS byte (the Precendence bits) are eligible to be 
      examined and updated.
      
      When either the setTosByte is set to yes, or when the TosMap 
      component is provisioned, a zero tosMask is considered invalid,"
   DEFVAL     { 224 }
::= { mscVrIpPgCosTreatmentProvEntry 5 }




-- 
-- Version and Compliance statements
-- 



-- Object-Group Statement:
-- A list of all current accessible leaf objects.

-- OBJECTS { mscVrIpPgPolicyIpAddrLayer4FlowPortNumberRangeValue,
--           mscVrIpPgCosTreatmentTosMask,
--           mscVrIpPgUsersValue,
--           mscVrIpPgCosTreatmentCos,
--           mscVrIpPgCosTreatmentComponentName,
--           mscVrIpPgRowStatus,
--           mscVrIpPgCosTreatmentStorageType,
--           mscVrIpPgPolicyIpAddrLayer4FlowPortNumberRangeRowStatus,
--           mscVrIpPgPolicyIpAddrLayer4FlowRowStatus,
--           mscVrIpPgPolicyRowStatus,
--           mscVrIpPgPolicyTosMapTosRowStatus,
--           mscVrIpPgPolicyIpAddrLayer4FlowPrefix,
--           mscVrIpPgPolicyTosMapRowStatus,
--           mscVrIpPgPolicyTosMapStorageType,
--           mscVrIpPgCosTreatmentSetTosByte,
--           mscVrIpPgComponentName,
--           mscVrIpPgPolicyIpAddrLayer4FlowCos,
--           mscVrIpPgPolicyTosMapTosValue,
--           mscVrIpPgCosTreatmentTos,
--           mscVrIpPgPolicyCosTreatmentIndex,
--           mscVrIpPgPolicyComponentName,
--           mscVrIpPgCosTreatmentRowStatus,
--           mscVrIpPgPolicyIpAddrLayer4FlowProtocol,
--           mscVrIpPgPolicyIpAddrLayer4FlowStorageType,
--           mscVrIpPgPolicyTosMapCos,
--           mscVrIpPgUsersRowStatus,
--           mscVrIpPgStorageType,
--           mscVrIpPgPolicyIpAddrLayer4FlowPrefixLength,
--           mscVrIpPgPolicyStorageType,
--           mscVrIpPgPolicyIpAddrLayer4FlowComponentName,
--           mscVrIpPgPolicyTosMapComponentName }
-- STATUS  mandatory
-- DESCRIPTION
--   "A list of all current accessible leaf objects."

ipCosGroup OBJECT IDENTIFIER ::= { ipCosMIB 1 }
ipCosGroupCA OBJECT IDENTIFIER ::= { ipCosGroup 1 }
ipCosGroupCA02 OBJECT IDENTIFIER ::= { ipCosGroupCA 3 }
ipCosGroupCA02A OBJECT IDENTIFIER ::= { ipCosGroupCA02 2 }



-- Agent-Capabilities Statement:

-- PRODUCT-RELEASE "MscPassport Release 1.2 IpCos."
-- STATUS          mandatory
-- DESCRIPTION     "Carrier Passport IpCos MIB: MIB Version CA02A,
--                  Software Version CA02S9C."
-- SUPPORTS        Nortel-MsCarrier-MscPassport-IpCosMIB
--    INCLUDES     { ipCosGroupCA02A }

ipCosCapabilities OBJECT IDENTIFIER ::= { ipCosMIB 3 }
ipCosCapabilitiesCA OBJECT IDENTIFIER ::= { ipCosCapabilities 1 }
ipCosCapabilitiesCA02 OBJECT IDENTIFIER ::= { ipCosCapabilitiesCA 3 }
ipCosCapabilitiesCA02A OBJECT IDENTIFIER ::= { ipCosCapabilitiesCA02 2 }





END
