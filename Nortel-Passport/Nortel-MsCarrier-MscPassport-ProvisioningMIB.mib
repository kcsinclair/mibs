Nortel-MsCarrier-MscPassport-ProvisioningMIB
DEFINITIONS ::= BEGIN



IMPORTS

      OBJECT-TYPE
   FROM RFC-1212

      mscPassportMIBs,
      mscComponents
   FROM Nortel-MsCarrier-MscPassport-UsefulDefinitionsMIB

      RowPointer,
      DisplayString,
      StorageType,
      RowStatus,
      Unsigned32
   FROM Nortel-MsCarrier-MscPassport-StandardTextualConventionsMIB

      AsciiString,
      NonReplicated,
      EnterpriseDateAndTime,
      AsciiStringIndex
   FROM Nortel-MsCarrier-MscPassport-TextualConventionsMIB;




-- LAST-UPDATED   "9909010000Z"
-- ORGANIZATION   "Nortel Networks"
-- CONTACT-INFO   "
--         Nortel Carrier Data Network Management
--         
--         Postal:       P.O. Box 3511, Station C 
--                       Ottawa, Ontario 
--                       Canada  K1Y 4H7
--         
--         via the WEB:  http://www.nortelnetworks.com  
--                       select 'Contact Us' from the menu
--          
--         via phone:    1-800-4NORTEL"
-- DESCRIPTION
--    "The module describing the Nortel MsCarrier MscPassport
--     Provisioning Enterprise MIB."

provisioningMIB OBJECT IDENTIFIER ::= { mscPassportMIBs 19 }










-- ProvisioningSystem
-- This component implements the operator commands which are 
-- specific to the provisioning system. It also provides information 
-- about the state of the provisioning system.
-- 
-- The ProvisioningSystem is automatically created on system start-up.

mscProv OBJECT IDENTIFIER ::= { mscComponents 11 }



mscProvRowStatusTable OBJECT-TYPE
   SYNTAX     SEQUENCE OF MscProvRowStatusEntry
   ACCESS     not-accessible
   STATUS     mandatory
   DESCRIPTION
     "This entry controls the addition and deletion of 
      mscProv components."
::= { mscProv 1 }

mscProvRowStatusEntry OBJECT-TYPE
   SYNTAX     MscProvRowStatusEntry
   ACCESS     not-accessible
   STATUS     mandatory
   DESCRIPTION
     "A single entry in the table represents a single 
      mscProv component."
   INDEX {
      mscProvIndex }
::= { mscProvRowStatusTable 1 }

MscProvRowStatusEntry ::= SEQUENCE {
   mscProvRowStatus
      RowStatus,
   mscProvComponentName
      DisplayString,
   mscProvStorageType
      StorageType,
   mscProvIndex
      NonReplicated }

mscProvRowStatus OBJECT-TYPE
   SYNTAX     RowStatus 
   ACCESS     read-only
   STATUS     mandatory
   DESCRIPTION
     "This variable is used as the basis for SNMP naming of
      mscProv components.
      These components cannot be added nor deleted."
::= { mscProvRowStatusEntry 1 }

mscProvComponentName OBJECT-TYPE
   SYNTAX     DisplayString 
   ACCESS     read-only
   STATUS     mandatory
   DESCRIPTION
     "This variable provides the component's string name for
      use with the ASCII Console Interface"
::= { mscProvRowStatusEntry 2 }

mscProvStorageType OBJECT-TYPE
   SYNTAX     StorageType 
   ACCESS     read-only
   STATUS     mandatory
   DESCRIPTION
     "This variable represents the storage type value for the
      mscProv tables."
::= { mscProvRowStatusEntry 4 }

mscProvIndex OBJECT-TYPE
   SYNTAX     NonReplicated 
   ACCESS     not-accessible
   STATUS     mandatory
   DESCRIPTION
     "This variable represents the index for the mscProv tables."
::= { mscProvRowStatusEntry 10 }

mscProvStateTable OBJECT-TYPE
   SYNTAX     SEQUENCE OF MscProvStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscProv 10 }

mscProvStateEntry OBJECT-TYPE
   SYNTAX     MscProvStateEntry
   ACCESS     not-accessible
   STATUS     mandatory
   DESCRIPTION
     "An entry in the mscProvStateTable."
   INDEX {
      mscProvIndex }
::= { mscProvStateTable 1 }

MscProvStateEntry ::= SEQUENCE {
   mscProvAdminState
      INTEGER,
   mscProvOperationalState
      INTEGER,
   mscProvUsageState
      INTEGER }

mscProvAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscProvStateEntry 1 }

mscProvOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscProvStateEntry 2 }

mscProvUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscProvStateEntry 3 }

mscProvOperTable OBJECT-TYPE
   SYNTAX     SEQUENCE OF MscProvOperEntry
   ACCESS     not-accessible
   STATUS     mandatory
   DESCRIPTION
     "This group contains the operational attributes for the 
      ProvisioningSystem component."
::= { mscProv 11 }

mscProvOperEntry OBJECT-TYPE
   SYNTAX     MscProvOperEntry
   ACCESS     not-accessible
   STATUS     mandatory
   DESCRIPTION
     "An entry in the mscProvOperTable."
   INDEX {
      mscProvIndex }
::= { mscProvOperTable 1 }

MscProvOperEntry ::= SEQUENCE {
   mscProvProvisioningActivity
      INTEGER,
   mscProvActivityProgress
      AsciiString,
   mscProvCommittedFileName
      AsciiString,
   mscProvCurrentViewFileName
      AsciiString,
   mscProvLastUsedFileName
      AsciiString,
   mscProvProvisioningSession
      RowPointer,
   mscProvProvisioningUser
      AsciiString,
   mscProvCheckRequired
      INTEGER,
   mscProvNextFileSequenceNumber
      Unsigned32,
   mscProvConfirmRequired
      INTEGER,
   mscProvProvisioningDirectory
      AsciiString,
   mscProvEditViewName
      AsciiString,
   mscProvEditViewAddedComponents
      Unsigned32,
   mscProvEditViewDeletedComponents
      Unsigned32,
   mscProvEditViewChangedComponents
      Unsigned32,
   mscProvStandbyCpActivity
      INTEGER,
   mscProvStandbyCpActivityProgress
      AsciiString }

mscProvProvisioningActivity OBJECT-TYPE
   SYNTAX     INTEGER  {
                 initialLoading(0),
                 none(2),
                 activation(3),
                 initialActivation(4),
                 rollingBack(5),
                 saving(6),
                 loadingOrApplying(7),
                 semanticChecking(8),
                 waitingForConfirm(9),
                 clearing(11),
                 copying(12),
                 committing(13),
                 deleting(14),
                 confirming(15),
                 adding(21) }
   ACCESS     read-only
   STATUS     mandatory
   DESCRIPTION
     "This attribute describes the type of provisioning activity that the 
      ProvisioningSystem component is performing."
::= { mscProvOperEntry 1 }

mscProvActivityProgress OBJECT-TYPE
   SYNTAX     AsciiString (SIZE (1..255))
   ACCESS     read-only
   STATUS     mandatory
   DESCRIPTION
     "This attribute indicates the status relating to a long-running 
      command handled by the ProvisioningSystem. It is usually 
      expressed as a percentage of the number of elements (for example, 
      components) processed with respect to the total set of elements that 
      need to be processed for that activity. Note that, one cannot assume 
      that the percentage implies how much time the task may still take. 
      The time to complete the activity is dependent on many things 
      which are beyond the control of the ProvisioningSystem itself."
::= { mscProvOperEntry 2 }

mscProvCommittedFileName OBJECT-TYPE
   SYNTAX     AsciiString (SIZE (1..40))
   ACCESS     read-only
   STATUS     mandatory
   DESCRIPTION
     "This attribute contains the name of the committed file. This is the 
      file that will be used to obtain the provisioning data if the module 
      restarts.
      
      Immediately after system power-up, this attribute contains the name 
      of the file used during initial loading."
::= { mscProvOperEntry 3 }

mscProvCurrentViewFileName OBJECT-TYPE
   SYNTAX     AsciiString (SIZE (1..40))
   ACCESS     read-only
   STATUS     mandatory
   DESCRIPTION
     "This attribute contains the name of the provisioning file that 
      contains the current view provisioning data.
      
      After system power-up, this attribute contains the name of the file 
      used during initial loading.
      
      If the current view data has not been saved, this attribute is empty."
::= { mscProvOperEntry 4 }

mscProvLastUsedFileName OBJECT-TYPE
   SYNTAX     AsciiString (SIZE (1..40))
   ACCESS     read-only
   STATUS     mandatory
   DESCRIPTION
     "This attribute contains the last saved, loaded or committed file 
      name. If a Load, Save or Commit command returns an error, this 
      attribute remains unchanged.
      
      Immediately after system power-up, this attribute contains the name 
      of the file used during initial loading."
::= { mscProvOperEntry 5 }

mscProvProvisioningSession OBJECT-TYPE
   SYNTAX     RowPointer 
   ACCESS     read-only
   STATUS     mandatory
   DESCRIPTION
     "This attribute contains the component name of the operator session 
      which is currently in provisioning mode. For example,
      NMIS Telnet Session/2
      If no session is in provisioning mode, this attribute will be empty."
::= { mscProvOperEntry 6 }

mscProvProvisioningUser OBJECT-TYPE
   SYNTAX     AsciiString (SIZE (1..8))
   ACCESS     read-only
   STATUS     mandatory
   DESCRIPTION
     "This attribute contains the userid of the operator who is currently 
      provisioning the module. If no session is in provisioning mode, this 
      attribute will be empty."
::= { mscProvOperEntry 7 }

mscProvCheckRequired OBJECT-TYPE
   SYNTAX     INTEGER  {
                 no(0),
                 yes(1) }
   ACCESS     read-only
   STATUS     mandatory
   DESCRIPTION
     "This attribute indicates whether semantic checking is required 
      before activating the edit view."
::= { mscProvOperEntry 8 }

mscProvNextFileSequenceNumber OBJECT-TYPE
   SYNTAX     Unsigned32 (1..999)
   ACCESS     read-write
   STATUS     obsolete
   DESCRIPTION
     "This attribute is no longer supported."
::= { mscProvOperEntry 9 }

mscProvConfirmRequired OBJECT-TYPE
   SYNTAX     INTEGER  {
                 no(0),
                 yes(1) }
   ACCESS     read-only
   STATUS     mandatory
   DESCRIPTION
     "This attribute indicates whether the operator must enter a
      Confirm Prov
      command in order to keep a newly activated current view in effect.
      
      If an activation is not confirmed within 20 minutes of its 
      completion, the module will restart using the committed 
      provisioning data."
::= { mscProvOperEntry 10 }

mscProvProvisioningDirectory OBJECT-TYPE
   SYNTAX     AsciiString (SIZE (1..128))
   ACCESS     read-only
   STATUS     obsolete
   DESCRIPTION
     "This attribute indicates the name of the provisioning directory."
::= { mscProvOperEntry 11 }

mscProvEditViewName OBJECT-TYPE
   SYNTAX     AsciiString (SIZE (0..40))
   ACCESS     read-only
   STATUS     mandatory
   DESCRIPTION
     "This attribute indicates the name of the provisioning view that 
      represents the edit view provisioning data.
      
      If the edit view data has not been saved, this attribute is empty."
::= { mscProvOperEntry 12 }

mscProvEditViewAddedComponents OBJECT-TYPE
   SYNTAX     Unsigned32 (0..4294967295)
   ACCESS     read-only
   STATUS     mandatory
   DESCRIPTION
     "This attribute indicates the number of provisioning components that 
      have been added to the edit view with respect to the current view."
::= { mscProvOperEntry 13 }

mscProvEditViewDeletedComponents OBJECT-TYPE
   SYNTAX     Unsigned32 (0..4294967295)
   ACCESS     read-only
   STATUS     mandatory
   DESCRIPTION
     "This attribute indicates the number of provisioned components that 
      have been deleted from the edit view with respect to the current 
      view."
::= { mscProvOperEntry 14 }

mscProvEditViewChangedComponents OBJECT-TYPE
   SYNTAX     Unsigned32 (0..4294967295)
   ACCESS     read-only
   STATUS     mandatory
   DESCRIPTION
     "This attribute indicates the number of provisioned components 
      whose attributes differ between the edit and current views."
::= { mscProvOperEntry 15 }

mscProvStandbyCpActivity OBJECT-TYPE
   SYNTAX     INTEGER  {
                 none(0),
                 loadingProvisioningData(1),
                 savingCommitFormatProvisioningData(6) }
   ACCESS     read-only
   STATUS     mandatory
   DESCRIPTION
     "This attribute descibes the type of provisionin activity, which 
      ProvisioningSystem is performing on standby CP."
::= { mscProvOperEntry 16 }

mscProvStandbyCpActivityProgress OBJECT-TYPE
   SYNTAX     AsciiString (SIZE (1..255))
   ACCESS     read-only
   STATUS     mandatory
   DESCRIPTION
     "This attribute indicates status of a provisioning activity, which 
      ProvisioningSystem is performing on standby CP."
::= { mscProvOperEntry 17 }

-- 
-- *** THIS SUBTREE CURRENTLY NOT IMPLEMENTED ***
-- 

-- Prov View/<string>
-- This component represents information about provisioning views. 
-- 
-- Most of these views have been saved and can be activated or loaded. 
-- In this case, the format for <string> is
-- <name>.<type>.<number>
-- where <name> is the view's name; <type> is either full or part, 
-- <number> is a unique sequence number generated by the system.
-- 
-- The current and edit views are not necessarily saved.

mscProvView OBJECT IDENTIFIER ::= { mscProv 2 }



mscProvViewRowStatusTable OBJECT-TYPE
   SYNTAX     SEQUENCE OF MscProvViewRowStatusEntry
   ACCESS     not-accessible
   STATUS     mandatory
   DESCRIPTION
     "*** THIS TABLE CURRENTLY NOT IMPLEMENTED ***

      This entry controls the addition and deletion of 
      mscProvView components."
::= { mscProvView 1 }

mscProvViewRowStatusEntry OBJECT-TYPE
   SYNTAX     MscProvViewRowStatusEntry
   ACCESS     not-accessible
   STATUS     mandatory
   DESCRIPTION
     "A single entry in the table represents a single 
      mscProvView component."
   INDEX {
      mscProvIndex,
      mscProvViewIndex }
::= { mscProvViewRowStatusTable 1 }

MscProvViewRowStatusEntry ::= SEQUENCE {
   mscProvViewRowStatus
      RowStatus,
   mscProvViewComponentName
      DisplayString,
   mscProvViewStorageType
      StorageType,
   mscProvViewIndex
      AsciiStringIndex }

mscProvViewRowStatus OBJECT-TYPE
   SYNTAX     RowStatus 
   ACCESS     read-only
   STATUS     mandatory
   DESCRIPTION
     "This variable is used as the basis for SNMP naming of
      mscProvView components.
      These components cannot be added nor deleted."
::= { mscProvViewRowStatusEntry 1 }

mscProvViewComponentName OBJECT-TYPE
   SYNTAX     DisplayString 
   ACCESS     read-only
   STATUS     mandatory
   DESCRIPTION
     "This variable provides the component's string name for
      use with the ASCII Console Interface"
::= { mscProvViewRowStatusEntry 2 }

mscProvViewStorageType OBJECT-TYPE
   SYNTAX     StorageType 
   ACCESS     read-only
   STATUS     mandatory
   DESCRIPTION
     "This variable represents the storage type value for the
      mscProvView tables."
::= { mscProvViewRowStatusEntry 4 }

mscProvViewIndex OBJECT-TYPE
   SYNTAX     AsciiStringIndex (SIZE (1..40))
   ACCESS     not-accessible
   STATUS     mandatory
   DESCRIPTION
     "This variable represents the index for the mscProvView tables."
::= { mscProvViewRowStatusEntry 10 }

mscProvViewOperTable OBJECT-TYPE
   SYNTAX     SEQUENCE OF MscProvViewOperEntry
   ACCESS     not-accessible
   STATUS     mandatory
   DESCRIPTION
     "*** THIS TABLE CURRENTLY NOT IMPLEMENTED ***

      This group contains the operational attributes for the View 
      component."
::= { mscProvView 100 }

mscProvViewOperEntry OBJECT-TYPE
   SYNTAX     MscProvViewOperEntry
   ACCESS     not-accessible
   STATUS     mandatory
   DESCRIPTION
     "An entry in the mscProvViewOperTable."
   INDEX {
      mscProvIndex,
      mscProvViewIndex }
::= { mscProvViewOperTable 1 }

MscProvViewOperEntry ::= SEQUENCE {
   mscProvViewUser
      AsciiString,
   mscProvViewCheckState
      INTEGER,
   mscProvViewComponents
      Unsigned32,
   mscProvViewFormats
      OCTET STRING,
   mscProvViewBaseView
      AsciiString,
   mscProvViewVersion
      AsciiString,
   mscProvViewCreationDate
      EnterpriseDateAndTime }

mscProvViewUser OBJECT-TYPE
   SYNTAX     AsciiString (SIZE (0..8))
   ACCESS     read-only
   STATUS     mandatory
   DESCRIPTION
     "This attribute indicates the userid of the operator who first saved 
      this view. It may be empty if unknown or if the view has not been 
      saved."
::= { mscProvViewOperEntry 1 }

mscProvViewCheckState OBJECT-TYPE
   SYNTAX     INTEGER  {
                 failed(0),
                 unknown(1),
                 partial(2),
                 softwareChanged(3),
                 full(4) }
   ACCESS     read-only
   STATUS     mandatory
   DESCRIPTION
     "This attribute indicates the semantic check state of the view when it 
      was saved. The values are described in worst to best order.
      
      The failed state indicates that the view has failed a semantic check 
      and cannot be activated.
      
      The unknown state indicates that semantic checks have not been 
      run and the view cannot be activated.
      
      The partial state indicates that the view has passed incomplete 
      checks, that is Check -changed Prov has succeeded. This is also the 
      best state value for a partial view. Thew view cannot be activated 
      until it has been fully checked.
      
      The softwareChanged state indicates that the view has passed 
      complete checks, but by software other than that to be activated, 
      that is, either the application versions have changed, or features 
      have been added. After activation, the new software may detect 
      semantic errors. After correcting these errors, if any, the view will 
      need to be re-saved or re-committed as appropriate.
      
      The full state indicates that the view has passed complete checks, 
      that is, it has been fully verified. It can be activated."
::= { mscProvViewOperEntry 2 }

mscProvViewComponents OBJECT-TYPE
   SYNTAX     Unsigned32 (0..999999)
   ACCESS     read-only
   STATUS     mandatory
   DESCRIPTION
     "This attributes indicates the number of provisioned components that 
      have been (or could be) saved."
::= { mscProvViewOperEntry 3 }

mscProvViewFormats OBJECT-TYPE
   SYNTAX     OCTET STRING (SIZE (1))
   ACCESS     read-only
   STATUS     mandatory
   DESCRIPTION
     "This attribute indicates the formats of the saved information. Each 
      serves a different purpose.
      
      The ascii format is readable by operators and can be easily parsed 
      and generated by scripts. NMS makes use of this format. Note that 
      the syntax is subject to change without notice. This format is 
      generated via Save -ascii Prov. A view with an ascii format can be 
      loaded and activated.
      
      The commit format is generated via Commit Prov and allows for 
      fast activation, that is, a shorter service outage time. The system 
      will never leave a view with only this format, as it cannot be loaded.
      
      The delta format contains the changes made between the current 
      view and the edit view. It is, therefore, much smaller and faster to 
      Load or Save than the other formats. A view containing this format 
      can be loaded or have the changes applied to the edit view. This 
      provides a mechanism to propagate a set of changes from one view 
      to another. A view containing only this format can be activated if 
      this would not require a system reload. To generate this format, 
      issue Save Prov without the -ascii or portable options. 
      
      The part format is generated via Save component() Prov. The part 
      format can be loaded. The syntax of this format is subject to change 
      without notice.
      
      The portable format is a compact representation that can be quickly 
      loaded. It can be transported from one Passport to another, or to an 
      NMS. It is generated via Save -portable Prov. The portable format 
      can be loaded and activated.

      Description of bits:
      ascii(0)
      commit(1)
      delta(2)
      part(3)
      portable(4)"
::= { mscProvViewOperEntry 4 }

mscProvViewBaseView OBJECT-TYPE
   SYNTAX     AsciiString (SIZE (0..40))
   ACCESS     read-only
   STATUS     mandatory
   DESCRIPTION
     "This attribute indicates the name of the view upon which this view's 
      changes are based (even if the delta format does not exists). In other 
      words, it indicates the name of the current view that existed at the 
      time that this view was saved. This may not be the name of the 
      current view that is running now.
      
      This attribute is empty when the view is unsaved or if the current 
      view was saved."
::= { mscProvViewOperEntry 5 }

mscProvViewVersion OBJECT-TYPE
   SYNTAX     AsciiString (SIZE (0..16))
   ACCESS     read-only
   STATUS     mandatory
   DESCRIPTION
     "This attribute represents the version of base software that saved this 
      view.
      
      It is empty if unknown."
::= { mscProvViewOperEntry 6 }

mscProvViewCreationDate OBJECT-TYPE
   SYNTAX     EnterpriseDateAndTime (SIZE (0 | 19))
   ACCESS     read-only
   STATUS     mandatory
   DESCRIPTION
     "This attribute indicates the creation date of this view."
::= { mscProvViewOperEntry 7 }




-- 
-- Version and Compliance statements
-- 



-- Object-Group Statement:
-- A list of all current accessible leaf objects.

-- OBJECTS { mscProvAdminState,
--           mscProvViewComponentName,
--           mscProvViewRowStatus,
--           mscProvViewStorageType,
--           mscProvRowStatus,
--           mscProvViewComponents,
--           mscProvProvisioningUser,
--           mscProvProvisioningSession,
--           mscProvViewBaseView,
--           mscProvStandbyCpActivity,
--           mscProvViewUser,
--           mscProvLastUsedFileName,
--           mscProvViewFormats,
--           mscProvProvisioningActivity,
--           mscProvActivityProgress,
--           mscProvEditViewChangedComponents,
--           mscProvUsageState,
--           mscProvStandbyCpActivityProgress,
--           mscProvConfirmRequired,
--           mscProvComponentName,
--           mscProvEditViewAddedComponents,
--           mscProvEditViewDeletedComponents,
--           mscProvStorageType,
--           mscProvViewVersion,
--           mscProvCurrentViewFileName,
--           mscProvViewCheckState,
--           mscProvOperationalState,
--           mscProvCheckRequired,
--           mscProvViewCreationDate,
--           mscProvEditViewName,
--           mscProvCommittedFileName }
-- STATUS  mandatory
-- DESCRIPTION
--   "A list of all current accessible leaf objects."

provisioningGroup OBJECT IDENTIFIER ::= { provisioningMIB 1 }
provisioningGroupCA OBJECT IDENTIFIER ::= { provisioningGroup 1 }
provisioningGroupCA02 OBJECT IDENTIFIER ::= { provisioningGroupCA 3 }
provisioningGroupCA02A OBJECT IDENTIFIER ::= { provisioningGroupCA02 2 }



-- Agent-Capabilities Statement:

-- PRODUCT-RELEASE "MscPassport Release 1.2 Provisioning."
-- STATUS          mandatory
-- DESCRIPTION     "Carrier Passport Provisioning MIB: MIB Version CA02A,
--                  Software Version CA02S9C."
-- SUPPORTS        Nortel-MsCarrier-MscPassport-ProvisioningMIB
--    INCLUDES     { provisioningGroupCA02A }

provisioningCapabilities OBJECT IDENTIFIER ::= { provisioningMIB 3 }
provisioningCapabilitiesCA OBJECT IDENTIFIER ::= { provisioningCapabilities 1 }
provisioningCapabilitiesCA02 OBJECT IDENTIFIER ::= { provisioningCapabilitiesCA 3 }
provisioningCapabilitiesCA02A OBJECT IDENTIFIER ::= { provisioningCapabilitiesCA02 2 }





END
