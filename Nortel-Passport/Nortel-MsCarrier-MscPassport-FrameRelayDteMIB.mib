Nortel-MsCarrier-MscPassport-FrameRelayDteMIB
DEFINITIONS ::= BEGIN



IMPORTS

      OBJECT-TYPE
   FROM RFC-1212

      mscPassportMIBs,
      mscComponents
   FROM Nortel-MsCarrier-MscPassport-UsefulDefinitionsMIB

      Counter32,
      DisplayString,
      StorageType,
      RowStatus,
      InterfaceIndex,
      Gauge32,
      Integer32,
      Unsigned32
   FROM Nortel-MsCarrier-MscPassport-StandardTextualConventionsMIB

      DashedHexString,
      NonReplicated,
      HexString,
      EnterpriseDateAndTime,
      PassportCounter64,
      Link
   FROM Nortel-MsCarrier-MscPassport-TextualConventionsMIB;




-- LAST-UPDATED   "9909010000Z"
-- ORGANIZATION   "Nortel Networks"
-- CONTACT-INFO   "
--         Nortel Carrier Data Network Management
--         
--         Postal:       P.O. Box 3511, Station C 
--                       Ottawa, Ontario 
--                       Canada  K1Y 4H7
--         
--         via the WEB:  http://www.nortelnetworks.com  
--                       select 'Contact Us' from the menu
--          
--         via phone:    1-800-4NORTEL"
-- DESCRIPTION
--    "The module describing the Nortel MsCarrier MscPassport
--     FrameRelayDte Enterprise MIB."

frameRelayDteMIB OBJECT IDENTIFIER ::= { mscPassportMIBs 32 }










-- FrameRelayDte/n
-- The FrameRelayDte component defines the general parameters for 
-- implementing the Frame Relay DTE interface.

mscFrDte OBJECT IDENTIFIER ::= { mscComponents 101 }



mscFrDteRowStatusTable OBJECT-TYPE
   SYNTAX     SEQUENCE OF MscFrDteRowStatusEntry
   ACCESS     not-accessible
   STATUS     mandatory
   DESCRIPTION
     "This entry controls the addition and deletion of 
      mscFrDte components."
::= { mscFrDte 1 }

mscFrDteRowStatusEntry OBJECT-TYPE
   SYNTAX     MscFrDteRowStatusEntry
   ACCESS     not-accessible
   STATUS     mandatory
   DESCRIPTION
     "A single entry in the table represents a single 
      mscFrDte component."
   INDEX {
      mscFrDteIndex }
::= { mscFrDteRowStatusTable 1 }

MscFrDteRowStatusEntry ::= SEQUENCE {
   mscFrDteRowStatus
      RowStatus,
   mscFrDteComponentName
      DisplayString,
   mscFrDteStorageType
      StorageType,
   mscFrDteIndex
      Integer32 }

mscFrDteRowStatus OBJECT-TYPE
   SYNTAX     RowStatus 
   ACCESS     read-write
   STATUS     mandatory
   DESCRIPTION
     "This variable is used as the basis for SNMP naming of
      mscFrDte components.
      These components can be added and deleted."
::= { mscFrDteRowStatusEntry 1 }

mscFrDteComponentName OBJECT-TYPE
   SYNTAX     DisplayString 
   ACCESS     read-only
   STATUS     mandatory
   DESCRIPTION
     "This variable provides the component's string name for
      use with the ASCII Console Interface"
::= { mscFrDteRowStatusEntry 2 }

mscFrDteStorageType OBJECT-TYPE
   SYNTAX     StorageType 
   ACCESS     read-only
   STATUS     mandatory
   DESCRIPTION
     "This variable represents the storage type value for the
      mscFrDte tables."
::= { mscFrDteRowStatusEntry 4 }

mscFrDteIndex OBJECT-TYPE
   SYNTAX     Integer32 (1..65535)
   ACCESS     not-accessible
   STATUS     mandatory
   DESCRIPTION
     "This variable represents the index for the mscFrDte tables."
::= { mscFrDteRowStatusEntry 10 }

mscFrDteCidDataTable OBJECT-TYPE
   SYNTAX     SEQUENCE OF MscFrDteCidDataEntry
   ACCESS     not-accessible
   STATUS     mandatory
   DESCRIPTION
     "This group contains the attribute for a component's Customer 
      Identifier (CID). Refer to the attribute description for a detailed 
      explanation of CIDs."
::= { mscFrDte 20 }

mscFrDteCidDataEntry OBJECT-TYPE
   SYNTAX     MscFrDteCidDataEntry
   ACCESS     not-accessible
   STATUS     mandatory
   DESCRIPTION
     "An entry in the mscFrDteCidDataTable."
   INDEX {
      mscFrDteIndex }
::= { mscFrDteCidDataTable 1 }

MscFrDteCidDataEntry ::= SEQUENCE {
   mscFrDteCustomerIdentifier
      Unsigned32 }

mscFrDteCustomerIdentifier OBJECT-TYPE
   SYNTAX     Unsigned32 (0 | 1..8191)
   ACCESS     read-write
   STATUS     mandatory
   DESCRIPTION
     "This attribute holds the Customer Identifier (CID).
      
      Every component has a CID. If a component has a cid attribute, the 
      component's CID is the provisioned value of that attribute; 
      otherwise the component inherits the CID of its parent. The top-
      level component has a CID of 0.
      
      Every operator session also has a CID, which is the CID 
      provisioned for the operator's user ID. An operator will see only the 
      stream data for components having a matching CID. Also, the 
      operator will be allowed to issue commands for only those 
      components which have a matching CID.
      
      An operator CID of 0 is used to identify the Network Manager 
      (referred to as 'NetMan' in DPN). This CID matches the CID of 
      any component. Values 1 to 8191 inclusive (equivalent to 'basic 
      CIDs' in DPN) may be assigned to specific customers."
   DEFVAL     { 0 }
::= { mscFrDteCidDataEntry 1 }

mscFrDteIfEntryTable OBJECT-TYPE
   SYNTAX     SEQUENCE OF MscFrDteIfEntryEntry
   ACCESS     not-accessible
   STATUS     mandatory
   DESCRIPTION
     "This group contains the provisionable attributes for the ifEntry."
::= { mscFrDte 21 }

mscFrDteIfEntryEntry OBJECT-TYPE
   SYNTAX     MscFrDteIfEntryEntry
   ACCESS     not-accessible
   STATUS     mandatory
   DESCRIPTION
     "An entry in the mscFrDteIfEntryTable."
   INDEX {
      mscFrDteIndex }
::= { mscFrDteIfEntryTable 1 }

MscFrDteIfEntryEntry ::= SEQUENCE {
   mscFrDteIfAdminStatus
      INTEGER,
   mscFrDteIfIndex
      InterfaceIndex }

mscFrDteIfAdminStatus OBJECT-TYPE
   SYNTAX     INTEGER  {
                 up(1),
                 down(2),
                 testing(3) }
   ACCESS     read-write
   STATUS     mandatory
   DESCRIPTION
     "The desired state of the interface. The up state indicates the 
      interface is operational. The down state indicates the interface is not 
      operational. The testing state indicates that no operational packets 
      can be passed."
   DEFVAL     { up }
::= { mscFrDteIfEntryEntry 1 }

mscFrDteIfIndex OBJECT-TYPE
   SYNTAX     InterfaceIndex (1..65535)
   ACCESS     read-only
   STATUS     mandatory
   DESCRIPTION
     "This is the index for the IfEntry. Its value is automatically initialized 
      during the provisioning process."
::= { mscFrDteIfEntryEntry 2 }

mscFrDteProvTable OBJECT-TYPE
   SYNTAX     SEQUENCE OF MscFrDteProvEntry
   ACCESS     not-accessible
   STATUS     mandatory
   DESCRIPTION
     "This group contains the provisioned attributes for the FrDte component."
::= { mscFrDte 22 }

mscFrDteProvEntry OBJECT-TYPE
   SYNTAX     MscFrDteProvEntry
   ACCESS     not-accessible
   STATUS     mandatory
   DESCRIPTION
     "An entry in the mscFrDteProvTable."
   INDEX {
      mscFrDteIndex }
::= { mscFrDteProvTable 1 }

MscFrDteProvEntry ::= SEQUENCE {
   mscFrDteAcceptUndefinedDlci
      INTEGER }

mscFrDteAcceptUndefinedDlci OBJECT-TYPE
   SYNTAX     INTEGER  {
                 enabled(1),
                 disabled(2) }
   ACCESS     read-write
   STATUS     mandatory
   DESCRIPTION
     "This parameter allows previously undefined Data Link Connection 
      Identifiers (DLCIs) to be dynamically accepted in the default remote 
      group. If set to enabled, undefined DLCIs will be accepted, if disabled, 
      they will not."
   DEFVAL     { enabled }
::= { mscFrDteProvEntry 1 }

mscFrDteStateTable OBJECT-TYPE
   SYNTAX     SEQUENCE OF MscFrDteStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscFrDte 23 }

mscFrDteStateEntry OBJECT-TYPE
   SYNTAX     MscFrDteStateEntry
   ACCESS     not-accessible
   STATUS     mandatory
   DESCRIPTION
     "An entry in the mscFrDteStateTable."
   INDEX {
      mscFrDteIndex }
::= { mscFrDteStateTable 1 }

MscFrDteStateEntry ::= SEQUENCE {
   mscFrDteAdminState
      INTEGER,
   mscFrDteOperationalState
      INTEGER,
   mscFrDteUsageState
      INTEGER }

mscFrDteAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscFrDteStateEntry 1 }

mscFrDteOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscFrDteStateEntry 2 }

mscFrDteUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscFrDteStateEntry 3 }

mscFrDteOperStatusTable OBJECT-TYPE
   SYNTAX     SEQUENCE OF MscFrDteOperStatusEntry
   ACCESS     not-accessible
   STATUS     mandatory
   DESCRIPTION
     "This group includes the Operational Status attribute. This attribute 
      defines the current operational state of this component."
::= { mscFrDte 24 }

mscFrDteOperStatusEntry OBJECT-TYPE
   SYNTAX     MscFrDteOperStatusEntry
   ACCESS     not-accessible
   STATUS     mandatory
   DESCRIPTION
     "An entry in the mscFrDteOperStatusTable."
   INDEX {
      mscFrDteIndex }
::= { mscFrDteOperStatusTable 1 }

MscFrDteOperStatusEntry ::= SEQUENCE {
   mscFrDteSnmpOperStatus
      INTEGER }

mscFrDteSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { mscFrDteOperStatusEntry 1 }

mscFrDteOperTable OBJECT-TYPE
   SYNTAX     SEQUENCE OF MscFrDteOperEntry
   ACCESS     not-accessible
   STATUS     mandatory
   DESCRIPTION
     "This group contains the operational attributes for the FrDte component."
::= { mscFrDte 25 }

mscFrDteOperEntry OBJECT-TYPE
   SYNTAX     MscFrDteOperEntry
   ACCESS     not-accessible
   STATUS     mandatory
   DESCRIPTION
     "An entry in the mscFrDteOperTable."
   INDEX {
      mscFrDteIndex }
::= { mscFrDteOperTable 1 }

MscFrDteOperEntry ::= SEQUENCE {
   mscFrDteLinkOperState
      INTEGER }

mscFrDteLinkOperState OBJECT-TYPE
   SYNTAX     INTEGER  {
                 active(1),
                 down(2),
                 polling(3) }
   ACCESS     read-only
   STATUS     mandatory
   DESCRIPTION
     "This attribute describes the operational state of the Link Control 
      protocol. If the interface to the physical link hardware is inactive, the 
      linkOperState is in the down state. 
      
      The polling state only occurs when the Local Management Interface 
      (LMI) is enabled and the physical link is active. The polling state 
      indicates LMI is polling for its peer. Once communication is established 
      the linkOperState will transition to the active state. 
      
      If the procedure attribute of the Lmi component is set to none, 
      linkOperState will transition to the active state once the physical link 
      becomes active."
   DEFVAL     { down }
::= { mscFrDteOperEntry 1 }

mscFrDteErrTable OBJECT-TYPE
   SYNTAX     SEQUENCE OF MscFrDteErrEntry
   ACCESS     not-accessible
   STATUS     mandatory
   DESCRIPTION
     "This group contains the SNMP frErrEntry attributes for the FrDte 
      component."
::= { mscFrDte 26 }

mscFrDteErrEntry OBJECT-TYPE
   SYNTAX     MscFrDteErrEntry
   ACCESS     not-accessible
   STATUS     mandatory
   DESCRIPTION
     "An entry in the mscFrDteErrTable."
   INDEX {
      mscFrDteIndex }
::= { mscFrDteErrTable 1 }

MscFrDteErrEntry ::= SEQUENCE {
   mscFrDteErrType
      INTEGER,
   mscFrDteErrData
      HexString,
   mscFrDteErrTime
      EnterpriseDateAndTime,
   mscFrDteErrDiscards
      Counter32,
   mscFrDteErrFaults
      Counter32,
   mscFrDteErrFaultTime
      EnterpriseDateAndTime }

mscFrDteErrType OBJECT-TYPE
   SYNTAX     INTEGER  {
                 unknownError(1),
                 receiveShort(2),
                 receiveLong(3),
                 illegalDlci(4),
                 dlcmiProtoErr(5),
                 dlcmiUnknownIe(6),
                 dlcmiSequenceErr(7),
                 dlcmiUnknownRpt(8),
                 noErrorSinceReset(9) }
   ACCESS     read-only
   STATUS     mandatory
   DESCRIPTION
     "The type of error that was last seen on this interface. The error types are 
      as follows:
      
      receiveShort: This error indicates a received frame was discarded 
      because it was less than four octets long or it was missing the 
      Organizationally Unique Identifier (OUI) for a SNAP header.
      
      receiveLong: This error indicates a received frame was discarded 
      because it was longer than expected. This error is currently not used on 
      this interface.
      
      illegalDlci: This error indicates that a received frame was discarded 
      because it's Q.922 address was not two octets in length. This error could 
      also indicate that a frame was discarded because it was received on a 
      DLCI reserved for LMI which had not been provisioned active.
      
      dlcmiProtoErr: This error indicates an LMI frame was received with 
      contents formatted incorrectly.
      
      dlcmiUnknownIe: This error indicates that an LMI frame was received 
      which contained an unsupported Information Element (IE) type
      
      dlcmiSequenceErr: This error indicates that an LMI frame was received 
      whose Keep Alive Sequence was incorrect.
      
      dlcmiUnknownRpt: This error indicates that an LMI frame was received 
      which contained a Report-type Information Element with an invalid type 
      of report.
      
      noErrorSinceReset: This error type indicates that there has not been an 
      error since the interface has been reset.
      
      unknownError: This error type contains the cumulation of receive 
      frame errors that did not fit one of the MIB error descriptions above. 
      These errors include those counted by the following attributes:
      
      ulpUnknownProtocol - A received frame was discarded because the 
      Upper Level Protocol (ULP) encapsulation used was unsupported.
      
      badFc - A received frame was discarded because the frame control 
      character was incorrect.
      
      defragSequenceErrors - A fragment was received which was discarded 
      due to an out of sequence error detection."
   DEFVAL     { noErrorSinceReset }
::= { mscFrDteErrEntry 2 }

mscFrDteErrData OBJECT-TYPE
   SYNTAX     HexString (SIZE (64))
   ACCESS     read-only
   STATUS     mandatory
   DESCRIPTION
     "An octet string containing the first part of the frame in which an error 
      was last detected."
::= { mscFrDteErrEntry 3 }

mscFrDteErrTime OBJECT-TYPE
   SYNTAX     EnterpriseDateAndTime (SIZE (0 | 19))
   ACCESS     read-only
   STATUS     mandatory
   DESCRIPTION
     "The time at which the last error was detected and recorded in errType."
::= { mscFrDteErrEntry 4 }

mscFrDteErrDiscards OBJECT-TYPE
   SYNTAX     Counter32 
   ACCESS     read-only
   STATUS     mandatory
   DESCRIPTION
     "Number of inbound frames dropped because of format errors or because 
      the virtual circuit was not known. Format errors, in this case, are any 
      errors which would prevent the system from recognizing the DLCI and 
      placing the error in the discard category.
      
      This counter will wrap around to 0 when it exceeds its maximum count."
::= { mscFrDteErrEntry 6 }

mscFrDteErrFaults OBJECT-TYPE
   SYNTAX     Counter32 
   ACCESS     read-only
   STATUS     mandatory
   DESCRIPTION
     "This attribute counts the number of times LMI has taken down the 
      interface. When the procedure attribute of the Lmi component is set to 
      none, this counter will not be incremented.
      
      This counter will wrap around to 0 when it exceeds its maximum count."
::= { mscFrDteErrEntry 7 }

mscFrDteErrFaultTime OBJECT-TYPE
   SYNTAX     EnterpriseDateAndTime (SIZE (0 | 19))
   ACCESS     read-only
   STATUS     mandatory
   DESCRIPTION
     "The last time the errFaults counter was incremented."
::= { mscFrDteErrEntry 8 }

mscFrDteErrStatsTable OBJECT-TYPE
   SYNTAX     SEQUENCE OF MscFrDteErrStatsEntry
   ACCESS     not-accessible
   STATUS     mandatory
   DESCRIPTION
     "This group contains error counters for the FrDte."
::= { mscFrDte 27 }

mscFrDteErrStatsEntry OBJECT-TYPE
   SYNTAX     MscFrDteErrStatsEntry
   ACCESS     not-accessible
   STATUS     mandatory
   DESCRIPTION
     "An entry in the mscFrDteErrStatsTable."
   INDEX {
      mscFrDteIndex }
::= { mscFrDteErrStatsTable 1 }

MscFrDteErrStatsEntry ::= SEQUENCE {
   mscFrDteXmitDiscardPvcDown
      Counter32,
   mscFrDteXmitDiscardLmiInactive
      Counter32,
   mscFrDteXmitDiscardFramerDown
      Counter32,
   mscFrDteXmitDiscardPvcInactive
      Counter32,
   mscFrDteXmitDiscardCirExceeded
      Counter32,
   mscFrDteRecvDiscardPvcDown
      Counter32,
   mscFrDteRecvDiscardLmiInactive
      Counter32,
   mscFrDteRecvDiscardPvcInactive
      Counter32,
   mscFrDteBadFc
      Counter32,
   mscFrDteUlpUnknownProtocol
      Counter32,
   mscFrDteDefragSequenceErrors
      Counter32,
   mscFrDteReceiveShort
      Counter32,
   mscFrDteIllegalDlci
      Counter32,
   mscFrDteDlcmiProtoErr
      Counter32,
   mscFrDteDlcmiUnknownIe
      Counter32,
   mscFrDteDlcmiSequenceErr
      Counter32,
   mscFrDteDlcmiUnknownRpt
      Counter32 }

mscFrDteXmitDiscardPvcDown OBJECT-TYPE
   SYNTAX     Counter32 
   ACCESS     read-only
   STATUS     mandatory
   DESCRIPTION
     "Count of transmitted frames discarded because the Dlci or a component 
      positioned in a hierarchically fashion above it (e.g. it's remote group or 
      the FrDte component) was administratively disabled.
      
      This counter will wrap around to 0 when it exceeds its maximum count."
::= { mscFrDteErrStatsEntry 1 }

mscFrDteXmitDiscardLmiInactive OBJECT-TYPE
   SYNTAX     Counter32 
   ACCESS     read-only
   STATUS     mandatory
   DESCRIPTION
     "Count of transmitted frames discarded because the Local Management 
      Interface (LMI) was not yet active (i.e. LMI was still in the polling 
      state).
      
      This counter will wrap around to 0 when it exceeds its maximum count."
::= { mscFrDteErrStatsEntry 2 }

mscFrDteXmitDiscardFramerDown OBJECT-TYPE
   SYNTAX     Counter32 
   ACCESS     read-only
   STATUS     mandatory
   DESCRIPTION
     "Count of transmitted frames discarded because the framer component 
      was down.
      
      This counter will wrap around to 0 when it exceeds its maximum count."
::= { mscFrDteErrStatsEntry 3 }

mscFrDteXmitDiscardPvcInactive OBJECT-TYPE
   SYNTAX     Counter32 
   ACCESS     read-only
   STATUS     mandatory
   DESCRIPTION
     "Count of transmitted frames discarded because the Local Management 
      Interface (LMI) had inactivated or invalidated the Dlci.
      
      This counter will wrap around to 0 when it exceeds its maximum count."
::= { mscFrDteErrStatsEntry 4 }

mscFrDteXmitDiscardCirExceeded OBJECT-TYPE
   SYNTAX     Counter32 
   ACCESS     read-only
   STATUS     mandatory
   DESCRIPTION
     "Count of transmitted frames discarded because CIR was enabled on a 
      Dlci without a HibernationQueue subcomponent and the traffic 
      exceeded the combined Committed and Excess Burst thresholds.
      
      This counter will wrap around to 0 when it exceeds its maximum count."
::= { mscFrDteErrStatsEntry 5 }

mscFrDteRecvDiscardPvcDown OBJECT-TYPE
   SYNTAX     Counter32 
   ACCESS     read-only
   STATUS     mandatory
   DESCRIPTION
     "Count of received frames discarded because the Dlci or a component 
      positioned in a hierarchically fashion above it (e.g. it's remote group or 
      the FrDte component) was administratively disabled.
      
      This counter will wrap around to 0 when it exceeds its maximum count."
::= { mscFrDteErrStatsEntry 6 }

mscFrDteRecvDiscardLmiInactive OBJECT-TYPE
   SYNTAX     Counter32 
   ACCESS     read-only
   STATUS     mandatory
   DESCRIPTION
     "Count of received frames discarded because the Local Management 
      Interface (LMI) was not yet active (i.e. LMI was still in the polling 
      state).
      
      This counter will wrap around to 0 when it exceeds its maximum count."
::= { mscFrDteErrStatsEntry 7 }

mscFrDteRecvDiscardPvcInactive OBJECT-TYPE
   SYNTAX     Counter32 
   ACCESS     read-only
   STATUS     mandatory
   DESCRIPTION
     "Count of received frames discarded because the Local Management 
      Interface (LMI) had inactivated or invalidated the Dlci.
      
      This counter will wrap around to 0 when it exceeds its maximum count."
::= { mscFrDteErrStatsEntry 8 }

mscFrDteBadFc OBJECT-TYPE
   SYNTAX     Counter32 
   ACCESS     read-only
   STATUS     mandatory
   DESCRIPTION
     "Count of received frames discarded because the frame control character 
      was incorrect. This may indicate that the other side of the link is 
      configured for a different link level protocol.
      
      This counter will wrap around to 0 when it exceeds its maximum count."
::= { mscFrDteErrStatsEntry 9 }

mscFrDteUlpUnknownProtocol OBJECT-TYPE
   SYNTAX     Counter32 
   ACCESS     read-only
   STATUS     mandatory
   DESCRIPTION
     "Count of received frames discarded because the Upper Level Protocol 
      (ULP) encapsulation used was unsupported.
      
      This counter will wrap around to 0 when it exceeds its maximum count."
::= { mscFrDteErrStatsEntry 10 }

mscFrDteDefragSequenceErrors OBJECT-TYPE
   SYNTAX     Counter32 
   ACCESS     read-only
   STATUS     mandatory
   DESCRIPTION
     "Count of fragments received which were discarded due to out of 
      sequence error detection.
      
      This counter will wrap around to 0 when it exceeds its maximum count."
::= { mscFrDteErrStatsEntry 11 }

mscFrDteReceiveShort OBJECT-TYPE
   SYNTAX     Counter32 
   ACCESS     read-only
   STATUS     mandatory
   DESCRIPTION
     "Count of received frames (including LMI frames) discarded because 
      they were less than four octets long or they were missing the 
      Organizationally Unique Identifier (OUI) for a SNAP header.
      
      This counter will wrap around to 0 when it exceeds its maximum count."
::= { mscFrDteErrStatsEntry 12 }

mscFrDteIllegalDlci OBJECT-TYPE
   SYNTAX     Counter32 
   ACCESS     read-only
   STATUS     mandatory
   DESCRIPTION
     "Count of received frames discarded because their Q.922 address was not 
      two octets in length. This count also includes frames discarded because 
      they were received on a Dlci reserved for LMI which had not been 
      provisioned active.
      
      This counter will wrap around to 0 when it exceeds its maximum count."
::= { mscFrDteErrStatsEntry 13 }

mscFrDteDlcmiProtoErr OBJECT-TYPE
   SYNTAX     Counter32 
   ACCESS     read-only
   STATUS     mandatory
   DESCRIPTION
     "Count of received LMI frames whose contents were formatted 
      incorrectly.
      
      This counter will wrap around to 0 when it exceeds its maximum count."
::= { mscFrDteErrStatsEntry 14 }

mscFrDteDlcmiUnknownIe OBJECT-TYPE
   SYNTAX     Counter32 
   ACCESS     read-only
   STATUS     mandatory
   DESCRIPTION
     "Count of received LMI frames which contained an unsupported 
      Information Element (IE) type.
      
      This counter will wrap around to 0 when it exceeds its maximum count."
::= { mscFrDteErrStatsEntry 15 }

mscFrDteDlcmiSequenceErr OBJECT-TYPE
   SYNTAX     Counter32 
   ACCESS     read-only
   STATUS     mandatory
   DESCRIPTION
     "Count of received LMI frames whose Keep Alive Sequence was 
      incorrect.
      
      This counter will wrap around to 0 when it exceeds its maximum count."
::= { mscFrDteErrStatsEntry 16 }

mscFrDteDlcmiUnknownRpt OBJECT-TYPE
   SYNTAX     Counter32 
   ACCESS     read-only
   STATUS     mandatory
   DESCRIPTION
     "Count of received LMI frames which contained a Report-type 
      Information Element with an invalid type of report.
      
      This counter will wrap around to 0 when it exceeds its maximum count."
::= { mscFrDteErrStatsEntry 17 }


-- 
-- FrDte/n Framer
-- 
-- The Framer component controls link layer framing for application 
-- components sending and receiving data on a link interface. It is also 
-- through Framer, that an application component is associated with a 
-- specific hardware link interface.
-- 
-- The Framer component provides provisional attributes related to 
-- datapath aspects of the hardware interface (such as crc and frame length) 
-- rather than interface specific attributes (such as modem leads and 
-- clocking) which are associated with specific hardware components (such 
-- as V35/n or DS1/n). The Framer component also provides a provisional 
-- attribute which binds the application component to a specific hardware 
-- component.
-- 
-- The Framer component contains operational attributes for link interface 
-- datapath statistics (such as frame counts and aborts).
-- 

mscFrDteFramer OBJECT IDENTIFIER ::= { mscFrDte 2 }



mscFrDteFramerRowStatusTable OBJECT-TYPE
   SYNTAX     SEQUENCE OF MscFrDteFramerRowStatusEntry
   ACCESS     not-accessible
   STATUS     mandatory
   DESCRIPTION
     "This entry controls the addition and deletion of 
      mscFrDteFramer components."
::= { mscFrDteFramer 1 }

mscFrDteFramerRowStatusEntry OBJECT-TYPE
   SYNTAX     MscFrDteFramerRowStatusEntry
   ACCESS     not-accessible
   STATUS     mandatory
   DESCRIPTION
     "A single entry in the table represents a single 
      mscFrDteFramer component."
   INDEX {
      mscFrDteIndex,
      mscFrDteFramerIndex }
::= { mscFrDteFramerRowStatusTable 1 }

MscFrDteFramerRowStatusEntry ::= SEQUENCE {
   mscFrDteFramerRowStatus
      RowStatus,
   mscFrDteFramerComponentName
      DisplayString,
   mscFrDteFramerStorageType
      StorageType,
   mscFrDteFramerIndex
      NonReplicated }

mscFrDteFramerRowStatus OBJECT-TYPE
   SYNTAX     RowStatus 
   ACCESS     read-write
   STATUS     mandatory
   DESCRIPTION
     "This variable is used as the basis for SNMP naming of
      mscFrDteFramer components.
      These components can be added and deleted."
::= { mscFrDteFramerRowStatusEntry 1 }

mscFrDteFramerComponentName OBJECT-TYPE
   SYNTAX     DisplayString 
   ACCESS     read-only
   STATUS     mandatory
   DESCRIPTION
     "This variable provides the component's string name for
      use with the ASCII Console Interface"
::= { mscFrDteFramerRowStatusEntry 2 }

mscFrDteFramerStorageType OBJECT-TYPE
   SYNTAX     StorageType 
   ACCESS     read-only
   STATUS     mandatory
   DESCRIPTION
     "This variable represents the storage type value for the
      mscFrDteFramer tables."
::= { mscFrDteFramerRowStatusEntry 4 }

mscFrDteFramerIndex OBJECT-TYPE
   SYNTAX     NonReplicated 
   ACCESS     not-accessible
   STATUS     mandatory
   DESCRIPTION
     "This variable represents the index for the mscFrDteFramer tables."
::= { mscFrDteFramerRowStatusEntry 10 }

mscFrDteFramerProvTable OBJECT-TYPE
   SYNTAX     SEQUENCE OF MscFrDteFramerProvEntry
   ACCESS     not-accessible
   STATUS     mandatory
   DESCRIPTION
     "This group contains the base provisioning data for the Framer 
      component. Application or hardware interface specific provisioning data 
      is contained in other provisional Framer groups."
::= { mscFrDteFramer 10 }

mscFrDteFramerProvEntry OBJECT-TYPE
   SYNTAX     MscFrDteFramerProvEntry
   ACCESS     not-accessible
   STATUS     mandatory
   DESCRIPTION
     "An entry in the mscFrDteFramerProvTable."
   INDEX {
      mscFrDteIndex,
      mscFrDteFramerIndex }
::= { mscFrDteFramerProvTable 1 }

MscFrDteFramerProvEntry ::= SEQUENCE {
   mscFrDteFramerInterfaceName
      Link }

mscFrDteFramerInterfaceName OBJECT-TYPE
   SYNTAX     Link 
   ACCESS     read-write
   STATUS     mandatory
   DESCRIPTION
     "This attribute contains a hardware component name.
      
      The attribute associates the application with a specific link. This defines 
      the module processor on which Framer's parent component (as well as 
      Framer itself) will run."
::= { mscFrDteFramerProvEntry 1 }

mscFrDteFramerStateTable OBJECT-TYPE
   SYNTAX     SEQUENCE OF MscFrDteFramerStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscFrDteFramer 12 }

mscFrDteFramerStateEntry OBJECT-TYPE
   SYNTAX     MscFrDteFramerStateEntry
   ACCESS     not-accessible
   STATUS     mandatory
   DESCRIPTION
     "An entry in the mscFrDteFramerStateTable."
   INDEX {
      mscFrDteIndex,
      mscFrDteFramerIndex }
::= { mscFrDteFramerStateTable 1 }

MscFrDteFramerStateEntry ::= SEQUENCE {
   mscFrDteFramerAdminState
      INTEGER,
   mscFrDteFramerOperationalState
      INTEGER,
   mscFrDteFramerUsageState
      INTEGER }

mscFrDteFramerAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscFrDteFramerStateEntry 1 }

mscFrDteFramerOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscFrDteFramerStateEntry 2 }

mscFrDteFramerUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscFrDteFramerStateEntry 3 }

mscFrDteFramerStatsTable OBJECT-TYPE
   SYNTAX     SEQUENCE OF MscFrDteFramerStatsEntry
   ACCESS     not-accessible
   STATUS     mandatory
   DESCRIPTION
     "This group contains the operational statistics data for a Framer 
      component."
::= { mscFrDteFramer 13 }

mscFrDteFramerStatsEntry OBJECT-TYPE
   SYNTAX     MscFrDteFramerStatsEntry
   ACCESS     not-accessible
   STATUS     mandatory
   DESCRIPTION
     "An entry in the mscFrDteFramerStatsTable."
   INDEX {
      mscFrDteIndex,
      mscFrDteFramerIndex }
::= { mscFrDteFramerStatsTable 1 }

MscFrDteFramerStatsEntry ::= SEQUENCE {
   mscFrDteFramerFrmToIf
      Counter32,
   mscFrDteFramerFrmFromIf
      Counter32,
   mscFrDteFramerAborts
      Counter32,
   mscFrDteFramerCrcErrors
      Counter32,
   mscFrDteFramerLrcErrors
      Counter32,
   mscFrDteFramerNonOctetErrors
      Counter32,
   mscFrDteFramerOverruns
      Counter32,
   mscFrDteFramerUnderruns
      Counter32,
   mscFrDteFramerLargeFrmErrors
      Counter32 }

mscFrDteFramerFrmToIf OBJECT-TYPE
   SYNTAX     Counter32 
   ACCESS     read-only
   STATUS     mandatory
   DESCRIPTION
     "This attribute counts the number of frames transmitted to the link 
      interface by Framer.
      
      Note: This does not include the number of frames transmitted directly to 
      the hardware queue, thus bypassing the Framer component."
::= { mscFrDteFramerStatsEntry 1 }

mscFrDteFramerFrmFromIf OBJECT-TYPE
   SYNTAX     Counter32 
   ACCESS     read-only
   STATUS     mandatory
   DESCRIPTION
     "This attribute counts the number of frames received from the link 
      interface by Framer."
::= { mscFrDteFramerStatsEntry 2 }

mscFrDteFramerAborts OBJECT-TYPE
   SYNTAX     Counter32 
   ACCESS     read-only
   STATUS     mandatory
   DESCRIPTION
     "This attribute counts the total number of aborts received."
::= { mscFrDteFramerStatsEntry 3 }

mscFrDteFramerCrcErrors OBJECT-TYPE
   SYNTAX     Counter32 
   ACCESS     read-only
   STATUS     mandatory
   DESCRIPTION
     "This attribute counts the total number of frames with CRC errors."
::= { mscFrDteFramerStatsEntry 4 }

mscFrDteFramerLrcErrors OBJECT-TYPE
   SYNTAX     Counter32 
   ACCESS     read-only
   STATUS     mandatory
   DESCRIPTION
     "This attribute counts the total number of frames with LRC errors."
::= { mscFrDteFramerStatsEntry 5 }

mscFrDteFramerNonOctetErrors OBJECT-TYPE
   SYNTAX     Counter32 
   ACCESS     read-only
   STATUS     mandatory
   DESCRIPTION
     "This attribute counts the total number of frames that were non octet 
      aligned."
::= { mscFrDteFramerStatsEntry 6 }

mscFrDteFramerOverruns OBJECT-TYPE
   SYNTAX     Counter32 
   ACCESS     read-only
   STATUS     mandatory
   DESCRIPTION
     "This attribute counts the total number of frames received from the link 
      for which overruns occurred."
::= { mscFrDteFramerStatsEntry 7 }

mscFrDteFramerUnderruns OBJECT-TYPE
   SYNTAX     Counter32 
   ACCESS     read-only
   STATUS     mandatory
   DESCRIPTION
     "This attribute counts the total number of frames transmitted to the link 
      for which underruns occurred."
::= { mscFrDteFramerStatsEntry 8 }

mscFrDteFramerLargeFrmErrors OBJECT-TYPE
   SYNTAX     Counter32 
   ACCESS     read-only
   STATUS     mandatory
   DESCRIPTION
     "This attribute counts the total number of frames received which were too 
      large. The frame exceeded the maximumFrameLengthLimit 
      provisioned attribute or it contained more than the 255 block hardware 
      limit."
::= { mscFrDteFramerStatsEntry 9 }

mscFrDteFramerUtilTable OBJECT-TYPE
   SYNTAX     SEQUENCE OF MscFrDteFramerUtilEntry
   ACCESS     not-accessible
   STATUS     mandatory
   DESCRIPTION
     "This group contains the link utilization operational data for a Framer 
      component."
::= { mscFrDteFramer 14 }

mscFrDteFramerUtilEntry OBJECT-TYPE
   SYNTAX     MscFrDteFramerUtilEntry
   ACCESS     not-accessible
   STATUS     mandatory
   DESCRIPTION
     "An entry in the mscFrDteFramerUtilTable."
   INDEX {
      mscFrDteIndex,
      mscFrDteFramerIndex }
::= { mscFrDteFramerUtilTable 1 }

MscFrDteFramerUtilEntry ::= SEQUENCE {
   mscFrDteFramerNormPrioLinkUtilToIf
      Gauge32,
   mscFrDteFramerNormPrioLinkUtilFromIf
      Gauge32 }

mscFrDteFramerNormPrioLinkUtilToIf OBJECT-TYPE
   SYNTAX     Gauge32 (0..100)
   ACCESS     read-only
   STATUS     mandatory
   DESCRIPTION
     "This attribute is the utilization of the normal priority data sent to the link 
      as a percentage of the available bandwidth on the link. The utilization is 
      the average for the last minute."
   DEFVAL     { 0 }
::= { mscFrDteFramerUtilEntry 1 }

mscFrDteFramerNormPrioLinkUtilFromIf OBJECT-TYPE
   SYNTAX     Gauge32 (0..100)
   ACCESS     read-only
   STATUS     mandatory
   DESCRIPTION
     "This attribute is the utilization of the normal priority data received from 
      the link as a percentage of the available bandwidth on the link. The 
      utilization is the average for the last minute."
   DEFVAL     { 0 }
::= { mscFrDteFramerUtilEntry 3 }


-- FrDte/n Lmi
-- This component defines parameters for implementing the Local 
-- Management Interface (LMI) protocol for the FrDte interface.

mscFrDteLmi OBJECT IDENTIFIER ::= { mscFrDte 3 }



mscFrDteLmiRowStatusTable OBJECT-TYPE
   SYNTAX     SEQUENCE OF MscFrDteLmiRowStatusEntry
   ACCESS     not-accessible
   STATUS     mandatory
   DESCRIPTION
     "This entry controls the addition and deletion of 
      mscFrDteLmi components."
::= { mscFrDteLmi 1 }

mscFrDteLmiRowStatusEntry OBJECT-TYPE
   SYNTAX     MscFrDteLmiRowStatusEntry
   ACCESS     not-accessible
   STATUS     mandatory
   DESCRIPTION
     "A single entry in the table represents a single 
      mscFrDteLmi component."
   INDEX {
      mscFrDteIndex,
      mscFrDteLmiIndex }
::= { mscFrDteLmiRowStatusTable 1 }

MscFrDteLmiRowStatusEntry ::= SEQUENCE {
   mscFrDteLmiRowStatus
      RowStatus,
   mscFrDteLmiComponentName
      DisplayString,
   mscFrDteLmiStorageType
      StorageType,
   mscFrDteLmiIndex
      NonReplicated }

mscFrDteLmiRowStatus OBJECT-TYPE
   SYNTAX     RowStatus 
   ACCESS     read-only
   STATUS     mandatory
   DESCRIPTION
     "This variable is used as the basis for SNMP naming of
      mscFrDteLmi components.
      These components cannot be added nor deleted."
::= { mscFrDteLmiRowStatusEntry 1 }

mscFrDteLmiComponentName OBJECT-TYPE
   SYNTAX     DisplayString 
   ACCESS     read-only
   STATUS     mandatory
   DESCRIPTION
     "This variable provides the component's string name for
      use with the ASCII Console Interface"
::= { mscFrDteLmiRowStatusEntry 2 }

mscFrDteLmiStorageType OBJECT-TYPE
   SYNTAX     StorageType 
   ACCESS     read-only
   STATUS     mandatory
   DESCRIPTION
     "This variable represents the storage type value for the
      mscFrDteLmi tables."
::= { mscFrDteLmiRowStatusEntry 4 }

mscFrDteLmiIndex OBJECT-TYPE
   SYNTAX     NonReplicated 
   ACCESS     not-accessible
   STATUS     mandatory
   DESCRIPTION
     "This variable represents the index for the mscFrDteLmi tables."
::= { mscFrDteLmiRowStatusEntry 10 }

mscFrDteLmiProvTable OBJECT-TYPE
   SYNTAX     SEQUENCE OF MscFrDteLmiProvEntry
   ACCESS     not-accessible
   STATUS     mandatory
   DESCRIPTION
     "This group contains the provisioned attributes for the Lmi component."
::= { mscFrDteLmi 10 }

mscFrDteLmiProvEntry OBJECT-TYPE
   SYNTAX     MscFrDteLmiProvEntry
   ACCESS     not-accessible
   STATUS     mandatory
   DESCRIPTION
     "An entry in the mscFrDteLmiProvTable."
   INDEX {
      mscFrDteIndex,
      mscFrDteLmiIndex }
::= { mscFrDteLmiProvTable 1 }

MscFrDteLmiProvEntry ::= SEQUENCE {
   mscFrDteLmiProcedures
      INTEGER,
   mscFrDteLmiPollingInterval
      Unsigned32,
   mscFrDteLmiFullEnquiryInterval
      Unsigned32,
   mscFrDteLmiErrorThreshold
      Unsigned32,
   mscFrDteLmiMonitoredEvents
      Unsigned32 }

mscFrDteLmiProcedures OBJECT-TYPE
   SYNTAX     INTEGER  {
                 none(1),
                 vendorForum(2),
                 ansi(3),
                 ccitt(5) }
   ACCESS     read-write
   STATUS     mandatory
   DESCRIPTION
     "This attribute selects the Local Management Interface (LMI) protocol to 
      be used on the interface. This attribute is equivalent to the SNMP 
      variable frDlcmiState. The vendorForum LMI protocol automatically 
      implies that the DLCI used by the protocol is 1023. The ansi (T1.617 
      Annex D) and ccitt (Q.933 Annex A) LMI protocols use DLCI 0. If 
      none is selected, no LMI procedures will run on the interface."
   DEFVAL     { ccitt }
::= { mscFrDteLmiProvEntry 1 }

mscFrDteLmiPollingInterval OBJECT-TYPE
   SYNTAX     Unsigned32 (5..30)
   ACCESS     read-write
   STATUS     mandatory
   DESCRIPTION
     "This is the number of seconds between successive status enquiry 
      messages. This field corresponds to the parameter T391 described in the 
      ANSI T1.617-1991 Annex D."
   DEFVAL     { 10 }
::= { mscFrDteLmiProvEntry 4 }

mscFrDteLmiFullEnquiryInterval OBJECT-TYPE
   SYNTAX     Unsigned32 (1..255)
   ACCESS     read-write
   STATUS     mandatory
   DESCRIPTION
     "The count of status polls before a full status enquiry message is issued. 
      Every nth poll will request a full status. This field corresponds to the 
      parameter N391 described in the ANSI T1.617-1991 Annex D."
   DEFVAL     { 6 }
::= { mscFrDteLmiProvEntry 5 }

mscFrDteLmiErrorThreshold OBJECT-TYPE
   SYNTAX     Unsigned32 (1..10)
   ACCESS     read-write
   STATUS     mandatory
   DESCRIPTION
     "The number of errors detected within the monitored events window 
      before declaring the link non-functional. This field corresponds to the 
      parameter N392 described in the ANSI T1.617-1991 Annex D."
   DEFVAL     { 3 }
::= { mscFrDteLmiProvEntry 6 }

mscFrDteLmiMonitoredEvents OBJECT-TYPE
   SYNTAX     Unsigned32 (1..10)
   ACCESS     read-write
   STATUS     mandatory
   DESCRIPTION
     "The number of status polling intervals over which the errorthreshold is 
      counted This is used to determine if the errorThreshold is exceeded. 
      This field corresponds to the parameter N393 described in the ANSI 
      T1.617-1991 Annex D."
   DEFVAL     { 4 }
::= { mscFrDteLmiProvEntry 7 }

mscFrDteLmiOperTable OBJECT-TYPE
   SYNTAX     SEQUENCE OF MscFrDteLmiOperEntry
   ACCESS     not-accessible
   STATUS     mandatory
   DESCRIPTION
     "This group contains the operational attributes for the Lmi component."
::= { mscFrDteLmi 11 }

mscFrDteLmiOperEntry OBJECT-TYPE
   SYNTAX     MscFrDteLmiOperEntry
   ACCESS     not-accessible
   STATUS     mandatory
   DESCRIPTION
     "An entry in the mscFrDteLmiOperTable."
   INDEX {
      mscFrDteIndex,
      mscFrDteLmiIndex }
::= { mscFrDteLmiOperTable 1 }

MscFrDteLmiOperEntry ::= SEQUENCE {
   mscFrDteLmiLmiStatus
      INTEGER }

mscFrDteLmiLmiStatus OBJECT-TYPE
   SYNTAX     INTEGER  {
                 running(1),
                 fault(2),
                 initializing(3) }
   ACCESS     read-only
   STATUS     mandatory
   DESCRIPTION
     "This indicates the status of the Frame Relay interface as determined by 
      the performance of the link management interface (LMI). If no LMI is 
      running, lmiStatus will stay in the running state indefinitely."
::= { mscFrDteLmiOperEntry 2 }


-- FrDte/n Rg/n
-- 
-- This component describes the links between a group of Dlcis and a 
-- Protocol Port.
-- 
-- The Rg/1 instance is required.

mscFrDteRg OBJECT IDENTIFIER ::= { mscFrDte 4 }



mscFrDteRgRowStatusTable OBJECT-TYPE
   SYNTAX     SEQUENCE OF MscFrDteRgRowStatusEntry
   ACCESS     not-accessible
   STATUS     mandatory
   DESCRIPTION
     "This entry controls the addition and deletion of 
      mscFrDteRg components."
::= { mscFrDteRg 1 }

mscFrDteRgRowStatusEntry OBJECT-TYPE
   SYNTAX     MscFrDteRgRowStatusEntry
   ACCESS     not-accessible
   STATUS     mandatory
   DESCRIPTION
     "A single entry in the table represents a single 
      mscFrDteRg component."
   INDEX {
      mscFrDteIndex,
      mscFrDteRgIndex }
::= { mscFrDteRgRowStatusTable 1 }

MscFrDteRgRowStatusEntry ::= SEQUENCE {
   mscFrDteRgRowStatus
      RowStatus,
   mscFrDteRgComponentName
      DisplayString,
   mscFrDteRgStorageType
      StorageType,
   mscFrDteRgIndex
      Integer32 }

mscFrDteRgRowStatus OBJECT-TYPE
   SYNTAX     RowStatus 
   ACCESS     read-write
   STATUS     mandatory
   DESCRIPTION
     "This variable is used as the basis for SNMP naming of
      mscFrDteRg components.
      These components can be added and deleted."
::= { mscFrDteRgRowStatusEntry 1 }

mscFrDteRgComponentName OBJECT-TYPE
   SYNTAX     DisplayString 
   ACCESS     read-only
   STATUS     mandatory
   DESCRIPTION
     "This variable provides the component's string name for
      use with the ASCII Console Interface"
::= { mscFrDteRgRowStatusEntry 2 }

mscFrDteRgStorageType OBJECT-TYPE
   SYNTAX     StorageType 
   ACCESS     read-only
   STATUS     mandatory
   DESCRIPTION
     "This variable represents the storage type value for the
      mscFrDteRg tables."
::= { mscFrDteRgRowStatusEntry 4 }

mscFrDteRgIndex OBJECT-TYPE
   SYNTAX     Integer32 (1..256)
   ACCESS     not-accessible
   STATUS     mandatory
   DESCRIPTION
     "This variable represents the index for the mscFrDteRg tables."
::= { mscFrDteRgRowStatusEntry 10 }

mscFrDteRgIfEntryTable OBJECT-TYPE
   SYNTAX     SEQUENCE OF MscFrDteRgIfEntryEntry
   ACCESS     not-accessible
   STATUS     mandatory
   DESCRIPTION
     "This group contains the provisionable attributes for the ifEntry."
::= { mscFrDteRg 10 }

mscFrDteRgIfEntryEntry OBJECT-TYPE
   SYNTAX     MscFrDteRgIfEntryEntry
   ACCESS     not-accessible
   STATUS     mandatory
   DESCRIPTION
     "An entry in the mscFrDteRgIfEntryTable."
   INDEX {
      mscFrDteIndex,
      mscFrDteRgIndex }
::= { mscFrDteRgIfEntryTable 1 }

MscFrDteRgIfEntryEntry ::= SEQUENCE {
   mscFrDteRgIfAdminStatus
      INTEGER,
   mscFrDteRgIfIndex
      InterfaceIndex }

mscFrDteRgIfAdminStatus OBJECT-TYPE
   SYNTAX     INTEGER  {
                 up(1),
                 down(2),
                 testing(3) }
   ACCESS     read-write
   STATUS     mandatory
   DESCRIPTION
     "The desired state of the interface. The up state indicates the 
      interface is operational. The down state indicates the interface is not 
      operational. The testing state indicates that no operational packets 
      can be passed."
   DEFVAL     { up }
::= { mscFrDteRgIfEntryEntry 1 }

mscFrDteRgIfIndex OBJECT-TYPE
   SYNTAX     InterfaceIndex (1..65535)
   ACCESS     read-only
   STATUS     mandatory
   DESCRIPTION
     "This is the index for the IfEntry. Its value is automatically initialized 
      during the provisioning process."
::= { mscFrDteRgIfEntryEntry 2 }

mscFrDteRgProvTable OBJECT-TYPE
   SYNTAX     SEQUENCE OF MscFrDteRgProvEntry
   ACCESS     not-accessible
   STATUS     mandatory
   DESCRIPTION
     "This group contains the provisioned attributes for the Remote Group 
      component."
::= { mscFrDteRg 11 }

mscFrDteRgProvEntry OBJECT-TYPE
   SYNTAX     MscFrDteRgProvEntry
   ACCESS     not-accessible
   STATUS     mandatory
   DESCRIPTION
     "An entry in the mscFrDteRgProvTable."
   INDEX {
      mscFrDteIndex,
      mscFrDteRgIndex }
::= { mscFrDteRgProvTable 1 }

MscFrDteRgProvEntry ::= SEQUENCE {
   mscFrDteRgMaxTransmissionUnit
      Unsigned32 }

mscFrDteRgMaxTransmissionUnit OBJECT-TYPE
   SYNTAX     Unsigned32 (262..9190)
   ACCESS     read-write
   STATUS     mandatory
   DESCRIPTION
     "The Maximum Transmission Unit size of the largest datagram 
      (including Frame Relay header) which can be sent on the interface."
   DEFVAL     { 1604 }
::= { mscFrDteRgProvEntry 1 }

mscFrDteRgMpTable OBJECT-TYPE
   SYNTAX     SEQUENCE OF MscFrDteRgMpEntry
   ACCESS     not-accessible
   STATUS     mandatory
   DESCRIPTION
     "This group contains the base provisioning data for the Media 
      Application component."
::= { mscFrDteRg 12 }

mscFrDteRgMpEntry OBJECT-TYPE
   SYNTAX     MscFrDteRgMpEntry
   ACCESS     not-accessible
   STATUS     mandatory
   DESCRIPTION
     "An entry in the mscFrDteRgMpTable."
   INDEX {
      mscFrDteIndex,
      mscFrDteRgIndex }
::= { mscFrDteRgMpTable 1 }

MscFrDteRgMpEntry ::= SEQUENCE {
   mscFrDteRgLinkToProtocolPort
      Link }

mscFrDteRgLinkToProtocolPort OBJECT-TYPE
   SYNTAX     Link 
   ACCESS     read-write
   STATUS     mandatory
   DESCRIPTION
     "This attribute contains a protocol port component name. The attribute 
      associates the application with a protocol port."
::= { mscFrDteRgMpEntry 1 }

mscFrDteRgStateTable OBJECT-TYPE
   SYNTAX     SEQUENCE OF MscFrDteRgStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscFrDteRg 13 }

mscFrDteRgStateEntry OBJECT-TYPE
   SYNTAX     MscFrDteRgStateEntry
   ACCESS     not-accessible
   STATUS     mandatory
   DESCRIPTION
     "An entry in the mscFrDteRgStateTable."
   INDEX {
      mscFrDteIndex,
      mscFrDteRgIndex }
::= { mscFrDteRgStateTable 1 }

MscFrDteRgStateEntry ::= SEQUENCE {
   mscFrDteRgAdminState
      INTEGER,
   mscFrDteRgOperationalState
      INTEGER,
   mscFrDteRgUsageState
      INTEGER }

mscFrDteRgAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscFrDteRgStateEntry 1 }

mscFrDteRgOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscFrDteRgStateEntry 2 }

mscFrDteRgUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscFrDteRgStateEntry 3 }

mscFrDteRgOperStatusTable OBJECT-TYPE
   SYNTAX     SEQUENCE OF MscFrDteRgOperStatusEntry
   ACCESS     not-accessible
   STATUS     mandatory
   DESCRIPTION
     "This group includes the Operational Status attribute. This attribute 
      defines the current operational state of this component."
::= { mscFrDteRg 14 }

mscFrDteRgOperStatusEntry OBJECT-TYPE
   SYNTAX     MscFrDteRgOperStatusEntry
   ACCESS     not-accessible
   STATUS     mandatory
   DESCRIPTION
     "An entry in the mscFrDteRgOperStatusTable."
   INDEX {
      mscFrDteIndex,
      mscFrDteRgIndex }
::= { mscFrDteRgOperStatusTable 1 }

MscFrDteRgOperStatusEntry ::= SEQUENCE {
   mscFrDteRgSnmpOperStatus
      INTEGER }

mscFrDteRgSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { mscFrDteRgOperStatusEntry 1 }

mscFrDteRgLtDlciTable OBJECT-TYPE
   SYNTAX     SEQUENCE OF MscFrDteRgLtDlciEntry
   ACCESS     not-accessible
   STATUS     mandatory
   DESCRIPTION
     "This attribute associates a Rg component with zero or more StDlci 
      components. The Rg and StDlci components must be under the same 
      FrDte component."
::= { mscFrDteRg 219 }

mscFrDteRgLtDlciEntry OBJECT-TYPE
   SYNTAX     MscFrDteRgLtDlciEntry
   ACCESS     not-accessible
   STATUS     mandatory
   DESCRIPTION
     "An entry in the mscFrDteRgLtDlciTable."
   INDEX {
      mscFrDteIndex,
      mscFrDteRgIndex,
      mscFrDteRgLtDlciValue }
::= { mscFrDteRgLtDlciTable 1 }

MscFrDteRgLtDlciEntry ::= SEQUENCE {
   mscFrDteRgLtDlciValue
      Link,
   mscFrDteRgLtDlciRowStatus
      RowStatus }

mscFrDteRgLtDlciValue OBJECT-TYPE
   SYNTAX     Link 
   ACCESS     read-write
   STATUS     mandatory
   DESCRIPTION
     "This variable represents both the value and the index for the
      mscFrDteRgLtDlciTable."
::= { mscFrDteRgLtDlciEntry 1 }

mscFrDteRgLtDlciRowStatus OBJECT-TYPE
   SYNTAX     RowStatus 
   ACCESS     write-only
   STATUS     mandatory
   DESCRIPTION
     "This variable is used to control the addition and deletion 
      of individual values of the mscFrDteRgLtDlciTable."
::= { mscFrDteRgLtDlciEntry 2 }


-- 
-- FrDte/n Rg/n Bridged Frame Routing
-- 
-- The BridgedFrameRouting component defines the parameters for 
-- implementing the Bridged Frame Routing port.

mscFrDteRgBfr OBJECT IDENTIFIER ::= { mscFrDteRg 15 }



mscFrDteRgBfrRowStatusTable OBJECT-TYPE
   SYNTAX     SEQUENCE OF MscFrDteRgBfrRowStatusEntry
   ACCESS     not-accessible
   STATUS     mandatory
   DESCRIPTION
     "This entry controls the addition and deletion of 
      mscFrDteRgBfr components."
::= { mscFrDteRgBfr 1 }

mscFrDteRgBfrRowStatusEntry OBJECT-TYPE
   SYNTAX     MscFrDteRgBfrRowStatusEntry
   ACCESS     not-accessible
   STATUS     mandatory
   DESCRIPTION
     "A single entry in the table represents a single 
      mscFrDteRgBfr component."
   INDEX {
      mscFrDteIndex,
      mscFrDteRgIndex,
      mscFrDteRgBfrIndex }
::= { mscFrDteRgBfrRowStatusTable 1 }

MscFrDteRgBfrRowStatusEntry ::= SEQUENCE {
   mscFrDteRgBfrRowStatus
      RowStatus,
   mscFrDteRgBfrComponentName
      DisplayString,
   mscFrDteRgBfrStorageType
      StorageType,
   mscFrDteRgBfrIndex
      NonReplicated }

mscFrDteRgBfrRowStatus OBJECT-TYPE
   SYNTAX     RowStatus 
   ACCESS     read-write
   STATUS     mandatory
   DESCRIPTION
     "This variable is used as the basis for SNMP naming of
      mscFrDteRgBfr components.
      These components can be added and deleted."
::= { mscFrDteRgBfrRowStatusEntry 1 }

mscFrDteRgBfrComponentName OBJECT-TYPE
   SYNTAX     DisplayString 
   ACCESS     read-only
   STATUS     mandatory
   DESCRIPTION
     "This variable provides the component's string name for
      use with the ASCII Console Interface"
::= { mscFrDteRgBfrRowStatusEntry 2 }

mscFrDteRgBfrStorageType OBJECT-TYPE
   SYNTAX     StorageType 
   ACCESS     read-only
   STATUS     mandatory
   DESCRIPTION
     "This variable represents the storage type value for the
      mscFrDteRgBfr tables."
::= { mscFrDteRgBfrRowStatusEntry 4 }

mscFrDteRgBfrIndex OBJECT-TYPE
   SYNTAX     NonReplicated 
   ACCESS     not-accessible
   STATUS     mandatory
   DESCRIPTION
     "This variable represents the index for the mscFrDteRgBfr tables."
::= { mscFrDteRgBfrRowStatusEntry 10 }

mscFrDteRgBfrProvTable OBJECT-TYPE
   SYNTAX     SEQUENCE OF MscFrDteRgBfrProvEntry
   ACCESS     not-accessible
   STATUS     mandatory
   DESCRIPTION
     "This group contains the provisioning attributes for the Bfr component."
::= { mscFrDteRgBfr 10 }

mscFrDteRgBfrProvEntry OBJECT-TYPE
   SYNTAX     MscFrDteRgBfrProvEntry
   ACCESS     not-accessible
   STATUS     mandatory
   DESCRIPTION
     "An entry in the mscFrDteRgBfrProvTable."
   INDEX {
      mscFrDteIndex,
      mscFrDteRgIndex,
      mscFrDteRgBfrIndex }
::= { mscFrDteRgBfrProvTable 1 }

MscFrDteRgBfrProvEntry ::= SEQUENCE {
   mscFrDteRgBfrMacType
      INTEGER,
   mscFrDteRgBfrBfrIndex
      INTEGER }

mscFrDteRgBfrMacType OBJECT-TYPE
   SYNTAX     INTEGER  {
                 fddi(0),
                 enet(1),
                 tokenRing(2) }
   ACCESS     read-write
   STATUS     mandatory
   DESCRIPTION
     "This attribute specifies the MAC address type of the Bfr component. 
      The value must be chosen based on the media of the traffic source. For 
      traffic originated from FDDI, use fddi; for ethernet, use enet; for token 
      ring, use tokenRing"
   DEFVAL     { enet }
::= { mscFrDteRgBfrProvEntry 1 }

mscFrDteRgBfrBfrIndex OBJECT-TYPE
   SYNTAX     INTEGER (0..511)
   ACCESS     read-write
   STATUS     mandatory
   DESCRIPTION
     "This attribute specifies the value which is used to derive a unique MAC 
      address for the Bfr. The bfrIndex must be unique across all Bfrs on the 
      same Lp."
::= { mscFrDteRgBfrProvEntry 2 }

mscFrDteRgBfrOprTable OBJECT-TYPE
   SYNTAX     SEQUENCE OF MscFrDteRgBfrOprEntry
   ACCESS     not-accessible
   STATUS     mandatory
   DESCRIPTION
     "This group contains the operational attributes for the Bfr component.."
::= { mscFrDteRgBfr 11 }

mscFrDteRgBfrOprEntry OBJECT-TYPE
   SYNTAX     MscFrDteRgBfrOprEntry
   ACCESS     not-accessible
   STATUS     mandatory
   DESCRIPTION
     "An entry in the mscFrDteRgBfrOprTable."
   INDEX {
      mscFrDteIndex,
      mscFrDteRgIndex,
      mscFrDteRgBfrIndex }
::= { mscFrDteRgBfrOprTable 1 }

MscFrDteRgBfrOprEntry ::= SEQUENCE {
   mscFrDteRgBfrMacAddr
      DashedHexString }

mscFrDteRgBfrMacAddr OBJECT-TYPE
   SYNTAX     DashedHexString (SIZE (6))
   ACCESS     read-only
   STATUS     mandatory
   DESCRIPTION
     "This attribute indicates the unique MAC address of the Bfr component. 
      This value is derived by the value of the attribute bfrIndex.
      The value is displayed as cannonical format."
::= { mscFrDteRgBfrOprEntry 1 }


-- FrDte/n DynDlciDefs
-- This component defines the default values that will be used when a Dlci 
-- of creationType dynamic is created.

mscFrDteDynDlciDefs OBJECT IDENTIFIER ::= { mscFrDte 5 }



mscFrDteDynDlciDefsRowStatusTable OBJECT-TYPE
   SYNTAX     SEQUENCE OF MscFrDteDynDlciDefsRowStatusEntry
   ACCESS     not-accessible
   STATUS     mandatory
   DESCRIPTION
     "This entry controls the addition and deletion of 
      mscFrDteDynDlciDefs components."
::= { mscFrDteDynDlciDefs 1 }

mscFrDteDynDlciDefsRowStatusEntry OBJECT-TYPE
   SYNTAX     MscFrDteDynDlciDefsRowStatusEntry
   ACCESS     not-accessible
   STATUS     mandatory
   DESCRIPTION
     "A single entry in the table represents a single 
      mscFrDteDynDlciDefs component."
   INDEX {
      mscFrDteIndex,
      mscFrDteDynDlciDefsIndex }
::= { mscFrDteDynDlciDefsRowStatusTable 1 }

MscFrDteDynDlciDefsRowStatusEntry ::= SEQUENCE {
   mscFrDteDynDlciDefsRowStatus
      RowStatus,
   mscFrDteDynDlciDefsComponentName
      DisplayString,
   mscFrDteDynDlciDefsStorageType
      StorageType,
   mscFrDteDynDlciDefsIndex
      NonReplicated }

mscFrDteDynDlciDefsRowStatus OBJECT-TYPE
   SYNTAX     RowStatus 
   ACCESS     read-only
   STATUS     mandatory
   DESCRIPTION
     "This variable is used as the basis for SNMP naming of
      mscFrDteDynDlciDefs components.
      These components cannot be added nor deleted."
::= { mscFrDteDynDlciDefsRowStatusEntry 1 }

mscFrDteDynDlciDefsComponentName OBJECT-TYPE
   SYNTAX     DisplayString 
   ACCESS     read-only
   STATUS     mandatory
   DESCRIPTION
     "This variable provides the component's string name for
      use with the ASCII Console Interface"
::= { mscFrDteDynDlciDefsRowStatusEntry 2 }

mscFrDteDynDlciDefsStorageType OBJECT-TYPE
   SYNTAX     StorageType 
   ACCESS     read-only
   STATUS     mandatory
   DESCRIPTION
     "This variable represents the storage type value for the
      mscFrDteDynDlciDefs tables."
::= { mscFrDteDynDlciDefsRowStatusEntry 4 }

mscFrDteDynDlciDefsIndex OBJECT-TYPE
   SYNTAX     NonReplicated 
   ACCESS     not-accessible
   STATUS     mandatory
   DESCRIPTION
     "This variable represents the index for the mscFrDteDynDlciDefs tables."
::= { mscFrDteDynDlciDefsRowStatusEntry 10 }

mscFrDteDynDlciDefsProvTable OBJECT-TYPE
   SYNTAX     SEQUENCE OF MscFrDteDynDlciDefsProvEntry
   ACCESS     not-accessible
   STATUS     mandatory
   DESCRIPTION
     "This group contains the provisioned attributes for a virtual circuit. These 
      attributes represent the default settings for the resulting Dlci components 
      and can be operationally changed using the corresponding attributes 
      under the Dlci component."
::= { mscFrDteDynDlciDefs 10 }

mscFrDteDynDlciDefsProvEntry OBJECT-TYPE
   SYNTAX     MscFrDteDynDlciDefsProvEntry
   ACCESS     not-accessible
   STATUS     mandatory
   DESCRIPTION
     "An entry in the mscFrDteDynDlciDefsProvTable."
   INDEX {
      mscFrDteIndex,
      mscFrDteDynDlciDefsIndex }
::= { mscFrDteDynDlciDefsProvTable 1 }

MscFrDteDynDlciDefsProvEntry ::= SEQUENCE {
   mscFrDteDynDlciDefsStdRowStatus
      INTEGER,
   mscFrDteDynDlciDefsRateEnforcement
      INTEGER,
   mscFrDteDynDlciDefsCommittedInformationRate
      Unsigned32,
   mscFrDteDynDlciDefsCommittedBurst
      Unsigned32,
   mscFrDteDynDlciDefsExcessBurst
      Unsigned32,
   mscFrDteDynDlciDefsExcessBurstAction
      INTEGER,
   mscFrDteDynDlciDefsIpCos
      Unsigned32 }

mscFrDteDynDlciDefsStdRowStatus OBJECT-TYPE
   SYNTAX     INTEGER  {
                 active(1),
                 notInService(2) }
   ACCESS     read-write
   STATUS     mandatory
   DESCRIPTION
     "This attribute is used to manage the status of a StDlci component.
      
      Set to active to enable the StDlci component.
      Set to notInService to disable the StDlci component.
      Set to createAndGo (SNMP only) to create a new StDlci component.
      Set to destroy (SNMP only) to delete an existing StDlci component."
   DEFVAL     { active }
::= { mscFrDteDynDlciDefsProvEntry 1 }

mscFrDteDynDlciDefsRateEnforcement OBJECT-TYPE
   SYNTAX     INTEGER  {
                 enabled(1),
                 disabled(2) }
   ACCESS     read-write
   STATUS     mandatory
   DESCRIPTION
     "This attribute specifies whether the CIR attributes 
      committedInformationRate, committedBurst, and excessBurst are used to 
      define rate enforcement on this user DLCI.
      
      If rateEnforcement is enabled, and the combined Committed and Excess 
      burst thresholds are exceeded, the frame in violation will be discarded 
      immediately if a HibernationQueue subcomponent is not provisioned 
      under the StDlci component. If a HibernationQueue is provisioned, the 
      frame will be placed on the HibernationQueue at time of violation and 
      transmission will be attempted later after the point at which the burst 
      thresholds will no longer be exceeded.
      
      Setting all the CIR attributes to zero has the same affect as setting this 
      attribute to disabled."
   DEFVAL     { disabled }
::= { mscFrDteDynDlciDefsProvEntry 2 }

mscFrDteDynDlciDefsCommittedInformationRate OBJECT-TYPE
   SYNTAX     Unsigned32 (0..48000000)
   ACCESS     read-write
   STATUS     mandatory
   DESCRIPTION
     "The average number of bits to be transferred per second over the DLCI 
      to the DCE. When this attribute is set to zero, the link speed will be used 
      instead."
   DEFVAL     { 64000 }
::= { mscFrDteDynDlciDefsProvEntry 3 }

mscFrDteDynDlciDefsCommittedBurst OBJECT-TYPE
   SYNTAX     Unsigned32 (0..2048000)
   ACCESS     read-write
   STATUS     mandatory
   DESCRIPTION
     "The committed burst size (in bits) to which the DLCI wants to 
      subscribe."
   DEFVAL     { 64000 }
::= { mscFrDteDynDlciDefsProvEntry 4 }

mscFrDteDynDlciDefsExcessBurst OBJECT-TYPE
   SYNTAX     Unsigned32 (0..2048000)
   ACCESS     read-write
   STATUS     mandatory
   DESCRIPTION
     "The excess burst size (in bits) to which the DLCI wants to subscribe."
   DEFVAL     { 0 }
::= { mscFrDteDynDlciDefsProvEntry 5 }

mscFrDteDynDlciDefsExcessBurstAction OBJECT-TYPE
   SYNTAX     INTEGER  {
                 none(1),
                 setDeBit(2) }
   ACCESS     read-write
   STATUS     mandatory
   DESCRIPTION
     "This attribute specifies the action taken when the committedBurst size 
      has been exceeded on the DLCI but the excessBurst size has not. If the 
      attribute is set to setDeBit, the Discard Eligibility bit in the Frame Relay 
      header will be turned on. If the attribute is set to none, no action will be 
      taken."
   DEFVAL     { none }
::= { mscFrDteDynDlciDefsProvEntry 6 }

mscFrDteDynDlciDefsIpCos OBJECT-TYPE
   SYNTAX     Unsigned32 (0..3)
   ACCESS     read-write
   STATUS     mandatory
   DESCRIPTION
     "This attribute specifies the initial Class of Service (CoS) given to each 
      packet received on the virtual circuit identified by the DLCI. The CoS 
      value n is used to select Vr/<string> QosP/n. which determines the 
      QualityofService-Profile to be used when the packet is forwarded.
      
      The initial CoS given to a packet by the assignedQoS attribute may be 
      overridden when the cosPolicyAssignment attribute is defined on the 
      IpPort or Ip components. 
      
      When a packet is to be transmitted on a frDte protocol port where 
      multiple virtual circuits are available for the packet's next hop, the 
      packet is forwarded using the dlci where the ipCos value matches the 
      CoS of the packet. When the packets's CoS does not match the ipCos 
      value of any of the available virtual circuits, the packet will be 
      forwarded using next lowest CoS; failing this, the packet will be 
      forwarded using the next highest CoS."
   DEFVAL     { 0 }
::= { mscFrDteDynDlciDefsProvEntry 7 }


-- FrDte/n StDlci/n
-- This component is used to provision a static virtual circuit on the Frame 
-- Relay DTE interface. For each StDlci provisioned, there will be a 
-- matching Dlci component. Dlci components of creationType dynamic 
-- will be converted to static without disruption of service when a StDlci 
-- component is provisioned with the same instance number.

mscFrDteStDlci OBJECT IDENTIFIER ::= { mscFrDte 6 }



mscFrDteStDlciRowStatusTable OBJECT-TYPE
   SYNTAX     SEQUENCE OF MscFrDteStDlciRowStatusEntry
   ACCESS     not-accessible
   STATUS     mandatory
   DESCRIPTION
     "This entry controls the addition and deletion of 
      mscFrDteStDlci components."
::= { mscFrDteStDlci 1 }

mscFrDteStDlciRowStatusEntry OBJECT-TYPE
   SYNTAX     MscFrDteStDlciRowStatusEntry
   ACCESS     not-accessible
   STATUS     mandatory
   DESCRIPTION
     "A single entry in the table represents a single 
      mscFrDteStDlci component."
   INDEX {
      mscFrDteIndex,
      mscFrDteStDlciIndex }
::= { mscFrDteStDlciRowStatusTable 1 }

MscFrDteStDlciRowStatusEntry ::= SEQUENCE {
   mscFrDteStDlciRowStatus
      RowStatus,
   mscFrDteStDlciComponentName
      DisplayString,
   mscFrDteStDlciStorageType
      StorageType,
   mscFrDteStDlciIndex
      Integer32 }

mscFrDteStDlciRowStatus OBJECT-TYPE
   SYNTAX     RowStatus 
   ACCESS     read-write
   STATUS     mandatory
   DESCRIPTION
     "This variable is used as the basis for SNMP naming of
      mscFrDteStDlci components.
      These components can be added and deleted."
::= { mscFrDteStDlciRowStatusEntry 1 }

mscFrDteStDlciComponentName OBJECT-TYPE
   SYNTAX     DisplayString 
   ACCESS     read-only
   STATUS     mandatory
   DESCRIPTION
     "This variable provides the component's string name for
      use with the ASCII Console Interface"
::= { mscFrDteStDlciRowStatusEntry 2 }

mscFrDteStDlciStorageType OBJECT-TYPE
   SYNTAX     StorageType 
   ACCESS     read-only
   STATUS     mandatory
   DESCRIPTION
     "This variable represents the storage type value for the
      mscFrDteStDlci tables."
::= { mscFrDteStDlciRowStatusEntry 4 }

mscFrDteStDlciIndex OBJECT-TYPE
   SYNTAX     Integer32 (16..1007)
   ACCESS     not-accessible
   STATUS     mandatory
   DESCRIPTION
     "This variable represents the index for the mscFrDteStDlci tables."
::= { mscFrDteStDlciRowStatusEntry 10 }

mscFrDteStDlciProvTable OBJECT-TYPE
   SYNTAX     SEQUENCE OF MscFrDteStDlciProvEntry
   ACCESS     not-accessible
   STATUS     mandatory
   DESCRIPTION
     "This group contains the provisioned attributes for a virtual circuit. These 
      attributes represent the default settings for the resulting Dlci components 
      and can be operationally changed using the corresponding attributes 
      under the Dlci component."
::= { mscFrDteStDlci 10 }

mscFrDteStDlciProvEntry OBJECT-TYPE
   SYNTAX     MscFrDteStDlciProvEntry
   ACCESS     not-accessible
   STATUS     mandatory
   DESCRIPTION
     "An entry in the mscFrDteStDlciProvTable."
   INDEX {
      mscFrDteIndex,
      mscFrDteStDlciIndex }
::= { mscFrDteStDlciProvTable 1 }

MscFrDteStDlciProvEntry ::= SEQUENCE {
   mscFrDteStDlciStdRowStatus
      INTEGER,
   mscFrDteStDlciRateEnforcement
      INTEGER,
   mscFrDteStDlciCommittedInformationRate
      Unsigned32,
   mscFrDteStDlciCommittedBurst
      Unsigned32,
   mscFrDteStDlciExcessBurst
      Unsigned32,
   mscFrDteStDlciExcessBurstAction
      INTEGER,
   mscFrDteStDlciIpCos
      Unsigned32 }

mscFrDteStDlciStdRowStatus OBJECT-TYPE
   SYNTAX     INTEGER  {
                 active(1),
                 notInService(2) }
   ACCESS     read-write
   STATUS     mandatory
   DESCRIPTION
     "This attribute is used to manage the status of a StDlci component.
      
      Set to active to enable the StDlci component.
      Set to notInService to disable the StDlci component.
      Set to createAndGo (SNMP only) to create a new StDlci component.
      Set to destroy (SNMP only) to delete an existing StDlci component."
   DEFVAL     { active }
::= { mscFrDteStDlciProvEntry 1 }

mscFrDteStDlciRateEnforcement OBJECT-TYPE
   SYNTAX     INTEGER  {
                 enabled(1),
                 disabled(2) }
   ACCESS     read-write
   STATUS     mandatory
   DESCRIPTION
     "This attribute specifies whether the CIR attributes 
      committedInformationRate, committedBurst, and excessBurst are used to 
      define rate enforcement on this user DLCI.
      
      If rateEnforcement is enabled, and the combined Committed and Excess 
      burst thresholds are exceeded, the frame in violation will be discarded 
      immediately if a HibernationQueue subcomponent is not provisioned 
      under the StDlci component. If a HibernationQueue is provisioned, the 
      frame will be placed on the HibernationQueue at time of violation and 
      transmission will be attempted later after the point at which the burst 
      thresholds will no longer be exceeded.
      
      Setting all the CIR attributes to zero has the same affect as setting this 
      attribute to disabled."
   DEFVAL     { disabled }
::= { mscFrDteStDlciProvEntry 2 }

mscFrDteStDlciCommittedInformationRate OBJECT-TYPE
   SYNTAX     Unsigned32 (0..48000000)
   ACCESS     read-write
   STATUS     mandatory
   DESCRIPTION
     "The average number of bits to be transferred per second over the DLCI 
      to the DCE. When this attribute is set to zero, the link speed will be used 
      instead."
   DEFVAL     { 64000 }
::= { mscFrDteStDlciProvEntry 3 }

mscFrDteStDlciCommittedBurst OBJECT-TYPE
   SYNTAX     Unsigned32 (0..2048000)
   ACCESS     read-write
   STATUS     mandatory
   DESCRIPTION
     "The committed burst size (in bits) to which the DLCI wants to 
      subscribe."
   DEFVAL     { 64000 }
::= { mscFrDteStDlciProvEntry 4 }

mscFrDteStDlciExcessBurst OBJECT-TYPE
   SYNTAX     Unsigned32 (0..2048000)
   ACCESS     read-write
   STATUS     mandatory
   DESCRIPTION
     "The excess burst size (in bits) to which the DLCI wants to subscribe."
   DEFVAL     { 0 }
::= { mscFrDteStDlciProvEntry 5 }

mscFrDteStDlciExcessBurstAction OBJECT-TYPE
   SYNTAX     INTEGER  {
                 none(1),
                 setDeBit(2) }
   ACCESS     read-write
   STATUS     mandatory
   DESCRIPTION
     "This attribute specifies the action taken when the committedBurst size 
      has been exceeded on the DLCI but the excessBurst size has not. If the 
      attribute is set to setDeBit, the Discard Eligibility bit in the Frame Relay 
      header will be turned on. If the attribute is set to none, no action will be 
      taken."
   DEFVAL     { none }
::= { mscFrDteStDlciProvEntry 6 }

mscFrDteStDlciIpCos OBJECT-TYPE
   SYNTAX     Unsigned32 (0..3)
   ACCESS     read-write
   STATUS     mandatory
   DESCRIPTION
     "This attribute specifies the initial Class of Service (CoS) given to each 
      packet received on the virtual circuit identified by the DLCI. The CoS 
      value n is used to select Vr/<string> QosP/n. which determines the 
      QualityofService-Profile to be used when the packet is forwarded.
      
      The initial CoS given to a packet by the assignedQoS attribute may be 
      overridden when the cosPolicyAssignment attribute is defined on the 
      IpPort or Ip components. 
      
      When a packet is to be transmitted on a frDte protocol port where 
      multiple virtual circuits are available for the packet's next hop, the 
      packet is forwarded using the dlci where the ipCos value matches the 
      CoS of the packet. When the packets's CoS does not match the ipCos 
      value of any of the available virtual circuits, the packet will be 
      forwarded using next lowest CoS; failing this, the packet will be 
      forwarded using the next highest CoS."
   DEFVAL     { 0 }
::= { mscFrDteStDlciProvEntry 7 }

mscFrDteStDlciRgLinkTable OBJECT-TYPE
   SYNTAX     SEQUENCE OF MscFrDteStDlciRgLinkEntry
   ACCESS     not-accessible
   STATUS     mandatory
   DESCRIPTION
     "This group provides the link between a Dlci and a remoteGroup."
::= { mscFrDteStDlci 11 }

mscFrDteStDlciRgLinkEntry OBJECT-TYPE
   SYNTAX     MscFrDteStDlciRgLinkEntry
   ACCESS     not-accessible
   STATUS     mandatory
   DESCRIPTION
     "An entry in the mscFrDteStDlciRgLinkTable."
   INDEX {
      mscFrDteIndex,
      mscFrDteStDlciIndex }
::= { mscFrDteStDlciRgLinkTable 1 }

MscFrDteStDlciRgLinkEntry ::= SEQUENCE {
   mscFrDteStDlciLinkToRemoteGroup
      Link }

mscFrDteStDlciLinkToRemoteGroup OBJECT-TYPE
   SYNTAX     Link 
   ACCESS     read-write
   STATUS     mandatory
   DESCRIPTION
     "This attribute associates a StDlci component with a Rg component. 
      Provisioned StDlci components must be linked to a Rg component 
      which is under the same FrDte component."
::= { mscFrDteStDlciRgLinkEntry 1 }


-- FrDte/n StDlci/n Hq
-- This component provides a Hibernation Queue capability for a Dlci 
-- component which has been provisioned with CIR enforcement enabled. 
-- The HibernationQueue provides priority placement of frames on the 
-- queue, Time To Live (TTL) discarding of frames from the queue, and 
-- queue statistics.

mscFrDteStDlciHq OBJECT IDENTIFIER ::= { mscFrDteStDlci 2 }



mscFrDteStDlciHqRowStatusTable OBJECT-TYPE
   SYNTAX     SEQUENCE OF MscFrDteStDlciHqRowStatusEntry
   ACCESS     not-accessible
   STATUS     mandatory
   DESCRIPTION
     "This entry controls the addition and deletion of 
      mscFrDteStDlciHq components."
::= { mscFrDteStDlciHq 1 }

mscFrDteStDlciHqRowStatusEntry OBJECT-TYPE
   SYNTAX     MscFrDteStDlciHqRowStatusEntry
   ACCESS     not-accessible
   STATUS     mandatory
   DESCRIPTION
     "A single entry in the table represents a single 
      mscFrDteStDlciHq component."
   INDEX {
      mscFrDteIndex,
      mscFrDteStDlciIndex,
      mscFrDteStDlciHqIndex }
::= { mscFrDteStDlciHqRowStatusTable 1 }

MscFrDteStDlciHqRowStatusEntry ::= SEQUENCE {
   mscFrDteStDlciHqRowStatus
      RowStatus,
   mscFrDteStDlciHqComponentName
      DisplayString,
   mscFrDteStDlciHqStorageType
      StorageType,
   mscFrDteStDlciHqIndex
      NonReplicated }

mscFrDteStDlciHqRowStatus OBJECT-TYPE
   SYNTAX     RowStatus 
   ACCESS     read-write
   STATUS     mandatory
   DESCRIPTION
     "This variable is used as the basis for SNMP naming of
      mscFrDteStDlciHq components.
      These components can be added and deleted."
::= { mscFrDteStDlciHqRowStatusEntry 1 }

mscFrDteStDlciHqComponentName OBJECT-TYPE
   SYNTAX     DisplayString 
   ACCESS     read-only
   STATUS     mandatory
   DESCRIPTION
     "This variable provides the component's string name for
      use with the ASCII Console Interface"
::= { mscFrDteStDlciHqRowStatusEntry 2 }

mscFrDteStDlciHqStorageType OBJECT-TYPE
   SYNTAX     StorageType 
   ACCESS     read-only
   STATUS     mandatory
   DESCRIPTION
     "This variable represents the storage type value for the
      mscFrDteStDlciHq tables."
::= { mscFrDteStDlciHqRowStatusEntry 4 }

mscFrDteStDlciHqIndex OBJECT-TYPE
   SYNTAX     NonReplicated 
   ACCESS     not-accessible
   STATUS     mandatory
   DESCRIPTION
     "This variable represents the index for the mscFrDteStDlciHq tables."
::= { mscFrDteStDlciHqRowStatusEntry 10 }

mscFrDteStDlciHqProvTable OBJECT-TYPE
   SYNTAX     SEQUENCE OF MscFrDteStDlciHqProvEntry
   ACCESS     not-accessible
   STATUS     mandatory
   DESCRIPTION
     "This group contains the Link Emission Queue provisioned attributes."
::= { mscFrDteStDlciHq 10 }

mscFrDteStDlciHqProvEntry OBJECT-TYPE
   SYNTAX     MscFrDteStDlciHqProvEntry
   ACCESS     not-accessible
   STATUS     mandatory
   DESCRIPTION
     "An entry in the mscFrDteStDlciHqProvTable."
   INDEX {
      mscFrDteIndex,
      mscFrDteStDlciIndex,
      mscFrDteStDlciHqIndex }
::= { mscFrDteStDlciHqProvTable 1 }

MscFrDteStDlciHqProvEntry ::= SEQUENCE {
   mscFrDteStDlciHqMaxPackets
      Unsigned32,
   mscFrDteStDlciHqMaxMsecData
      Unsigned32,
   mscFrDteStDlciHqMaxPercentMulticast
      Unsigned32,
   mscFrDteStDlciHqTimeToLive
      Unsigned32 }

mscFrDteStDlciHqMaxPackets OBJECT-TYPE
   SYNTAX     Unsigned32 (0..2048)
   ACCESS     read-write
   STATUS     mandatory
   DESCRIPTION
     "This attribute specifies the maximum number of packets allowed in the 
      Leq before being discarded. If this attribute is set to zero then the 
      maximum number of packets is calculated from the transmit data rate. 
      This calculated value is placed in queuePktThreshold."
   DEFVAL     { 0 }
::= { mscFrDteStDlciHqProvEntry 1 }

mscFrDteStDlciHqMaxMsecData OBJECT-TYPE
   SYNTAX     Unsigned32 (100..60000)
   ACCESS     read-write
   STATUS     mandatory
   DESCRIPTION
     "This attribute specifies the maximum number of 'Milliseconds worth of 
      data' allowed in the Leq before packets are discarded. The 
      queueByteThreshold will be calculated from this attribute, based on the 
      transmit data rate."
   DEFVAL     { 10000 }
::= { mscFrDteStDlciHqProvEntry 2 }

mscFrDteStDlciHqMaxPercentMulticast OBJECT-TYPE
   SYNTAX     Unsigned32 (1..100)
   ACCESS     read-write
   STATUS     mandatory
   DESCRIPTION
     "This attribute specifies the maximum percentage of multicast packets 
      allowed in the Leq, based on queuePktThreshold, before being 
      discarded. The calculated value will be placed in 
      queueMulticastThreshold."
   DEFVAL     { 50 }
::= { mscFrDteStDlciHqProvEntry 3 }

mscFrDteStDlciHqTimeToLive OBJECT-TYPE
   SYNTAX     Unsigned32 (100..60000)
   ACCESS     read-write
   STATUS     mandatory
   DESCRIPTION
     "This attribute specifies the 'Milliseconds Time To Live' of packets in 
      the Leq. If the timeToLive of a packet expires, it will be discarded."
   DEFVAL     { 10000 }
::= { mscFrDteStDlciHqProvEntry 4 }

mscFrDteStDlciHqStatsTable OBJECT-TYPE
   SYNTAX     SEQUENCE OF MscFrDteStDlciHqStatsEntry
   ACCESS     not-accessible
   STATUS     mandatory
   DESCRIPTION
     "This group contains HibernationQueue general statistics."
::= { mscFrDteStDlciHq 11 }

mscFrDteStDlciHqStatsEntry OBJECT-TYPE
   SYNTAX     MscFrDteStDlciHqStatsEntry
   ACCESS     not-accessible
   STATUS     mandatory
   DESCRIPTION
     "An entry in the mscFrDteStDlciHqStatsTable."
   INDEX {
      mscFrDteIndex,
      mscFrDteStDlciIndex,
      mscFrDteStDlciHqIndex }
::= { mscFrDteStDlciHqStatsTable 1 }

MscFrDteStDlciHqStatsEntry ::= SEQUENCE {
   mscFrDteStDlciHqTimedOutPkt
      Counter32,
   mscFrDteStDlciHqQueuePurgeDiscards
      Counter32 }

mscFrDteStDlciHqTimedOutPkt OBJECT-TYPE
   SYNTAX     Counter32 
   ACCESS     read-only
   STATUS     mandatory
   DESCRIPTION
     "This attribute counts the number of packets that have been discarded due 
      to exceeding the timeToLive. This counter will wrap around to 0 when it 
      exceeds its maximum count."
::= { mscFrDteStDlciHqStatsEntry 1 }

mscFrDteStDlciHqQueuePurgeDiscards OBJECT-TYPE
   SYNTAX     Counter32 
   ACCESS     read-only
   STATUS     mandatory
   DESCRIPTION
     "This attribute counts the total number of packets discarded by a queue 
      purge which occurs when the Dlci goes down. This counter will wrap 
      around to 0 when it exceeds its maximum count."
::= { mscFrDteStDlciHqStatsEntry 2 }

mscFrDteStDlciHqTStatsTable OBJECT-TYPE
   SYNTAX     SEQUENCE OF MscFrDteStDlciHqTStatsEntry
   ACCESS     not-accessible
   STATUS     mandatory
   DESCRIPTION
     "This group contains Link Emission Queue total statistics."
::= { mscFrDteStDlciHq 12 }

mscFrDteStDlciHqTStatsEntry OBJECT-TYPE
   SYNTAX     MscFrDteStDlciHqTStatsEntry
   ACCESS     not-accessible
   STATUS     mandatory
   DESCRIPTION
     "An entry in the mscFrDteStDlciHqTStatsTable."
   INDEX {
      mscFrDteIndex,
      mscFrDteStDlciIndex,
      mscFrDteStDlciHqIndex }
::= { mscFrDteStDlciHqTStatsTable 1 }

MscFrDteStDlciHqTStatsEntry ::= SEQUENCE {
   mscFrDteStDlciHqTotalPktHandled
      Counter32,
   mscFrDteStDlciHqTotalPktForwarded
      Counter32,
   mscFrDteStDlciHqTotalPktQueued
      Counter32,
   mscFrDteStDlciHqTotalMulticastPkt
      Counter32,
   mscFrDteStDlciHqTotalPktDiscards
      Counter32 }

mscFrDteStDlciHqTotalPktHandled OBJECT-TYPE
   SYNTAX     Counter32 
   ACCESS     read-only
   STATUS     mandatory
   DESCRIPTION
     "This attribute counts the total number of packets handled by the Leq. 
      This counter will wrap around to 0 when it exceeds its maximum count."
::= { mscFrDteStDlciHqTStatsEntry 1 }

mscFrDteStDlciHqTotalPktForwarded OBJECT-TYPE
   SYNTAX     Counter32 
   ACCESS     read-only
   STATUS     mandatory
   DESCRIPTION
     "This attribute counts the total number of packets forwarded by the Leq. 
      This counter will wrap around to 0 when it exceeds its maximum count."
::= { mscFrDteStDlciHqTStatsEntry 2 }

mscFrDteStDlciHqTotalPktQueued OBJECT-TYPE
   SYNTAX     Counter32 
   ACCESS     read-only
   STATUS     mandatory
   DESCRIPTION
     "This attribute counts the total number of packets that required queuing 
      by the Leq due to transmit congestion. This counter will wrap around to 
      0 when it exceeds its maximum count."
::= { mscFrDteStDlciHqTStatsEntry 3 }

mscFrDteStDlciHqTotalMulticastPkt OBJECT-TYPE
   SYNTAX     Counter32 
   ACCESS     read-only
   STATUS     mandatory
   DESCRIPTION
     "This attribute counts the total number of multicast packets handled by 
      this instance of FrDte. This counter will wrap around to 0 when it 
      exceeds its maximum count."
::= { mscFrDteStDlciHqTStatsEntry 4 }

mscFrDteStDlciHqTotalPktDiscards OBJECT-TYPE
   SYNTAX     Counter32 
   ACCESS     read-only
   STATUS     mandatory
   DESCRIPTION
     "This attribute counts the total number of packets that were discarded for 
      this instance of FrDte. This is the sum of timedOutPkt, 
      forcedPktDiscards, queuePurgeDiscards, pktThresholdExceeded, 
      byteThresholdExceeded, mulThresholdExceeded and 
      memThresholdExceeded. This counter will wrap around to 0 when it 
      exceeds its maximum count."
::= { mscFrDteStDlciHqTStatsEntry 5 }

mscFrDteStDlciHqCStatsTable OBJECT-TYPE
   SYNTAX     SEQUENCE OF MscFrDteStDlciHqCStatsEntry
   ACCESS     not-accessible
   STATUS     mandatory
   DESCRIPTION
     "This group contains Link Emission Queue current statistics."
::= { mscFrDteStDlciHq 13 }

mscFrDteStDlciHqCStatsEntry OBJECT-TYPE
   SYNTAX     MscFrDteStDlciHqCStatsEntry
   ACCESS     not-accessible
   STATUS     mandatory
   DESCRIPTION
     "An entry in the mscFrDteStDlciHqCStatsTable."
   INDEX {
      mscFrDteIndex,
      mscFrDteStDlciIndex,
      mscFrDteStDlciHqIndex }
::= { mscFrDteStDlciHqCStatsTable 1 }

MscFrDteStDlciHqCStatsEntry ::= SEQUENCE {
   mscFrDteStDlciHqCurrentPktQueued
      Gauge32,
   mscFrDteStDlciHqCurrentBytesQueued
      Gauge32,
   mscFrDteStDlciHqCurrentMulticastQueued
      Gauge32 }

mscFrDteStDlciHqCurrentPktQueued OBJECT-TYPE
   SYNTAX     Gauge32 (0..4294967295)
   ACCESS     read-only
   STATUS     mandatory
   DESCRIPTION
     "This attribute contains the current number of packets queued."
   DEFVAL     { 0 }
::= { mscFrDteStDlciHqCStatsEntry 1 }

mscFrDteStDlciHqCurrentBytesQueued OBJECT-TYPE
   SYNTAX     Gauge32 (0..4294967295)
   ACCESS     read-only
   STATUS     mandatory
   DESCRIPTION
     "This attribute contains the current number of bytes queued."
   DEFVAL     { 0 }
::= { mscFrDteStDlciHqCStatsEntry 2 }

mscFrDteStDlciHqCurrentMulticastQueued OBJECT-TYPE
   SYNTAX     Gauge32 (0..4294967295)
   ACCESS     read-only
   STATUS     mandatory
   DESCRIPTION
     "This attribute counts the current number of multicast packets in the 
      queue."
   DEFVAL     { 0 }
::= { mscFrDteStDlciHqCStatsEntry 3 }

mscFrDteStDlciHqThrStatsTable OBJECT-TYPE
   SYNTAX     SEQUENCE OF MscFrDteStDlciHqThrStatsEntry
   ACCESS     not-accessible
   STATUS     mandatory
   DESCRIPTION
     "This group contains Link Emission Queue threshold statistics."
::= { mscFrDteStDlciHq 14 }

mscFrDteStDlciHqThrStatsEntry OBJECT-TYPE
   SYNTAX     MscFrDteStDlciHqThrStatsEntry
   ACCESS     not-accessible
   STATUS     mandatory
   DESCRIPTION
     "An entry in the mscFrDteStDlciHqThrStatsTable."
   INDEX {
      mscFrDteIndex,
      mscFrDteStDlciIndex,
      mscFrDteStDlciHqIndex }
::= { mscFrDteStDlciHqThrStatsTable 1 }

MscFrDteStDlciHqThrStatsEntry ::= SEQUENCE {
   mscFrDteStDlciHqQueuePktThreshold
      Unsigned32,
   mscFrDteStDlciHqPktThresholdExceeded
      Counter32,
   mscFrDteStDlciHqQueueByteThreshold
      Unsigned32,
   mscFrDteStDlciHqByteThresholdExceeded
      Counter32,
   mscFrDteStDlciHqQueueMulticastThreshold
      Unsigned32,
   mscFrDteStDlciHqMulThresholdExceeded
      Counter32,
   mscFrDteStDlciHqMemThresholdExceeded
      Counter32 }

mscFrDteStDlciHqQueuePktThreshold OBJECT-TYPE
   SYNTAX     Unsigned32 (0..4294967295)
   ACCESS     read-only
   STATUS     mandatory
   DESCRIPTION
     "This attribute is the maximum number of packets that can be contained 
      in the queue before being discarded. If maxPackets was set to 0 then this 
      attribute will contain the value that has been calculated based on the 
      transmit data rate. If maxPackets was set to one or more than this 
      attribute will contain that number."
   DEFVAL     { 0 }
::= { mscFrDteStDlciHqThrStatsEntry 1 }

mscFrDteStDlciHqPktThresholdExceeded OBJECT-TYPE
   SYNTAX     Counter32 
   ACCESS     read-only
   STATUS     mandatory
   DESCRIPTION
     "This attribute counts the number of packets discarded due to the 
      queuePktThreshold being exceeded. This counter will wrap around to 0 
      when it exceeds its maximum count."
::= { mscFrDteStDlciHqThrStatsEntry 2 }

mscFrDteStDlciHqQueueByteThreshold OBJECT-TYPE
   SYNTAX     Unsigned32 (0..4294967295)
   ACCESS     read-only
   STATUS     mandatory
   DESCRIPTION
     "This attribute is the maximum number of bytes allowed in the queue 
      based on maxMsecData and the transmit data rate."
   DEFVAL     { 0 }
::= { mscFrDteStDlciHqThrStatsEntry 3 }

mscFrDteStDlciHqByteThresholdExceeded OBJECT-TYPE
   SYNTAX     Counter32 
   ACCESS     read-only
   STATUS     mandatory
   DESCRIPTION
     "This attribute counts the number of packets discarded due to the 
      queueByteThreshold being exceeded. This counter will wrap around to 0 
      when it exceeds its maximum count."
::= { mscFrDteStDlciHqThrStatsEntry 4 }

mscFrDteStDlciHqQueueMulticastThreshold OBJECT-TYPE
   SYNTAX     Unsigned32 (0..4294967295)
   ACCESS     read-only
   STATUS     mandatory
   DESCRIPTION
     "This attribute is the number of multicast packets allowed in the queue 
      based on maxPercentMulticast and maxPackets."
   DEFVAL     { 0 }
::= { mscFrDteStDlciHqThrStatsEntry 5 }

mscFrDteStDlciHqMulThresholdExceeded OBJECT-TYPE
   SYNTAX     Counter32 
   ACCESS     read-only
   STATUS     mandatory
   DESCRIPTION
     "This attribute counts the number of packets discarded due to the 
      queueMulticastThreshold being exceeded. This counter will wrap 
      around to 0 when it exceeds its maximum count."
::= { mscFrDteStDlciHqThrStatsEntry 6 }

mscFrDteStDlciHqMemThresholdExceeded OBJECT-TYPE
   SYNTAX     Counter32 
   ACCESS     read-only
   STATUS     mandatory
   DESCRIPTION
     "This attribute counts the number of packets discarded due to exceeding 
      the memory usage threshold for Leq. The memory usage threshold is 
      determined by the Leq software, guaranteeing that the Leq does not 
      consume all of the memory. This counter will wrap around to 0 when it 
      exceeds its maximum count."
::= { mscFrDteStDlciHqThrStatsEntry 7 }


-- FrDte/n Leq 
-- This component provides a means of statistics gathering and packet 
-- discard.

mscFrDteLeq OBJECT IDENTIFIER ::= { mscFrDte 7 }



mscFrDteLeqRowStatusTable OBJECT-TYPE
   SYNTAX     SEQUENCE OF MscFrDteLeqRowStatusEntry
   ACCESS     not-accessible
   STATUS     mandatory
   DESCRIPTION
     "This entry controls the addition and deletion of 
      mscFrDteLeq components."
::= { mscFrDteLeq 1 }

mscFrDteLeqRowStatusEntry OBJECT-TYPE
   SYNTAX     MscFrDteLeqRowStatusEntry
   ACCESS     not-accessible
   STATUS     mandatory
   DESCRIPTION
     "A single entry in the table represents a single 
      mscFrDteLeq component."
   INDEX {
      mscFrDteIndex,
      mscFrDteLeqIndex }
::= { mscFrDteLeqRowStatusTable 1 }

MscFrDteLeqRowStatusEntry ::= SEQUENCE {
   mscFrDteLeqRowStatus
      RowStatus,
   mscFrDteLeqComponentName
      DisplayString,
   mscFrDteLeqStorageType
      StorageType,
   mscFrDteLeqIndex
      NonReplicated }

mscFrDteLeqRowStatus OBJECT-TYPE
   SYNTAX     RowStatus 
   ACCESS     read-write
   STATUS     mandatory
   DESCRIPTION
     "This variable is used as the basis for SNMP naming of
      mscFrDteLeq components.
      These components can be added and deleted."
::= { mscFrDteLeqRowStatusEntry 1 }

mscFrDteLeqComponentName OBJECT-TYPE
   SYNTAX     DisplayString 
   ACCESS     read-only
   STATUS     mandatory
   DESCRIPTION
     "This variable provides the component's string name for
      use with the ASCII Console Interface"
::= { mscFrDteLeqRowStatusEntry 2 }

mscFrDteLeqStorageType OBJECT-TYPE
   SYNTAX     StorageType 
   ACCESS     read-only
   STATUS     mandatory
   DESCRIPTION
     "This variable represents the storage type value for the
      mscFrDteLeq tables."
::= { mscFrDteLeqRowStatusEntry 4 }

mscFrDteLeqIndex OBJECT-TYPE
   SYNTAX     NonReplicated 
   ACCESS     not-accessible
   STATUS     mandatory
   DESCRIPTION
     "This variable represents the index for the mscFrDteLeq tables."
::= { mscFrDteLeqRowStatusEntry 10 }

mscFrDteLeqProvTable OBJECT-TYPE
   SYNTAX     SEQUENCE OF MscFrDteLeqProvEntry
   ACCESS     not-accessible
   STATUS     mandatory
   DESCRIPTION
     "This group contains the Link Emission Queue provisioned attributes."
::= { mscFrDteLeq 10 }

mscFrDteLeqProvEntry OBJECT-TYPE
   SYNTAX     MscFrDteLeqProvEntry
   ACCESS     not-accessible
   STATUS     mandatory
   DESCRIPTION
     "An entry in the mscFrDteLeqProvTable."
   INDEX {
      mscFrDteIndex,
      mscFrDteLeqIndex }
::= { mscFrDteLeqProvTable 1 }

MscFrDteLeqProvEntry ::= SEQUENCE {
   mscFrDteLeqMaxPackets
      Unsigned32,
   mscFrDteLeqMaxMsecData
      Unsigned32,
   mscFrDteLeqMaxPercentMulticast
      Unsigned32,
   mscFrDteLeqTimeToLive
      Unsigned32 }

mscFrDteLeqMaxPackets OBJECT-TYPE
   SYNTAX     Unsigned32 (0..2048)
   ACCESS     read-write
   STATUS     mandatory
   DESCRIPTION
     "This attribute specifies the maximum number of packets allowed in the 
      Leq before being discarded. If this attribute is set to zero then the 
      maximum number of packets is calculated from the transmit data rate. 
      This calculated value is placed in queuePktThreshold."
   DEFVAL     { 0 }
::= { mscFrDteLeqProvEntry 1 }

mscFrDteLeqMaxMsecData OBJECT-TYPE
   SYNTAX     Unsigned32 (100..60000)
   ACCESS     read-write
   STATUS     mandatory
   DESCRIPTION
     "This attribute specifies the maximum number of 'Milliseconds worth of 
      data' allowed in the Leq before packets are discarded. The 
      queueByteThreshold will be calculated from this attribute, based on the 
      transmit data rate."
   DEFVAL     { 10000 }
::= { mscFrDteLeqProvEntry 2 }

mscFrDteLeqMaxPercentMulticast OBJECT-TYPE
   SYNTAX     Unsigned32 (1..100)
   ACCESS     read-write
   STATUS     mandatory
   DESCRIPTION
     "This attribute specifies the maximum percentage of multicast packets 
      allowed in the Leq, based on queuePktThreshold, before being 
      discarded. The calculated value will be placed in 
      queueMulticastThreshold."
   DEFVAL     { 50 }
::= { mscFrDteLeqProvEntry 3 }

mscFrDteLeqTimeToLive OBJECT-TYPE
   SYNTAX     Unsigned32 (100..60000)
   ACCESS     read-write
   STATUS     mandatory
   DESCRIPTION
     "This attribute specifies the 'Milliseconds Time To Live' of packets in 
      the Leq. If the timeToLive of a packet expires, it will be discarded."
   DEFVAL     { 10000 }
::= { mscFrDteLeqProvEntry 4 }

mscFrDteLeqStatsTable OBJECT-TYPE
   SYNTAX     SEQUENCE OF MscFrDteLeqStatsEntry
   ACCESS     not-accessible
   STATUS     mandatory
   DESCRIPTION
     "This group contains Link Emission Queue general statistics."
::= { mscFrDteLeq 11 }

mscFrDteLeqStatsEntry OBJECT-TYPE
   SYNTAX     MscFrDteLeqStatsEntry
   ACCESS     not-accessible
   STATUS     mandatory
   DESCRIPTION
     "An entry in the mscFrDteLeqStatsTable."
   INDEX {
      mscFrDteIndex,
      mscFrDteLeqIndex }
::= { mscFrDteLeqStatsTable 1 }

MscFrDteLeqStatsEntry ::= SEQUENCE {
   mscFrDteLeqTimedOutPkt
      Counter32,
   mscFrDteLeqHardwareForcedPkt
      Counter32,
   mscFrDteLeqForcedPktDiscards
      Counter32,
   mscFrDteLeqQueuePurgeDiscards
      Counter32 }

mscFrDteLeqTimedOutPkt OBJECT-TYPE
   SYNTAX     Counter32 
   ACCESS     read-only
   STATUS     mandatory
   DESCRIPTION
     "This attribute counts the number of packets that have been discarded due 
      to exceeding the timeToLive. This counter will wrap around to 0 when it 
      exceeds its maximum count."
::= { mscFrDteLeqStatsEntry 1 }

mscFrDteLeqHardwareForcedPkt OBJECT-TYPE
   SYNTAX     Counter32 
   ACCESS     read-only
   STATUS     mandatory
   DESCRIPTION
     "This attribute counts the number of hardware forced packets on this 
      instance of FrDte. This counter will wrap around to 0 when it exceeds 
      its maximum count."
::= { mscFrDteLeqStatsEntry 2 }

mscFrDteLeqForcedPktDiscards OBJECT-TYPE
   SYNTAX     Counter32 
   ACCESS     read-only
   STATUS     mandatory
   DESCRIPTION
     "This attribute counts the total number of hardware forced packets that 
      had to be discarded due to link failure. This counter will wrap around to 
      0 when it exceeds its maximum count."
::= { mscFrDteLeqStatsEntry 3 }

mscFrDteLeqQueuePurgeDiscards OBJECT-TYPE
   SYNTAX     Counter32 
   ACCESS     read-only
   STATUS     mandatory
   DESCRIPTION
     "This attribute counts the total number of packets discarded by a queue 
      purge (i.e. a discarding of all packets on the queue). This counter will 
      wrap around to 0 when it exceeds its maximum count."
::= { mscFrDteLeqStatsEntry 4 }

mscFrDteLeqTStatsTable OBJECT-TYPE
   SYNTAX     SEQUENCE OF MscFrDteLeqTStatsEntry
   ACCESS     not-accessible
   STATUS     mandatory
   DESCRIPTION
     "This group contains Link Emission Queue total statistics."
::= { mscFrDteLeq 12 }

mscFrDteLeqTStatsEntry OBJECT-TYPE
   SYNTAX     MscFrDteLeqTStatsEntry
   ACCESS     not-accessible
   STATUS     mandatory
   DESCRIPTION
     "An entry in the mscFrDteLeqTStatsTable."
   INDEX {
      mscFrDteIndex,
      mscFrDteLeqIndex }
::= { mscFrDteLeqTStatsTable 1 }

MscFrDteLeqTStatsEntry ::= SEQUENCE {
   mscFrDteLeqTotalPktHandled
      Counter32,
   mscFrDteLeqTotalPktForwarded
      Counter32,
   mscFrDteLeqTotalPktQueued
      Counter32,
   mscFrDteLeqTotalMulticastPkt
      Counter32,
   mscFrDteLeqTotalPktDiscards
      Counter32 }

mscFrDteLeqTotalPktHandled OBJECT-TYPE
   SYNTAX     Counter32 
   ACCESS     read-only
   STATUS     mandatory
   DESCRIPTION
     "This attribute counts the total number of packets handled by the Leq. 
      This counter will wrap around to 0 when it exceeds its maximum count."
::= { mscFrDteLeqTStatsEntry 1 }

mscFrDteLeqTotalPktForwarded OBJECT-TYPE
   SYNTAX     Counter32 
   ACCESS     read-only
   STATUS     mandatory
   DESCRIPTION
     "This attribute counts the total number of packets forwarded by the Leq. 
      This counter will wrap around to 0 when it exceeds its maximum count."
::= { mscFrDteLeqTStatsEntry 2 }

mscFrDteLeqTotalPktQueued OBJECT-TYPE
   SYNTAX     Counter32 
   ACCESS     read-only
   STATUS     mandatory
   DESCRIPTION
     "This attribute counts the total number of packets that required queuing 
      by the Leq due to transmit congestion. This counter will wrap around to 
      0 when it exceeds its maximum count."
::= { mscFrDteLeqTStatsEntry 3 }

mscFrDteLeqTotalMulticastPkt OBJECT-TYPE
   SYNTAX     Counter32 
   ACCESS     read-only
   STATUS     mandatory
   DESCRIPTION
     "This attribute counts the total number of multicast packets handled by 
      this instance of FrDte. This counter will wrap around to 0 when it 
      exceeds its maximum count."
::= { mscFrDteLeqTStatsEntry 4 }

mscFrDteLeqTotalPktDiscards OBJECT-TYPE
   SYNTAX     Counter32 
   ACCESS     read-only
   STATUS     mandatory
   DESCRIPTION
     "This attribute counts the total number of packets that were discarded for 
      this instance of FrDte. This is the sum of timedOutPkt, 
      forcedPktDiscards, queuePurgeDiscards, pktThresholdExceeded, 
      byteThresholdExceeded, mulThresholdExceeded and 
      memThresholdExceeded. This counter will wrap around to 0 when it 
      exceeds its maximum count."
::= { mscFrDteLeqTStatsEntry 5 }

mscFrDteLeqCStatsTable OBJECT-TYPE
   SYNTAX     SEQUENCE OF MscFrDteLeqCStatsEntry
   ACCESS     not-accessible
   STATUS     mandatory
   DESCRIPTION
     "This group contains Link Emission Queue current statistics."
::= { mscFrDteLeq 13 }

mscFrDteLeqCStatsEntry OBJECT-TYPE
   SYNTAX     MscFrDteLeqCStatsEntry
   ACCESS     not-accessible
   STATUS     mandatory
   DESCRIPTION
     "An entry in the mscFrDteLeqCStatsTable."
   INDEX {
      mscFrDteIndex,
      mscFrDteLeqIndex }
::= { mscFrDteLeqCStatsTable 1 }

MscFrDteLeqCStatsEntry ::= SEQUENCE {
   mscFrDteLeqCurrentPktQueued
      Gauge32,
   mscFrDteLeqCurrentBytesQueued
      Gauge32,
   mscFrDteLeqCurrentMulticastQueued
      Gauge32 }

mscFrDteLeqCurrentPktQueued OBJECT-TYPE
   SYNTAX     Gauge32 (0..4294967295)
   ACCESS     read-only
   STATUS     mandatory
   DESCRIPTION
     "This attribute contains the current number of packets queued."
   DEFVAL     { 0 }
::= { mscFrDteLeqCStatsEntry 1 }

mscFrDteLeqCurrentBytesQueued OBJECT-TYPE
   SYNTAX     Gauge32 (0..4294967295)
   ACCESS     read-only
   STATUS     mandatory
   DESCRIPTION
     "This attribute contains the current number of bytes queued."
   DEFVAL     { 0 }
::= { mscFrDteLeqCStatsEntry 2 }

mscFrDteLeqCurrentMulticastQueued OBJECT-TYPE
   SYNTAX     Gauge32 (0..4294967295)
   ACCESS     read-only
   STATUS     mandatory
   DESCRIPTION
     "This attribute counts the current number of multicast packets in the 
      queue."
   DEFVAL     { 0 }
::= { mscFrDteLeqCStatsEntry 3 }

mscFrDteLeqThrStatsTable OBJECT-TYPE
   SYNTAX     SEQUENCE OF MscFrDteLeqThrStatsEntry
   ACCESS     not-accessible
   STATUS     mandatory
   DESCRIPTION
     "This group contains Link Emission Queue threshold statistics."
::= { mscFrDteLeq 14 }

mscFrDteLeqThrStatsEntry OBJECT-TYPE
   SYNTAX     MscFrDteLeqThrStatsEntry
   ACCESS     not-accessible
   STATUS     mandatory
   DESCRIPTION
     "An entry in the mscFrDteLeqThrStatsTable."
   INDEX {
      mscFrDteIndex,
      mscFrDteLeqIndex }
::= { mscFrDteLeqThrStatsTable 1 }

MscFrDteLeqThrStatsEntry ::= SEQUENCE {
   mscFrDteLeqQueuePktThreshold
      Unsigned32,
   mscFrDteLeqPktThresholdExceeded
      Counter32,
   mscFrDteLeqQueueByteThreshold
      Unsigned32,
   mscFrDteLeqByteThresholdExceeded
      Counter32,
   mscFrDteLeqQueueMulticastThreshold
      Unsigned32,
   mscFrDteLeqMulThresholdExceeded
      Counter32,
   mscFrDteLeqMemThresholdExceeded
      Counter32 }

mscFrDteLeqQueuePktThreshold OBJECT-TYPE
   SYNTAX     Unsigned32 (0..4294967295)
   ACCESS     read-only
   STATUS     mandatory
   DESCRIPTION
     "This attribute is the maximum number of packets that can be contained 
      in the queue before being discarded. If maxPackets was set to 0 then this 
      attribute will contain the value that has been calculated based on the 
      transmit data rate. If maxPackets was set to one or more than this 
      attribute will contain that number."
   DEFVAL     { 0 }
::= { mscFrDteLeqThrStatsEntry 1 }

mscFrDteLeqPktThresholdExceeded OBJECT-TYPE
   SYNTAX     Counter32 
   ACCESS     read-only
   STATUS     mandatory
   DESCRIPTION
     "This attribute counts the number of packets discarded due to the 
      queuePktThreshold being exceeded. This counter will wrap around to 0 
      when it exceeds its maximum count."
::= { mscFrDteLeqThrStatsEntry 2 }

mscFrDteLeqQueueByteThreshold OBJECT-TYPE
   SYNTAX     Unsigned32 (0..4294967295)
   ACCESS     read-only
   STATUS     mandatory
   DESCRIPTION
     "This attribute is the maximum number of bytes allowed in the queue 
      based on maxMsecData and the transmit data rate."
   DEFVAL     { 0 }
::= { mscFrDteLeqThrStatsEntry 3 }

mscFrDteLeqByteThresholdExceeded OBJECT-TYPE
   SYNTAX     Counter32 
   ACCESS     read-only
   STATUS     mandatory
   DESCRIPTION
     "This attribute counts the number of packets discarded due to the 
      queueByteThreshold being exceeded. This counter will wrap around to 0 
      when it exceeds its maximum count."
::= { mscFrDteLeqThrStatsEntry 4 }

mscFrDteLeqQueueMulticastThreshold OBJECT-TYPE
   SYNTAX     Unsigned32 (0..4294967295)
   ACCESS     read-only
   STATUS     mandatory
   DESCRIPTION
     "This attribute is the number of multicast packets allowed in the queue 
      based on maxPercentMulticast and maxPackets."
   DEFVAL     { 0 }
::= { mscFrDteLeqThrStatsEntry 5 }

mscFrDteLeqMulThresholdExceeded OBJECT-TYPE
   SYNTAX     Counter32 
   ACCESS     read-only
   STATUS     mandatory
   DESCRIPTION
     "This attribute counts the number of packets discarded due to the 
      queueMulticastThreshold being exceeded. This counter will wrap 
      around to 0 when it exceeds its maximum count."
::= { mscFrDteLeqThrStatsEntry 6 }

mscFrDteLeqMemThresholdExceeded OBJECT-TYPE
   SYNTAX     Counter32 
   ACCESS     read-only
   STATUS     mandatory
   DESCRIPTION
     "This attribute counts the number of packets discarded due to exceeding 
      the memory usage threshold for Leq. The memory usage threshold is 
      determined by the Leq software, guaranteeing that the Leq does not 
      consume all of the memory. This counter will wrap around to 0 when it 
      exceeds its maximum count."
::= { mscFrDteLeqThrStatsEntry 7 }

-- 
-- *** THIS SUBTREE CURRENTLY NOT IMPLEMENTED ***
-- 

-- FrDte/n Dlci/n
-- This component provides access to both static and dynamic virtual 
-- circuit instances.

mscFrDteDlci OBJECT IDENTIFIER ::= { mscFrDte 8 }



mscFrDteDlciRowStatusTable OBJECT-TYPE
   SYNTAX     SEQUENCE OF MscFrDteDlciRowStatusEntry
   ACCESS     not-accessible
   STATUS     mandatory
   DESCRIPTION
     "*** THIS TABLE CURRENTLY NOT IMPLEMENTED ***

      This entry controls the addition and deletion of 
      mscFrDteDlci components."
::= { mscFrDteDlci 1 }

mscFrDteDlciRowStatusEntry OBJECT-TYPE
   SYNTAX     MscFrDteDlciRowStatusEntry
   ACCESS     not-accessible
   STATUS     mandatory
   DESCRIPTION
     "A single entry in the table represents a single 
      mscFrDteDlci component."
   INDEX {
      mscFrDteIndex,
      mscFrDteDlciIndex }
::= { mscFrDteDlciRowStatusTable 1 }

MscFrDteDlciRowStatusEntry ::= SEQUENCE {
   mscFrDteDlciRowStatus
      RowStatus,
   mscFrDteDlciComponentName
      DisplayString,
   mscFrDteDlciStorageType
      StorageType,
   mscFrDteDlciIndex
      Integer32 }

mscFrDteDlciRowStatus OBJECT-TYPE
   SYNTAX     RowStatus 
   ACCESS     read-only
   STATUS     mandatory
   DESCRIPTION
     "This variable is used as the basis for SNMP naming of
      mscFrDteDlci components.
      These components cannot be added nor deleted."
::= { mscFrDteDlciRowStatusEntry 1 }

mscFrDteDlciComponentName OBJECT-TYPE
   SYNTAX     DisplayString 
   ACCESS     read-only
   STATUS     mandatory
   DESCRIPTION
     "This variable provides the component's string name for
      use with the ASCII Console Interface"
::= { mscFrDteDlciRowStatusEntry 2 }

mscFrDteDlciStorageType OBJECT-TYPE
   SYNTAX     StorageType 
   ACCESS     read-only
   STATUS     mandatory
   DESCRIPTION
     "This variable represents the storage type value for the
      mscFrDteDlci tables."
::= { mscFrDteDlciRowStatusEntry 4 }

mscFrDteDlciIndex OBJECT-TYPE
   SYNTAX     Integer32 (0..1023)
   ACCESS     not-accessible
   STATUS     mandatory
   DESCRIPTION
     "This variable represents the index for the mscFrDteDlci tables."
::= { mscFrDteDlciRowStatusEntry 10 }

mscFrDteDlciStateTable OBJECT-TYPE
   SYNTAX     SEQUENCE OF MscFrDteDlciStateEntry
   ACCESS     not-accessible
   STATUS     mandatory
   DESCRIPTION
     "*** THIS TABLE CURRENTLY NOT IMPLEMENTED ***

      This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscFrDteDlci 10 }

mscFrDteDlciStateEntry OBJECT-TYPE
   SYNTAX     MscFrDteDlciStateEntry
   ACCESS     not-accessible
   STATUS     mandatory
   DESCRIPTION
     "An entry in the mscFrDteDlciStateTable."
   INDEX {
      mscFrDteIndex,
      mscFrDteDlciIndex }
::= { mscFrDteDlciStateTable 1 }

MscFrDteDlciStateEntry ::= SEQUENCE {
   mscFrDteDlciAdminState
      INTEGER,
   mscFrDteDlciOperationalState
      INTEGER,
   mscFrDteDlciUsageState
      INTEGER }

mscFrDteDlciAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscFrDteDlciStateEntry 1 }

mscFrDteDlciOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscFrDteDlciStateEntry 2 }

mscFrDteDlciUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscFrDteDlciStateEntry 3 }

mscFrDteDlciOperTable OBJECT-TYPE
   SYNTAX     SEQUENCE OF MscFrDteDlciOperEntry
   ACCESS     not-accessible
   STATUS     mandatory
   DESCRIPTION
     "*** THIS TABLE CURRENTLY NOT IMPLEMENTED ***

      This group contains the operational attributes for the Dlci component."
::= { mscFrDteDlci 11 }

mscFrDteDlciOperEntry OBJECT-TYPE
   SYNTAX     MscFrDteDlciOperEntry
   ACCESS     not-accessible
   STATUS     mandatory
   DESCRIPTION
     "An entry in the mscFrDteDlciOperTable."
   INDEX {
      mscFrDteIndex,
      mscFrDteDlciIndex }
::= { mscFrDteDlciOperTable 1 }

MscFrDteDlciOperEntry ::= SEQUENCE {
   mscFrDteDlciDlciState
      INTEGER,
   mscFrDteDlciLastTimeChange
      EnterpriseDateAndTime,
   mscFrDteDlciSentFrames
      Counter32,
   mscFrDteDlciSentOctets
      Counter32,
   mscFrDteDlciReceivedFrames
      Counter32,
   mscFrDteDlciReceivedOctets
      Counter32,
   mscFrDteDlciReceivedFECNs
      Counter32,
   mscFrDteDlciReceivedBECNs
      Counter32,
   mscFrDteDlciDiscardedFrames
      Counter32,
   mscFrDteDlciCreationType
      INTEGER,
   mscFrDteDlciCreationTime
      EnterpriseDateAndTime,
   mscFrDteDlciRateEnforcement
      INTEGER,
   mscFrDteDlciCommittedInformationRate
      Gauge32,
   mscFrDteDlciCommittedBurst
      Unsigned32,
   mscFrDteDlciExcessBurst
      Unsigned32,
   mscFrDteDlciExcessBurstAction
      INTEGER }

mscFrDteDlciDlciState OBJECT-TYPE
   SYNTAX     INTEGER  {
                 invalid(1),
                 active(2),
                 inactive(3) }
   ACCESS     read-only
   STATUS     mandatory
   DESCRIPTION
     "This attribute reflects the current operational circuit state of the Dlci. 
      The state active indicates that the circuit is up and inactive that the 
      circuit is down. The state invalid means the circuit has been deleted by 
      the DCE (via Lmi)."
   DEFVAL     { inactive }
::= { mscFrDteDlciOperEntry 4 }

mscFrDteDlciLastTimeChange OBJECT-TYPE
   SYNTAX     EnterpriseDateAndTime (SIZE (0 | 19))
   ACCESS     read-only
   STATUS     mandatory
   DESCRIPTION
     "The last time dlciState changed state."
::= { mscFrDteDlciOperEntry 5 }

mscFrDteDlciSentFrames OBJECT-TYPE
   SYNTAX     Counter32 
   ACCESS     read-only
   STATUS     mandatory
   DESCRIPTION
     "Number of frames transmitted across the interface. This counter will 
      wrap around to 0 when it exceeds its maximum count."
::= { mscFrDteDlciOperEntry 7 }

mscFrDteDlciSentOctets OBJECT-TYPE
   SYNTAX     Counter32 
   ACCESS     read-only
   STATUS     mandatory
   DESCRIPTION
     "The number of octets sent from this virtual circuit since it was created. 
      This counter will wrap around to 0 when it exceeds its maximum count."
::= { mscFrDteDlciOperEntry 8 }

mscFrDteDlciReceivedFrames OBJECT-TYPE
   SYNTAX     Counter32 
   ACCESS     read-only
   STATUS     mandatory
   DESCRIPTION
     "Number of frames received across the interface. This counter will wrap 
      around to 0 when it exceeds its maximum count."
::= { mscFrDteDlciOperEntry 9 }

mscFrDteDlciReceivedOctets OBJECT-TYPE
   SYNTAX     Counter32 
   ACCESS     read-only
   STATUS     mandatory
   DESCRIPTION
     "The number of octets sent from this virtual circuit since it was created. 
      This counter will wrap around to 0 when it exceeds its maximum count."
::= { mscFrDteDlciOperEntry 10 }

mscFrDteDlciReceivedFECNs OBJECT-TYPE
   SYNTAX     Counter32 
   ACCESS     read-only
   STATUS     mandatory
   DESCRIPTION
     "Number of frames with the FECN bit set received from the network. 
      This counter will wrap around to 0 when it exceeds its maximum count."
::= { mscFrDteDlciOperEntry 11 }

mscFrDteDlciReceivedBECNs OBJECT-TYPE
   SYNTAX     Counter32 
   ACCESS     read-only
   STATUS     mandatory
   DESCRIPTION
     "Number of frames with the BECN bit set received from the network. 
      This counter will wrap around to 0 when it exceeds its maximum count."
::= { mscFrDteDlciOperEntry 12 }

mscFrDteDlciDiscardedFrames OBJECT-TYPE
   SYNTAX     Counter32 
   ACCESS     read-only
   STATUS     mandatory
   DESCRIPTION
     "The number of inbound frames dropped because of format errors, or 
      because the VC was inactive. This counter will wrap around to 0 when it 
      exceeds its maximum count."
::= { mscFrDteDlciOperEntry 13 }

mscFrDteDlciCreationType OBJECT-TYPE
   SYNTAX     INTEGER  {
                 static(1),
                 dynamic(2) }
   ACCESS     read-only
   STATUS     mandatory
   DESCRIPTION
     "This indicates whether the virtual circuit was manually created (static), 
      or dynamically created (dynamic) via the data link control management 
      interface."
::= { mscFrDteDlciOperEntry 14 }

mscFrDteDlciCreationTime OBJECT-TYPE
   SYNTAX     EnterpriseDateAndTime (SIZE (0 | 19))
   ACCESS     read-only
   STATUS     mandatory
   DESCRIPTION
     "The time when the circuit was created, whether by the Data Link 
      Connection Management Interface or by an SNMP set request."
::= { mscFrDteDlciOperEntry 15 }

mscFrDteDlciRateEnforcement OBJECT-TYPE
   SYNTAX     INTEGER  {
                 enabled(1),
                 disabled(2) }
   ACCESS     read-write
   STATUS     mandatory
   DESCRIPTION
     "This attribute specifies whether the CIR attributes 
      committedInformationRate, committedBurst, and excessBurst are used to 
      define rate enforcement on this user DLCI.
      
      If rateEnforcement is enabled, and the combined Committed and Excess 
      burst thresholds are exceeded, the frame in violation will be discarded 
      immediately if a HibernationQueue subcomponent is not provisioned 
      under the StDlci component (static entries only). If a HibernationQueue 
      is provisioned, the frame will be placed on the HibernationQueue at 
      time of violation and transmission will be attempted later after the point 
      at which the burst thresholds will no longer be exceeded.
      
      Setting all the CIR attributes to zero has the same affect as setting this 
      attribute to disabled.
      
      Setting this attribute will operationally override the corresponding 
      provisional value on static entries."
   DEFVAL     { disabled }
::= { mscFrDteDlciOperEntry 17 }

mscFrDteDlciCommittedInformationRate OBJECT-TYPE
   SYNTAX     Gauge32 (0..48000000)
   ACCESS     read-write
   STATUS     mandatory
   DESCRIPTION
     "The average number of bits to be transferred per second over the DLCI 
      to the DCE. When this attribute is set to zero, the link speed will be used 
      instead.
      
      Setting this attribute will operationally override the corresponding 
      provisional value on static entries."
   DEFVAL     { 64000 }
::= { mscFrDteDlciOperEntry 18 }

mscFrDteDlciCommittedBurst OBJECT-TYPE
   SYNTAX     Unsigned32 (0..2048000)
   ACCESS     read-write
   STATUS     mandatory
   DESCRIPTION
     "The committed burst size (in bits) to which the DLCI wants to 
      subscribe.
      
      Setting this attribute will operationally override the corresponding 
      provisional value on static entries."
   DEFVAL     { 64000 }
::= { mscFrDteDlciOperEntry 19 }

mscFrDteDlciExcessBurst OBJECT-TYPE
   SYNTAX     Unsigned32 (0..2048000)
   ACCESS     read-write
   STATUS     mandatory
   DESCRIPTION
     "The excess burst size (in bits) to which the DLCI wants to subscribe.
      
      Setting this attribute will operationally override the corresponding 
      provisional value on static entries."
   DEFVAL     { 0 }
::= { mscFrDteDlciOperEntry 20 }

mscFrDteDlciExcessBurstAction OBJECT-TYPE
   SYNTAX     INTEGER  {
                 none(1),
                 setDeBit(2) }
   ACCESS     read-write
   STATUS     mandatory
   DESCRIPTION
     "This attribute specifies the action taken when the committedBurst size 
      has been exceeded on the Dlci but the excessBurst size has not. If the 
      attribute is set to setDeBit, the Discard Eligibility bit in the Frame Relay 
      header will be turned on. If the attribute is set to none, no action will be 
      taken.
      
      Setting this attribute will operationally override the corresponding 
      provisional value on static entries."
   DEFVAL     { none }
::= { mscFrDteDlciOperEntry 21 }


-- FrUni/n VirtualFramer
-- FrDte/n VirtualFramer
-- The VirtualFramer component binds two services together to 
-- provide data transfer between them. It is mutually exclusive from 
-- Framer component. 

mscFrDteVFramer OBJECT IDENTIFIER ::= { mscFrDte 9 }



mscFrDteVFramerRowStatusTable OBJECT-TYPE
   SYNTAX     SEQUENCE OF MscFrDteVFramerRowStatusEntry
   ACCESS     not-accessible
   STATUS     mandatory
   DESCRIPTION
     "This entry controls the addition and deletion of 
      mscFrDteVFramer components."
::= { mscFrDteVFramer 1 }

mscFrDteVFramerRowStatusEntry OBJECT-TYPE
   SYNTAX     MscFrDteVFramerRowStatusEntry
   ACCESS     not-accessible
   STATUS     mandatory
   DESCRIPTION
     "A single entry in the table represents a single 
      mscFrDteVFramer component."
   INDEX {
      mscFrDteIndex,
      mscFrDteVFramerIndex }
::= { mscFrDteVFramerRowStatusTable 1 }

MscFrDteVFramerRowStatusEntry ::= SEQUENCE {
   mscFrDteVFramerRowStatus
      RowStatus,
   mscFrDteVFramerComponentName
      DisplayString,
   mscFrDteVFramerStorageType
      StorageType,
   mscFrDteVFramerIndex
      NonReplicated }

mscFrDteVFramerRowStatus OBJECT-TYPE
   SYNTAX     RowStatus 
   ACCESS     read-write
   STATUS     mandatory
   DESCRIPTION
     "This variable is used as the basis for SNMP naming of
      mscFrDteVFramer components.
      These components can be added and deleted."
::= { mscFrDteVFramerRowStatusEntry 1 }

mscFrDteVFramerComponentName OBJECT-TYPE
   SYNTAX     DisplayString 
   ACCESS     read-only
   STATUS     mandatory
   DESCRIPTION
     "This variable provides the component's string name for
      use with the ASCII Console Interface"
::= { mscFrDteVFramerRowStatusEntry 2 }

mscFrDteVFramerStorageType OBJECT-TYPE
   SYNTAX     StorageType 
   ACCESS     read-only
   STATUS     mandatory
   DESCRIPTION
     "This variable represents the storage type value for the
      mscFrDteVFramer tables."
::= { mscFrDteVFramerRowStatusEntry 4 }

mscFrDteVFramerIndex OBJECT-TYPE
   SYNTAX     NonReplicated 
   ACCESS     not-accessible
   STATUS     mandatory
   DESCRIPTION
     "This variable represents the index for the mscFrDteVFramer tables."
::= { mscFrDteVFramerRowStatusEntry 10 }

mscFrDteVFramerProvTable OBJECT-TYPE
   SYNTAX     SEQUENCE OF MscFrDteVFramerProvEntry
   ACCESS     not-accessible
   STATUS     mandatory
   DESCRIPTION
     "This group contains provisionable attributes for the VirtualFramer 
      component."
::= { mscFrDteVFramer 10 }

mscFrDteVFramerProvEntry OBJECT-TYPE
   SYNTAX     MscFrDteVFramerProvEntry
   ACCESS     not-accessible
   STATUS     mandatory
   DESCRIPTION
     "An entry in the mscFrDteVFramerProvTable."
   INDEX {
      mscFrDteIndex,
      mscFrDteVFramerIndex }
::= { mscFrDteVFramerProvTable 1 }

MscFrDteVFramerProvEntry ::= SEQUENCE {
   mscFrDteVFramerOtherVirtualFramer
      Link,
   mscFrDteVFramerLogicalProcessor
      Link }

mscFrDteVFramerOtherVirtualFramer OBJECT-TYPE
   SYNTAX     Link 
   ACCESS     read-write
   STATUS     mandatory
   DESCRIPTION
     "This attribute specifies the other VirtualFramer to which the service 
      is linked, for example, FrUni/n VirtualFramer, FrDte/n 
      VirtualFramer."
::= { mscFrDteVFramerProvEntry 1 }

mscFrDteVFramerLogicalProcessor OBJECT-TYPE
   SYNTAX     Link 
   ACCESS     read-write
   STATUS     mandatory
   DESCRIPTION
     "This attribute specifies the logical processor on which the service 
      component will reside."
::= { mscFrDteVFramerProvEntry 2 }

mscFrDteVFramerStateTable OBJECT-TYPE
   SYNTAX     SEQUENCE OF MscFrDteVFramerStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscFrDteVFramer 11 }

mscFrDteVFramerStateEntry OBJECT-TYPE
   SYNTAX     MscFrDteVFramerStateEntry
   ACCESS     not-accessible
   STATUS     mandatory
   DESCRIPTION
     "An entry in the mscFrDteVFramerStateTable."
   INDEX {
      mscFrDteIndex,
      mscFrDteVFramerIndex }
::= { mscFrDteVFramerStateTable 1 }

MscFrDteVFramerStateEntry ::= SEQUENCE {
   mscFrDteVFramerAdminState
      INTEGER,
   mscFrDteVFramerOperationalState
      INTEGER,
   mscFrDteVFramerUsageState
      INTEGER }

mscFrDteVFramerAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscFrDteVFramerStateEntry 1 }

mscFrDteVFramerOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscFrDteVFramerStateEntry 2 }

mscFrDteVFramerUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscFrDteVFramerStateEntry 3 }

mscFrDteVFramerStatsTable OBJECT-TYPE
   SYNTAX     SEQUENCE OF MscFrDteVFramerStatsEntry
   ACCESS     not-accessible
   STATUS     mandatory
   DESCRIPTION
     "This group contains the operational statistics data for a 
      VirtualFramer component."
::= { mscFrDteVFramer 12 }

mscFrDteVFramerStatsEntry OBJECT-TYPE
   SYNTAX     MscFrDteVFramerStatsEntry
   ACCESS     not-accessible
   STATUS     mandatory
   DESCRIPTION
     "An entry in the mscFrDteVFramerStatsTable."
   INDEX {
      mscFrDteIndex,
      mscFrDteVFramerIndex }
::= { mscFrDteVFramerStatsTable 1 }

MscFrDteVFramerStatsEntry ::= SEQUENCE {
   mscFrDteVFramerFrmToOtherVFramer
      PassportCounter64,
   mscFrDteVFramerFrmFromOtherVFramer
      PassportCounter64,
   mscFrDteVFramerOctetFromOtherVFramer
      PassportCounter64 }

mscFrDteVFramerFrmToOtherVFramer OBJECT-TYPE
   SYNTAX     PassportCounter64 
   ACCESS     read-only
   STATUS     mandatory
   DESCRIPTION
     "This attribute counts the frames transmitted to the 
      otherVirtualFramer."
::= { mscFrDteVFramerStatsEntry 2 }

mscFrDteVFramerFrmFromOtherVFramer OBJECT-TYPE
   SYNTAX     PassportCounter64 
   ACCESS     read-only
   STATUS     mandatory
   DESCRIPTION
     "This attribute counts the frames received from the 
      otherVirtualFramer."
::= { mscFrDteVFramerStatsEntry 3 }

mscFrDteVFramerOctetFromOtherVFramer OBJECT-TYPE
   SYNTAX     PassportCounter64 
   ACCESS     read-only
   STATUS     mandatory
   DESCRIPTION
     "This attribute counts the octets received from the 
      otherVirtualFramer."
::= { mscFrDteVFramerStatsEntry 5 }




-- 
-- Version and Compliance statements
-- 



-- Object-Group Statement:
-- A list of all current accessible leaf objects.

-- OBJECTS { mscFrDteLmiLmiStatus,
--           mscFrDteFramerCrcErrors,
--           mscFrDteStorageType,
--           mscFrDteLeqComponentName,
--           mscFrDteRgLinkToProtocolPort,
--           mscFrDteDlciAdminState,
--           mscFrDteVFramerFrmToOtherVFramer,
--           mscFrDteLeqPktThresholdExceeded,
--           mscFrDteVFramerStorageType,
--           mscFrDteStDlciHqMulThresholdExceeded,
--           mscFrDteLeqForcedPktDiscards,
--           mscFrDteStDlciHqTimeToLive,
--           mscFrDteStDlciHqQueueByteThreshold,
--           mscFrDteFramerAdminState,
--           mscFrDteXmitDiscardLmiInactive,
--           mscFrDteDynDlciDefsIpCos,
--           mscFrDteDynDlciDefsRowStatus,
--           mscFrDteFramerLargeFrmErrors,
--           mscFrDteStDlciHqCurrentBytesQueued,
--           mscFrDteLeqMulThresholdExceeded,
--           mscFrDteFramerRowStatus,
--           mscFrDteDlciRateEnforcement,
--           mscFrDteDlciReceivedFrames,
--           mscFrDteLeqQueueByteThreshold,
--           mscFrDteDlciUsageState,
--           mscFrDteStDlciExcessBurstAction,
--           mscFrDteVFramerFrmFromOtherVFramer,
--           mscFrDteDynDlciDefsRateEnforcement,
--           mscFrDteStDlciHqTimedOutPkt,
--           mscFrDteCustomerIdentifier,
--           mscFrDteStDlciHqMemThresholdExceeded,
--           mscFrDteFramerNonOctetErrors,
--           mscFrDteLeqMaxPercentMulticast,
--           mscFrDteDlciReceivedBECNs,
--           mscFrDteFramerUsageState,
--           mscFrDteStDlciHqTotalPktQueued,
--           mscFrDteComponentName,
--           mscFrDteFramerNormPrioLinkUtilFromIf,
--           mscFrDteRgBfrComponentName,
--           mscFrDteLeqStorageType,
--           mscFrDteVFramerLogicalProcessor,
--           mscFrDteUsageState,
--           mscFrDteStDlciCommittedInformationRate,
--           mscFrDteLeqMemThresholdExceeded,
--           mscFrDteStDlciStdRowStatus,
--           mscFrDteFramerInterfaceName,
--           mscFrDteLmiStorageType,
--           mscFrDteStDlciExcessBurst,
--           mscFrDteErrData,
--           mscFrDteVFramerOperationalState,
--           mscFrDteStDlciHqMaxMsecData,
--           mscFrDteStDlciComponentName,
--           mscFrDteFramerOperationalState,
--           mscFrDteErrType,
--           mscFrDteStDlciHqStorageType,
--           mscFrDteStDlciHqQueueMulticastThreshold,
--           mscFrDteOperationalState,
--           mscFrDteDlciCreationType,
--           mscFrDteLeqCurrentBytesQueued,
--           mscFrDteStDlciHqRowStatus,
--           mscFrDteDlciOperationalState,
--           mscFrDteVFramerComponentName,
--           mscFrDteStDlciHqQueuePurgeDiscards,
--           mscFrDteFramerLrcErrors,
--           mscFrDteRgBfrMacAddr,
--           mscFrDteDynDlciDefsStdRowStatus,
--           mscFrDteLmiRowStatus,
--           mscFrDteFramerAborts,
--           mscFrDteRgComponentName,
--           mscFrDteDlciCommittedBurst,
--           mscFrDteStDlciHqCurrentPktQueued,
--           mscFrDteStDlciHqTotalPktDiscards,
--           mscFrDteDlciCommittedInformationRate,
--           mscFrDteDlcmiProtoErr,
--           mscFrDteLeqCurrentMulticastQueued,
--           mscFrDteLmiFullEnquiryInterval,
--           mscFrDteLeqTotalPktHandled,
--           mscFrDteRecvDiscardLmiInactive,
--           mscFrDteStDlciHqQueuePktThreshold,
--           mscFrDteSnmpOperStatus,
--           mscFrDteLeqCurrentPktQueued,
--           mscFrDteLeqTotalPktDiscards,
--           mscFrDteXmitDiscardCirExceeded,
--           mscFrDteErrDiscards,
--           mscFrDteDlciSentFrames,
--           mscFrDteStDlciHqTotalPktHandled,
--           mscFrDteLinkOperState,
--           mscFrDteRgBfrStorageType,
--           mscFrDteStDlciIpCos,
--           mscFrDteErrFaultTime,
--           mscFrDteAdminState,
--           mscFrDteAcceptUndefinedDlci,
--           mscFrDteReceiveShort,
--           mscFrDteLeqTimedOutPkt,
--           mscFrDteRgBfrMacType,
--           mscFrDteRowStatus,
--           mscFrDteBadFc,
--           mscFrDteDlciReceivedOctets,
--           mscFrDteStDlciStorageType,
--           mscFrDteLeqTimeToLive,
--           mscFrDteUlpUnknownProtocol,
--           mscFrDteXmitDiscardPvcInactive,
--           mscFrDteXmitDiscardPvcDown,
--           mscFrDteDynDlciDefsExcessBurstAction,
--           mscFrDteDlcmiUnknownIe,
--           mscFrDteRgSnmpOperStatus,
--           mscFrDteRgIfIndex,
--           mscFrDteIfAdminStatus,
--           mscFrDteStDlciHqTotalPktForwarded,
--           mscFrDteRgBfrRowStatus,
--           mscFrDteLeqQueuePktThreshold,
--           mscFrDteLmiErrorThreshold,
--           mscFrDteStDlciHqCurrentMulticastQueued,
--           mscFrDteFramerOverruns,
--           mscFrDteDlciDlciState,
--           mscFrDteLmiPollingInterval,
--           mscFrDteDynDlciDefsCommittedInformationRate,
--           mscFrDteDlciExcessBurst,
--           mscFrDteLeqTotalMulticastPkt,
--           mscFrDteRgStorageType,
--           mscFrDteLeqQueuePurgeDiscards,
--           mscFrDteStDlciRowStatus,
--           mscFrDteDynDlciDefsExcessBurst,
--           mscFrDteRgMaxTransmissionUnit,
--           mscFrDteErrTime,
--           mscFrDteDynDlciDefsComponentName,
--           mscFrDteLeqHardwareForcedPkt,
--           mscFrDteFramerComponentName,
--           mscFrDteDlciCreationTime,
--           mscFrDteDlciDiscardedFrames,
--           mscFrDteVFramerOtherVirtualFramer,
--           mscFrDteStDlciRateEnforcement,
--           mscFrDteLeqMaxMsecData,
--           mscFrDteVFramerRowStatus,
--           mscFrDteFramerFrmToIf,
--           mscFrDteLeqQueueMulticastThreshold,
--           mscFrDteDlciComponentName,
--           mscFrDteRgAdminState,
--           mscFrDteLmiMonitoredEvents,
--           mscFrDteStDlciHqMaxPackets,
--           mscFrDteFramerUnderruns,
--           mscFrDteLeqTotalPktForwarded,
--           mscFrDteDlcmiSequenceErr,
--           mscFrDteDlciLastTimeChange,
--           mscFrDteRgRowStatus,
--           mscFrDteRgIfAdminStatus,
--           mscFrDteLeqTotalPktQueued,
--           mscFrDteRgUsageState,
--           mscFrDteStDlciHqMaxPercentMulticast,
--           mscFrDteLeqMaxPackets,
--           mscFrDteErrFaults,
--           mscFrDteLeqRowStatus,
--           mscFrDteVFramerAdminState,
--           mscFrDteStDlciHqTotalMulticastPkt,
--           mscFrDteXmitDiscardFramerDown,
--           mscFrDteIllegalDlci,
--           mscFrDteRgBfrBfrIndex,
--           mscFrDteVFramerUsageState,
--           mscFrDteDlcmiUnknownRpt,
--           mscFrDteStDlciHqByteThresholdExceeded,
--           mscFrDteDynDlciDefsCommittedBurst,
--           mscFrDteStDlciLinkToRemoteGroup,
--           mscFrDteRgLtDlciValue,
--           mscFrDteVFramerOctetFromOtherVFramer,
--           mscFrDteRgLtDlciRowStatus,
--           mscFrDteRecvDiscardPvcInactive,
--           mscFrDteRecvDiscardPvcDown,
--           mscFrDteStDlciHqComponentName,
--           mscFrDteLeqByteThresholdExceeded,
--           mscFrDteDefragSequenceErrors,
--           mscFrDteDlciRowStatus,
--           mscFrDteDlciStorageType,
--           mscFrDteRgOperationalState,
--           mscFrDteDlciSentOctets,
--           mscFrDteDlciExcessBurstAction,
--           mscFrDteIfIndex,
--           mscFrDteDlciReceivedFECNs,
--           mscFrDteFramerNormPrioLinkUtilToIf,
--           mscFrDteLmiComponentName,
--           mscFrDteDynDlciDefsStorageType,
--           mscFrDteFramerFrmFromIf,
--           mscFrDteStDlciHqPktThresholdExceeded,
--           mscFrDteFramerStorageType,
--           mscFrDteStDlciCommittedBurst,
--           mscFrDteLmiProcedures }
-- STATUS  mandatory
-- DESCRIPTION
--   "A list of all current accessible leaf objects."

frameRelayDteGroup OBJECT IDENTIFIER ::= { frameRelayDteMIB 1 }
frameRelayDteGroupCA OBJECT IDENTIFIER ::= { frameRelayDteGroup 1 }
frameRelayDteGroupCA02 OBJECT IDENTIFIER ::= { frameRelayDteGroupCA 3 }
frameRelayDteGroupCA02A OBJECT IDENTIFIER ::= { frameRelayDteGroupCA02 2 }



-- Agent-Capabilities Statement:

-- PRODUCT-RELEASE "MscPassport Release 1.2 FrameRelayDte."
-- STATUS          mandatory
-- DESCRIPTION     "Carrier Passport FrameRelayDte MIB: MIB Version CA02A,
--                  Software Version CA02S9C."
-- SUPPORTS        Nortel-MsCarrier-MscPassport-FrameRelayDteMIB
--    INCLUDES     { frameRelayDteGroupCA02A }
--        draft-ietf-iplpdn-frmib-dte-02.txt
--        (a draft for the evolution of RFC1315)
-- 
-- SUPPORTS RFCxxxx-MIB
--    INCLUDES        { frDlcmiTable, frCircuitTable, frErrTable }  
--     				   frameRelayTrapControl is not supported.
--  
--        variations for frDlcmiTable
--  
--    VARIATION		frDlcmiState
--       SYNTAX INTEGER      {
--       noLmiConfigured   (1),
--       lmiRev1           (2),
--       ansiT1-617-D      (3),     ANSI T1.617 Annex D
--       ccitt-933-A       (5)      CCITT Q933 Annex A
--       }
--       DEFVAL            { ccitt-933-A }
--       DESCRIPTION       "The ANSI T1.617 Annix B procedures are not supported."
--  
--    VARIATION		frDlcmiAddress
--       SYNTAX INTEGER      {
--       q922              (4)      Final Standard
--       }
--       DEFVAL            { q922 }
--       DESCRIPTION       "The Q.921, Q.922 (March 90), and Q.922 (November 90)
--                         address schemes are not supported."
--  
--    VARIATION		frDlcmiAddressLen
--       SYNTAX INTEGER      {
--       two-octets        (2)
--       }
--       DEFVAL            { two-octets }
--       DESCRIPTION       "Three and four octet addresses are not supported."
--  
--    VARIATION		frDlcmiMaxSupportedVCs
--       SYNTAX            Integer32 (1024)
--       DEFVAL            { 1024 }
--       DESCRIPTION       "Only 1024 virtual circuits are supported per ifEntry."
--  
--    VARIATION		frDlcmiMulticast
--       SYNTAX INTEGER      {
--        nonBroadcast     (1)
--       }
--       DEFVAL            { nonBroadcast }
--       DESCRIPTION       "Broadcast virtual circuits are not supported."
--  
--       variations for frCircuitTable
--  
--    VARIATION		frCircuitState
--       MAX-ACCESS        read-only
--       DEFVAL            { inactive }
--       DESCRIPTION       "Write access is not supported, use frCircuitRowStatus
--                         instead.  Defaults to inactive."
--  
--    VARIATION		frCircuitCommittedBurst
--       DEFVAL            { 64000 }
--       DESCRIPTION       "This implementation defaults to 64000 bits."
--  
--    VARIATION		frCircuitThroughput
--       DEFVAL            { 64000 }
--       DESCRIPTION       "This implementation defaults to 64000 bits/sec."
-- 
-- 
-- 
-- 

frameRelayDteCapabilities OBJECT IDENTIFIER ::= { frameRelayDteMIB 3 }
frameRelayDteCapabilitiesCA OBJECT IDENTIFIER ::= { frameRelayDteCapabilities 1 }
frameRelayDteCapabilitiesCA02 OBJECT IDENTIFIER ::= { frameRelayDteCapabilitiesCA 3 }
frameRelayDteCapabilitiesCA02A OBJECT IDENTIFIER ::= { frameRelayDteCapabilitiesCA02 2 }





END
