Nortel-MsCarrier-MscPassport-FrameRelayNniMIB
DEFINITIONS ::= BEGIN



IMPORTS

      OBJECT-TYPE
   FROM RFC-1212

      mscPassportMIBs,
      mscComponents
   FROM Nortel-MsCarrier-MscPassport-UsefulDefinitionsMIB

      Counter32,
      RowPointer,
      DisplayString,
      StorageType,
      RowStatus,
      InterfaceIndex,
      Gauge32,
      Integer32,
      Unsigned32
   FROM Nortel-MsCarrier-MscPassport-StandardTextualConventionsMIB

      AsciiString,
      Hex,
      NonReplicated,
      FixedPoint3,
      HexString,
      EnterpriseDateAndTime,
      PassportCounter64,
      Link,
      DigitString,
      Unsigned64
   FROM Nortel-MsCarrier-MscPassport-TextualConventionsMIB;




-- LAST-UPDATED   "9909010000Z"
-- ORGANIZATION   "Nortel Networks"
-- CONTACT-INFO   "
--         Nortel Carrier Data Network Management
--         
--         Postal:       P.O. Box 3511, Station C 
--                       Ottawa, Ontario 
--                       Canada  K1Y 4H7
--         
--         via the WEB:  http://www.nortelnetworks.com  
--                       select 'Contact Us' from the menu
--          
--         via phone:    1-800-4NORTEL"
-- DESCRIPTION
--    "The module describing the Nortel MsCarrier MscPassport
--     FrameRelayNni Enterprise MIB."

frameRelayNniMIB OBJECT IDENTIFIER ::= { mscPassportMIBs 23 }










-- FrameRelayNni/n
-- This component defines an instance of the Frame Relay Network-
-- to-Network Interface (NNI) service. This service allows two 
-- networks to be interconnected using the Frame Relay protocol. The 
-- component instance value n is a unique positive integer within a 
-- module. The FrNni interface must have either a Framer or a 
-- VirtualFramer subcomponent. As a default, a Framer is created 
-- whenever the FrNni is added. Users who need a VirtualFramer 
-- should delete the Framer and then add the VirtualFramer.

mscFrNni OBJECT IDENTIFIER ::= { mscComponents 70 }



mscFrNniRowStatusTable OBJECT-TYPE
   SYNTAX     SEQUENCE OF MscFrNniRowStatusEntry
   ACCESS     not-accessible
   STATUS     mandatory
   DESCRIPTION
     "This entry controls the addition and deletion of 
      mscFrNni components."
::= { mscFrNni 1 }

mscFrNniRowStatusEntry OBJECT-TYPE
   SYNTAX     MscFrNniRowStatusEntry
   ACCESS     not-accessible
   STATUS     mandatory
   DESCRIPTION
     "A single entry in the table represents a single 
      mscFrNni component."
   INDEX {
      mscFrNniIndex }
::= { mscFrNniRowStatusTable 1 }

MscFrNniRowStatusEntry ::= SEQUENCE {
   mscFrNniRowStatus
      RowStatus,
   mscFrNniComponentName
      DisplayString,
   mscFrNniStorageType
      StorageType,
   mscFrNniIndex
      Integer32 }

mscFrNniRowStatus OBJECT-TYPE
   SYNTAX     RowStatus 
   ACCESS     read-write
   STATUS     mandatory
   DESCRIPTION
     "This variable is used as the basis for SNMP naming of
      mscFrNni components.
      These components can be added and deleted."
::= { mscFrNniRowStatusEntry 1 }

mscFrNniComponentName OBJECT-TYPE
   SYNTAX     DisplayString 
   ACCESS     read-only
   STATUS     mandatory
   DESCRIPTION
     "This variable provides the component's string name for
      use with the ASCII Console Interface"
::= { mscFrNniRowStatusEntry 2 }

mscFrNniStorageType OBJECT-TYPE
   SYNTAX     StorageType 
   ACCESS     read-only
   STATUS     mandatory
   DESCRIPTION
     "This variable represents the storage type value for the
      mscFrNni tables."
::= { mscFrNniRowStatusEntry 4 }

mscFrNniIndex OBJECT-TYPE
   SYNTAX     Integer32 (1..65535)
   ACCESS     not-accessible
   STATUS     mandatory
   DESCRIPTION
     "This variable represents the index for the mscFrNni tables."
::= { mscFrNniRowStatusEntry 10 }

mscFrNniCidDataTable OBJECT-TYPE
   SYNTAX     SEQUENCE OF MscFrNniCidDataEntry
   ACCESS     not-accessible
   STATUS     mandatory
   DESCRIPTION
     "This group contains the attribute for a component's Customer 
      Identifier (CID). Refer to the attribute description for a detailed 
      explanation of CIDs."
::= { mscFrNni 10 }

mscFrNniCidDataEntry OBJECT-TYPE
   SYNTAX     MscFrNniCidDataEntry
   ACCESS     not-accessible
   STATUS     mandatory
   DESCRIPTION
     "An entry in the mscFrNniCidDataTable."
   INDEX {
      mscFrNniIndex }
::= { mscFrNniCidDataTable 1 }

MscFrNniCidDataEntry ::= SEQUENCE {
   mscFrNniCustomerIdentifier
      Unsigned32 }

mscFrNniCustomerIdentifier OBJECT-TYPE
   SYNTAX     Unsigned32 (0 | 1..8191)
   ACCESS     read-write
   STATUS     mandatory
   DESCRIPTION
     "This attribute holds the Customer Identifier (CID).
      
      Every component has a CID. If a component has a cid attribute, the 
      component's CID is the provisioned value of that attribute; 
      otherwise the component inherits the CID of its parent. The top-
      level component has a CID of 0.
      
      Every operator session also has a CID, which is the CID 
      provisioned for the operator's user ID. An operator will see only the 
      stream data for components having a matching CID. Also, the 
      operator will be allowed to issue commands for only those 
      components which have a matching CID.
      
      An operator CID of 0 is used to identify the Network Manager 
      (referred to as 'NetMan' in DPN). This CID matches the CID of 
      any component. Values 1 to 8191 inclusive (equivalent to 'basic 
      CIDs' in DPN) may be assigned to specific customers."
   DEFVAL     { 0 }
::= { mscFrNniCidDataEntry 1 }

mscFrNniStateTable OBJECT-TYPE
   SYNTAX     SEQUENCE OF MscFrNniStateEntry
   ACCESS     not-accessible
   STATUS     mandatory
   DESCRIPTION
     "This group contains the three OSI State attributes and the six OSI 
      Status attributes. The descriptions generically indicate what each 
      attribute implies about the component. Note that not all the values 
      and state combinations described here are supported by every 
      component which uses this group. For component-specific 
      information and the valid state combinations, refer to NTP 241-
      7001-150, Passport Operations and Maintenance Guide."
::= { mscFrNni 11 }

mscFrNniStateEntry OBJECT-TYPE
   SYNTAX     MscFrNniStateEntry
   ACCESS     not-accessible
   STATUS     mandatory
   DESCRIPTION
     "An entry in the mscFrNniStateTable."
   INDEX {
      mscFrNniIndex }
::= { mscFrNniStateTable 1 }

MscFrNniStateEntry ::= SEQUENCE {
   mscFrNniAdminState
      INTEGER,
   mscFrNniOperationalState
      INTEGER,
   mscFrNniUsageState
      INTEGER,
   mscFrNniAvailabilityStatus
      OCTET STRING,
   mscFrNniProceduralStatus
      OCTET STRING,
   mscFrNniControlStatus
      OCTET STRING,
   mscFrNniAlarmStatus
      OCTET STRING,
   mscFrNniStandbyStatus
      INTEGER,
   mscFrNniUnknownStatus
      INTEGER }

mscFrNniAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component.
      
      The OSI Status attributes, if supported by the component, may 
      provide more details, qualifying the state of the component."
   DEFVAL     { unlocked }
::= { mscFrNniStateEntry 1 }

mscFrNniOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle.
      
      The OSI Status attributes, if supported by the component, may 
      provide more details, qualifying the state of the component."
   DEFVAL     { disabled }
::= { mscFrNniStateEntry 2 }

mscFrNniUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time.
      
      The OSI Status attributes, if supported by the component, may 
      provide more details, qualifying the state of the component."
   DEFVAL     { idle }
::= { mscFrNniStateEntry 3 }

mscFrNniAvailabilityStatus OBJECT-TYPE
   SYNTAX     OCTET STRING (SIZE (2))
   ACCESS     read-only
   STATUS     mandatory
   DESCRIPTION
     "If supported by the component, this attribute indicates the OSI 
      Availability status of the component. Note that, even though it is 
      defined as a multi-valued set, at most one value is shown to the user.
      
      When no values are in the set, this indicates that either the attribute 
      is not supported or that none of the status conditions described 
      below are present.
      
      The value inTest indicates that the resource is undergoing a test 
      procedure. If adminState is locked or shuttingDown, the normal 
      users are precluded from using the resource and controlStatus is 
      reservedForTest. Tests that do not exclude additional users can be 
      present in any operational or administrative state but the 
      reservedForTest condition should not be present.
      
      The value failed indicates that the component has an internal fault 
      that prevents it from operating. The operationalState is disabled.
      
      The value dependency indicates that the component cannot operate 
      because some other resource on which it depends is unavailable. 
      The operationalState is disabled.
      
      The value powerOff indicates the resource requires power to be 
      applied and it is not powered on. The operationalState is disabled.
      
      The value offLine indicates the resource requires a routine 
      operation (either manual, automatic, or both) to be performed to 
      place it on-line and make it available for use. The operationalState 
      is disabled.
      
      The value offDuty indicates the resource is inactive in accordance 
      with a predetermined time schedule. In the absence of other 
      disabling conditions, the operationalState is enabled or disabled.
      
      The value degraded indicates the service provided by the 
      component is degraded in some way, such as in speed or operating 
      capacity. However, the resource remains available for service. The 
      operationalState is enabled.
      
      The value notInstalled indicates the resource is not present. The 
      operationalState is disabled.
      
      The value logFull is not used.

      Description of bits:
      inTest(0)
      failed(1)
      powerOff(2)
      offLine(3)
      offDuty(4)
      dependency(5)
      degraded(6)
      notInstalled(7)
      logFull(8)"
::= { mscFrNniStateEntry 4 }

mscFrNniProceduralStatus OBJECT-TYPE
   SYNTAX     OCTET STRING (SIZE (1))
   ACCESS     read-only
   STATUS     mandatory
   DESCRIPTION
     "If supported by the component, this attribute indicates the OSI 
      Procedural status of the component. Note that, even though it is 
      defined as a multi-valued set, at most one value is shown to the user.
      
      When no values are in the set, this indicates that either the attribute 
      is not supported or that none of the status conditions described 
      below are present.
      
      The value initializationRequired indicates (for a resource which 
      doesn't initialize autonomously) that initialization is required before 
      it can perform its normal functions, and this procedure has not been 
      initiated. The operationalState is disabled.
      
      The value notInitialized indicates (for a resource which does 
      initialize autonomously) that initialization is required before it can 
      perform its normal functions, and this procedure has not been 
      initiated. The operationalState may be enabled or disabled.
      
      The value initializing indicates that initialization has been initiated 
      but is not yet complete. The operationalState may be enabled or 
      disabled.
      
      The value reporting indicates the resource has completed some 
      processing operation and is notifying the results. The 
      operationalState is enabled.
      
      The value terminating indicates the component is in a termination 
      phase. If the resource doesn't reinitialize autonomously, 
      operationalState is disabled; otherwise it is enabled or disabled.

      Description of bits:
      initializationRequired(0)
      notInitialized(1)
      initializing(2)
      reporting(3)
      terminating(4)"
::= { mscFrNniStateEntry 5 }

mscFrNniControlStatus OBJECT-TYPE
   SYNTAX     OCTET STRING (SIZE (1))
   ACCESS     read-only
   STATUS     mandatory
   DESCRIPTION
     "If supported by the component, this attribute indicates the OSI 
      Control status of the component. Note that, even though it is defined 
      as a multi-valued set, at most one value is shown to the user.
      
      When no values are in the set, this indicates that either the attribute 
      is not supported or that none of the status conditions described 
      below are present.
      
      The value subjectToTest indicates the resource is available but tests 
      may be conducted simultaneously at unpredictable times, which 
      may cause it to exhibit unusual characteristics.
      
      The value partOfServicesLocked indicates that part of the service is 
      restricted from users of a resource. The adminState is unlocked.
      
      The value reservedForTest indicates that the component is 
      administratively unavailable because it is undergoing a test 
      procedure. The adminState is locked.
      
      The value suspended indicates that the service has been 
      administratively suspended.

      Description of bits:
      subjectToTest(0)
      partOfServicesLocked(1)
      reservedForTest(2)
      suspended(3)"
::= { mscFrNniStateEntry 6 }

mscFrNniAlarmStatus OBJECT-TYPE
   SYNTAX     OCTET STRING (SIZE (1))
   ACCESS     read-only
   STATUS     mandatory
   DESCRIPTION
     "If supported by the component, this attribute indicates the OSI 
      Alarm status of the component. Note that, even though it is defined 
      as a multi-valued set, at most one value is shown to the user.
      
      When no values are in the set, this indicates that either the attribute 
      is not supported or that none of the status conditions described 
      below are present.
      
      The value underRepair indicates the component is currently being 
      repaired. The operationalState is enabled or disabled.
      
      The value critical indicates one or more critical alarms are 
      outstanding against the component. Other, less severe, alarms may 
      also be outstanding. The operationalState is enabled or disabled.
      
      The value major indicates one or more major alarms are 
      outstanding against the component. Other, less severe, alarms may 
      also be outstanding. The operationalState is enabled or disabled.
      
      The value minor indicates one or more minor alarms are 
      outstanding against the component. Other, less severe, alarms may 
      also be outstanding. The operationalState is enabled or disabled.
      
      The value alarmOutstanding generically indicates that an alarm of 
      some severity is outstanding against the component.

      Description of bits:
      underRepair(0)
      critical(1)
      major(2)
      minor(3)
      alarmOutstanding(4)"
::= { mscFrNniStateEntry 7 }

mscFrNniStandbyStatus OBJECT-TYPE
   SYNTAX     INTEGER  {
                 hotStandby(0),
                 coldStandby(1),
                 providingService(2),
                 notSet(15) }
   ACCESS     read-only
   STATUS     mandatory
   DESCRIPTION
     "If supported by the component, this attribute indicates the OSI 
      Standby status of the component.
      
      The value notSet indicates that either the attribute is not supported 
      or that none of the status conditions described below are present. 
      Note that this is a non-standard value, used because the original 
      specification indicated this attribute was set-valued and thus, did not 
      provide a value to indicate that none of the other three are 
      applicable.
      
      The value hotStandby indicates that the resource is not providing 
      service but will be immediately able to take over the role of the 
      resource to be backed up, without initialization activity, and 
      containing the same information as the resource to be backed up.
      
      The value coldStandby indicates the resource is a backup for 
      another resource but will not be immediately able to take over the 
      role of the backed up resource and will require some initialization 
      activity.
      
      The value providingService indicates that this component, as a 
      backup resource, is currently backing up another resource."
   DEFVAL     { notSet }
::= { mscFrNniStateEntry 8 }

mscFrNniUnknownStatus OBJECT-TYPE
   SYNTAX     INTEGER  {
                 false(0),
                 true(1) }
   ACCESS     read-only
   STATUS     mandatory
   DESCRIPTION
     "This attribute indicates the OSI Unknown status of the component.
      
      The value false indicates that all of the other OSI State and Status 
      attribute values can be considered accurate.
      
      The value true indicates that the actual state of the component is not 
      known for sure."
   DEFVAL     { false }
::= { mscFrNniStateEntry 9 }

mscFrNniStatsTable OBJECT-TYPE
   SYNTAX     SEQUENCE OF MscFrNniStatsEntry
   ACCESS     not-accessible
   STATUS     mandatory
   DESCRIPTION
     "This group contains the statistics about the operational behaviour of 
      the service at the interface level."
::= { mscFrNni 12 }

mscFrNniStatsEntry OBJECT-TYPE
   SYNTAX     MscFrNniStatsEntry
   ACCESS     not-accessible
   STATUS     mandatory
   DESCRIPTION
     "An entry in the mscFrNniStatsTable."
   INDEX {
      mscFrNniIndex }
::= { mscFrNniStatsTable 1 }

MscFrNniStatsEntry ::= SEQUENCE {
   mscFrNniLastUnknownDlci
      Unsigned32,
   mscFrNniUnknownDlciFramesFromIf
      Counter32,
   mscFrNniInvalidHeaderFramesFromIf
      Counter32 }

mscFrNniLastUnknownDlci OBJECT-TYPE
   SYNTAX     Unsigned32 (0..1023)
   ACCESS     read-only
   STATUS     mandatory
   DESCRIPTION
     "This attribute identifies the most recent DLCI which user frames 
      were received on for which a DLCI has not been provisioned on the 
      port."
   DEFVAL     { 0 }
::= { mscFrNniStatsEntry 1 }

mscFrNniUnknownDlciFramesFromIf OBJECT-TYPE
   SYNTAX     Counter32 
   ACCESS     read-only
   STATUS     mandatory
   DESCRIPTION
     "This attribute contains a count of the number of frames received 
      from the interface with an unknown DLCI (DLCI which is not 
      provisioned). When the maximum is exceeded the count wraps to 
      zero."
::= { mscFrNniStatsEntry 2 }

mscFrNniInvalidHeaderFramesFromIf OBJECT-TYPE
   SYNTAX     Counter32 
   ACCESS     read-only
   STATUS     mandatory
   DESCRIPTION
     "This attribute counts the number of frames received from the 
      interface with an invalid header format. When the maximum is 
      exceeded the count wraps to zero."
::= { mscFrNniStatsEntry 3 }

mscFrNniIfEntryTable OBJECT-TYPE
   SYNTAX     SEQUENCE OF MscFrNniIfEntryEntry
   ACCESS     not-accessible
   STATUS     mandatory
   DESCRIPTION
     "This group contains the provisionable attributes for the ifEntry."
::= { mscFrNni 13 }

mscFrNniIfEntryEntry OBJECT-TYPE
   SYNTAX     MscFrNniIfEntryEntry
   ACCESS     not-accessible
   STATUS     mandatory
   DESCRIPTION
     "An entry in the mscFrNniIfEntryTable."
   INDEX {
      mscFrNniIndex }
::= { mscFrNniIfEntryTable 1 }

MscFrNniIfEntryEntry ::= SEQUENCE {
   mscFrNniIfAdminStatus
      INTEGER,
   mscFrNniIfIndex
      InterfaceIndex }

mscFrNniIfAdminStatus OBJECT-TYPE
   SYNTAX     INTEGER  {
                 up(1),
                 down(2),
                 testing(3) }
   ACCESS     read-write
   STATUS     mandatory
   DESCRIPTION
     "The desired state of the interface. The up state indicates the 
      interface is operational. The down state indicates the interface is not 
      operational. The testing state indicates that no operational packets 
      can be passed."
   DEFVAL     { up }
::= { mscFrNniIfEntryEntry 1 }

mscFrNniIfIndex OBJECT-TYPE
   SYNTAX     InterfaceIndex (1..65535)
   ACCESS     read-only
   STATUS     mandatory
   DESCRIPTION
     "This is the index for the IfEntry. Its value is automatically initialized 
      during the provisioning process."
::= { mscFrNniIfEntryEntry 2 }

mscFrNniOperStatusTable OBJECT-TYPE
   SYNTAX     SEQUENCE OF MscFrNniOperStatusEntry
   ACCESS     not-accessible
   STATUS     mandatory
   DESCRIPTION
     "This group includes the Operational Status attribute. This attribute 
      defines the current operational state of this component."
::= { mscFrNni 14 }

mscFrNniOperStatusEntry OBJECT-TYPE
   SYNTAX     MscFrNniOperStatusEntry
   ACCESS     not-accessible
   STATUS     mandatory
   DESCRIPTION
     "An entry in the mscFrNniOperStatusTable."
   INDEX {
      mscFrNniIndex }
::= { mscFrNniOperStatusTable 1 }

MscFrNniOperStatusEntry ::= SEQUENCE {
   mscFrNniSnmpOperStatus
      INTEGER }

mscFrNniSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { mscFrNniOperStatusEntry 1 }

mscFrNniEmissionPriorityQsTable OBJECT-TYPE
   SYNTAX     SEQUENCE OF MscFrNniEmissionPriorityQsEntry
   ACCESS     not-accessible
   STATUS     mandatory
   DESCRIPTION
     "This group contains the provisionable attribute to specifie the 
      number of Frame Relay egress emission priority queues to be used 
      on that Frame Relay Interface"
::= { mscFrNni 15 }

mscFrNniEmissionPriorityQsEntry OBJECT-TYPE
   SYNTAX     MscFrNniEmissionPriorityQsEntry
   ACCESS     not-accessible
   STATUS     mandatory
   DESCRIPTION
     "An entry in the mscFrNniEmissionPriorityQsTable."
   INDEX {
      mscFrNniIndex }
::= { mscFrNniEmissionPriorityQsTable 1 }

MscFrNniEmissionPriorityQsEntry ::= SEQUENCE {
   mscFrNniNumberOfEmissionQs
      Unsigned32 }

mscFrNniNumberOfEmissionQs OBJECT-TYPE
   SYNTAX     Unsigned32 (2 | 4)
   ACCESS     read-write
   STATUS     mandatory
   DESCRIPTION
     "This attribute specifies the number of egress emission priority 
      queues that will be used for that Frame Relay interface. The 
      possible values of this attribute are 2 or 4:
      For V.35, V.11, HSSI, E1, DS1, E3, DS3 or 8pDS1 the possible 
      values are: 2 (in which case they are hardware queues), or 4 (in 
      which case they are software queues).
      For DS1C, E1C or DS3C the possible values are 2, 4 (in all cases 
      they are software queues)."
   DEFVAL     { 2 }
::= { mscFrNniEmissionPriorityQsEntry 1 }

mscFrNniFrmToIfByQueueTable OBJECT-TYPE
   SYNTAX     SEQUENCE OF MscFrNniFrmToIfByQueueEntry
   ACCESS     not-accessible
   STATUS     mandatory
   DESCRIPTION
     "This attribute counts the total number of frames transmitted to the 
      interface per egress emission priority queue since the component 
      has been activated. There is potientially a maximum of 4 emission 
      priority queues. The number of available egress queues varies 
      according to the value of the provisionable attribute 
      numberOfEmissionQs. Egress queue 0 has the lowest priority, while 
      egress queue 3 has the highest priority. The queue values
      are only indicated when the numberOfEmissionQs is set to 4 
      queues."
::= { mscFrNni 341 }

mscFrNniFrmToIfByQueueEntry OBJECT-TYPE
   SYNTAX     MscFrNniFrmToIfByQueueEntry
   ACCESS     not-accessible
   STATUS     mandatory
   DESCRIPTION
     "An entry in the mscFrNniFrmToIfByQueueTable."
   INDEX {
      mscFrNniIndex,
      mscFrNniFrmToIfByQueueIndex }
::= { mscFrNniFrmToIfByQueueTable 1 }

MscFrNniFrmToIfByQueueEntry ::= SEQUENCE {
   mscFrNniFrmToIfByQueueIndex
      Integer32,
   mscFrNniFrmToIfByQueueValue
      Unsigned32 }

mscFrNniFrmToIfByQueueIndex OBJECT-TYPE
   SYNTAX     Integer32 (0..3)
   ACCESS     not-accessible
   STATUS     mandatory
   DESCRIPTION
     "This variable represents the index for the mscFrNniFrmToIfByQueueTable."
::= { mscFrNniFrmToIfByQueueEntry 1 }

mscFrNniFrmToIfByQueueValue OBJECT-TYPE
   SYNTAX     Unsigned32 (0..4294967295)
   ACCESS     read-only
   STATUS     mandatory
   DESCRIPTION
     "This variable represents an individual value for the
      mscFrNniFrmToIfByQueueTable."
::= { mscFrNniFrmToIfByQueueEntry 2 }

mscFrNniOctetToIfByQueueTable OBJECT-TYPE
   SYNTAX     SEQUENCE OF MscFrNniOctetToIfByQueueEntry
   ACCESS     not-accessible
   STATUS     mandatory
   DESCRIPTION
     "This attribute counts the total number of octets transmitted from the 
      service to the interface per emission priority queue since the 
      component has been activated. There is potientially a maximum of 
      4 emission priority queues. The number of available egress queues 
      varies according to the value of the provisionable attribute 
      numberOfEmissionQs. Egress queue 0 has the lowest priority, while 
      egress queue 3 has the highest priority."
::= { mscFrNni 342 }

mscFrNniOctetToIfByQueueEntry OBJECT-TYPE
   SYNTAX     MscFrNniOctetToIfByQueueEntry
   ACCESS     not-accessible
   STATUS     mandatory
   DESCRIPTION
     "An entry in the mscFrNniOctetToIfByQueueTable."
   INDEX {
      mscFrNniIndex,
      mscFrNniOctetToIfByQueueIndex }
::= { mscFrNniOctetToIfByQueueTable 1 }

MscFrNniOctetToIfByQueueEntry ::= SEQUENCE {
   mscFrNniOctetToIfByQueueIndex
      Integer32,
   mscFrNniOctetToIfByQueueValue
      Unsigned32 }

mscFrNniOctetToIfByQueueIndex OBJECT-TYPE
   SYNTAX     Integer32 (0..3)
   ACCESS     not-accessible
   STATUS     mandatory
   DESCRIPTION
     "This variable represents the index for the mscFrNniOctetToIfByQueueTable."
::= { mscFrNniOctetToIfByQueueEntry 1 }

mscFrNniOctetToIfByQueueValue OBJECT-TYPE
   SYNTAX     Unsigned32 (0..4294967295)
   ACCESS     read-only
   STATUS     mandatory
   DESCRIPTION
     "This variable represents an individual value for the
      mscFrNniOctetToIfByQueueTable."
::= { mscFrNniOctetToIfByQueueEntry 2 }


-- This group contains a superset of all attributes which may apply to a 
-- VC. Particular applications will typically offer only a subset of 
-- these attributes by providing a definition of their own DNA 
-- subcomponent. 

mscFrNniDna OBJECT IDENTIFIER ::= { mscFrNni 2 }



mscFrNniDnaRowStatusTable OBJECT-TYPE
   SYNTAX     SEQUENCE OF MscFrNniDnaRowStatusEntry
   ACCESS     not-accessible
   STATUS     mandatory
   DESCRIPTION
     "This entry controls the addition and deletion of 
      mscFrNniDna components."
::= { mscFrNniDna 1 }

mscFrNniDnaRowStatusEntry OBJECT-TYPE
   SYNTAX     MscFrNniDnaRowStatusEntry
   ACCESS     not-accessible
   STATUS     mandatory
   DESCRIPTION
     "A single entry in the table represents a single 
      mscFrNniDna component."
   INDEX {
      mscFrNniIndex,
      mscFrNniDnaIndex }
::= { mscFrNniDnaRowStatusTable 1 }

MscFrNniDnaRowStatusEntry ::= SEQUENCE {
   mscFrNniDnaRowStatus
      RowStatus,
   mscFrNniDnaComponentName
      DisplayString,
   mscFrNniDnaStorageType
      StorageType,
   mscFrNniDnaIndex
      NonReplicated }

mscFrNniDnaRowStatus OBJECT-TYPE
   SYNTAX     RowStatus 
   ACCESS     read-only
   STATUS     mandatory
   DESCRIPTION
     "This variable is used as the basis for SNMP naming of
      mscFrNniDna components.
      These components cannot be added nor deleted."
::= { mscFrNniDnaRowStatusEntry 1 }

mscFrNniDnaComponentName OBJECT-TYPE
   SYNTAX     DisplayString 
   ACCESS     read-only
   STATUS     mandatory
   DESCRIPTION
     "This variable provides the component's string name for
      use with the ASCII Console Interface"
::= { mscFrNniDnaRowStatusEntry 2 }

mscFrNniDnaStorageType OBJECT-TYPE
   SYNTAX     StorageType 
   ACCESS     read-only
   STATUS     mandatory
   DESCRIPTION
     "This variable represents the storage type value for the
      mscFrNniDna tables."
::= { mscFrNniDnaRowStatusEntry 4 }

mscFrNniDnaIndex OBJECT-TYPE
   SYNTAX     NonReplicated 
   ACCESS     not-accessible
   STATUS     mandatory
   DESCRIPTION
     "This variable represents the index for the mscFrNniDna tables."
::= { mscFrNniDnaRowStatusEntry 10 }

mscFrNniDnaAddressTable OBJECT-TYPE
   SYNTAX     SEQUENCE OF MscFrNniDnaAddressEntry
   ACCESS     not-accessible
   STATUS     mandatory
   DESCRIPTION
     "This group contains attributes common to all DNAs. Every DNA 
      used in the network is defined with this group of 2 attributes."
::= { mscFrNniDna 10 }

mscFrNniDnaAddressEntry OBJECT-TYPE
   SYNTAX     MscFrNniDnaAddressEntry
   ACCESS     not-accessible
   STATUS     mandatory
   DESCRIPTION
     "An entry in the mscFrNniDnaAddressTable."
   INDEX {
      mscFrNniIndex,
      mscFrNniDnaIndex }
::= { mscFrNniDnaAddressTable 1 }

MscFrNniDnaAddressEntry ::= SEQUENCE {
   mscFrNniDnaNumberingPlanIndicator
      INTEGER,
   mscFrNniDnaDataNetworkAddress
      DigitString }

mscFrNniDnaNumberingPlanIndicator OBJECT-TYPE
   SYNTAX     INTEGER  {
                 x121(0),
                 e164(1) }
   ACCESS     read-write
   STATUS     mandatory
   DESCRIPTION
     "This attribute indicates the Numbering Plan Indicator (NPI) of the 
      DNA that is entered. Address may belong to X.121 or E.164 plans. 
      X.121 is used in packet switched data networks."
   DEFVAL     { x121 }
::= { mscFrNniDnaAddressEntry 1 }

mscFrNniDnaDataNetworkAddress OBJECT-TYPE
   SYNTAX     DigitString (SIZE (1..15))
   ACCESS     read-write
   STATUS     mandatory
   DESCRIPTION
     "This attribute indicates the customer's unique identifier. It is the 
      equivalent of the telephone number in the telephone network."
::= { mscFrNniDnaAddressEntry 2 }

mscFrNniDnaOutgoingOptionsTable OBJECT-TYPE
   SYNTAX     SEQUENCE OF MscFrNniDnaOutgoingOptionsEntry
   ACCESS     not-accessible
   STATUS     mandatory
   DESCRIPTION
     "This group defines DNA call options for calls made from the 
      interface. These options are not used for calls arriving to the 
      interface represented by this DNA."
::= { mscFrNniDna 11 }

mscFrNniDnaOutgoingOptionsEntry OBJECT-TYPE
   SYNTAX     MscFrNniDnaOutgoingOptionsEntry
   ACCESS     not-accessible
   STATUS     mandatory
   DESCRIPTION
     "An entry in the mscFrNniDnaOutgoingOptionsTable."
   INDEX {
      mscFrNniIndex,
      mscFrNniDnaIndex }
::= { mscFrNniDnaOutgoingOptionsTable 1 }

MscFrNniDnaOutgoingOptionsEntry ::= SEQUENCE {
   mscFrNniDnaOutDefaultPriority
      INTEGER,
   mscFrNniDnaOutDefaultPathSensitivity
      INTEGER,
   mscFrNniDnaOutPathSensitivityOverRide
      INTEGER,
   mscFrNniDnaOutDefaultPathReliability
      INTEGER,
   mscFrNniDnaOutAccess
      INTEGER,
   mscFrNniDnaDefaultTransferPriority
      INTEGER,
   mscFrNniDnaTransferPriorityOverRide
      INTEGER }

mscFrNniDnaOutDefaultPriority OBJECT-TYPE
   SYNTAX     INTEGER  {
                 normal(0),
                 high(1) }
   ACCESS     read-write
   STATUS     mandatory
   DESCRIPTION
     "This attribute indicates the default priority of outgoing calls from 
      the DTE to the network.
      
      It can be overridden by the discardPriority under DLCI Direct Call 
      subcomponent.
      
      This option can be also included in X.25 signalling, in such case it 
      will be overruled."
   DEFVAL     { normal }
::= { mscFrNniDnaOutgoingOptionsEntry 7 }

mscFrNniDnaOutDefaultPathSensitivity OBJECT-TYPE
   SYNTAX     INTEGER  {
                 throughput(0),
                 delay(1) }
   ACCESS     read-write
   STATUS     obsolete
   DESCRIPTION
     "This attribute specifies the default class of path sensitivity to 
      network for all outgoing calls that use this DNA. The chosen default 
      class of path sensitivity applies to all outgoing calls established 
      using this DNA. 
      
      This attribute, if set to throughput, indicates that the default class is 
      throughput sensitive. If set to delay, then the default class is delay 
      sensitive. The default of outDefaultPathSensitivity is throughput."
   DEFVAL     { throughput }
::= { mscFrNniDnaOutgoingOptionsEntry 11 }

mscFrNniDnaOutPathSensitivityOverRide OBJECT-TYPE
   SYNTAX     INTEGER  {
                 no(0),
                 yes(1) }
   ACCESS     read-write
   STATUS     obsolete
   DESCRIPTION
     "If this attribute is set to yes in the call request, the called end will 
      use the calling end provisioning data on path sensitivity to override 
      its own provisioning data.
      
      The default of outPathSensitivityOverRide is yes."
   DEFVAL     { yes }
::= { mscFrNniDnaOutgoingOptionsEntry 12 }

mscFrNniDnaOutDefaultPathReliability OBJECT-TYPE
   SYNTAX     INTEGER  {
                 high(0),
                 normal(1) }
   ACCESS     read-write
   STATUS     mandatory
   DESCRIPTION
     "This attribute specifies the default class of routing for reliability 
      routing for all outgoing calls (from the DTE to the network) using 
      this particular DNA. The chosen default class of routing applies to 
      all outgoing calls established using this DNA, and applies to the 
      packets travelling in both directions on all outgoing calls (local to 
      remote, and remote to local). For incoming calls, the default class of 
      routing is chosen by the calling party (as opposed to DPN, where 
      either end of the call can choose the default routing class).
      This attribute, if set to a value of normal, indicates that the default 
      class of routing is normal reliability routing. If set to a value of 
      high, then the default class of routing is high reliability routing.
      High reliability is the standard choice for most DPN and Passport 
      services. It usually indicates that packets are overflowed or 
      retransmitted at various routing levels. Typically high reliability 
      results in duplication and disordering of packets in the network 
      when errors are detected or during link congestion. However, the 
      VC handles the duplication and disordering to ensure that packets 
      are delivered to the DTE properly.
      For the Frame Relay service, duplication of packets is not desired, 
      in which case, normal reliability may be chosen as the preferred 
      class of routing."
   DEFVAL     { normal }
::= { mscFrNniDnaOutgoingOptionsEntry 14 }

mscFrNniDnaOutAccess OBJECT-TYPE
   SYNTAX     INTEGER  {
                 disallowed(0),
                 allowed(1) }
   ACCESS     read-write
   STATUS     obsolete
   DESCRIPTION
     "This attribute is an extension of the Closed User Group (CUG) 
      facility, as follows:
      This attribute, if set to a value of allowed indicates that outgoing 
      calls (from the DTE to the network) to the open (non-CUG) part of 
      the network are permitted. It also permits outgoing calls to DTEs 
      that have Incoming Access capabilities. If set to a value of 
      disallowed, then such calls cannot be made using this DNA. Such 
      calls will be cleared by the local DCE.
      This attribute corresponds to the ITU-T 'Closed User Group with 
      Outgoing Access' feature for DNAs in that outgoing access is 
      granted if this attribute is set to a value of allowed."
   DEFVAL     { disallowed }
::= { mscFrNniDnaOutgoingOptionsEntry 17 }

mscFrNniDnaDefaultTransferPriority OBJECT-TYPE
   SYNTAX     INTEGER  {
                 n0(0),
                 n1(1),
                 n2(2),
                 n3(3),
                 n4(4),
                 n5(5),
                 n6(6),
                 n7(7),
                 n8(8),
                 n9(9),
                 n10(10),
                 n11(11),
                 n12(12),
                 n13(13),
                 n14(14),
                 n15(15) }
   ACCESS     read-write
   STATUS     mandatory
   DESCRIPTION
     "This attribute specifies the default transfer priority for all outgoing 
      calls using this particular DNA. It can be overridden by the 
      transferPriority provisioned in the Dlci DirectCall sub-component.
      
      The transfer priority is a preference configured for an application 
      according to its delay-sensitivity requirement. Frames with higher 
      transfer priority are served by the network before the frames with 
      lower priority. The transfer priority standard is defined to have 16 
      levels from 0 to 15.
      
      Each transfer priority n, where n indicates the transfer priority 
      index, contains a default setting for routing class of service 
      (multimedia, delay or throughput) and frame relay egress queue 
      (depending on the number of supported egress queues on the remote 
      end interface) specified by the routingClassOfService and 
      emissionPriority attributes provisioned in the Mod Frs DprsNet 
      Tpm/n component. The default mapping can be altered by a user if 
      required.
      
      The default defaultTransferPriority is 0."
   DEFVAL     { n0 }
::= { mscFrNniDnaOutgoingOptionsEntry 18 }

mscFrNniDnaTransferPriorityOverRide OBJECT-TYPE
   SYNTAX     INTEGER  {
                 no(0),
                 yes(1) }
   ACCESS     read-write
   STATUS     mandatory
   DESCRIPTION
     "When this attribute is set to yes in the call request, the called end 
      will use the calling end provisioning data on transfer priority to 
      override its own provisioning data. If it is set no, the called end 
      will use its own provisioning data on transfer priority.
      
      This attribute is not applicable for Frame Relay SVCs.
      
      For more information about transfer priority, please refer to the 
      previous attribute defaultTransferPriority.
      
      The default of transferPriorityOverRide is yes."
   DEFVAL     { yes }
::= { mscFrNniDnaOutgoingOptionsEntry 19 }

mscFrNniDnaIncomingOptionsTable OBJECT-TYPE
   SYNTAX     SEQUENCE OF MscFrNniDnaIncomingOptionsEntry
   ACCESS     not-accessible
   STATUS     mandatory
   DESCRIPTION
     "This group defines options for incoming calls. These options are 
      used for calls arriving to the interface represented by this DNA. For 
      calls originated from the interface, IncomingOptions attributes are 
      not used."
::= { mscFrNniDna 12 }

mscFrNniDnaIncomingOptionsEntry OBJECT-TYPE
   SYNTAX     MscFrNniDnaIncomingOptionsEntry
   ACCESS     not-accessible
   STATUS     mandatory
   DESCRIPTION
     "An entry in the mscFrNniDnaIncomingOptionsTable."
   INDEX {
      mscFrNniIndex,
      mscFrNniDnaIndex }
::= { mscFrNniDnaIncomingOptionsTable 1 }

MscFrNniDnaIncomingOptionsEntry ::= SEQUENCE {
   mscFrNniDnaIncAccess
      INTEGER }

mscFrNniDnaIncAccess OBJECT-TYPE
   SYNTAX     INTEGER  {
                 disallowed(0),
                 allowed(1) }
   ACCESS     read-write
   STATUS     obsolete
   DESCRIPTION
     "This attribute, if set to a value of allowed specifies that incoming 
      calls (from the network to the DTE) from the open (non-CUG) part 
      of the network are permitted. It also permits incoming calls from 
      DTEs that have outgoing access capabilities. If set to a value of 
      disallowed, such calls cannot be made to this DNA. They will be 
      cleared by the local DCE.
      This attribute corresponds to the CCITT 'Closed User Group with 
      Incoming Access' feature for DNAs in that incoming access is 
      granted if this attribute is set to a value of allowed."
   DEFVAL     { disallowed }
::= { mscFrNniDnaIncomingOptionsEntry 9 }

mscFrNniDnaCallOptionsTable OBJECT-TYPE
   SYNTAX     SEQUENCE OF MscFrNniDnaCallOptionsEntry
   ACCESS     not-accessible
   STATUS     mandatory
   DESCRIPTION
     "This group defines additional all options for not related to direction 
      of the call."
::= { mscFrNniDna 13 }

mscFrNniDnaCallOptionsEntry OBJECT-TYPE
   SYNTAX     MscFrNniDnaCallOptionsEntry
   ACCESS     not-accessible
   STATUS     mandatory
   DESCRIPTION
     "An entry in the mscFrNniDnaCallOptionsTable."
   INDEX {
      mscFrNniIndex,
      mscFrNniDnaIndex }
::= { mscFrNniDnaCallOptionsTable 1 }

MscFrNniDnaCallOptionsEntry ::= SEQUENCE {
   mscFrNniDnaAccountClass
      Unsigned32,
   mscFrNniDnaAccountCollection
      OCTET STRING,
   mscFrNniDnaServiceExchange
      Unsigned32,
   mscFrNniDnaEgressAccounting
      INTEGER,
   mscFrNniDnaDataPath
      INTEGER }

mscFrNniDnaAccountClass OBJECT-TYPE
   SYNTAX     Unsigned32 (0..255)
   ACCESS     read-write
   STATUS     mandatory
   DESCRIPTION
     "This attribute specifies the accounting class which is reserved for 
      network operations usage. Its value is returned in the accounting 
      record in the local and remote service type attributes. Use of this 
      attribute is decided by network operator.
      This attribute is returned by the local VC in the accounting record 
      for all calls that are set up using this particular DNA."
   DEFVAL     { 0 }
::= { mscFrNniDnaCallOptionsEntry 10 }

mscFrNniDnaAccountCollection OBJECT-TYPE
   SYNTAX     OCTET STRING (SIZE (1))
   ACCESS     read-write
   STATUS     mandatory
   DESCRIPTION
     "This attribute indicates that accounting records are to be collected 
      by the network for the various reasons: billing, test, study, auditing. 
      The last of the parameters, force, indicates that accounting records 
      are to be collected irrespective of other collection reasons. The 
      force option is available for X.75 Gateways only. If none of these 
      reasons are set, then accounting will be suppressed.
      To set a specific accounting collection reason, the reason is entered 
      and the corresponding bit in the structure is set to a value of 1. To 
      turn off a specific accounting collection reason, the reason is 
      entered preceded with the '~' character, and the corresponding bit in 
      the structure is set to a value of 0.
      The bit placement for the accounting collection reasons is as 
      follows:
      Bit 0  - Bill
      Bit 1  - Test
      Bit 2  - Study
      Bit 3  - Audit
      Bit 4  - Force

      Description of bits:
      bill(0)
      test(1)
      study(2)
      audit(3)
      force(4)"
   DEFVAL     { '80'H }
::= { mscFrNniDnaCallOptionsEntry 11 }

mscFrNniDnaServiceExchange OBJECT-TYPE
   SYNTAX     Unsigned32 (0..255)
   ACCESS     read-write
   STATUS     mandatory
   DESCRIPTION
     "This attribute is an arbitrary number, Data Service Exchange, as 
      entered by the network operator and reported in accounting record. 
      It is converted into an internal 8-bit integer value for use in the 
      accounting record as well as in various X.25 and X.75 Tariff 
      utilities."
   DEFVAL     { 0 }
::= { mscFrNniDnaCallOptionsEntry 12 }

mscFrNniDnaEgressAccounting OBJECT-TYPE
   SYNTAX     INTEGER  {
                 no(0),
                 yes(1) }
   ACCESS     read-write
   STATUS     mandatory
   DESCRIPTION
     "This attribute specifies if egress accounting is enabled by the frame 
      relay service. If egress accounting is disabled, only segment counts 
      are collected by the VC. No frame relay counts appear in the 
      accounting records for the frame relay service. If egress accounting 
      is enabled, the accounting records for the frame relay service will 
      contain frame relay specific counts."
   DEFVAL     { no }
::= { mscFrNniDnaCallOptionsEntry 13 }

mscFrNniDnaDataPath OBJECT-TYPE
   SYNTAX     INTEGER  {
                 dprsOnly(0),
                 dprsMcsOnly(1),
                 dprsMcsFirst(2) }
   ACCESS     read-write
   STATUS     mandatory
   DESCRIPTION
     "This attribute specifies the data path to be used by Virtual Circuits 
      on this interface. If the connection has a DirectCall component then 
      the value can be overridden by the dataPath attribute of the 
      DirectCall component.
      
      This value applies to the connection after data transfer state is 
      reached. All the data and control trafic will be sent using this data 
      path. If the provisioned dataPath is not available the connection is 
      not established.
      
      The value of the dataPath is signalled by both ends of the 
      connection. If this value is not the same at both ends dprsOnly is 
      used for the duration of the connection.
      
      A virtual circuit connection is always established using dprsOnly 
      even if this attribute is provisioned as some other value.
      
      dprsOnly - dynamic packet routing system is used
      
      dprsMcsOnly - dprs Multi-Service Cut-Through Switching path is 
      used.
      
      dprsMcsFirst - dprs Multi-Service Cut-Through Switching path is 
      used if it is available. If it is not avaliable dprsOnly is used."
   DEFVAL     { dprsOnly }
::= { mscFrNniDnaCallOptionsEntry 21 }


-- 
-- FrNni/n Dna ClosedUserGroup
-- This group defines options associated with national or international 
-- CUG Identifier. Other DNAs in the network can have CUGs defined 
-- which groups these DNAs by CUG interlockCode. If DNAs are 
-- defined with CUGs, calls from DNAs which do not have the same 
-- interlockCode defined are refused. Attributes incAccess and 
-- outAccess can override this rule.
-- 
-- A CUG is provisioned by default as a SELECTABLE CUG. If a 
-- SELECTABLE CUG is provisioned, the DTE can include a CUG 
-- facility in the call request. If it does, the DTE selects a specific 
-- CUG by signaling the CUG's index. A DTE can subscribe to as 
-- many as 256 SELECTABLE CUGs.
-- 
-- A SIMPLE CUG is provisioned by setting a SELECTABLE CUG's 
-- preferential attribute to the value yes. There are two prerequisites: a 
-- single SELECTABLE CUG must exist; its attributes incCalls and 
-- outCalls must both be set to allowed. If a SIMPLE CUG is 
-- provisioned, it is the default CUG used to establish a call when the 
-- call request sent by the DTE does not include any CUG facility. If 
-- the DTE includes any CUG facility in the call request, the call is 
-- cleared. A DTE subscribing to a SIMPLE CUG cannot subscribe to 
-- any other CUG.

mscFrNniDnaCug OBJECT IDENTIFIER ::= { mscFrNniDna 2 }



mscFrNniDnaCugRowStatusTable OBJECT-TYPE
   SYNTAX     SEQUENCE OF MscFrNniDnaCugRowStatusEntry
   ACCESS     not-accessible
   STATUS     obsolete
   DESCRIPTION
     "This entry controls the addition and deletion of 
      mscFrNniDnaCug components."
::= { mscFrNniDnaCug 1 }

mscFrNniDnaCugRowStatusEntry OBJECT-TYPE
   SYNTAX     MscFrNniDnaCugRowStatusEntry
   ACCESS     not-accessible
   STATUS     obsolete
   DESCRIPTION
     "A single entry in the table represents a single 
      mscFrNniDnaCug component."
   INDEX {
      mscFrNniIndex,
      mscFrNniDnaIndex,
      mscFrNniDnaCugIndex }
::= { mscFrNniDnaCugRowStatusTable 1 }

MscFrNniDnaCugRowStatusEntry ::= SEQUENCE {
   mscFrNniDnaCugRowStatus
      RowStatus,
   mscFrNniDnaCugComponentName
      DisplayString,
   mscFrNniDnaCugStorageType
      StorageType,
   mscFrNniDnaCugIndex
      Integer32 }

mscFrNniDnaCugRowStatus OBJECT-TYPE
   SYNTAX     RowStatus 
   ACCESS     read-write
   STATUS     obsolete
   DESCRIPTION
     "This variable is used as the basis for SNMP naming of
      mscFrNniDnaCug components.
      These components can be added and deleted."
::= { mscFrNniDnaCugRowStatusEntry 1 }

mscFrNniDnaCugComponentName OBJECT-TYPE
   SYNTAX     DisplayString 
   ACCESS     read-only
   STATUS     obsolete
   DESCRIPTION
     "This variable provides the component's string name for
      use with the ASCII Console Interface"
::= { mscFrNniDnaCugRowStatusEntry 2 }

mscFrNniDnaCugStorageType OBJECT-TYPE
   SYNTAX     StorageType 
   ACCESS     read-only
   STATUS     obsolete
   DESCRIPTION
     "This variable represents the storage type value for the
      mscFrNniDnaCug tables."
::= { mscFrNniDnaCugRowStatusEntry 4 }

mscFrNniDnaCugIndex OBJECT-TYPE
   SYNTAX     Integer32 (0..255)
   ACCESS     not-accessible
   STATUS     obsolete
   DESCRIPTION
     "This variable represents the index for the mscFrNniDnaCug tables."
::= { mscFrNniDnaCugRowStatusEntry 10 }

mscFrNniDnaCugCugOptionsTable OBJECT-TYPE
   SYNTAX     SEQUENCE OF MscFrNniDnaCugCugOptionsEntry
   ACCESS     not-accessible
   STATUS     obsolete
   DESCRIPTION
     "Attributes in this group define ClosedUserGroup options associated 
      with interlockCode. DNA's with the same CUG (interlockCode) can 
      make calls within this group. Various combinations which permit or 
      prevent calls in the same CUG group are defined here."
::= { mscFrNniDnaCug 10 }

mscFrNniDnaCugCugOptionsEntry OBJECT-TYPE
   SYNTAX     MscFrNniDnaCugCugOptionsEntry
   ACCESS     not-accessible
   STATUS     obsolete
   DESCRIPTION
     "An entry in the mscFrNniDnaCugCugOptionsTable."
   INDEX {
      mscFrNniIndex,
      mscFrNniDnaIndex,
      mscFrNniDnaCugIndex }
::= { mscFrNniDnaCugCugOptionsTable 1 }

MscFrNniDnaCugCugOptionsEntry ::= SEQUENCE {
   mscFrNniDnaCugType
      INTEGER,
   mscFrNniDnaCugDnic
      DigitString,
   mscFrNniDnaCugInterlockCode
      Unsigned32,
   mscFrNniDnaCugPreferential
      INTEGER,
   mscFrNniDnaCugOutCalls
      INTEGER,
   mscFrNniDnaCugIncCalls
      INTEGER }

mscFrNniDnaCugType OBJECT-TYPE
   SYNTAX     INTEGER  {
                 national(0),
                 international(1) }
   ACCESS     read-write
   STATUS     obsolete
   DESCRIPTION
     "This attribute specifies the CUG type - the CUG is either a national 
      CUG, or an international CUG. International closed user groups are 
      usually established between DTEs for which there is an X.75 
      Gateway between; whereas national closed user groups are usually 
      established between DTEs for which there is no X.75 Gateway 
      between. (National CUGs cannot normally traverse an X.75 
      Gateway).
      If this attribute is set to national, then the CUG is a national CUG, 
      in which case, the dnic should be left at its default value since it is 
      not part of a national CUG. If this attribute is set to international, 
      then the CUG is an international CUG, in which case, the dnic 
      should be set appropriately as part of the CUG interlockCode."
   DEFVAL     { national }
::= { mscFrNniDnaCugCugOptionsEntry 1 }

mscFrNniDnaCugDnic OBJECT-TYPE
   SYNTAX     DigitString (SIZE (4))
   ACCESS     read-write
   STATUS     obsolete
   DESCRIPTION
     "This attribute specifies the dnic (Data Network ID Code) of the 
      CUG by which packet networks are identified. This attribute is not 
      applicable if the CUG is a national CUG, as specified by the CUG 
      type attribute. There are usually 1 or 2 dnics assigned per country, 
      for public networks. The U.S. is an exception where each BOC has 
      a dnic. Also, a group of private networks can have its own dnic.
      
      dnic value is not an arbitrary number. It is assigned by international 
      agreement and controlled by CCITT."
   DEFVAL     { '30303030'H }  -- "0000"
::= { mscFrNniDnaCugCugOptionsEntry 2 }

mscFrNniDnaCugInterlockCode OBJECT-TYPE
   SYNTAX     Unsigned32 (0..65535)
   ACCESS     read-write
   STATUS     obsolete
   DESCRIPTION
     "This attribute specifies the CUG identifier of a national or 
      international CUG call. It is an arbitrary number and it also can be 
      called CUG in some descriptions. Interfaces (DNA's) defined with 
      this number can make calls to DNA's with the same interlockCode."
   DEFVAL     { 65535 }
::= { mscFrNniDnaCugCugOptionsEntry 3 }

mscFrNniDnaCugPreferential OBJECT-TYPE
   SYNTAX     INTEGER  {
                 no(0),
                 yes(1) }
   ACCESS     read-write
   STATUS     obsolete
   DESCRIPTION
     "The attribute 'preferential', if set to yes indicates that this CUG is 
      the SIMPLE CUG (as defined in ITU X.36 [10/96]), in which case 
      it will be used during the call establishment phase if the DTE has 
      not explicitly specified a CUG index in the call request packet. If set 
      to no, then this CUG is not the SIMPLE CUG, but an instance of 
      the SELECTABLE CUG.
      
      The attribute 'preferential' is set to no by CAS when a CUG 
      instance is created. If only one CUG instance exists under a DNA, 
      and if this CUG's attributes 'incCalls' and 'outCall' are both set to 
      allowed, then this CUG instance can be changed to a SIMPLE CUG 
      by setting the attribute 'preferential' to yes. If more than one CUG 
      instances exist under a DNA, none of the CUGs can be set by the 
      user as 'preferential'. Essentially, the attribute 'preferential' 
      distinguishes a SIMPLE CUG from a SELECTABLE CUG.
      
      In the case of a FRUNI DNA with a single CUG instance, the CUG 
      can be a SIMPLE CUG (preferential = yes) or the only instance of a 
      SELECTABLE CUG (preferential = no)."
   DEFVAL     { no }
::= { mscFrNniDnaCugCugOptionsEntry 4 }

mscFrNniDnaCugOutCalls OBJECT-TYPE
   SYNTAX     INTEGER  {
                 disallowed(0),
                 allowed(1) }
   ACCESS     read-write
   STATUS     obsolete
   DESCRIPTION
     "This attribute, if set to allowed indicates that outgoing calls (from 
      the DTE into the network) can be made using this particular CUG. 
      If set to a value of disallowed, then outgoing calls cannot be made 
      using this CUG - such calls will be cleared by the local DCE.
      This attribute corresponds to the CCITT 'Outgoing Calls Barred' 
      feature for CUGs in that outgoing calls are barred if this attribute is 
      set to a value of disallowed."
   DEFVAL     { allowed }
::= { mscFrNniDnaCugCugOptionsEntry 5 }

mscFrNniDnaCugIncCalls OBJECT-TYPE
   SYNTAX     INTEGER  {
                 disallowed(0),
                 allowed(1) }
   ACCESS     read-write
   STATUS     obsolete
   DESCRIPTION
     "This attribute, if set to allowed indicates that incoming calls (from 
      the network to the DTE) can be made using this particular CUG. If 
      set to disallowed, then incoming calls cannot be made using this 
      CUG - such calls will be cleared by the local DCE.
      This attribute corresponds to the CCITT 'Incoming Calls Barred' 
      feature for CUGs in that incoming calls are barred if this attribute is 
      set to a value of disallowed."
   DEFVAL     { allowed }
::= { mscFrNniDnaCugCugOptionsEntry 6 }


-- FrNni/n Dna HuntGroupMember
-- This component specifies the interaction of this DNA with one or 
-- more hunt groups to which it is expected to belong.
-- Note that is not possible to automatically verify the consistency of 
-- the hunt group membership specified under this component with the 
-- hunt group provisioning on the DPN Hunt Group Server(s).

mscFrNniDnaHgM OBJECT IDENTIFIER ::= { mscFrNniDna 3 }



mscFrNniDnaHgMRowStatusTable OBJECT-TYPE
   SYNTAX     SEQUENCE OF MscFrNniDnaHgMRowStatusEntry
   ACCESS     not-accessible
   STATUS     mandatory
   DESCRIPTION
     "This entry controls the addition and deletion of 
      mscFrNniDnaHgM components."
::= { mscFrNniDnaHgM 1 }

mscFrNniDnaHgMRowStatusEntry OBJECT-TYPE
   SYNTAX     MscFrNniDnaHgMRowStatusEntry
   ACCESS     not-accessible
   STATUS     mandatory
   DESCRIPTION
     "A single entry in the table represents a single 
      mscFrNniDnaHgM component."
   INDEX {
      mscFrNniIndex,
      mscFrNniDnaIndex,
      mscFrNniDnaHgMIndex }
::= { mscFrNniDnaHgMRowStatusTable 1 }

MscFrNniDnaHgMRowStatusEntry ::= SEQUENCE {
   mscFrNniDnaHgMRowStatus
      RowStatus,
   mscFrNniDnaHgMComponentName
      DisplayString,
   mscFrNniDnaHgMStorageType
      StorageType,
   mscFrNniDnaHgMIndex
      NonReplicated }

mscFrNniDnaHgMRowStatus OBJECT-TYPE
   SYNTAX     RowStatus 
   ACCESS     read-write
   STATUS     mandatory
   DESCRIPTION
     "This variable is used as the basis for SNMP naming of
      mscFrNniDnaHgM components.
      These components can be added and deleted."
::= { mscFrNniDnaHgMRowStatusEntry 1 }

mscFrNniDnaHgMComponentName OBJECT-TYPE
   SYNTAX     DisplayString 
   ACCESS     read-only
   STATUS     mandatory
   DESCRIPTION
     "This variable provides the component's string name for
      use with the ASCII Console Interface"
::= { mscFrNniDnaHgMRowStatusEntry 2 }

mscFrNniDnaHgMStorageType OBJECT-TYPE
   SYNTAX     StorageType 
   ACCESS     read-only
   STATUS     mandatory
   DESCRIPTION
     "This variable represents the storage type value for the
      mscFrNniDnaHgM tables."
::= { mscFrNniDnaHgMRowStatusEntry 4 }

mscFrNniDnaHgMIndex OBJECT-TYPE
   SYNTAX     NonReplicated 
   ACCESS     not-accessible
   STATUS     mandatory
   DESCRIPTION
     "This variable represents the index for the mscFrNniDnaHgM tables."
::= { mscFrNniDnaHgMRowStatusEntry 10 }

mscFrNniDnaHgMIfTable OBJECT-TYPE
   SYNTAX     SEQUENCE OF MscFrNniDnaHgMIfEntry
   ACCESS     not-accessible
   STATUS     mandatory
   DESCRIPTION
     "This group contains the interface parameters between the 
      HuntGroupMember and the hunt group server."
::= { mscFrNniDnaHgM 10 }

mscFrNniDnaHgMIfEntry OBJECT-TYPE
   SYNTAX     MscFrNniDnaHgMIfEntry
   ACCESS     not-accessible
   STATUS     mandatory
   DESCRIPTION
     "An entry in the mscFrNniDnaHgMIfTable."
   INDEX {
      mscFrNniIndex,
      mscFrNniDnaIndex,
      mscFrNniDnaHgMIndex }
::= { mscFrNniDnaHgMIfTable 1 }

MscFrNniDnaHgMIfEntry ::= SEQUENCE {
   mscFrNniDnaHgMAvailabilityUpdateThreshold
      Unsigned32 }

mscFrNniDnaHgMAvailabilityUpdateThreshold OBJECT-TYPE
   SYNTAX     Unsigned32 (2048..16777216)
   ACCESS     read-write
   STATUS     mandatory
   DESCRIPTION
     "This attribute specifies how much availableAggregateCIR can 
      change before an Availability Message Packet (AMP) is sent to the 
      hunt group server informing it of the change.
      If the value specified is not a multiple of 2048, the value actually 
      used as the threshold will be the next higher multiple of 2048."
   DEFVAL     { 8192 }
::= { mscFrNniDnaHgMIfEntry 1 }

mscFrNniDnaHgMOpTable OBJECT-TYPE
   SYNTAX     SEQUENCE OF MscFrNniDnaHgMOpEntry
   ACCESS     not-accessible
   STATUS     mandatory
   DESCRIPTION
     "This group contains the operational attributes of the 
      HuntGroupMember component."
::= { mscFrNniDnaHgM 11 }

mscFrNniDnaHgMOpEntry OBJECT-TYPE
   SYNTAX     MscFrNniDnaHgMOpEntry
   ACCESS     not-accessible
   STATUS     mandatory
   DESCRIPTION
     "An entry in the mscFrNniDnaHgMOpTable."
   INDEX {
      mscFrNniIndex,
      mscFrNniDnaIndex,
      mscFrNniDnaHgMIndex }
::= { mscFrNniDnaHgMOpTable 1 }

MscFrNniDnaHgMOpEntry ::= SEQUENCE {
   mscFrNniDnaHgMMaximumAvailableAggregateCir
      Unsigned32,
   mscFrNniDnaHgMAvailableAggregateCir
      Unsigned32,
   mscFrNniDnaHgMAvailabilityDelta
      INTEGER,
   mscFrNniDnaHgMAvailableDlcis
      Unsigned32,
   mscFrNniDnaHgMMaximumAvailableAggregateCir64
      Unsigned64,
   mscFrNniDnaHgMAvailableAggregateCir64
      Unsigned64 }

mscFrNniDnaHgMMaximumAvailableAggregateCir OBJECT-TYPE
   SYNTAX     Unsigned32 (0..4294967295)
   ACCESS     read-only
   STATUS     obsolete
   DESCRIPTION
     "This attribute indicates the maximum available bandwidth for this 
      hunt group member. This value represents the total sum of the 
      sixteen egress bandwidth pools. It is the sum of the sixteen indices 
      of the FrNni Ca egressBandwidthPool attribute multiplied by the 
      link speed."
::= { mscFrNniDnaHgMOpEntry 1 }

mscFrNniDnaHgMAvailableAggregateCir OBJECT-TYPE
   SYNTAX     Unsigned32 (0..4294967295)
   ACCESS     read-only
   STATUS     obsolete
   DESCRIPTION
     "This attribute indicates the current total available bandwidth 
      reported to the hunt group server in the Availability Message Packet 
      (AMP). This value represents the sum of the sixteen currently 
      available egress bandwidth pools. It is the sum of the sixteen indices 
      of the FrNni Ca egressPoolAvailableBandwidth attribute. 
      It increments when a connection is released. 
      It decrements when a connection is accepted.
      Both this attribute and the availableDlcis attribute must be non zero 
      for this interface to receive calls on a hunt group."
::= { mscFrNniDnaHgMOpEntry 2 }

mscFrNniDnaHgMAvailabilityDelta OBJECT-TYPE
   SYNTAX     INTEGER (-16777216..16777215)
   ACCESS     read-only
   STATUS     mandatory
   DESCRIPTION
     "This attribute indicates the net change in the available aggregate 
      CIR since the last Availability Message Packet (AMP) was sent to 
      the Hunt Group. Once the absolute value of this attribute reaches 
      the availabilityUpdateThreshold an AMP is sent to the hunt group 
      server(s) and the availabilityDelta is re-computed."
::= { mscFrNniDnaHgMOpEntry 3 }

mscFrNniDnaHgMAvailableDlcis OBJECT-TYPE
   SYNTAX     Unsigned32 (0..4096)
   ACCESS     read-only
   STATUS     mandatory
   DESCRIPTION
     "This attribute indicates the number of DLCIs available for SVCs on 
      the interface associated with this DNA. If this value reaches 0, an 
      AMP with zero availability is sent to the hunt group server(s).
      Both this attribute and the availableAggregateCir attribute must be 
      non zero for this DNA to receive calls on the hunt group."
::= { mscFrNniDnaHgMOpEntry 5 }

mscFrNniDnaHgMMaximumAvailableAggregateCir64 OBJECT-TYPE
   SYNTAX     Unsigned64 (SIZE (8))
   ACCESS     read-only
   STATUS     mandatory
   DESCRIPTION
     "This attribute indicates the maximum available bandwidth for this 
      hunt group member. This value represents the total sum of the 
      sixteen egress bandwidth pools. It is the sum of the sixteen indices 
      of the FrNni Ca egressBandwidthPool attribute multiplied by the 
      link speed."
::= { mscFrNniDnaHgMOpEntry 6 }

mscFrNniDnaHgMAvailableAggregateCir64 OBJECT-TYPE
   SYNTAX     Unsigned64 (SIZE (8))
   ACCESS     read-only
   STATUS     mandatory
   DESCRIPTION
     "This attribute indicates the current total available bandwidth 
      reported to the hunt group server in the Availability Message Packet 
      (AMP). This value represents the sum of the sixteen currently 
      available egress bandwidth pools. It is the sum of the sixteen indices 
      of the FrNni Ca egressPoolAvailableBandwidth attribute. 
      It increments when a connection is released. 
      It decrements when a connection is accepted.
      Both this attribute and the availableDlcis attribute must be non zero 
      for this interface to receive calls on a hunt group."
::= { mscFrNniDnaHgMOpEntry 7 }


-- FrNni/n Dna HgM HuntGroupAddress/n
-- This component specifies a hunt group address to which this 
-- member belongs. A hunt group member belongs to at least one hunt 
-- group.

mscFrNniDnaHgMHgAddr OBJECT IDENTIFIER ::= { mscFrNniDnaHgM 2 }



mscFrNniDnaHgMHgAddrRowStatusTable OBJECT-TYPE
   SYNTAX     SEQUENCE OF MscFrNniDnaHgMHgAddrRowStatusEntry
   ACCESS     not-accessible
   STATUS     mandatory
   DESCRIPTION
     "This entry controls the addition and deletion of 
      mscFrNniDnaHgMHgAddr components."
::= { mscFrNniDnaHgMHgAddr 1 }

mscFrNniDnaHgMHgAddrRowStatusEntry OBJECT-TYPE
   SYNTAX     MscFrNniDnaHgMHgAddrRowStatusEntry
   ACCESS     not-accessible
   STATUS     mandatory
   DESCRIPTION
     "A single entry in the table represents a single 
      mscFrNniDnaHgMHgAddr component."
   INDEX {
      mscFrNniIndex,
      mscFrNniDnaIndex,
      mscFrNniDnaHgMIndex,
      mscFrNniDnaHgMHgAddrIndex }
::= { mscFrNniDnaHgMHgAddrRowStatusTable 1 }

MscFrNniDnaHgMHgAddrRowStatusEntry ::= SEQUENCE {
   mscFrNniDnaHgMHgAddrRowStatus
      RowStatus,
   mscFrNniDnaHgMHgAddrComponentName
      DisplayString,
   mscFrNniDnaHgMHgAddrStorageType
      StorageType,
   mscFrNniDnaHgMHgAddrIndex
      Integer32 }

mscFrNniDnaHgMHgAddrRowStatus OBJECT-TYPE
   SYNTAX     RowStatus 
   ACCESS     read-write
   STATUS     mandatory
   DESCRIPTION
     "This variable is used as the basis for SNMP naming of
      mscFrNniDnaHgMHgAddr components.
      These components can be added and deleted."
::= { mscFrNniDnaHgMHgAddrRowStatusEntry 1 }

mscFrNniDnaHgMHgAddrComponentName OBJECT-TYPE
   SYNTAX     DisplayString 
   ACCESS     read-only
   STATUS     mandatory
   DESCRIPTION
     "This variable provides the component's string name for
      use with the ASCII Console Interface"
::= { mscFrNniDnaHgMHgAddrRowStatusEntry 2 }

mscFrNniDnaHgMHgAddrStorageType OBJECT-TYPE
   SYNTAX     StorageType 
   ACCESS     read-only
   STATUS     mandatory
   DESCRIPTION
     "This variable represents the storage type value for the
      mscFrNniDnaHgMHgAddr tables."
::= { mscFrNniDnaHgMHgAddrRowStatusEntry 4 }

mscFrNniDnaHgMHgAddrIndex OBJECT-TYPE
   SYNTAX     Integer32 (0..63)
   ACCESS     not-accessible
   STATUS     mandatory
   DESCRIPTION
     "This variable represents the index for the mscFrNniDnaHgMHgAddr tables."
::= { mscFrNniDnaHgMHgAddrRowStatusEntry 10 }

mscFrNniDnaHgMHgAddrAddrTable OBJECT-TYPE
   SYNTAX     SEQUENCE OF MscFrNniDnaHgMHgAddrAddrEntry
   ACCESS     not-accessible
   STATUS     mandatory
   DESCRIPTION
     "This group contains attributes common to all DNAs. Every DNA 
      used in the network is defined with this group of 2 attributes."
::= { mscFrNniDnaHgMHgAddr 10 }

mscFrNniDnaHgMHgAddrAddrEntry OBJECT-TYPE
   SYNTAX     MscFrNniDnaHgMHgAddrAddrEntry
   ACCESS     not-accessible
   STATUS     mandatory
   DESCRIPTION
     "An entry in the mscFrNniDnaHgMHgAddrAddrTable."
   INDEX {
      mscFrNniIndex,
      mscFrNniDnaIndex,
      mscFrNniDnaHgMIndex,
      mscFrNniDnaHgMHgAddrIndex }
::= { mscFrNniDnaHgMHgAddrAddrTable 1 }

MscFrNniDnaHgMHgAddrAddrEntry ::= SEQUENCE {
   mscFrNniDnaHgMHgAddrNumberingPlanIndicator
      INTEGER,
   mscFrNniDnaHgMHgAddrDataNetworkAddress
      DigitString }

mscFrNniDnaHgMHgAddrNumberingPlanIndicator OBJECT-TYPE
   SYNTAX     INTEGER  {
                 x121(0),
                 e164(1) }
   ACCESS     read-write
   STATUS     mandatory
   DESCRIPTION
     "This attribute indicates the Numbering Plan Indicator (NPI) of the 
      DNA. The address may belong to X.121 or E.164 plans."
   DEFVAL     { x121 }
::= { mscFrNniDnaHgMHgAddrAddrEntry 1 }

mscFrNniDnaHgMHgAddrDataNetworkAddress OBJECT-TYPE
   SYNTAX     DigitString (SIZE (1..15))
   ACCESS     read-write
   STATUS     mandatory
   DESCRIPTION
     "This attribute contains digits which form the unique identifier of the 
      customer interface. It can be compared (approximation only) to a 
      telephone number where the phone number identifies a unique 
      telephone set. DNA digits are selected and assigned by network 
      operators."
::= { mscFrNniDnaHgMHgAddrAddrEntry 2 }


-- FrUni/n Framer
-- FrNni/n Framer
-- FrAtm/n Framer
-- This component controls link layer framing for application 
-- components sending and receiving data on a link interface. It is also 
-- through Framer, that an application component is associated with a 
-- specific hardware link interface.
-- 
-- The Framer component provides provisionable attributes related to 
-- datapath aspects of the hardware interface (such as crc and frame 
-- length) rather than interface specific attributes (such as modem 
-- leads and clocking) which are associated with specific hardware 
-- components (such as V35/n or DS1/n). The Framer component also 
-- provides a provisionable attribute which binds the application 
-- component to a specific hardware component.
-- 
-- The Framer component contains operational attributes for link 
-- interface datapath statistics (such as frame counts and aborts).
-- 

mscFrNniFramer OBJECT IDENTIFIER ::= { mscFrNni 3 }



mscFrNniFramerRowStatusTable OBJECT-TYPE
   SYNTAX     SEQUENCE OF MscFrNniFramerRowStatusEntry
   ACCESS     not-accessible
   STATUS     mandatory
   DESCRIPTION
     "This entry controls the addition and deletion of 
      mscFrNniFramer components."
::= { mscFrNniFramer 1 }

mscFrNniFramerRowStatusEntry OBJECT-TYPE
   SYNTAX     MscFrNniFramerRowStatusEntry
   ACCESS     not-accessible
   STATUS     mandatory
   DESCRIPTION
     "A single entry in the table represents a single 
      mscFrNniFramer component."
   INDEX {
      mscFrNniIndex,
      mscFrNniFramerIndex }
::= { mscFrNniFramerRowStatusTable 1 }

MscFrNniFramerRowStatusEntry ::= SEQUENCE {
   mscFrNniFramerRowStatus
      RowStatus,
   mscFrNniFramerComponentName
      DisplayString,
   mscFrNniFramerStorageType
      StorageType,
   mscFrNniFramerIndex
      NonReplicated }

mscFrNniFramerRowStatus OBJECT-TYPE
   SYNTAX     RowStatus 
   ACCESS     read-write
   STATUS     mandatory
   DESCRIPTION
     "This variable is used as the basis for SNMP naming of
      mscFrNniFramer components.
      These components can be added and deleted."
::= { mscFrNniFramerRowStatusEntry 1 }

mscFrNniFramerComponentName OBJECT-TYPE
   SYNTAX     DisplayString 
   ACCESS     read-only
   STATUS     mandatory
   DESCRIPTION
     "This variable provides the component's string name for
      use with the ASCII Console Interface"
::= { mscFrNniFramerRowStatusEntry 2 }

mscFrNniFramerStorageType OBJECT-TYPE
   SYNTAX     StorageType 
   ACCESS     read-only
   STATUS     mandatory
   DESCRIPTION
     "This variable represents the storage type value for the
      mscFrNniFramer tables."
::= { mscFrNniFramerRowStatusEntry 4 }

mscFrNniFramerIndex OBJECT-TYPE
   SYNTAX     NonReplicated 
   ACCESS     not-accessible
   STATUS     mandatory
   DESCRIPTION
     "This variable represents the index for the mscFrNniFramer tables."
::= { mscFrNniFramerRowStatusEntry 10 }

mscFrNniFramerProvTable OBJECT-TYPE
   SYNTAX     SEQUENCE OF MscFrNniFramerProvEntry
   ACCESS     not-accessible
   STATUS     mandatory
   DESCRIPTION
     "This group contains the base provisioning data for the Framer 
      component. Application or hardware interface specific provisioning 
      data is contained in other provisionable Framer groups."
::= { mscFrNniFramer 10 }

mscFrNniFramerProvEntry OBJECT-TYPE
   SYNTAX     MscFrNniFramerProvEntry
   ACCESS     not-accessible
   STATUS     mandatory
   DESCRIPTION
     "An entry in the mscFrNniFramerProvTable."
   INDEX {
      mscFrNniIndex,
      mscFrNniFramerIndex }
::= { mscFrNniFramerProvTable 1 }

MscFrNniFramerProvEntry ::= SEQUENCE {
   mscFrNniFramerInterfaceName
      Link }

mscFrNniFramerInterfaceName OBJECT-TYPE
   SYNTAX     Link 
   ACCESS     read-write
   STATUS     mandatory
   DESCRIPTION
     "This attribute contains a hardware component name.
      
      The attribute associates the application with a specific link. This 
      defines the module processor on which Framer's parent component 
      (as well as Framer itself) will run."
::= { mscFrNniFramerProvEntry 1 }

mscFrNniFramerLinkTable OBJECT-TYPE
   SYNTAX     SEQUENCE OF MscFrNniFramerLinkEntry
   ACCESS     not-accessible
   STATUS     mandatory
   DESCRIPTION
     "This group contains attributes defining the framing of data on the 
      link interface."
::= { mscFrNniFramer 11 }

mscFrNniFramerLinkEntry OBJECT-TYPE
   SYNTAX     MscFrNniFramerLinkEntry
   ACCESS     not-accessible
   STATUS     mandatory
   DESCRIPTION
     "An entry in the mscFrNniFramerLinkTable."
   INDEX {
      mscFrNniIndex,
      mscFrNniFramerIndex }
::= { mscFrNniFramerLinkTable 1 }

MscFrNniFramerLinkEntry ::= SEQUENCE {
   mscFrNniFramerDataInversion
      INTEGER,
   mscFrNniFramerFrameCrcType
      INTEGER,
   mscFrNniFramerFlagsBetweenFrames
      Unsigned32 }

mscFrNniFramerDataInversion OBJECT-TYPE
   SYNTAX     INTEGER  {
                 off(0),
                 on(16) }
   ACCESS     read-write
   STATUS     mandatory
   DESCRIPTION
     "This attribute determines whether data bits are to be inverted (1 to 0 
      and 0 to 1) before transmission of frames to the interface. If the 
      value of this attribute is On, the incoming data bits will also be 
      inverted when frames are received from the link before being 
      processed.
      
      This option is typically used in hdlc framing mode when inversion 
      is used to guarantee 1's density.
      
      Note that aborts (in hdlc and interrupting modes) are corrupted 
      when data is inverted.
      
      This attribute may only take its default value for non-MSA cards."
   DEFVAL     { off }
::= { mscFrNniFramerLinkEntry 2 }

mscFrNniFramerFrameCrcType OBJECT-TYPE
   SYNTAX     INTEGER  {
                 crc16(0),
                 crc32(1),
                 noCrc(2) }
   ACCESS     read-write
   STATUS     mandatory
   DESCRIPTION
     "This attribute defines the type of CRC used. 
      
      The CRC value calculated is appended to the end of the frames 
      transmitted to the link. The CRC value is removed from the end of 
      frames received from the link and checked for correctness.
      NoCrc means that CRC is not used.
      
      This attribute may take only its default value for non-MSA cards."
   DEFVAL     { crc16 }
::= { mscFrNniFramerLinkEntry 3 }

mscFrNniFramerFlagsBetweenFrames OBJECT-TYPE
   SYNTAX     Unsigned32 (1..16)
   ACCESS     read-write
   STATUS     mandatory
   DESCRIPTION
     "This attribute defines the number of flags that are inserted between 
      frames sent to the link interface."
   DEFVAL     { 1 }
::= { mscFrNniFramerLinkEntry 4 }

mscFrNniFramerStateTable OBJECT-TYPE
   SYNTAX     SEQUENCE OF MscFrNniFramerStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscFrNniFramer 12 }

mscFrNniFramerStateEntry OBJECT-TYPE
   SYNTAX     MscFrNniFramerStateEntry
   ACCESS     not-accessible
   STATUS     mandatory
   DESCRIPTION
     "An entry in the mscFrNniFramerStateTable."
   INDEX {
      mscFrNniIndex,
      mscFrNniFramerIndex }
::= { mscFrNniFramerStateTable 1 }

MscFrNniFramerStateEntry ::= SEQUENCE {
   mscFrNniFramerAdminState
      INTEGER,
   mscFrNniFramerOperationalState
      INTEGER,
   mscFrNniFramerUsageState
      INTEGER }

mscFrNniFramerAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscFrNniFramerStateEntry 1 }

mscFrNniFramerOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscFrNniFramerStateEntry 2 }

mscFrNniFramerUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscFrNniFramerStateEntry 3 }

mscFrNniFramerStatsTable OBJECT-TYPE
   SYNTAX     SEQUENCE OF MscFrNniFramerStatsEntry
   ACCESS     not-accessible
   STATUS     mandatory
   DESCRIPTION
     "This group contains the operational statistics data for a Framer 
      component."
::= { mscFrNniFramer 13 }

mscFrNniFramerStatsEntry OBJECT-TYPE
   SYNTAX     MscFrNniFramerStatsEntry
   ACCESS     not-accessible
   STATUS     mandatory
   DESCRIPTION
     "An entry in the mscFrNniFramerStatsTable."
   INDEX {
      mscFrNniIndex,
      mscFrNniFramerIndex }
::= { mscFrNniFramerStatsTable 1 }

MscFrNniFramerStatsEntry ::= SEQUENCE {
   mscFrNniFramerFrmToIf
      Counter32,
   mscFrNniFramerFrmFromIf
      Counter32,
   mscFrNniFramerOctetFromIf
      Counter32,
   mscFrNniFramerAborts
      Counter32,
   mscFrNniFramerCrcErrors
      Counter32,
   mscFrNniFramerLrcErrors
      Counter32,
   mscFrNniFramerNonOctetErrors
      Counter32,
   mscFrNniFramerOverruns
      Counter32,
   mscFrNniFramerUnderruns
      Counter32,
   mscFrNniFramerLargeFrmErrors
      Counter32,
   mscFrNniFramerFrmModeErrors
      Counter32,
   mscFrNniFramerFrmToIf64
      PassportCounter64,
   mscFrNniFramerFrmFromIf64
      PassportCounter64,
   mscFrNniFramerOctetFromIf64
      PassportCounter64 }

mscFrNniFramerFrmToIf OBJECT-TYPE
   SYNTAX     Counter32 
   ACCESS     read-only
   STATUS     obsolete
   DESCRIPTION
     "The number of frames transmitted to the link interface by Framer.
      
      Note: This does not include the number of frames transmitted 
      directly to the hardware queue, thus bypassing the Framer 
      component."
::= { mscFrNniFramerStatsEntry 1 }

mscFrNniFramerFrmFromIf OBJECT-TYPE
   SYNTAX     Counter32 
   ACCESS     read-only
   STATUS     obsolete
   DESCRIPTION
     "The number of frames received from the link interface by Framer."
::= { mscFrNniFramerStatsEntry 2 }

mscFrNniFramerOctetFromIf OBJECT-TYPE
   SYNTAX     Counter32 
   ACCESS     read-only
   STATUS     obsolete
   DESCRIPTION
     "The number of bytes received from the link interface by Framer."
::= { mscFrNniFramerStatsEntry 3 }

mscFrNniFramerAborts OBJECT-TYPE
   SYNTAX     Counter32 
   ACCESS     read-only
   STATUS     mandatory
   DESCRIPTION
     "This attribute is the total number of aborts received."
::= { mscFrNniFramerStatsEntry 4 }

mscFrNniFramerCrcErrors OBJECT-TYPE
   SYNTAX     Counter32 
   ACCESS     read-only
   STATUS     mandatory
   DESCRIPTION
     "This attribute is the total number of frames with CRC errors, 
      occurring in the receive direction from the link."
::= { mscFrNniFramerStatsEntry 5 }

mscFrNniFramerLrcErrors OBJECT-TYPE
   SYNTAX     Counter32 
   ACCESS     read-only
   STATUS     mandatory
   DESCRIPTION
     "This attribute is the total number of frames with LRC errors, 
      occurring in the Tx link prior to transmission onto the link."
::= { mscFrNniFramerStatsEntry 6 }

mscFrNniFramerNonOctetErrors OBJECT-TYPE
   SYNTAX     Counter32 
   ACCESS     read-only
   STATUS     mandatory
   DESCRIPTION
     "This attribute is the total number of frames that were non octet 
      aligned."
::= { mscFrNniFramerStatsEntry 7 }

mscFrNniFramerOverruns OBJECT-TYPE
   SYNTAX     Counter32 
   ACCESS     read-only
   STATUS     mandatory
   DESCRIPTION
     "This attribute is the total number of frames received from the link 
      for which overruns occurred."
::= { mscFrNniFramerStatsEntry 8 }

mscFrNniFramerUnderruns OBJECT-TYPE
   SYNTAX     Counter32 
   ACCESS     read-only
   STATUS     mandatory
   DESCRIPTION
     "This attribute is the total number of frames transmitted to the link 
      for which underruns occurred."
::= { mscFrNniFramerStatsEntry 9 }

mscFrNniFramerLargeFrmErrors OBJECT-TYPE
   SYNTAX     Counter32 
   ACCESS     read-only
   STATUS     mandatory
   DESCRIPTION
     "This attribute is the total number of frames received which were too 
      large. The frame execeeded the maximumFrameLengthLimit 
      provisioned attribute or it contained more than the 255 block 
      hardware limit."
::= { mscFrNniFramerStatsEntry 10 }

mscFrNniFramerFrmModeErrors OBJECT-TYPE
   SYNTAX     Counter32 
   ACCESS     read-only
   STATUS     mandatory
   DESCRIPTION
     "This attribute is the total number of frames detected with framing 
      mode errors. A framingModeError is flagged when frames are 
      inconsistent with the specified framingType, that is when 
      interrupting frames are used while running in hdlc mode."
::= { mscFrNniFramerStatsEntry 11 }

mscFrNniFramerFrmToIf64 OBJECT-TYPE
   SYNTAX     PassportCounter64 
   ACCESS     read-only
   STATUS     mandatory
   DESCRIPTION
     "The number of frames transmitted to the link interface by Framer.
      
      Note: This does not include the number of frames transmitted 
      directly to the hardware queue, thus bypassing the Framer 
      component."
::= { mscFrNniFramerStatsEntry 14 }

mscFrNniFramerFrmFromIf64 OBJECT-TYPE
   SYNTAX     PassportCounter64 
   ACCESS     read-only
   STATUS     mandatory
   DESCRIPTION
     "The number of frames received from the link interface by Framer."
::= { mscFrNniFramerStatsEntry 15 }

mscFrNniFramerOctetFromIf64 OBJECT-TYPE
   SYNTAX     PassportCounter64 
   ACCESS     read-only
   STATUS     mandatory
   DESCRIPTION
     "The number of bytes received from the link interface by Framer."
::= { mscFrNniFramerStatsEntry 16 }

mscFrNniFramerUtilTable OBJECT-TYPE
   SYNTAX     SEQUENCE OF MscFrNniFramerUtilEntry
   ACCESS     not-accessible
   STATUS     mandatory
   DESCRIPTION
     "This group contains the link utilizaiton operational data for a 
      Framer component."
::= { mscFrNniFramer 14 }

mscFrNniFramerUtilEntry OBJECT-TYPE
   SYNTAX     MscFrNniFramerUtilEntry
   ACCESS     not-accessible
   STATUS     mandatory
   DESCRIPTION
     "An entry in the mscFrNniFramerUtilTable."
   INDEX {
      mscFrNniIndex,
      mscFrNniFramerIndex }
::= { mscFrNniFramerUtilTable 1 }

MscFrNniFramerUtilEntry ::= SEQUENCE {
   mscFrNniFramerNormPrioLinkUtilToIf
      Gauge32,
   mscFrNniFramerNormPrioLinkUtilFromIf
      Gauge32 }

mscFrNniFramerNormPrioLinkUtilToIf OBJECT-TYPE
   SYNTAX     Gauge32 (0..100)
   ACCESS     read-only
   STATUS     mandatory
   DESCRIPTION
     "This attribute is the utilization of the normal and high priority data 
      traffic (interruptable traffic) sent to the link as a percentage of the 
      available bandwidth on the link. Note that this indluces traffic with 
      Transfer Priorities (TP) of 0, 6 and 9 and/or Emission Priority of 2 
      and 3. The utilization is the average for the last minute."
   DEFVAL     { 0 }
::= { mscFrNniFramerUtilEntry 1 }

mscFrNniFramerNormPrioLinkUtilFromIf OBJECT-TYPE
   SYNTAX     Gauge32 (0..100)
   ACCESS     read-only
   STATUS     mandatory
   DESCRIPTION
     "This attribute is the utilization of the normal and high priority data 
      traffic (interruptable traffic) received from the link as a percentage 
      of the available bandwidth on the link. Note that this includes traffic 
      with Transfer Priorities (TP) of 0, 6 and 9 and/or Emission Priority 
      of 2 and 3. The utilization is the average for the last minute."
   DEFVAL     { 0 }
::= { mscFrNniFramerUtilEntry 3 }


-- FrNni/n LocalManagementInterface
-- This component defines the parameters for implementing the Frame 
-- Relay NNI Local Management Interface protocol. This differs from 
-- its UNI counterpart in that bi-directional LMI procedures are 
-- supported and protocols other than ANSI and CCITT are not 
-- supported.

mscFrNniLmi OBJECT IDENTIFIER ::= { mscFrNni 4 }



mscFrNniLmiRowStatusTable OBJECT-TYPE
   SYNTAX     SEQUENCE OF MscFrNniLmiRowStatusEntry
   ACCESS     not-accessible
   STATUS     mandatory
   DESCRIPTION
     "This entry controls the addition and deletion of 
      mscFrNniLmi components."
::= { mscFrNniLmi 1 }

mscFrNniLmiRowStatusEntry OBJECT-TYPE
   SYNTAX     MscFrNniLmiRowStatusEntry
   ACCESS     not-accessible
   STATUS     mandatory
   DESCRIPTION
     "A single entry in the table represents a single 
      mscFrNniLmi component."
   INDEX {
      mscFrNniIndex,
      mscFrNniLmiIndex }
::= { mscFrNniLmiRowStatusTable 1 }

MscFrNniLmiRowStatusEntry ::= SEQUENCE {
   mscFrNniLmiRowStatus
      RowStatus,
   mscFrNniLmiComponentName
      DisplayString,
   mscFrNniLmiStorageType
      StorageType,
   mscFrNniLmiIndex
      NonReplicated }

mscFrNniLmiRowStatus OBJECT-TYPE
   SYNTAX     RowStatus 
   ACCESS     read-only
   STATUS     mandatory
   DESCRIPTION
     "This variable is used as the basis for SNMP naming of
      mscFrNniLmi components.
      These components cannot be added nor deleted."
::= { mscFrNniLmiRowStatusEntry 1 }

mscFrNniLmiComponentName OBJECT-TYPE
   SYNTAX     DisplayString 
   ACCESS     read-only
   STATUS     mandatory
   DESCRIPTION
     "This variable provides the component's string name for
      use with the ASCII Console Interface"
::= { mscFrNniLmiRowStatusEntry 2 }

mscFrNniLmiStorageType OBJECT-TYPE
   SYNTAX     StorageType 
   ACCESS     read-only
   STATUS     mandatory
   DESCRIPTION
     "This variable represents the storage type value for the
      mscFrNniLmi tables."
::= { mscFrNniLmiRowStatusEntry 4 }

mscFrNniLmiIndex OBJECT-TYPE
   SYNTAX     NonReplicated 
   ACCESS     not-accessible
   STATUS     mandatory
   DESCRIPTION
     "This variable represents the index for the mscFrNniLmi tables."
::= { mscFrNniLmiRowStatusEntry 10 }

mscFrNniLmiParmsTable OBJECT-TYPE
   SYNTAX     SEQUENCE OF MscFrNniLmiParmsEntry
   ACCESS     not-accessible
   STATUS     mandatory
   DESCRIPTION
     "This group contains the provisionable attributes of the Local 
      Management Interface component."
::= { mscFrNniLmi 10 }

mscFrNniLmiParmsEntry OBJECT-TYPE
   SYNTAX     MscFrNniLmiParmsEntry
   ACCESS     not-accessible
   STATUS     mandatory
   DESCRIPTION
     "An entry in the mscFrNniLmiParmsTable."
   INDEX {
      mscFrNniIndex,
      mscFrNniLmiIndex }
::= { mscFrNniLmiParmsTable 1 }

MscFrNniLmiParmsEntry ::= SEQUENCE {
   mscFrNniLmiProcedures
      INTEGER,
   mscFrNniLmiAsyncStatusReport
      INTEGER,
   mscFrNniLmiErrorEventThreshold
      Unsigned32,
   mscFrNniLmiEventCount
      Unsigned32,
   mscFrNniLmiCheckPointTimer
      Unsigned32,
   mscFrNniLmiIgnoreActiveBit
      INTEGER }

mscFrNniLmiProcedures OBJECT-TYPE
   SYNTAX     INTEGER  {
                 none(0),
                 ansi(2),
                 itu(3),
                 autoConfigure(4) }
   ACCESS     read-write
   STATUS     mandatory
   DESCRIPTION
     "This attribute selects the procedures to be used for the Local 
      Management Interface. The following are the supported procedures:
      
      none: Local Management Interface procedures are not running on 
      this interface. This accommodates Frame Relay user equipment 
      which didn't implement any LMI procedures. In this case, the 
      remaining attributes of this group are ignored.
      
      ansi: Local Management Interface procedures from the ANSI 
      specification are supported. DLCI 0 is used for the LMI protocol.
      
      itu: Local Management Interface procedures from the ITU-T 
      specification are supported. DLCI 0 is used for the LMI protocol. 
      Was previously ccitt.
      
      autoConfigure:	The interface determines automatically which Local 
      Management Interface procedures to use. 
      
      The procedures currently being used can be seen in the operational 
      attribute opProcedures."
   DEFVAL     { autoConfigure }
::= { mscFrNniLmiParmsEntry 1 }

mscFrNniLmiAsyncStatusReport OBJECT-TYPE
   SYNTAX     INTEGER  {
                 off(0),
                 on(1) }
   ACCESS     read-write
   STATUS     mandatory
   DESCRIPTION
     "This attribute selects the use of asynchronous PVC status report 
      procedures as specified in ANSI and CCITT specification."
   DEFVAL     { off }
::= { mscFrNniLmiParmsEntry 2 }

mscFrNniLmiErrorEventThreshold OBJECT-TYPE
   SYNTAX     Unsigned32 (1..10)
   ACCESS     read-write
   STATUS     mandatory
   DESCRIPTION
     "For the network-side-procedure, an event is defined as follows: (1) 
      receipt of a STATUS ENQUIRY message, or (2) expiration of timer 
      T392. An error event is (1) nonreceipt of STATUS ENQUIRY in 
      T392 seconds; (2) invalid format of a LMI message; (3) invalid 
      receive sequence number. 
      For the user-side-procedure, an event is defined as a polling cycle or 
      a status enquiry and status report exchange. An error event is (1) 
      non-receipt of a STATUS within the polling cycle, or (2) invalid 
      format of a LMI message, or (3) invalid sequence number
      This attribute specifies the number of error events which, if they 
      occur within eventCount events, will cause a protocol error 
      condition. The condition is cleared after eventCount sequential 
      correct events occur. 
      
      It must be less than or equal to eventCount (n393)"
   DEFVAL     { 3 }
::= { mscFrNniLmiParmsEntry 3 }

mscFrNniLmiEventCount OBJECT-TYPE
   SYNTAX     Unsigned32 (1..10)
   ACCESS     read-write
   STATUS     mandatory
   DESCRIPTION
     "This attribute specifies the number of contiguous events within 
      which no more than eventErrorThreshold error events are allowed.
      
      It must be greater than or equal to errorEventThreshold (n392)."
   DEFVAL     { 4 }
::= { mscFrNniLmiParmsEntry 4 }

mscFrNniLmiCheckPointTimer OBJECT-TYPE
   SYNTAX     Unsigned32 (5 | 10 | 15 | 20 | 25 | 30)
   ACCESS     read-write
   STATUS     mandatory
   DESCRIPTION
     "This attribute selects the time (in seconds) within which a STATUS 
      ENQUIRY message is expected. It must be greater than 
      linkVerificationTimer (t391)."
   DEFVAL     { 15 }
::= { mscFrNniLmiParmsEntry 5 }

mscFrNniLmiIgnoreActiveBit OBJECT-TYPE
   SYNTAX     INTEGER  {
                 no(0),
                 yes(1) }
   ACCESS     read-write
   STATUS     mandatory
   DESCRIPTION
     "This attribute specifies whether the Frame Relay LMI Active Bit 
      (A-bit) has a bearing on the transfer of user data across this Frame 
      Relay interface for both directions of traffic flow.
      
      When this attribute is set to yes, the A-bit status of a user DLCI 
      connection does not affect data transfer.
      
      When this attribute is set to no, data received from the local 
      interface is discarded if an A-bit =0 condition exists towards the 
      local user. Data being sent to the local interface is discarded if an A-
      bit = 0 condition exists towards the local user."
   DEFVAL     { no }
::= { mscFrNniLmiParmsEntry 7 }

mscFrNniLmiNniParmsTable OBJECT-TYPE
   SYNTAX     SEQUENCE OF MscFrNniLmiNniParmsEntry
   ACCESS     not-accessible
   STATUS     mandatory
   DESCRIPTION
     "This group contains the provisionable attributes of the Local 
      Management Interface component which are unique to NNI."
::= { mscFrNniLmi 11 }

mscFrNniLmiNniParmsEntry OBJECT-TYPE
   SYNTAX     MscFrNniLmiNniParmsEntry
   ACCESS     not-accessible
   STATUS     mandatory
   DESCRIPTION
     "An entry in the mscFrNniLmiNniParmsTable."
   INDEX {
      mscFrNniIndex,
      mscFrNniLmiIndex }
::= { mscFrNniLmiNniParmsTable 1 }

MscFrNniLmiNniParmsEntry ::= SEQUENCE {
   mscFrNniLmiFullStatusPollingCycles
      Unsigned32,
   mscFrNniLmiLinkVerificationTimer
      Unsigned32 }

mscFrNniLmiFullStatusPollingCycles OBJECT-TYPE
   SYNTAX     Unsigned32 (1..255)
   ACCESS     read-write
   STATUS     mandatory
   DESCRIPTION
     "This attribute specifies how frequently the Frame Relay NNI service 
      should initiate a Status Enquiry for a full PVC status report. A 
      polling cycle is a Status Enquiry and Status Report exchange."
   DEFVAL     { 6 }
::= { mscFrNniLmiNniParmsEntry 1 }

mscFrNniLmiLinkVerificationTimer OBJECT-TYPE
   SYNTAX     Unsigned32 (5 | 10 | 15 | 20 | 25 | 30)
   ACCESS     read-write
   STATUS     mandatory
   DESCRIPTION
     "This attribute specifies how frequently the Frame Relay NNI service 
      should initiate a Status Enquiry for link integrity verification. It 
      must be less than checkPointTimer (t392)."
   DEFVAL     { 10 }
::= { mscFrNniLmiNniParmsEntry 2 }

mscFrNniLmiStateTable OBJECT-TYPE
   SYNTAX     SEQUENCE OF MscFrNniLmiStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscFrNniLmi 12 }

mscFrNniLmiStateEntry OBJECT-TYPE
   SYNTAX     MscFrNniLmiStateEntry
   ACCESS     not-accessible
   STATUS     mandatory
   DESCRIPTION
     "An entry in the mscFrNniLmiStateTable."
   INDEX {
      mscFrNniIndex,
      mscFrNniLmiIndex }
::= { mscFrNniLmiStateTable 1 }

MscFrNniLmiStateEntry ::= SEQUENCE {
   mscFrNniLmiAdminState
      INTEGER,
   mscFrNniLmiOperationalState
      INTEGER,
   mscFrNniLmiUsageState
      INTEGER }

mscFrNniLmiAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscFrNniLmiStateEntry 1 }

mscFrNniLmiOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscFrNniLmiStateEntry 2 }

mscFrNniLmiUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscFrNniLmiStateEntry 3 }

mscFrNniLmiPsiTable OBJECT-TYPE
   SYNTAX     SEQUENCE OF MscFrNniLmiPsiEntry
   ACCESS     not-accessible
   STATUS     mandatory
   DESCRIPTION
     "This group provides the protocol status of the Local Management 
      Interface."
::= { mscFrNniLmi 13 }

mscFrNniLmiPsiEntry OBJECT-TYPE
   SYNTAX     MscFrNniLmiPsiEntry
   ACCESS     not-accessible
   STATUS     mandatory
   DESCRIPTION
     "An entry in the mscFrNniLmiPsiTable."
   INDEX {
      mscFrNniIndex,
      mscFrNniLmiIndex }
::= { mscFrNniLmiPsiTable 1 }

MscFrNniLmiPsiEntry ::= SEQUENCE {
   mscFrNniLmiProtocolStatus
      INTEGER,
   mscFrNniLmiOpProcedures
      INTEGER }

mscFrNniLmiProtocolStatus OBJECT-TYPE
   SYNTAX     INTEGER  {
                 errorCondition(0),
                 normalCondition(1),
                 configuring(2) }
   ACCESS     read-only
   STATUS     mandatory
   DESCRIPTION
     "This attribute indicates whether the LMI is in an error condition or 
      whether the LMI procedures are behaving normally. When 
      operating with no LMI protocol, this attribute is always set to 
      normalCondition. When operating with LMI procedures, this 
      attribute is set to errorCondition after n392 of the last n393 events 
      are in error. The consequence of an errorCondition is that all 
      DLCIs on this interface will become inactive in both directions. The 
      errorCondition is lifted and a normalCondition is indicated when a 
      sufficient number of events have occurred without error. In ANSI, 
      this occurs when n393 consecutive good events take place.
      
      If the procedures attribute is set to autoConfigure, this attribute is 
      se to configuring while adaptive LMI determines which LMI 
      procedures are running on the link. A single LMI error event during 
      auto configuration causes the attribute value to change to 
      errorCondition. If during configuring no LMI message is received, 
      an LMI errorCondition is raised after n392 x t392 seconds."
::= { mscFrNniLmiPsiEntry 1 }

mscFrNniLmiOpProcedures OBJECT-TYPE
   SYNTAX     INTEGER  {
                 none(0),
                 ansi(2),
                 itu(3),
                 unknown(4) }
   ACCESS     read-only
   STATUS     mandatory
   DESCRIPTION
     "This attribute indicates the procedures being used for the Local 
      Management Interface. This attribute should be ignored if 
      protocolStatus is not normalCondition. The following procedures 
      are supported:
      
      none: Local Management Interface procedures are not running on 
      this interface. This accommodates Frame Relay user equipment that 
      has not implemented any LMI procedures.
      
      ansi: Local Management Interface procedures from the ANSI 
      specification are running. DLCI 0 is used for the LMI protocol.
      
      itu: Local Management Interface procedures from the ITU-T 
      specification are running. DLCI 0 is used for the LMI protocol. Was 
      previously ccitt.
      
      unknown: Local Management Interface procedures have yet to be 
      determined by Adaptive LMI."
::= { mscFrNniLmiPsiEntry 2 }

mscFrNniLmiStatsTable OBJECT-TYPE
   SYNTAX     SEQUENCE OF MscFrNniLmiStatsEntry
   ACCESS     not-accessible
   STATUS     mandatory
   DESCRIPTION
     "This group contains the operational statistics for the Frame Relay 
      NNI Local Management Interface."
::= { mscFrNniLmi 14 }

mscFrNniLmiStatsEntry OBJECT-TYPE
   SYNTAX     MscFrNniLmiStatsEntry
   ACCESS     not-accessible
   STATUS     mandatory
   DESCRIPTION
     "An entry in the mscFrNniLmiStatsTable."
   INDEX {
      mscFrNniIndex,
      mscFrNniLmiIndex }
::= { mscFrNniLmiStatsTable 1 }

MscFrNniLmiStatsEntry ::= SEQUENCE {
   mscFrNniLmiKeepAliveStatusToIf
      Counter32,
   mscFrNniLmiFullStatusToIf
      Counter32,
   mscFrNniLmiKeepAliveStatusEnqFromIf
      Counter32,
   mscFrNniLmiFullStatusEnqFromIf
      Counter32,
   mscFrNniLmiNetworkSideEventHistory
      AsciiString,
   mscFrNniLmiUserSideEventHistory
      AsciiString,
   mscFrNniLmiProtocolErrors
      Counter32,
   mscFrNniLmiUnexpectedIes
      Counter32,
   mscFrNniLmiSequenceErrors
      Counter32,
   mscFrNniLmiStatusSequenceErrors
      Counter32,
   mscFrNniLmiUnexpectedReports
      Counter32,
   mscFrNniLmiPollingVerifTimeouts
      Counter32,
   mscFrNniLmiNoStatusReportCount
      Counter32 }

mscFrNniLmiKeepAliveStatusToIf OBJECT-TYPE
   SYNTAX     Counter32 
   ACCESS     read-only
   STATUS     mandatory
   DESCRIPTION
     "This attribute counts the number of Local Management Interface 
      keep alive status messages sent to the external network in response 
      to a status enquiry for keep alive status. When the maximum count 
      is exceeded it wraps to zero."
::= { mscFrNniLmiStatsEntry 1 }

mscFrNniLmiFullStatusToIf OBJECT-TYPE
   SYNTAX     Counter32 
   ACCESS     read-only
   STATUS     mandatory
   DESCRIPTION
     "This attribute counts the number of Local Management Interface 
      full status messages sent to the external network in response to a 
      status enquiry for keep alive or full status. When the maximum 
      count is exceeded it wraps to zero."
::= { mscFrNniLmiStatsEntry 2 }

mscFrNniLmiKeepAliveStatusEnqFromIf OBJECT-TYPE
   SYNTAX     Counter32 
   ACCESS     read-only
   STATUS     mandatory
   DESCRIPTION
     "This attribute counts the number of Local Management Interface 
      valid keep alive status enquiry messages received from the external 
      network. When the maximum count is exceeded it wraps to zero."
::= { mscFrNniLmiStatsEntry 3 }

mscFrNniLmiFullStatusEnqFromIf OBJECT-TYPE
   SYNTAX     Counter32 
   ACCESS     read-only
   STATUS     mandatory
   DESCRIPTION
     "This attribute counts the number of Local Management Interface 
      valid full status enquiry messages received from the external 
      network. When the maximum count is exceeded it wraps to zero."
::= { mscFrNniLmiStatsEntry 4 }

mscFrNniLmiNetworkSideEventHistory OBJECT-TYPE
   SYNTAX     AsciiString (SIZE (1..10))
   ACCESS     read-only
   STATUS     mandatory
   DESCRIPTION
     "This attribute displays the Local Management Interface network 
      side procedure event history in order of occurrence. An event is 
      represented by a single symbol. A '+' symbol indicates a good 
      event. An 'X' symbol indicates a protocol error event. The leftmost 
      event is the most recent to occur. The provisioned eventCount (nN3/
      N393) dictates the maximum number of events displayed. A good 
      event is triggered by receipt of a valid status enquiry message. An 
      error event is either a nT2/T392 timer expiry or receipt of a status 
      enquiry with bad sequence numbers."
::= { mscFrNniLmiStatsEntry 5 }

mscFrNniLmiUserSideEventHistory OBJECT-TYPE
   SYNTAX     AsciiString (SIZE (1..10))
   ACCESS     read-only
   STATUS     mandatory
   DESCRIPTION
     "This attribute displays the Local Management Interface user side 
      procedure event history in order of occurrence. An event is 
      represented by a single symbol. A '+' symbol indicates a good 
      event. An 'X' symbol indicates a protocol error event. The leftmost 
      event is the most recent to occur. The provisioned eventCount (nN3/
      N393) dictates the maximum number of events displayed. A good 
      event is triggered by receipt of a valid status message. An error 
      event is either a nT1/T391 timer expiry or receipt of a status 
      message with bad sequence numbers."
::= { mscFrNniLmiStatsEntry 6 }

mscFrNniLmiProtocolErrors OBJECT-TYPE
   SYNTAX     Counter32 
   ACCESS     read-only
   STATUS     mandatory
   DESCRIPTION
     "This attribute counts the number of Local Management Interface 
      protocol errors. It is the sum of the sequence (sequenceErrors and 
      statusSequenceErrors) and timeout (pollingVerifTimeouts and 
      noStatusReportCount) errors. When the maximum count is 
      exceeded it wraps to zero."
::= { mscFrNniLmiStatsEntry 7 }

mscFrNniLmiUnexpectedIes OBJECT-TYPE
   SYNTAX     Counter32 
   ACCESS     read-only
   STATUS     mandatory
   DESCRIPTION
     "This attribute counts the number of Local Management Interface 
      frames received with an Information Element identifier that is 
      unknown or unexpected. An unexpected Information Element is not 
      a protocol error. When the maximum count is exceeded, this 
      counter wraps to zero."
::= { mscFrNniLmiStatsEntry 8 }

mscFrNniLmiSequenceErrors OBJECT-TYPE
   SYNTAX     Counter32 
   ACCESS     read-only
   STATUS     mandatory
   DESCRIPTION
     "This attribute counts the number of Local Management Interface 
      Status Enquiry message sequence errors. A sequence error is receipt 
      of a Status Enquiry message with a receive sequence number not 
      equal to the last send sequence number. When the maximum count 
      is exceeded the counter wraps to zero."
::= { mscFrNniLmiStatsEntry 9 }

mscFrNniLmiStatusSequenceErrors OBJECT-TYPE
   SYNTAX     Counter32 
   ACCESS     read-only
   STATUS     mandatory
   DESCRIPTION
     "This attribute counts the number of Local Management Interface 
      Status message sequence errors. A sequence error is receipt of a 
      Status message with a receive sequence number not equal to the last 
      send sequence number. When the maximum count is exceeded the 
      counter wraps to zero."
::= { mscFrNniLmiStatsEntry 10 }

mscFrNniLmiUnexpectedReports OBJECT-TYPE
   SYNTAX     Counter32 
   ACCESS     read-only
   STATUS     mandatory
   DESCRIPTION
     "This attribute counts the number of Local Management Interface 
      frames received with an unknown or unexpected report type. An 
      unexpected report type is not a protocol error. When the maximum 
      count is exceeded the counter wraps to zero."
::= { mscFrNniLmiStatsEntry 11 }

mscFrNniLmiPollingVerifTimeouts OBJECT-TYPE
   SYNTAX     Counter32 
   ACCESS     read-only
   STATUS     mandatory
   DESCRIPTION
     "This attribute counts the number of checkPointTImer (t392) timer 
      expiries occurring on the Local Management Interface. When the 
      maximum count is exceeded the counter wraps to zero."
::= { mscFrNniLmiStatsEntry 12 }

mscFrNniLmiNoStatusReportCount OBJECT-TYPE
   SYNTAX     Counter32 
   ACCESS     read-only
   STATUS     mandatory
   DESCRIPTION
     "This attribute counts the number of times when no status report or 
      an invalid status report comes from the external network. This 
      attribute is incremented in two cases: 
      i) after a status enquiry is sent out and T391 timer expires without 
      having a status report received.
      ii) an invalid status report is received.
      
      When the maximum count is exceeded it wraps to zero."
::= { mscFrNniLmiStatsEntry 13 }


-- FrNni/n DataLinkConnectionIdentifier/n
-- This component represents a Data Link Connection Identifier. It is 
-- responsible for the Frame Relay U-plane (User-plane) protocol for 
-- the specified instance. There can be many instances of Dlci for each 
-- FrNni. The instance value is used to identify the logical connection, 
-- multiplexed within the physical channel, with which a frame is 
-- associated. All frames carried within a particular physical channel 
-- and having the same DLCI value are associated with the same 
-- logical connection.
-- 
-- A DLCI instance can be a permanent virtual circuit (PVC) or 
-- switched permanent virtual circuit (P-SPVC) added through 
-- provisioning, or a switched virtual circuit (SVC) or S-SPVC which 
-- is created dynamically through signaling.
-- 
-- The lock and unlock commands apply to permanent DLCIs. The 
-- clear command applies to switched DLCIs.

mscFrNniDlci OBJECT IDENTIFIER ::= { mscFrNni 5 }



mscFrNniDlciRowStatusTable OBJECT-TYPE
   SYNTAX     SEQUENCE OF MscFrNniDlciRowStatusEntry
   ACCESS     not-accessible
   STATUS     mandatory
   DESCRIPTION
     "This entry controls the addition and deletion of 
      mscFrNniDlci components."
::= { mscFrNniDlci 1 }

mscFrNniDlciRowStatusEntry OBJECT-TYPE
   SYNTAX     MscFrNniDlciRowStatusEntry
   ACCESS     not-accessible
   STATUS     mandatory
   DESCRIPTION
     "A single entry in the table represents a single 
      mscFrNniDlci component."
   INDEX {
      mscFrNniIndex,
      mscFrNniDlciIndex }
::= { mscFrNniDlciRowStatusTable 1 }

MscFrNniDlciRowStatusEntry ::= SEQUENCE {
   mscFrNniDlciRowStatus
      RowStatus,
   mscFrNniDlciComponentName
      DisplayString,
   mscFrNniDlciStorageType
      StorageType,
   mscFrNniDlciIndex
      Integer32 }

mscFrNniDlciRowStatus OBJECT-TYPE
   SYNTAX     RowStatus 
   ACCESS     read-write
   STATUS     mandatory
   DESCRIPTION
     "This variable is used as the basis for SNMP naming of
      mscFrNniDlci components.
      These components can be added and deleted."
::= { mscFrNniDlciRowStatusEntry 1 }

mscFrNniDlciComponentName OBJECT-TYPE
   SYNTAX     DisplayString 
   ACCESS     read-only
   STATUS     mandatory
   DESCRIPTION
     "This variable provides the component's string name for
      use with the ASCII Console Interface"
::= { mscFrNniDlciRowStatusEntry 2 }

mscFrNniDlciStorageType OBJECT-TYPE
   SYNTAX     StorageType 
   ACCESS     read-only
   STATUS     mandatory
   DESCRIPTION
     "This variable represents the storage type value for the
      mscFrNniDlci tables."
::= { mscFrNniDlciRowStatusEntry 4 }

mscFrNniDlciIndex OBJECT-TYPE
   SYNTAX     Integer32 (16..1007)
   ACCESS     not-accessible
   STATUS     mandatory
   DESCRIPTION
     "This variable represents the index for the mscFrNniDlci tables."
::= { mscFrNniDlciRowStatusEntry 10 }

mscFrNniDlciStateTable OBJECT-TYPE
   SYNTAX     SEQUENCE OF MscFrNniDlciStateEntry
   ACCESS     not-accessible
   STATUS     mandatory
   DESCRIPTION
     "This group contains the three OSI State attributes and the six OSI 
      Status attributes. The descriptions generically indicate what each 
      attribute implies about the component. Note that not all the values 
      and state combinations described here are supported by every 
      component which uses this group. For component-specific 
      information and the valid state combinations, refer to NTP 241-
      7001-150, Passport Operations and Maintenance Guide."
::= { mscFrNniDlci 10 }

mscFrNniDlciStateEntry OBJECT-TYPE
   SYNTAX     MscFrNniDlciStateEntry
   ACCESS     not-accessible
   STATUS     mandatory
   DESCRIPTION
     "An entry in the mscFrNniDlciStateTable."
   INDEX {
      mscFrNniIndex,
      mscFrNniDlciIndex }
::= { mscFrNniDlciStateTable 1 }

MscFrNniDlciStateEntry ::= SEQUENCE {
   mscFrNniDlciAdminState
      INTEGER,
   mscFrNniDlciOperationalState
      INTEGER,
   mscFrNniDlciUsageState
      INTEGER,
   mscFrNniDlciAvailabilityStatus
      OCTET STRING,
   mscFrNniDlciProceduralStatus
      OCTET STRING,
   mscFrNniDlciControlStatus
      OCTET STRING,
   mscFrNniDlciAlarmStatus
      OCTET STRING,
   mscFrNniDlciStandbyStatus
      INTEGER,
   mscFrNniDlciUnknownStatus
      INTEGER }

mscFrNniDlciAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component.
      
      The OSI Status attributes, if supported by the component, may 
      provide more details, qualifying the state of the component."
   DEFVAL     { unlocked }
::= { mscFrNniDlciStateEntry 1 }

mscFrNniDlciOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle.
      
      The OSI Status attributes, if supported by the component, may 
      provide more details, qualifying the state of the component."
   DEFVAL     { disabled }
::= { mscFrNniDlciStateEntry 2 }

mscFrNniDlciUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time.
      
      The OSI Status attributes, if supported by the component, may 
      provide more details, qualifying the state of the component."
   DEFVAL     { idle }
::= { mscFrNniDlciStateEntry 3 }

mscFrNniDlciAvailabilityStatus OBJECT-TYPE
   SYNTAX     OCTET STRING (SIZE (2))
   ACCESS     read-only
   STATUS     mandatory
   DESCRIPTION
     "If supported by the component, this attribute indicates the OSI 
      Availability status of the component. Note that, even though it is 
      defined as a multi-valued set, at most one value is shown to the user.
      
      When no values are in the set, this indicates that either the attribute 
      is not supported or that none of the status conditions described 
      below are present.
      
      The value inTest indicates that the resource is undergoing a test 
      procedure. If adminState is locked or shuttingDown, the normal 
      users are precluded from using the resource and controlStatus is 
      reservedForTest. Tests that do not exclude additional users can be 
      present in any operational or administrative state but the 
      reservedForTest condition should not be present.
      
      The value failed indicates that the component has an internal fault 
      that prevents it from operating. The operationalState is disabled.
      
      The value dependency indicates that the component cannot operate 
      because some other resource on which it depends is unavailable. 
      The operationalState is disabled.
      
      The value powerOff indicates the resource requires power to be 
      applied and it is not powered on. The operationalState is disabled.
      
      The value offLine indicates the resource requires a routine 
      operation (either manual, automatic, or both) to be performed to 
      place it on-line and make it available for use. The operationalState 
      is disabled.
      
      The value offDuty indicates the resource is inactive in accordance 
      with a predetermined time schedule. In the absence of other 
      disabling conditions, the operationalState is enabled or disabled.
      
      The value degraded indicates the service provided by the 
      component is degraded in some way, such as in speed or operating 
      capacity. However, the resource remains available for service. The 
      operationalState is enabled.
      
      The value notInstalled indicates the resource is not present. The 
      operationalState is disabled.
      
      The value logFull is not used.

      Description of bits:
      inTest(0)
      failed(1)
      powerOff(2)
      offLine(3)
      offDuty(4)
      dependency(5)
      degraded(6)
      notInstalled(7)
      logFull(8)"
::= { mscFrNniDlciStateEntry 4 }

mscFrNniDlciProceduralStatus OBJECT-TYPE
   SYNTAX     OCTET STRING (SIZE (1))
   ACCESS     read-only
   STATUS     mandatory
   DESCRIPTION
     "If supported by the component, this attribute indicates the OSI 
      Procedural status of the component. Note that, even though it is 
      defined as a multi-valued set, at most one value is shown to the user.
      
      When no values are in the set, this indicates that either the attribute 
      is not supported or that none of the status conditions described 
      below are present.
      
      The value initializationRequired indicates (for a resource which 
      doesn't initialize autonomously) that initialization is required before 
      it can perform its normal functions, and this procedure has not been 
      initiated. The operationalState is disabled.
      
      The value notInitialized indicates (for a resource which does 
      initialize autonomously) that initialization is required before it can 
      perform its normal functions, and this procedure has not been 
      initiated. The operationalState may be enabled or disabled.
      
      The value initializing indicates that initialization has been initiated 
      but is not yet complete. The operationalState may be enabled or 
      disabled.
      
      The value reporting indicates the resource has completed some 
      processing operation and is notifying the results. The 
      operationalState is enabled.
      
      The value terminating indicates the component is in a termination 
      phase. If the resource doesn't reinitialize autonomously, 
      operationalState is disabled; otherwise it is enabled or disabled.

      Description of bits:
      initializationRequired(0)
      notInitialized(1)
      initializing(2)
      reporting(3)
      terminating(4)"
::= { mscFrNniDlciStateEntry 5 }

mscFrNniDlciControlStatus OBJECT-TYPE
   SYNTAX     OCTET STRING (SIZE (1))
   ACCESS     read-only
   STATUS     mandatory
   DESCRIPTION
     "If supported by the component, this attribute indicates the OSI 
      Control status of the component. Note that, even though it is defined 
      as a multi-valued set, at most one value is shown to the user.
      
      When no values are in the set, this indicates that either the attribute 
      is not supported or that none of the status conditions described 
      below are present.
      
      The value subjectToTest indicates the resource is available but tests 
      may be conducted simultaneously at unpredictable times, which 
      may cause it to exhibit unusual characteristics.
      
      The value partOfServicesLocked indicates that part of the service is 
      restricted from users of a resource. The adminState is unlocked.
      
      The value reservedForTest indicates that the component is 
      administratively unavailable because it is undergoing a test 
      procedure. The adminState is locked.
      
      The value suspended indicates that the service has been 
      administratively suspended.

      Description of bits:
      subjectToTest(0)
      partOfServicesLocked(1)
      reservedForTest(2)
      suspended(3)"
::= { mscFrNniDlciStateEntry 6 }

mscFrNniDlciAlarmStatus OBJECT-TYPE
   SYNTAX     OCTET STRING (SIZE (1))
   ACCESS     read-only
   STATUS     mandatory
   DESCRIPTION
     "If supported by the component, this attribute indicates the OSI 
      Alarm status of the component. Note that, even though it is defined 
      as a multi-valued set, at most one value is shown to the user.
      
      When no values are in the set, this indicates that either the attribute 
      is not supported or that none of the status conditions described 
      below are present.
      
      The value underRepair indicates the component is currently being 
      repaired. The operationalState is enabled or disabled.
      
      The value critical indicates one or more critical alarms are 
      outstanding against the component. Other, less severe, alarms may 
      also be outstanding. The operationalState is enabled or disabled.
      
      The value major indicates one or more major alarms are 
      outstanding against the component. Other, less severe, alarms may 
      also be outstanding. The operationalState is enabled or disabled.
      
      The value minor indicates one or more minor alarms are 
      outstanding against the component. Other, less severe, alarms may 
      also be outstanding. The operationalState is enabled or disabled.
      
      The value alarmOutstanding generically indicates that an alarm of 
      some severity is outstanding against the component.

      Description of bits:
      underRepair(0)
      critical(1)
      major(2)
      minor(3)
      alarmOutstanding(4)"
::= { mscFrNniDlciStateEntry 7 }

mscFrNniDlciStandbyStatus OBJECT-TYPE
   SYNTAX     INTEGER  {
                 hotStandby(0),
                 coldStandby(1),
                 providingService(2),
                 notSet(15) }
   ACCESS     read-only
   STATUS     mandatory
   DESCRIPTION
     "If supported by the component, this attribute indicates the OSI 
      Standby status of the component.
      
      The value notSet indicates that either the attribute is not supported 
      or that none of the status conditions described below are present. 
      Note that this is a non-standard value, used because the original 
      specification indicated this attribute was set-valued and thus, did not 
      provide a value to indicate that none of the other three are 
      applicable.
      
      The value hotStandby indicates that the resource is not providing 
      service but will be immediately able to take over the role of the 
      resource to be backed up, without initialization activity, and 
      containing the same information as the resource to be backed up.
      
      The value coldStandby indicates the resource is a backup for 
      another resource but will not be immediately able to take over the 
      role of the backed up resource and will require some initialization 
      activity.
      
      The value providingService indicates that this component, as a 
      backup resource, is currently backing up another resource."
   DEFVAL     { notSet }
::= { mscFrNniDlciStateEntry 8 }

mscFrNniDlciUnknownStatus OBJECT-TYPE
   SYNTAX     INTEGER  {
                 false(0),
                 true(1) }
   ACCESS     read-only
   STATUS     mandatory
   DESCRIPTION
     "This attribute indicates the OSI Unknown status of the component.
      
      The value false indicates that all of the other OSI State and Status 
      attribute values can be considered accurate.
      
      The value true indicates that the actual state of the component is not 
      known for sure."
   DEFVAL     { false }
::= { mscFrNniDlciStateEntry 9 }

mscFrNniDlciAbitTable OBJECT-TYPE
   SYNTAX     SEQUENCE OF MscFrNniDlciAbitEntry
   ACCESS     not-accessible
   STATUS     mandatory
   DESCRIPTION
     "This group contains the A-Bit status information for this Data Link 
      Connection Identifier."
::= { mscFrNniDlci 12 }

mscFrNniDlciAbitEntry OBJECT-TYPE
   SYNTAX     MscFrNniDlciAbitEntry
   ACCESS     not-accessible
   STATUS     mandatory
   DESCRIPTION
     "An entry in the mscFrNniDlciAbitTable."
   INDEX {
      mscFrNniIndex,
      mscFrNniDlciIndex }
::= { mscFrNniDlciAbitTable 1 }

MscFrNniDlciAbitEntry ::= SEQUENCE {
   mscFrNniDlciABitStatusToIf
      INTEGER,
   mscFrNniDlciABitReasonToIf
      INTEGER,
   mscFrNniDlciABitStatusFromIf
      INTEGER,
   mscFrNniDlciABitReasonFromIf
      INTEGER,
   mscFrNniDlciLoopbackState
      INTEGER }

mscFrNniDlciABitStatusToIf OBJECT-TYPE
   SYNTAX     INTEGER  {
                 inactive(0),
                 active(1),
                 notApplicable(2) }
   ACCESS     read-only
   STATUS     mandatory
   DESCRIPTION
     "This attribute is the most recent A-bit status sent to the interface. 
      The A-bit status is part of the LMI protocol, and indicates 
      willingness to accept data from the local interface.
      
      inactive - the Frame Relay service discards all data offered from the 
      local interface.
      
      active - the Frame Relay service tries to process all data offered 
      from the local interface.
      
      notApplicable - the DLCI is switched, so this attribute is ignored."
   DEFVAL     { inactive }
::= { mscFrNniDlciAbitEntry 1 }

mscFrNniDlciABitReasonToIf OBJECT-TYPE
   SYNTAX     INTEGER  {
                 notApplicable(0),
                 remoteUserSignaled(1),
                 localLmiError(2),
                 remoteLmiError(3),
                 localLinkDown(4),
                 remoteLinkDown(5),
                 pvcSpvcDown(6),
                 userNotAuthorized(8),
                 resourceNotAvailable(9),
                 dlciCollisionAtNni(10) }
   ACCESS     read-only
   STATUS     mandatory
   DESCRIPTION
     "This attribute provides the reason (if any) for an inactive status to 
      be sent to the interface. This reason is notApplicable for an active 
      status."
   DEFVAL     { notApplicable }
::= { mscFrNniDlciAbitEntry 2 }

mscFrNniDlciABitStatusFromIf OBJECT-TYPE
   SYNTAX     INTEGER  {
                 inactive(0),
                 active(1),
                 notApplicable(2) }
   ACCESS     read-only
   STATUS     mandatory
   DESCRIPTION
     "This attribute is the most recent A-Bit status received from the 
      interface.
      
      inactive - the Frame Relay service informs the remote DLCI not to 
      send user data to this interface.
      
      active - the Frame Relay service informs the remote DLCI that it is 
      okay to send user data to this interface.
      
      notApplicable - the DLCI is switched, so this attribute is ignored."
   DEFVAL     { inactive }
::= { mscFrNniDlciAbitEntry 3 }

mscFrNniDlciABitReasonFromIf OBJECT-TYPE
   SYNTAX     INTEGER  {
                 notApplicable(0),
                 remoteUserSignaled(1),
                 localLmiError(2),
                 localLinkDown(4),
                 missingFromLmiReport(7) }
   ACCESS     read-only
   STATUS     mandatory
   DESCRIPTION
     "This attribute provides the reason (if any) for an inactive status to 
      be sent to the subnet. This reason is notApplicable for an active 
      status."
   DEFVAL     { notApplicable }
::= { mscFrNniDlciAbitEntry 4 }

mscFrNniDlciLoopbackState OBJECT-TYPE
   SYNTAX     INTEGER  {
                 off(0),
                 on(1) }
   ACCESS     read-only
   STATUS     mandatory
   DESCRIPTION
     "This attribute has the value on when the DLCI is in loopback mode 
      and off otherwise. The loopback command verbs start and stop are 
      used to initiate and terminate the loopback mode for a DLCI. While 
      loopbackState is on, the local LMI will report to the interface the A-
      bit status as active. Also an active A-bit signal will be reliably 
      propagated across the subnet to the remote DLCI."
   DEFVAL     { off }
::= { mscFrNniDlciAbitEntry 5 }

mscFrNniDlciSpOpTable OBJECT-TYPE
   SYNTAX     SEQUENCE OF MscFrNniDlciSpOpEntry
   ACCESS     not-accessible
   STATUS     mandatory
   DESCRIPTION
     "This group defines the service and traffic parameters specific to this 
      instance of DLCI. In the case of permanent (PVC and P-SPVC) 
      DLCIs, the values of attributes with the exception of the 
      measurementInterval reflect the provisioning under the FrNni Dlci 
      Sp component. In the case of switched (SVC and S-SPVC) DLCIs, 
      the values of attributes reflect the service parameter negotiations 
      between what is provisioned under the FrNni Sig component and 
      the signaled parameters."
::= { mscFrNniDlci 13 }

mscFrNniDlciSpOpEntry OBJECT-TYPE
   SYNTAX     MscFrNniDlciSpOpEntry
   ACCESS     not-accessible
   STATUS     mandatory
   DESCRIPTION
     "An entry in the mscFrNniDlciSpOpTable."
   INDEX {
      mscFrNniIndex,
      mscFrNniDlciIndex }
::= { mscFrNniDlciSpOpTable 1 }

MscFrNniDlciSpOpEntry ::= SEQUENCE {
   mscFrNniDlciMaximumFrameSize
      Unsigned32,
   mscFrNniDlciRateEnforcement
      INTEGER,
   mscFrNniDlciCommittedInformationRate
      Unsigned32,
   mscFrNniDlciCommittedBurstSize
      Unsigned32,
   mscFrNniDlciExcessBurstSize
      Unsigned32,
   mscFrNniDlciMeasurementInterval
      Unsigned32,
   mscFrNniDlciRateAdaptation
      INTEGER,
   mscFrNniDlciAccounting
      INTEGER,
   mscFrNniDlciEmissionPriorityToIf
      INTEGER,
   mscFrNniDlciTransferPriToNwk
      Unsigned32,
   mscFrNniDlciTransferPriFromNwk
      Unsigned32 }

mscFrNniDlciMaximumFrameSize OBJECT-TYPE
   SYNTAX     Unsigned32 (1..8187)
   ACCESS     read-only
   STATUS     mandatory
   DESCRIPTION
     "This attribute indicates the maximum number of octets which may 
      be included in the information field. The frame relay header and 
      CRC octets are not included in this definition. This attribute 
      corresponds to the dN1 parameter described in the Vendor Forum 
      Specification."
::= { mscFrNniDlciSpOpEntry 1 }

mscFrNniDlciRateEnforcement OBJECT-TYPE
   SYNTAX     INTEGER  {
                 off(0),
                 on(1) }
   ACCESS     read-only
   STATUS     obsolete
   DESCRIPTION
     "This attribute is obsolete. It provided the information which is now 
      represented by the provisionable attribute rateEnforcement under 
      the ServiceParameters component."
::= { mscFrNniDlciSpOpEntry 2 }

mscFrNniDlciCommittedInformationRate OBJECT-TYPE
   SYNTAX     Unsigned32 (0..2048000)
   ACCESS     read-only
   STATUS     mandatory
   DESCRIPTION
     "This attribute indicates the committed information rate (CIR) in bits 
      per second (bit/s). When rateEnforcement is set to on, cir is the rate 
      at which the network agrees to transfer information under normal 
      conditions. This rate is measured over a measurement interval (t) 
      that is determined internally based on CIR and the committed burst 
      size (Bc). An exception to this occurs when CIR is provisioned to 
      be zero, in which case the measurement interval (t) must be 
      provisioned explicitly.
      
      This attribute should be ignored when rateEnforcement is off."
::= { mscFrNniDlciSpOpEntry 3 }

mscFrNniDlciCommittedBurstSize OBJECT-TYPE
   SYNTAX     Unsigned32 (0..2048000)
   ACCESS     read-only
   STATUS     mandatory
   DESCRIPTION
     "This attribute indicates the committed burst size (Bc) in bits. bc is 
      the amount of data that a network agrees to transfer under normal 
      conditions over a measurement interval (t). Data marked DE=1 is 
      not accounted for in Bc.
      
      This attribute should be ignored when rateEnforcement is off."
::= { mscFrNniDlciSpOpEntry 4 }

mscFrNniDlciExcessBurstSize OBJECT-TYPE
   SYNTAX     Unsigned32 (0..2048000)
   ACCESS     read-only
   STATUS     mandatory
   DESCRIPTION
     "This attribute indicates the excess burst size (Be) in bits. Be is the 
      amount of uncommitted data that the network will attempt to deliver 
      over measurement interval T. Data marked DE=1 by the user or by 
      the network is accounted for here.
      
      This attribute should be ignored when rateEnforcement is off."
::= { mscFrNniDlciSpOpEntry 5 }

mscFrNniDlciMeasurementInterval OBJECT-TYPE
   SYNTAX     Unsigned32 (0..4294967295)
   ACCESS     read-only
   STATUS     mandatory
   DESCRIPTION
     "This attribute indicates the time interval (in milliseconds) over 
      which rates and burst sizes are measured.
      
      This attribute should be ignored when rateEnforcement is off."
::= { mscFrNniDlciSpOpEntry 6 }

mscFrNniDlciRateAdaptation OBJECT-TYPE
   SYNTAX     INTEGER  {
                 off(0),
                 on(1),
                 eirOnly(2) }
   ACCESS     read-only
   STATUS     obsolete
   DESCRIPTION
     "This attribute is obsolete. It provided the information which is now 
      represented by the provisionable attribute rateAdaptation under the 
      ServiceParameters component."
::= { mscFrNniDlciSpOpEntry 7 }

mscFrNniDlciAccounting OBJECT-TYPE
   SYNTAX     INTEGER  {
                 off(0),
                 on(1) }
   ACCESS     read-only
   STATUS     mandatory
   DESCRIPTION
     "This attribute indicates whether accounting data collection and 
      record generation is turned on at this DLCI. For accounting data 
      collection and record generation to be turned on, the accountingOn 
      bit and at least one of the accountCollection bits in the 
      DataNetworkAddress component must be set to on."
::= { mscFrNniDlciSpOpEntry 8 }

mscFrNniDlciEmissionPriorityToIf OBJECT-TYPE
   SYNTAX     INTEGER (0 | 1 | 2 | 3)
   ACCESS     read-only
   STATUS     mandatory
   DESCRIPTION
     "This attribute indicates the emission priority of frames sent to the 
      interface. A larger value denotes a higher priority."
::= { mscFrNniDlciSpOpEntry 9 }

mscFrNniDlciTransferPriToNwk OBJECT-TYPE
   SYNTAX     Unsigned32 (0..15)
   ACCESS     read-only
   STATUS     mandatory
   DESCRIPTION
     "This attribute indicates the priority at which data is transferred to 
      the network.
      
      The transfer priority is a preference configured for an application 
      according to its delay-sensitivity requirement. Frames with higher 
      transfer priority are served by the network before the frames with 
      lower priority. The transfer priority standard is defined to have 16 
      indices from 0 to 15. 
      
      Each transfer priority n, where n specifies the transfer priority 
      index, contains a default setting for routing class of service 
      (multimedia, delay, or throughput) and frame relay egress queue 
      (depending on the number of supported egress queues on the remote 
      end interface) specified by the routingClassOfService and 
      emissionPriority attributes provisioned in the Mod Frs DprsNet 
      Tpm/n component. The default mapping can be altered by a user if 
      required."
::= { mscFrNniDlciSpOpEntry 10 }

mscFrNniDlciTransferPriFromNwk OBJECT-TYPE
   SYNTAX     Unsigned32 (0..15)
   ACCESS     read-only
   STATUS     mandatory
   DESCRIPTION
     "This attribute indicates the priority at which data is transferred from 
      the network.
      
      The transfer priority is a preference configured for an application 
      according to its delay-sensitivity requirement. Frames with higher 
      transfer priority are served by the network before the frames with 
      lower priority. The transfer priority standard is defined to have 16 
      indices from 0 to 15.
      
      Each transfer priority n, where n specifies the transfer priority 
      index, contains a default setting for routing class of service 
      (multimedia, delay, or throughput) and frame relay egress queue 
      (depending on the number of supported egress queues on the remote 
      end interface) specified by the routingClassOfService and 
      emissionPriority attributes provisioned in the Mod Frs DprsNet 
      Tpm/n component. The default mapping can be altered by a user if 
      required."
::= { mscFrNniDlciSpOpEntry 11 }

mscFrNniDlciStatsTable OBJECT-TYPE
   SYNTAX     SEQUENCE OF MscFrNniDlciStatsEntry
   ACCESS     not-accessible
   STATUS     mandatory
   DESCRIPTION
     "This group contains the operational statistics for the Frame Relay 
      Data Link Connection Identifier."
::= { mscFrNniDlci 14 }

mscFrNniDlciStatsEntry OBJECT-TYPE
   SYNTAX     MscFrNniDlciStatsEntry
   ACCESS     not-accessible
   STATUS     mandatory
   DESCRIPTION
     "An entry in the mscFrNniDlciStatsTable."
   INDEX {
      mscFrNniIndex,
      mscFrNniDlciIndex }
::= { mscFrNniDlciStatsTable 1 }

MscFrNniDlciStatsEntry ::= SEQUENCE {
   mscFrNniDlciFrmToIf
      Unsigned32,
   mscFrNniDlciFecnFrmToIf
      Unsigned32,
   mscFrNniDlciBecnFrmToIf
      Unsigned32,
   mscFrNniDlciBciToSubnet
      Unsigned32,
   mscFrNniDlciDeFrmToIf
      Unsigned32,
   mscFrNniDlciDiscCongestedToIf
      Unsigned32,
   mscFrNniDlciDiscDeCongestedToIf
      Unsigned32,
   mscFrNniDlciFrmFromIf
      Unsigned32,
   mscFrNniDlciFecnFrmFromIf
      Unsigned32,
   mscFrNniDlciBecnFrmFromIf
      Unsigned32,
   mscFrNniDlciFciFromSubnet
      Unsigned32,
   mscFrNniDlciBciFromSubnet
      Unsigned32,
   mscFrNniDlciDeFrmFromIf
      Unsigned32,
   mscFrNniDlciExcessFrmFromIf
      Unsigned32,
   mscFrNniDlciDiscExcessFromIf
      Unsigned32,
   mscFrNniDlciDiscFrameAbit
      Unsigned32,
   mscFrNniDlciDiscCongestedFromIf
      Unsigned32,
   mscFrNniDlciDiscDeCongestedFromIf
      Unsigned32,
   mscFrNniDlciErrorShortFrmFromIf
      Unsigned32,
   mscFrNniDlciErrorLongFrmFromIf
      Unsigned32,
   mscFrNniDlciBecnFrmSetByService
      Unsigned32,
   mscFrNniDlciBytesToIf
      Unsigned32,
   mscFrNniDlciDeBytesToIf
      Unsigned32,
   mscFrNniDlciDiscCongestedToIfBytes
      Unsigned32,
   mscFrNniDlciDiscDeCongestedToIfBytes
      Unsigned32,
   mscFrNniDlciBytesFromIf
      Unsigned32,
   mscFrNniDlciDeBytesFromIf
      Unsigned32,
   mscFrNniDlciExcessBytesFromIf
      Unsigned32,
   mscFrNniDlciDiscExcessFromIfBytes
      Unsigned32,
   mscFrNniDlciDiscByteAbit
      Unsigned32,
   mscFrNniDlciDiscCongestedFromIfBytes
      Unsigned32,
   mscFrNniDlciDiscDeCongestedFromIfBytes
      Unsigned32,
   mscFrNniDlciErrorShortBytesFromIf
      Unsigned32,
   mscFrNniDlciErrorLongBytesFromIf
      Unsigned32,
   mscFrNniDlciRateAdaptReduct
      Unsigned32,
   mscFrNniDlciRateAdaptReductPeriod
      Unsigned32,
   mscFrNniDlciTransferPriorityToNetwork
      INTEGER,
   mscFrNniDlciTransferPriorityFromNetwork
      INTEGER,
   mscFrNniDlciCirPresent
      Unsigned32,
   mscFrNniDlciEirPresent
      Unsigned32 }

mscFrNniDlciFrmToIf OBJECT-TYPE
   SYNTAX     Unsigned32 (0..4294967295)
   ACCESS     read-only
   STATUS     mandatory
   DESCRIPTION
     "This attribute counts the frames sent out the interface. When the 
      maximum count is reached the count wraps to zero."
   DEFVAL     { 0 }
::= { mscFrNniDlciStatsEntry 1 }

mscFrNniDlciFecnFrmToIf OBJECT-TYPE
   SYNTAX     Unsigned32 (0..4294967295)
   ACCESS     read-only
   STATUS     mandatory
   DESCRIPTION
     "This attribute counts the frames sent to the interface with the 
      Forward Explicit Congestion Notification (FECN) bit set. When the 
      count reaches maximum it wraps to zero."
   DEFVAL     { 0 }
::= { mscFrNniDlciStatsEntry 2 }

mscFrNniDlciBecnFrmToIf OBJECT-TYPE
   SYNTAX     Unsigned32 (0..4294967295)
   ACCESS     read-only
   STATUS     mandatory
   DESCRIPTION
     "This attribute counts the frames sent to the interface with the 
      Backward Explicit Congestion Notification (BECN) bit set. When 
      the count reaches maximum it wraps to zero."
   DEFVAL     { 0 }
::= { mscFrNniDlciStatsEntry 3 }

mscFrNniDlciBciToSubnet OBJECT-TYPE
   SYNTAX     Unsigned32 (0..4294967295)
   ACCESS     read-only
   STATUS     mandatory
   DESCRIPTION
     "This attribute counts the frames sent into the local network with the 
      Backward Congestion Indication (BCI) bit set. When the count 
      reaches maximum it wraps to zero."
   DEFVAL     { 0 }
::= { mscFrNniDlciStatsEntry 4 }

mscFrNniDlciDeFrmToIf OBJECT-TYPE
   SYNTAX     Unsigned32 (0..4294967295)
   ACCESS     read-only
   STATUS     mandatory
   DESCRIPTION
     "This attribute counts the frames sent to the interface with the 
      Discard Eligibility (DE) bit set. When the count reaches maximum 
      it wraps to zero."
   DEFVAL     { 0 }
::= { mscFrNniDlciStatsEntry 5 }

mscFrNniDlciDiscCongestedToIf OBJECT-TYPE
   SYNTAX     Unsigned32 (0..4294967295)
   ACCESS     read-only
   STATUS     mandatory
   DESCRIPTION
     "This attribute counts the number of frame discards at the Frame 
      Relay service due to local congestion in the direction toward the 
      interface. When this count reaches maximum, it wraps to zero."
   DEFVAL     { 0 }
::= { mscFrNniDlciStatsEntry 6 }

mscFrNniDlciDiscDeCongestedToIf OBJECT-TYPE
   SYNTAX     Unsigned32 (0..4294967295)
   ACCESS     read-only
   STATUS     mandatory
   DESCRIPTION
     "This attribute counts the number of discarded frames, with the 
      Discard Eligibility (DE) bit set, at the Frame Relay service, due to 
      local congestion in the direction toward the interface. When this 
      count reaches maximum, it wraps to zero."
   DEFVAL     { 0 }
::= { mscFrNniDlciStatsEntry 7 }

mscFrNniDlciFrmFromIf OBJECT-TYPE
   SYNTAX     Unsigned32 (0..4294967295)
   ACCESS     read-only
   STATUS     mandatory
   DESCRIPTION
     "This attribute counts the frames received from the interface. It 
      includes the frames that are discarded due to error or excess. When 
      the maximum count is reached the count wraps to zero."
   DEFVAL     { 0 }
::= { mscFrNniDlciStatsEntry 8 }

mscFrNniDlciFecnFrmFromIf OBJECT-TYPE
   SYNTAX     Unsigned32 (0..4294967295)
   ACCESS     read-only
   STATUS     mandatory
   DESCRIPTION
     "This attribute counts the frames received from the interface with the 
      Forward Explicit Congestion Notification (FECN) bit set. When the 
      count reaches maximum it wraps to zero."
   DEFVAL     { 0 }
::= { mscFrNniDlciStatsEntry 9 }

mscFrNniDlciBecnFrmFromIf OBJECT-TYPE
   SYNTAX     Unsigned32 (0..4294967295)
   ACCESS     read-only
   STATUS     mandatory
   DESCRIPTION
     "This attribute counts the frames received from the interface with the 
      Backward Explicit Congestion Notification (BECN) bit set. When 
      the count reaches maximum it wraps to zero."
   DEFVAL     { 0 }
::= { mscFrNniDlciStatsEntry 10 }

mscFrNniDlciFciFromSubnet OBJECT-TYPE
   SYNTAX     Unsigned32 (0..4294967295)
   ACCESS     read-only
   STATUS     mandatory
   DESCRIPTION
     "This attribute counts the frames received from the network with the 
      Forward Congestion Indication (FCI) bit set. When the count 
      reaches maximum it wraps to zero."
   DEFVAL     { 0 }
::= { mscFrNniDlciStatsEntry 11 }

mscFrNniDlciBciFromSubnet OBJECT-TYPE
   SYNTAX     Unsigned32 (0..4294967295)
   ACCESS     read-only
   STATUS     mandatory
   DESCRIPTION
     "This attribute counts the frames received from the network with the 
      Backward Congestion Indication (BCI) bit set. When the count 
      reaches maximum it wraps to zero."
   DEFVAL     { 0 }
::= { mscFrNniDlciStatsEntry 12 }

mscFrNniDlciDeFrmFromIf OBJECT-TYPE
   SYNTAX     Unsigned32 (0..4294967295)
   ACCESS     read-only
   STATUS     mandatory
   DESCRIPTION
     "This attribute counts the frames received from the interface with the 
      Discard Eligibility (DE) bit set. When the count reaches maximum 
      it wraps to zero."
   DEFVAL     { 0 }
::= { mscFrNniDlciStatsEntry 13 }

mscFrNniDlciExcessFrmFromIf OBJECT-TYPE
   SYNTAX     Unsigned32 (0..4294967295)
   ACCESS     read-only
   STATUS     mandatory
   DESCRIPTION
     "This attribute counts the frames received from the interface with the 
      Discard Eligibility (DE) bit clear, but subsequently set by the 
      network due to rate enforcement. When the count reaches 
      maximum it wraps to zero."
   DEFVAL     { 0 }
::= { mscFrNniDlciStatsEntry 14 }

mscFrNniDlciDiscExcessFromIf OBJECT-TYPE
   SYNTAX     Unsigned32 (0..4294967295)
   ACCESS     read-only
   STATUS     mandatory
   DESCRIPTION
     "This attribute counts the frames which were discarded due to rate 
      enforcement. When the count reaches maximum it wraps to zero."
   DEFVAL     { 0 }
::= { mscFrNniDlciStatsEntry 15 }

mscFrNniDlciDiscFrameAbit OBJECT-TYPE
   SYNTAX     Unsigned32 (0..4294967295)
   ACCESS     read-only
   STATUS     mandatory
   DESCRIPTION
     "This attribute counts the number of frame discards at the Frame 
      Relay Service, due to an inactive PVC status, in the direction 
      toward the local network. When this count reaches maximum, it 
      wraps to zero."
   DEFVAL     { 0 }
::= { mscFrNniDlciStatsEntry 16 }

mscFrNniDlciDiscCongestedFromIf OBJECT-TYPE
   SYNTAX     Unsigned32 (0..4294967295)
   ACCESS     read-only
   STATUS     mandatory
   DESCRIPTION
     "This attribute counts the number of frame discards at the Frame 
      Relay service due to local congestion in the direction toward the 
      network. When this count reaches maximum, it wraps to zero."
   DEFVAL     { 0 }
::= { mscFrNniDlciStatsEntry 17 }

mscFrNniDlciDiscDeCongestedFromIf OBJECT-TYPE
   SYNTAX     Unsigned32 (0..4294967295)
   ACCESS     read-only
   STATUS     mandatory
   DESCRIPTION
     "This attribute counts the number of discarded frames, with the 
      Discard Eligibility (DE) bit set, at the Frame Relay service, due to 
      local congestion, in the direction toward the local network. When 
      this count reaches maximum, it wraps to zero."
   DEFVAL     { 0 }
::= { mscFrNniDlciStatsEntry 18 }

mscFrNniDlciErrorShortFrmFromIf OBJECT-TYPE
   SYNTAX     Unsigned32 (0..4294967295)
   ACCESS     read-only
   STATUS     mandatory
   DESCRIPTION
     "This attribute counts the frames received with 0 octets in the 
      information field. When the count reaches maximum it wraps to 
      zero."
   DEFVAL     { 0 }
::= { mscFrNniDlciStatsEntry 19 }

mscFrNniDlciErrorLongFrmFromIf OBJECT-TYPE
   SYNTAX     Unsigned32 (0..4294967295)
   ACCESS     read-only
   STATUS     mandatory
   DESCRIPTION
     "This attribute counts the frames received with number of octets in 
      the information field greater than the subscribed maximum. When 
      the count reaches maximum it wraps to zero. Frames whose lengths 
      are greater than the hardware receive buffer are ignored by the 
      hardware and are therefore not included in this count."
   DEFVAL     { 0 }
::= { mscFrNniDlciStatsEntry 20 }

mscFrNniDlciBecnFrmSetByService OBJECT-TYPE
   SYNTAX     Unsigned32 (0..4294967295)
   ACCESS     read-only
   STATUS     mandatory
   DESCRIPTION
     "This attribute counts the number of frames with BECN set by the 
      Frame Relay service. It is incremented whenever the Frame Relay 
      service sets BECN on a frame upon detecting local congestion. This 
      count is incremented regardless of whether the frame already bears 
      a set BECN bit since its use is to determine the place of congestion. 
      When the count reaches maximum, it wraps to zero."
   DEFVAL     { 0 }
::= { mscFrNniDlciStatsEntry 21 }

mscFrNniDlciBytesToIf OBJECT-TYPE
   SYNTAX     Unsigned32 (0..4294967295)
   ACCESS     read-only
   STATUS     mandatory
   DESCRIPTION
     "This attribute counts the bytes sent out the interface. When the 
      maximum count is reached the count wraps to zero."
   DEFVAL     { 0 }
::= { mscFrNniDlciStatsEntry 22 }

mscFrNniDlciDeBytesToIf OBJECT-TYPE
   SYNTAX     Unsigned32 (0..4294967295)
   ACCESS     read-only
   STATUS     mandatory
   DESCRIPTION
     "This attribute counts the bytes sent to the interface with the Discard 
      Eligibility (DE) bit set. When the count reaches maximum it wraps 
      to zero."
   DEFVAL     { 0 }
::= { mscFrNniDlciStatsEntry 23 }

mscFrNniDlciDiscCongestedToIfBytes OBJECT-TYPE
   SYNTAX     Unsigned32 (0..4294967295)
   ACCESS     read-only
   STATUS     mandatory
   DESCRIPTION
     "This attribute counts the number of byte discards at the Frame 
      Relay service due to local congestion in the direction toward the 
      link. When this count reaches maximum, it wraps to zero."
   DEFVAL     { 0 }
::= { mscFrNniDlciStatsEntry 24 }

mscFrNniDlciDiscDeCongestedToIfBytes OBJECT-TYPE
   SYNTAX     Unsigned32 (0..4294967295)
   ACCESS     read-only
   STATUS     mandatory
   DESCRIPTION
     "This attribute counts the number of discard eligible (DE=1) byte 
      discards at the Frame Relay service due to local congestion in the 
      direction toward the link. When the maximum count is reached the 
      count wraps to zero."
   DEFVAL     { 0 }
::= { mscFrNniDlciStatsEntry 25 }

mscFrNniDlciBytesFromIf OBJECT-TYPE
   SYNTAX     Unsigned32 (0..4294967295)
   ACCESS     read-only
   STATUS     mandatory
   DESCRIPTION
     "This attribute counts the bytes received from the interface. Bytes 
      that are discarded due to error or excess are not counted. When the 
      maximum count is reached the count wraps to zero."
   DEFVAL     { 0 }
::= { mscFrNniDlciStatsEntry 26 }

mscFrNniDlciDeBytesFromIf OBJECT-TYPE
   SYNTAX     Unsigned32 (0..4294967295)
   ACCESS     read-only
   STATUS     mandatory
   DESCRIPTION
     "This attribute counts the bytes received from the interface with the 
      Discard Eligibility (DE) bit set. When the count reaches maximum 
      it wraps to zero."
   DEFVAL     { 0 }
::= { mscFrNniDlciStatsEntry 27 }

mscFrNniDlciExcessBytesFromIf OBJECT-TYPE
   SYNTAX     Unsigned32 (0..4294967295)
   ACCESS     read-only
   STATUS     mandatory
   DESCRIPTION
     "This attribute counts the bytes received from the interface with the 
      Discard Eligibility (DE) bit clear, but subsequently set by the 
      network due to rate enforcement. When the count reaches 
      maximum it wraps to zero."
   DEFVAL     { 0 }
::= { mscFrNniDlciStatsEntry 28 }

mscFrNniDlciDiscExcessFromIfBytes OBJECT-TYPE
   SYNTAX     Unsigned32 (0..4294967295)
   ACCESS     read-only
   STATUS     mandatory
   DESCRIPTION
     "This attribute counts the bytes which were discarded due to rate 
      enforcement. When the count reaches maximum it wraps to zero."
   DEFVAL     { 0 }
::= { mscFrNniDlciStatsEntry 29 }

mscFrNniDlciDiscByteAbit OBJECT-TYPE
   SYNTAX     Unsigned32 (0..4294967295)
   ACCESS     read-only
   STATUS     mandatory
   DESCRIPTION
     "This attribute counts the bytes which were discarded due to aBit 
      turned off."
   DEFVAL     { 0 }
::= { mscFrNniDlciStatsEntry 30 }

mscFrNniDlciDiscCongestedFromIfBytes OBJECT-TYPE
   SYNTAX     Unsigned32 (0..4294967295)
   ACCESS     read-only
   STATUS     mandatory
   DESCRIPTION
     "This attribute counts the number of byte discards at the Frame 
      Relay service due to local congestion in the direction toward the 
      network. When this count reaches maximum, it wraps to zero."
   DEFVAL     { 0 }
::= { mscFrNniDlciStatsEntry 31 }

mscFrNniDlciDiscDeCongestedFromIfBytes OBJECT-TYPE
   SYNTAX     Unsigned32 (0..4294967295)
   ACCESS     read-only
   STATUS     mandatory
   DESCRIPTION
     "This attribute counts the number of discard eligible (DE=1) byte 
      discards at the Frame Relay service due to local congestion in the 
      direction toward the network. When the maximum count is reached 
      the count wraps to zero."
   DEFVAL     { 0 }
::= { mscFrNniDlciStatsEntry 32 }

mscFrNniDlciErrorShortBytesFromIf OBJECT-TYPE
   SYNTAX     Unsigned32 (0..4294967295)
   ACCESS     read-only
   STATUS     mandatory
   DESCRIPTION
     "This attribute counts the bytes received with 0 octets in the 
      information field. When the count reaches maximum it wraps to 
      zero."
   DEFVAL     { 0 }
::= { mscFrNniDlciStatsEntry 33 }

mscFrNniDlciErrorLongBytesFromIf OBJECT-TYPE
   SYNTAX     Unsigned32 (0..4294967295)
   ACCESS     read-only
   STATUS     mandatory
   DESCRIPTION
     "This attribute counts the bytes received with number of octets in the 
      information field greater than the subscribed maximum. When the 
      count reaches maximum it wraps to zero. Bytes whose lengths are 
      greater than the hardware receive buffer are ignored by the 
      hardware and are therefore not included in this count."
   DEFVAL     { 0 }
::= { mscFrNniDlciStatsEntry 34 }

mscFrNniDlciRateAdaptReduct OBJECT-TYPE
   SYNTAX     Unsigned32 (0..4294967295)
   ACCESS     read-only
   STATUS     mandatory
   DESCRIPTION
     "This attribute counts the number of rate reductions due to rate 
      adaptation. Rate adaptation causes the allowed rate to be reduced in 
      steps. After each reduction, a period of time is awaited before 
      further action is taken. At the end of this period, the allowed rate is 
      further reduced if congestion is still prevalent. When this count 
      reaches maximum, it wraps to zero."
   DEFVAL     { 0 }
::= { mscFrNniDlciStatsEntry 35 }

mscFrNniDlciRateAdaptReductPeriod OBJECT-TYPE
   SYNTAX     Unsigned32 (0..4294967295)
   ACCESS     read-only
   STATUS     mandatory
   DESCRIPTION
     "This attribute provides a cumulative count of the amount of time 
      that rate adaptation procedures have been in effect. When this count 
      reaches maximum, it wraps to zero."
   DEFVAL     { 0 }
::= { mscFrNniDlciStatsEntry 36 }

mscFrNniDlciTransferPriorityToNetwork OBJECT-TYPE
   SYNTAX     INTEGER (0..15)
   ACCESS     read-only
   STATUS     obsolete
   DESCRIPTION
     "This attribute is obsolete. It is replaced by attribute 
      transferPriorityToNetwork under group 
      FrsNniDataLinkConnectionIdentifierServiceParametersOp."
::= { mscFrNniDlciStatsEntry 37 }

mscFrNniDlciTransferPriorityFromNetwork OBJECT-TYPE
   SYNTAX     INTEGER (0..15)
   ACCESS     read-only
   STATUS     obsolete
   DESCRIPTION
     "This attribute is obsolete. It is replaced by attribute 
      transferPriorityFromNetwork under group 
      FrsNniDataLinkConnectionIdentifierServiceParametersOp."
::= { mscFrNniDlciStatsEntry 38 }

mscFrNniDlciCirPresent OBJECT-TYPE
   SYNTAX     Unsigned32 (0..4294967295)
   ACCESS     read-only
   STATUS     mandatory
   DESCRIPTION
     "This attribute provides the actual Committed Information Rate 
      (CIR) enforced for this DLCI. This number is in units of 800 bits/
      sec, since that is the internal resolution of Passport rate 
      enforcement. If rateEnforcement is off, then this number does not 
      have meaning. Normally, this attribute matches the provisioned CIR 
      for the DLCI. But when Rate Adaptation is active, then this number 
      will vary to represent the actual Allowed CIR at the moment that 
      this attribute is collected."
   DEFVAL     { 0 }
::= { mscFrNniDlciStatsEntry 39 }

mscFrNniDlciEirPresent OBJECT-TYPE
   SYNTAX     Unsigned32 (0..4294967295)
   ACCESS     read-only
   STATUS     mandatory
   DESCRIPTION
     "This attribute provides the actual Excess Information Rate (EIR) 
      enforced for this DLCI. This number is in units of 800 bits/sec, 
      since that is the internal resolution of Passport rate enforcement. If 
      rateEnforcement is off, then this number does not have meaning. 
      Normally, this attribute matches the provisioned EIR for the DLCI. 
      But when Rate Adaptation is active, then this number will vary to 
      represent the actual Allowed EIR at the moment that this attribute is 
      collected."
   DEFVAL     { 0 }
::= { mscFrNniDlciStatsEntry 40 }

mscFrNniDlciIntTable OBJECT-TYPE
   SYNTAX     SEQUENCE OF MscFrNniDlciIntEntry
   ACCESS     not-accessible
   STATUS     mandatory
   DESCRIPTION
     "This group contains the operational statistics for the Frame Relay 
      Data Link Connection Identifier interval data (accounting data)."
::= { mscFrNniDlci 15 }

mscFrNniDlciIntEntry OBJECT-TYPE
   SYNTAX     MscFrNniDlciIntEntry
   ACCESS     not-accessible
   STATUS     mandatory
   DESCRIPTION
     "An entry in the mscFrNniDlciIntTable."
   INDEX {
      mscFrNniIndex,
      mscFrNniDlciIndex }
::= { mscFrNniDlciIntTable 1 }

MscFrNniDlciIntEntry ::= SEQUENCE {
   mscFrNniDlciStartTime
      EnterpriseDateAndTime,
   mscFrNniDlciTotalIngressBytes
      Unsigned64,
   mscFrNniDlciTotalEgressBytes
      Unsigned64,
   mscFrNniDlciEirIngressBytes
      Unsigned64,
   mscFrNniDlciEirEgressBytes
      Unsigned64,
   mscFrNniDlciDiscardedBytes
      Unsigned64,
   mscFrNniDlciTotalIngressSegFrm
      Unsigned32,
   mscFrNniDlciTotalEgressSegFrm
      Unsigned32,
   mscFrNniDlciEirIngressSegFrm
      Unsigned32,
   mscFrNniDlciEirEgressSegFrm
      Unsigned32,
   mscFrNniDlciDiscardedSegFrm
      Unsigned32,
   mscFrNniDlciCirPresentObs
      Unsigned32,
   mscFrNniDlciEirPresentObs
      Unsigned32,
   mscFrNniDlciRateEnforcementPresent
      INTEGER,
   mscFrNniDlciRateAdaptationPresent
      INTEGER,
   mscFrNniDlciLocalRateAdaptOccurred
      INTEGER,
   mscFrNniDlciCallReferenceNumber
      Hex,
   mscFrNniDlciElapsedDifference
      Unsigned32,
   mscFrNniDlciCallRefNumber
      Unsigned32 }

mscFrNniDlciStartTime OBJECT-TYPE
   SYNTAX     EnterpriseDateAndTime (SIZE (0 | 19))
   ACCESS     read-only
   STATUS     mandatory
   DESCRIPTION
     "This attribute indicates the start time of this interval period. If Vc 
      spans 12 hour time or time of day change startTime reflects new 
      time as recorded at 12 hour periods or time of day changes. A new 
      interval period is started each time an accounting record is 
      generated."
::= { mscFrNniDlciIntEntry 1 }

mscFrNniDlciTotalIngressBytes OBJECT-TYPE
   SYNTAX     Unsigned64 (SIZE (8))
   ACCESS     read-only
   STATUS     mandatory
   DESCRIPTION
     "This attribute counts the total bytes received from the interface 
      since the start of the interval period. The start of the interval period 
      is captured in the startTime attribute. The count is reset to zero 
      when an accounting record is generated."
::= { mscFrNniDlciIntEntry 2 }

mscFrNniDlciTotalEgressBytes OBJECT-TYPE
   SYNTAX     Unsigned64 (SIZE (8))
   ACCESS     read-only
   STATUS     mandatory
   DESCRIPTION
     "This attribute counts the total bytes sent to the interface since the 
      start of the interval period. The start of the interval period is 
      captured in the startTime attribute. The count is reset to zero when 
      an accounting record is generated."
::= { mscFrNniDlciIntEntry 3 }

mscFrNniDlciEirIngressBytes OBJECT-TYPE
   SYNTAX     Unsigned64 (SIZE (8))
   ACCESS     read-only
   STATUS     mandatory
   DESCRIPTION
     "This attribute counts the total bytes with the Discard Eligibility 
      (DE) bit set sent to the subnet since the start of the interval period. 
      The start of the interval period is captured in the startTime attribute. 
      The count is reset to zero when an accounting record is generated."
::= { mscFrNniDlciIntEntry 4 }

mscFrNniDlciEirEgressBytes OBJECT-TYPE
   SYNTAX     Unsigned64 (SIZE (8))
   ACCESS     read-only
   STATUS     mandatory
   DESCRIPTION
     "This attribute counts the total bytes with the Discard Eligibility 
      (DE) bit set sent to the interface since the start of the interval 
      period. The start of the interval period is captured in the startTime 
      attribute. The count is reset to zero when an accounting record is 
      generated."
::= { mscFrNniDlciIntEntry 5 }

mscFrNniDlciDiscardedBytes OBJECT-TYPE
   SYNTAX     Unsigned64 (SIZE (8))
   ACCESS     read-only
   STATUS     mandatory
   DESCRIPTION
     "This attribute counts the total bytes in invalid frames received from 
      the interface and discarded at the DLCI since the start of the interval 
      period. This count is a sum of octets in frames discarded due to the 
      number of octets in the information field greater than the subscribed 
      maximum or equal to 0, due to aBit turned off, or due to rate 
      enforcement. The start of the interval period is captured in the 
      startTime attribute. The count is reset to zero when an accounting 
      record is generated."
::= { mscFrNniDlciIntEntry 6 }

mscFrNniDlciTotalIngressSegFrm OBJECT-TYPE
   SYNTAX     Unsigned32 (0..4294967295)
   ACCESS     read-only
   STATUS     mandatory
   DESCRIPTION
     "If the value of the unitsCounted attribute in moduleData component 
      is segments, this attribute counts the total number of segments in 
      frames received from the interface since the start of the interval 
      period. If the value of the unitsCounted attribute in moduleData 
      component is frames, this attribute counts the total number of 
      frames received from the interface since the start of the interval 
      period. The start of the interval period is captured in the startTime 
      attribute. The count is reset to zero when an accounting record is 
      generated."
   DEFVAL     { 0 }
::= { mscFrNniDlciIntEntry 7 }

mscFrNniDlciTotalEgressSegFrm OBJECT-TYPE
   SYNTAX     Unsigned32 (0..4294967295)
   ACCESS     read-only
   STATUS     mandatory
   DESCRIPTION
     "If the value of the unitsCounted attribute in moduleData component 
      is segments, this attribute counts the total number of segments in 
      frames sent to the interface since the start of the interval period. If 
      the value of the unitsCounted attribute in moduleData component is 
      frames, this attribute counts the total number of frames sent to the 
      interface since the start of the interval period. The start of the 
      interval period is captured in the startTime attribute. The count is 
      reset to zero when an accounting record is generated."
   DEFVAL     { 0 }
::= { mscFrNniDlciIntEntry 8 }

mscFrNniDlciEirIngressSegFrm OBJECT-TYPE
   SYNTAX     Unsigned32 (0..4294967295)
   ACCESS     read-only
   STATUS     mandatory
   DESCRIPTION
     "If the value of the unitsCounted attribute in moduleData component 
      is segments, this attribute counts the number of segments in frames 
      with the Discard Eligibility (DE) bit set sent to the subnet since the 
      start of the interval period. If the value of the unitsCounted attribute 
      in moduleData component is frames, this attribute counts the 
      number of frames with the Discard Eligibility (DE) bit set sent to 
      the subnet since the start of the interval period. The start of the 
      interval period is captured in the startTime attribute. The count is 
      reset to zero when an accounting record is generated."
   DEFVAL     { 0 }
::= { mscFrNniDlciIntEntry 9 }

mscFrNniDlciEirEgressSegFrm OBJECT-TYPE
   SYNTAX     Unsigned32 (0..4294967295)
   ACCESS     read-only
   STATUS     mandatory
   DESCRIPTION
     "If the value of the unitsCounted attribute in moduleData component 
      is segments, this attribute counts the number of segments in frames 
      with the Discard Eligibility (DE) bit set sent to the interface since 
      the start of the interval period. If the value of the unitsCounted 
      attribute in moduleData component is frames, this attribute counts 
      the number of frames with the Discard Eligibility (DE) bit set sent 
      to the interface since the start of the interval period. The start of the 
      interval period is captured in the startTime attribute. The count is 
      reset to zero when an accounting record is generated"
   DEFVAL     { 0 }
::= { mscFrNniDlciIntEntry 10 }

mscFrNniDlciDiscardedSegFrm OBJECT-TYPE
   SYNTAX     Unsigned32 (0..4294967295)
   ACCESS     read-only
   STATUS     mandatory
   DESCRIPTION
     "If the value of the unitsCounted attribute in moduleData component 
      is segments, this attribute counts the number of segments in invalid 
      frames received from the interface and discarded at the DLCI. If the 
      value of the unitsCounted attribute in moduleData component is 
      frames, this attribute counts the number of invalid frames received 
      from the interface and discarded at the DLCI. Segments of frames 
      are counted since the start of the interval period. The count is reset 
      to zero when an accounting record is generated. The count is a sum 
      of segments in frames or frames discarded due to the number of 
      octets in the information field greater than the subscribed maximum 
      or equal to 0, due to aBit turned off, or due to rate enforcement."
   DEFVAL     { 0 }
::= { mscFrNniDlciIntEntry 11 }

mscFrNniDlciCirPresentObs OBJECT-TYPE
   SYNTAX     Unsigned32 (0..4294967295)
   ACCESS     read-only
   STATUS     obsolete
   DESCRIPTION
     "This attribute has moved to the statistics subgroup. See cirPresent.."
   DEFVAL     { 0 }
::= { mscFrNniDlciIntEntry 12 }

mscFrNniDlciEirPresentObs OBJECT-TYPE
   SYNTAX     Unsigned32 (0..4294967295)
   ACCESS     read-only
   STATUS     obsolete
   DESCRIPTION
     "This attribute has moved to the statistics group. See eirPresent."
   DEFVAL     { 0 }
::= { mscFrNniDlciIntEntry 13 }

mscFrNniDlciRateEnforcementPresent OBJECT-TYPE
   SYNTAX     INTEGER  {
                 off(0),
                 on(1) }
   ACCESS     read-only
   STATUS     obsolete
   DESCRIPTION
     "This attribute is obsolete. See the provisionable rateEnforcement 
      attribute."
   DEFVAL     { off }
::= { mscFrNniDlciIntEntry 14 }

mscFrNniDlciRateAdaptationPresent OBJECT-TYPE
   SYNTAX     INTEGER  {
                 off(0),
                 on(1) }
   ACCESS     read-only
   STATUS     obsolete
   DESCRIPTION
     "This attribute is obsolete. See the provisionable rateAdaptation 
      attribute."
   DEFVAL     { off }
::= { mscFrNniDlciIntEntry 15 }

mscFrNniDlciLocalRateAdaptOccurred OBJECT-TYPE
   SYNTAX     INTEGER  {
                 no(0),
                 yes(1) }
   ACCESS     read-only
   STATUS     mandatory
   DESCRIPTION
     "This attribute indicates whether rate adaptation has occurred on this 
      user Data Link Connection on this Frame Relay interface. The value 
      is set to no when an accounting record is generated."
   DEFVAL     { no }
::= { mscFrNniDlciIntEntry 16 }

mscFrNniDlciCallReferenceNumber OBJECT-TYPE
   SYNTAX     Hex (0..16777215)
   ACCESS     read-only
   STATUS     obsolete
   DESCRIPTION
     "This attribute is obsoleted and replaced by callRefNumber."
   DEFVAL     { 0 }
::= { mscFrNniDlciIntEntry 17 }

mscFrNniDlciElapsedDifference OBJECT-TYPE
   SYNTAX     Unsigned32 (0..4294967295)
   ACCESS     read-only
   STATUS     mandatory
   DESCRIPTION
     "This attribute indicates the elapsed time representing the period of 
      this interval data. It is elapsed time in 0.1 second increments since 
      the call started."
   DEFVAL     { 0 }
::= { mscFrNniDlciIntEntry 18 }

mscFrNniDlciCallRefNumber OBJECT-TYPE
   SYNTAX     Unsigned32 (0..4294967295)
   ACCESS     read-only
   STATUS     mandatory
   DESCRIPTION
     "This attribute indicates the call reference number which is a unique 
      number generated by the switch. The same Call Reference Number 
      is stored in the interval data (accounting record) at both ends of the 
      call. It can be used as one of the attributes in matching duplicate 
      records generated at each end of the connection."
   DEFVAL     { 0 }
::= { mscFrNniDlciIntEntry 20 }

mscFrNniDlciCalldTable OBJECT-TYPE
   SYNTAX     SEQUENCE OF MscFrNniDlciCalldEntry
   ACCESS     not-accessible
   STATUS     mandatory
   DESCRIPTION
     "This group of attributes describes the characteristics of the call such 
      as call type and call state."
::= { mscFrNniDlci 16 }

mscFrNniDlciCalldEntry OBJECT-TYPE
   SYNTAX     MscFrNniDlciCalldEntry
   ACCESS     not-accessible
   STATUS     mandatory
   DESCRIPTION
     "An entry in the mscFrNniDlciCalldTable."
   INDEX {
      mscFrNniIndex,
      mscFrNniDlciIndex }
::= { mscFrNniDlciCalldTable 1 }

MscFrNniDlciCalldEntry ::= SEQUENCE {
   mscFrNniDlciCallType
      INTEGER,
   mscFrNniDlciCallState
      INTEGER,
   mscFrNniDlciCallReference
      Unsigned32 }

mscFrNniDlciCallType OBJECT-TYPE
   SYNTAX     INTEGER  {
                 pvc(0),
                 svc(1),
                 spvc(2) }
   ACCESS     read-only
   STATUS     mandatory
   DESCRIPTION
     "This attribute indicates whether this DLCI is a permancent virtual 
      circuit (PVC), a switched virtual circuit (SVC), or a switched 
      permament virtual circuit (SPVC)."
::= { mscFrNniDlciCalldEntry 1 }

mscFrNniDlciCallState OBJECT-TYPE
   SYNTAX     INTEGER  {
                 null(0),
                 callInitiated(1),
                 callProceedingSent(3),
                 callPresent(6),
                 callProceedingReceived(9),
                 active(10),
                 releaseRequest(11),
                 releaseIndication(12),
                 notApplicable(20),
                 restartRequest(61),
                 restart(62) }
   ACCESS     read-only
   STATUS     mandatory
   DESCRIPTION
     "This attribute indicates the FRF.10 state of a switched call. The 
      value of this attribute for a permanent (PVC and P-SPVC) DLCI is 
      always notApplicable. In the description that follows, 'calling STE' 
      refers to the network who has initiated the SETUP request, and 
      'called STE' refers to the network that receives the request.
      
      State description:
      In the null state, the network has neither received nor sent call setup 
      requests for this DLCI.
      
      In the callInitiated state, the called STE has received a SETUP 
      message from the calling STE.
      
      In the callProceedingSent state, the called STE has sent a CALL 
      PROCEEDING message to the calling STE in response to the 
      SETUP message.
      
      In the callPresent state, the calling STE has sent a SETUP message 
      to the called STE but has not received a response.
      
      In the callProceedingReceived state, the calling STE has received a 
      CALL PROCEEDING message from the called STE in response to 
      a SETUP message.
      
      In the active state, either the called STE has sent a CONNECT 
      message to the calling STE, or the calling STE has received a 
      CONNECT from the called STE.
      
      In the releaseRequest state, the STE has sent a RELEASE message 
      to release the call and is waiting for a RELEASE COMPLETE 
      message.
      
      In the releaseIndication state, the STE has received a RELEASE 
      and sends a RELEASE COMPLETE message after releasing the 
      relevant call resources.
      
      In the restartRequest state, the STE has sent a RESTART request to 
      the other STE and is waiting for an acknowledgement.
      
      In the restart state, the STE has received a request for a restart from 
      the other STE and this STE has not returned an acknowledgement."
::= { mscFrNniDlciCalldEntry 2 }

mscFrNniDlciCallReference OBJECT-TYPE
   SYNTAX     Unsigned32 (0..32767)
   ACCESS     read-only
   STATUS     mandatory
   DESCRIPTION
     "This attribute indicates the FRF.10 call reference number associated 
      with this DLCI. The value of this attribute for a provisioned (PVC 
      or P-SPVC) DLCI is always 0."
::= { mscFrNniDlciCalldEntry 3 }


-- FrUni/n Dlci/n DirectCall 
-- FrNni/n Dlci/n DirectCall 
-- This component defines direct call options for calls issued without 
-- operator intervention. Connection is complete and can be initiated 
-- automatically. Frequency of connection tries is controlled by retry 
-- timer.

mscFrNniDlciDc OBJECT IDENTIFIER ::= { mscFrNniDlci 2 }



mscFrNniDlciDcRowStatusTable OBJECT-TYPE
   SYNTAX     SEQUENCE OF MscFrNniDlciDcRowStatusEntry
   ACCESS     not-accessible
   STATUS     mandatory
   DESCRIPTION
     "This entry controls the addition and deletion of 
      mscFrNniDlciDc components."
::= { mscFrNniDlciDc 1 }

mscFrNniDlciDcRowStatusEntry OBJECT-TYPE
   SYNTAX     MscFrNniDlciDcRowStatusEntry
   ACCESS     not-accessible
   STATUS     mandatory
   DESCRIPTION
     "A single entry in the table represents a single 
      mscFrNniDlciDc component."
   INDEX {
      mscFrNniIndex,
      mscFrNniDlciIndex,
      mscFrNniDlciDcIndex }
::= { mscFrNniDlciDcRowStatusTable 1 }

MscFrNniDlciDcRowStatusEntry ::= SEQUENCE {
   mscFrNniDlciDcRowStatus
      RowStatus,
   mscFrNniDlciDcComponentName
      DisplayString,
   mscFrNniDlciDcStorageType
      StorageType,
   mscFrNniDlciDcIndex
      NonReplicated }

mscFrNniDlciDcRowStatus OBJECT-TYPE
   SYNTAX     RowStatus 
   ACCESS     read-only
   STATUS     mandatory
   DESCRIPTION
     "This variable is used as the basis for SNMP naming of
      mscFrNniDlciDc components.
      These components cannot be added nor deleted."
::= { mscFrNniDlciDcRowStatusEntry 1 }

mscFrNniDlciDcComponentName OBJECT-TYPE
   SYNTAX     DisplayString 
   ACCESS     read-only
   STATUS     mandatory
   DESCRIPTION
     "This variable provides the component's string name for
      use with the ASCII Console Interface"
::= { mscFrNniDlciDcRowStatusEntry 2 }

mscFrNniDlciDcStorageType OBJECT-TYPE
   SYNTAX     StorageType 
   ACCESS     read-only
   STATUS     mandatory
   DESCRIPTION
     "This variable represents the storage type value for the
      mscFrNniDlciDc tables."
::= { mscFrNniDlciDcRowStatusEntry 4 }

mscFrNniDlciDcIndex OBJECT-TYPE
   SYNTAX     NonReplicated 
   ACCESS     not-accessible
   STATUS     mandatory
   DESCRIPTION
     "This variable represents the index for the mscFrNniDlciDc tables."
::= { mscFrNniDlciDcRowStatusEntry 10 }

mscFrNniDlciDcOptionsTable OBJECT-TYPE
   SYNTAX     SEQUENCE OF MscFrNniDlciDcOptionsEntry
   ACCESS     not-accessible
   STATUS     mandatory
   DESCRIPTION
     "This group defines attributes associated with a direct call. It defines 
      connection in terms of path and call option parameters. This 
      connection can be permanent (PVC), switched (SVC), or switched 
      permanent (SPVC). It can have four facilities:
      - 						CCITT Facilities
      - DTE Facilities
      - National Facilities
      - International Facilities
      The total number of bytes of facilities including the facility codes 
      and all of the facility data from all of the four classes of facilities 
      must not exceed 512 bytes."
::= { mscFrNniDlciDc 10 }

mscFrNniDlciDcOptionsEntry OBJECT-TYPE
   SYNTAX     MscFrNniDlciDcOptionsEntry
   ACCESS     not-accessible
   STATUS     mandatory
   DESCRIPTION
     "An entry in the mscFrNniDlciDcOptionsTable."
   INDEX {
      mscFrNniIndex,
      mscFrNniDlciIndex,
      mscFrNniDlciDcIndex }
::= { mscFrNniDlciDcOptionsTable 1 }

MscFrNniDlciDcOptionsEntry ::= SEQUENCE {
   mscFrNniDlciDcRemoteNpi
      INTEGER,
   mscFrNniDlciDcRemoteDna
      DigitString,
   mscFrNniDlciDcRemoteDlci
      Unsigned32,
   mscFrNniDlciDcType
      INTEGER,
   mscFrNniDlciDcTransferPriority
      INTEGER,
   mscFrNniDlciDcDiscardPriority
      INTEGER,
   mscFrNniDlciDcDeDiscardPriority
      INTEGER,
   mscFrNniDlciDcDataPath
      INTEGER,
   mscFrNniDlciDcCugIndex
      Unsigned32,
   mscFrNniDlciDcCugType
      INTEGER,
   mscFrNniDlciDcMapIpCosToFrQos
      INTEGER }

mscFrNniDlciDcRemoteNpi OBJECT-TYPE
   SYNTAX     INTEGER  {
                 x121(0),
                 e164(1) }
   ACCESS     read-write
   STATUS     mandatory
   DESCRIPTION
     "This attribute specifies the Numbering Plan Indicator (NPI) of the 
      remoteDna."
   DEFVAL     { x121 }
::= { mscFrNniDlciDcOptionsEntry 3 }

mscFrNniDlciDcRemoteDna OBJECT-TYPE
   SYNTAX     DigitString (SIZE (1..15))
   ACCESS     read-write
   STATUS     mandatory
   DESCRIPTION
     "This attribute specifies the Data Network Address (DNA) of the 
      service at the remote end of the DLCI. This is the called 
      (destination) DCE address (DNA) of this PVC."
::= { mscFrNniDlciDcOptionsEntry 4 }

mscFrNniDlciDcRemoteDlci OBJECT-TYPE
   SYNTAX     Unsigned32 (16..1007)
   ACCESS     read-write
   STATUS     mandatory
   DESCRIPTION
     "This attribute specifies the remote DLCI of the PVC connection."
::= { mscFrNniDlciDcOptionsEntry 5 }

mscFrNniDlciDcType OBJECT-TYPE
   SYNTAX     INTEGER  {
                 permanentMaster(1),
                 permanentSlave(2),
                 permanentBackupSlave(3),
                 permanentSlaveWithBackup(4),
                 spvcMaster(5),
                 spvcSlave(6),
                 spvcBackupSlave(7),
                 spvcSlaveWithBackup(8) }
   ACCESS     read-write
   STATUS     mandatory
   DESCRIPTION
     "This attribute specifies the type of VC call.
      
      If the value is set to permanentMaster, then a permanent 
      connection will be established between two ends. The remote end 
      must be defined as a permanentSlave, permanentBackupSlave, or 
      permanentSlaveWithBackup. The connection cannot be established 
      if the remote end is defined as anything else. The end defined as 
      permanentMaster always initiates the calls. It attempts to call once 
      per minute.
      
      If the value is set to permanentSlave then a permanent connection 
      will be established between two ends. The remote end must be 
      defined as a permanentMaster. The connection cannot be 
      established if the remote end is defined as anything else. The 
      permanentSlave end attempts to call once per minute.
      
      If the value is set to permanentSlaveWithBackup then a permanent 
      connection will be established between the two ends. The remote 
      end must be defined as a permanentMaster. The connection cannot 
      be established if the remote interface is defined as anything else. 
      The permanentSlaveWithBackup attempts to call once per minute. 
      When type is set to permanentSlaveWithBackup, the connection is 
      cleared if the interface becomes unavailable. This enables a retry of 
      the connection which can be redirected to the 
      permanentBackupSlave.
      
      If the value is set to permanentBackupSlave then a permanent 
      connection is established between the two ends only if the 
      permanentMaster end is disconnected from the 
      permanentSlaveWithBackup end and a backup call is established 
      by the call redirection system. If the permanentSlaveWithBackup 
      interface becomes available again, the permanentBackupSlave end 
      is disconnected and the permanentSlaveWithBackup end is 
      reconnected to the permanentMaster end. The 
      permanentBackupSlave end does not try to establish a call.
      
      If the value is set to spvcMaster, then a permanent connection is 
      established between two ends, with resiliency at the NNI), if the 
      connection transits across two or more networks. The remote end, 
      which may be in the same network, or an external network that is 
      reachable via Frame Relay NNIs, must be defined as either a 
      spvcSlave, spvcBackupSlave or spvcSlaveWithBackup. The 
      connection cannot be established if the remote end is defined as 
      anything else. The end defined as spvcMaster always initiates the 
      call. It attempts to call once per minute. The call is attempted by the 
      spvcMaster and accepted by the remote end only if all of the 
      following conditions are satisfied, at both ends:
      1. The physical layer must be operational.
      2. The LMI procedures must be in normalCondition (that is, no 
      service affecting condition).
      3. If the LMI side attribute is provisioned to both, the A-bit 
      received from the interface must be Active. If the LMI side 
      attribute is not provisioned to both, this condition does not 
      apply.
      
      After a call is cleared, the spvcMaster end attempts to retry the call 
      according to the rule for the clear cause. If the call is cleared or 
      rejected due to the failure of one of the three conditions indicated 
      above, or due to unavailability of resources along any point in the 
      connection path, the call will be retried after 60 seconds. For all 
      other causes, such as loss of service at an NNI, the call will be 
      retried immediately.
      
      If the value is set to spvcSlave then an SPVC connection is 
      established between two ends. The remote end must be defined as 
      an spvcMaster. The connection cannot be established if the remote 
      end is defined as anything else. The spvcSlave end does not attempt 
      to call.
      
      If the value is set to spvcSlaveWithBackup then a SPVC connection 
      is established between the two ends. The remote end must be 
      defined as an spvcMaster. The connection cannot be established if 
      the remote interface end is defined as anything else. Unlike a 
      permanentSlaveWithBackup end, the spvcSlaveWithBackup end 
      does not attempt to call. If the value is set to spvcSlaveWithBackup, 
      the connection is cleared if the interface becomes unavailable. This 
      enables a retry of the connection by the spvcMaster end, which may 
      be redirected to an end that is set to spvcBackupSlave.
      
      If the value is set to spvcBackupSlave then an SPVC connection is 
      established between the two ends only if the spvcMaster end is 
      disconnected from the spvcSlaveWithBackup end, and a backup 
      call is redirected by the call redirection system. Unlike the PVC 
      connection, if the spvcSlaveWithBackup interface becomes 
      available again, the spvcBackupSlave end is not disconnected and 
      the spvcSlaveWithBackup end is not reconnected to the spvcMaster 
      end. Neither the spvcBackupSlave nor the spvcSlaveWithBackup 
      ends try to establish an SPVC call."
   DEFVAL     { permanentMaster }
::= { mscFrNniDlciDcOptionsEntry 6 }

mscFrNniDlciDcTransferPriority OBJECT-TYPE
   SYNTAX     INTEGER  {
                 n0(0),
                 n1(1),
                 n2(2),
                 n3(3),
                 n4(4),
                 n5(5),
                 n6(6),
                 n7(7),
                 n8(8),
                 n9(9),
                 n10(10),
                 n11(11),
                 n12(12),
                 n13(13),
                 n14(14),
                 n15(15),
                 useDnaDefTP(255) }
   ACCESS     read-write
   STATUS     mandatory
   DESCRIPTION
     "This attribute specifies the transfer priority to the local network for 
      the outgoing calls using this particular DLCI. It overrides the 
      defaultTransferPriority provisioned in its associated Dna 
      component.
      
      The transfer priority is a preference configured for an application 
      according to its delay-sensitivity requirement. Frames with higher 
      transfer priority are served by the network before the frames with 
      lower priority. The transfer priority standard is defined to have 16 
      levels from 0 to 15.
      
      Each transfer priority n, where n is the transfer priority index, has a 
      default setting for routing class of service (multimedia, delay, or 
      throughput) and Frame Relay egress queue (depending on the 
      number of supported egress queues on the remote end interface).
      These settings are specified by the routingClassOfService and 
      emissionPriority attributes provisioned under the Mod Frs DprsNet 
      Tpm/n component.
      
      Specifying useDnaDefTP means using the value given by 
      defaultTransferPriority in the associated Dna for this DLCI."
   DEFVAL     { useDnaDefTP }
::= { mscFrNniDlciDcOptionsEntry 9 }

mscFrNniDlciDcDiscardPriority OBJECT-TYPE
   SYNTAX     INTEGER  {
                 normal(0),
                 high(1),
                 useDnaDefPriority(3) }
   ACCESS     read-write
   STATUS     mandatory
   DESCRIPTION
     "This attribute specifies the discard priority for outgoing call using 
      this DLCI. 
      
      The discard priority has three provisioning values: normal, high, 
      and useDnaDefPriority. Under congestion conditions, traffic with 
      normal priority is discarded before traffic with high priority. The 
      Dna default value (provisioned by outDefaultPriority) is taken if 
      this attribute is set to the value useDnaDefPriority."
   DEFVAL     { useDnaDefPriority }
::= { mscFrNniDlciDcOptionsEntry 10 }

mscFrNniDlciDcDeDiscardPriority OBJECT-TYPE
   SYNTAX     INTEGER  {
                 lowest(0),
                 determinedByDiscardPriority(1) }
   ACCESS     read-write
   STATUS     mandatory
   DESCRIPTION
     "This attribute specifies whether the discardPriority applies to DE 
      frames for this DLCI.
      
      When set to determinedByDiscardPriority, traffic with DE bit set 
      will be discarded according to the setting of the discardPriority.
      
      When set to lowest, all traffic with DE bit set is treated the same and 
      is sent to the subnet at the lowest discard priority."
   DEFVAL     { determinedByDiscardPriority }
::= { mscFrNniDlciDcOptionsEntry 11 }

mscFrNniDlciDcDataPath OBJECT-TYPE
   SYNTAX     INTEGER  {
                 dprsOnly(0),
                 dprsMcsOnly(1),
                 dprsMcsFirst(2),
                 useDnaValue(3) }
   ACCESS     read-write
   STATUS     mandatory
   DESCRIPTION
     "This attribute specifies the data path to be used by Virtual Circuits 
      on this interface. The value of the dataPath attribute in the Dna 
      component is overridden by this attribute if the value is not 
      useDnaValue.
      
      This value applies to the connection after data transfer state is 
      reached. All the data and control traffic will be sent using this data 
      path. If the provisioned dataPath is not available the connection is 
      not established.
      
      The value of the dataPath is signalled by both ends of the 
      connection. If this value is not the same at both ends dprsOnly is 
      used for the duration of the connection.
      
      A virtual circuit connection is always established using dprsOnly 
      even if this attribute is provisioned as some other value.
      
      dprsOnly - The dynamic packet routing system is used.
      
      dprsMcsOnly - The DPRS Multi-Service Cut-Through Switching 
      path is used.
      
      dprsMcsFirst - The DPRS Multi-Service Cut-Through Switching 
      path is used if it is available. If it is not available, dprsOnly is used.
      
      useDnaValue - The routing system used is based on the value 
      provisioned in the Dna component."
   DEFVAL     { useDnaValue }
::= { mscFrNniDlciDcOptionsEntry 12 }

mscFrNniDlciDcCugIndex OBJECT-TYPE
   SYNTAX     Unsigned32 (0..255)
   ACCESS     read-write
   STATUS     mandatory
   DESCRIPTION
     "This attribute specifies the CUG index which is to be signalled in 
      PVC and SPVC call requests to the remote end.
      
      The type of CUG signalling is defined in attribute cugType in this 
      component."
   DEFVAL     { 0 }
::= { mscFrNniDlciDcOptionsEntry 13 }

mscFrNniDlciDcCugType OBJECT-TYPE
   SYNTAX     INTEGER  {
                 doNotSignal(0),
                 cug(3),
                 cugOa(9) }
   ACCESS     read-write
   STATUS     mandatory
   DESCRIPTION
     "This attribute specifies the type of CUG signalling to be used in 
      PVC and SPVC call requests. Index of CUG to be used is defined in 
      attribute cugIndex in this component.
      
      Possible values are:
      cug - signal CUG
      cugOa - signal CUG with outgoing access
      doNotSignal - no CUG in call request"
   DEFVAL     { doNotSignal }
::= { mscFrNniDlciDcOptionsEntry 14 }

mscFrNniDlciDcMapIpCosToFrQos OBJECT-TYPE
   SYNTAX     INTEGER  {
                 no(0),
                 yes(1) }
   ACCESS     read-write
   STATUS     mandatory
   DESCRIPTION
     "This attribute specifies whether an IP TOS value is mapped to an 
      FR QOS. The mapping used is provisioned in the Mod Frs 
      IpCosToFrQos component.
      
      When this attribute is set to yes, at Frame Relay egress, the IP TOS 
      byte in each frame is checked. The TOS value determines the egress 
      emission queue and the discard priority for that frame.
      
      When this attribute is set to no, FR QOS is determined by the 
      provisioned discard priority and transfer priority."
   DEFVAL     { no }
::= { mscFrNniDlciDcOptionsEntry 15 }

mscFrNniDlciDcNfaTable OBJECT-TYPE
   SYNTAX     SEQUENCE OF MscFrNniDlciDcNfaEntry
   ACCESS     not-accessible
   STATUS     obsolete
   DESCRIPTION
     "This is the i'th National facility required for this direct call. Within 
      the provisioning system, the user specifies the facility code along 
      with the facility parameters. The facility is represented internally as 
      a hexadecimal string following the X.25 ITU-T representation for 
      facility data.
      
      Two explicit attributes discardPriority and pathSensitivity are 
      created to replace H.01 and H.30 in the group 
      VcsDirectCallOptionsProv of this file. The migrate escape here 
      (DcComponent::migrateFaxEscape) propagates the old provisioning 
      data under H.01 and H.30 into discardPriority and transferPriority. 
      
      The rule of the above propagation are: 0 in H.01 is equivalent to 
      discardPriority 0; 1 in H.01 is equivalent to discardPriority 1. And 0 
      in H.30 is equivalent to transferPriority throughput; 1 in H.30 is 
      equivalent to pathSensitivity delay.
      
      Please refer to discardPriority and pathSensitivity for more 
      information on how to use them."
::= { mscFrNniDlciDc 202 }

mscFrNniDlciDcNfaEntry OBJECT-TYPE
   SYNTAX     MscFrNniDlciDcNfaEntry
   ACCESS     not-accessible
   STATUS     obsolete
   DESCRIPTION
     "An entry in the mscFrNniDlciDcNfaTable."
   INDEX {
      mscFrNniIndex,
      mscFrNniDlciIndex,
      mscFrNniDlciDcIndex,
      mscFrNniDlciDcNfaIndex }
::= { mscFrNniDlciDcNfaTable 1 }

MscFrNniDlciDcNfaEntry ::= SEQUENCE {
   mscFrNniDlciDcNfaIndex
      Integer32,
   mscFrNniDlciDcNfaValue
      HexString,
   mscFrNniDlciDcNfaRowStatus
      RowStatus }

mscFrNniDlciDcNfaIndex OBJECT-TYPE
   SYNTAX     Integer32 (1 | 48)
   ACCESS     not-accessible
   STATUS     obsolete
   DESCRIPTION
     "This variable represents the index for the mscFrNniDlciDcNfaTable."
::= { mscFrNniDlciDcNfaEntry 1 }

mscFrNniDlciDcNfaValue OBJECT-TYPE
   SYNTAX     HexString (SIZE (0..128))
   ACCESS     read-write
   STATUS     obsolete
   DESCRIPTION
     "This variable represents an individual value for the
      mscFrNniDlciDcNfaTable."
::= { mscFrNniDlciDcNfaEntry 2 }

mscFrNniDlciDcNfaRowStatus OBJECT-TYPE
   SYNTAX     RowStatus 
   ACCESS     write-only
   STATUS     obsolete
   DESCRIPTION
     "This variable is used to control the addition and deletion 
      of individual values of the mscFrNniDlciDcNfaTable."
::= { mscFrNniDlciDcNfaEntry 3 }


-- This component defines attributes collected by Frame Relay Vc.

mscFrNniDlciVc OBJECT IDENTIFIER ::= { mscFrNniDlci 3 }



mscFrNniDlciVcRowStatusTable OBJECT-TYPE
   SYNTAX     SEQUENCE OF MscFrNniDlciVcRowStatusEntry
   ACCESS     not-accessible
   STATUS     mandatory
   DESCRIPTION
     "This entry controls the addition and deletion of 
      mscFrNniDlciVc components."
::= { mscFrNniDlciVc 1 }

mscFrNniDlciVcRowStatusEntry OBJECT-TYPE
   SYNTAX     MscFrNniDlciVcRowStatusEntry
   ACCESS     not-accessible
   STATUS     mandatory
   DESCRIPTION
     "A single entry in the table represents a single 
      mscFrNniDlciVc component."
   INDEX {
      mscFrNniIndex,
      mscFrNniDlciIndex,
      mscFrNniDlciVcIndex }
::= { mscFrNniDlciVcRowStatusTable 1 }

MscFrNniDlciVcRowStatusEntry ::= SEQUENCE {
   mscFrNniDlciVcRowStatus
      RowStatus,
   mscFrNniDlciVcComponentName
      DisplayString,
   mscFrNniDlciVcStorageType
      StorageType,
   mscFrNniDlciVcIndex
      NonReplicated }

mscFrNniDlciVcRowStatus OBJECT-TYPE
   SYNTAX     RowStatus 
   ACCESS     read-only
   STATUS     mandatory
   DESCRIPTION
     "This variable is used as the basis for SNMP naming of
      mscFrNniDlciVc components.
      These components cannot be added nor deleted."
::= { mscFrNniDlciVcRowStatusEntry 1 }

mscFrNniDlciVcComponentName OBJECT-TYPE
   SYNTAX     DisplayString 
   ACCESS     read-only
   STATUS     mandatory
   DESCRIPTION
     "This variable provides the component's string name for
      use with the ASCII Console Interface"
::= { mscFrNniDlciVcRowStatusEntry 2 }

mscFrNniDlciVcStorageType OBJECT-TYPE
   SYNTAX     StorageType 
   ACCESS     read-only
   STATUS     mandatory
   DESCRIPTION
     "This variable represents the storage type value for the
      mscFrNniDlciVc tables."
::= { mscFrNniDlciVcRowStatusEntry 4 }

mscFrNniDlciVcIndex OBJECT-TYPE
   SYNTAX     NonReplicated 
   ACCESS     not-accessible
   STATUS     mandatory
   DESCRIPTION
     "This variable represents the index for the mscFrNniDlciVc tables."
::= { mscFrNniDlciVcRowStatusEntry 10 }

mscFrNniDlciVcCadTable OBJECT-TYPE
   SYNTAX     SEQUENCE OF MscFrNniDlciVcCadEntry
   ACCESS     not-accessible
   STATUS     mandatory
   DESCRIPTION
     "This group represents operational call data related to Frame Relay 
      Vc. It can be displayed only for Frame Relay Vc which is created by 
      application."
::= { mscFrNniDlciVc 10 }

mscFrNniDlciVcCadEntry OBJECT-TYPE
   SYNTAX     MscFrNniDlciVcCadEntry
   ACCESS     not-accessible
   STATUS     mandatory
   DESCRIPTION
     "An entry in the mscFrNniDlciVcCadTable."
   INDEX {
      mscFrNniIndex,
      mscFrNniDlciIndex,
      mscFrNniDlciVcIndex }
::= { mscFrNniDlciVcCadTable 1 }

MscFrNniDlciVcCadEntry ::= SEQUENCE {
   mscFrNniDlciVcType
      INTEGER,
   mscFrNniDlciVcState
      INTEGER,
   mscFrNniDlciVcPreviousState
      INTEGER,
   mscFrNniDlciVcDiagnosticCode
      Unsigned32,
   mscFrNniDlciVcPreviousDiagnosticCode
      Unsigned32,
   mscFrNniDlciVcCalledNpi
      INTEGER,
   mscFrNniDlciVcCalledDna
      DigitString,
   mscFrNniDlciVcCalledLcn
      Unsigned32,
   mscFrNniDlciVcCallingNpi
      INTEGER,
   mscFrNniDlciVcCallingDna
      DigitString,
   mscFrNniDlciVcCallingLcn
      Unsigned32,
   mscFrNniDlciVcAccountingEnabled
      INTEGER,
   mscFrNniDlciVcFastSelectCall
      INTEGER,
   mscFrNniDlciVcPathReliability
      INTEGER,
   mscFrNniDlciVcAccountingEnd
      INTEGER,
   mscFrNniDlciVcPriority
      INTEGER,
   mscFrNniDlciVcSegmentSize
      Unsigned32,
   mscFrNniDlciVcMaxSubnetPktSize
      Unsigned32,
   mscFrNniDlciVcRcosToNetwork
      INTEGER,
   mscFrNniDlciVcRcosFromNetwork
      INTEGER,
   mscFrNniDlciVcEmissionPriorityToNetwork
      INTEGER,
   mscFrNniDlciVcEmissionPriorityFromNetwork
      INTEGER,
   mscFrNniDlciVcDataPath
      AsciiString }

mscFrNniDlciVcType OBJECT-TYPE
   SYNTAX     INTEGER  {
                 svc(0),
                 pvc(1),
                 spvc(2),
                 frf10spvc(3) }
   ACCESS     read-only
   STATUS     mandatory
   DESCRIPTION
     "This attribute displays the type of call, pvc,svc,spvc or frf10spvc."
::= { mscFrNniDlciVcCadEntry 1 }

mscFrNniDlciVcState OBJECT-TYPE
   SYNTAX     INTEGER  {
                 creating(0),
                 readyP1(1),
                 dteWaitingP2(2),
                 dceWaitingP3(3),
                 dataTransferP4(4),
                 unsupportedP5(5),
                 dteClearRequestP6(6),
                 dceClearIndicationP7(7),
                 termination(8) }
   ACCESS     read-only
   STATUS     mandatory
   DESCRIPTION
     "This attribute displays the state of call control. P5 state is not 
      supported but is listed for completness. Transitions from one state to 
      another take very short time. state most often displayed is 
      dataTransferP4."
::= { mscFrNniDlciVcCadEntry 2 }

mscFrNniDlciVcPreviousState OBJECT-TYPE
   SYNTAX     INTEGER  {
                 creating(0),
                 readyP1(1),
                 dteWaitingP2(2),
                 dceWaitingP3(3),
                 dataTransferP4(4),
                 unsupportedP5(5),
                 dteClearRequestP6(6),
                 dceClearIndicationP7(7),
                 termination(8) }
   ACCESS     read-only
   STATUS     mandatory
   DESCRIPTION
     "This attribute displays the previous state of call control. This is a 
      valuable field to determine how the processing is progressing."
::= { mscFrNniDlciVcCadEntry 3 }

mscFrNniDlciVcDiagnosticCode OBJECT-TYPE
   SYNTAX     Unsigned32 (0..255)
   ACCESS     read-only
   STATUS     mandatory
   DESCRIPTION
     "This attribute displays the internal substate of call control. It is used 
      to further refine state of call processing."
::= { mscFrNniDlciVcCadEntry 4 }

mscFrNniDlciVcPreviousDiagnosticCode OBJECT-TYPE
   SYNTAX     Unsigned32 (0..255)
   ACCESS     read-only
   STATUS     mandatory
   DESCRIPTION
     "This attribute displays the internal substate of call control. It is used 
      to further refine state of call processing."
::= { mscFrNniDlciVcCadEntry 5 }

mscFrNniDlciVcCalledNpi OBJECT-TYPE
   SYNTAX     INTEGER  {
                 x121(0),
                 e164(1) }
   ACCESS     read-only
   STATUS     mandatory
   DESCRIPTION
     "This attribute displays the Numbering Plan Indicator (NPI) of the 
      called end."
::= { mscFrNniDlciVcCadEntry 6 }

mscFrNniDlciVcCalledDna OBJECT-TYPE
   SYNTAX     DigitString (SIZE (1..15))
   ACCESS     read-only
   STATUS     mandatory
   DESCRIPTION
     "This attribute displays the Data Network Address (Dna) of the 
      called (destination) DTE to which this call is sent. This address if 
      defined at recieving end will complete Vc connection."
::= { mscFrNniDlciVcCadEntry 7 }

mscFrNniDlciVcCalledLcn OBJECT-TYPE
   SYNTAX     Unsigned32 (1..65535)
   ACCESS     read-only
   STATUS     mandatory
   DESCRIPTION
     "This attribute displays the Logical Channel Number of the called 
      end. It is valid only after both ends of Vc exchanged relevant 
      information."
::= { mscFrNniDlciVcCadEntry 8 }

mscFrNniDlciVcCallingNpi OBJECT-TYPE
   SYNTAX     INTEGER  {
                 x121(0),
                 e164(1) }
   ACCESS     read-only
   STATUS     mandatory
   DESCRIPTION
     "This attribute displays the Numbering Plan Indicator (NPI) of the 
      calling end."
::= { mscFrNniDlciVcCadEntry 9 }

mscFrNniDlciVcCallingDna OBJECT-TYPE
   SYNTAX     DigitString (SIZE (1..15))
   ACCESS     read-only
   STATUS     mandatory
   DESCRIPTION
     "This attribute displays the Data Network Address (Dna) of the 
      calling end."
::= { mscFrNniDlciVcCadEntry 10 }

mscFrNniDlciVcCallingLcn OBJECT-TYPE
   SYNTAX     Unsigned32 (1..65535)
   ACCESS     read-only
   STATUS     mandatory
   DESCRIPTION
     "This attribute displays the Logical Channel Number of the calling 
      end."
::= { mscFrNniDlciVcCadEntry 11 }

mscFrNniDlciVcAccountingEnabled OBJECT-TYPE
   SYNTAX     INTEGER  {
                 yes(0),
                 no(1) }
   ACCESS     read-only
   STATUS     mandatory
   DESCRIPTION
     "This attribute indicates that this optional section of accounting 
      record is suppressed or permitted. If accountingEnabled is yes, 
      conditions for generation of accounting record were met. These 
      conditions include billing options, vc recovery conditions and 
      Module wide accounting data options."
::= { mscFrNniDlciVcCadEntry 12 }

mscFrNniDlciVcFastSelectCall OBJECT-TYPE
   SYNTAX     INTEGER  {
                 no(0),
                 yes(1) }
   ACCESS     read-only
   STATUS     mandatory
   DESCRIPTION
     "This attribute displays that this is a fast select call."
::= { mscFrNniDlciVcCadEntry 13 }

mscFrNniDlciVcPathReliability OBJECT-TYPE
   SYNTAX     INTEGER  {
                 high(0),
                 normal(1) }
   ACCESS     read-only
   STATUS     mandatory
   DESCRIPTION
     "This attribute displays the path reliability."
::= { mscFrNniDlciVcCadEntry 19 }

mscFrNniDlciVcAccountingEnd OBJECT-TYPE
   SYNTAX     INTEGER  {
                 callingEnd(0),
                 calledEnd(1) }
   ACCESS     read-only
   STATUS     mandatory
   DESCRIPTION
     "This attribute indicates if this end should generate an accounting 
      record. Normally, callingEnd is the end to generate an accounting 
      record."
::= { mscFrNniDlciVcCadEntry 20 }

mscFrNniDlciVcPriority OBJECT-TYPE
   SYNTAX     INTEGER  {
                 normal(0),
                 high(1) }
   ACCESS     read-only
   STATUS     mandatory
   DESCRIPTION
     "This attribute displays whether the call is a normal or a high 
      priority call."
::= { mscFrNniDlciVcCadEntry 21 }

mscFrNniDlciVcSegmentSize OBJECT-TYPE
   SYNTAX     Unsigned32 (0..4096)
   ACCESS     read-only
   STATUS     mandatory
   DESCRIPTION
     "This attribute displays the segment size (in bytes) used on the call. 
      It is used to calculate the number of segments transmitted and 
      received."
::= { mscFrNniDlciVcCadEntry 22 }

mscFrNniDlciVcMaxSubnetPktSize OBJECT-TYPE
   SYNTAX     Unsigned32 (0..4096)
   ACCESS     read-only
   STATUS     mandatory
   DESCRIPTION
     "This attribute indicates the maximum packet size allowed on the Vc."
::= { mscFrNniDlciVcCadEntry 27 }

mscFrNniDlciVcRcosToNetwork OBJECT-TYPE
   SYNTAX     INTEGER  {
                 throughput(0),
                 delay(1),
                 multimedia(2) }
   ACCESS     read-only
   STATUS     mandatory
   DESCRIPTION
     "This attribute indicates the routing metric routing class of service to
      the network."
::= { mscFrNniDlciVcCadEntry 28 }

mscFrNniDlciVcRcosFromNetwork OBJECT-TYPE
   SYNTAX     INTEGER  {
                 throughput(0),
                 delay(1),
                 multimedia(2) }
   ACCESS     read-only
   STATUS     mandatory
   DESCRIPTION
     "This attribute displays the routing metric Routing Class of Service 
      from the Network."
::= { mscFrNniDlciVcCadEntry 29 }

mscFrNniDlciVcEmissionPriorityToNetwork OBJECT-TYPE
   SYNTAX     INTEGER  {
                 normal(0),
                 high(1),
                 interrupting(2) }
   ACCESS     read-only
   STATUS     mandatory
   DESCRIPTION
     "This attribute displays the network internal emission priotity to the 
      network."
::= { mscFrNniDlciVcCadEntry 30 }

mscFrNniDlciVcEmissionPriorityFromNetwork OBJECT-TYPE
   SYNTAX     INTEGER  {
                 normal(0),
                 high(1),
                 interrupting(2) }
   ACCESS     read-only
   STATUS     mandatory
   DESCRIPTION
     "This attribute displays the network internal emission priotity from 
      the network."
::= { mscFrNniDlciVcCadEntry 31 }

mscFrNniDlciVcDataPath OBJECT-TYPE
   SYNTAX     AsciiString (SIZE (0..32))
   ACCESS     read-only
   STATUS     mandatory
   DESCRIPTION
     "This attribute indicates the data path used by the connection. The 
      data path is provisioned in Dna and DirectCall components. The 
      displayed value of this attribute can be different from the 
      provisioned value.
      
      If the connection is using dprsOnly data path, the string 
      dprsOnly is displayed. (dynamic packet routing system)
      
      If the connection is using dprsMcsOnly data path, the string 
      dprsMcsOnly is displayed.
      
      If the connection is using dprsMcsFirst data path, the string 
      dprsMcsFirst is displayed."
::= { mscFrNniDlciVcCadEntry 32 }

mscFrNniDlciVcIntdTable OBJECT-TYPE
   SYNTAX     SEQUENCE OF MscFrNniDlciVcIntdEntry
   ACCESS     not-accessible
   STATUS     mandatory
   DESCRIPTION
     "This group defines display of interval data collected by Vc. Data in 
      this group is variable and may depend on time when this display 
      command is issued."
::= { mscFrNniDlciVc 11 }

mscFrNniDlciVcIntdEntry OBJECT-TYPE
   SYNTAX     MscFrNniDlciVcIntdEntry
   ACCESS     not-accessible
   STATUS     mandatory
   DESCRIPTION
     "An entry in the mscFrNniDlciVcIntdTable."
   INDEX {
      mscFrNniIndex,
      mscFrNniDlciIndex,
      mscFrNniDlciVcIndex }
::= { mscFrNniDlciVcIntdTable 1 }

MscFrNniDlciVcIntdEntry ::= SEQUENCE {
   mscFrNniDlciVcCallReferenceNumber
      Hex,
   mscFrNniDlciVcElapsedTimeTillNow
      Unsigned32,
   mscFrNniDlciVcSegmentsRx
      Unsigned32,
   mscFrNniDlciVcSegmentsSent
      Unsigned32,
   mscFrNniDlciVcStartTime
      EnterpriseDateAndTime,
   mscFrNniDlciVcCallReferenceNumberDecimal
      Unsigned32 }

mscFrNniDlciVcCallReferenceNumber OBJECT-TYPE
   SYNTAX     Hex (0..16777215)
   ACCESS     read-only
   STATUS     obsolete
   DESCRIPTION
     "This attribute is obsolete. It is replaced by the callReferenceNumber 
      attribute to display the call reference number in decimal. The 
      SNMP reference for the callReferenceNumber attribute is 
      callReferenceNumberDecimal."
::= { mscFrNniDlciVcIntdEntry 1 }

mscFrNniDlciVcElapsedTimeTillNow OBJECT-TYPE
   SYNTAX     Unsigned32 (0..16777215)
   ACCESS     read-only
   STATUS     mandatory
   DESCRIPTION
     "This attribute displays the elapsed time representing the period of 
      this interval data. It is elapsed time in 0.1 second increments since 
      Vc started."
::= { mscFrNniDlciVcIntdEntry 2 }

mscFrNniDlciVcSegmentsRx OBJECT-TYPE
   SYNTAX     Unsigned32 (0..16777215)
   ACCESS     read-only
   STATUS     mandatory
   DESCRIPTION
     "This attribute displays the number of segments received at the time 
      command was issued. This is the segment received count 
      maintained by accounting at each end of the Vc. This counter is 
      updated only when the packet cannot be successfully delivered out 
      of the sink Vc and to the sink AP Conditions in which packets may 
      be discarded by the sink Vc include: missing packets due to subnet 
      discards, segmentation protocol violations due to subnet discard, 
      duplicated and out-of-ranged packets and packets that arrive while 
      Vc is in path recovery state."
::= { mscFrNniDlciVcIntdEntry 3 }

mscFrNniDlciVcSegmentsSent OBJECT-TYPE
   SYNTAX     Unsigned32 (0..16777215)
   ACCESS     read-only
   STATUS     mandatory
   DESCRIPTION
     "This attribute displays the number of segments sent at the time 
      command was issued. This is the segment sent count maintained by 
      accounting at the source Vc. Vc only counts packets that Vc thinks 
      can be delivered successfully into the subnet. In reality, these 
      packets may be dropped by trunking, for instance. This counter is 
      not updated when splitting fails, when Vc is in a path recovery state, 
      when packet forwarding fails to forward this packet and when 
      subsequent packets have to be discarded as we want to minimize the 
      chance of out-of-sequence and do not intentionally send out-of-
      sequenced packets into the subnet."
::= { mscFrNniDlciVcIntdEntry 4 }

mscFrNniDlciVcStartTime OBJECT-TYPE
   SYNTAX     EnterpriseDateAndTime (SIZE (0 | 19))
   ACCESS     read-only
   STATUS     mandatory
   DESCRIPTION
     "This attribute displays the start time of this interval period. If Vc 
      spans 12 hour time or time of day change startTime reflects new 
      time as recorded at 12 hour periods or time of day changes."
::= { mscFrNniDlciVcIntdEntry 5 }

mscFrNniDlciVcCallReferenceNumberDecimal OBJECT-TYPE
   SYNTAX     Unsigned32 (0..4294967295)
   ACCESS     read-only
   STATUS     mandatory
   DESCRIPTION
     "This attribute displays the call reference number which is a unique 
      number generated by the switch.The same Call Reference Number 
      is stored in the interval data (accounting record) at both ends of the 
      call. It can be used as one of the attributes in matching duplicate 
      records generated at each end of the call."
::= { mscFrNniDlciVcIntdEntry 7 }

mscFrNniDlciVcFrdTable OBJECT-TYPE
   SYNTAX     SEQUENCE OF MscFrNniDlciVcFrdEntry
   ACCESS     not-accessible
   STATUS     mandatory
   DESCRIPTION
     "This group defines Frame Relay attributes collected by Frame Relay 
      Vc.
      The purpose of Vc attributes is to aid end users and verification 
      people to understand the Vc internal behavior. This is particularly 
      useful when the network has experienced abnormality and we want 
      to isolate problems and pinpoint trouble spots. 
      Attributes are collected on a per Vc basis. Until a need is identified, 
      statistics are not collected at a processor level. Each attribute is 
      stored in a 32 bit field and is initialized to zero when a Vc enters 
      into the data transfer state. When a PVC is disconnected and then 
      connected again, the attributes will be reset. Attributes cannot be 
      reset through other methods. 
      Frame Relay Vc uses a best effort data packet delivery protocol and 
      a different packet segmentation and combination methods from the 
      General Vc. The Frame Relay Vc uses the same call setup and 
      control mechanism (e.g. the support of non-flow control data 
      packets) as in a General Vc. Most General Vc statistics and internal 
      variables are used in a Frame Relay Vc and are displayed by 
      software developers"
::= { mscFrNniDlciVc 12 }

mscFrNniDlciVcFrdEntry OBJECT-TYPE
   SYNTAX     MscFrNniDlciVcFrdEntry
   ACCESS     not-accessible
   STATUS     mandatory
   DESCRIPTION
     "An entry in the mscFrNniDlciVcFrdTable."
   INDEX {
      mscFrNniIndex,
      mscFrNniDlciIndex,
      mscFrNniDlciVcIndex }
::= { mscFrNniDlciVcFrdTable 1 }

MscFrNniDlciVcFrdEntry ::= SEQUENCE {
   mscFrNniDlciVcFrmCongestedToSubnet
      Unsigned32,
   mscFrNniDlciVcCannotForwardToSubnet
      Unsigned32,
   mscFrNniDlciVcNotDataXferToSubnet
      Unsigned32,
   mscFrNniDlciVcOutOfRangeFrmFromSubnet
      Unsigned32,
   mscFrNniDlciVcCombErrorsFromSubnet
      Unsigned32,
   mscFrNniDlciVcDuplicatesFromSubnet
      Unsigned32,
   mscFrNniDlciVcNotDataXferFromSubnet
      Unsigned32,
   mscFrNniDlciVcFrmLossTimeouts
      Unsigned32,
   mscFrNniDlciVcOoSeqByteCntExceeded
      Unsigned32,
   mscFrNniDlciVcPeakOoSeqPktCount
      Unsigned32,
   mscFrNniDlciVcPeakOoSeqFrmForwarded
      Unsigned32,
   mscFrNniDlciVcSendSequenceNumber
      Unsigned32,
   mscFrNniDlciVcPktRetryTimeouts
      Unsigned32,
   mscFrNniDlciVcPeakRetryQueueSize
      Unsigned32,
   mscFrNniDlciVcSubnetRecoveries
      Unsigned32,
   mscFrNniDlciVcOoSeqPktCntExceeded
      Unsigned32,
   mscFrNniDlciVcPeakOoSeqByteCount
      Unsigned32 }

mscFrNniDlciVcFrmCongestedToSubnet OBJECT-TYPE
   SYNTAX     Unsigned32 (0..5000)
   ACCESS     read-only
   STATUS     mandatory
   DESCRIPTION
     "This attribute displays the number of frames from link discarded 
      due to lack of resources. It keeps track of the number of frames 
      from link that have to be discarded. The discard reasons include 
      insufficient memory for splitting the frame into smaller subnet 
      packet size."
::= { mscFrNniDlciVcFrdEntry 2 }

mscFrNniDlciVcCannotForwardToSubnet OBJECT-TYPE
   SYNTAX     Unsigned32 (0..5000)
   ACCESS     read-only
   STATUS     mandatory
   DESCRIPTION
     "This attribute displays the number of discarded packets that can not 
      be forwarded into the subnet because of subnet congestion.
      Number of frames from link discarded due to failure in forwarding 
      a packet from Vc into the subnet.- This attribute is increased when 
      packet forwarding fails to forward a packet into the subnet. If a 
      frame is split into multiple subnet packets and a partial packet has 
      to be discarded, all subsequent partial packets that have not yet been 
      delivered to the subnet will be discarded as well."
::= { mscFrNniDlciVcFrdEntry 3 }

mscFrNniDlciVcNotDataXferToSubnet OBJECT-TYPE
   SYNTAX     Unsigned32 (0..5000)
   ACCESS     read-only
   STATUS     mandatory
   DESCRIPTION
     "This attribute records the number of frames from link discarded 
      when the Vc tries to recover from internal path failure."
::= { mscFrNniDlciVcFrdEntry 4 }

mscFrNniDlciVcOutOfRangeFrmFromSubnet OBJECT-TYPE
   SYNTAX     Unsigned32 (0..5000)
   ACCESS     read-only
   STATUS     mandatory
   DESCRIPTION
     "This attribute displays the number of frames from subnet discarded 
      due to out of sequence range for arriving too late."
::= { mscFrNniDlciVcFrdEntry 5 }

mscFrNniDlciVcCombErrorsFromSubnet OBJECT-TYPE
   SYNTAX     Unsigned32 (0..5000)
   ACCESS     read-only
   STATUS     mandatory
   DESCRIPTION
     "This attribute records the number of subnet packets discarded at the 
      sink Vc due to the Vc segmentation and combination protocol error. 
      Usually, this occurs when the subnet discards packets and thus this 
      statistics can be used to guest the number of subnet packets that are 
      not delivered to the Vc. It cannot be used as an actual measure 
      because some subnet packets may have been delivered to Vc but 
      have to be discarded because these are partial packets to a frame in 
      which some other partial packets have not been properly delivered 
      to Vc"
::= { mscFrNniDlciVcFrdEntry 6 }

mscFrNniDlciVcDuplicatesFromSubnet OBJECT-TYPE
   SYNTAX     Unsigned32 (0..5000)
   ACCESS     read-only
   STATUS     mandatory
   DESCRIPTION
     "This attribute displays the number of subnet packets discarded due 
      to duplication. Although packets are not retransmitted by the Frame 
      Relay Vc, it is possible for the subnet to retransmit packets. When 
      packets are out-of-sequenced and copies of the same packets arrive, 
      then this attribute is increased."
::= { mscFrNniDlciVcFrdEntry 7 }

mscFrNniDlciVcNotDataXferFromSubnet OBJECT-TYPE
   SYNTAX     Unsigned32 (0..5000)
   ACCESS     read-only
   STATUS     mandatory
   DESCRIPTION
     "This attribute displays the number of subnet packets discarded when 
      data transfer is suspended in Vc recovery."
::= { mscFrNniDlciVcFrdEntry 8 }

mscFrNniDlciVcFrmLossTimeouts OBJECT-TYPE
   SYNTAX     Unsigned32 (0..5000)
   ACCESS     read-only
   STATUS     mandatory
   DESCRIPTION
     "This attribute displays the number of lost frame timer expiries.
      When this count is excessive, the network is very congested and 
      packets have been discarded in the subnet."
::= { mscFrNniDlciVcFrdEntry 9 }

mscFrNniDlciVcOoSeqByteCntExceeded OBJECT-TYPE
   SYNTAX     Unsigned32 (0..5000)
   ACCESS     read-only
   STATUS     mandatory
   DESCRIPTION
     "This attribute displays the number times that the out of sequence 
      byte threshold is exceeded. When the threshold is exceeded, this 
      condition is treated as if the loss frame timer has expired and all 
      frames queued at the sink Vc are delivered to the AP. We need to 
      keep this count to examine if the threshold is engineered properly. 
      This should be used in conjunction with the peak value of out-of-
      sequenced queue and the number of times the loss frame timer has 
      expired. This count should be relatively small when compared with 
      loss frame timer expiry count."
::= { mscFrNniDlciVcFrdEntry 10 }

mscFrNniDlciVcPeakOoSeqPktCount OBJECT-TYPE
   SYNTAX     Unsigned32 (0..5000)
   ACCESS     read-only
   STATUS     mandatory
   DESCRIPTION
     "This attribute displays the frame relay peak packet count of the out 
      of sequence queue. This attribute records the maximum queue 
      length of the out-of-sequenced queue. The counter can be used to 
      deduce the message buffer requirement on a Vc."
::= { mscFrNniDlciVcFrdEntry 11 }

mscFrNniDlciVcPeakOoSeqFrmForwarded OBJECT-TYPE
   SYNTAX     Unsigned32 (0..5000)
   ACCESS     read-only
   STATUS     mandatory
   DESCRIPTION
     "This attribute displays the frame relay peak size of the 
      sequence packet queue. The subnet may deliver packets out-of-
      sequenced. These packets are then queued in an out-of-sequenced 
      queue, waiting for a packet with the expected sequence number to 
      come. When that packet arrives, this attribute records the maximum 
      number of packets that were out-of-sequenced, but now have 
      become in-sequenced. The statistics is used to measure expected 
      queue size due to normal subnet packet disorder (not due to subnet 
      packet discard). Current implementation also uses this statistics to 
      set a maximum size for the out-of-sequenced queue."
::= { mscFrNniDlciVcFrdEntry 12 }

mscFrNniDlciVcSendSequenceNumber OBJECT-TYPE
   SYNTAX     Unsigned32 (0..5000)
   ACCESS     read-only
   STATUS     mandatory
   DESCRIPTION
     "This attribute displays the Vc internal packet's send sequence 
      number. Note that a 'packet' in this context, may be either a user 
      data packet, or an OAM frame."
::= { mscFrNniDlciVcFrdEntry 13 }

mscFrNniDlciVcPktRetryTimeouts OBJECT-TYPE
   SYNTAX     Unsigned32 (0..5000)
   ACCESS     read-only
   STATUS     mandatory
   DESCRIPTION
     "This attribute displays the number of packets which have 
      retransmission time-outs. When this count is excessive, the network 
      is very congested and packets have been discarded in the subnet."
::= { mscFrNniDlciVcFrdEntry 15 }

mscFrNniDlciVcPeakRetryQueueSize OBJECT-TYPE
   SYNTAX     Unsigned32 (0..5000)
   ACCESS     read-only
   STATUS     mandatory
   DESCRIPTION
     "This attribute displays the peak size of retransmission queue.
      This attribute is used as an indicator of the acknowledgment 
      behavior across the subnet. Records the largest body of 
      unacknowledged packets."
::= { mscFrNniDlciVcFrdEntry 16 }

mscFrNniDlciVcSubnetRecoveries OBJECT-TYPE
   SYNTAX     Unsigned32 (0..5000)
   ACCESS     read-only
   STATUS     mandatory
   DESCRIPTION
     "This attribute displays the number of successful Vc recovery 
      attempts."
::= { mscFrNniDlciVcFrdEntry 17 }

mscFrNniDlciVcOoSeqPktCntExceeded OBJECT-TYPE
   SYNTAX     Unsigned32 (0..255)
   ACCESS     read-only
   STATUS     mandatory
   DESCRIPTION
     "This attribute displays the number times that the out of sequence 
      packet threshold is exceeded. When the threshold is exceeded, this 
      condition is treated as if the loss frame timer has expired and all 
      frames queued at the sink Vc are delivered to the AP. We need to 
      keep this count to examine if the threshold is engineered properly. 
      This should be used in conjunction with the peak value of out-of-
      sequenced queue and the number of times the loss frame timer has 
      expired. This count should be relatively small when compared with 
      loss frame timer expiry count."
::= { mscFrNniDlciVcFrdEntry 19 }

mscFrNniDlciVcPeakOoSeqByteCount OBJECT-TYPE
   SYNTAX     Unsigned32 (0..50000)
   ACCESS     read-only
   STATUS     mandatory
   DESCRIPTION
     "This attribute displays the frame relay peak byte count of the out of 
      sequence queue. This attribute records the maximum queue length 
      of the out-of-sequenced queue. The counter can be used to deduce 
      the message buffer requirement on a Vc."
::= { mscFrNniDlciVcFrdEntry 20 }

mscFrNniDlciVcDmepTable OBJECT-TYPE
   SYNTAX     SEQUENCE OF MscFrNniDlciVcDmepEntry
   ACCESS     not-accessible
   STATUS     mandatory
   DESCRIPTION
     "This attribute displays the data path used by the connection. Data 
      path is provisioned in Dna and DirectCall components.
      
      If the connection is using dprsOnly data path, this attribute is 
      empty.
      
      If the connection is using dprsMcsOnly or dprsMcsFirst data path, 
      this attribute displays component name of the dprsMcsEndPoint."
::= { mscFrNniDlciVc 417 }

mscFrNniDlciVcDmepEntry OBJECT-TYPE
   SYNTAX     MscFrNniDlciVcDmepEntry
   ACCESS     not-accessible
   STATUS     mandatory
   DESCRIPTION
     "An entry in the mscFrNniDlciVcDmepTable."
   INDEX {
      mscFrNniIndex,
      mscFrNniDlciIndex,
      mscFrNniDlciVcIndex,
      mscFrNniDlciVcDmepValue }
::= { mscFrNniDlciVcDmepTable 1 }

MscFrNniDlciVcDmepEntry ::= SEQUENCE {
   mscFrNniDlciVcDmepValue
      RowPointer }

mscFrNniDlciVcDmepValue OBJECT-TYPE
   SYNTAX     RowPointer 
   ACCESS     read-only
   STATUS     mandatory
   DESCRIPTION
     "This variable represents both the value and the index for the
      mscFrNniDlciVcDmepTable."
::= { mscFrNniDlciVcDmepEntry 1 }


-- FrNni/n Dlci/n ServiceParametersProv
-- This component contains the provisionable traffic control attributes 
-- for its parent Dlci component.

mscFrNniDlciSp OBJECT IDENTIFIER ::= { mscFrNniDlci 4 }



mscFrNniDlciSpRowStatusTable OBJECT-TYPE
   SYNTAX     SEQUENCE OF MscFrNniDlciSpRowStatusEntry
   ACCESS     not-accessible
   STATUS     mandatory
   DESCRIPTION
     "This entry controls the addition and deletion of 
      mscFrNniDlciSp components."
::= { mscFrNniDlciSp 1 }

mscFrNniDlciSpRowStatusEntry OBJECT-TYPE
   SYNTAX     MscFrNniDlciSpRowStatusEntry
   ACCESS     not-accessible
   STATUS     mandatory
   DESCRIPTION
     "A single entry in the table represents a single 
      mscFrNniDlciSp component."
   INDEX {
      mscFrNniIndex,
      mscFrNniDlciIndex,
      mscFrNniDlciSpIndex }
::= { mscFrNniDlciSpRowStatusTable 1 }

MscFrNniDlciSpRowStatusEntry ::= SEQUENCE {
   mscFrNniDlciSpRowStatus
      RowStatus,
   mscFrNniDlciSpComponentName
      DisplayString,
   mscFrNniDlciSpStorageType
      StorageType,
   mscFrNniDlciSpIndex
      NonReplicated }

mscFrNniDlciSpRowStatus OBJECT-TYPE
   SYNTAX     RowStatus 
   ACCESS     read-only
   STATUS     mandatory
   DESCRIPTION
     "This variable is used as the basis for SNMP naming of
      mscFrNniDlciSp components.
      These components cannot be added nor deleted."
::= { mscFrNniDlciSpRowStatusEntry 1 }

mscFrNniDlciSpComponentName OBJECT-TYPE
   SYNTAX     DisplayString 
   ACCESS     read-only
   STATUS     mandatory
   DESCRIPTION
     "This variable provides the component's string name for
      use with the ASCII Console Interface"
::= { mscFrNniDlciSpRowStatusEntry 2 }

mscFrNniDlciSpStorageType OBJECT-TYPE
   SYNTAX     StorageType 
   ACCESS     read-only
   STATUS     mandatory
   DESCRIPTION
     "This variable represents the storage type value for the
      mscFrNniDlciSp tables."
::= { mscFrNniDlciSpRowStatusEntry 4 }

mscFrNniDlciSpIndex OBJECT-TYPE
   SYNTAX     NonReplicated 
   ACCESS     not-accessible
   STATUS     mandatory
   DESCRIPTION
     "This variable represents the index for the mscFrNniDlciSp tables."
::= { mscFrNniDlciSpRowStatusEntry 10 }

mscFrNniDlciSpParmsTable OBJECT-TYPE
   SYNTAX     SEQUENCE OF MscFrNniDlciSpParmsEntry
   ACCESS     not-accessible
   STATUS     mandatory
   DESCRIPTION
     "This group contains the provisionable attributes for the Data Link 
      Connection Identifier. These attributes reflect the service parameters 
      specific to this instance of DLCI . The congestion control attributes 
      in this group are defined in T1.606 Addendum 1."
::= { mscFrNniDlciSp 11 }

mscFrNniDlciSpParmsEntry OBJECT-TYPE
   SYNTAX     MscFrNniDlciSpParmsEntry
   ACCESS     not-accessible
   STATUS     mandatory
   DESCRIPTION
     "An entry in the mscFrNniDlciSpParmsTable."
   INDEX {
      mscFrNniIndex,
      mscFrNniDlciIndex,
      mscFrNniDlciSpIndex }
::= { mscFrNniDlciSpParmsTable 1 }

MscFrNniDlciSpParmsEntry ::= SEQUENCE {
   mscFrNniDlciSpMaximumFrameSize
      Unsigned32,
   mscFrNniDlciSpRateEnforcement
      INTEGER,
   mscFrNniDlciSpCommittedInformationRate
      Gauge32,
   mscFrNniDlciSpCommittedBurstSize
      Gauge32,
   mscFrNniDlciSpExcessBurstSize
      Gauge32,
   mscFrNniDlciSpMeasurementInterval
      Unsigned32,
   mscFrNniDlciSpRateAdaptation
      INTEGER,
   mscFrNniDlciSpAccounting
      INTEGER,
   mscFrNniDlciSpRaSensitivity
      Unsigned32,
   mscFrNniDlciSpUpdateBCI
      INTEGER }

mscFrNniDlciSpMaximumFrameSize OBJECT-TYPE
   SYNTAX     Unsigned32 (1..8187)
   ACCESS     read-write
   STATUS     mandatory
   DESCRIPTION
     "This attribute specifies the maximum number of octets which may 
      be included in the information field. The frame relay header and 
      CRC octets are not included in this definition. This attribute 
      corresponds to the dN1 parameter described in the Vendor Forum 
      Specification."
   DEFVAL     { 2100 }
::= { mscFrNniDlciSpParmsEntry 1 }

mscFrNniDlciSpRateEnforcement OBJECT-TYPE
   SYNTAX     INTEGER  {
                 off(0),
                 on(1) }
   ACCESS     read-write
   STATUS     mandatory
   DESCRIPTION
     "This attribute specifies whether rate enforcement is in effect for this 
      user Data Link Connection on this Frame Relay interface. Turning 
      on rate enforcement means that CIR and DE=1 traffic will be 
      measured and enforced. Turning off rate enforcement means that all 
      frames from the user will be accepted and no modifications to the 
      frame with respect to the DE bit will be made."
   DEFVAL     { off }
::= { mscFrNniDlciSpParmsEntry 2 }

mscFrNniDlciSpCommittedInformationRate OBJECT-TYPE
   SYNTAX     Gauge32 (0..50000000)
   ACCESS     read-write
   STATUS     mandatory
   DESCRIPTION
     "This attribute specifies the committed information rate (CIR) in bits 
      per second (bit/s). When rateEnforcement is set to on, cir is the rate 
      at which the network agrees to transfer information under normal 
      conditions. This rate is measured over a measurement interval (t) 
      that is determined internally based on CIR and the committed burst 
      size (Bc). An exception to this occurs when CIR is provisioned to 
      be zero, in which case the measurement interval (t) must be 
      provisioned explicitly.
      
      This attribute is ignored when rateEnforcement is off. If 
      rateEnforcement is on and this attribute is 0, Bc must also be 0."
   DEFVAL     { 64000 }
::= { mscFrNniDlciSpParmsEntry 3 }

mscFrNniDlciSpCommittedBurstSize OBJECT-TYPE
   SYNTAX     Gauge32 (0..50000000)
   ACCESS     read-write
   STATUS     mandatory
   DESCRIPTION
     "This attribute specifies the committed burst size (Bc) in bits. bc is 
      the amount of data that a network agrees to transfer under normal 
      conditions over a measurement interval (t). Data marked DE=1 is 
      not accounted for in Bc.
      
      This attribute is ignored when rateEnforcement is off. If 
      rateEnforcement is on and this attribute is 0, cir must also be 0."
   DEFVAL     { 64000 }
::= { mscFrNniDlciSpParmsEntry 4 }

mscFrNniDlciSpExcessBurstSize OBJECT-TYPE
   SYNTAX     Gauge32 (0..50000000)
   ACCESS     read-write
   STATUS     mandatory
   DESCRIPTION
     "This attribute specifies the excess burst size (Be) in bits. Be is the 
      amount of uncommitted data that the network will attempt to deliver 
      over measurement interval T. Data marked DE=1 by the user or by 
      the network is accounted for here.
      
      CIR, Bc, and Be cannot all be zero when rateEnforcement is on."
   DEFVAL     { 0 }
::= { mscFrNniDlciSpParmsEntry 5 }

mscFrNniDlciSpMeasurementInterval OBJECT-TYPE
   SYNTAX     Unsigned32 (0..25500)
   ACCESS     read-write
   STATUS     mandatory
   DESCRIPTION
     "When cir and bc are zero and rateEnforcement is on, this attribute 
      must be provisioned to specify the time interval (in milliseconds) 
      over which rates and burst sizes are measured.
      
      When cir and bc are non-zero, the time interval is internally 
      calculated and is not shown. In that situation, this field is ignored, 
      and is not representative of the time interval.
      
      This attribute is ignored when rateEnforcement is off, or when cir 
      and bc are non-zero. If rateEnforcement is on and both cir and bc 
      are zero, this field must be non-zero."
   DEFVAL     { 0 }
::= { mscFrNniDlciSpParmsEntry 6 }

mscFrNniDlciSpRateAdaptation OBJECT-TYPE
   SYNTAX     INTEGER  {
                 off(0),
                 on(1),
                 eirOnly(2),
                 cirProportionate(3) }
   ACCESS     read-write
   STATUS     mandatory
   DESCRIPTION
     "This attribute specifies whether rate adaptation is in effect for this 
      user Data Link Connection on this Frame Relay interface. Rate 
      adaptation is a feature that, in periods of congestion, adapts the rate 
      at which the user is allowed to send data into the network to that 
      which the network is able to handle at that time. This pro-active 
      measure of handling congestion optimizes network resources by 
      causing the ingress to discard frames that would otherwise be 
      discarded in the network.
      
      If this attribute is set to on, then, at the onset of congestion, the 
      excess information rate (EIR) is reduced to a very low rate. If 
      congestion persists, then the allowed CIR is reduced geometrically 
      by 25% of the current value at that time. The minimum to which 
      CIR can be reduced is 1/16th (6.25%) of the provisioned value. As 
      congestion alleviates, CIR is increased linearly by 6.25% of the 
      provisioned value specified in committedInformationRate.
      
      If set to eirOnly, then rate adaptation will only apply to the excess 
      information rate (EIR). At the onset of congestion, the allowed EIR 
      is reduced by 25% of its provisioned value. If congestion persists, 
      EIR is reduced geometrically by 25% of the current value at that 
      time. As congestion alleviates, EIR is gradually increased linearly 
      by 6.25% of the provisioned EIR.
      
      If set to cirProportionate, then rate adaptation will also only apply 
      to the excess information rate (EIR). At the onset of congestion the 
      initial allowed EIR is set to a multiple of the provisioned CIR. If 
      congestion persists, the allowed EIR is reduced geometrically by 
      25% of the current value at that time. As congestion alleviates, EIR 
      is gradually increased linearly by 6.25% of the provisioned EIR. 
      Note that the allowed EIR may be set higher than the provisioned 
      EIR, since it is calculated initially using another parameter, the 
      provisioned CIR. If the allowed EIR at the moment is higher than 
      the provisioned EIR, then the provisioned EIR is used instead.
      
      This attribute can only be set to on eirOnly or cirProportionate if 
      rateEnforcement is turned on."
   DEFVAL     { off }
::= { mscFrNniDlciSpParmsEntry 7 }

mscFrNniDlciSpAccounting OBJECT-TYPE
   SYNTAX     INTEGER  {
                 off(0),
                 on(1) }
   ACCESS     read-write
   STATUS     mandatory
   DESCRIPTION
     "This attribute specifies whether accounting data collection and 
      record generation is turned on at this DLCI. For accounting data 
      collection and record generation to be turned on, the accountingOn 
      bit and at least one of the accountCollection bits in the 
      DataNetworkAddress component must be set to on."
   DEFVAL     { on }
::= { mscFrNniDlciSpParmsEntry 8 }

mscFrNniDlciSpRaSensitivity OBJECT-TYPE
   SYNTAX     Unsigned32 (1..20)
   ACCESS     read-write
   STATUS     mandatory
   DESCRIPTION
     "This attribute specifies the sensitivity of the rate adaptation system. 
      A higher number indicates a higher sensitivity and therefore a 
      quicker reaction time to network conditions. A quicker reaction 
      time allows the network to discard frames at the access and protect 
      network resources, but can lead to false alarms and a greater 
      fluctuation of the allowed rate. A higher setting therefore tends to 
      favour the protection of the network over the allowed throughput of 
      the user.
      
      A lower number indicates a lower sensitivity and therefore a slower 
      reaction to network conditions. A slower reaction time results in a 
      greater amount of user traffic allowed into the network, but can lead 
      to a waste of network bandwidth since the traffic may be discarded 
      at the congested resource. A lower setting therefore tends to favour 
      the allowed throughput of the user over the protection of the 
      network.
      
      This attribute is applicable for adapting EIR when rateAdaptation is 
      eirOnly or cirProportionate, or CIR when rateAdaptation is on.
      
      This attribute is ignored if rateAdaptation is turned off."
   DEFVAL     { 7 }
::= { mscFrNniDlciSpParmsEntry 9 }

mscFrNniDlciSpUpdateBCI OBJECT-TYPE
   SYNTAX     INTEGER  {
                 off(0),
                 on(1) }
   ACCESS     read-write
   STATUS     mandatory
   DESCRIPTION
     "This attribute specifies whether internal Backward Congestion 
      Indication (BCI) bits will report congestion external to the Passport 
      network, as communicated through incoming BECN bits.
      
      If updateBCI is set to on, then BCI bits for incoming frames will be 
      set if the BECN on the frame is set. If updatBCI is set to off, then 
      incoming BECN bits will have no effect.
      
      Setting updateBCI on for a DLCI means that the remote end of the 
      DLCI, which is specified by the remotedna and remotedlci attributes 
      of the dc component of the dlci, may perform Rate Adaptation 
      using the flow of incoming BECN bits, in addition to internal 
      Passport congestion management systems.
      
      If the rateAdaptation attribute of the remote dlci is provisioned as 
      eirOnly, cirProportionate, or on, then congestion from another 
      network connected to a Passport network may trigger dynamic 
      congestion management. If the rateAdaptation attribute of the 
      remote dlci is provisioned to off, then the setting of updateBCI 
      attribute here will have no effect.."
   DEFVAL     { off }
::= { mscFrNniDlciSpParmsEntry 10 }


-- FrUni/n Dlci/n LoopBack	
-- FrNni/n Dlci/n LoopBack		
-- This component is the data loopback tool for the parent DLCI.

mscFrNniDlciLb OBJECT IDENTIFIER ::= { mscFrNniDlci 5 }



mscFrNniDlciLbRowStatusTable OBJECT-TYPE
   SYNTAX     SEQUENCE OF MscFrNniDlciLbRowStatusEntry
   ACCESS     not-accessible
   STATUS     mandatory
   DESCRIPTION
     "This entry controls the addition and deletion of 
      mscFrNniDlciLb components."
::= { mscFrNniDlciLb 1 }

mscFrNniDlciLbRowStatusEntry OBJECT-TYPE
   SYNTAX     MscFrNniDlciLbRowStatusEntry
   ACCESS     not-accessible
   STATUS     mandatory
   DESCRIPTION
     "A single entry in the table represents a single 
      mscFrNniDlciLb component."
   INDEX {
      mscFrNniIndex,
      mscFrNniDlciIndex,
      mscFrNniDlciLbIndex }
::= { mscFrNniDlciLbRowStatusTable 1 }

MscFrNniDlciLbRowStatusEntry ::= SEQUENCE {
   mscFrNniDlciLbRowStatus
      RowStatus,
   mscFrNniDlciLbComponentName
      DisplayString,
   mscFrNniDlciLbStorageType
      StorageType,
   mscFrNniDlciLbIndex
      NonReplicated }

mscFrNniDlciLbRowStatus OBJECT-TYPE
   SYNTAX     RowStatus 
   ACCESS     read-only
   STATUS     mandatory
   DESCRIPTION
     "This variable is used as the basis for SNMP naming of
      mscFrNniDlciLb components.
      These components cannot be added nor deleted."
::= { mscFrNniDlciLbRowStatusEntry 1 }

mscFrNniDlciLbComponentName OBJECT-TYPE
   SYNTAX     DisplayString 
   ACCESS     read-only
   STATUS     mandatory
   DESCRIPTION
     "This variable provides the component's string name for
      use with the ASCII Console Interface"
::= { mscFrNniDlciLbRowStatusEntry 2 }

mscFrNniDlciLbStorageType OBJECT-TYPE
   SYNTAX     StorageType 
   ACCESS     read-only
   STATUS     mandatory
   DESCRIPTION
     "This variable represents the storage type value for the
      mscFrNniDlciLb tables."
::= { mscFrNniDlciLbRowStatusEntry 4 }

mscFrNniDlciLbIndex OBJECT-TYPE
   SYNTAX     NonReplicated 
   ACCESS     not-accessible
   STATUS     mandatory
   DESCRIPTION
     "This variable represents the index for the mscFrNniDlciLb tables."
::= { mscFrNniDlciLbRowStatusEntry 10 }

mscFrNniDlciLbStatsTable OBJECT-TYPE
   SYNTAX     SEQUENCE OF MscFrNniDlciLbStatsEntry
   ACCESS     not-accessible
   STATUS     mandatory
   DESCRIPTION
     "This group contains all the statistics for the data loopback tool."
::= { mscFrNniDlciLb 10 }

mscFrNniDlciLbStatsEntry OBJECT-TYPE
   SYNTAX     MscFrNniDlciLbStatsEntry
   ACCESS     not-accessible
   STATUS     mandatory
   DESCRIPTION
     "An entry in the mscFrNniDlciLbStatsTable."
   INDEX {
      mscFrNniIndex,
      mscFrNniDlciIndex,
      mscFrNniDlciLbIndex }
::= { mscFrNniDlciLbStatsTable 1 }

MscFrNniDlciLbStatsEntry ::= SEQUENCE {
   mscFrNniDlciLbLocalTotalFrm
      Unsigned32,
   mscFrNniDlciLbLocalTotalBytes
      Unsigned32,
   mscFrNniDlciLbLocalFecnFrm
      Unsigned32,
   mscFrNniDlciLbLocalBecnFrm
      Unsigned32,
   mscFrNniDlciLbLocalDeFrm
      Unsigned32,
   mscFrNniDlciLbLocalDeBytes
      Unsigned32,
   mscFrNniDlciLbRemoteTotalFrm
      Unsigned32,
   mscFrNniDlciLbRemoteTotalBytes
      Unsigned32,
   mscFrNniDlciLbRemoteFecnFrm
      Unsigned32,
   mscFrNniDlciLbRemoteBecnFrm
      Unsigned32,
   mscFrNniDlciLbRemoteDeFrm
      Unsigned32,
   mscFrNniDlciLbRemoteDeBytes
      Unsigned32 }

mscFrNniDlciLbLocalTotalFrm OBJECT-TYPE
   SYNTAX     Unsigned32 (0..4294967295)
   ACCESS     read-only
   STATUS     mandatory
   DESCRIPTION
     "This attribute records the number of frames looped back to the link 
      since loopback was last started."
   DEFVAL     { 0 }
::= { mscFrNniDlciLbStatsEntry 1 }

mscFrNniDlciLbLocalTotalBytes OBJECT-TYPE
   SYNTAX     Unsigned32 (0..4294967295)
   ACCESS     read-only
   STATUS     mandatory
   DESCRIPTION
     "This attribute records the number of bytes looped back to the link 
      since loopback mode was started."
   DEFVAL     { 0 }
::= { mscFrNniDlciLbStatsEntry 2 }

mscFrNniDlciLbLocalFecnFrm OBJECT-TYPE
   SYNTAX     Unsigned32 (0..4294967295)
   ACCESS     read-only
   STATUS     mandatory
   DESCRIPTION
     "This attribute records the number of frames with the Forward 
      Explicit Congestion Notification (FECN) bit set, looped back to the 
      link since the loopback mode was started."
   DEFVAL     { 0 }
::= { mscFrNniDlciLbStatsEntry 3 }

mscFrNniDlciLbLocalBecnFrm OBJECT-TYPE
   SYNTAX     Unsigned32 (0..4294967295)
   ACCESS     read-only
   STATUS     mandatory
   DESCRIPTION
     "This attribute records the number of frames with the Backward 
      Explicit Congestion Notification (BECN) bit set, looped back to the 
      link since the loopback mode was started."
   DEFVAL     { 0 }
::= { mscFrNniDlciLbStatsEntry 4 }

mscFrNniDlciLbLocalDeFrm OBJECT-TYPE
   SYNTAX     Unsigned32 (0..4294967295)
   ACCESS     read-only
   STATUS     mandatory
   DESCRIPTION
     "This attribute records the number of frames with the Discard 
      Eligibility (DE) bit set, looped back to the link since the loopback 
      mode was started."
   DEFVAL     { 0 }
::= { mscFrNniDlciLbStatsEntry 5 }

mscFrNniDlciLbLocalDeBytes OBJECT-TYPE
   SYNTAX     Unsigned32 (0..4294967295)
   ACCESS     read-only
   STATUS     mandatory
   DESCRIPTION
     "This attribute records the number of bytes in frames with the 
      Discard Eligibility (DE) bit set, looped back to the link since the 
      loopback mode was started."
   DEFVAL     { 0 }
::= { mscFrNniDlciLbStatsEntry 6 }

mscFrNniDlciLbRemoteTotalFrm OBJECT-TYPE
   SYNTAX     Unsigned32 (0..4294967295)
   ACCESS     read-only
   STATUS     mandatory
   DESCRIPTION
     "This attribute records the number of frames looped back to the 
      subnet since loopback was last started."
   DEFVAL     { 0 }
::= { mscFrNniDlciLbStatsEntry 7 }

mscFrNniDlciLbRemoteTotalBytes OBJECT-TYPE
   SYNTAX     Unsigned32 (0..4294967295)
   ACCESS     read-only
   STATUS     mandatory
   DESCRIPTION
     "This attribute records the number of bytes looped back to the subnet 
      since loopback was last started."
   DEFVAL     { 0 }
::= { mscFrNniDlciLbStatsEntry 8 }

mscFrNniDlciLbRemoteFecnFrm OBJECT-TYPE
   SYNTAX     Unsigned32 (0..4294967295)
   ACCESS     read-only
   STATUS     mandatory
   DESCRIPTION
     "This attribute records the number of frames with the Forward 
      Explicit Congestion Notification (FECN) bit set, looped back to the 
      subnet since the loopback mode was started."
   DEFVAL     { 0 }
::= { mscFrNniDlciLbStatsEntry 9 }

mscFrNniDlciLbRemoteBecnFrm OBJECT-TYPE
   SYNTAX     Unsigned32 (0..4294967295)
   ACCESS     read-only
   STATUS     mandatory
   DESCRIPTION
     "This attribute records the number of frames with the Backward 
      Explicit Congestion Notification (BECN) bit set, looped back to the 
      subnet since the loopback mode was started."
   DEFVAL     { 0 }
::= { mscFrNniDlciLbStatsEntry 10 }

mscFrNniDlciLbRemoteDeFrm OBJECT-TYPE
   SYNTAX     Unsigned32 (0..4294967295)
   ACCESS     read-only
   STATUS     mandatory
   DESCRIPTION
     "This attribute records the number of frames with the Discard 
      Eligibility (DE) bit set, looped back to the subnet since the 
      loopback mode was started."
   DEFVAL     { 0 }
::= { mscFrNniDlciLbStatsEntry 13 }

mscFrNniDlciLbRemoteDeBytes OBJECT-TYPE
   SYNTAX     Unsigned32 (0..4294967295)
   ACCESS     read-only
   STATUS     mandatory
   DESCRIPTION
     "This attribute records the number of bytes in frames with the 
      Discard Eligibility (DE) bit set, looped back to the subnet since the 
      loopback mode was started."
   DEFVAL     { 0 }
::= { mscFrNniDlciLbStatsEntry 14 }


-- FrNni/n Dlci/n EgressServiceParameters
-- This component contains the provisionable attributes of the egress 
-- direction for the parent Dlci component.

mscFrNniDlciEgressSp OBJECT IDENTIFIER ::= { mscFrNniDlci 6 }



mscFrNniDlciEgressSpRowStatusTable OBJECT-TYPE
   SYNTAX     SEQUENCE OF MscFrNniDlciEgressSpRowStatusEntry
   ACCESS     not-accessible
   STATUS     mandatory
   DESCRIPTION
     "This entry controls the addition and deletion of 
      mscFrNniDlciEgressSp components."
::= { mscFrNniDlciEgressSp 1 }

mscFrNniDlciEgressSpRowStatusEntry OBJECT-TYPE
   SYNTAX     MscFrNniDlciEgressSpRowStatusEntry
   ACCESS     not-accessible
   STATUS     mandatory
   DESCRIPTION
     "A single entry in the table represents a single 
      mscFrNniDlciEgressSp component."
   INDEX {
      mscFrNniIndex,
      mscFrNniDlciIndex,
      mscFrNniDlciEgressSpIndex }
::= { mscFrNniDlciEgressSpRowStatusTable 1 }

MscFrNniDlciEgressSpRowStatusEntry ::= SEQUENCE {
   mscFrNniDlciEgressSpRowStatus
      RowStatus,
   mscFrNniDlciEgressSpComponentName
      DisplayString,
   mscFrNniDlciEgressSpStorageType
      StorageType,
   mscFrNniDlciEgressSpIndex
      NonReplicated }

mscFrNniDlciEgressSpRowStatus OBJECT-TYPE
   SYNTAX     RowStatus 
   ACCESS     read-only
   STATUS     mandatory
   DESCRIPTION
     "This variable is used as the basis for SNMP naming of
      mscFrNniDlciEgressSp components.
      These components cannot be added nor deleted."
::= { mscFrNniDlciEgressSpRowStatusEntry 1 }

mscFrNniDlciEgressSpComponentName OBJECT-TYPE
   SYNTAX     DisplayString 
   ACCESS     read-only
   STATUS     mandatory
   DESCRIPTION
     "This variable provides the component's string name for
      use with the ASCII Console Interface"
::= { mscFrNniDlciEgressSpRowStatusEntry 2 }

mscFrNniDlciEgressSpStorageType OBJECT-TYPE
   SYNTAX     StorageType 
   ACCESS     read-only
   STATUS     mandatory
   DESCRIPTION
     "This variable represents the storage type value for the
      mscFrNniDlciEgressSp tables."
::= { mscFrNniDlciEgressSpRowStatusEntry 4 }

mscFrNniDlciEgressSpIndex OBJECT-TYPE
   SYNTAX     NonReplicated 
   ACCESS     not-accessible
   STATUS     mandatory
   DESCRIPTION
     "This variable represents the index for the mscFrNniDlciEgressSp tables."
::= { mscFrNniDlciEgressSpRowStatusEntry 10 }

mscFrNniDlciEgressSpProvTable OBJECT-TYPE
   SYNTAX     SEQUENCE OF MscFrNniDlciEgressSpProvEntry
   ACCESS     not-accessible
   STATUS     mandatory
   DESCRIPTION
     "This group contains the provisionable attributes for this component."
::= { mscFrNniDlciEgressSp 10 }

mscFrNniDlciEgressSpProvEntry OBJECT-TYPE
   SYNTAX     MscFrNniDlciEgressSpProvEntry
   ACCESS     not-accessible
   STATUS     mandatory
   DESCRIPTION
     "An entry in the mscFrNniDlciEgressSpProvTable."
   INDEX {
      mscFrNniIndex,
      mscFrNniDlciIndex,
      mscFrNniDlciEgressSpIndex }
::= { mscFrNniDlciEgressSpProvTable 1 }

MscFrNniDlciEgressSpProvEntry ::= SEQUENCE {
   mscFrNniDlciEgressSpCommittedInformationRate
      Unsigned32,
   mscFrNniDlciEgressSpCommittedBurstSize
      Unsigned32,
   mscFrNniDlciEgressSpExcessBurstSize
      Unsigned32,
   mscFrNniDlciEgressSpMeasurementInterval
      Unsigned32 }

mscFrNniDlciEgressSpCommittedInformationRate OBJECT-TYPE
   SYNTAX     Unsigned32 (0..50000000 | 50000001)
   ACCESS     read-write
   STATUS     mandatory
   DESCRIPTION
     "This attribute specifies the committed information rate (CIR) for the 
      egress direction. It is used for Call Admission Control (CAC) at the 
      egress link.
      If the value is set to sameAsSp, the value of this attribute is the 
      same as the committedInformationRate attribute under the 
      ServiceParameters component.

      VALUES (

      50000001 = sameAsServiceParameters

      )"
   DEFVAL     { 50000001 }
::= { mscFrNniDlciEgressSpProvEntry 1 }

mscFrNniDlciEgressSpCommittedBurstSize OBJECT-TYPE
   SYNTAX     Unsigned32 (0..50000000 | 50000001)
   ACCESS     read-write
   STATUS     mandatory
   DESCRIPTION
     "This attribute specifies the committed burst size (Bc) for the egress 
      direction. It is used for performing Call Admission Control (CAC) 
      at the egress link.
      If the value is set to sameAsSp, the value of this attribute is the 
      same as the committedBurstSize attribute under the 
      ServiceParameters component.

      VALUES (

      50000001 = sameAsServiceParameters

      )"
   DEFVAL     { 50000001 }
::= { mscFrNniDlciEgressSpProvEntry 2 }

mscFrNniDlciEgressSpExcessBurstSize OBJECT-TYPE
   SYNTAX     Unsigned32 (0..50000000 | 50000001)
   ACCESS     read-write
   STATUS     mandatory
   DESCRIPTION
     "This attribute specifies the excess burst size (Be) for the egress 
      direction. It is used for Call Admission Control (CAC) function 
      towards the egress link.
      If the value is set to sameAsSp, the value of this attribute is the 
      same as the excessBurstSize attribute under the ServiceParameters 
      component.

      VALUES (

      50000001 = sameAsServiceParameters

      )"
   DEFVAL     { 50000001 }
::= { mscFrNniDlciEgressSpProvEntry 3 }

mscFrNniDlciEgressSpMeasurementInterval OBJECT-TYPE
   SYNTAX     Unsigned32 (0..25500 | 25501)
   ACCESS     read-write
   STATUS     mandatory
   DESCRIPTION
     "This attribute specifies the time interval over which rates and burst 
      sizes are measured in the egress direction. It is used for bandwidth 
      reservation for Call Admission Control (CAC) towards the egress 
      link.
      If the value is set to sameAsSp, the value of this attribute is the 
      same as the measurementInterval attribute under the 
      ServiceParameters component.

      VALUES (

      25501 = sameAsServiceParameters

      )"
   DEFVAL     { 25501 }
::= { mscFrNniDlciEgressSpProvEntry 4 }


-- FrUni/n VirtualFramer
-- FrDte/n VirtualFramer
-- The VirtualFramer component binds two services together to 
-- provide data transfer between them. It is mutually exclusive from 
-- Framer component. 

mscFrNniVFramer OBJECT IDENTIFIER ::= { mscFrNni 6 }



mscFrNniVFramerRowStatusTable OBJECT-TYPE
   SYNTAX     SEQUENCE OF MscFrNniVFramerRowStatusEntry
   ACCESS     not-accessible
   STATUS     mandatory
   DESCRIPTION
     "This entry controls the addition and deletion of 
      mscFrNniVFramer components."
::= { mscFrNniVFramer 1 }

mscFrNniVFramerRowStatusEntry OBJECT-TYPE
   SYNTAX     MscFrNniVFramerRowStatusEntry
   ACCESS     not-accessible
   STATUS     mandatory
   DESCRIPTION
     "A single entry in the table represents a single 
      mscFrNniVFramer component."
   INDEX {
      mscFrNniIndex,
      mscFrNniVFramerIndex }
::= { mscFrNniVFramerRowStatusTable 1 }

MscFrNniVFramerRowStatusEntry ::= SEQUENCE {
   mscFrNniVFramerRowStatus
      RowStatus,
   mscFrNniVFramerComponentName
      DisplayString,
   mscFrNniVFramerStorageType
      StorageType,
   mscFrNniVFramerIndex
      NonReplicated }

mscFrNniVFramerRowStatus OBJECT-TYPE
   SYNTAX     RowStatus 
   ACCESS     read-write
   STATUS     mandatory
   DESCRIPTION
     "This variable is used as the basis for SNMP naming of
      mscFrNniVFramer components.
      These components can be added and deleted."
::= { mscFrNniVFramerRowStatusEntry 1 }

mscFrNniVFramerComponentName OBJECT-TYPE
   SYNTAX     DisplayString 
   ACCESS     read-only
   STATUS     mandatory
   DESCRIPTION
     "This variable provides the component's string name for
      use with the ASCII Console Interface"
::= { mscFrNniVFramerRowStatusEntry 2 }

mscFrNniVFramerStorageType OBJECT-TYPE
   SYNTAX     StorageType 
   ACCESS     read-only
   STATUS     mandatory
   DESCRIPTION
     "This variable represents the storage type value for the
      mscFrNniVFramer tables."
::= { mscFrNniVFramerRowStatusEntry 4 }

mscFrNniVFramerIndex OBJECT-TYPE
   SYNTAX     NonReplicated 
   ACCESS     not-accessible
   STATUS     mandatory
   DESCRIPTION
     "This variable represents the index for the mscFrNniVFramer tables."
::= { mscFrNniVFramerRowStatusEntry 10 }

mscFrNniVFramerProvTable OBJECT-TYPE
   SYNTAX     SEQUENCE OF MscFrNniVFramerProvEntry
   ACCESS     not-accessible
   STATUS     mandatory
   DESCRIPTION
     "This group contains provisionable attributes for the VirtualFramer 
      component."
::= { mscFrNniVFramer 10 }

mscFrNniVFramerProvEntry OBJECT-TYPE
   SYNTAX     MscFrNniVFramerProvEntry
   ACCESS     not-accessible
   STATUS     mandatory
   DESCRIPTION
     "An entry in the mscFrNniVFramerProvTable."
   INDEX {
      mscFrNniIndex,
      mscFrNniVFramerIndex }
::= { mscFrNniVFramerProvTable 1 }

MscFrNniVFramerProvEntry ::= SEQUENCE {
   mscFrNniVFramerOtherVirtualFramer
      Link,
   mscFrNniVFramerLogicalProcessor
      Link }

mscFrNniVFramerOtherVirtualFramer OBJECT-TYPE
   SYNTAX     Link 
   ACCESS     read-write
   STATUS     mandatory
   DESCRIPTION
     "This attribute specifies the other VirtualFramer to which the service 
      is linked, for example, FrUni/n VirtualFramer, FrDte/n 
      VirtualFramer."
::= { mscFrNniVFramerProvEntry 1 }

mscFrNniVFramerLogicalProcessor OBJECT-TYPE
   SYNTAX     Link 
   ACCESS     read-write
   STATUS     mandatory
   DESCRIPTION
     "This attribute specifies the logical processor on which the service 
      component will reside."
::= { mscFrNniVFramerProvEntry 2 }

mscFrNniVFramerStateTable OBJECT-TYPE
   SYNTAX     SEQUENCE OF MscFrNniVFramerStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscFrNniVFramer 11 }

mscFrNniVFramerStateEntry OBJECT-TYPE
   SYNTAX     MscFrNniVFramerStateEntry
   ACCESS     not-accessible
   STATUS     mandatory
   DESCRIPTION
     "An entry in the mscFrNniVFramerStateTable."
   INDEX {
      mscFrNniIndex,
      mscFrNniVFramerIndex }
::= { mscFrNniVFramerStateTable 1 }

MscFrNniVFramerStateEntry ::= SEQUENCE {
   mscFrNniVFramerAdminState
      INTEGER,
   mscFrNniVFramerOperationalState
      INTEGER,
   mscFrNniVFramerUsageState
      INTEGER }

mscFrNniVFramerAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscFrNniVFramerStateEntry 1 }

mscFrNniVFramerOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscFrNniVFramerStateEntry 2 }

mscFrNniVFramerUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscFrNniVFramerStateEntry 3 }

mscFrNniVFramerStatsTable OBJECT-TYPE
   SYNTAX     SEQUENCE OF MscFrNniVFramerStatsEntry
   ACCESS     not-accessible
   STATUS     mandatory
   DESCRIPTION
     "This group contains the operational statistics data for a 
      VirtualFramer component."
::= { mscFrNniVFramer 12 }

mscFrNniVFramerStatsEntry OBJECT-TYPE
   SYNTAX     MscFrNniVFramerStatsEntry
   ACCESS     not-accessible
   STATUS     mandatory
   DESCRIPTION
     "An entry in the mscFrNniVFramerStatsTable."
   INDEX {
      mscFrNniIndex,
      mscFrNniVFramerIndex }
::= { mscFrNniVFramerStatsTable 1 }

MscFrNniVFramerStatsEntry ::= SEQUENCE {
   mscFrNniVFramerFrmToOtherVFramer
      PassportCounter64,
   mscFrNniVFramerFrmFromOtherVFramer
      PassportCounter64,
   mscFrNniVFramerOctetFromOtherVFramer
      PassportCounter64 }

mscFrNniVFramerFrmToOtherVFramer OBJECT-TYPE
   SYNTAX     PassportCounter64 
   ACCESS     read-only
   STATUS     mandatory
   DESCRIPTION
     "This attribute counts the frames transmitted to the 
      otherVirtualFramer."
::= { mscFrNniVFramerStatsEntry 2 }

mscFrNniVFramerFrmFromOtherVFramer OBJECT-TYPE
   SYNTAX     PassportCounter64 
   ACCESS     read-only
   STATUS     mandatory
   DESCRIPTION
     "This attribute counts the frames received from the 
      otherVirtualFramer."
::= { mscFrNniVFramerStatsEntry 3 }

mscFrNniVFramerOctetFromOtherVFramer OBJECT-TYPE
   SYNTAX     PassportCounter64 
   ACCESS     read-only
   STATUS     mandatory
   DESCRIPTION
     "This attribute counts the octets received from the 
      otherVirtualFramer."
::= { mscFrNniVFramerStatsEntry 5 }


-- FrNni/n Signaling
-- This component defines the FRF.10 and Q.922 (LAPF) parameters 
-- for Frame Relay switched virtual circuits at the Network-Network 
-- interface. This component must be provisioned for the FrNni 
-- interface to support switched connections.

mscFrNniSig OBJECT IDENTIFIER ::= { mscFrNni 8 }



mscFrNniSigRowStatusTable OBJECT-TYPE
   SYNTAX     SEQUENCE OF MscFrNniSigRowStatusEntry
   ACCESS     not-accessible
   STATUS     mandatory
   DESCRIPTION
     "This entry controls the addition and deletion of 
      mscFrNniSig components."
::= { mscFrNniSig 1 }

mscFrNniSigRowStatusEntry OBJECT-TYPE
   SYNTAX     MscFrNniSigRowStatusEntry
   ACCESS     not-accessible
   STATUS     mandatory
   DESCRIPTION
     "A single entry in the table represents a single 
      mscFrNniSig component."
   INDEX {
      mscFrNniIndex,
      mscFrNniSigIndex }
::= { mscFrNniSigRowStatusTable 1 }

MscFrNniSigRowStatusEntry ::= SEQUENCE {
   mscFrNniSigRowStatus
      RowStatus,
   mscFrNniSigComponentName
      DisplayString,
   mscFrNniSigStorageType
      StorageType,
   mscFrNniSigIndex
      NonReplicated }

mscFrNniSigRowStatus OBJECT-TYPE
   SYNTAX     RowStatus 
   ACCESS     read-write
   STATUS     mandatory
   DESCRIPTION
     "This variable is used as the basis for SNMP naming of
      mscFrNniSig components.
      These components can be added and deleted."
::= { mscFrNniSigRowStatusEntry 1 }

mscFrNniSigComponentName OBJECT-TYPE
   SYNTAX     DisplayString 
   ACCESS     read-only
   STATUS     mandatory
   DESCRIPTION
     "This variable provides the component's string name for
      use with the ASCII Console Interface"
::= { mscFrNniSigRowStatusEntry 2 }

mscFrNniSigStorageType OBJECT-TYPE
   SYNTAX     StorageType 
   ACCESS     read-only
   STATUS     mandatory
   DESCRIPTION
     "This variable represents the storage type value for the
      mscFrNniSig tables."
::= { mscFrNniSigRowStatusEntry 4 }

mscFrNniSigIndex OBJECT-TYPE
   SYNTAX     NonReplicated 
   ACCESS     not-accessible
   STATUS     mandatory
   DESCRIPTION
     "This variable represents the index for the mscFrNniSig tables."
::= { mscFrNniSigRowStatusEntry 10 }

mscFrNniSigProvTable OBJECT-TYPE
   SYNTAX     SEQUENCE OF MscFrNniSigProvEntry
   ACCESS     not-accessible
   STATUS     mandatory
   DESCRIPTION
     "This group contains common provisionable attributes for signaling 
      at the interface."
::= { mscFrNniSig 11 }

mscFrNniSigProvEntry OBJECT-TYPE
   SYNTAX     MscFrNniSigProvEntry
   ACCESS     not-accessible
   STATUS     mandatory
   DESCRIPTION
     "An entry in the mscFrNniSigProvTable."
   INDEX {
      mscFrNniIndex,
      mscFrNniSigIndex }
::= { mscFrNniSigProvTable 1 }

MscFrNniSigProvEntry ::= SEQUENCE {
   mscFrNniSigDlciAllocation
      INTEGER,
   mscFrNniSigHighestPermanentDlci
      Unsigned32,
   mscFrNniSigHighestPvcDlci
      Unsigned32 }

mscFrNniSigDlciAllocation OBJECT-TYPE
   SYNTAX     INTEGER  {
                 fromLowEnd(0),
                 fromHighEnd(1) }
   ACCESS     read-write
   STATUS     mandatory
   DESCRIPTION
     "This attribute specifies the order in which DLCIs are dynamically 
      allocated for SVCs. The purpose of this attribute is to prevent DLCI 
      collisions between SVCs initiated by two FrNni interfaces talking to 
      each other. This is achieved by provisioning a different value for 
      this attribute at each end of the NNI link.
      
      A value of fromLowEnd specifies that the DLCI number 
      assignment for SVC connections is initiated from the lowest value 
      of the range (that is, highestPvcDlci+1 up to 1007).
      
      A value of fromHighEnd specifies that the DLCI number 
      assignment for SVC connections is initiated from the highest value 
      of the range (that is, 1007 down to highestPvcDlci+1)."
   DEFVAL     { fromLowEnd }
::= { mscFrNniSigProvEntry 3 }

mscFrNniSigHighestPermanentDlci OBJECT-TYPE
   SYNTAX     Unsigned32 (0 | 16..1007)
   ACCESS     read-write
   STATUS     obsolete
   DESCRIPTION
     "This attribute specifies the highest DLCI value that can be 
      provisioned for a permanent connection. It partitions the DLCI 
      space into permanent and switched connections. Permanent DLCI 
      numbers higher than this value cannot be provisioned. The value 0 
      is used to indicate that no permanent connections are allowed on 
      this interface. The value 1007 indicates that no switched 
      connections are allowed on this interface."
   DEFVAL     { 500 }
::= { mscFrNniSigProvEntry 4 }

mscFrNniSigHighestPvcDlci OBJECT-TYPE
   SYNTAX     Unsigned32 (0 | 16..1007)
   ACCESS     read-write
   STATUS     mandatory
   DESCRIPTION
     "This attribute specifies the highest DLCI value that can be 
      provisioned for a permanent connection. It partitions the DLCI 
      space into permanent and switched connections. Permanent DLCI 
      numbers higher than this value cannot be provisioned. The value 0 
      is used to indicate that no permanent connections are allowed on 
      this interface. The value 1007 indicates that no switched 
      connections are allowed on this interface."
   DEFVAL     { 500 }
::= { mscFrNniSigProvEntry 5 }

mscFrNniSigServParmsTable OBJECT-TYPE
   SYNTAX     SEQUENCE OF MscFrNniSigServParmsEntry
   ACCESS     not-accessible
   STATUS     mandatory
   DESCRIPTION
     "This group contains the provisionable service parameters."
::= { mscFrNniSig 12 }

mscFrNniSigServParmsEntry OBJECT-TYPE
   SYNTAX     MscFrNniSigServParmsEntry
   ACCESS     not-accessible
   STATUS     mandatory
   DESCRIPTION
     "An entry in the mscFrNniSigServParmsTable."
   INDEX {
      mscFrNniIndex,
      mscFrNniSigIndex }
::= { mscFrNniSigServParmsTable 1 }

MscFrNniSigServParmsEntry ::= SEQUENCE {
   mscFrNniSigMaximumFrameSize
      Unsigned32,
   mscFrNniSigDefaultMaximumFrameSize
      Unsigned32,
   mscFrNniSigDefaultCommittedInformationRate
      Unsigned32,
   mscFrNniSigDefaultCommittedBurstSize
      Unsigned32,
   mscFrNniSigDefaultExcessBurstSize
      Unsigned32,
   mscFrNniSigRateEnforcement
      INTEGER,
   mscFrNniSigRateAdaptation
      INTEGER,
   mscFrNniSigRaSensitivity
      Unsigned32,
   mscFrNniSigUpdateBCI
      INTEGER }

mscFrNniSigMaximumFrameSize OBJECT-TYPE
   SYNTAX     Unsigned32 (1..8187)
   ACCESS     read-write
   STATUS     mandatory
   DESCRIPTION
     "This attribute specifies the maximum number of octets that may be 
      included in the information field of the user DLCI of any switched 
      connections using this interface. Its value must not be smaller than 
      the value of defaultMaximumFrameSize."
   DEFVAL     { 4096 }
::= { mscFrNniSigServParmsEntry 1 }

mscFrNniSigDefaultMaximumFrameSize OBJECT-TYPE
   SYNTAX     Unsigned32 (1..8187)
   ACCESS     read-write
   STATUS     mandatory
   DESCRIPTION
     "This attribute specifies the default maximum number of octets that 
      may be included in the information field of the user DLCI assigned 
      for any switched connections using this interface. This value is used 
      during call parameter negotiation for switched calls on this interface 
      when the maximum frame size is not specified in the user's SETUP 
      message. The value of this attribute must not exceed the value of the 
      maximumFrameSize attribute."
   DEFVAL     { 2100 }
::= { mscFrNniSigServParmsEntry 2 }

mscFrNniSigDefaultCommittedInformationRate OBJECT-TYPE
   SYNTAX     Unsigned32 (0..52000000)
   ACCESS     read-write
   STATUS     mandatory
   DESCRIPTION
     "This attribute specifies the default user to network direction CIR. 
      This value is used during call parameter negotiation for switched 
      calls on this interface when the CIR is not specified in the user's 
      SETUP message."
   DEFVAL     { 64000 }
::= { mscFrNniSigServParmsEntry 3 }

mscFrNniSigDefaultCommittedBurstSize OBJECT-TYPE
   SYNTAX     Unsigned32 (0..52000000)
   ACCESS     read-write
   STATUS     mandatory
   DESCRIPTION
     "This attribute specifies the default user to network direction Bc. 
      This value is used during call parameter negotiation for switched 
      calls on this interface when the Bc is not specified in the user's 
      SETUP message."
   DEFVAL     { 64000 }
::= { mscFrNniSigServParmsEntry 4 }

mscFrNniSigDefaultExcessBurstSize OBJECT-TYPE
   SYNTAX     Unsigned32 (0..52000000)
   ACCESS     read-write
   STATUS     mandatory
   DESCRIPTION
     "This attribute specifies the default user to network direction Be. 
      This value is used during call parameter negotiation for switched 
      calls on this interface when the Be is not specified in the user's 
      SETUP message."
   DEFVAL     { 0 }
::= { mscFrNniSigServParmsEntry 5 }

mscFrNniSigRateEnforcement OBJECT-TYPE
   SYNTAX     INTEGER  {
                 off(0),
                 on(1) }
   ACCESS     read-write
   STATUS     mandatory
   DESCRIPTION
     "This attribute specifies whether rate enforcement is in effect for 
      SVCs on this interface."
   DEFVAL     { on }
::= { mscFrNniSigServParmsEntry 6 }

mscFrNniSigRateAdaptation OBJECT-TYPE
   SYNTAX     INTEGER  {
                 off(0),
                 on(1),
                 eirOnly(2),
                 cirProportionate(3) }
   ACCESS     read-write
   STATUS     mandatory
   DESCRIPTION
     "This attribute specifies whether closed-loop rate adaptation is in 
      effect for SVCs on this interface. Rate adaptation is a feature that, in 
      periods of congestion, adapts the rate at which the user is allowed to 
      send data into the network to that which the network is able to 
      handle at that time. This proactive measure of handling congestion 
      optimizes network resources by causing the ingress to discard 
      frames that would otherwise be discarded in the network.
      
      If this attribute is set to on, then, at the onset of congestion, the 
      excess information rate (EIR) is reduced to a very low rate. If 
      congestion persists, then the allowed CIR is reduced geometrically 
      by 25% of the current value at that time. The minimum to which 
      CIR can be reduced is 1/16th (6.25%) of the provisioned value. As 
      congestion alleviates, CIR is increased linearly by 6.25% of the 
      provisioned value specified in committedInformationRate.
      
      If set to eirOnly, then rate adaptation will only apply to the excess 
      information rate (EIR). At the onset of congestion, the allowed EIR 
      is reduced by 25% of its provisioned value. If congestion persists, 
      EIR is reduced geometrically by 25% of the current value at that 
      time. As congestion alleviates, EIR is gradually increased linearly 
      by 6.25% of the provisioned EIR.
      
      If set to cirProportionate, then rate adaptation will also only apply 
      to the excess information rate (EIR). At the onset of congestion the 
      initial allowed EIR is set to a multiple of the provisioned CIR. If 
      congestion persists, the allowed EIR is reduced geometrically by 
      25% of the current value at that time. As congestion alleviates, EIR 
      is gradually increased linearly by 6.25% of the provisioned EIR. 
      Note that the allowed EIR may be set higher than the provisioned 
      EIR, since it is calculated initially using another parameter, the 
      provisioned CIR. If the allowed EIR at the moment is higher than 
      the provisioned EIR, then the provisioned EIR is used instead.
      
      This attribute can only be set to on or eirOnly if rateEnforcement is 
      set to on."
   DEFVAL     { off }
::= { mscFrNniSigServParmsEntry 7 }

mscFrNniSigRaSensitivity OBJECT-TYPE
   SYNTAX     Unsigned32 (1..20)
   ACCESS     read-write
   STATUS     mandatory
   DESCRIPTION
     "This attribute specifies the sensitivity of the rate adaptation system 
      for all switched connections on this interface.
      
      A higher number indicates a higher sensitivity and therefore a 
      quicker reaction time to network conditions. A quicker reaction 
      time allows the network to discard frames at the access and protect 
      network resources, but can lead to false alarms and a greater 
      fluctuation of the allowed rate. A higher setting therefore tends to 
      favor the protection of the network over the allowed throughput of 
      the user.
      
      A lower number indicates a lower sensitivity and therefore a slower 
      reaction to network conditions. A slower reaction time results in a 
      greater amount of user traffic allowed into the network, but can lead 
      to a waste of network bandwidth since the traffic may be discarded 
      at the congested resource. A lower setting therefore tends to favour 
      the allowed throughput of the user over the protection of the 
      network.
      
      This attribute is applicable for adapting EIR when rateAdaptation is 
      eirOnly or cirProportionate, or CIR when rateAdaptation is on. 
      
      This attribute is ignored if rateAdaptation is off."
   DEFVAL     { 7 }
::= { mscFrNniSigServParmsEntry 8 }

mscFrNniSigUpdateBCI OBJECT-TYPE
   SYNTAX     INTEGER  {
                 off(0),
                 on(1) }
   ACCESS     read-write
   STATUS     mandatory
   DESCRIPTION
     "This attribute specifies whether internal Backward Congestion 
      Indication (BCI) bits will report congestion external to the Passport 
      network, as communicated through incoming BECN bits.
      
      If updateBCI is set to on, then BCI bits for incoming frames will be 
      set if the BECN on the frame is set. If updateBCI is set to off, then 
      incoming BECN bits has no effect.
      
      Setting updateBCI on for a DLCI means that the remote end of the 
      DLCI, which is specified by the remoteDna and remoteDlci 
      attributes of the Dc component of the Dlci, may perform Rate 
      Adaptation using the flow of incoming BECN bits, in addition to 
      internal Passport congestion management systems.
      
      If the rateAdaptation attribute of the remote DLCI is provisioned as 
      eirOnly, cirProportionate, or on, then congestion from another 
      network connected to a Passport network may trigger dynamic 
      congestion management. If there is no rate adaptation at the other 
      end, then the setting of updateBCI attribute here will have no effect."
   DEFVAL     { off }
::= { mscFrNniSigServParmsEntry 9 }

mscFrNniSigSysParmsTable OBJECT-TYPE
   SYNTAX     SEQUENCE OF MscFrNniSigSysParmsEntry
   ACCESS     not-accessible
   STATUS     mandatory
   DESCRIPTION
     "This group contains the provisionable FRF.10 system parameters."
::= { mscFrNniSig 13 }

mscFrNniSigSysParmsEntry OBJECT-TYPE
   SYNTAX     MscFrNniSigSysParmsEntry
   ACCESS     not-accessible
   STATUS     mandatory
   DESCRIPTION
     "An entry in the mscFrNniSigSysParmsTable."
   INDEX {
      mscFrNniIndex,
      mscFrNniSigIndex }
::= { mscFrNniSigSysParmsTable 1 }

MscFrNniSigSysParmsEntry ::= SEQUENCE {
   mscFrNniSigCallSetupTimer
      Unsigned32,
   mscFrNniSigReleaseTimer
      Unsigned32,
   mscFrNniSigCallProceedingTimer
      Unsigned32,
   mscFrNniSigRestartReqTimer
      Unsigned32,
   mscFrNniSigRestartRcvTimer
      Unsigned32,
   mscFrNniSigStatusEnqTimer
      Unsigned32,
   mscFrNniSigNetworkType
      INTEGER }

mscFrNniSigCallSetupTimer OBJECT-TYPE
   SYNTAX     Unsigned32 (1..255)
   ACCESS     read-write
   STATUS     mandatory
   DESCRIPTION
     "This attribute specifies the time this interface waits for a response to 
      the SETUP message sent to the adjacent network. Upon timer 
      expiry, the SETUP message is retransmitted. The second expiry of 
      this timer causes the call to be cleared."
   DEFVAL     { 4 }
::= { mscFrNniSigSysParmsEntry 1 }

mscFrNniSigReleaseTimer OBJECT-TYPE
   SYNTAX     Unsigned32 (1..255)
   ACCESS     read-write
   STATUS     mandatory
   DESCRIPTION
     "This attribute specifies the time this interface waits for a response to 
      the RELEASE message sent to the adjacent network. Upon timer 
      expiry, the RELEASE message is retransmitted. The second expiry 
      of the timer causes the call to be released."
   DEFVAL     { 4 }
::= { mscFrNniSigSysParmsEntry 2 }

mscFrNniSigCallProceedingTimer OBJECT-TYPE
   SYNTAX     Unsigned32 (1..255)
   ACCESS     read-write
   STATUS     mandatory
   DESCRIPTION
     "This attribute specifies the time this interface waits for the 
      CONNECT message from the adjacent network after the network 
      has received the optional CALL PROCEEDING message from the 
      adjacent network. Upon timer expiry, the call is cleared."
   DEFVAL     { 30 }
::= { mscFrNniSigSysParmsEntry 3 }

mscFrNniSigRestartReqTimer OBJECT-TYPE
   SYNTAX     Unsigned32 (0..255)
   ACCESS     read-write
   STATUS     mandatory
   DESCRIPTION
     "This attribute specifies the time this interface waits for the 
      RESTART ACKNOWLEDGE message from the adjacent network 
      after sending a first RESTART message. Upon timer expiry, another 
      RESTART message is sent. After the second expiry, the interface is 
      treated as idle. 
      
      If the restartReqTimer attribute is set to the default value, then the 
      interface is treated as idle when it receives an indication that the 
      link is up and does not send a RESTART message."
   DEFVAL     { 0 }
::= { mscFrNniSigSysParmsEntry 4 }

mscFrNniSigRestartRcvTimer OBJECT-TYPE
   SYNTAX     Unsigned32 (1..255)
   ACCESS     read-write
   STATUS     mandatory
   DESCRIPTION
     "This attribute specifies the time this interface waits for the 
      processing of a RESTART message received by the interface. Upon 
      expiry of this timer, an alarm will be displayed to report the 
      problem. The timer value must be less than the restartReqTimer 
      provisioned value at the adjacent node."
   DEFVAL     { 110 }
::= { mscFrNniSigSysParmsEntry 5 }

mscFrNniSigStatusEnqTimer OBJECT-TYPE
   SYNTAX     Unsigned32 (1..255)
   ACCESS     read-write
   STATUS     mandatory
   DESCRIPTION
     "This attribute specifies the time the network waits for the requested 
      STATUS message from the adjacent network. Upon expiry of this 
      timer, another STATUS ENQUIRY message will be sent."
   DEFVAL     { 4 }
::= { mscFrNniSigSysParmsEntry 6 }

mscFrNniSigNetworkType OBJECT-TYPE
   SYNTAX     INTEGER  {
                 private(1),
                 public(2) }
   ACCESS     read-write
   STATUS     mandatory
   DESCRIPTION
     "This attribute specifies whether this Frame Relay service is running 
      on a public or a private network. This value is used solely in 
      populating applicable information elements within those signaling 
      messages that require a public or private network indication."
   DEFVAL     { private }
::= { mscFrNniSigSysParmsEntry 7 }

mscFrNniSigLapfSysTable OBJECT-TYPE
   SYNTAX     SEQUENCE OF MscFrNniSigLapfSysEntry
   ACCESS     not-accessible
   STATUS     mandatory
   DESCRIPTION
     "This group contains the provisionable attributes for the SVC data 
      link layer. The data link layer is governed primarily through ITU 
      specification Q.922, and operates over DLCI 0."
::= { mscFrNniSig 14 }

mscFrNniSigLapfSysEntry OBJECT-TYPE
   SYNTAX     MscFrNniSigLapfSysEntry
   ACCESS     not-accessible
   STATUS     mandatory
   DESCRIPTION
     "An entry in the mscFrNniSigLapfSysTable."
   INDEX {
      mscFrNniIndex,
      mscFrNniSigIndex }
::= { mscFrNniSigLapfSysTable 1 }

MscFrNniSigLapfSysEntry ::= SEQUENCE {
   mscFrNniSigWindowSize
      Unsigned32,
   mscFrNniSigRetransmitLimit
      Unsigned32,
   mscFrNniSigAckTimer
      Unsigned32,
   mscFrNniSigAckDelayTimer
      Unsigned32,
   mscFrNniSigIdleProbeTimer
      Unsigned32 }

mscFrNniSigWindowSize OBJECT-TYPE
   SYNTAX     Unsigned32 (1..127)
   ACCESS     read-write
   STATUS     mandatory
   DESCRIPTION
     "This attribute specifies the window size. This is the maximum 
      number of unacknowledged sequenced frames that may be 
      outstanding from or to this interface at any one time."
   DEFVAL     { 7 }
::= { mscFrNniSigLapfSysEntry 2 }

mscFrNniSigRetransmitLimit OBJECT-TYPE
   SYNTAX     Unsigned32 (0..20)
   ACCESS     read-write
   STATUS     mandatory
   DESCRIPTION
     "This attribute specifies the number of times a frame can be 
      retransmitted by the SVC data link layer before appropriate 
      recovery action is taken."
   DEFVAL     { 3 }
::= { mscFrNniSigLapfSysEntry 3 }

mscFrNniSigAckTimer OBJECT-TYPE
   SYNTAX     Unsigned32 (1000..10000)
   ACCESS     read-write
   STATUS     mandatory
   DESCRIPTION
     "This attribute specifies how long the layer 2 protocol waits for an 
      acknowledgment to a sent frame. The value set for ackTimer must 
      be less than the value set for idleProbeTimer."
   DEFVAL     { 1500 }
::= { mscFrNniSigLapfSysEntry 4 }

mscFrNniSigAckDelayTimer OBJECT-TYPE
   SYNTAX     Unsigned32 (0..10000)
   ACCESS     read-write
   STATUS     mandatory
   DESCRIPTION
     "This attribute specifies how long the network waits before sending 
      an acknowledgment for a received in-sequence I-frame. A value of 
      0 means that every frame is acknowledged and there will be no 
      delay in acknowledgment. A non-zero value means that one 
      acknowledgement is sent for a number of frames."
   DEFVAL     { 0 }
::= { mscFrNniSigLapfSysEntry 5 }

mscFrNniSigIdleProbeTimer OBJECT-TYPE
   SYNTAX     Unsigned32 (1000..65535000)
   ACCESS     read-write
   STATUS     mandatory
   DESCRIPTION
     "This attribute specifies how long the link is permitted to remain idle 
      (that is, no frames are exchanged on the data link). Upon expiry of 
      this timer, the network side's link layer polls its peer for status. The 
      value set for idleProbeTimer must be greater than the value set for 
      ackTimer."
   DEFVAL     { 30000 }
::= { mscFrNniSigLapfSysEntry 6 }

mscFrNniSigCodesTable OBJECT-TYPE
   SYNTAX     SEQUENCE OF MscFrNniSigCodesEntry
   ACCESS     not-accessible
   STATUS     mandatory
   DESCRIPTION
     "This group contains the remote data network address, the last SVC 
      clear cause and the last SVC diagnostic code coming from the 
      subnet or the local VC."
::= { mscFrNniSig 15 }

mscFrNniSigCodesEntry OBJECT-TYPE
   SYNTAX     MscFrNniSigCodesEntry
   ACCESS     not-accessible
   STATUS     mandatory
   DESCRIPTION
     "An entry in the mscFrNniSigCodesTable."
   INDEX {
      mscFrNniIndex,
      mscFrNniSigIndex }
::= { mscFrNniSigCodesTable 1 }

MscFrNniSigCodesEntry ::= SEQUENCE {
   mscFrNniSigLastClearRemoteDataNetworkAddress
      DigitString,
   mscFrNniSigLastClearCause
      Unsigned32,
   mscFrNniSigLastDiagnosticCode
      Unsigned32 }

mscFrNniSigLastClearRemoteDataNetworkAddress OBJECT-TYPE
   SYNTAX     DigitString (SIZE (0..15))
   ACCESS     read-only
   STATUS     mandatory
   DESCRIPTION
     "This attribute indicates the Data Network Address (DNA) of the
      remote (the other end of the SVC connection) of the call which 
      cleared last and whose clear and diagnostic codes were recorded."
::= { mscFrNniSigCodesEntry 1 }

mscFrNniSigLastClearCause OBJECT-TYPE
   SYNTAX     Unsigned32 (0..255)
   ACCESS     read-only
   STATUS     mandatory
   DESCRIPTION
     "This attribute indicates the last SVC clear cause signalled at the end 
      of the connection or failure to connect. It is updated only if the clear 
      request comes from the subnet or the call is rejected locally by the 
      VC. The same set of possible values provides the clear cause field 
      in the accounting record."
   DEFVAL     { 0 }
::= { mscFrNniSigCodesEntry 2 }

mscFrNniSigLastDiagnosticCode OBJECT-TYPE
   SYNTAX     Unsigned32 (0..255)
   ACCESS     read-only
   STATUS     mandatory
   DESCRIPTION
     "This attribute indicates the last SVC diagnostic code signalled at the 
      end of the connection or failure to connect. It is updated if the clear 
      request comes from the subnet or the call is rejected locally by the 
      VC. The same set of possible values provides the diagnostic code 
      field in the accounting record."
   DEFVAL     { 0 }
::= { mscFrNniSigCodesEntry 3 }

mscFrNniSigStateTable OBJECT-TYPE
   SYNTAX     SEQUENCE OF MscFrNniSigStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscFrNniSig 16 }

mscFrNniSigStateEntry OBJECT-TYPE
   SYNTAX     MscFrNniSigStateEntry
   ACCESS     not-accessible
   STATUS     mandatory
   DESCRIPTION
     "An entry in the mscFrNniSigStateTable."
   INDEX {
      mscFrNniIndex,
      mscFrNniSigIndex }
::= { mscFrNniSigStateTable 1 }

MscFrNniSigStateEntry ::= SEQUENCE {
   mscFrNniSigAdminState
      INTEGER,
   mscFrNniSigOperationalState
      INTEGER,
   mscFrNniSigUsageState
      INTEGER }

mscFrNniSigAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscFrNniSigStateEntry 1 }

mscFrNniSigOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscFrNniSigStateEntry 2 }

mscFrNniSigUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscFrNniSigStateEntry 3 }

mscFrNniSigStatsTable OBJECT-TYPE
   SYNTAX     SEQUENCE OF MscFrNniSigStatsEntry
   ACCESS     not-accessible
   STATUS     mandatory
   DESCRIPTION
     "This group contains the statistics related to the SVC signaling layer 
      at the interface level."
::= { mscFrNniSig 17 }

mscFrNniSigStatsEntry OBJECT-TYPE
   SYNTAX     MscFrNniSigStatsEntry
   ACCESS     not-accessible
   STATUS     mandatory
   DESCRIPTION
     "An entry in the mscFrNniSigStatsTable."
   INDEX {
      mscFrNniIndex,
      mscFrNniSigIndex }
::= { mscFrNniSigStatsTable 1 }

MscFrNniSigStatsEntry ::= SEQUENCE {
   mscFrNniSigCurrentNumberOfSvcCalls
      Gauge32,
   mscFrNniSigInCalls
      Gauge32,
   mscFrNniSigInCallsRefused
      Counter32,
   mscFrNniSigOutCalls
      Gauge32,
   mscFrNniSigOutCallsFailed
      Counter32,
   mscFrNniSigProtocolErrors
      Counter32,
   mscFrNniSigQualityOfServiceNotAvailable
      Counter32,
   mscFrNniSigSetupTimeout
      Counter32,
   mscFrNniSigLastCauseInStatusMsgReceived
      Unsigned32,
   mscFrNniSigLastStateInStatusMsgReceived
      INTEGER,
   mscFrNniSigLastDlciReceivedStatus
      Unsigned32,
   mscFrNniSigLastStateReceivedStatus
      INTEGER,
   mscFrNniSigDlciCollisions
      Counter32 }

mscFrNniSigCurrentNumberOfSvcCalls OBJECT-TYPE
   SYNTAX     Gauge32 (0..992)
   ACCESS     read-only
   STATUS     mandatory
   DESCRIPTION
     "This attribute indicates the number of Frame Relay SVCs currently 
      existing on this interface."
::= { mscFrNniSigStatsEntry 1 }

mscFrNniSigInCalls OBJECT-TYPE
   SYNTAX     Gauge32 (0..992)
   ACCESS     read-only
   STATUS     mandatory
   DESCRIPTION
     "This attribute indicates the current number of incoming SVCs on 
      this interface (that is, the number of SVCs for which this interface 
      represents the destination end of the call)."
::= { mscFrNniSigStatsEntry 2 }

mscFrNniSigInCallsRefused OBJECT-TYPE
   SYNTAX     Counter32 
   ACCESS     read-only
   STATUS     mandatory
   DESCRIPTION
     "This attribute counts the incoming SVC call requests that are 
      rejected by either this interface or by the called user. When this 
      count exceeds the maximum, it wraps to zero."
::= { mscFrNniSigStatsEntry 3 }

mscFrNniSigOutCalls OBJECT-TYPE
   SYNTAX     Gauge32 (0..992)
   ACCESS     read-only
   STATUS     mandatory
   DESCRIPTION
     "This attribute indicates the current number of outgoing SVCs on 
      this interface (that is, the number of SVCs for which this interface 
      represents the source end of the call)."
::= { mscFrNniSigStatsEntry 4 }

mscFrNniSigOutCallsFailed OBJECT-TYPE
   SYNTAX     Counter32 
   ACCESS     read-only
   STATUS     mandatory
   DESCRIPTION
     "This attribute counts the outgoing SVC call requests that are 
      rejected by either this interface, or by the network side of the 
      destination end, or by the called user. When this count exceeds the 
      maximum, it wraps to zero."
::= { mscFrNniSigStatsEntry 5 }

mscFrNniSigProtocolErrors OBJECT-TYPE
   SYNTAX     Counter32 
   ACCESS     read-only
   STATUS     mandatory
   DESCRIPTION
     "This attribute counts the number of times a FRF.10 protocol error 
      has occurred. Any one of the following events constitutes a protocol 
      error:
      1. In the user-signaled Link Layer Core Parameters IE within the
      SETUP or CONNECT messages, Cir, Bc and Be are all zero;
      2. In the user-signaled Link Layer Core Parameters IE within the
      SETUP or CONNECT messages, Cir is zero but Bc is 
      non-zero, or Bc is zero but Cir is non-zero;
      3. In the user-signaled Link Layer Core Parameters IE within the
      SETUP or CONNECT messages, the Minimum Acceptable CIR
      is greater than Cir;
      4. At the destination end, any of the destination to source direction 
      link layer core parameters has been increased in the 
      CONNECT message from the called user;
      5. At the destination end, the destination to source direction Cir
      in the CONNECT message is smaller than the corresponding 
      minimum acceptable Cir signaled to the called user;
      6. At the source end, any of the source to destination direction 
      link layer core parameters in the CONNECT message from the 
      destination end has been increased;
      7. At the source end, the source to destination direction Cir, after
      negotiation, is smaller than the corresponding minimum
      acceptable Cir;
      8. The network has received a STATUS message from the user
      with an incompatible FRF.10 state.	
      
      When this count reaches maximum, it wraps to zero."
::= { mscFrNniSigStatsEntry 6 }

mscFrNniSigQualityOfServiceNotAvailable OBJECT-TYPE
   SYNTAX     Counter32 
   ACCESS     read-only
   STATUS     mandatory
   DESCRIPTION
     "This attribute counts the number of incoming and outgoing SVCs 
      that are rejected because the quality of service requested cannot be 
      met by the network. When this count reaches maximum, it wraps to 
      zero."
::= { mscFrNniSigStatsEntry 7 }

mscFrNniSigSetupTimeout OBJECT-TYPE
   SYNTAX     Counter32 
   ACCESS     read-only
   STATUS     mandatory
   DESCRIPTION
     "This attribute counts the number of times the T303 setup timer has 
      expired. When this count reaches maximum, it wraps to zero."
::= { mscFrNniSigStatsEntry 8 }

mscFrNniSigLastCauseInStatusMsgReceived OBJECT-TYPE
   SYNTAX     Unsigned32 (0..255)
   ACCESS     read-only
   STATUS     mandatory
   DESCRIPTION
     "This attribute indicates the cause value in the last received user's 
      STATUS message to an existing call. The DLCI to which this 
      STATUS message applies is specified in the lastDlciReceivedStatus 
      attribute.
      
      The initial value of this attribute is 0 which means that no STATUS 
      message has been received for an existing call yet."
   DEFVAL     { 0 }
::= { mscFrNniSigStatsEntry 9 }

mscFrNniSigLastStateInStatusMsgReceived OBJECT-TYPE
   SYNTAX     INTEGER  {
                 null(0),
                 callInitiated(1),
                 n2(2),
                 outgoingCallProceeding(3),
                 n4(4),
                 n5(5),
                 callPresent(6),
                 n7(7),
                 n8(8),
                 incomingCallProceeding(9),
                 active(10),
                 releaseRequest(11),
                 releaseIndication(12),
                 n13(13),
                 n14(14),
                 n15(15),
                 n16(16),
                 n17(17),
                 n18(18),
                 n19(19),
                 notApplicable(20),
                 n21(21),
                 n22(22),
                 n23(23),
                 n24(24),
                 n25(25),
                 n26(26),
                 n27(27),
                 n28(28),
                 n29(29),
                 n30(30),
                 n31(31),
                 n32(32),
                 n33(33),
                 n34(34),
                 n35(35),
                 n36(36),
                 n37(37),
                 n38(38),
                 n39(39),
                 n40(40),
                 n41(41),
                 n42(42),
                 n43(43),
                 n44(44),
                 n45(45),
                 n46(46),
                 n47(47),
                 n48(48),
                 n49(49),
                 n50(50),
                 n51(51),
                 n52(52),
                 n53(53),
                 n54(54),
                 n55(55),
                 n56(56),
                 n57(57),
                 n58(58),
                 n59(59),
                 n60(60),
                 restartRequest(61),
                 restart(62),
                 n63(63) }
   ACCESS     read-only
   STATUS     mandatory
   DESCRIPTION
     "This attribute indicates the state value in the last received user's 
      STATUS message to an existing call. The DLCI to which this 
      STATUS message applies is specified in the lastDlciReceivedStatus 
      attribute.
      
      The initial value of this attribute is notApplicable."
   DEFVAL     { notApplicable }
::= { mscFrNniSigStatsEntry 10 }

mscFrNniSigLastDlciReceivedStatus OBJECT-TYPE
   SYNTAX     Unsigned32 (0 | 16..1007)
   ACCESS     read-only
   STATUS     mandatory
   DESCRIPTION
     "This attribute shows the value of the DLCI that has most recently 
      received a STATUS message from the user.
      
      The initial value of this attribute is 0."
   DEFVAL     { 0 }
::= { mscFrNniSigStatsEntry 11 }

mscFrNniSigLastStateReceivedStatus OBJECT-TYPE
   SYNTAX     INTEGER  {
                 null(0),
                 callInitiated(1),
                 outgoingCallProceeding(3),
                 callPresent(6),
                 incomingCallProceeding(9),
                 active(10),
                 releaseRequest(11),
                 releaseIndication(12),
                 notApplicable(20),
                 restartRequest(61),
                 restart(62) }
   ACCESS     read-only
   STATUS     mandatory
   DESCRIPTION
     "This attribute shows the network FRF.10 state of the DLCI that has 
      most recently received a STATUS message from the user. The DLCI 
      to which this STATUS message applies is specified in the 
      lastDlciReceivedStatus attribute.
      
      The initial value of this attribute is notApplicable."
   DEFVAL     { notApplicable }
::= { mscFrNniSigStatsEntry 12 }

mscFrNniSigDlciCollisions OBJECT-TYPE
   SYNTAX     Counter32 
   ACCESS     read-only
   STATUS     mandatory
   DESCRIPTION
     "This attribute counts the number of call failures due to DLCI 
      collisions."
::= { mscFrNniSigStatsEntry 15 }

mscFrNniSigLapfStatusTable OBJECT-TYPE
   SYNTAX     SEQUENCE OF MscFrNniSigLapfStatusEntry
   ACCESS     not-accessible
   STATUS     mandatory
   DESCRIPTION
     "This group contains the Q.922 SVC data link layer status."
::= { mscFrNniSig 18 }

mscFrNniSigLapfStatusEntry OBJECT-TYPE
   SYNTAX     MscFrNniSigLapfStatusEntry
   ACCESS     not-accessible
   STATUS     mandatory
   DESCRIPTION
     "An entry in the mscFrNniSigLapfStatusTable."
   INDEX {
      mscFrNniIndex,
      mscFrNniSigIndex }
::= { mscFrNniSigLapfStatusTable 1 }

MscFrNniSigLapfStatusEntry ::= SEQUENCE {
   mscFrNniSigCurrentState
      INTEGER,
   mscFrNniSigLastStateChangeReason
      INTEGER,
   mscFrNniSigFrmrReceive
      HexString,
   mscFrNniSigCurrentQueueSize
      Counter32 }

mscFrNniSigCurrentState OBJECT-TYPE
   SYNTAX     INTEGER  {
                 disconnected(1),
                 linkSetup(2),
                 disconnectRequest(4),
                 informationTransfer(5),
                 waitingAck(7) }
   ACCESS     read-only
   STATUS     mandatory
   DESCRIPTION
     "This attribute shows the current state of the SVC data link layer 
      interface."
::= { mscFrNniSigLapfStatusEntry 1 }

mscFrNniSigLastStateChangeReason OBJECT-TYPE
   SYNTAX     INTEGER  {
                 notStarted(1),
                 abmeEntered(3),
                 abmeReset(5),
                 dmReceived(6),
                 dmSent(7),
                 discReceived(8),
                 discSent(9),
                 frmrReceived(10),
                 n200RetranTimeOut(12),
                 other(13) }
   ACCESS     read-only
   STATUS     mandatory
   DESCRIPTION
     "This attribute shows the reason for the most recent state change.
      notStarted - this is the default state after SVC data link has just 
      been created.
      
      abmeEntered - SVC data link has entered Asynchronous Balanced 
      Mode after SABME or UA has been received.
      abmeReset - the data link has been reset.
      dmReceived - DM response received.
      dmSent - DM sent.
      discReceived - DISC response received.
      discSent - DISC sent.
      frmrReceived - FRMR received.
      n200RetranTimeOut - retransmitLimit has been exceeded.
      other - unspecified state change reasons. The most likely reason for 
      this is the transition from state waitingAck to state 
      informationTransfer."
   DEFVAL     { notStarted }
::= { mscFrNniSigLapfStatusEntry 2 }

mscFrNniSigFrmrReceive OBJECT-TYPE
   SYNTAX     HexString (SIZE (0..8))
   ACCESS     read-only
   STATUS     mandatory
   DESCRIPTION
     "This attribute shows the information field of the Frame Reject 
      (FRMR) most recently received."
::= { mscFrNniSigLapfStatusEntry 3 }

mscFrNniSigCurrentQueueSize OBJECT-TYPE
   SYNTAX     Counter32 
   ACCESS     read-only
   STATUS     mandatory
   DESCRIPTION
     "This attribute shows the current number of frames in the SVC data 
      link layer transmit queue."
::= { mscFrNniSigLapfStatusEntry 4 }

mscFrNniSigLapfStatsTable OBJECT-TYPE
   SYNTAX     SEQUENCE OF MscFrNniSigLapfStatsEntry
   ACCESS     not-accessible
   STATUS     mandatory
   DESCRIPTION
     "This group contains the statistics for the SVC data link layer."
::= { mscFrNniSig 19 }

mscFrNniSigLapfStatsEntry OBJECT-TYPE
   SYNTAX     MscFrNniSigLapfStatsEntry
   ACCESS     not-accessible
   STATUS     mandatory
   DESCRIPTION
     "An entry in the mscFrNniSigLapfStatsTable."
   INDEX {
      mscFrNniIndex,
      mscFrNniSigIndex }
::= { mscFrNniSigLapfStatsTable 1 }

MscFrNniSigLapfStatsEntry ::= SEQUENCE {
   mscFrNniSigRemoteBusy
      Counter32,
   mscFrNniSigReceiveRejectFrame
      Counter32,
   mscFrNniSigAckTimeout
      Counter32,
   mscFrNniSigIFramesTransmitted
      Counter32,
   mscFrNniSigIFramesTxDiscarded
      Counter32,
   mscFrNniSigIFramesReceived
      Counter32,
   mscFrNniSigIFramesRcvdDiscarded
      Counter32,
   mscFrNniSigStateChange
      Counter32 }

mscFrNniSigRemoteBusy OBJECT-TYPE
   SYNTAX     Counter32 
   ACCESS     read-only
   STATUS     mandatory
   DESCRIPTION
     "This attribute counts the number of times transmission of an I-frame 
      was unsuccessful due to a perceived remote busy condition 
      (window closed or remote busy). When this count reaches 
      maximum, it wraps to zero."
::= { mscFrNniSigLapfStatsEntry 2 }

mscFrNniSigReceiveRejectFrame OBJECT-TYPE
   SYNTAX     Counter32 
   ACCESS     read-only
   STATUS     mandatory
   DESCRIPTION
     "This attribute counts the number of REJ frames received by the 
      interface. When this count reaches maximum, it wraps to zero."
::= { mscFrNniSigLapfStatsEntry 3 }

mscFrNniSigAckTimeout OBJECT-TYPE
   SYNTAX     Counter32 
   ACCESS     read-only
   STATUS     mandatory
   DESCRIPTION
     "This attribute counts the number of times the ackTimer has expired. 
      Frequent increments of this counter indicate a problem at the link or 
      improper values have been chosen for ackTimer and ackDelayTimer 
      between the local and remote sides. When this count reaches 
      maximum, it wraps to zero."
::= { mscFrNniSigLapfStatsEntry 4 }

mscFrNniSigIFramesTransmitted OBJECT-TYPE
   SYNTAX     Counter32 
   ACCESS     read-only
   STATUS     mandatory
   DESCRIPTION
     "This attribute counts the number of SVC I-frames transmitted to the 
      interface on DLCI 0. An I-frame may be counted more than once if 
      there are retransmissions at the SVC data link layer. When this 
      count reaches maximum, it wraps to zero."
::= { mscFrNniSigLapfStatsEntry 5 }

mscFrNniSigIFramesTxDiscarded OBJECT-TYPE
   SYNTAX     Counter32 
   ACCESS     read-only
   STATUS     mandatory
   DESCRIPTION
     "This attribute counts the number of SVC I-frames that are bound for 
      the link but have been discarded. Discard reasons may be one of the 
      following:
      1.	 the frame length is beyond the allowed limit.
      2.	 the SVC data link layer is in disconnected state.
      3. 	the transmit queue has been purged because the queue length 
      has reached the reset threshold.
      4. 	the transmit queue or the queue waiting for acknowledgment
      has been 			purged because the link cannot be re-established.
      
      When this count reaches maximum, it wraps to zero."
::= { mscFrNniSigLapfStatsEntry 6 }

mscFrNniSigIFramesReceived OBJECT-TYPE
   SYNTAX     Counter32 
   ACCESS     read-only
   STATUS     mandatory
   DESCRIPTION
     "This attribute counts the number of SVC I-frames received from the 
      interface. When this count reaches maximum, it wraps to zero."
::= { mscFrNniSigLapfStatsEntry 7 }

mscFrNniSigIFramesRcvdDiscarded OBJECT-TYPE
   SYNTAX     Counter32 
   ACCESS     read-only
   STATUS     mandatory
   DESCRIPTION
     "This attribute counts the number of SVC I-frames received but have 
      been discarded. The discard reasons are:
      1.	 incorrect frame size
      2. frame is out of sequence
      3. frame received while the network side of the SVC data link
      layer is not in the informationTransfer or waitingAck state.
      
      When this count reaches maximum, it wraps to zero."
::= { mscFrNniSigLapfStatsEntry 8 }

mscFrNniSigStateChange OBJECT-TYPE
   SYNTAX     Counter32 
   ACCESS     read-only
   STATUS     mandatory
   DESCRIPTION
     "This attribute counts the number of times the SVC data link layer 
      interface has changed state. While the data link layer is in 
      informationTransfer state, this counter will increment on each 
      expiry of idleProbeTimer as its state goes from 
      informationTransfer to waitingAck and back. When this count 
      exceeds the maximum, it wraps to zero."
::= { mscFrNniSigLapfStatsEntry 8650 }

mscFrNniSigSvcaccTable OBJECT-TYPE
   SYNTAX     SEQUENCE OF MscFrNniSigSvcaccEntry
   ACCESS     not-accessible
   STATUS     mandatory
   DESCRIPTION
     "This group contains the provisionable attribute which controls 
      accounting for this interface."
::= { mscFrNniSig 20 }

mscFrNniSigSvcaccEntry OBJECT-TYPE
   SYNTAX     MscFrNniSigSvcaccEntry
   ACCESS     not-accessible
   STATUS     mandatory
   DESCRIPTION
     "An entry in the mscFrNniSigSvcaccTable."
   INDEX {
      mscFrNniIndex,
      mscFrNniSigIndex }
::= { mscFrNniSigSvcaccTable 1 }

MscFrNniSigSvcaccEntry ::= SEQUENCE {
   mscFrNniSigDefaultAccounting
      INTEGER }

mscFrNniSigDefaultAccounting OBJECT-TYPE
   SYNTAX     INTEGER  {
                 off(0),
                 on(1) }
   ACCESS     read-write
   STATUS     mandatory
   DESCRIPTION
     "This attribute specifies whether accounting data collection and 
      record generation is turned on for switched connections at this 
      interface. For accounting data collection and record generation to 
      occur, this attribute must be on and at least one of the 
      accountCollection reasons in the Dna component must be present."
   DEFVAL     { on }
::= { mscFrNniSigSvcaccEntry 1 }

mscFrNniSigBandwidthNotAvailableTable OBJECT-TYPE
   SYNTAX     SEQUENCE OF MscFrNniSigBandwidthNotAvailableEntry
   ACCESS     not-accessible
   STATUS     mandatory
   DESCRIPTION
     "This attribute counts the number of call failures for each bandwidth 
      pool due to the requested bandwidth not being available."
::= { mscFrNniSig 672 }

mscFrNniSigBandwidthNotAvailableEntry OBJECT-TYPE
   SYNTAX     MscFrNniSigBandwidthNotAvailableEntry
   ACCESS     not-accessible
   STATUS     mandatory
   DESCRIPTION
     "An entry in the mscFrNniSigBandwidthNotAvailableTable."
   INDEX {
      mscFrNniIndex,
      mscFrNniSigIndex,
      mscFrNniSigBandwidthNotAvailableIndex }
::= { mscFrNniSigBandwidthNotAvailableTable 1 }

MscFrNniSigBandwidthNotAvailableEntry ::= SEQUENCE {
   mscFrNniSigBandwidthNotAvailableIndex
      Integer32,
   mscFrNniSigBandwidthNotAvailableValue
      Counter32 }

mscFrNniSigBandwidthNotAvailableIndex OBJECT-TYPE
   SYNTAX     Integer32 (0..15)
   ACCESS     not-accessible
   STATUS     mandatory
   DESCRIPTION
     "This variable represents the mscFrNniSigBandwidthNotAvailableTable
      specific index for the mscFrNniSigBandwidthNotAvailableTable."
::= { mscFrNniSigBandwidthNotAvailableEntry 1 }

mscFrNniSigBandwidthNotAvailableValue OBJECT-TYPE
   SYNTAX     Counter32 
   ACCESS     read-only
   STATUS     mandatory
   DESCRIPTION
     "This variable represents an individual value for the
      mscFrNniSigBandwidthNotAvailableTable."
::= { mscFrNniSigBandwidthNotAvailableEntry 2 }


-- FrUni/n LoadTestSystem
-- FrNni/n LoadTestSystem
-- This component defines an instance of the Frame Relay Load Test 
-- System (UNI) service. The component instance value n is a unique 
-- positive integer within a module.

mscFrNniLts OBJECT IDENTIFIER ::= { mscFrNni 9 }



mscFrNniLtsRowStatusTable OBJECT-TYPE
   SYNTAX     SEQUENCE OF MscFrNniLtsRowStatusEntry
   ACCESS     not-accessible
   STATUS     mandatory
   DESCRIPTION
     "This entry controls the addition and deletion of 
      mscFrNniLts components."
::= { mscFrNniLts 1 }

mscFrNniLtsRowStatusEntry OBJECT-TYPE
   SYNTAX     MscFrNniLtsRowStatusEntry
   ACCESS     not-accessible
   STATUS     mandatory
   DESCRIPTION
     "A single entry in the table represents a single 
      mscFrNniLts component."
   INDEX {
      mscFrNniIndex,
      mscFrNniLtsIndex }
::= { mscFrNniLtsRowStatusTable 1 }

MscFrNniLtsRowStatusEntry ::= SEQUENCE {
   mscFrNniLtsRowStatus
      RowStatus,
   mscFrNniLtsComponentName
      DisplayString,
   mscFrNniLtsStorageType
      StorageType,
   mscFrNniLtsIndex
      NonReplicated }

mscFrNniLtsRowStatus OBJECT-TYPE
   SYNTAX     RowStatus 
   ACCESS     read-write
   STATUS     mandatory
   DESCRIPTION
     "This variable is used as the basis for SNMP naming of
      mscFrNniLts components.
      These components can be added and deleted."
::= { mscFrNniLtsRowStatusEntry 1 }

mscFrNniLtsComponentName OBJECT-TYPE
   SYNTAX     DisplayString 
   ACCESS     read-only
   STATUS     mandatory
   DESCRIPTION
     "This variable provides the component's string name for
      use with the ASCII Console Interface"
::= { mscFrNniLtsRowStatusEntry 2 }

mscFrNniLtsStorageType OBJECT-TYPE
   SYNTAX     StorageType 
   ACCESS     read-only
   STATUS     mandatory
   DESCRIPTION
     "This variable represents the storage type value for the
      mscFrNniLts tables."
::= { mscFrNniLtsRowStatusEntry 4 }

mscFrNniLtsIndex OBJECT-TYPE
   SYNTAX     NonReplicated 
   ACCESS     not-accessible
   STATUS     mandatory
   DESCRIPTION
     "This variable represents the index for the mscFrNniLts tables."
::= { mscFrNniLtsRowStatusEntry 10 }

mscFrNniLtsSetupTable OBJECT-TYPE
   SYNTAX     SEQUENCE OF MscFrNniLtsSetupEntry
   ACCESS     not-accessible
   STATUS     mandatory
   DESCRIPTION
     "This attribute group contains the parameters used to configure the 
      behavior of the Frame Relay Load Test System."
::= { mscFrNniLts 10 }

mscFrNniLtsSetupEntry OBJECT-TYPE
   SYNTAX     MscFrNniLtsSetupEntry
   ACCESS     not-accessible
   STATUS     mandatory
   DESCRIPTION
     "An entry in the mscFrNniLtsSetupTable."
   INDEX {
      mscFrNniIndex,
      mscFrNniLtsIndex }
::= { mscFrNniLtsSetupTable 1 }

MscFrNniLtsSetupEntry ::= SEQUENCE {
   mscFrNniLtsDuration
      Unsigned32,
   mscFrNniLtsAlgorithm
      INTEGER,
   mscFrNniLtsBurstSize
      Unsigned32,
   mscFrNniLtsTimeInterval
      Unsigned32 }

mscFrNniLtsDuration OBJECT-TYPE
   SYNTAX     Unsigned32 (0..4294967295)
   ACCESS     read-write
   STATUS     mandatory
   DESCRIPTION
     "This attribute specifies the duration of the test in milliseconds. The 
      test will run until the duration expires or the STOP command is 
      issued. A value of 0 is used to indicate infinity."
   DEFVAL     { 0 }
::= { mscFrNniLtsSetupEntry 200 }

mscFrNniLtsAlgorithm OBJECT-TYPE
   SYNTAX     INTEGER  {
                 continousBurst(0),
                 intervalBurst(1),
                 delayBurst(2),
                 fixedBurst(3) }
   ACCESS     read-write
   STATUS     mandatory
   DESCRIPTION
     "This attribute specifies which algorithm is used to generate the 
      frames.
      
      ContinuousBurst
      This mode of traffic generation creates traffic at the maximum rate 
      possible until all of the frames have been sent. The generator then 
      waits until the end of the timeInterval to begin again.
      
      IntervalBurst
      This algorithm attempts to generate 10 ms bursts of burstSize 
      frames. It will generate as many of the burstSize frames as it can per 
      sub-interval.
      
      DelayedBurst
      This algorithm generates bursts of burstSize frames separated by 10 
      ms delays.
      
      FixedBurst
      This aglorithm is similar to IntervalBurst, except a fixed burst size 
      of 12 frames is used.
      
      delayMeasurement
      This algorithm is used to measure delay. The specified number of 
      frames in the indicated pattern are generated, one at a time, with a 
      maximum wait of maxDelay before sending the next frame.
      This algorithm is not implemented yet."
   DEFVAL     { continousBurst }
::= { mscFrNniLtsSetupEntry 201 }

mscFrNniLtsBurstSize OBJECT-TYPE
   SYNTAX     Unsigned32 (1..250)
   ACCESS     read-write
   STATUS     mandatory
   DESCRIPTION
     "This attribute specifies the number of frames per burst under the 
      delayedBurst and intervalBurst algorithms."
   DEFVAL     { 50 }
::= { mscFrNniLtsSetupEntry 204 }

mscFrNniLtsTimeInterval OBJECT-TYPE
   SYNTAX     Unsigned32 (1..60000)
   ACCESS     read-write
   STATUS     mandatory
   DESCRIPTION
     "This attribute specifies the time interval to the specified number of 
      seconds. Granuality is in centiseconds. Maximum is 1 minute."
   DEFVAL     { 100 }
::= { mscFrNniLtsSetupEntry 205 }

mscFrNniLtsStateTable OBJECT-TYPE
   SYNTAX     SEQUENCE OF MscFrNniLtsStateEntry
   ACCESS     not-accessible
   STATUS     mandatory
   DESCRIPTION
     "This group contains the operation statistics of the load generator."
::= { mscFrNniLts 11 }

mscFrNniLtsStateEntry OBJECT-TYPE
   SYNTAX     MscFrNniLtsStateEntry
   ACCESS     not-accessible
   STATUS     mandatory
   DESCRIPTION
     "An entry in the mscFrNniLtsStateTable."
   INDEX {
      mscFrNniIndex,
      mscFrNniLtsIndex }
::= { mscFrNniLtsStateTable 1 }

MscFrNniLtsStateEntry ::= SEQUENCE {
   mscFrNniLtsGeneratorState
      INTEGER,
   mscFrNniLtsCycleIncomplete
      INTEGER,
   mscFrNniLtsLastActiveInterval
      Unsigned32,
   mscFrNniLtsLoad
      FixedPoint3,
   mscFrNniLtsElapsedGenerationTime
      Unsigned32 }

mscFrNniLtsGeneratorState OBJECT-TYPE
   SYNTAX     INTEGER  {
                 stopped(0),
                 running(1) }
   ACCESS     read-only
   STATUS     mandatory
   DESCRIPTION
     "This attribute indicates whether the Lts is generating traffic."
   DEFVAL     { stopped }
::= { mscFrNniLtsStateEntry 200 }

mscFrNniLtsCycleIncomplete OBJECT-TYPE
   SYNTAX     INTEGER  {
                 false(0),
                 true(1) }
   ACCESS     read-only
   STATUS     mandatory
   DESCRIPTION
     "This attribute indicates whether the time required to generate all of 
      the enabled patterns is more than timeInterval by a true value. 
      Otherwise, this flag is set to false. Default is True."
   DEFVAL     { true }
::= { mscFrNniLtsStateEntry 201 }

mscFrNniLtsLastActiveInterval OBJECT-TYPE
   SYNTAX     Unsigned32 (0..4294967295)
   ACCESS     read-only
   STATUS     mandatory
   DESCRIPTION
     "This attribute indicates the actual time it took to generate all of the 
      enabled patterns in the last cycle. If cycleIncomplete is true, this 
      value should be zero."
::= { mscFrNniLtsStateEntry 202 }

mscFrNniLtsLoad OBJECT-TYPE
   SYNTAX     FixedPoint3 (0..4294967295)
   ACCESS     read-only
   STATUS     mandatory
   DESCRIPTION
     "This attribute indicates the load being generated. This value 
      represents that calculated using the set number of ticks. The actual 
      burstTimeInterval may differ. One entire cycle of the patterns is 
      completed in activeInterval and thus most of the load may be 
      concentrated early in the set interval."
::= { mscFrNniLtsStateEntry 204 }

mscFrNniLtsElapsedGenerationTime OBJECT-TYPE
   SYNTAX     Unsigned32 (0..4294967295)
   ACCESS     read-only
   STATUS     mandatory
   DESCRIPTION
     "This attribute indicates how many milliseconds have elapsed since 
      the start of this test."
::= { mscFrNniLtsStateEntry 205 }

mscFrNniLtsResultsTable OBJECT-TYPE
   SYNTAX     SEQUENCE OF MscFrNniLtsResultsEntry
   ACCESS     not-accessible
   STATUS     mandatory
   DESCRIPTION
     "This group contains the frame counting attributes for the LTS 
      component."
::= { mscFrNniLts 12 }

mscFrNniLtsResultsEntry OBJECT-TYPE
   SYNTAX     MscFrNniLtsResultsEntry
   ACCESS     not-accessible
   STATUS     mandatory
   DESCRIPTION
     "An entry in the mscFrNniLtsResultsTable."
   INDEX {
      mscFrNniIndex,
      mscFrNniLtsIndex }
::= { mscFrNniLtsResultsTable 1 }

MscFrNniLtsResultsEntry ::= SEQUENCE {
   mscFrNniLtsFramesTx
      Counter32,
   mscFrNniLtsBytesTx
      Unsigned32,
   mscFrNniLtsBitRateTx
      FixedPoint3,
   mscFrNniLtsFrameRateTx
      Unsigned32 }

mscFrNniLtsFramesTx OBJECT-TYPE
   SYNTAX     Counter32 
   ACCESS     read-only
   STATUS     mandatory
   DESCRIPTION
     "This attribute specifies the number of frames send to the network 
      since the last time these statistics were cleared. This is similar to the 
      framesToIf attribute of the FRAMER component."
::= { mscFrNniLtsResultsEntry 200 }

mscFrNniLtsBytesTx OBJECT-TYPE
   SYNTAX     Unsigned32 (0..4294967295)
   ACCESS     read-only
   STATUS     mandatory
   DESCRIPTION
     "This attribute indicates the number of bytes sent."
   DEFVAL     { 0 }
::= { mscFrNniLtsResultsEntry 204 }

mscFrNniLtsBitRateTx OBJECT-TYPE
   SYNTAX     FixedPoint3 (0..4294967295)
   ACCESS     read-only
   STATUS     mandatory
   DESCRIPTION
     "This attribute indicates the bit rate being sent to the link. It should 
      only differ from the load if the burstTimeInterval would be >= the 
      timeInterval or burstSize frames cannot be generated in 10ms 
      (intervalBurst algorithm)."
   DEFVAL     { 0 }
::= { mscFrNniLtsResultsEntry 208 }

mscFrNniLtsFrameRateTx OBJECT-TYPE
   SYNTAX     Unsigned32 (0..4294967295)
   ACCESS     read-only
   STATUS     mandatory
   DESCRIPTION
     "This attribute indicates the frame rate being sent to the link. It is 
      calculated using the number of frames sent to the link in one cycle 
      of the patterns."
   DEFVAL     { 0 }
::= { mscFrNniLtsResultsEntry 209 }


-- FrUni/n Lts Pattern
-- FrNni/n Lts Pattern
-- Each instance of this component specifies a pattern to be generated 
-- as part of each cycle.  One cycle represents one pass through each 
-- pattern.

mscFrNniLtsPat OBJECT IDENTIFIER ::= { mscFrNniLts 2 }



mscFrNniLtsPatRowStatusTable OBJECT-TYPE
   SYNTAX     SEQUENCE OF MscFrNniLtsPatRowStatusEntry
   ACCESS     not-accessible
   STATUS     mandatory
   DESCRIPTION
     "This entry controls the addition and deletion of 
      mscFrNniLtsPat components."
::= { mscFrNniLtsPat 1 }

mscFrNniLtsPatRowStatusEntry OBJECT-TYPE
   SYNTAX     MscFrNniLtsPatRowStatusEntry
   ACCESS     not-accessible
   STATUS     mandatory
   DESCRIPTION
     "A single entry in the table represents a single 
      mscFrNniLtsPat component."
   INDEX {
      mscFrNniIndex,
      mscFrNniLtsIndex,
      mscFrNniLtsPatIndex }
::= { mscFrNniLtsPatRowStatusTable 1 }

MscFrNniLtsPatRowStatusEntry ::= SEQUENCE {
   mscFrNniLtsPatRowStatus
      RowStatus,
   mscFrNniLtsPatComponentName
      DisplayString,
   mscFrNniLtsPatStorageType
      StorageType,
   mscFrNniLtsPatIndex
      Integer32 }

mscFrNniLtsPatRowStatus OBJECT-TYPE
   SYNTAX     RowStatus 
   ACCESS     read-write
   STATUS     mandatory
   DESCRIPTION
     "This variable is used as the basis for SNMP naming of
      mscFrNniLtsPat components.
      These components can be added and deleted."
::= { mscFrNniLtsPatRowStatusEntry 1 }

mscFrNniLtsPatComponentName OBJECT-TYPE
   SYNTAX     DisplayString 
   ACCESS     read-only
   STATUS     mandatory
   DESCRIPTION
     "This variable provides the component's string name for
      use with the ASCII Console Interface"
::= { mscFrNniLtsPatRowStatusEntry 2 }

mscFrNniLtsPatStorageType OBJECT-TYPE
   SYNTAX     StorageType 
   ACCESS     read-only
   STATUS     mandatory
   DESCRIPTION
     "This variable represents the storage type value for the
      mscFrNniLtsPat tables."
::= { mscFrNniLtsPatRowStatusEntry 4 }

mscFrNniLtsPatIndex OBJECT-TYPE
   SYNTAX     Integer32 (0..29)
   ACCESS     not-accessible
   STATUS     mandatory
   DESCRIPTION
     "This variable represents the index for the mscFrNniLtsPat tables."
::= { mscFrNniLtsPatRowStatusEntry 10 }

mscFrNniLtsPatDefaultsTable OBJECT-TYPE
   SYNTAX     SEQUENCE OF MscFrNniLtsPatDefaultsEntry
   ACCESS     not-accessible
   STATUS     mandatory
   DESCRIPTION
     "This attribute group contains the specifications of the pattern."
::= { mscFrNniLtsPat 10 }

mscFrNniLtsPatDefaultsEntry OBJECT-TYPE
   SYNTAX     MscFrNniLtsPatDefaultsEntry
   ACCESS     not-accessible
   STATUS     mandatory
   DESCRIPTION
     "An entry in the mscFrNniLtsPatDefaultsTable."
   INDEX {
      mscFrNniIndex,
      mscFrNniLtsIndex,
      mscFrNniLtsPatIndex }
::= { mscFrNniLtsPatDefaultsTable 1 }

MscFrNniLtsPatDefaultsEntry ::= SEQUENCE {
   mscFrNniLtsPatDefaultDlci
      Unsigned32,
   mscFrNniLtsPatDefaultNumFrames
      Unsigned32,
   mscFrNniLtsPatDefaultDataSize
      Unsigned32,
   mscFrNniLtsPatDefaultHeaderBits
      OCTET STRING,
   mscFrNniLtsPatDefaultHeaderLength
      Unsigned32,
   mscFrNniLtsPatDefaultEABits
      Hex,
   mscFrNniLtsPatDefaultPayloadPattern
      HexString,
   mscFrNniLtsPatDefaultRfc1490Header
      INTEGER,
   mscFrNniLtsPatDefaultUseBadLrc
      INTEGER }

mscFrNniLtsPatDefaultDlci OBJECT-TYPE
   SYNTAX     Unsigned32 (16..1007)
   ACCESS     read-write
   STATUS     mandatory
   DESCRIPTION
     "This attribute specifies for which dlci (on the local end) the frames 
      are destined."
   DEFVAL     { 16 }
::= { mscFrNniLtsPatDefaultsEntry 200 }

mscFrNniLtsPatDefaultNumFrames OBJECT-TYPE
   SYNTAX     Unsigned32 (0..4294967295)
   ACCESS     read-write
   STATUS     mandatory
   DESCRIPTION
     "This attribute specifies the number of frames in this pattern.  This is 
      the number of frames of this type which will be generated in one 
      timeInterval."
   DEFVAL     { 100 }
::= { mscFrNniLtsPatDefaultsEntry 201 }

mscFrNniLtsPatDefaultDataSize OBJECT-TYPE
   SYNTAX     Unsigned32 (0..8200)
   ACCESS     read-write
   STATUS     mandatory
   DESCRIPTION
     "This attribute specifies the payload size of each frame in bytes.  
      This is in excess to the header."
   DEFVAL     { 512 }
::= { mscFrNniLtsPatDefaultsEntry 202 }

mscFrNniLtsPatDefaultHeaderBits OBJECT-TYPE
   SYNTAX     OCTET STRING (SIZE (1))
   ACCESS     read-write
   STATUS     mandatory
   DESCRIPTION
     "This attribute specifies whether the following bits are on/off in the 
      header of each frame. The following bits can be set:
      BeCn, C/R, De, FeCn

      Description of bits:
      becn(0)
      fecn(1)
      cr(2)
      de(3)"
::= { mscFrNniLtsPatDefaultsEntry 203 }

mscFrNniLtsPatDefaultHeaderLength OBJECT-TYPE
   SYNTAX     Unsigned32 (0 | 2..4)
   ACCESS     read-write
   STATUS     mandatory
   DESCRIPTION
     "This attribute specifies the size of the frame relay header in bytes.  
      Passport currently only supports a 2-byte header."
   DEFVAL     { 2 }
::= { mscFrNniLtsPatDefaultsEntry 204 }

mscFrNniLtsPatDefaultEABits OBJECT-TYPE
   SYNTAX     Hex (0..15)
   ACCESS     read-write
   STATUS     mandatory
   DESCRIPTION
     "This attribute specifies how the address field extension bits are set in 
      the frame header.  Consider the value to be a four bit binary number.  
      For example, 4 = 0100.  Only the first headerLength bits are used. 
      For instance, suppose headerLength is 3, then the appropriate 
      EABits is 2, or 0010.  This attribute can be used to create a header 
      of length greater than two bytes or to specify incorrect EABits in 
      the header."
   DEFVAL     { 4 }
::= { mscFrNniLtsPatDefaultsEntry 205 }

mscFrNniLtsPatDefaultPayloadPattern OBJECT-TYPE
   SYNTAX     HexString (SIZE (1..12))
   ACCESS     read-write
   STATUS     mandatory
   DESCRIPTION
     "This attribute specifies the payload of each frame.  The value 
      specified is in hexadecimal, where every two digits represent a byte.  
      A maximum of 24 digits (12 bytes) may be set, after which the 
      pattern will repeat in the payload (depending on repeatPattern 
      attribute). 
      NOTE: If a RFC 1490 header is specified, via the 1490Header 
      attribute, the specified pattern will begin following the header (i.e. 
      at the 9th byte in the payload)."
   DEFVAL     { '55'H }  -- "55"
::= { mscFrNniLtsPatDefaultsEntry 206 }

mscFrNniLtsPatDefaultRfc1490Header OBJECT-TYPE
   SYNTAX     INTEGER  {
                 n0(0),
                 n1(1),
                 n2(2),
                 n3(3),
                 n4(4),
                 n5(5),
                 n6(6),
                 n7(7),
                 n8(8),
                 n9(9),
                 n10(10),
                 n11(11),
                 n12(12),
                 n13(13),
                 n14(14),
                 n15(15),
                 n16(16),
                 n17(17),
                 none(18) }
   ACCESS     read-write
   STATUS     mandatory
   DESCRIPTION
     "This attribute specifies the appropriate RFC 1490 encapsulated 
      header of the frame.  A value of 0 indicates no 1490 header.
      NOTE: This header resides in the first 8 bytes of the payload.  If the 
      specified value is non-zero, then the payload pattern provisioned 
      will begin at the 9th byte."
   DEFVAL     { none }
::= { mscFrNniLtsPatDefaultsEntry 207 }

mscFrNniLtsPatDefaultUseBadLrc OBJECT-TYPE
   SYNTAX     INTEGER  {
                 no(0),
                 yes(1) }
   ACCESS     read-write
   STATUS     mandatory
   DESCRIPTION
     "This attribute specifies whether the frames from this pattern are to 
      have a bad LRC prior to being sent to the framer.  The LRC is 
      checked while the frame is being put onto the link and the failure 
      should cause an abort frame to be sent."
   DEFVAL     { no }
::= { mscFrNniLtsPatDefaultsEntry 208 }

mscFrNniLtsPatSetupTable OBJECT-TYPE
   SYNTAX     SEQUENCE OF MscFrNniLtsPatSetupEntry
   ACCESS     not-accessible
   STATUS     mandatory
   DESCRIPTION
     "This attribute group contains the specifications of the pattern."
::= { mscFrNniLtsPat 11 }

mscFrNniLtsPatSetupEntry OBJECT-TYPE
   SYNTAX     MscFrNniLtsPatSetupEntry
   ACCESS     not-accessible
   STATUS     mandatory
   DESCRIPTION
     "An entry in the mscFrNniLtsPatSetupTable."
   INDEX {
      mscFrNniIndex,
      mscFrNniLtsIndex,
      mscFrNniLtsPatIndex }
::= { mscFrNniLtsPatSetupTable 1 }

MscFrNniLtsPatSetupEntry ::= SEQUENCE {
   mscFrNniLtsPatDlci
      Unsigned32,
   mscFrNniLtsPatNumFrames
      Unsigned32,
   mscFrNniLtsPatDataSize
      Unsigned32,
   mscFrNniLtsPatHeaderBits
      OCTET STRING,
   mscFrNniLtsPatHeaderLength
      Unsigned32,
   mscFrNniLtsPatEaBits
      Hex,
   mscFrNniLtsPatPayloadPattern
      HexString,
   mscFrNniLtsPatRfc1490Header
      INTEGER,
   mscFrNniLtsPatUseBadLrc
      INTEGER }

mscFrNniLtsPatDlci OBJECT-TYPE
   SYNTAX     Unsigned32 (16..1007)
   ACCESS     read-write
   STATUS     mandatory
   DESCRIPTION
     "This attribute specifies for which dlci (on the local end) the frames 
      are destined."
   DEFVAL     { 16 }
::= { mscFrNniLtsPatSetupEntry 200 }

mscFrNniLtsPatNumFrames OBJECT-TYPE
   SYNTAX     Unsigned32 (0..4294967295)
   ACCESS     read-write
   STATUS     mandatory
   DESCRIPTION
     "This attribute specifies the number of frames in this pattern.  This is 
      the number of frames of this type which will be generated in one 
      timeInterval."
   DEFVAL     { 100 }
::= { mscFrNniLtsPatSetupEntry 201 }

mscFrNniLtsPatDataSize OBJECT-TYPE
   SYNTAX     Unsigned32 (0..8200)
   ACCESS     read-write
   STATUS     mandatory
   DESCRIPTION
     "This attribute specifies the payload size of each frame in bytes.  
      This is in excess to the header."
   DEFVAL     { 512 }
::= { mscFrNniLtsPatSetupEntry 202 }

mscFrNniLtsPatHeaderBits OBJECT-TYPE
   SYNTAX     OCTET STRING (SIZE (1))
   ACCESS     read-write
   STATUS     mandatory
   DESCRIPTION
     "This attribute specifies whether the following bits are on/off in the 
      header of each frame. The following bits can be set:
      BeCn, C/R, De, FeCn

      Description of bits:
      becn(0)
      fecn(1)
      cr(2)
      de(3)"
::= { mscFrNniLtsPatSetupEntry 203 }

mscFrNniLtsPatHeaderLength OBJECT-TYPE
   SYNTAX     Unsigned32 (0 | 2..4)
   ACCESS     read-write
   STATUS     mandatory
   DESCRIPTION
     "This attribute specifies the size of the frame relay header in bytes.  
      Passport currently only supports a 2-byte header.  Valid values are 
      0, 2, 3, 4.  0 indicates to use no header.  That is, the frame will start 
      with either the payload or rfc1490 header."
   DEFVAL     { 2 }
::= { mscFrNniLtsPatSetupEntry 204 }

mscFrNniLtsPatEaBits OBJECT-TYPE
   SYNTAX     Hex (0..15)
   ACCESS     read-write
   STATUS     mandatory
   DESCRIPTION
     "This attribute specifies how the address field extension bits are set in 
      the frame header.  Consider the value to be a four bit binary number.  
      For example, 4 = 0100.  Only the first headerLength bits are used. 
      For instance, suppose headerLength is 3, then the appropriate eaBits 
      is 2, or 0010.  This attribute can be used to create a header of length 
      greater than two bytes or to specify incorrect eaBits in the header."
   DEFVAL     { 4 }
::= { mscFrNniLtsPatSetupEntry 205 }

mscFrNniLtsPatPayloadPattern OBJECT-TYPE
   SYNTAX     HexString (SIZE (1..12))
   ACCESS     read-write
   STATUS     mandatory
   DESCRIPTION
     "This attribute specifies the payload of each frame.  The value 
      specified is in hexadecimal, where every two digits represent a byte.  
      A maximum of 24 digits (12 bytes) may be set, after which the 
      pattern will repeat in the payload (depending on repeatPattern 
      attribute). 
      NOTE: If a RFC 1490 header is specified, via the 1490Header 
      attribute, the specified pattern will begin following the header (i.e. 
      at the 9th byte in the payload)."
   DEFVAL     { '55'H }  -- "55"
::= { mscFrNniLtsPatSetupEntry 206 }

mscFrNniLtsPatRfc1490Header OBJECT-TYPE
   SYNTAX     INTEGER  {
                 n0(0),
                 n1(1),
                 n2(2),
                 n3(3),
                 n4(4),
                 n5(5),
                 n6(6),
                 n7(7),
                 n8(8),
                 n9(9),
                 n10(10),
                 n11(11),
                 n12(12),
                 n13(13),
                 n14(14),
                 n15(15),
                 n16(16),
                 n17(17),
                 none(18) }
   ACCESS     read-write
   STATUS     mandatory
   DESCRIPTION
     "This attribute specifies the appropriate RFC 1490 encapsulated 
      header of the frame.  A value of 0 indicates no 1490 header.
      NOTE: This header resides in the first 8 bytes of the payload.  If the 
      specified value is non-zero, then the payload pattern provisioned 
      will begin at the 9th byte."
   DEFVAL     { none }
::= { mscFrNniLtsPatSetupEntry 207 }

mscFrNniLtsPatUseBadLrc OBJECT-TYPE
   SYNTAX     INTEGER  {
                 no(0),
                 yes(1) }
   ACCESS     read-write
   STATUS     mandatory
   DESCRIPTION
     "This attribute specifies whether the frames from this pattern are to 
      have a bad LRC prior to being sent to the framer.  The LRC is 
      checked while the frame is being put onto the link and the failure 
      should cause an abort frame to be sent."
   DEFVAL     { no }
::= { mscFrNniLtsPatSetupEntry 208 }

mscFrNniLtsPatOpDataTable OBJECT-TYPE
   SYNTAX     SEQUENCE OF MscFrNniLtsPatOpDataEntry
   ACCESS     not-accessible
   STATUS     mandatory
   DESCRIPTION
     "This group contains the operational attributes which allow changing 
      the pattern outside of provisioning mode."
::= { mscFrNniLtsPat 12 }

mscFrNniLtsPatOpDataEntry OBJECT-TYPE
   SYNTAX     MscFrNniLtsPatOpDataEntry
   ACCESS     not-accessible
   STATUS     mandatory
   DESCRIPTION
     "An entry in the mscFrNniLtsPatOpDataTable."
   INDEX {
      mscFrNniIndex,
      mscFrNniLtsIndex,
      mscFrNniLtsPatIndex }
::= { mscFrNniLtsPatOpDataTable 1 }

MscFrNniLtsPatOpDataEntry ::= SEQUENCE {
   mscFrNniLtsPatFramePattern
      HexString,
   mscFrNniLtsPatHdlcBitsInserted
      Unsigned32 }

mscFrNniLtsPatFramePattern OBJECT-TYPE
   SYNTAX     HexString (SIZE (20..24))
   ACCESS     read-only
   STATUS     mandatory
   DESCRIPTION
     "This attribute displays the first 20 to 24 bytes of the frame payload, 
      depending on the frame relay header size selected.  This attribute 
      represents the frame if it were at least 20 to 24 bytes in size.  That 
      is, the actual frame may be smaller."
::= { mscFrNniLtsPatOpDataEntry 200 }

mscFrNniLtsPatHdlcBitsInserted OBJECT-TYPE
   SYNTAX     Unsigned32 (0..65535)
   ACCESS     read-only
   STATUS     mandatory
   DESCRIPTION
     "This attribute displays how many times a zero bit will be inserted 
      after 5 consecutive 1 bits when a frame from this pattern is sent out."
::= { mscFrNniLtsPatOpDataEntry 201 }

mscFrNniLtsPatOpStateTable OBJECT-TYPE
   SYNTAX     SEQUENCE OF MscFrNniLtsPatOpStateEntry
   ACCESS     not-accessible
   STATUS     mandatory
   DESCRIPTION
     "This group contains the attributes containing the operational 
      statistics of the pattern."
::= { mscFrNniLtsPat 13 }

mscFrNniLtsPatOpStateEntry OBJECT-TYPE
   SYNTAX     MscFrNniLtsPatOpStateEntry
   ACCESS     not-accessible
   STATUS     mandatory
   DESCRIPTION
     "An entry in the mscFrNniLtsPatOpStateTable."
   INDEX {
      mscFrNniIndex,
      mscFrNniLtsIndex,
      mscFrNniLtsPatIndex }
::= { mscFrNniLtsPatOpStateTable 1 }

MscFrNniLtsPatOpStateEntry ::= SEQUENCE {
   mscFrNniLtsPatLoad
      FixedPoint3,
   mscFrNniLtsPatStatus
      INTEGER }

mscFrNniLtsPatLoad OBJECT-TYPE
   SYNTAX     FixedPoint3 (0..4294967295)
   ACCESS     read-only
   STATUS     mandatory
   DESCRIPTION
     "This attribute indicates the load due to this particular pattern.  The 
      loads associated with all of the provisioned patterns are summed to 
      arrive at the FrLts load."
::= { mscFrNniLtsPatOpStateEntry 200 }

mscFrNniLtsPatStatus OBJECT-TYPE
   SYNTAX     INTEGER  {
                 enabled(0),
                 disabled(1) }
   ACCESS     read-write
   STATUS     mandatory
   DESCRIPTION
     "This attributes specifies the administrative state of the pattern.  A 
      disabled pattern will not be generated, although it can still be 
      triggered."
   DEFVAL     { enabled }
::= { mscFrNniLtsPatOpStateEntry 201 }


-- FrNni/n ConnectionAdministrator
-- The Ca component allows the network operator to specify common 
-- subscription options for the parent  interface. It defines the call 
-- admission control parameters in the ingress and egress direction for 
-- the parent interface. 

mscFrNniCa OBJECT IDENTIFIER ::= { mscFrNni 101 }



mscFrNniCaRowStatusTable OBJECT-TYPE
   SYNTAX     SEQUENCE OF MscFrNniCaRowStatusEntry
   ACCESS     not-accessible
   STATUS     mandatory
   DESCRIPTION
     "This entry controls the addition and deletion of 
      mscFrNniCa components."
::= { mscFrNniCa 1 }

mscFrNniCaRowStatusEntry OBJECT-TYPE
   SYNTAX     MscFrNniCaRowStatusEntry
   ACCESS     not-accessible
   STATUS     mandatory
   DESCRIPTION
     "A single entry in the table represents a single 
      mscFrNniCa component."
   INDEX {
      mscFrNniIndex,
      mscFrNniCaIndex }
::= { mscFrNniCaRowStatusTable 1 }

MscFrNniCaRowStatusEntry ::= SEQUENCE {
   mscFrNniCaRowStatus
      RowStatus,
   mscFrNniCaComponentName
      DisplayString,
   mscFrNniCaStorageType
      StorageType,
   mscFrNniCaIndex
      NonReplicated }

mscFrNniCaRowStatus OBJECT-TYPE
   SYNTAX     RowStatus 
   ACCESS     read-only
   STATUS     mandatory
   DESCRIPTION
     "This variable is used as the basis for SNMP naming of
      mscFrNniCa components.
      These components cannot be added nor deleted."
::= { mscFrNniCaRowStatusEntry 1 }

mscFrNniCaComponentName OBJECT-TYPE
   SYNTAX     DisplayString 
   ACCESS     read-only
   STATUS     mandatory
   DESCRIPTION
     "This variable provides the component's string name for
      use with the ASCII Console Interface"
::= { mscFrNniCaRowStatusEntry 2 }

mscFrNniCaStorageType OBJECT-TYPE
   SYNTAX     StorageType 
   ACCESS     read-only
   STATUS     mandatory
   DESCRIPTION
     "This variable represents the storage type value for the
      mscFrNniCa tables."
::= { mscFrNniCaRowStatusEntry 4 }

mscFrNniCaIndex OBJECT-TYPE
   SYNTAX     NonReplicated 
   ACCESS     not-accessible
   STATUS     mandatory
   DESCRIPTION
     "This variable represents the index for the mscFrNniCa tables."
::= { mscFrNniCaRowStatusEntry 10 }

mscFrNniCaProvTable OBJECT-TYPE
   SYNTAX     SEQUENCE OF MscFrNniCaProvEntry
   ACCESS     not-accessible
   STATUS     mandatory
   DESCRIPTION
     "This attribute group contains the common provisionable attributes 
      of the Ca component."
::= { mscFrNniCa 10 }

mscFrNniCaProvEntry OBJECT-TYPE
   SYNTAX     MscFrNniCaProvEntry
   ACCESS     not-accessible
   STATUS     mandatory
   DESCRIPTION
     "An entry in the mscFrNniCaProvTable."
   INDEX {
      mscFrNniIndex,
      mscFrNniCaIndex }
::= { mscFrNniCaProvTable 1 }

MscFrNniCaProvEntry ::= SEQUENCE {
   mscFrNniCaOverrideLinkRate
      Unsigned32,
   mscFrNniCaMaximumBandwidthPerCall
      Unsigned32 }

mscFrNniCaOverrideLinkRate OBJECT-TYPE
   SYNTAX     Unsigned32 (0..429496729)
   ACCESS     read-write
   STATUS     mandatory
   DESCRIPTION
     "This attribute allows the link rate to be overridden for this interface.  
      This allows the user to specify a value other than the actual physical 
      link rate computed when a Framer component is provisioned.  
      When a VFramer component is provisioned, this attribute overrides 
      a link rate set to the maximum value supported by CAC .
      
      This attribute serves to provide the user control on the amount of 
      bandwidth available for performing CAC."
   DEFVAL     { 0 }
::= { mscFrNniCaProvEntry 2 }

mscFrNniCaMaximumBandwidthPerCall OBJECT-TYPE
   SYNTAX     Unsigned32 (0..520000000)
   ACCESS     read-write
   STATUS     mandatory
   DESCRIPTION
     "This attribute specifies the maximum bandwidth that can be 
      allocated per connection."
   DEFVAL     { 520000000 }
::= { mscFrNniCaProvEntry 3 }

mscFrNniCaIngressCacTable OBJECT-TYPE
   SYNTAX     SEQUENCE OF MscFrNniCaIngressCacEntry
   ACCESS     not-accessible
   STATUS     mandatory
   DESCRIPTION
     "This attribute group contains the common provisionable attributes 
      for ingress call admission control."
::= { mscFrNniCa 11 }

mscFrNniCaIngressCacEntry OBJECT-TYPE
   SYNTAX     MscFrNniCaIngressCacEntry
   ACCESS     not-accessible
   STATUS     mandatory
   DESCRIPTION
     "An entry in the mscFrNniCaIngressCacTable."
   INDEX {
      mscFrNniIndex,
      mscFrNniCaIndex }
::= { mscFrNniCaIngressCacTable 1 }

MscFrNniCaIngressCacEntry ::= SEQUENCE {
   mscFrNniCaIngressApplyToCos
      INTEGER,
   mscFrNniCaIngressMaximumEirOnlyCalls
      Unsigned32 }

mscFrNniCaIngressApplyToCos OBJECT-TYPE
   SYNTAX     INTEGER  {
                 none(0),
                 cirOnly(1),
                 cirAndEir(2) }
   ACCESS     read-write
   STATUS     mandatory
   DESCRIPTION
     "This attribute specifies which Classes of Service (CoS) have ingress 
      Call Admission Control (CAC) applied to them. Ingress CAC 
      applies only to swithced connections (SVCs and S-SPVCs).
      
      none - Ingress CAC is turned off for all classes of service.
      cirOnly - Ingress CAC is applied only to the CIR portion of a 
      connection's bandwidth requirements for CIR>0 classes of service.
      cirAndEir - Ingress CAC is applied to both CIR and EIR portions 
      of a connections bandwidth requirements for all classes of service."
   DEFVAL     { cirOnly }
::= { mscFrNniCaIngressCacEntry 2 }

mscFrNniCaIngressMaximumEirOnlyCalls OBJECT-TYPE
   SYNTAX     Unsigned32 (0..992)
   ACCESS     read-write
   STATUS     mandatory
   DESCRIPTION
     "This attribute specifies the maximum number of connections in the 
      ingress direction with EIR only traffic that can be up at a given 
      time."
   DEFVAL     { 992 }
::= { mscFrNniCaIngressCacEntry 4 }

mscFrNniCaEgressCacTable OBJECT-TYPE
   SYNTAX     SEQUENCE OF MscFrNniCaEgressCacEntry
   ACCESS     not-accessible
   STATUS     mandatory
   DESCRIPTION
     "This attribute group contains the common provisionable attributes 
      for egress call admission control."
::= { mscFrNniCa 12 }

mscFrNniCaEgressCacEntry OBJECT-TYPE
   SYNTAX     MscFrNniCaEgressCacEntry
   ACCESS     not-accessible
   STATUS     mandatory
   DESCRIPTION
     "An entry in the mscFrNniCaEgressCacTable."
   INDEX {
      mscFrNniIndex,
      mscFrNniCaIndex }
::= { mscFrNniCaEgressCacTable 1 }

MscFrNniCaEgressCacEntry ::= SEQUENCE {
   mscFrNniCaEgressApplyToCos
      INTEGER,
   mscFrNniCaEgressMaximumEirOnlyCalls
      Unsigned32 }

mscFrNniCaEgressApplyToCos OBJECT-TYPE
   SYNTAX     INTEGER  {
                 none(0),
                 cirOnly(1),
                 cirAndEir(2) }
   ACCESS     read-write
   STATUS     mandatory
   DESCRIPTION
     "This attribute specifies which Classes of Service (CoS) have egress 
      Call Admission Control (CAC) applied to them. Egress CAC 
      applies only to swithced connections (SVCs and S-SPVCs).
      
      none - Egress CAC is turned off for all classes of service.
      cirOnly - Egress CAC is applied only to the CIR portion of a 
      connection's bandwidth requirements for CIR>0 classes of service.
      cirAndEir - Egress CAC is applied to both CIR and EIR portions of 
      a connections bandwidth requirements for all classes of service."
   DEFVAL     { none }
::= { mscFrNniCaEgressCacEntry 2 }

mscFrNniCaEgressMaximumEirOnlyCalls OBJECT-TYPE
   SYNTAX     Unsigned32 (0..992)
   ACCESS     read-write
   STATUS     mandatory
   DESCRIPTION
     "This attribute specifies the maximum number of connections in the 
      egress direction with EIR only traffic that can be up at a given time."
   DEFVAL     { 992 }
::= { mscFrNniCaEgressCacEntry 4 }

mscFrNniCaOpTable OBJECT-TYPE
   SYNTAX     SEQUENCE OF MscFrNniCaOpEntry
   ACCESS     not-accessible
   STATUS     mandatory
   DESCRIPTION
     "This attribute group contains the operational status of the Ca 
      component."
::= { mscFrNniCa 13 }

mscFrNniCaOpEntry OBJECT-TYPE
   SYNTAX     MscFrNniCaOpEntry
   ACCESS     not-accessible
   STATUS     mandatory
   DESCRIPTION
     "An entry in the mscFrNniCaOpTable."
   INDEX {
      mscFrNniIndex,
      mscFrNniCaIndex }
::= { mscFrNniCaOpTable 1 }

MscFrNniCaOpEntry ::= SEQUENCE {
   mscFrNniCaLinkRate
      Unsigned32,
   mscFrNniCaNumberRejectedEgressCirPermConn
      Gauge32,
   mscFrNniCaNumberRejectedEgressEirPermConn
      Gauge32 }

mscFrNniCaLinkRate OBJECT-TYPE
   SYNTAX     Unsigned32 (0..520000000)
   ACCESS     read-only
   STATUS     mandatory
   DESCRIPTION
     "This attribute indicates the link rate used by both ingress and egress 
      CAC to calculate the effective bandwidth pool sizes.
      
      If the provisionable attribute overrideLinkRate under this 
      component is 0, then the link rate reported is the actual link rate of 
      the port or channel.  Otherwise, the link rate reported is the 
      overrideLinkRate under this component."
::= { mscFrNniCaOpEntry 2 }

mscFrNniCaNumberRejectedEgressCirPermConn OBJECT-TYPE
   SYNTAX     Gauge32 (0..992)
   ACCESS     read-only
   STATUS     mandatory
   DESCRIPTION
     "This attribute indicates the number of permanent connections (that 
      is, PVC and P-SPVC) that are rejected by egress CAC. A 
      connection is rejected by egress CAC if it requests more egress CIR 
      bandwidth than is available, and the egressApplyToCos attribute is 
      set to either cirOnly or cirAndEir."
::= { mscFrNniCaOpEntry 681 }

mscFrNniCaNumberRejectedEgressEirPermConn OBJECT-TYPE
   SYNTAX     Gauge32 (0..992)
   ACCESS     read-only
   STATUS     mandatory
   DESCRIPTION
     "This attribute indicates the number of permanent connections (that 
      is, PVC and P-SPVC) that are rejected by egress CAC.  A 
      connection is rejected by egress CAC if it requests more egress EIR 
      bandwidth than is available, and the egressApplyToCos attribute is 
      set to cirAndEir."
::= { mscFrNniCaOpEntry 682 }

mscFrNniCaIngCirBPTable OBJECT-TYPE
   SYNTAX     SEQUENCE OF MscFrNniCaIngCirBPEntry
   ACCESS     not-accessible
   STATUS     mandatory
   DESCRIPTION
     "Port capacity is partitioned into 16 pools (pool 0 through pool 15) 
      for the ingress CIR traffic. This attribute specifies the percentage of 
      port capacity that is allowed for each pool. The percentage for each 
      pool ranges from 0% to 1000% of the link rate. It allows for under 
      or over subscription of the port. Under subscription occurs when the 
      sum of the percentages assigned to the 16 pools is less than 100%. 
      Over subscription occurs when the sum of the percentages for the 
      16 pools exceeds 100%.
      
      The default is full sharing of port capacity with three pre-set 
      partitions."
::= { mscFrNniCa 666 }

mscFrNniCaIngCirBPEntry OBJECT-TYPE
   SYNTAX     MscFrNniCaIngCirBPEntry
   ACCESS     not-accessible
   STATUS     mandatory
   DESCRIPTION
     "An entry in the mscFrNniCaIngCirBPTable."
   INDEX {
      mscFrNniIndex,
      mscFrNniCaIndex,
      mscFrNniCaIngCirBPIndex }
::= { mscFrNniCaIngCirBPTable 1 }

MscFrNniCaIngCirBPEntry ::= SEQUENCE {
   mscFrNniCaIngCirBPIndex
      Integer32,
   mscFrNniCaIngCirBPValue
      Unsigned32 }

mscFrNniCaIngCirBPIndex OBJECT-TYPE
   SYNTAX     Integer32 (0..15)
   ACCESS     not-accessible
   STATUS     mandatory
   DESCRIPTION
     "This variable represents the mscFrNniCaIngCirBPTable
      specific index for the mscFrNniCaIngCirBPTable."
::= { mscFrNniCaIngCirBPEntry 1 }

mscFrNniCaIngCirBPValue OBJECT-TYPE
   SYNTAX     Unsigned32 (0..1000)
   ACCESS     read-write
   STATUS     mandatory
   DESCRIPTION
     "This variable represents an individual value for the
      mscFrNniCaIngCirBPTable."
::= { mscFrNniCaIngCirBPEntry 2 }

mscFrNniCaEgCirBpTable OBJECT-TYPE
   SYNTAX     SEQUENCE OF MscFrNniCaEgCirBpEntry
   ACCESS     not-accessible
   STATUS     mandatory
   DESCRIPTION
     "Port capacity is partitioned into 16 pools (pool 0 through pool 15) 
      for the egress CIR traffic. This attribute specifies the percentage of 
      port capacity that is allowed for each pool. The percentage for each 
      pool ranges from 0% to 1000% of the link rate. It allows for under 
      or over subscription of the port. Under subscription occurs when the 
      sum of the percentages assigned to the 16 pools is less than 100%. 
      Over subscription occurs when the sum of the percentages for the 
      16 pools exceeds 100%.
      
      The default is full sharing of port capacity with three pre-set 
      partitions."
::= { mscFrNniCa 667 }

mscFrNniCaEgCirBpEntry OBJECT-TYPE
   SYNTAX     MscFrNniCaEgCirBpEntry
   ACCESS     not-accessible
   STATUS     mandatory
   DESCRIPTION
     "An entry in the mscFrNniCaEgCirBpTable."
   INDEX {
      mscFrNniIndex,
      mscFrNniCaIndex,
      mscFrNniCaEgCirBpIndex }
::= { mscFrNniCaEgCirBpTable 1 }

MscFrNniCaEgCirBpEntry ::= SEQUENCE {
   mscFrNniCaEgCirBpIndex
      Integer32,
   mscFrNniCaEgCirBpValue
      Unsigned32 }

mscFrNniCaEgCirBpIndex OBJECT-TYPE
   SYNTAX     Integer32 (0..15)
   ACCESS     not-accessible
   STATUS     mandatory
   DESCRIPTION
     "This variable represents the mscFrNniCaEgCirBpTable
      specific index for the mscFrNniCaEgCirBpTable."
::= { mscFrNniCaEgCirBpEntry 1 }

mscFrNniCaEgCirBpValue OBJECT-TYPE
   SYNTAX     Unsigned32 (0..1000)
   ACCESS     read-write
   STATUS     mandatory
   DESCRIPTION
     "This variable represents an individual value for the
      mscFrNniCaEgCirBpTable."
::= { mscFrNniCaEgCirBpEntry 2 }

mscFrNniCaIngCirPoolAdmitBwTable OBJECT-TYPE
   SYNTAX     SEQUENCE OF MscFrNniCaIngCirPoolAdmitBwEntry
   ACCESS     not-accessible
   STATUS     mandatory
   DESCRIPTION
     "This attribute indicates the total admitted CIR bandwidth from each 
      CIR bandwidth pool in the ingress direction. Each value is the sum 
      of the equivalent bit rates of the admitted connections."
::= { mscFrNniCa 668 }

mscFrNniCaIngCirPoolAdmitBwEntry OBJECT-TYPE
   SYNTAX     MscFrNniCaIngCirPoolAdmitBwEntry
   ACCESS     not-accessible
   STATUS     mandatory
   DESCRIPTION
     "An entry in the mscFrNniCaIngCirPoolAdmitBwTable."
   INDEX {
      mscFrNniIndex,
      mscFrNniCaIndex,
      mscFrNniCaIngCirPoolAdmitBwIndex }
::= { mscFrNniCaIngCirPoolAdmitBwTable 1 }

MscFrNniCaIngCirPoolAdmitBwEntry ::= SEQUENCE {
   mscFrNniCaIngCirPoolAdmitBwIndex
      Integer32,
   mscFrNniCaIngCirPoolAdmitBwValue
      Gauge32 }

mscFrNniCaIngCirPoolAdmitBwIndex OBJECT-TYPE
   SYNTAX     Integer32 (0..15)
   ACCESS     not-accessible
   STATUS     mandatory
   DESCRIPTION
     "This variable represents the mscFrNniCaIngCirPoolAdmitBwTable
      specific index for the mscFrNniCaIngCirPoolAdmitBwTable."
::= { mscFrNniCaIngCirPoolAdmitBwEntry 1 }

mscFrNniCaIngCirPoolAdmitBwValue OBJECT-TYPE
   SYNTAX     Gauge32 (0..520000000)
   ACCESS     read-only
   STATUS     mandatory
   DESCRIPTION
     "This variable represents an individual value for the
      mscFrNniCaIngCirPoolAdmitBwTable."
::= { mscFrNniCaIngCirPoolAdmitBwEntry 2 }

mscFrNniCaIngCirPoolAvailBwTable OBJECT-TYPE
   SYNTAX     SEQUENCE OF MscFrNniCaIngCirPoolAvailBwEntry
   ACCESS     not-accessible
   STATUS     mandatory
   DESCRIPTION
     "This attribute indicates the remaining available CIR bandwidth in 
      each ingress CIR bandwidth pool."
::= { mscFrNniCa 669 }

mscFrNniCaIngCirPoolAvailBwEntry OBJECT-TYPE
   SYNTAX     MscFrNniCaIngCirPoolAvailBwEntry
   ACCESS     not-accessible
   STATUS     mandatory
   DESCRIPTION
     "An entry in the mscFrNniCaIngCirPoolAvailBwTable."
   INDEX {
      mscFrNniIndex,
      mscFrNniCaIndex,
      mscFrNniCaIngCirPoolAvailBwIndex }
::= { mscFrNniCaIngCirPoolAvailBwTable 1 }

MscFrNniCaIngCirPoolAvailBwEntry ::= SEQUENCE {
   mscFrNniCaIngCirPoolAvailBwIndex
      Integer32,
   mscFrNniCaIngCirPoolAvailBwValue
      Gauge32 }

mscFrNniCaIngCirPoolAvailBwIndex OBJECT-TYPE
   SYNTAX     Integer32 (0..15)
   ACCESS     not-accessible
   STATUS     mandatory
   DESCRIPTION
     "This variable represents the mscFrNniCaIngCirPoolAvailBwTable
      specific index for the mscFrNniCaIngCirPoolAvailBwTable."
::= { mscFrNniCaIngCirPoolAvailBwEntry 1 }

mscFrNniCaIngCirPoolAvailBwValue OBJECT-TYPE
   SYNTAX     Gauge32 (0..52000000)
   ACCESS     read-only
   STATUS     mandatory
   DESCRIPTION
     "This variable represents an individual value for the
      mscFrNniCaIngCirPoolAvailBwTable."
::= { mscFrNniCaIngCirPoolAvailBwEntry 2 }

mscFrNniCaEgCirPoolAdmitBwTable OBJECT-TYPE
   SYNTAX     SEQUENCE OF MscFrNniCaEgCirPoolAdmitBwEntry
   ACCESS     not-accessible
   STATUS     mandatory
   DESCRIPTION
     "This attribute indicates the total admitted CIR bandwidth from each 
      CIR bandwidth pool in the egress direction. Each value is the sum 
      of the equivalent bit rates of the admitted connections."
::= { mscFrNniCa 670 }

mscFrNniCaEgCirPoolAdmitBwEntry OBJECT-TYPE
   SYNTAX     MscFrNniCaEgCirPoolAdmitBwEntry
   ACCESS     not-accessible
   STATUS     mandatory
   DESCRIPTION
     "An entry in the mscFrNniCaEgCirPoolAdmitBwTable."
   INDEX {
      mscFrNniIndex,
      mscFrNniCaIndex,
      mscFrNniCaEgCirPoolAdmitBwIndex }
::= { mscFrNniCaEgCirPoolAdmitBwTable 1 }

MscFrNniCaEgCirPoolAdmitBwEntry ::= SEQUENCE {
   mscFrNniCaEgCirPoolAdmitBwIndex
      Integer32,
   mscFrNniCaEgCirPoolAdmitBwValue
      Gauge32 }

mscFrNniCaEgCirPoolAdmitBwIndex OBJECT-TYPE
   SYNTAX     Integer32 (0..15)
   ACCESS     not-accessible
   STATUS     mandatory
   DESCRIPTION
     "This variable represents the mscFrNniCaEgCirPoolAdmitBwTable
      specific index for the mscFrNniCaEgCirPoolAdmitBwTable."
::= { mscFrNniCaEgCirPoolAdmitBwEntry 1 }

mscFrNniCaEgCirPoolAdmitBwValue OBJECT-TYPE
   SYNTAX     Gauge32 (0..520000000)
   ACCESS     read-only
   STATUS     mandatory
   DESCRIPTION
     "This variable represents an individual value for the
      mscFrNniCaEgCirPoolAdmitBwTable."
::= { mscFrNniCaEgCirPoolAdmitBwEntry 2 }

mscFrNniCaEgCirPoolAvailBwTable OBJECT-TYPE
   SYNTAX     SEQUENCE OF MscFrNniCaEgCirPoolAvailBwEntry
   ACCESS     not-accessible
   STATUS     mandatory
   DESCRIPTION
     "This attribute indicates the remaining available CIR bandwidth in 
      each egress CIR bandwidth pool."
::= { mscFrNniCa 671 }

mscFrNniCaEgCirPoolAvailBwEntry OBJECT-TYPE
   SYNTAX     MscFrNniCaEgCirPoolAvailBwEntry
   ACCESS     not-accessible
   STATUS     mandatory
   DESCRIPTION
     "An entry in the mscFrNniCaEgCirPoolAvailBwTable."
   INDEX {
      mscFrNniIndex,
      mscFrNniCaIndex,
      mscFrNniCaEgCirPoolAvailBwIndex }
::= { mscFrNniCaEgCirPoolAvailBwTable 1 }

MscFrNniCaEgCirPoolAvailBwEntry ::= SEQUENCE {
   mscFrNniCaEgCirPoolAvailBwIndex
      Integer32,
   mscFrNniCaEgCirPoolAvailBwValue
      Gauge32 }

mscFrNniCaEgCirPoolAvailBwIndex OBJECT-TYPE
   SYNTAX     Integer32 (0..15)
   ACCESS     not-accessible
   STATUS     mandatory
   DESCRIPTION
     "This variable represents the mscFrNniCaEgCirPoolAvailBwTable
      specific index for the mscFrNniCaEgCirPoolAvailBwTable."
::= { mscFrNniCaEgCirPoolAvailBwEntry 1 }

mscFrNniCaEgCirPoolAvailBwValue OBJECT-TYPE
   SYNTAX     Gauge32 (0..52000000)
   ACCESS     read-only
   STATUS     mandatory
   DESCRIPTION
     "This variable represents an individual value for the
      mscFrNniCaEgCirPoolAvailBwTable."
::= { mscFrNniCaEgCirPoolAvailBwEntry 2 }

mscFrNniCaIngEirBpTable OBJECT-TYPE
   SYNTAX     SEQUENCE OF MscFrNniCaIngEirBpEntry
   ACCESS     not-accessible
   STATUS     mandatory
   DESCRIPTION
     "Port capacity is partitioned into 16 pools (pool 0 through pool 15) 
      for the ingress EIR traffic. This attribute specifies the percentage of 
      port capacity that is allowed for each pool. The percentage for each 
      pool ranges from 0% to 1000% of the link rate. It allows for under 
      or over subscription of the port. Under subscription occurs when the 
      sum of the percentages assigned to the 16 pools is less than 100%. 
      Over subscription occurs when the sum of the percentages for the 
      16 pools exceeds 100%.
      
      The default is full sharing of port capacity with three pre-set 
      partitions."
::= { mscFrNniCa 673 }

mscFrNniCaIngEirBpEntry OBJECT-TYPE
   SYNTAX     MscFrNniCaIngEirBpEntry
   ACCESS     not-accessible
   STATUS     mandatory
   DESCRIPTION
     "An entry in the mscFrNniCaIngEirBpTable."
   INDEX {
      mscFrNniIndex,
      mscFrNniCaIndex,
      mscFrNniCaIngEirBpIndex }
::= { mscFrNniCaIngEirBpTable 1 }

MscFrNniCaIngEirBpEntry ::= SEQUENCE {
   mscFrNniCaIngEirBpIndex
      Integer32,
   mscFrNniCaIngEirBpValue
      Unsigned32 }

mscFrNniCaIngEirBpIndex OBJECT-TYPE
   SYNTAX     Integer32 (0..15)
   ACCESS     not-accessible
   STATUS     mandatory
   DESCRIPTION
     "This variable represents the mscFrNniCaIngEirBpTable
      specific index for the mscFrNniCaIngEirBpTable."
::= { mscFrNniCaIngEirBpEntry 1 }

mscFrNniCaIngEirBpValue OBJECT-TYPE
   SYNTAX     Unsigned32 (0..1000)
   ACCESS     read-write
   STATUS     mandatory
   DESCRIPTION
     "This variable represents an individual value for the
      mscFrNniCaIngEirBpTable."
::= { mscFrNniCaIngEirBpEntry 2 }

mscFrNniCaEgEirBpTable OBJECT-TYPE
   SYNTAX     SEQUENCE OF MscFrNniCaEgEirBpEntry
   ACCESS     not-accessible
   STATUS     mandatory
   DESCRIPTION
     "Port capacity is partitioned into 16 pools (pool 0 through pool 15) 
      for the egress EIR traffic. This attribute specifies the percentage of 
      port capacity that is allowed for each pool. The percentage for each 
      pool ranges from 0% to 1000% of the link rate. It allows for under 
      or over subscription of the port. Under subscription occurs when the 
      sum of the percentages assigned to the 16 pools is less than 100%. 
      Over subscription occurs when the sum of the percentages for the 
      16 pools exceeds 100%.
      
      The default is full sharing of port capacity with three pre-set 
      partitions."
::= { mscFrNniCa 674 }

mscFrNniCaEgEirBpEntry OBJECT-TYPE
   SYNTAX     MscFrNniCaEgEirBpEntry
   ACCESS     not-accessible
   STATUS     mandatory
   DESCRIPTION
     "An entry in the mscFrNniCaEgEirBpTable."
   INDEX {
      mscFrNniIndex,
      mscFrNniCaIndex,
      mscFrNniCaEgEirBpIndex }
::= { mscFrNniCaEgEirBpTable 1 }

MscFrNniCaEgEirBpEntry ::= SEQUENCE {
   mscFrNniCaEgEirBpIndex
      Integer32,
   mscFrNniCaEgEirBpValue
      Unsigned32 }

mscFrNniCaEgEirBpIndex OBJECT-TYPE
   SYNTAX     Integer32 (0..15)
   ACCESS     not-accessible
   STATUS     mandatory
   DESCRIPTION
     "This variable represents the mscFrNniCaEgEirBpTable
      specific index for the mscFrNniCaEgEirBpTable."
::= { mscFrNniCaEgEirBpEntry 1 }

mscFrNniCaEgEirBpValue OBJECT-TYPE
   SYNTAX     Unsigned32 (0..1000)
   ACCESS     read-write
   STATUS     mandatory
   DESCRIPTION
     "This variable represents an individual value for the
      mscFrNniCaEgEirBpTable."
::= { mscFrNniCaEgEirBpEntry 2 }

mscFrNniCaIngEirPoolAdmitBwTable OBJECT-TYPE
   SYNTAX     SEQUENCE OF MscFrNniCaIngEirPoolAdmitBwEntry
   ACCESS     not-accessible
   STATUS     mandatory
   DESCRIPTION
     "This attribute indicates the total admitted EIR bandwidth from each 
      EIR bandwidth pool in the ingress direction. Each value is the sum 
      of the equivalent bit rates of the admitted connections.
      
      If the ingressApplyToCos attribute is set to none, all ingress CIR 
      bandwidth pools are set to 0."
::= { mscFrNniCa 675 }

mscFrNniCaIngEirPoolAdmitBwEntry OBJECT-TYPE
   SYNTAX     MscFrNniCaIngEirPoolAdmitBwEntry
   ACCESS     not-accessible
   STATUS     mandatory
   DESCRIPTION
     "An entry in the mscFrNniCaIngEirPoolAdmitBwTable."
   INDEX {
      mscFrNniIndex,
      mscFrNniCaIndex,
      mscFrNniCaIngEirPoolAdmitBwIndex }
::= { mscFrNniCaIngEirPoolAdmitBwTable 1 }

MscFrNniCaIngEirPoolAdmitBwEntry ::= SEQUENCE {
   mscFrNniCaIngEirPoolAdmitBwIndex
      Integer32,
   mscFrNniCaIngEirPoolAdmitBwValue
      Gauge32 }

mscFrNniCaIngEirPoolAdmitBwIndex OBJECT-TYPE
   SYNTAX     Integer32 (0..15)
   ACCESS     not-accessible
   STATUS     mandatory
   DESCRIPTION
     "This variable represents the mscFrNniCaIngEirPoolAdmitBwTable
      specific index for the mscFrNniCaIngEirPoolAdmitBwTable."
::= { mscFrNniCaIngEirPoolAdmitBwEntry 1 }

mscFrNniCaIngEirPoolAdmitBwValue OBJECT-TYPE
   SYNTAX     Gauge32 (0..520000000)
   ACCESS     read-only
   STATUS     mandatory
   DESCRIPTION
     "This variable represents an individual value for the
      mscFrNniCaIngEirPoolAdmitBwTable."
::= { mscFrNniCaIngEirPoolAdmitBwEntry 2 }

mscFrNniCaIngEirPoolAvailBwTable OBJECT-TYPE
   SYNTAX     SEQUENCE OF MscFrNniCaIngEirPoolAvailBwEntry
   ACCESS     not-accessible
   STATUS     mandatory
   DESCRIPTION
     "This attribute indicates the remaining available EIR bandwidth in 
      each ingress EIR bandwidth pool.
      
      If the ingressApplyToCos attribute is set to either none or cirOnly, 
      all ingress EIR bandwidth pools are set to 0."
::= { mscFrNniCa 676 }

mscFrNniCaIngEirPoolAvailBwEntry OBJECT-TYPE
   SYNTAX     MscFrNniCaIngEirPoolAvailBwEntry
   ACCESS     not-accessible
   STATUS     mandatory
   DESCRIPTION
     "An entry in the mscFrNniCaIngEirPoolAvailBwTable."
   INDEX {
      mscFrNniIndex,
      mscFrNniCaIndex,
      mscFrNniCaIngEirPoolAvailBwIndex }
::= { mscFrNniCaIngEirPoolAvailBwTable 1 }

MscFrNniCaIngEirPoolAvailBwEntry ::= SEQUENCE {
   mscFrNniCaIngEirPoolAvailBwIndex
      Integer32,
   mscFrNniCaIngEirPoolAvailBwValue
      Gauge32 }

mscFrNniCaIngEirPoolAvailBwIndex OBJECT-TYPE
   SYNTAX     Integer32 (0..15)
   ACCESS     not-accessible
   STATUS     mandatory
   DESCRIPTION
     "This variable represents the mscFrNniCaIngEirPoolAvailBwTable
      specific index for the mscFrNniCaIngEirPoolAvailBwTable."
::= { mscFrNniCaIngEirPoolAvailBwEntry 1 }

mscFrNniCaIngEirPoolAvailBwValue OBJECT-TYPE
   SYNTAX     Gauge32 (0..52000000)
   ACCESS     read-only
   STATUS     mandatory
   DESCRIPTION
     "This variable represents an individual value for the
      mscFrNniCaIngEirPoolAvailBwTable."
::= { mscFrNniCaIngEirPoolAvailBwEntry 2 }

mscFrNniCaEgEirPoolAdmitBwTable OBJECT-TYPE
   SYNTAX     SEQUENCE OF MscFrNniCaEgEirPoolAdmitBwEntry
   ACCESS     not-accessible
   STATUS     mandatory
   DESCRIPTION
     "This attribute indicates the total admitted EIR bandwidth from each 
      EIR bandwidth pool in the egress direction. Each value is the sum 
      of the equivalent bit rates of the admitted connections.
      
      If the egressApplyToCos attribute is set to none, all egress CIR 
      bandwidth pools are set to 0."
::= { mscFrNniCa 677 }

mscFrNniCaEgEirPoolAdmitBwEntry OBJECT-TYPE
   SYNTAX     MscFrNniCaEgEirPoolAdmitBwEntry
   ACCESS     not-accessible
   STATUS     mandatory
   DESCRIPTION
     "An entry in the mscFrNniCaEgEirPoolAdmitBwTable."
   INDEX {
      mscFrNniIndex,
      mscFrNniCaIndex,
      mscFrNniCaEgEirPoolAdmitBwIndex }
::= { mscFrNniCaEgEirPoolAdmitBwTable 1 }

MscFrNniCaEgEirPoolAdmitBwEntry ::= SEQUENCE {
   mscFrNniCaEgEirPoolAdmitBwIndex
      Integer32,
   mscFrNniCaEgEirPoolAdmitBwValue
      Gauge32 }

mscFrNniCaEgEirPoolAdmitBwIndex OBJECT-TYPE
   SYNTAX     Integer32 (0..15)
   ACCESS     not-accessible
   STATUS     mandatory
   DESCRIPTION
     "This variable represents the mscFrNniCaEgEirPoolAdmitBwTable
      specific index for the mscFrNniCaEgEirPoolAdmitBwTable."
::= { mscFrNniCaEgEirPoolAdmitBwEntry 1 }

mscFrNniCaEgEirPoolAdmitBwValue OBJECT-TYPE
   SYNTAX     Gauge32 (0..520000000)
   ACCESS     read-only
   STATUS     mandatory
   DESCRIPTION
     "This variable represents an individual value for the
      mscFrNniCaEgEirPoolAdmitBwTable."
::= { mscFrNniCaEgEirPoolAdmitBwEntry 2 }

mscFrNniCaEgEirPoolAvailBwTable OBJECT-TYPE
   SYNTAX     SEQUENCE OF MscFrNniCaEgEirPoolAvailBwEntry
   ACCESS     not-accessible
   STATUS     mandatory
   DESCRIPTION
     "This attribute indicates the remaining available EIR bandwidth in 
      each egress EIR bandwidth pool.
      
      If the egressApplyToCos attribute is set to either none or cirOnly, 
      all egress EIR bandwidth pools are set to 0."
::= { mscFrNniCa 678 }

mscFrNniCaEgEirPoolAvailBwEntry OBJECT-TYPE
   SYNTAX     MscFrNniCaEgEirPoolAvailBwEntry
   ACCESS     not-accessible
   STATUS     mandatory
   DESCRIPTION
     "An entry in the mscFrNniCaEgEirPoolAvailBwTable."
   INDEX {
      mscFrNniIndex,
      mscFrNniCaIndex,
      mscFrNniCaEgEirPoolAvailBwIndex }
::= { mscFrNniCaEgEirPoolAvailBwTable 1 }

MscFrNniCaEgEirPoolAvailBwEntry ::= SEQUENCE {
   mscFrNniCaEgEirPoolAvailBwIndex
      Integer32,
   mscFrNniCaEgEirPoolAvailBwValue
      Gauge32 }

mscFrNniCaEgEirPoolAvailBwIndex OBJECT-TYPE
   SYNTAX     Integer32 (0..15)
   ACCESS     not-accessible
   STATUS     mandatory
   DESCRIPTION
     "This variable represents the mscFrNniCaEgEirPoolAvailBwTable
      specific index for the mscFrNniCaEgEirPoolAvailBwTable."
::= { mscFrNniCaEgEirPoolAvailBwEntry 1 }

mscFrNniCaEgEirPoolAvailBwValue OBJECT-TYPE
   SYNTAX     Gauge32 (0..52000000)
   ACCESS     read-only
   STATUS     mandatory
   DESCRIPTION
     "This variable represents an individual value for the
      mscFrNniCaEgEirPoolAvailBwTable."
::= { mscFrNniCaEgEirPoolAvailBwEntry 2 }


-- FrNni/n Ca TransferPriorityMapping/n
-- The Tpm component defines the corresponding traffic management 
-- subscription options on a FrNni interface corresponding to a 
-- particular transfer priority.  This component is needed only if there 
-- is a requirement to override the Mod Frs DprsNet Tpm component 
-- defaults.

mscFrNniCaTpm OBJECT IDENTIFIER ::= { mscFrNniCa 2 }



mscFrNniCaTpmRowStatusTable OBJECT-TYPE
   SYNTAX     SEQUENCE OF MscFrNniCaTpmRowStatusEntry
   ACCESS     not-accessible
   STATUS     mandatory
   DESCRIPTION
     "This entry controls the addition and deletion of 
      mscFrNniCaTpm components."
::= { mscFrNniCaTpm 1 }

mscFrNniCaTpmRowStatusEntry OBJECT-TYPE
   SYNTAX     MscFrNniCaTpmRowStatusEntry
   ACCESS     not-accessible
   STATUS     mandatory
   DESCRIPTION
     "A single entry in the table represents a single 
      mscFrNniCaTpm component."
   INDEX {
      mscFrNniIndex,
      mscFrNniCaIndex,
      mscFrNniCaTpmIndex }
::= { mscFrNniCaTpmRowStatusTable 1 }

MscFrNniCaTpmRowStatusEntry ::= SEQUENCE {
   mscFrNniCaTpmRowStatus
      RowStatus,
   mscFrNniCaTpmComponentName
      DisplayString,
   mscFrNniCaTpmStorageType
      StorageType,
   mscFrNniCaTpmIndex
      Integer32 }

mscFrNniCaTpmRowStatus OBJECT-TYPE
   SYNTAX     RowStatus 
   ACCESS     read-write
   STATUS     mandatory
   DESCRIPTION
     "This variable is used as the basis for SNMP naming of
      mscFrNniCaTpm components.
      These components can be added and deleted."
::= { mscFrNniCaTpmRowStatusEntry 1 }

mscFrNniCaTpmComponentName OBJECT-TYPE
   SYNTAX     DisplayString 
   ACCESS     read-only
   STATUS     mandatory
   DESCRIPTION
     "This variable provides the component's string name for
      use with the ASCII Console Interface"
::= { mscFrNniCaTpmRowStatusEntry 2 }

mscFrNniCaTpmStorageType OBJECT-TYPE
   SYNTAX     StorageType 
   ACCESS     read-only
   STATUS     mandatory
   DESCRIPTION
     "This variable represents the storage type value for the
      mscFrNniCaTpm tables."
::= { mscFrNniCaTpmRowStatusEntry 4 }

mscFrNniCaTpmIndex OBJECT-TYPE
   SYNTAX     Integer32 (0..15)
   ACCESS     not-accessible
   STATUS     mandatory
   DESCRIPTION
     "This variable represents the index for the mscFrNniCaTpm tables."
::= { mscFrNniCaTpmRowStatusEntry 10 }

mscFrNniCaTpmProvTable OBJECT-TYPE
   SYNTAX     SEQUENCE OF MscFrNniCaTpmProvEntry
   ACCESS     not-accessible
   STATUS     mandatory
   DESCRIPTION
     "This attribute group contains the provisionable attributes of the Tpm 
      component at this interface."
::= { mscFrNniCaTpm 10 }

mscFrNniCaTpmProvEntry OBJECT-TYPE
   SYNTAX     MscFrNniCaTpmProvEntry
   ACCESS     not-accessible
   STATUS     mandatory
   DESCRIPTION
     "An entry in the mscFrNniCaTpmProvTable."
   INDEX {
      mscFrNniIndex,
      mscFrNniCaIndex,
      mscFrNniCaTpmIndex }
::= { mscFrNniCaTpmProvTable 1 }

MscFrNniCaTpmProvEntry ::= SEQUENCE {
   mscFrNniCaTpmAssignedIngressBandwidthPool
      Unsigned32,
   mscFrNniCaTpmAssignedEgressBandwidthPool
      Unsigned32 }

mscFrNniCaTpmAssignedIngressBandwidthPool OBJECT-TYPE
   SYNTAX     Unsigned32 (0..15 | 16)
   ACCESS     read-write
   STATUS     mandatory
   DESCRIPTION
     "This attribute specifies the ingress bandwidth pool which is used to 
      support this transfer priority at this interface. When this attribute is 
      set to sameAsModule, the bandwidth pool that is used is obtained 
      from the  assignedIngressBandwidthPool attribute under the Mod 
      Frs DprsNet Tpm/n component.

      VALUES (

      16 = sameAsModule

      )"
   DEFVAL     { 16 }
::= { mscFrNniCaTpmProvEntry 2 }

mscFrNniCaTpmAssignedEgressBandwidthPool OBJECT-TYPE
   SYNTAX     Unsigned32 (0..15 | 16)
   ACCESS     read-write
   STATUS     mandatory
   DESCRIPTION
     "This attribute specifies the egress bandwidth pool which is used to 
      support this transfer priority at this interface. When this attribute is 
      set to sameAsModule, the bandwidth pool that is used is obtained 
      from the assignedEgressBandwidthPool attribute under the Mod 
      Frs DprsNet Tpm/n component.

      VALUES (

      16 = sameAsModule

      )"
   DEFVAL     { 16 }
::= { mscFrNniCaTpmProvEntry 3 }




-- 
-- Version and Compliance statements
-- 



-- Object-Group Statement:
-- A list of all current accessible leaf objects.

-- OBJECTS { mscFrNniVFramerStorageType,
--           mscFrNniDnaDefaultTransferPriority,
--           mscFrNniSigDlciCollisions,
--           mscFrNniCaEgCirPoolAdmitBwValue,
--           mscFrNniDlciVcCalledLcn,
--           mscFrNniDlciTotalEgressSegFrm,
--           mscFrNniDnaHgMAvailableDlcis,
--           mscFrNniNumberOfEmissionQs,
--           mscFrNniDlciEgressSpMeasurementInterval,
--           mscFrNniVFramerAdminState,
--           mscFrNniDlciSpExcessBurstSize,
--           mscFrNniDlciCallReference,
--           mscFrNniLtsTimeInterval,
--           mscFrNniDlciVcRowStatus,
--           mscFrNniVFramerOctetFromOtherVFramer,
--           mscFrNniSigSetupTimeout,
--           mscFrNniDlciDiscCongestedFromIfBytes,
--           mscFrNniLmiRowStatus,
--           mscFrNniDlciCallState,
--           mscFrNniDlciEirIngressBytes,
--           mscFrNniSigProtocolErrors,
--           mscFrNniCaEgCirPoolAvailBwValue,
--           mscFrNniDlciDcCugIndex,
--           mscFrNniUnknownDlciFramesFromIf,
--           mscFrNniSigDefaultAccounting,
--           mscFrNniDlciVcCombErrorsFromSubnet,
--           mscFrNniLmiProtocolErrors,
--           mscFrNniDlciVcSegmentsRx,
--           mscFrNniFramerFrmFromIf64,
--           mscFrNniSigDefaultCommittedBurstSize,
--           mscFrNniDlciDeBytesToIf,
--           mscFrNniLmiEventCount,
--           mscFrNniFramerCrcErrors,
--           mscFrNniCaNumberRejectedEgressCirPermConn,
--           mscFrNniLtsPatNumFrames,
--           mscFrNniDlciUnknownStatus,
--           mscFrNniSigIdleProbeTimer,
--           mscFrNniDlciEgressSpStorageType,
--           mscFrNniSigCurrentNumberOfSvcCalls,
--           mscFrNniSnmpOperStatus,
--           mscFrNniIfIndex,
--           mscFrNniDlciErrorShortBytesFromIf,
--           mscFrNniSigOutCalls,
--           mscFrNniLtsPatStorageType,
--           mscFrNniLmiLinkVerificationTimer,
--           mscFrNniDlciEgressSpCommittedBurstSize,
--           mscFrNniDlciErrorShortFrmFromIf,
--           mscFrNniDlciDcDeDiscardPriority,
--           mscFrNniLtsPatDefaultUseBadLrc,
--           mscFrNniLmiUnexpectedReports,
--           mscFrNniDlciSpRateAdaptation,
--           mscFrNniDnaHgMAvailabilityUpdateThreshold,
--           mscFrNniCaTpmAssignedEgressBandwidthPool,
--           mscFrNniDlciVcCallingLcn,
--           mscFrNniVFramerFrmToOtherVFramer,
--           mscFrNniDnaAccountClass,
--           mscFrNniDlciDcDataPath,
--           mscFrNniSigDefaultExcessBurstSize,
--           mscFrNniDlciDiscardedSegFrm,
--           mscFrNniLtsPatDefaultHeaderLength,
--           mscFrNniDlciDeFrmToIf,
--           mscFrNniSigInCallsRefused,
--           mscFrNniRowStatus,
--           mscFrNniDnaHgMRowStatus,
--           mscFrNniFramerNonOctetErrors,
--           mscFrNniDlciVcDuplicatesFromSubnet,
--           mscFrNniDlciVcOutOfRangeFrmFromSubnet,
--           mscFrNniDlciVcOoSeqPktCntExceeded,
--           mscFrNniSigStatusEnqTimer,
--           mscFrNniCaNumberRejectedEgressEirPermConn,
--           mscFrNniSigIFramesTransmitted,
--           mscFrNniDlciEgressSpExcessBurstSize,
--           mscFrNniDlciDiscExcessFromIf,
--           mscFrNniLtsPatFramePattern,
--           mscFrNniLmiFullStatusToIf,
--           mscFrNniOperationalState,
--           mscFrNniDlciDiscDeCongestedToIfBytes,
--           mscFrNniDlciEirEgressSegFrm,
--           mscFrNniDnaAccountCollection,
--           mscFrNniCaLinkRate,
--           mscFrNniSigHighestPvcDlci,
--           mscFrNniDnaDataPath,
--           mscFrNniLtsPatDefaultEABits,
--           mscFrNniDlciCallType,
--           mscFrNniAvailabilityStatus,
--           mscFrNniFramerOctetFromIf64,
--           mscFrNniDlciFciFromSubnet,
--           mscFrNniSigCurrentState,
--           mscFrNniCaIngEirBpValue,
--           mscFrNniDlciCirPresent,
--           mscFrNniSigDefaultCommittedInformationRate,
--           mscFrNniLmiNetworkSideEventHistory,
--           mscFrNniDnaRowStatus,
--           mscFrNniFramerDataInversion,
--           mscFrNniVFramerOtherVirtualFramer,
--           mscFrNniFramerUnderruns,
--           mscFrNniDlciLbRowStatus,
--           mscFrNniDlciSpUpdateBCI,
--           mscFrNniDnaHgMHgAddrRowStatus,
--           mscFrNniDnaTransferPriorityOverRide,
--           mscFrNniDlciTransferPriToNwk,
--           mscFrNniDlciSpComponentName,
--           mscFrNniDnaNumberingPlanIndicator,
--           mscFrNniDnaServiceExchange,
--           mscFrNniLtsElapsedGenerationTime,
--           mscFrNniDlciEgressSpCommittedInformationRate,
--           mscFrNniSigNetworkType,
--           mscFrNniLtsPatPayloadPattern,
--           mscFrNniDnaHgMHgAddrNumberingPlanIndicator,
--           mscFrNniDlciDiscardedBytes,
--           mscFrNniDlciVcElapsedTimeTillNow,
--           mscFrNniDlciComponentName,
--           mscFrNniDlciVcPeakOoSeqPktCount,
--           mscFrNniCaIngressMaximumEirOnlyCalls,
--           mscFrNniDlciABitReasonFromIf,
--           mscFrNniSigDefaultMaximumFrameSize,
--           mscFrNniFramerComponentName,
--           mscFrNniCaEgressApplyToCos,
--           mscFrNniDlciLbLocalDeBytes,
--           mscFrNniVFramerRowStatus,
--           mscFrNniDlciDiscCongestedFromIf,
--           mscFrNniDlciLbLocalDeFrm,
--           mscFrNniDlciDeFrmFromIf,
--           mscFrNniLtsPatDefaultDataSize,
--           mscFrNniLmiFullStatusEnqFromIf,
--           mscFrNniDlciVcEmissionPriorityFromNetwork,
--           mscFrNniDlciOperationalState,
--           mscFrNniSigCurrentQueueSize,
--           mscFrNniSigQualityOfServiceNotAvailable,
--           mscFrNniDlciDcStorageType,
--           mscFrNniLmiUnexpectedIes,
--           mscFrNniDlciVcCallingDna,
--           mscFrNniDlciExcessBytesFromIf,
--           mscFrNniDlciVcPeakOoSeqFrmForwarded,
--           mscFrNniLtsCycleIncomplete,
--           mscFrNniDlciVcFrmCongestedToSubnet,
--           mscFrNniDlciExcessFrmFromIf,
--           mscFrNniDlciLocalRateAdaptOccurred,
--           mscFrNniDnaHgMAvailableAggregateCir64,
--           mscFrNniDlciVcPriority,
--           mscFrNniVFramerOperationalState,
--           mscFrNniSigComponentName,
--           mscFrNniSigIFramesRcvdDiscarded,
--           mscFrNniDlciBecnFrmToIf,
--           mscFrNniLtsPatDefaultNumFrames,
--           mscFrNniLmiComponentName,
--           mscFrNniLmiErrorEventThreshold,
--           mscFrNniLastUnknownDlci,
--           mscFrNniLtsStorageType,
--           mscFrNniDlciLbRemoteFecnFrm,
--           mscFrNniLmiProcedures,
--           mscFrNniLtsPatDefaultDlci,
--           mscFrNniDlciRateAdaptReductPeriod,
--           mscFrNniDlciControlStatus,
--           mscFrNniSigLastStateChangeReason,
--           mscFrNniDlciDcRowStatus,
--           mscFrNniDlciEgressSpRowStatus,
--           mscFrNniDlciVcDmepValue,
--           mscFrNniCaIngCirBPValue,
--           mscFrNniLtsPatRowStatus,
--           mscFrNniLtsPatDataSize,
--           mscFrNniDlciDcMapIpCosToFrQos,
--           mscFrNniDlciUsageState,
--           mscFrNniIfAdminStatus,
--           mscFrNniDlciVcSegmentsSent,
--           mscFrNniCaMaximumBandwidthPerCall,
--           mscFrNniDlciDcComponentName,
--           mscFrNniVFramerLogicalProcessor,
--           mscFrNniLtsPatHeaderBits,
--           mscFrNniLmiOpProcedures,
--           mscFrNniCaStorageType,
--           mscFrNniCaTpmAssignedIngressBandwidthPool,
--           mscFrNniDlciLoopbackState,
--           mscFrNniDlciBciFromSubnet,
--           mscFrNniDlciVcFastSelectCall,
--           mscFrNniDlciVcComponentName,
--           mscFrNniSigFrmrReceive,
--           mscFrNniDlciStartTime,
--           mscFrNniFramerAdminState,
--           mscFrNniDlciDiscDeCongestedToIf,
--           mscFrNniFramerLrcErrors,
--           mscFrNniSigCallProceedingTimer,
--           mscFrNniSigAckTimeout,
--           mscFrNniLtsPatRfc1490Header,
--           mscFrNniDlciABitStatusToIf,
--           mscFrNniDlciEmissionPriorityToIf,
--           mscFrNniDlciVcSendSequenceNumber,
--           mscFrNniLmiUsageState,
--           mscFrNniLtsBitRateTx,
--           mscFrNniCaIngEirPoolAdmitBwValue,
--           mscFrNniDnaEgressAccounting,
--           mscFrNniDlciDcRemoteNpi,
--           mscFrNniDlciVcState,
--           mscFrNniLtsGeneratorState,
--           mscFrNniSigDlciAllocation,
--           mscFrNniSigLastClearRemoteDataNetworkAddress,
--           mscFrNniDlciLbRemoteDeBytes,
--           mscFrNniCaIngCirPoolAdmitBwValue,
--           mscFrNniDlciLbRemoteDeFrm,
--           mscFrNniDlciDiscDeCongestedFromIfBytes,
--           mscFrNniDlciDcRemoteDna,
--           mscFrNniDlciProceduralStatus,
--           mscFrNniControlStatus,
--           mscFrNniDlciSpMeasurementInterval,
--           mscFrNniLmiNoStatusReportCount,
--           mscFrNniFramerOverruns,
--           mscFrNniDlciVcCalledNpi,
--           mscFrNniDlciTotalEgressBytes,
--           mscFrNniDlciBytesToIf,
--           mscFrNniDlciVcNotDataXferToSubnet,
--           mscFrNniDlciFrmToIf,
--           mscFrNniLmiSequenceErrors,
--           mscFrNniCaIngCirPoolAvailBwValue,
--           mscFrNniDlciMeasurementInterval,
--           mscFrNniCustomerIdentifier,
--           mscFrNniSigStateChange,
--           mscFrNniComponentName,
--           mscFrNniDlciVcRcosToNetwork,
--           mscFrNniDnaHgMComponentName,
--           mscFrNniLmiStatusSequenceErrors,
--           mscFrNniSigRaSensitivity,
--           mscFrNniCaEgEirPoolAdmitBwValue,
--           mscFrNniDlciDeBytesFromIf,
--           mscFrNniDlciTransferPriFromNwk,
--           mscFrNniDlciEirPresent,
--           mscFrNniDlciEirEgressBytes,
--           mscFrNniInvalidHeaderFramesFromIf,
--           mscFrNniDlciSpStorageType,
--           mscFrNniDlciFecnFrmFromIf,
--           mscFrNniDlciSpAccounting,
--           mscFrNniSigIFramesReceived,
--           mscFrNniLtsPatUseBadLrc,
--           mscFrNniLmiCheckPointTimer,
--           mscFrNniDlciSpCommittedBurstSize,
--           mscFrNniDlciStandbyStatus,
--           mscFrNniLmiUserSideEventHistory,
--           mscFrNniSigLastCauseInStatusMsgReceived,
--           mscFrNniLmiKeepAliveStatusToIf,
--           mscFrNniDlciStorageType,
--           mscFrNniDlciAccounting,
--           mscFrNniLmiFullStatusPollingCycles,
--           mscFrNniDlciSpRaSensitivity,
--           mscFrNniFramerStorageType,
--           mscFrNniDlciCallRefNumber,
--           mscFrNniSigRateAdaptation,
--           mscFrNniDlciCommittedBurstSize,
--           mscFrNniDlciVcStartTime,
--           mscFrNniDlciSpRateEnforcement,
--           mscFrNniDlciAdminState,
--           mscFrNniDlciVcDiagnosticCode,
--           mscFrNniLtsAlgorithm,
--           mscFrNniCaTpmComponentName,
--           mscFrNniLtsPatLoad,
--           mscFrNniDnaComponentName,
--           mscFrNniFramerNormPrioLinkUtilToIf,
--           mscFrNniLmiAsyncStatusReport,
--           mscFrNniLtsPatDefaultPayloadPattern,
--           mscFrNniFramerLargeFrmErrors,
--           mscFrNniLtsRowStatus,
--           mscFrNniFrmToIfByQueueValue,
--           mscFrNniDlciLbComponentName,
--           mscFrNniDnaHgMHgAddrComponentName,
--           mscFrNniDlciLbLocalBecnFrm,
--           mscFrNniDlciVcType,
--           mscFrNniDlciBecnFrmFromIf,
--           mscFrNniCaIngEirPoolAvailBwValue,
--           mscFrNniDlciVcAccountingEnabled,
--           mscFrNniDlciVcFrmLossTimeouts,
--           mscFrNniSigStorageType,
--           mscFrNniDlciDcDiscardPriority,
--           mscFrNniCaEgEirPoolAvailBwValue,
--           mscFrNniCaComponentName,
--           mscFrNniDlciVcPreviousState,
--           mscFrNniDlciVcPeakRetryQueueSize,
--           mscFrNniSigCallSetupTimer,
--           mscFrNniUsageState,
--           mscFrNniDlciDcTransferPriority,
--           mscFrNniLmiStorageType,
--           mscFrNniLmiKeepAliveStatusEnqFromIf,
--           mscFrNniSigAdminState,
--           mscFrNniDlciExcessBurstSize,
--           mscFrNniSigLastClearCause,
--           mscFrNniDnaDataNetworkAddress,
--           mscFrNniVFramerComponentName,
--           mscFrNniLmiAdminState,
--           mscFrNniCaRowStatus,
--           mscFrNniSigRateEnforcement,
--           mscFrNniSigUsageState,
--           mscFrNniLtsPatDlci,
--           mscFrNniDnaHgMHgAddrDataNetworkAddress,
--           mscFrNniDlciVcEmissionPriorityToNetwork,
--           mscFrNniDlciAlarmStatus,
--           mscFrNniDnaOutDefaultPriority,
--           mscFrNniDnaOutDefaultPathReliability,
--           mscFrNniDlciVcPathReliability,
--           mscFrNniDlciVcCannotForwardToSubnet,
--           mscFrNniDlciLbLocalTotalBytes,
--           mscFrNniSigAckDelayTimer,
--           mscFrNniCaTpmRowStatus,
--           mscFrNniLtsFrameRateTx,
--           mscFrNniSigUpdateBCI,
--           mscFrNniDlciElapsedDifference,
--           mscFrNniDlciDiscCongestedToIfBytes,
--           mscFrNniDlciRateAdaptReduct,
--           mscFrNniSigLastDlciReceivedStatus,
--           mscFrNniLtsPatHeaderLength,
--           mscFrNniFramerFlagsBetweenFrames,
--           mscFrNniDlciSpCommittedInformationRate,
--           mscFrNniDlciDcCugType,
--           mscFrNniDlciSpMaximumFrameSize,
--           mscFrNniCaEgEirBpValue,
--           mscFrNniLtsFramesTx,
--           mscFrNniFramerFrameCrcType,
--           mscFrNniDlciDiscDeCongestedFromIf,
--           mscFrNniDlciVcStorageType,
--           mscFrNniUnknownStatus,
--           mscFrNniDlciCommittedInformationRate,
--           mscFrNniSigIFramesTxDiscarded,
--           mscFrNniFramerFrmToIf64,
--           mscFrNniDlciABitStatusFromIf,
--           mscFrNniCaIngressApplyToCos,
--           mscFrNniDlciVcAccountingEnd,
--           mscFrNniDlciEgressSpComponentName,
--           mscFrNniSigLastStateInStatusMsgReceived,
--           mscFrNniLtsBytesTx,
--           mscFrNniProceduralStatus,
--           mscFrNniLmiIgnoreActiveBit,
--           mscFrNniOctetToIfByQueueValue,
--           mscFrNniCaEgCirBpValue,
--           mscFrNniLtsPatComponentName,
--           mscFrNniLtsPatHdlcBitsInserted,
--           mscFrNniDlciVcMaxSubnetPktSize,
--           mscFrNniDlciVcPreviousDiagnosticCode,
--           mscFrNniSigLastDiagnosticCode,
--           mscFrNniCaEgressMaximumEirOnlyCalls,
--           mscFrNniLtsPatEaBits,
--           mscFrNniVFramerUsageState,
--           mscFrNniLtsPatDefaultHeaderBits,
--           mscFrNniSigBandwidthNotAvailableValue,
--           mscFrNniDlciMaximumFrameSize,
--           mscFrNniDlciFecnFrmToIf,
--           mscFrNniSigRestartRcvTimer,
--           mscFrNniLtsDuration,
--           mscFrNniCaOverrideLinkRate,
--           mscFrNniLmiPollingVerifTimeouts,
--           mscFrNniDlciLbRemoteTotalBytes,
--           mscFrNniDlciBytesFromIf,
--           mscFrNniDlciVcCallReferenceNumberDecimal,
--           mscFrNniDlciDcRemoteDlci,
--           mscFrNniDlciVcNotDataXferFromSubnet,
--           mscFrNniDlciLbRemoteTotalFrm,
--           mscFrNniDlciFrmFromIf,
--           mscFrNniDlciLbRemoteBecnFrm,
--           mscFrNniFramerUsageState,
--           mscFrNniLtsComponentName,
--           mscFrNniDlciSpRowStatus,
--           mscFrNniSigReleaseTimer,
--           mscFrNniDlciVcRcosFromNetwork,
--           mscFrNniStandbyStatus,
--           mscFrNniSigOutCallsFailed,
--           mscFrNniSigLastStateReceivedStatus,
--           mscFrNniStorageType,
--           mscFrNniDnaHgMStorageType,
--           mscFrNniDlciTotalIngressSegFrm,
--           mscFrNniLtsLoad,
--           mscFrNniDlciRowStatus,
--           mscFrNniDnaHgMMaximumAvailableAggregateCir64,
--           mscFrNniSigMaximumFrameSize,
--           mscFrNniDlciVcOoSeqByteCntExceeded,
--           mscFrNniSigRestartReqTimer,
--           mscFrNniDlciErrorLongBytesFromIf,
--           mscFrNniAdminState,
--           mscFrNniDlciVcPktRetryTimeouts,
--           mscFrNniFramerRowStatus,
--           mscFrNniDlciErrorLongFrmFromIf,
--           mscFrNniLtsLastActiveInterval,
--           mscFrNniDlciVcCalledDna,
--           mscFrNniVFramerFrmFromOtherVFramer,
--           mscFrNniDnaHgMAvailabilityDelta,
--           mscFrNniSigInCalls,
--           mscFrNniDlciVcSubnetRecoveries,
--           mscFrNniFramerNormPrioLinkUtilFromIf,
--           mscFrNniSigWindowSize,
--           mscFrNniDlciEirIngressSegFrm,
--           mscFrNniDlciLbLocalFecnFrm,
--           mscFrNniFramerInterfaceName,
--           mscFrNniDlciDiscExcessFromIfBytes,
--           mscFrNniDlciVcSegmentSize,
--           mscFrNniFramerOperationalState,
--           mscFrNniSigRowStatus,
--           mscFrNniFramerFrmModeErrors,
--           mscFrNniDlciLbLocalTotalFrm,
--           mscFrNniLmiProtocolStatus,
--           mscFrNniCaTpmStorageType,
--           mscFrNniDlciBecnFrmSetByService,
--           mscFrNniDlciVcCallingNpi,
--           mscFrNniDlciAvailabilityStatus,
--           mscFrNniDnaStorageType,
--           mscFrNniLtsBurstSize,
--           mscFrNniFramerAborts,
--           mscFrNniDlciVcDataPath,
--           mscFrNniDlciLbStorageType,
--           mscFrNniDnaHgMHgAddrStorageType,
--           mscFrNniSigAckTimer,
--           mscFrNniSigReceiveRejectFrame,
--           mscFrNniSigOperationalState,
--           mscFrNniAlarmStatus,
--           mscFrNniDlciABitReasonToIf,
--           mscFrNniDlciDcType,
--           mscFrNniDlciDiscFrameAbit,
--           mscFrNniLtsPatDefaultRfc1490Header,
--           mscFrNniDlciBciToSubnet,
--           mscFrNniDlciDiscCongestedToIf,
--           mscFrNniSigRemoteBusy,
--           mscFrNniLtsPatStatus,
--           mscFrNniLmiOperationalState,
--           mscFrNniSigRetransmitLimit,
--           mscFrNniDlciVcPeakOoSeqByteCount,
--           mscFrNniDlciDiscByteAbit,
--           mscFrNniDlciTotalIngressBytes }
-- STATUS  mandatory
-- DESCRIPTION
--   "A list of all current accessible leaf objects."

frameRelayNniGroup OBJECT IDENTIFIER ::= { frameRelayNniMIB 1 }
frameRelayNniGroupCA OBJECT IDENTIFIER ::= { frameRelayNniGroup 1 }
frameRelayNniGroupCA02 OBJECT IDENTIFIER ::= { frameRelayNniGroupCA 3 }
frameRelayNniGroupCA02A OBJECT IDENTIFIER ::= { frameRelayNniGroupCA02 2 }



-- Agent-Capabilities Statement:

-- PRODUCT-RELEASE "MscPassport Release 1.2 FrameRelayNni."
-- STATUS          mandatory
-- DESCRIPTION     "Carrier Passport FrameRelayNni MIB: MIB Version CA02A,
--                  Software Version CA02S9C."
-- SUPPORTS        Nortel-MsCarrier-MscPassport-FrameRelayNniMIB
--    INCLUDES     { frameRelayNniGroupCA02A }

frameRelayNniCapabilities OBJECT IDENTIFIER ::= { frameRelayNniMIB 3 }
frameRelayNniCapabilitiesCA OBJECT IDENTIFIER ::= { frameRelayNniCapabilities 1 }
frameRelayNniCapabilitiesCA02 OBJECT IDENTIFIER ::= { frameRelayNniCapabilitiesCA 3 }
frameRelayNniCapabilitiesCA02A OBJECT IDENTIFIER ::= { frameRelayNniCapabilitiesCA02 2 }





END
