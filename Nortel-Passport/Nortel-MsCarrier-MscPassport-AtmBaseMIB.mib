Nortel-MsCarrier-MscPassport-AtmBaseMIB
DEFINITIONS ::= BEGIN



IMPORTS

      OBJECT-TYPE
   FROM RFC-1212

      mscPassportMIBs
   FROM Nortel-MsCarrier-MscPassport-UsefulDefinitionsMIB

      DisplayString,
      StorageType,
      RowStatus,
      Gauge32,
      Integer32,
      Unsigned32
   FROM Nortel-MsCarrier-MscPassport-StandardTextualConventionsMIB

      NonReplicated,
      FixedPoint1
   FROM Nortel-MsCarrier-MscPassport-TextualConventionsMIB

      mscLpEng,
      mscLpIndex,
      mscLp,
      mscLpEngIndex
   FROM Nortel-MsCarrier-MscPassport-LogicalProcessorMIB;




-- LAST-UPDATED   "9909010000Z"
-- ORGANIZATION   "Nortel Networks"
-- CONTACT-INFO   "
--         Nortel Carrier Data Network Management
--         
--         Postal:       P.O. Box 3511, Station C 
--                       Ottawa, Ontario 
--                       Canada  K1Y 4H7
--         
--         via the WEB:  http://www.nortelnetworks.com  
--                       select 'Contact Us' from the menu
--          
--         via phone:    1-800-4NORTEL"
-- DESCRIPTION
--    "The module describing the Nortel MsCarrier MscPassport
--     AtmBase Enterprise MIB."

atmBaseMIB OBJECT IDENTIFIER ::= { mscPassportMIBs 63 }










-- Lp/n AtmResourceControl
-- The AtmResourceControl component is used to configure the usage 
-- of ATM-specific resources on a Logical Processor running ATM 
-- services. (This component is only permitted under Logical 
-- Processors which are linked to ATM card types.)

mscLpArc OBJECT IDENTIFIER ::= { mscLp 19 }



mscLpArcRowStatusTable OBJECT-TYPE
   SYNTAX     SEQUENCE OF MscLpArcRowStatusEntry
   ACCESS     not-accessible
   STATUS     obsolete
   DESCRIPTION
     "This entry controls the addition and deletion of 
      mscLpArc components."
::= { mscLpArc 1 }

mscLpArcRowStatusEntry OBJECT-TYPE
   SYNTAX     MscLpArcRowStatusEntry
   ACCESS     not-accessible
   STATUS     obsolete
   DESCRIPTION
     "A single entry in the table represents a single 
      mscLpArc component."
   INDEX {
      mscLpIndex,
      mscLpArcIndex }
::= { mscLpArcRowStatusTable 1 }

MscLpArcRowStatusEntry ::= SEQUENCE {
   mscLpArcRowStatus
      RowStatus,
   mscLpArcComponentName
      DisplayString,
   mscLpArcStorageType
      StorageType,
   mscLpArcIndex
      NonReplicated }

mscLpArcRowStatus OBJECT-TYPE
   SYNTAX     RowStatus 
   ACCESS     read-write
   STATUS     obsolete
   DESCRIPTION
     "This variable is used as the basis for SNMP naming of
      mscLpArc components.
      These components can be added and deleted."
::= { mscLpArcRowStatusEntry 1 }

mscLpArcComponentName OBJECT-TYPE
   SYNTAX     DisplayString 
   ACCESS     read-only
   STATUS     obsolete
   DESCRIPTION
     "This variable provides the component's string name for
      use with the ASCII Console Interface"
::= { mscLpArcRowStatusEntry 2 }

mscLpArcStorageType OBJECT-TYPE
   SYNTAX     StorageType 
   ACCESS     read-only
   STATUS     obsolete
   DESCRIPTION
     "This variable represents the storage type value for the
      mscLpArc tables."
::= { mscLpArcRowStatusEntry 4 }

mscLpArcIndex OBJECT-TYPE
   SYNTAX     NonReplicated 
   ACCESS     not-accessible
   STATUS     obsolete
   DESCRIPTION
     "This variable represents the index for the mscLpArc tables."
::= { mscLpArcRowStatusEntry 10 }

mscLpArcProvTable OBJECT-TYPE
   SYNTAX     SEQUENCE OF MscLpArcProvEntry
   ACCESS     not-accessible
   STATUS     obsolete
   DESCRIPTION
     "This group specifies the configuration of processor-wide ATM-
      specific resources on a Logical Processor running ATM services. 
      Note that altering any of these parameters will result in a card 
      reboot."
::= { mscLpArc 100 }

mscLpArcProvEntry OBJECT-TYPE
   SYNTAX     MscLpArcProvEntry
   ACCESS     not-accessible
   STATUS     obsolete
   DESCRIPTION
     "An entry in the mscLpArcProvTable."
   INDEX {
      mscLpIndex,
      mscLpArcIndex }
::= { mscLpArcProvTable 1 }

MscLpArcProvEntry ::= SEQUENCE {
   mscLpArcTotalConnectionPoolCapacity
      Unsigned32,
   mscLpArcMulticastBranchesCapacity
      Unsigned32,
   mscLpArcTxFrameMemoryAllocation
      Unsigned32,
   mscLpArcRxFrameMemoryAllocation
      Unsigned32,
   mscLpArcPerVcQueueInterfaces
      Unsigned32,
   mscLpArcShapingStackAllocation
      OCTET STRING,
   mscLpArcShapingScalingFactor
      FixedPoint1,
   mscLpArcCdvAttenuation
      INTEGER,
   mscLpArcPortAggregation
      INTEGER,
   mscLpArcSubConnectionPoolCapacity
      Unsigned32,
   mscLpArcLnnConnectionPoolCapacity
      Unsigned32 }

mscLpArcTotalConnectionPoolCapacity OBJECT-TYPE
   SYNTAX     Unsigned32 (0..10752)
   ACCESS     read-write
   STATUS     obsolete
   DESCRIPTION
     "This attribute is migrated to the Lp/n Eng Arc Ov attribute of the 
      same name.
      
      This attribute specifies the maximum number of connections (both 
      VCC and VPC) that can be enabled on the LogicalProcessor.
      
      If the LogicalProcessor is associated with a card of a cardType 
      other than one of the following: 3pE3Atm, 3pDS3Atm, 
      3pOC3MmAtm, 3pOC3SmAtm, 3pE1Atm, 3pDS1Atm, 
      2pJ6MAtm; the value of the attribute restricts the sum of the 
      (maxVccs + maxVpcs) across all AtmIfs bound to this 
      LogicalProcessor.
      
      If the LogicalProcessor is associated with a card of one of the 
      following cardTypes: 3pE3Atm, 3pDS3Atm, 3pOC3MmAtm, 
      3pOC3SmAtm, 3pE1Atm, 3pDS1Atm, 2pJ6MAtm; the number of 
      available connections are distributed equally across the ports on the 
      FP. The number of connections associated to a particular port will 
      limit the size of the Vcc space defined by the ConnMap of the AtmIf 
      linked to the port. Furthermore, the value of this attribute is 
      restricted based on the number of ports on the card. For one port 
      cards, the minimum is 512, the maximum is 4096 and the value 
      must be divisible by 256. For two port cards, the minimum is 1024, 
      the maximum is 8192 and the value must be divisible by 512. For 
      three port cards, the minimum is 1536, the maximum is 7680 and 
      the value must be divisible by 768.
      
      Increasing the value of this attribute reduces the CQM memory 
      available for cell and frame free list.
      
      This attribute must be set to 0 is the connectionPoolCapacity 
      attribute is set to non-zero values."
   DEFVAL     { 3072 }
::= { mscLpArcProvEntry 5 }

mscLpArcMulticastBranchesCapacity OBJECT-TYPE
   SYNTAX     Unsigned32 (0..10752)
   ACCESS     read-write
   STATUS     obsolete
   DESCRIPTION
     "This attribute is migrated to the Lp/n Eng Arc Ov attribute of the 
      same name.
      
      This attribute specifies the number of multicast branches that can be 
      enabled on the Logical Processor.
      
      A multicast branch is used for cell replication on a Vcc connection 
      whose Vcc distributionType is pointToMultipoint. A branch 
      represent one ATM destination for the replicated cells
      
      Increasing the value of this attribute reduces the CQM memory 
      available for the cell and frame free lists."
   DEFVAL     { 0 }
::= { mscLpArcProvEntry 6 }

mscLpArcTxFrameMemoryAllocation OBJECT-TYPE
   SYNTAX     Unsigned32 (0..100)
   ACCESS     read-write
   STATUS     obsolete
   DESCRIPTION
     "This attribute is migrated to the Lp/n Eng Arc Ov attribute 
      txCellMemoryAllocation. It is converted from frame percentage to 
      cell percentage by subtracting this value from 100.
      
      This attribute specifies the percentage of the transmit CQM memory 
      which should be allocated to the transmit frame free list on the 
      ATM-FP. The remaining transmit CQM memory is allocated to the 
      transmit cell free list. Frame memory is used for trunks, ATM VCC 
      testing and for inter-card communication. There is an absolute 
      minimum quantity of frame buffers which is required by ATM 
      software on the FP. If the value of this attribute is smaller than the 
      absolute minimum, the ATM software will allocate the minimum 
      required, rather than the actual number requested.
      
      The actual percentage of the transmit CQM memory allocated to the 
      transmit frame free list is indicated by the Aru 
      txFrameMemoryAllocation attribute. A difference between the 
      provisioned and the operational values may exist due to the 
      requirement for a minimum number of frame buffers or rounding 
      during computation within the FP."
   DEFVAL     { 50 }
::= { mscLpArcProvEntry 10 }

mscLpArcRxFrameMemoryAllocation OBJECT-TYPE
   SYNTAX     Unsigned32 (0..100)
   ACCESS     read-write
   STATUS     obsolete
   DESCRIPTION
     "This attribute is migrated to the Lp/n Eng Arc Ov attribute 
      rxCellMemoryAllocation. It is converted from frame percentage to 
      cell percentage by subtracting this value from 100.
      
      This attribute specifies the percentage of the receive CQM memory 
      which should be allocated to the receive frame free list on the ATM-
      FP. The remaining receive CQM memory is allocated to the receive 
      cell free list. Frame memory is used for trunks, ATM VCC testing 
      and for inter-card communication. There is an absolute minimum 
      quantity of frame buffers which is required by ATM software on the 
      FP. If the value of this attribute is smaller than the absolute 
      minimum, the ATM software will allocate the minimum required, 
      rather than the actual number requested. 
      
      The actual percentage of the receive CQM memory allocated to the 
      receive frame free list is indicated by the Aru 
      rxFrameMemoryAllocation attribute. A difference between the 
      provisioned and the operational values may exist due to the 
      requirement for a minimum number of frame buffers or rounding 
      during computation within the FP"
   DEFVAL     { 80 }
::= { mscLpArcProvEntry 20 }

mscLpArcPerVcQueueInterfaces OBJECT-TYPE
   SYNTAX     Unsigned32 (0..4)
   ACCESS     read-write
   STATUS     obsolete
   DESCRIPTION
     "This attribute is migrated to the Lp/n Eng Arc Cqc Ov attribute of 
      the same name.
      
      This attribute specifies the number of independent ports or IMA 
      components which support shaping and per-Vc queueing on the 
      LogicalProcessor. 
      
      When this attribute is not zero, at most 4 independent ports or 4 Ima 
      virtual links are supported, regardless of whether or not traffic 
      shaping is enabled on the associated AtmIf components. In this case 
      only independent port instances 0-3 or Ima instances 0-3 can be 
      supported on an associated AtmIf component.
      
      For 2 ports cards, the valid values for this attribute are 0, 1, or 2.
      For 3 ports cards, the valid values for this attribute are 0, 1, or 3.
      For 8 ports cards, the valid values for this attribute are 0, 1, 2, or 4."
   DEFVAL     { 0 }
::= { mscLpArcProvEntry 25 }

mscLpArcShapingStackAllocation OBJECT-TYPE
   SYNTAX     OCTET STRING (SIZE (1))
   ACCESS     read-write
   STATUS     obsolete
   DESCRIPTION
     "This attribute is migrated to the perVcQueueInterfaces attribute of 
      the Lp/n Eng Arc Cqc Ov. Value ~0,~1,~2 is migrated to the value 
      0; value 0,~1,~2 is migrated to value 1; value 0,1,~2 is migrated to 
      the value 2 and value 0,1,2 is migrated to the value 3 (for cardTypes 
      3pE3Atm, 3pDS3Atm, 3pOC3MmAtm, 3pOC3SmAtm, 3pE1Atm, 
      3pDS1Atm) or to the value 4 (for other cardTypes).
      
      This attribute specifies the allocation of shaping stack resources 
      among the ports on this FP. Shaping stacks can currently be 
      allocated on port 0, ports 0 and 1, or ports 0, 1 and 2. Allocating 
      shaping stacks on a port allows the use of traffic shaping and per-Vc 
      queueing on that port.

      Description of bits:
      n0(0)
      n1(1)
      n2(2)"
   DEFVAL     { '80'H }
::= { mscLpArcProvEntry 30 }

mscLpArcShapingScalingFactor OBJECT-TYPE
   SYNTAX     FixedPoint1 (10 | 14 | 20 | 28 | 40 | 56)
   ACCESS     read-write
   STATUS     obsolete
   DESCRIPTION
     "This attribute is migrated to the Lp/n Eng Arc Cqc Ov attribute of 
      the same name.
      
      This attribute specifies the scaling factor which is to be applied to 
      all shaping rates for this ATM-FP. The scaling factor is a 
      multiplicative factor which is applied to the chosen shaping rate to 
      produce an actual shaping rate. For example, if a shaping rate of 25 
      Mbps is used with a scaling factor of 2, the actual shaping rate is 
      12.5 Mbps."
   DEFVAL     { 10 }
::= { mscLpArcProvEntry 40 }

mscLpArcCdvAttenuation OBJECT-TYPE
   SYNTAX     INTEGER  {
                 off(0),
                 on(1) }
   ACCESS     read-write
   STATUS     obsolete
   DESCRIPTION
     "This attribute is migrated to the Lp/n Eng Arc Cqc Ov attribute 
      cdvReduction.
      
      This attribute enables the attenuation of the maximum Cell Delay 
      Variation (CDV) of shaped transmit traffic.
      
      When the value of this attribute is set to off, the CDV value can be 
      determined by the following equation:
      CDV <= 2/ASR + 1/LS
      where ASR is the Actual Shaping Rate of the connection and LS is 
      the Link Speed of the interface.
      
      When the value of this attribute is set to on, the CDV relationship 
      changes to the following equation:
      CDV <= 1/ASR + 1/LS
      
      As can be noted from the equations above, setting this attribute to 
      on can reduce the CDV significantly. CDV attenuation may be used 
      to conform to policers which have strict Cell Delay Variance 
      Tolerance (CDVT). However using this function reduces the 
      transmit bandwidth utilization of the following cards: 3pDS3Atm, 
      3pOC3Atm."
   DEFVAL     { off }
::= { mscLpArcProvEntry 41 }

mscLpArcPortAggregation OBJECT-TYPE
   SYNTAX     INTEGER  {
                 on(0),
                 off(1) }
   ACCESS     read-write
   STATUS     obsolete
   DESCRIPTION
     "This attribute is migrated to the Lp/n Eng Arc Cqc Ov attribute 
      portCongestionPolicy.
      
      This attribute specifies whether port aggregation is turned on or off 
      for this ATM-FP. It applies only to transmit traffic served on the 
      common queues and does not apply to perVc queues.
      
      When port aggregation is on, the enqueue decision of cells or 
      frames to a common queue is based upon the congestion state of the 
      entire port to which the queue belongs. A port is defined to be as 
      congested as the most congested queue amongst all its queues: the 
      low, medium and high emission priority queues. Thus, for example, 
      if the low priority queue is congested, the high priority queue will 
      also experience discards even though the high priority queue may 
      itself not be congested. Setting port aggregation on assures that the 
      low priority queues are also serviced in the event of congestion.
      
      When the value of this attribute is set to off, the enqueue decision of 
      cells or frames to a common queue is based solely upon the 
      congestion state of that queue, not the port. This setting assures that 
      the absolute priority of the traffic is taken into account, regardless of 
      whether or not the lower priority queues are being served."
   DEFVAL     { on }
::= { mscLpArcProvEntry 42 }

mscLpArcSubConnectionPoolCapacity OBJECT-TYPE
   SYNTAX     Unsigned32 (1..8192)
   ACCESS     read-write
   STATUS     obsolete
   DESCRIPTION
     "This attribute is migrated to the Lp/n Eng Fcrc Ov attribute of the 
      same name.
      
      This attribute specifies the maximum number of sub-connections 
      for the LogicalProcessor. 
      
      A sub-connection is used for interworking the ATM services with 
      the frame oriented services such as Frame Relay, and Path Oriented 
      Routing System (PORS). When a frame is received at a sub-
      connection, the frame header is modified to be compatible with the 
      service it is to be forwarded to.
      
      Due to limited resources, not all of the provisioned number of sub-
      connections may be allocated. The actual number of sub-
      connections allocated is indicated by the sum of Aru 
      subConnectionPoolAvailable and Aru SubConnectionPoolUsage 
      attributes. 
      
      This pool is used for connection oriented services only. Each of the 
      following components uses one sub-connection from this pool: 
      FrAtm/x Dlci/y Siwf
      McsMgr Frf5EpG/x Frf5Ep/y Lmi
      McsMgr Frf5EpG/x Frf5Ep/y Dlci/z
      
      When the sub-connection pool is exhausted, no more connections 
      will be accepted from the services which utilize this pool."
   DEFVAL     { 1024 }
::= { mscLpArcProvEntry 43 }

mscLpArcLnnConnectionPoolCapacity OBJECT-TYPE
   SYNTAX     Unsigned32 (1..512)
   ACCESS     read-write
   STATUS     obsolete
   DESCRIPTION
     "This attribute is migrated to the Lp/n Eng Fcrc Ov attribute of the 
      same name.
      
      This attribute specifies the maximum number of resource records 
      for the connections which utilize Logical Network Number (LNN) 
      on the LogicalProcessor.
      
      A logical network is a subset of passport modules together with a 
      subset of trunks that interconnect those modules. It carries the 
      traffic for a defined set of network protocols. A LNN is used to 
      identify a logical network. The connectionless services which 
      utilize the logical networks require some processing at the 
      intermediate nodes. This pool is allocated at the intermediate nodes 
      to sustain these connectionless services.
      
      Due to limited resources, not all of the provisioned number of LNN 
      connection resource records may be allocated. The actual number of 
      resource records allocated is indicated by the sum of Aru 
      lnnConnectionPoolAvailable and Aru lnnConnectionPoolUsage 
      attributes.
      
      If the McsMgr DprsMcsEpG/x Ep/y EpD 
      transportConnectionPreference attribute is set to atmOnly, each 
      instance of the McsMgr DprsMcsEpG/x Ep/y component uses one 
      resource record from this pool."
   DEFVAL     { 128 }
::= { mscLpArcProvEntry 44 }

mscLpArcConnCapTable OBJECT-TYPE
   SYNTAX     SEQUENCE OF MscLpArcConnCapEntry
   ACCESS     not-accessible
   STATUS     obsolete
   DESCRIPTION
     "This attribute is migrated to the Lp/n Eng Arc Cqc Ov attribute of 
      the same name.
      
      This attribute is provided for backward compatibility and can only 
      be used if the LogicalProcessor is associated to a card of one of the 
      following cardType: 3pE3Atm, 3pDS3Atm, 3pOC3MmAtm, 
      3pOC3SmAtm, 3pE1Atm, 3pDS1Atm, 2pJ6MAtm. This attribute 
      can be used when the desired distribution of connections across 
      ports cannot be achieved using the totalConnectionPoolCapacity 
      attribute.
      
      This attribute defines the maximum number of connections (both 
      VCC and VPC) that are available on each port. The entries are 
      indexed by port number. This number limits the range of the 
      ConnMap entries. Note that the value of this attribute must be 
      evenly divisible by 256, and that port 2 supports at most 2560 
      connections, not the full 4096."
::= { mscLpArc 291 }

mscLpArcConnCapEntry OBJECT-TYPE
   SYNTAX     MscLpArcConnCapEntry
   ACCESS     not-accessible
   STATUS     obsolete
   DESCRIPTION
     "An entry in the mscLpArcConnCapTable."
   INDEX {
      mscLpIndex,
      mscLpArcIndex,
      mscLpArcConnCapIndex }
::= { mscLpArcConnCapTable 1 }

MscLpArcConnCapEntry ::= SEQUENCE {
   mscLpArcConnCapIndex
      Integer32,
   mscLpArcConnCapValue
      Unsigned32 }

mscLpArcConnCapIndex OBJECT-TYPE
   SYNTAX     Integer32 (0..2)
   ACCESS     not-accessible
   STATUS     obsolete
   DESCRIPTION
     "This variable represents the mscLpArcConnCapTable
      specific index for the mscLpArcConnCapTable."
::= { mscLpArcConnCapEntry 1 }

mscLpArcConnCapValue OBJECT-TYPE
   SYNTAX     Unsigned32 (0 | 512..4096)
   ACCESS     read-write
   STATUS     obsolete
   DESCRIPTION
     "This variable represents an individual value for the
      mscLpArcConnCapTable."
::= { mscLpArcConnCapEntry 2 }


-- Lp/n AtmResourceUsage
-- The AtmResourceUsage component describes the usage of ATM-
-- specific resources on a LogicalProcessor running ATM services. 
-- This component is always dynamically created under the LP which 
-- supports an ATM-FP. 

mscLpAru OBJECT IDENTIFIER ::= { mscLp 20 }



mscLpAruRowStatusTable OBJECT-TYPE
   SYNTAX     SEQUENCE OF MscLpAruRowStatusEntry
   ACCESS     not-accessible
   STATUS     obsolete
   DESCRIPTION
     "This entry controls the addition and deletion of 
      mscLpAru components."
::= { mscLpAru 1 }

mscLpAruRowStatusEntry OBJECT-TYPE
   SYNTAX     MscLpAruRowStatusEntry
   ACCESS     not-accessible
   STATUS     obsolete
   DESCRIPTION
     "A single entry in the table represents a single 
      mscLpAru component."
   INDEX {
      mscLpIndex,
      mscLpAruIndex }
::= { mscLpAruRowStatusTable 1 }

MscLpAruRowStatusEntry ::= SEQUENCE {
   mscLpAruRowStatus
      RowStatus,
   mscLpAruComponentName
      DisplayString,
   mscLpAruStorageType
      StorageType,
   mscLpAruIndex
      NonReplicated }

mscLpAruRowStatus OBJECT-TYPE
   SYNTAX     RowStatus 
   ACCESS     read-only
   STATUS     obsolete
   DESCRIPTION
     "This variable is used as the basis for SNMP naming of
      mscLpAru components.
      These components cannot be added nor deleted."
::= { mscLpAruRowStatusEntry 1 }

mscLpAruComponentName OBJECT-TYPE
   SYNTAX     DisplayString 
   ACCESS     read-only
   STATUS     obsolete
   DESCRIPTION
     "This variable provides the component's string name for
      use with the ASCII Console Interface"
::= { mscLpAruRowStatusEntry 2 }

mscLpAruStorageType OBJECT-TYPE
   SYNTAX     StorageType 
   ACCESS     read-only
   STATUS     obsolete
   DESCRIPTION
     "This variable represents the storage type value for the
      mscLpAru tables."
::= { mscLpAruRowStatusEntry 4 }

mscLpAruIndex OBJECT-TYPE
   SYNTAX     NonReplicated 
   ACCESS     not-accessible
   STATUS     obsolete
   DESCRIPTION
     "This variable represents the index for the mscLpAru tables."
::= { mscLpAruRowStatusEntry 10 }

mscLpAruOperTable OBJECT-TYPE
   SYNTAX     SEQUENCE OF MscLpAruOperEntry
   ACCESS     not-accessible
   STATUS     obsolete
   DESCRIPTION
     "This group describes the usage of ATM-specific resources on a 
      Logical Processor running ATM services."
::= { mscLpAru 100 }

mscLpAruOperEntry OBJECT-TYPE
   SYNTAX     MscLpAruOperEntry
   ACCESS     not-accessible
   STATUS     obsolete
   DESCRIPTION
     "An entry in the mscLpAruOperTable."
   INDEX {
      mscLpIndex,
      mscLpAruIndex }
::= { mscLpAruOperTable 1 }

MscLpAruOperEntry ::= SEQUENCE {
   mscLpAruTotalConnectionPoolUsage
      Unsigned32,
   mscLpAruMulticastBranchesUsage
      Unsigned32,
   mscLpAruTxCellBlockCapacity
      Unsigned32,
   mscLpAruTxCellBlockUsage
      Gauge32,
   mscLpAruTxCellFreeListSize
      Unsigned32,
   mscLpAruTxCellFreeListCongestionState
      INTEGER,
   mscLpAruTxFrameMemoryAllocation
      Unsigned32,
   mscLpAruTxFrameBlockCapacity
      Unsigned32,
   mscLpAruTxFrameBlockUsage
      Gauge32,
   mscLpAruTxFrameFreeListSize
      Unsigned32,
   mscLpAruTxFrameFreeListCongestionState
      INTEGER,
   mscLpAruRxCellBlockCapacity
      Unsigned32,
   mscLpAruRxCellBlockUsage
      Gauge32,
   mscLpAruRxCellFreeListSize
      Unsigned32,
   mscLpAruRxCellFreeListCongestionState
      INTEGER,
   mscLpAruRxFrameMemoryAllocation
      Unsigned32,
   mscLpAruRxFrameBlockCapacity
      Unsigned32,
   mscLpAruRxFrameBlockUsage
      Gauge32,
   mscLpAruRxFrameFreeListSize
      Unsigned32,
   mscLpAruRxFrameFreeListCongestionState
      INTEGER,
   mscLpAruSubConnectionPoolAvailable
      Unsigned32,
   mscLpAruSubConnectionPoolUsage
      Unsigned32,
   mscLpAruLnnConnectionPoolAvailable
      Unsigned32,
   mscLpAruLnnConnectionPoolUsage
      Unsigned32 }

mscLpAruTotalConnectionPoolUsage OBJECT-TYPE
   SYNTAX     Unsigned32 (0..10752)
   ACCESS     read-only
   STATUS     obsolete
   DESCRIPTION
     "If the LogicalProcessor is associated with a card of a cardType 
      other than 4pE1Aal1 or 4pDS1Aal1, this attribute indicates the total 
      number of enabled VCCs and VPCs in AtmIfs associated with this 
      LogicalProcessor. An example of a VCC not in the enabled state is 
      a VCC with a Test subcomponent. This attribute is equal to the sum 
      of the AtmIf Ca connectionPoolUsage attributes of AtmIfs 
      associated with this LogicalProcessor.
      
      If the LogicalProcessor is associated with a card of cardType 
      4pE1Aal1 or 4pDS1Aal1, this attribute indicates the total number 
      of Ces components associated with this LogicalProcessor."
::= { mscLpAruOperEntry 5 }

mscLpAruMulticastBranchesUsage OBJECT-TYPE
   SYNTAX     Unsigned32 (0..10752)
   ACCESS     read-only
   STATUS     obsolete
   DESCRIPTION
     "This attribute indicates the total number of multicast branches that 
      are active on the Logical Processor."
::= { mscLpAruOperEntry 6 }

mscLpAruTxCellBlockCapacity OBJECT-TYPE
   SYNTAX     Unsigned32 (0..8192)
   ACCESS     read-only
   STATUS     obsolete
   DESCRIPTION
     "This attribute indicates the amount of memory reserved for storing 
      ATM cells to be transmitted by the Lp."
::= { mscLpAruOperEntry 10 }

mscLpAruTxCellBlockUsage OBJECT-TYPE
   SYNTAX     Gauge32 (0..8192)
   ACCESS     read-only
   STATUS     obsolete
   DESCRIPTION
     "This attribute indicates the amount of memory currently being used 
      to store ATM cells to be transmitted by the Lp."
::= { mscLpAruOperEntry 20 }

mscLpAruTxCellFreeListSize OBJECT-TYPE
   SYNTAX     Unsigned32 (0..16383)
   ACCESS     read-only
   STATUS     obsolete
   DESCRIPTION
     "This attribute indicates the current size of the transmit cell free list. 
      The transmit cell free list is the memory available for storing ATM 
      cells to be transmitted by the Lp."
::= { mscLpAruOperEntry 23 }

mscLpAruTxCellFreeListCongestionState OBJECT-TYPE
   SYNTAX     INTEGER (0..3)
   ACCESS     read-only
   STATUS     obsolete
   DESCRIPTION
     "This attribute indicates the congestion state of the transmit cell free 
      list on this ATM-FP. 
      
      The congestion state of a free list is indicated by a numeric value 
      ranging from 0 to 3. When a free list is in a congested state x, only 
      traffic with discard priority (DP) 0 to x will be stored. Traffic with 
      DP > x will be discarded. 
      
      Therefore, if the congestion state is 3, there is no congestion and all 
      traffic is stored. Likewise, when the congestion state is 0, there is 
      maximum congestion and only traffic with DP=0 will be stored."
::= { mscLpAruOperEntry 26 }

mscLpAruTxFrameMemoryAllocation OBJECT-TYPE
   SYNTAX     Unsigned32 (0..100)
   ACCESS     read-only
   STATUS     obsolete
   DESCRIPTION
     "This attribute defines the percentage of the transmit CQM memory 
      which is allocated to the transmit frame free list on the ATM-FP. 
      The remaining transmit CQM memory is allocated to the transmit 
      cell free list. Frame memory is used for trunks, ATM Vcc testing 
      and for inter-card communication."
::= { mscLpAruOperEntry 30 }

mscLpAruTxFrameBlockCapacity OBJECT-TYPE
   SYNTAX     Unsigned32 (0..8192)
   ACCESS     read-only
   STATUS     obsolete
   DESCRIPTION
     "This attribute indicates the amount of memory reserved for storing 
      frames to be transmitted by the Lp."
::= { mscLpAruOperEntry 40 }

mscLpAruTxFrameBlockUsage OBJECT-TYPE
   SYNTAX     Gauge32 (0..8192)
   ACCESS     read-only
   STATUS     obsolete
   DESCRIPTION
     "This attribute indicates the amount of memory currently being used 
      to store frames to be transmitted by the Lp."
::= { mscLpAruOperEntry 50 }

mscLpAruTxFrameFreeListSize OBJECT-TYPE
   SYNTAX     Unsigned32 (0..16383)
   ACCESS     read-only
   STATUS     obsolete
   DESCRIPTION
     "This attribute indicates the current size of the transmit frame free 
      list. The transmit frame free list is the memory (in ATM cells) 
      available for storing frames to be transmitted by the Lp."
::= { mscLpAruOperEntry 53 }

mscLpAruTxFrameFreeListCongestionState OBJECT-TYPE
   SYNTAX     INTEGER (0..3)
   ACCESS     read-only
   STATUS     obsolete
   DESCRIPTION
     "This attribute indicates the congestion state of the transmit frame 
      free list on this ATM-FP. 
      
      The congestion state of a free list is indicated by a numeric value 
      ranging from 0 to 3. When a free list is in a congested state x, only 
      traffic with discard priority (DP) 0 to x will be stored. Traffic with 
      DP > x will be discarded. 
      
      Therefore, if the congestion state is 3, there is no congestion and all 
      traffic is stored. Likewise, when the congestion state is 0, there is 
      maximum congestion and only traffic with DP=0 will be stored."
::= { mscLpAruOperEntry 56 }

mscLpAruRxCellBlockCapacity OBJECT-TYPE
   SYNTAX     Unsigned32 (0..8192)
   ACCESS     read-only
   STATUS     obsolete
   DESCRIPTION
     "This attribute indicates the amount of memory reserved for storing 
      ATM cells received by the Lp."
::= { mscLpAruOperEntry 60 }

mscLpAruRxCellBlockUsage OBJECT-TYPE
   SYNTAX     Gauge32 (0..8192)
   ACCESS     read-only
   STATUS     obsolete
   DESCRIPTION
     "This attribute indicates the amount of memory currently being used 
      to store ATM cells received by the Lp."
::= { mscLpAruOperEntry 70 }

mscLpAruRxCellFreeListSize OBJECT-TYPE
   SYNTAX     Unsigned32 (0..16383)
   ACCESS     read-only
   STATUS     obsolete
   DESCRIPTION
     "This attribute indicates the current size of the receive cell free list. 
      The receive cell free list is the memory available for storing ATM 
      cells received by the Lp."
::= { mscLpAruOperEntry 73 }

mscLpAruRxCellFreeListCongestionState OBJECT-TYPE
   SYNTAX     INTEGER (0..3)
   ACCESS     read-only
   STATUS     obsolete
   DESCRIPTION
     "This attribute indicates the congestion state of the receive cell free 
      list on this ATM-FP. 
      
      The congestion state of a free list is indicated by a numeric value 
      ranging from 0 to 3. When a free list is in a congested state x, only 
      traffic with discard priority (DP) 0 to x will be stored. Traffic with 
      DP > x will be discarded. 
      
      Therefore, if the congestion state is 3, there is no congestion and all 
      traffic is stored. Likewise, when the congestion state is 0, there is 
      maximum congestion and only traffic with DP=0 will be stored."
::= { mscLpAruOperEntry 76 }

mscLpAruRxFrameMemoryAllocation OBJECT-TYPE
   SYNTAX     Unsigned32 (0..100)
   ACCESS     read-only
   STATUS     obsolete
   DESCRIPTION
     "This attribute indicates the percentage of the receive CQM memory 
      which is allocated to the receive frame free list on the ATM-FP. The 
      remaining receive CQM memory is allocated to the receive cell free 
      list. Frame memory is used for trunks, ATM Vcc testing and for 
      inter-card communication."
::= { mscLpAruOperEntry 80 }

mscLpAruRxFrameBlockCapacity OBJECT-TYPE
   SYNTAX     Unsigned32 (0..8192)
   ACCESS     read-only
   STATUS     obsolete
   DESCRIPTION
     "This attribute indicates the amount of memory reserved for storing 
      frames received by the Lp."
::= { mscLpAruOperEntry 90 }

mscLpAruRxFrameBlockUsage OBJECT-TYPE
   SYNTAX     Gauge32 (0..8192)
   ACCESS     read-only
   STATUS     obsolete
   DESCRIPTION
     "This attribute indicates the amount of memory currently being used 
      to store frames received by the Lp."
::= { mscLpAruOperEntry 100 }

mscLpAruRxFrameFreeListSize OBJECT-TYPE
   SYNTAX     Unsigned32 (0..16383)
   ACCESS     read-only
   STATUS     obsolete
   DESCRIPTION
     "This attribute indicates the current size of the receive frame free list. 
      The receive frame free list is the memory (in ATM cells) available 
      for storing frames received by the Lp."
::= { mscLpAruOperEntry 103 }

mscLpAruRxFrameFreeListCongestionState OBJECT-TYPE
   SYNTAX     INTEGER (0..3)
   ACCESS     read-only
   STATUS     obsolete
   DESCRIPTION
     "This attribute indicates the congestion state of the receive frame free 
      list on this ATM-FP. 
      
      The congestion state of a free list is indicated by a numeric value 
      ranging from 0 to 3. When a free list is in a congested state x, only 
      traffic with discard priority (DP) 0 to x will be stored. Traffic with 
      DP > x will be discarded. 
      
      Therefore, if the congestion state is 3, there is no congestion and all 
      traffic is stored. Likewise, when the congestion state is 0, there is 
      maximum congestion and only traffic with DP=0 will be stored."
::= { mscLpAruOperEntry 106 }

mscLpAruSubConnectionPoolAvailable OBJECT-TYPE
   SYNTAX     Unsigned32 (0..8192)
   ACCESS     read-only
   STATUS     obsolete
   DESCRIPTION
     "This attribute indicates the number of sub-connections available for 
      the LogicalProcessor. 
      
      A sub-connection is used for interworking the ATM services with 
      the frame oriented services such as Frame Relay, and Path Oriented 
      Routing System (PORS). When a frame is received at a sub-
      connection, the frame header is modified to be compatible with the 
      service it is to be forwarded to. 
      
      This pool is used for connection oriented services only. Each of the 
      following components uses one sub-connection from this pool: 
      FrAtm/x Dlci/y Siwf
      McsMgr Frf5EpG/x Frf5Ep/y Lmi
      McsMgr Frf5EpG/x Frf5Ep/y Dlci/z
      
      Note when the value of this attribute reaches zero, no more 
      connections will be accepted for any of the services which utilize 
      this pool. To increase the size of this pool, use the Arc 
      subConnectionPoolCapacity attribute."
::= { mscLpAruOperEntry 107 }

mscLpAruSubConnectionPoolUsage OBJECT-TYPE
   SYNTAX     Unsigned32 (0..8192)
   ACCESS     read-only
   STATUS     obsolete
   DESCRIPTION
     "This attribute indicates the number of sub-connections being 
      utilized for the LogicalProcessor.
      
      A sub-connection is used for interworking the ATM services with 
      the frame oriented services such as Frame Relay, and Path Oriented 
      Routing System (PORS). When a frame is received at a sub-
      connection, the frame header is modified to be compatible with the 
      service it is to be forwarded to.
      
      This pool is used for connection oriented services only. Each of the 
      following components uses one sub-connection from this pool: 
      FrAtm/x Dlci/y Siwf
      McsMgr Frf5EpG/x Frf5Ep/y Lmi
      McsMgr Frf5EpG/x Frf5Ep/y Dlci/z"
::= { mscLpAruOperEntry 108 }

mscLpAruLnnConnectionPoolAvailable OBJECT-TYPE
   SYNTAX     Unsigned32 (0..512)
   ACCESS     read-only
   STATUS     obsolete
   DESCRIPTION
     "This attribute indicates the number of resource records available for 
      the connections which utilize Logical Network Number (LNN) on 
      the LogicalProcessor.
      
      A logical network is a subset of passport modules together with a 
      subset of trunks that interconnect those modules. It carries the 
      traffic for a defined set of network protocols. A LNN is used to 
      identify a logical network. The connectionless services which 
      utilize the logical networks require some processing at the 
      intermediate nodes. This pool is allocated at the intermediate nodes 
      to sustain these connectionless services.
      
      If the McsMgr DprsMcsEpG/x Ep/y EpD 
      transportConnectionPreference attribute is set to atmOnly, each 
      instance of the McsMgr DprsMcsEpG/x Ep/y component uses one 
      resource record from this pool.
      
      Note, when the value of this attribute reaches zero, no more 
      connections will be accepted for any of the services which utilize 
      this pool. To increase the size of this pool, use the Arc 
      lnnConnectionPoolCapacity attribute."
::= { mscLpAruOperEntry 109 }

mscLpAruLnnConnectionPoolUsage OBJECT-TYPE
   SYNTAX     Unsigned32 (0..512)
   ACCESS     read-only
   STATUS     obsolete
   DESCRIPTION
     "This attribute indicates the number of resource records being 
      utilized for the connections which use Logical Network Number 
      (LNN) on the LogicalProcessor.
      
      A logical network is a subset of passport modules together with a 
      subset of trunks that interconnect those modules. It carries the 
      traffic for a defined set of network protocols. A LNN is used to 
      identify a logical network. The connectionless services which 
      utilize the logical networks require some processing at the 
      intermediate nodes. This pool is applied at the intermediate nodes to 
      sustain these connectionless services.
      
      If the McsMgr DprsMcsEpG/x Ep/y EpD 
      transportConnectionPreference attribute is set to atmOnly, each 
      instance of the McsMgr DprsMcsEpG/x Ep/y component uses one 
      resource record from this pool."
::= { mscLpAruOperEntry 110 }

mscLpAruConnUsageTable OBJECT-TYPE
   SYNTAX     SEQUENCE OF MscLpAruConnUsageEntry
   ACCESS     not-accessible
   STATUS     obsolete
   DESCRIPTION
     "This attribute has been replaced by the set of AtmIf CA 
      connectionPoolUsage attributes for AtmIf associated to 
      independent links or IMA groups on this LogicalProcessor. The 
      change better encapsulates the information associated with the 
      AtmIf.
      
      This attribute indicates the number of connection identifiers (both 
      VCC and VPC) that are in use on each port. The entries are indexed 
      by port number."
::= { mscLpAru 292 }

mscLpAruConnUsageEntry OBJECT-TYPE
   SYNTAX     MscLpAruConnUsageEntry
   ACCESS     not-accessible
   STATUS     obsolete
   DESCRIPTION
     "An entry in the mscLpAruConnUsageTable."
   INDEX {
      mscLpIndex,
      mscLpAruIndex,
      mscLpAruConnUsageIndex }
::= { mscLpAruConnUsageTable 1 }

MscLpAruConnUsageEntry ::= SEQUENCE {
   mscLpAruConnUsageIndex
      Integer32,
   mscLpAruConnUsageValue
      Unsigned32 }

mscLpAruConnUsageIndex OBJECT-TYPE
   SYNTAX     Integer32 (0..2)
   ACCESS     not-accessible
   STATUS     obsolete
   DESCRIPTION
     "This variable represents the mscLpAruConnUsageTable
      specific index for the mscLpAruConnUsageTable."
::= { mscLpAruConnUsageEntry 1 }

mscLpAruConnUsageValue OBJECT-TYPE
   SYNTAX     Unsigned32 (0..16000)
   ACCESS     read-only
   STATUS     obsolete
   DESCRIPTION
     "This variable represents an individual value for the
      mscLpAruConnUsageTable."
::= { mscLpAruConnUsageEntry 2 }

mscLpAruTxCflThreshTable OBJECT-TYPE
   SYNTAX     SEQUENCE OF MscLpAruTxCflThreshEntry
   ACCESS     not-accessible
   STATUS     obsolete
   DESCRIPTION
     "This attribute indicates the maximum value of the 
      txCellFreeListSize and the discard thresholds of the transmit cell 
      free list. The transmit cell free list is the memory used for storing 
      ATM cells to be transmitted by the Lp.
      
      The first value indicates the maximum size of the transmit cell free 
      list. This is derived based upon the connectionPoolCapacity and the 
      txFrameMemoryAllocation under the ARC component.
      
      When the txCellFreeListSize decreases to the second value, the 
      txCellFreeListCongestionState changes from 3 to 2. In congestion 
      state 2, traffic with discard priority (DP) = 3 is discarded. This 
      threshold is set approximately at 25 percent of the first value, the 
      maximum transmit cell free list size.
      
      When the txCellFreeListSize decreases to the third value, the 
      txCellFreeListCongestionState changes from 2 to 1. In congestion 
      state 1, traffic with discard priority (DP) = 2 is discarded. This 
      threshold is set approximately at 20 percent of the first value, the 
      maximum transmit cell free list size.
      
      When the txCellFreeListSize decreases to the fourth value, the 
      txCellFreeListCongestionState changes from 1 to 0. In congestion 
      state 0, traffic with discard priority (DP) = 1 is discarded. This 
      threshold is set approximately at 10 percent of the first value, the 
      maximum transmit cell free list size."
::= { mscLpAru 353 }

mscLpAruTxCflThreshEntry OBJECT-TYPE
   SYNTAX     MscLpAruTxCflThreshEntry
   ACCESS     not-accessible
   STATUS     obsolete
   DESCRIPTION
     "An entry in the mscLpAruTxCflThreshTable."
   INDEX {
      mscLpIndex,
      mscLpAruIndex,
      mscLpAruTxCflThreshIndex }
::= { mscLpAruTxCflThreshTable 1 }

MscLpAruTxCflThreshEntry ::= SEQUENCE {
   mscLpAruTxCflThreshIndex
      Integer32,
   mscLpAruTxCflThreshValue
      Unsigned32 }

mscLpAruTxCflThreshIndex OBJECT-TYPE
   SYNTAX     Integer32 (0..3)
   ACCESS     not-accessible
   STATUS     obsolete
   DESCRIPTION
     "This variable represents the mscLpAruTxCflThreshTable
      specific index for the mscLpAruTxCflThreshTable."
::= { mscLpAruTxCflThreshEntry 1 }

mscLpAruTxCflThreshValue OBJECT-TYPE
   SYNTAX     Unsigned32 (0..16383)
   ACCESS     read-only
   STATUS     obsolete
   DESCRIPTION
     "This variable represents an individual value for the
      mscLpAruTxCflThreshTable."
::= { mscLpAruTxCflThreshEntry 2 }

mscLpAruTxFflThreshTable OBJECT-TYPE
   SYNTAX     SEQUENCE OF MscLpAruTxFflThreshEntry
   ACCESS     not-accessible
   STATUS     obsolete
   DESCRIPTION
     "This attribute indicates the maximum txFrameFeeListSize and the 
      discard thresholds of the transmit frame free list. The transmit frame 
      free list is the memory (in units of ATM cells) used for storing 
      frames to be transmitted by the Lp.
      
      The first parameter indicates the total size of the transmit frame free 
      list. This is derived based upon the connectionPoolCapacity and the 
      txFrameMemoryAllocation under the ARC component.
      
      When the txFrameFreeListSize decreases to the second value, the 
      txFrameFreeListCongestionState changes from 3 to 2. In congestion 
      state 2, traffic with discard priority (DP) = 3 is discarded. This 
      threshold is set approximately at 25 percent of the first value, the 
      maximum transmit frame free list size.
      
      When the txFrameFreeListSize decreases to the third value, the 
      txFrameFreeListCongestionState changes from 2 to 1. In congestion 
      state 1, traffic with discard priority (DP) = 2 is discarded. This 
      threshold is set approximately at 20 percent of the first value, the 
      maximum transmit frame free list size.
      
      When the txFameFreeListSize decreases to the fourth value, the 
      txFameFreeListCongestionState changes from 1 to 0. In congestion 
      state 0, traffic with discard priority (DP) = 1 is discarded. This 
      threshold is set approximately at 10 percent of the first value, the 
      maximum transmit frame free list size."
::= { mscLpAru 354 }

mscLpAruTxFflThreshEntry OBJECT-TYPE
   SYNTAX     MscLpAruTxFflThreshEntry
   ACCESS     not-accessible
   STATUS     obsolete
   DESCRIPTION
     "An entry in the mscLpAruTxFflThreshTable."
   INDEX {
      mscLpIndex,
      mscLpAruIndex,
      mscLpAruTxFflThreshIndex }
::= { mscLpAruTxFflThreshTable 1 }

MscLpAruTxFflThreshEntry ::= SEQUENCE {
   mscLpAruTxFflThreshIndex
      Integer32,
   mscLpAruTxFflThreshValue
      Unsigned32 }

mscLpAruTxFflThreshIndex OBJECT-TYPE
   SYNTAX     Integer32 (0..3)
   ACCESS     not-accessible
   STATUS     obsolete
   DESCRIPTION
     "This variable represents the mscLpAruTxFflThreshTable
      specific index for the mscLpAruTxFflThreshTable."
::= { mscLpAruTxFflThreshEntry 1 }

mscLpAruTxFflThreshValue OBJECT-TYPE
   SYNTAX     Unsigned32 (0..16383)
   ACCESS     read-only
   STATUS     obsolete
   DESCRIPTION
     "This variable represents an individual value for the
      mscLpAruTxFflThreshTable."
::= { mscLpAruTxFflThreshEntry 2 }

mscLpAruRxCflThreshTable OBJECT-TYPE
   SYNTAX     SEQUENCE OF MscLpAruRxCflThreshEntry
   ACCESS     not-accessible
   STATUS     obsolete
   DESCRIPTION
     "This attribute indicates the maximum value of the 
      rxCellFreeListSize and the discard thresholds of the receive cell free 
      list. The receive cell free list is the memory used for storing ATM 
      cells to be received by the Lp.
      
      The first value indicates the maximum size of the recieve cell free 
      list. This is derived based upon the connectionPoolCapacity and the 
      rxFrameMemoryAllocation under the ARC component.
      
      When the rxCellFreeListSize decreases to the second value, the 
      rxCellFreeListCongestionState changes from 3 to 2. In congestion 
      state 2, traffic with discard priority (DP) = 3 is discarded. This 
      threshold is set approximately at 25 percent of the first value, the 
      maximum receive cell free list size.
      
      When the rxCellFreeListSize decreases to the third value, the 
      rxCellFreeListCongestionState changes from 2 to 1. In congestion 
      state 1, traffic with discard priority (DP) = 2 is discarded. This 
      threshold is set approximately at 20 percent of the first value, the 
      maximum receive cell free list size.
      
      When the rxCellFreeListSize decreases to the fourth value, the 
      rxCellFreeListCongestionState changes from 1 to 0. In congestion 
      state 0, traffic with discard priority (DP) = 1 is discarded. This 
      threshold is set approximately at 10 percent of the first value, the 
      maximum receive cell free list size."
::= { mscLpAru 355 }

mscLpAruRxCflThreshEntry OBJECT-TYPE
   SYNTAX     MscLpAruRxCflThreshEntry
   ACCESS     not-accessible
   STATUS     obsolete
   DESCRIPTION
     "An entry in the mscLpAruRxCflThreshTable."
   INDEX {
      mscLpIndex,
      mscLpAruIndex,
      mscLpAruRxCflThreshIndex }
::= { mscLpAruRxCflThreshTable 1 }

MscLpAruRxCflThreshEntry ::= SEQUENCE {
   mscLpAruRxCflThreshIndex
      Integer32,
   mscLpAruRxCflThreshValue
      Unsigned32 }

mscLpAruRxCflThreshIndex OBJECT-TYPE
   SYNTAX     Integer32 (0..3)
   ACCESS     not-accessible
   STATUS     obsolete
   DESCRIPTION
     "This variable represents the mscLpAruRxCflThreshTable
      specific index for the mscLpAruRxCflThreshTable."
::= { mscLpAruRxCflThreshEntry 1 }

mscLpAruRxCflThreshValue OBJECT-TYPE
   SYNTAX     Unsigned32 (0..16383)
   ACCESS     read-only
   STATUS     obsolete
   DESCRIPTION
     "This variable represents an individual value for the
      mscLpAruRxCflThreshTable."
::= { mscLpAruRxCflThreshEntry 2 }

mscLpAruRxFflThreshTable OBJECT-TYPE
   SYNTAX     SEQUENCE OF MscLpAruRxFflThreshEntry
   ACCESS     not-accessible
   STATUS     obsolete
   DESCRIPTION
     "This attribute indicates the maximum rxFrameFeeListSize and the 
      discard thresholds of the transmit frame free list. The receive frame 
      free list is the memory (in units of ATM cells) used for storing 
      frames to be received by the Lp.
      
      The first parameter indicates the total size of the receive frame free 
      list. This is derived based upon the connectionPoolCapacity and the 
      rxFrameMemoryAllocation under the ARC component.
      
      When the rxFrameFreeListSize decreases to the second value, the 
      rxFrameFreeListCongestionState changes from 3 to 2. In 
      congestion state 2, traffic with discard priority (DP) = 3 is 
      discarded. This threshold is set approximately at 25 percent of the 
      first value, the maximum receive frame free list size.
      
      When the rxFrameFreeListSize decreases to the third value, the 
      rxFrameFreeListCongestionState changes from 2 to 1. In 
      congestion state 1, traffic with discard priority (DP) = 2 is 
      discarded. This threshold is set approximately at 20 percent of the 
      first value, the maximum receive frame free list size.
      
      When the rxFameFreeListSize decreases to the fourth value, the 
      rxFameFreeListCongestionState changes from 1 to 0. In congestion 
      state 0, traffic with discard priority (DP) = 1 is discarded. This 
      threshold is set approximately at 10 percent of the first value, the 
      maximum receive frame free list size."
::= { mscLpAru 356 }

mscLpAruRxFflThreshEntry OBJECT-TYPE
   SYNTAX     MscLpAruRxFflThreshEntry
   ACCESS     not-accessible
   STATUS     obsolete
   DESCRIPTION
     "An entry in the mscLpAruRxFflThreshTable."
   INDEX {
      mscLpIndex,
      mscLpAruIndex,
      mscLpAruRxFflThreshIndex }
::= { mscLpAruRxFflThreshTable 1 }

MscLpAruRxFflThreshEntry ::= SEQUENCE {
   mscLpAruRxFflThreshIndex
      Integer32,
   mscLpAruRxFflThreshValue
      Unsigned32 }

mscLpAruRxFflThreshIndex OBJECT-TYPE
   SYNTAX     Integer32 (0..3)
   ACCESS     not-accessible
   STATUS     obsolete
   DESCRIPTION
     "This variable represents the mscLpAruRxFflThreshTable
      specific index for the mscLpAruRxFflThreshTable."
::= { mscLpAruRxFflThreshEntry 1 }

mscLpAruRxFflThreshValue OBJECT-TYPE
   SYNTAX     Unsigned32 (0..16383)
   ACCESS     read-only
   STATUS     obsolete
   DESCRIPTION
     "This variable represents an individual value for the
      mscLpAruRxFflThreshTable."
::= { mscLpAruRxFflThreshEntry 2 }


-- Lp/n Eng AtmResourceControl
-- This component describes the usage of ATM-specific resources on 
-- an FP running ATM services. This component is always 
-- dynamically created under any LP Eng which supports an FP. 

mscLpEngArc OBJECT IDENTIFIER ::= { mscLpEng 5 }



mscLpEngArcRowStatusTable OBJECT-TYPE
   SYNTAX     SEQUENCE OF MscLpEngArcRowStatusEntry
   ACCESS     not-accessible
   STATUS     mandatory
   DESCRIPTION
     "This entry controls the addition and deletion of 
      mscLpEngArc components."
::= { mscLpEngArc 1 }

mscLpEngArcRowStatusEntry OBJECT-TYPE
   SYNTAX     MscLpEngArcRowStatusEntry
   ACCESS     not-accessible
   STATUS     mandatory
   DESCRIPTION
     "A single entry in the table represents a single 
      mscLpEngArc component."
   INDEX {
      mscLpIndex,
      mscLpEngIndex,
      mscLpEngArcIndex }
::= { mscLpEngArcRowStatusTable 1 }

MscLpEngArcRowStatusEntry ::= SEQUENCE {
   mscLpEngArcRowStatus
      RowStatus,
   mscLpEngArcComponentName
      DisplayString,
   mscLpEngArcStorageType
      StorageType,
   mscLpEngArcIndex
      NonReplicated }

mscLpEngArcRowStatus OBJECT-TYPE
   SYNTAX     RowStatus 
   ACCESS     read-write
   STATUS     mandatory
   DESCRIPTION
     "This variable is used as the basis for SNMP naming of
      mscLpEngArc components.
      These components can be added and deleted."
::= { mscLpEngArcRowStatusEntry 1 }

mscLpEngArcComponentName OBJECT-TYPE
   SYNTAX     DisplayString 
   ACCESS     read-only
   STATUS     mandatory
   DESCRIPTION
     "This variable provides the component's string name for
      use with the ASCII Console Interface"
::= { mscLpEngArcRowStatusEntry 2 }

mscLpEngArcStorageType OBJECT-TYPE
   SYNTAX     StorageType 
   ACCESS     read-only
   STATUS     mandatory
   DESCRIPTION
     "This variable represents the storage type value for the
      mscLpEngArc tables."
::= { mscLpEngArcRowStatusEntry 4 }

mscLpEngArcIndex OBJECT-TYPE
   SYNTAX     NonReplicated 
   ACCESS     not-accessible
   STATUS     mandatory
   DESCRIPTION
     "This variable represents the index for the mscLpEngArc tables."
::= { mscLpEngArcRowStatusEntry 10 }

mscLpEngArcOperTable OBJECT-TYPE
   SYNTAX     SEQUENCE OF MscLpEngArcOperEntry
   ACCESS     not-accessible
   STATUS     mandatory
   DESCRIPTION
     "This group describes the usage of ATM-specific resources on a 
      Logical Processor running ATM services.
      The attributes listed represent Queue Controller resource usage for 
      all ATM Cards (CQC for CQC based cards or PQC for SGAF 
      cards)."
::= { mscLpEngArc 10 }

mscLpEngArcOperEntry OBJECT-TYPE
   SYNTAX     MscLpEngArcOperEntry
   ACCESS     not-accessible
   STATUS     mandatory
   DESCRIPTION
     "An entry in the mscLpEngArcOperTable."
   INDEX {
      mscLpIndex,
      mscLpEngIndex,
      mscLpEngArcIndex }
::= { mscLpEngArcOperTable 1 }

MscLpEngArcOperEntry ::= SEQUENCE {
   mscLpEngArcTotalConnectionPoolAvailable
      Unsigned32,
   mscLpEngArcTotalConnectionPoolUsage
      Unsigned32,
   mscLpEngArcMulticastBranchesAvailable
      Unsigned32,
   mscLpEngArcMulticastBranchesUsage
      Unsigned32,
   mscLpEngArcTxCellMemoryAllocation
      Unsigned32,
   mscLpEngArcTxCellMemoryAvailable
      Gauge32,
   mscLpEngArcTxCellMemoryMinAvailable
      Gauge32,
   mscLpEngArcTxCellMemoryCongestionState
      Gauge32,
   mscLpEngArcRxCellMemoryAllocation
      Unsigned32,
   mscLpEngArcRxCellMemoryAvailable
      Gauge32,
   mscLpEngArcRxCellMemoryMinAvailable
      Gauge32,
   mscLpEngArcRxCellMemoryCongestionState
      Gauge32 }

mscLpEngArcTotalConnectionPoolAvailable OBJECT-TYPE
   SYNTAX     Unsigned32 (0..32768)
   ACCESS     read-only
   STATUS     mandatory
   DESCRIPTION
     "This attribute indicates the number of connection resources 
      available (VCC, VPC, and VPT) that can be used on this FP.
      
      A standard Vpt uses 3 connection resources and a basic Vpt uses 2."
::= { mscLpEngArcOperEntry 1 }

mscLpEngArcTotalConnectionPoolUsage OBJECT-TYPE
   SYNTAX     Unsigned32 (0..32768)
   ACCESS     read-only
   STATUS     mandatory
   DESCRIPTION
     "This attribute indicates the number of connection resources (VCC, 
      VPC, and VPT) in use on this FP.
      
      A standard Vpt uses 3 connection resources and a basic Vpt uses 2."
::= { mscLpEngArcOperEntry 2 }

mscLpEngArcMulticastBranchesAvailable OBJECT-TYPE
   SYNTAX     Unsigned32 (0..16384)
   ACCESS     read-only
   STATUS     mandatory
   DESCRIPTION
     "This attribute indicates the total number of multicast branches that 
      are available on this FP."
::= { mscLpEngArcOperEntry 3 }

mscLpEngArcMulticastBranchesUsage OBJECT-TYPE
   SYNTAX     Unsigned32 (0..16384)
   ACCESS     read-only
   STATUS     mandatory
   DESCRIPTION
     "This attribute indicates the total number of multicast branches that 
      are active on this FP."
::= { mscLpEngArcOperEntry 4 }

mscLpEngArcTxCellMemoryAllocation OBJECT-TYPE
   SYNTAX     Unsigned32 (1..99)
   ACCESS     read-only
   STATUS     mandatory
   DESCRIPTION
     "This attribute indicates the fraction of the transmit  memory which 
      is allocated for the transmission of cells on the FP. Cell memory is 
      used for Atm Bearer Services, ATM SVCs and ATM PVCs.
      
      The remaining transmit memory is allocated for the transmission of 
      frames. Frame memory is used for trunks, ATM VCC testing and 
      for inter-card communication."
::= { mscLpEngArcOperEntry 5 }

mscLpEngArcTxCellMemoryAvailable OBJECT-TYPE
   SYNTAX     Gauge32 (0..163839)
   ACCESS     read-only
   STATUS     mandatory
   DESCRIPTION
     "This attribute indicates the current availability of the transmit  cell 
      memory.
      
      The transmit cell memory is the memory available for storing ATM 
      cells to be transmitted by this FP."
::= { mscLpEngArcOperEntry 6 }

mscLpEngArcTxCellMemoryMinAvailable OBJECT-TYPE
   SYNTAX     Gauge32 (0..163839)
   ACCESS     read-only
   STATUS     mandatory
   DESCRIPTION
     "This attribute indicates the lowest availability of the transmit  cell 
      memory.
      
      The transmit cell memory is the memory available for storing ATM 
      cells to be transmitted by this FP.
      
      This value is reset to the current availability every 15 minutes and 
      when the card is reset."
::= { mscLpEngArcOperEntry 7 }

mscLpEngArcTxCellMemoryCongestionState OBJECT-TYPE
   SYNTAX     Gauge32 (0..3)
   ACCESS     read-only
   STATUS     mandatory
   DESCRIPTION
     "This attribute indicates the congestion state of the transmit  cell 
      memory on this FP. 
      
      The congestion state of memory is indicated by a numeric value 
      ranging from 0 to 3. When memory is in a congested state 'x', only 
      traffic with discard priority (DP) 0 to 'x' is processed. Traffic with 
      DP > 'x' is discarded. 
      
      Therefore, if the congestion state is 3, there is no congestion and all 
      traffic is stored. Likewise, when the congestion state is 0, there is 
      maximum congestion and only traffic with DP=0 is stored."
::= { mscLpEngArcOperEntry 8 }

mscLpEngArcRxCellMemoryAllocation OBJECT-TYPE
   SYNTAX     Unsigned32 (1..99)
   ACCESS     read-only
   STATUS     mandatory
   DESCRIPTION
     "This attribute indicates the fraction of the receive  memory which is 
      allocated for the reception of cells on the FP. Cell memory is used 
      for Atm Bearer Services, ATM SVCS and ATM PVCS.
      
      The remaining receive memory is allocated to the reception of 
      frame. Frame memory is used for trunks, ATM VCC testing and for 
      inter-card communication."
::= { mscLpEngArcOperEntry 9 }

mscLpEngArcRxCellMemoryAvailable OBJECT-TYPE
   SYNTAX     Gauge32 (0..163839)
   ACCESS     read-only
   STATUS     mandatory
   DESCRIPTION
     "This attribute indicates the current availability of the receive  cell 
      memory. 
      
      The receive cell memory is the memory available for storing ATM 
      cells to be transmitted by this FP."
::= { mscLpEngArcOperEntry 10 }

mscLpEngArcRxCellMemoryMinAvailable OBJECT-TYPE
   SYNTAX     Gauge32 (0..163839)
   ACCESS     read-only
   STATUS     mandatory
   DESCRIPTION
     "This attribute indicates the lowest availability of the receive  cell 
      memory. 
      
      The receive cell memory is the memory available for storing ATM 
      cells to be transmitted by this FP.
      
      This value is reset to the current availability every 15 minutes and 
      when the card is reset."
::= { mscLpEngArcOperEntry 11 }

mscLpEngArcRxCellMemoryCongestionState OBJECT-TYPE
   SYNTAX     Gauge32 (0..3)
   ACCESS     read-only
   STATUS     mandatory
   DESCRIPTION
     "This attribute indicates the congestion state of the receive cell 
      memory on this FP. 
      
      The congestion state of memory is indicated by a numeric value 
      ranging from 0 to 3. When memory is in a congested state 'x', only 
      traffic with discard priority (DP) 0 to 'x' is processed. Traffic with 
      DP > 'x' is discarded. 
      
      Therefore, if the congestion state is 3, there is no congestion and all 
      traffic is stored. Likewise, when the congestion state is 0, there is 
      maximum congestion and only traffic with DP=0 is stored."
::= { mscLpEngArcOperEntry 12 }

mscLpEngArcTxCellThreshTable OBJECT-TYPE
   SYNTAX     SEQUENCE OF MscLpEngArcTxCellThreshEntry
   ACCESS     not-accessible
   STATUS     mandatory
   DESCRIPTION
     "This attribute indicates the total transmit cell memory size and the 
      discard thresholds of the transmit  cell memory. The transmit cell 
      memory is the memory used for storing ATM cells to be transmitted 
      by this FP.
      
      The first value indicates the the total transmit cell memory size. 
      This is derived based upon the connectionPoolCapacity and the 
      txCellMemoryAllocation attributes.
      
      When the txCellMemoryAvailable attribute decreases to the second 
      value, the txCellMemoryCongestionState changes from 3 to 2. In 
      congestion state 2, traffic with discard priority (DP) = 3 is 
      discarded. This threshold is set approximately at 25 percent of the 
      first value, the total transmit cell memory size.
      
      When the txCellMemoryAvailable attribute decreases to the third 
      value, the txCellMemoryCongestionState changes from 2 to 1. In 
      congestion state 1, traffic with discard priority (DP) >= 2 is 
      discarded. This threshold is set approximately at 20 percent of the 
      first value, the total transmit cell memory size.
      
      When the txCellMemoryAvailable attribute decreases to the fourth 
      value, the txCellMemoryCongestionState changes from 1 to 0. In 
      congestion state 0, traffic with discard priority (DP) >= 1 is 
      discarded. This threshold is set approximately at 10 percent of the 
      first value, the total transmit cell memory size.
      
      The opposite effect occurs when the txCellMemoryAvailable 
      attribute increases (txCellMemoryCongestionState increases from 0 
      to 3 accordingly)."
::= { mscLpEngArc 440 }

mscLpEngArcTxCellThreshEntry OBJECT-TYPE
   SYNTAX     MscLpEngArcTxCellThreshEntry
   ACCESS     not-accessible
   STATUS     mandatory
   DESCRIPTION
     "An entry in the mscLpEngArcTxCellThreshTable."
   INDEX {
      mscLpIndex,
      mscLpEngIndex,
      mscLpEngArcIndex,
      mscLpEngArcTxCellThreshIndex }
::= { mscLpEngArcTxCellThreshTable 1 }

MscLpEngArcTxCellThreshEntry ::= SEQUENCE {
   mscLpEngArcTxCellThreshIndex
      Integer32,
   mscLpEngArcTxCellThreshValue
      Unsigned32 }

mscLpEngArcTxCellThreshIndex OBJECT-TYPE
   SYNTAX     Integer32 (0..3)
   ACCESS     not-accessible
   STATUS     mandatory
   DESCRIPTION
     "This variable represents the mscLpEngArcTxCellThreshTable
      specific index for the mscLpEngArcTxCellThreshTable."
::= { mscLpEngArcTxCellThreshEntry 1 }

mscLpEngArcTxCellThreshValue OBJECT-TYPE
   SYNTAX     Unsigned32 (0..163839)
   ACCESS     read-only
   STATUS     mandatory
   DESCRIPTION
     "This variable represents an individual value for the
      mscLpEngArcTxCellThreshTable."
::= { mscLpEngArcTxCellThreshEntry 2 }

mscLpEngArcRxCellThreshTable OBJECT-TYPE
   SYNTAX     SEQUENCE OF MscLpEngArcRxCellThreshEntry
   ACCESS     not-accessible
   STATUS     mandatory
   DESCRIPTION
     "This attribute indicates the total receive cell memory size and the 
      discard thresholds of the receive cell memory. The receive cell 
      memory is the memory used for storing ATM cells to be received by 
      this FP.
      
      The first value indicates the total receive cell memory size. This is 
      derived based upon the connectionPoolCapacity and the 
      rxCellMemoryAllocation under the ARC component.
      
      When the rxCellMemoryAvailable attribute decreases to the second 
      value, the rxCellMemoryCongestionState changes from 3 to 2. In 
      congestion state 2, traffic with discard priority (DP) = 3 is 
      discarded. This threshold is set approximately at 25 percent of the 
      first value, the total receive cell memory size.
      
      When the rxCellMemoryAvailable attribute decreases to the third 
      value, the rxCellMemoryCongestionState changes from 2 to 1. In 
      congestion state 1, traffic with discard priority (DP) >= 2 is 
      discarded. This threshold is set approximately at 20 percent of the 
      first value, the total receive cell memory size.
      
      When the rxCellMemoryAvailable attribute decreases to the fourth 
      value, the rxCellMemoryCongestionState changes from 1 to 0. In 
      congestion state 0, traffic with discard priority (DP) >= 1 is 
      discarded. This threshold is set approximately at 10 percent of the 
      first value, the total receive cell memory size.
      
      The opposite effect occurs when the rxCellMemoryAvailable 
      attribute increases (rxCellMemoryCongestionState increases from 0 
      to 3 accordingly)."
::= { mscLpEngArc 444 }

mscLpEngArcRxCellThreshEntry OBJECT-TYPE
   SYNTAX     MscLpEngArcRxCellThreshEntry
   ACCESS     not-accessible
   STATUS     mandatory
   DESCRIPTION
     "An entry in the mscLpEngArcRxCellThreshTable."
   INDEX {
      mscLpIndex,
      mscLpEngIndex,
      mscLpEngArcIndex,
      mscLpEngArcRxCellThreshIndex }
::= { mscLpEngArcRxCellThreshTable 1 }

MscLpEngArcRxCellThreshEntry ::= SEQUENCE {
   mscLpEngArcRxCellThreshIndex
      Integer32,
   mscLpEngArcRxCellThreshValue
      Unsigned32 }

mscLpEngArcRxCellThreshIndex OBJECT-TYPE
   SYNTAX     Integer32 (0..3)
   ACCESS     not-accessible
   STATUS     mandatory
   DESCRIPTION
     "This variable represents the mscLpEngArcRxCellThreshTable
      specific index for the mscLpEngArcRxCellThreshTable."
::= { mscLpEngArcRxCellThreshEntry 1 }

mscLpEngArcRxCellThreshValue OBJECT-TYPE
   SYNTAX     Unsigned32 (0..163839)
   ACCESS     read-only
   STATUS     mandatory
   DESCRIPTION
     "This variable represents an individual value for the
      mscLpEngArcRxCellThreshTable."
::= { mscLpEngArcRxCellThreshEntry 2 }


-- Lp/n Eng Arc Override
-- This component is used to configure the usage of ATM-specific 
-- resources on a Logical Processor running ATM services. The 
-- attributes listed represent Queue Controller resource configuration 
-- for all ATM Cards (CQC for CQC based cards or PQC for SGAF 
-- cards).
-- This component is only permitted under Logical Processors which 
-- are linked to ATM card types.)

mscLpEngArcOv OBJECT IDENTIFIER ::= { mscLpEngArc 2 }



mscLpEngArcOvRowStatusTable OBJECT-TYPE
   SYNTAX     SEQUENCE OF MscLpEngArcOvRowStatusEntry
   ACCESS     not-accessible
   STATUS     mandatory
   DESCRIPTION
     "This entry controls the addition and deletion of 
      mscLpEngArcOv components."
::= { mscLpEngArcOv 1 }

mscLpEngArcOvRowStatusEntry OBJECT-TYPE
   SYNTAX     MscLpEngArcOvRowStatusEntry
   ACCESS     not-accessible
   STATUS     mandatory
   DESCRIPTION
     "A single entry in the table represents a single 
      mscLpEngArcOv component."
   INDEX {
      mscLpIndex,
      mscLpEngIndex,
      mscLpEngArcIndex,
      mscLpEngArcOvIndex }
::= { mscLpEngArcOvRowStatusTable 1 }

MscLpEngArcOvRowStatusEntry ::= SEQUENCE {
   mscLpEngArcOvRowStatus
      RowStatus,
   mscLpEngArcOvComponentName
      DisplayString,
   mscLpEngArcOvStorageType
      StorageType,
   mscLpEngArcOvIndex
      NonReplicated }

mscLpEngArcOvRowStatus OBJECT-TYPE
   SYNTAX     RowStatus 
   ACCESS     read-write
   STATUS     mandatory
   DESCRIPTION
     "This variable is used as the basis for SNMP naming of
      mscLpEngArcOv components.
      These components can be added and deleted."
::= { mscLpEngArcOvRowStatusEntry 1 }

mscLpEngArcOvComponentName OBJECT-TYPE
   SYNTAX     DisplayString 
   ACCESS     read-only
   STATUS     mandatory
   DESCRIPTION
     "This variable provides the component's string name for
      use with the ASCII Console Interface"
::= { mscLpEngArcOvRowStatusEntry 2 }

mscLpEngArcOvStorageType OBJECT-TYPE
   SYNTAX     StorageType 
   ACCESS     read-only
   STATUS     mandatory
   DESCRIPTION
     "This variable represents the storage type value for the
      mscLpEngArcOv tables."
::= { mscLpEngArcOvRowStatusEntry 4 }

mscLpEngArcOvIndex OBJECT-TYPE
   SYNTAX     NonReplicated 
   ACCESS     not-accessible
   STATUS     mandatory
   DESCRIPTION
     "This variable represents the index for the mscLpEngArcOv tables."
::= { mscLpEngArcOvRowStatusEntry 10 }

mscLpEngArcOvProvTable OBJECT-TYPE
   SYNTAX     SEQUENCE OF MscLpEngArcOvProvEntry
   ACCESS     not-accessible
   STATUS     mandatory
   DESCRIPTION
     "This group specifies the configuration of processor-wide ATM-
      specific resources on a Logical Processor running ATM services on 
      ATM cards. Note that altering any of these parameters will result in 
      a card reboot."
::= { mscLpEngArcOv 10 }

mscLpEngArcOvProvEntry OBJECT-TYPE
   SYNTAX     MscLpEngArcOvProvEntry
   ACCESS     not-accessible
   STATUS     mandatory
   DESCRIPTION
     "An entry in the mscLpEngArcOvProvTable."
   INDEX {
      mscLpIndex,
      mscLpEngIndex,
      mscLpEngArcIndex,
      mscLpEngArcOvIndex }
::= { mscLpEngArcOvProvTable 1 }

MscLpEngArcOvProvEntry ::= SEQUENCE {
   mscLpEngArcOvTotalConnectionPoolCapacity
      Unsigned32,
   mscLpEngArcOvMulticastBranchesCapacity
      Unsigned32,
   mscLpEngArcOvTxCellMemoryAllocation
      Unsigned32,
   mscLpEngArcOvRxCellMemoryAllocation
      Unsigned32 }

mscLpEngArcOvTotalConnectionPoolCapacity OBJECT-TYPE
   SYNTAX     Unsigned32 (0..32768)
   ACCESS     read-write
   STATUS     mandatory
   DESCRIPTION
     "This attribute specifies the maximum number of connections (VCC, 
      VPC and VPT) that can be enabled on this FP.A standard Vpt uses 3 
      connections and a basic Vpt uses 2.
      
      If the LogicalProcessor is associated with a card of a cardType 
      other than one of the following: 3pE3Atm, 3pDS3Atm, 
      3pOC3MmAtm, 3pOC3SmAtm, 3pE1Atm, 3pDS1Atm, 
      2pJ6MAtm; the value of the attribute restricts the sum of the 
      (maxVccs + maxVpcs + (maxVpts * 3)) across all AtmIfs bound to 
      this LogicalProcessor.
      
      If the LogicalProcessor is associated with a card of one of the 
      following cardTypes: 3pE3Atm, 3pDS3Atm, 3pOC3MmAtm, 
      3pOC3SmAtm, 3pE1Atm, 3pDS1Atm, 2pJ6MAtm; the number of 
      available connections are distributed equally across the ports on the 
      FP. The number of connections associated to a particular port limits 
      the size of the Vcc space which can be defined by the ConnMap of 
      the AtmIf linked to the port. If the ConnMap component does not 
      exist, its default settings are used for this check. Furthermore, the 
      value of this attribute is restricted based on the number of ports on 
      the card. For one port cards, the minimum is 512, the maximum is 
      4096 and the value must be divisible by 256. For two port cards, the 
      minimum is 1024, the maximum is 8192 and the value must be 
      divisible by 512. For three port cards, the minimum is 1536, the 
      maximum is 7680 and the value must be divisible by 768.
      
      If the LogicalProcessor is associated with a card of one of 
      the following cardTypes: 8pE1Atm, 8pDS1Atm, the 
      maximum value for this attribute is 10752.
      
      For SGAF cards, the Connmap attributes are set to their default 
      values.
      
      Increasing the value of this attribute reduces the  memory available 
      for cell and frame memory.
      
      This attribute must be set to 0 if the connectionPoolCapacity 
      attribute of the Arc Ov component is set to non-zero values."
   DEFVAL     { 3072 }
::= { mscLpEngArcOvProvEntry 1 }

mscLpEngArcOvMulticastBranchesCapacity OBJECT-TYPE
   SYNTAX     Unsigned32 (0..16384)
   ACCESS     read-write
   STATUS     mandatory
   DESCRIPTION
     "This attribute specifies the number of multicast branches that can be 
      enabled on this FP.
      
      A multicast branch is used for cell replication on a VCC connection 
      whose Vcc distributionType is pointToMultipoint. A branch 
      represents one ATM destination for the replicated cells.
      
      Increasing the value of this attribute reduces the  memory 
      available for the cell and frame memorys.
      
      This attribute is ignored for the 1pOC48SmSrAtm card as it does 
      not support multicast connections.
      
      For CQC based ATM FPs, the maximum value for this attribute is 
      10752."
   DEFVAL     { 0 }
::= { mscLpEngArcOvProvEntry 2 }

mscLpEngArcOvTxCellMemoryAllocation OBJECT-TYPE
   SYNTAX     Unsigned32 (1..99)
   ACCESS     read-write
   STATUS     mandatory
   DESCRIPTION
     "This attribute specifies the fraction of the transmit memory which 
      should be allocated to the transmission of cells on an FP. The 
      remaining memory is allocated for the transmission of frames. 
      Frame memory is used for trunks, ATM VCC testing and for inter-
      card communication. Cell memory is used for Atm Bearer Service, 
      ATM SVCs and ATM PVCs.
      
      There is an absolute minimum quantity of frame buffers which is 
      required by ATM software on the FP. If the value of this attribute is 
      smaller than the absolute minimum, the ATM software allocates the 
      minimum required, rather than the actual number requested.
      
      The actual percentage of the transmit  memory allocated to the 
      transmit cell memory is indicated by the Arc 
      txCellMemoryAllocation attribute. A difference between the 
      provisioned and the operational values may exist due to the 
      requirement for a minimum number of frame buffers or rounding 
      during computation within the FP."
   DEFVAL     { 50 }
::= { mscLpEngArcOvProvEntry 3 }

mscLpEngArcOvRxCellMemoryAllocation OBJECT-TYPE
   SYNTAX     Unsigned32 (1..99)
   ACCESS     read-write
   STATUS     mandatory
   DESCRIPTION
     "This attribute specifies the fraction of the receive  memory which 
      should be allocated to the reception of cells on an FP. The 
      remaining receive  memory is allocated for the reception of frames. 
      Frame memory is used for trunks, ATM VCC testing and for inter-
      card communication. Cell memory is used for Atm Bearer Service, 
      ATM SVCs and ATM PVCs. 
      
      There is an absolute minimum quantity of frame buffers which is 
      required by ATM software on the FP. If the value of this attribute is 
      smaller than the absolute minimum, the ATM software allocates the 
      minimum required, rather than the actual number requested. 
      
      The actual percentage of the receive  memory allocated to the 
      receive cell memory is indicated by the Arc 
      rxCellMemoryAllocation attribute. A difference between the 
      provisioned and the operational values may exist due to the 
      requirement for a minimum number of frame buffers or rounding 
      during computation within the FP."
   DEFVAL     { 20 }
::= { mscLpEngArcOvProvEntry 4 }


-- Lp/n Eng Arc Cqc
-- The Cqc component describes the usage of ATM-specific resources 
-- on a LogicalProcessor running ATM services on CQC based ATM 
-- cards. This component is always dynamically created under the LP 
-- Eng Arc which supports a CQC based FP. 

mscLpEngArcCqc OBJECT IDENTIFIER ::= { mscLpEngArc 3 }



mscLpEngArcCqcRowStatusTable OBJECT-TYPE
   SYNTAX     SEQUENCE OF MscLpEngArcCqcRowStatusEntry
   ACCESS     not-accessible
   STATUS     mandatory
   DESCRIPTION
     "This entry controls the addition and deletion of 
      mscLpEngArcCqc components."
::= { mscLpEngArcCqc 1 }

mscLpEngArcCqcRowStatusEntry OBJECT-TYPE
   SYNTAX     MscLpEngArcCqcRowStatusEntry
   ACCESS     not-accessible
   STATUS     mandatory
   DESCRIPTION
     "A single entry in the table represents a single 
      mscLpEngArcCqc component."
   INDEX {
      mscLpIndex,
      mscLpEngIndex,
      mscLpEngArcIndex,
      mscLpEngArcCqcIndex }
::= { mscLpEngArcCqcRowStatusTable 1 }

MscLpEngArcCqcRowStatusEntry ::= SEQUENCE {
   mscLpEngArcCqcRowStatus
      RowStatus,
   mscLpEngArcCqcComponentName
      DisplayString,
   mscLpEngArcCqcStorageType
      StorageType,
   mscLpEngArcCqcIndex
      NonReplicated }

mscLpEngArcCqcRowStatus OBJECT-TYPE
   SYNTAX     RowStatus 
   ACCESS     read-write
   STATUS     mandatory
   DESCRIPTION
     "This variable is used as the basis for SNMP naming of
      mscLpEngArcCqc components.
      These components can be added and deleted."
::= { mscLpEngArcCqcRowStatusEntry 1 }

mscLpEngArcCqcComponentName OBJECT-TYPE
   SYNTAX     DisplayString 
   ACCESS     read-only
   STATUS     mandatory
   DESCRIPTION
     "This variable provides the component's string name for
      use with the ASCII Console Interface"
::= { mscLpEngArcCqcRowStatusEntry 2 }

mscLpEngArcCqcStorageType OBJECT-TYPE
   SYNTAX     StorageType 
   ACCESS     read-only
   STATUS     mandatory
   DESCRIPTION
     "This variable represents the storage type value for the
      mscLpEngArcCqc tables."
::= { mscLpEngArcCqcRowStatusEntry 4 }

mscLpEngArcCqcIndex OBJECT-TYPE
   SYNTAX     NonReplicated 
   ACCESS     not-accessible
   STATUS     mandatory
   DESCRIPTION
     "This variable represents the index for the mscLpEngArcCqc tables."
::= { mscLpEngArcCqcRowStatusEntry 10 }

mscLpEngArcCqcOperTable OBJECT-TYPE
   SYNTAX     SEQUENCE OF MscLpEngArcCqcOperEntry
   ACCESS     not-accessible
   STATUS     mandatory
   DESCRIPTION
     "This group describes the usage of ATM-specific resources on a 
      Logical Processor running ATM services on a CQC based card."
::= { mscLpEngArcCqc 10 }

mscLpEngArcCqcOperEntry OBJECT-TYPE
   SYNTAX     MscLpEngArcCqcOperEntry
   ACCESS     not-accessible
   STATUS     mandatory
   DESCRIPTION
     "An entry in the mscLpEngArcCqcOperTable."
   INDEX {
      mscLpIndex,
      mscLpEngIndex,
      mscLpEngArcIndex,
      mscLpEngArcCqcIndex }
::= { mscLpEngArcCqcOperTable 1 }

MscLpEngArcCqcOperEntry ::= SEQUENCE {
   mscLpEngArcCqcCdvReduction
      INTEGER }

mscLpEngArcCqcCdvReduction OBJECT-TYPE
   SYNTAX     INTEGER  {
                 disabled(0),
                 enabled(1),
                 cardDependent(2) }
   ACCESS     read-only
   STATUS     mandatory
   DESCRIPTION
     "This attribute indicates if the reduction of the maximum Cell Delay 
      Variation (CDV) of shaped transmit traffic is applicable.
      
      When the value of this attribute is disabled, the CDV value can be 
      determined by the following equation:
      
      CDV <= 2/ASR + 1/LS
      
      where ASR is the Actual Shaping Rate of the connection and LS is 
      the Link Speed of the interface.
      
      When the value of this attribute is enabled, the CDV relationship 
      changes to the following equation:
      
      CDV <= 1/ASR + 1/LS"
::= { mscLpEngArcCqcOperEntry 1 }


-- Lp/n Eng Arc Cqc Override
-- This cmponent is used to configure the usage of ATM-specific 
-- resources on a Logical Processor running ATM services on CQC 
-- based cards. (This component is only permitted under Logical 
-- Processors which are linked to ATM card types.)

mscLpEngArcCqcOv OBJECT IDENTIFIER ::= { mscLpEngArcCqc 2 }



mscLpEngArcCqcOvRowStatusTable OBJECT-TYPE
   SYNTAX     SEQUENCE OF MscLpEngArcCqcOvRowStatusEntry
   ACCESS     not-accessible
   STATUS     mandatory
   DESCRIPTION
     "This entry controls the addition and deletion of 
      mscLpEngArcCqcOv components."
::= { mscLpEngArcCqcOv 1 }

mscLpEngArcCqcOvRowStatusEntry OBJECT-TYPE
   SYNTAX     MscLpEngArcCqcOvRowStatusEntry
   ACCESS     not-accessible
   STATUS     mandatory
   DESCRIPTION
     "A single entry in the table represents a single 
      mscLpEngArcCqcOv component."
   INDEX {
      mscLpIndex,
      mscLpEngIndex,
      mscLpEngArcIndex,
      mscLpEngArcCqcIndex,
      mscLpEngArcCqcOvIndex }
::= { mscLpEngArcCqcOvRowStatusTable 1 }

MscLpEngArcCqcOvRowStatusEntry ::= SEQUENCE {
   mscLpEngArcCqcOvRowStatus
      RowStatus,
   mscLpEngArcCqcOvComponentName
      DisplayString,
   mscLpEngArcCqcOvStorageType
      StorageType,
   mscLpEngArcCqcOvIndex
      NonReplicated }

mscLpEngArcCqcOvRowStatus OBJECT-TYPE
   SYNTAX     RowStatus 
   ACCESS     read-only
   STATUS     mandatory
   DESCRIPTION
     "This variable is used as the basis for SNMP naming of
      mscLpEngArcCqcOv components.
      These components cannot be added nor deleted."
::= { mscLpEngArcCqcOvRowStatusEntry 1 }

mscLpEngArcCqcOvComponentName OBJECT-TYPE
   SYNTAX     DisplayString 
   ACCESS     read-only
   STATUS     mandatory
   DESCRIPTION
     "This variable provides the component's string name for
      use with the ASCII Console Interface"
::= { mscLpEngArcCqcOvRowStatusEntry 2 }

mscLpEngArcCqcOvStorageType OBJECT-TYPE
   SYNTAX     StorageType 
   ACCESS     read-only
   STATUS     mandatory
   DESCRIPTION
     "This variable represents the storage type value for the
      mscLpEngArcCqcOv tables."
::= { mscLpEngArcCqcOvRowStatusEntry 4 }

mscLpEngArcCqcOvIndex OBJECT-TYPE
   SYNTAX     NonReplicated 
   ACCESS     not-accessible
   STATUS     mandatory
   DESCRIPTION
     "This variable represents the index for the mscLpEngArcCqcOv tables."
::= { mscLpEngArcCqcOvRowStatusEntry 10 }

mscLpEngArcCqcOvProvTable OBJECT-TYPE
   SYNTAX     SEQUENCE OF MscLpEngArcCqcOvProvEntry
   ACCESS     not-accessible
   STATUS     mandatory
   DESCRIPTION
     "This group specifies the configuration of processor-wide ATM-
      specific resources on a Logical Processor running ATM services. 
      Note that altering any of these parameters will result in a card 
      reboot."
::= { mscLpEngArcCqcOv 10 }

mscLpEngArcCqcOvProvEntry OBJECT-TYPE
   SYNTAX     MscLpEngArcCqcOvProvEntry
   ACCESS     not-accessible
   STATUS     mandatory
   DESCRIPTION
     "An entry in the mscLpEngArcCqcOvProvTable."
   INDEX {
      mscLpIndex,
      mscLpEngIndex,
      mscLpEngArcIndex,
      mscLpEngArcCqcIndex,
      mscLpEngArcCqcOvIndex }
::= { mscLpEngArcCqcOvProvTable 1 }

MscLpEngArcCqcOvProvEntry ::= SEQUENCE {
   mscLpEngArcCqcOvPerVcQueueInterfaces
      Unsigned32,
   mscLpEngArcCqcOvShapingScalingFactor
      FixedPoint1,
   mscLpEngArcCqcOvCdvReduction
      INTEGER,
   mscLpEngArcCqcOvPortCongestionPolicy
      INTEGER }

mscLpEngArcCqcOvPerVcQueueInterfaces OBJECT-TYPE
   SYNTAX     Unsigned32 (0..4)
   ACCESS     read-write
   STATUS     mandatory
   DESCRIPTION
     "This attribute specifies the number of independent ports or IMA 
      components which support shaping and per-VC queueing on this 
      FP. 
      
      When this attribute is not zero, at most 4 independent ports or 4 Ima 
      virtual links are supported, regardless of whether or not traffic 
      shaping is enabled on the associated AtmIf components. In this case 
      only independent port instances 0-3 or Ima instances 0-3 can be 
      supported on an associated AtmIf component.
      
      For 2 ports cards, the valid values for this attribute are 0, 1, or 2.
      For 3 ports cards, the valid values for this attribute are 0, 1, 2 or 3.
      For 8 ports cards, the valid values for this attribute are 0, 1, 2, or 4."
   DEFVAL     { 0 }
::= { mscLpEngArcCqcOvProvEntry 1 }

mscLpEngArcCqcOvShapingScalingFactor OBJECT-TYPE
   SYNTAX     FixedPoint1 (10 | 14 | 20 | 28 | 40 | 56)
   ACCESS     read-write
   STATUS     mandatory
   DESCRIPTION
     "This attribute specifies the scaling factor which is to be applied to 
      all shaping rates for this FP. The scaling factor is an inverse factor 
      which is applied to the chosen shaping rate to produce an actual 
      shaping rate. For example, if a shaping rate of 25 Mbit/s is used 
      with a scaling factor of 2, the actual shaping rate is 12.5 Mbit/s."
   DEFVAL     { 10 }
::= { mscLpEngArcCqcOvProvEntry 2 }

mscLpEngArcCqcOvCdvReduction OBJECT-TYPE
   SYNTAX     INTEGER  {
                 disabled(0),
                 enabled(1),
                 cardDependent(2) }
   ACCESS     read-write
   STATUS     mandatory
   DESCRIPTION
     "This attribute specifies the reduction of the maximum Cell Delay 
      Variation (CDV) of shaped transmit traffic.
      
      When the value of this attribute is set to disabled, the CDV value 
      can be determined by the following equation:
      
      CDV <= 2/ASR + 1/LS
      
      where ASR is the Actual Shaping Rate of the connection and LS is 
      the Link Speed of the interface.
      
      When the value of this attribute is set to enabled, the CDV 
      relationship changes to the following equation:
      
      CDV <= 1/ASR + 1/LS
      
      As can be noted from the equations above, setting this attribute to 
      enabled can reduce the CDV significantly. CDV reduction may be 
      used to conform to policers which have strict Cell Delay Variance 
      Tolerance (CDVT). However using this function reduces the 
      transmit bandwidth utilization of the following cards: 3pDS3Atm, 
      3pOC3Atm, 2pJ6MAtm.
      
      When the value is cardDependent, CDV reduction is disabled for 
      cardtypes 3pDS3Atm, 3pOC3Atm, 2pJ6MAtm, 4pDS1Aal1, 
      4pE1Aal1 and enabled for all other cards."
   DEFVAL     { cardDependent }
::= { mscLpEngArcCqcOvProvEntry 3 }

mscLpEngArcCqcOvPortCongestionPolicy OBJECT-TYPE
   SYNTAX     INTEGER  {
                 aggregate(0),
                 individualQueue(1) }
   ACCESS     read-write
   STATUS     mandatory
   DESCRIPTION
     "This attribute specifies the congestion behavior of all ports on 
      this FP. It applies only to transmit traffic served on the 
      common queues and does not apply to per-VC queues.
      
      When the value is aggregate, the enqueue decision of cells or 
      frames to a common queue is based upon the congestion state 
      of the entire port to which the queue belongs. A port is 
      defined to be as congested as the most congested queue 
      amongst all its common queues: the low, medium and high 
      emission priority queues. Thus, for example, if the low 
      priority queue is congested, the high priority queue also 
      experiences discards even though the high priority queue may 
      itself not be congested. Setting this attribute to aggregate 
      assures that the low priority queues are also serviced in the 
      event of congestion.
      
      When the value of this attribute is set to individualQueue, 
      the enqueue decision of cells or frames to a common queue is 
      based solely upon the congestion state of that queue, not the 
      port. This setting assures that the absolute priority of the traffic is 
      taken into account, regardless of whether the lower priority queues 
      are being served."
   DEFVAL     { aggregate }
::= { mscLpEngArcCqcOvProvEntry 4 }

mscLpEngArcCqcOvConnCapTable OBJECT-TYPE
   SYNTAX     SEQUENCE OF MscLpEngArcCqcOvConnCapEntry
   ACCESS     not-accessible
   STATUS     mandatory
   DESCRIPTION
     "This attribute is provided for backward compatibility and can only 
      be used if the LogicalProcessor is associated with a card of one of 
      the following cardType: 3pE3Atm, 3pDS3Atm, 3pOC3MmAtm, 
      3pOC3SmAtm, 3pE1Atm, 3pDS1Atm, 2pJ6MAtm. This attribute 
      can be used when the desired distribution of connections across 
      ports cannot be achieved using the totalConnectionPoolCapacity 
      attribute.
      
      This attribute defines the maximum number of connections (VCC, 
      VPC and VPT) that are available on each port. A basic Vpt uses 2 
      connections. The entries are indexed by port number. This number 
      limits the range of the ConnMap entries. If the Connmap 
      component does not exist, its default settings are used for this 
      check. Note that the value of this attribute must be evenly divisible 
      by 256, and that port 2 supports at most 2560 connections, not the 
      full 4096.
      
      The connection pool for each port must be set to 0 if the 
      totalConnectionPoolCapacity attribute is set to a non-zero value."
::= { mscLpEngArcCqcOv 450 }

mscLpEngArcCqcOvConnCapEntry OBJECT-TYPE
   SYNTAX     MscLpEngArcCqcOvConnCapEntry
   ACCESS     not-accessible
   STATUS     mandatory
   DESCRIPTION
     "An entry in the mscLpEngArcCqcOvConnCapTable."
   INDEX {
      mscLpIndex,
      mscLpEngIndex,
      mscLpEngArcIndex,
      mscLpEngArcCqcIndex,
      mscLpEngArcCqcOvIndex,
      mscLpEngArcCqcOvConnCapIndex }
::= { mscLpEngArcCqcOvConnCapTable 1 }

MscLpEngArcCqcOvConnCapEntry ::= SEQUENCE {
   mscLpEngArcCqcOvConnCapIndex
      Integer32,
   mscLpEngArcCqcOvConnCapValue
      Unsigned32 }

mscLpEngArcCqcOvConnCapIndex OBJECT-TYPE
   SYNTAX     Integer32 (0..2)
   ACCESS     not-accessible
   STATUS     mandatory
   DESCRIPTION
     "This variable represents the mscLpEngArcCqcOvConnCapTable
      specific index for the mscLpEngArcCqcOvConnCapTable."
::= { mscLpEngArcCqcOvConnCapEntry 1 }

mscLpEngArcCqcOvConnCapValue OBJECT-TYPE
   SYNTAX     Unsigned32 (0 | 512..4096)
   ACCESS     read-write
   STATUS     mandatory
   DESCRIPTION
     "This variable represents an individual value for the
      mscLpEngArcCqcOvConnCapTable."
::= { mscLpEngArcCqcOvConnCapEntry 2 }


-- Lp/n Eng Arc Aqm/n
-- The Aqm component describes the usage of ATM-specific resources 
-- on a LogicalProcessor running ATM services for a specific ATM 
-- Queue Manager. This component is always dynamically created 
-- under any LP Eng which supports an SGAF FP. The number of 
-- instances depends upon the type of card.
-- 
-- For the 4-port OC3 cards, in unprotected mode one AQM instance is 
-- used per Sonet or SDH port, where the AQM instance is the same as 
-- the Sonet or SDH port instance. For example, Sonet/0 uses AQM/0. 
-- In protected mode, ports 0 and 1 work together and ports 2 and 3 
-- work together. If ports 0 and 1 are a protection pair, then AQM/0 is 
-- used. AQM/1 is dormant. If ports 2 and 3 are a protection pair, then 
-- AQM/2 is used. AQM/3 is dormant.
-- 
-- For the 1pOC12SmLrAtm card, only AQM/0 exists. Two physical 
-- ports exist, but if both ports are provisioned the second may be used 
-- for protection only. 
-- 
-- For 12pDS3Atm and 12pE3Atm cards, an AQM instance exists for 
-- each set of three ports. As clarification, DS3/0, DS3/1, and DS3/2 
-- use AQM/0. DS3/3, DS3/4, and DS3/5 use AQM/1. DS3/6, DS3/7, 
-- and DS3/8 use AQM/2. DS3/9, DS3/10, and DS3/11 use AQM/3.

mscLpEngArcAqm OBJECT IDENTIFIER ::= { mscLpEngArc 4 }



mscLpEngArcAqmRowStatusTable OBJECT-TYPE
   SYNTAX     SEQUENCE OF MscLpEngArcAqmRowStatusEntry
   ACCESS     not-accessible
   STATUS     mandatory
   DESCRIPTION
     "This entry controls the addition and deletion of 
      mscLpEngArcAqm components."
::= { mscLpEngArcAqm 1 }

mscLpEngArcAqmRowStatusEntry OBJECT-TYPE
   SYNTAX     MscLpEngArcAqmRowStatusEntry
   ACCESS     not-accessible
   STATUS     mandatory
   DESCRIPTION
     "A single entry in the table represents a single 
      mscLpEngArcAqm component."
   INDEX {
      mscLpIndex,
      mscLpEngIndex,
      mscLpEngArcIndex,
      mscLpEngArcAqmIndex }
::= { mscLpEngArcAqmRowStatusTable 1 }

MscLpEngArcAqmRowStatusEntry ::= SEQUENCE {
   mscLpEngArcAqmRowStatus
      RowStatus,
   mscLpEngArcAqmComponentName
      DisplayString,
   mscLpEngArcAqmStorageType
      StorageType,
   mscLpEngArcAqmIndex
      Integer32 }

mscLpEngArcAqmRowStatus OBJECT-TYPE
   SYNTAX     RowStatus 
   ACCESS     read-write
   STATUS     mandatory
   DESCRIPTION
     "This variable is used as the basis for SNMP naming of
      mscLpEngArcAqm components.
      These components can be added and deleted."
::= { mscLpEngArcAqmRowStatusEntry 1 }

mscLpEngArcAqmComponentName OBJECT-TYPE
   SYNTAX     DisplayString 
   ACCESS     read-only
   STATUS     mandatory
   DESCRIPTION
     "This variable provides the component's string name for
      use with the ASCII Console Interface"
::= { mscLpEngArcAqmRowStatusEntry 2 }

mscLpEngArcAqmStorageType OBJECT-TYPE
   SYNTAX     StorageType 
   ACCESS     read-only
   STATUS     mandatory
   DESCRIPTION
     "This variable represents the storage type value for the
      mscLpEngArcAqm tables."
::= { mscLpEngArcAqmRowStatusEntry 4 }

mscLpEngArcAqmIndex OBJECT-TYPE
   SYNTAX     Integer32 (0..3)
   ACCESS     not-accessible
   STATUS     mandatory
   DESCRIPTION
     "This variable represents the index for the mscLpEngArcAqm tables."
::= { mscLpEngArcAqmRowStatusEntry 10 }

mscLpEngArcAqmOperTable OBJECT-TYPE
   SYNTAX     SEQUENCE OF MscLpEngArcAqmOperEntry
   ACCESS     not-accessible
   STATUS     mandatory
   DESCRIPTION
     "This group describes the usage of ATM-specific resources for a 
      specific AQM on a Logical Processor running ATM services."
::= { mscLpEngArcAqm 10 }

mscLpEngArcAqmOperEntry OBJECT-TYPE
   SYNTAX     MscLpEngArcAqmOperEntry
   ACCESS     not-accessible
   STATUS     mandatory
   DESCRIPTION
     "An entry in the mscLpEngArcAqmOperTable."
   INDEX {
      mscLpIndex,
      mscLpEngIndex,
      mscLpEngArcIndex,
      mscLpEngArcAqmIndex }
::= { mscLpEngArcAqmOperTable 1 }

MscLpEngArcAqmOperEntry ::= SEQUENCE {
   mscLpEngArcAqmConnectionPoolAvailable
      Unsigned32,
   mscLpEngArcAqmConnectionPoolUsage
      Unsigned32,
   mscLpEngArcAqmTxCellMemoryAvailable
      Gauge32,
   mscLpEngArcAqmTxCellMemoryMinAvailable
      Gauge32,
   mscLpEngArcAqmTxCellMemoryCongestionState
      Gauge32 }

mscLpEngArcAqmConnectionPoolAvailable OBJECT-TYPE
   SYNTAX     Unsigned32 (0..16000)
   ACCESS     read-only
   STATUS     mandatory
   DESCRIPTION
     "This attribute indicates the number of connection resources 
      available (VCC, VPC and VPT) that can be configured on the AQM 
      instance of the LogicalProcessor.
      
      A standard Vpt uses 3 connection resources and a basic Vpt uses 2."
::= { mscLpEngArcAqmOperEntry 1 }

mscLpEngArcAqmConnectionPoolUsage OBJECT-TYPE
   SYNTAX     Unsigned32 (0..16000)
   ACCESS     read-only
   STATUS     mandatory
   DESCRIPTION
     "This attribute indicates the total number of configured VCCs, VPCs 
      and VPTs in AtmIfs associated with the AQM instance of the 
      LogicalProcessor. 
      
      A standard Vpt uses 3 connection resources and a basic Vpt uses 2."
::= { mscLpEngArcAqmOperEntry 2 }

mscLpEngArcAqmTxCellMemoryAvailable OBJECT-TYPE
   SYNTAX     Gauge32 (0..163839)
   ACCESS     read-only
   STATUS     mandatory
   DESCRIPTION
     "This attribute indicates the current availability of the transmit 
      cell memory. 
      
      The transmit cell memory is the memory available for storing ATM 
      cells to be transmitted by the Lp."
::= { mscLpEngArcAqmOperEntry 5 }

mscLpEngArcAqmTxCellMemoryMinAvailable OBJECT-TYPE
   SYNTAX     Gauge32 (0..163839)
   ACCESS     read-only
   STATUS     mandatory
   DESCRIPTION
     "This attribute indicates the lowest availability of the transmit 
      cell memory. 
      
      The transmit cell memory is the memory available for storing ATM 
      cells to be transmitted by the Lp.
      
      This attribute is reset to the current availability every 15 minutes 
      and when the card is reset."
::= { mscLpEngArcAqmOperEntry 6 }

mscLpEngArcAqmTxCellMemoryCongestionState OBJECT-TYPE
   SYNTAX     Gauge32 (0..3)
   ACCESS     read-only
   STATUS     mandatory
   DESCRIPTION
     "This attribute indicates the congestion state of the transmit cell 
      memory on this FP. 
      
      The congestion state of memory is indicated by a numeric value 
      ranging from 0 to 3. When memory is in a congested state 'x', only 
      traffic with discard priority (DP) 0 to 'x' is processed. Traffic with 
      DP > 'x' is discarded. 
      
      Therefore, if the congestion state is 3, there is no congestion and all 
      traffic is stored. Likewise, when the congestion state is 0, there is 
      maximum congestion and only traffic with DP=0 is processed."
::= { mscLpEngArcAqmOperEntry 7 }

mscLpEngArcAqmTxCellThreshTable OBJECT-TYPE
   SYNTAX     SEQUENCE OF MscLpEngArcAqmTxCellThreshEntry
   ACCESS     not-accessible
   STATUS     mandatory
   DESCRIPTION
     "This attribute indicates the total transmit cell memory size and the 
      discard thresholds of the transmit cell memory. The transmit cell 
      memory is the memory used for storing ATM cells to be transmitted 
      by the Lp.
      
      The first value indicates the total transmit cell memory size. This is 
      derived based upon the connectionPoolCapacity value.
      
      When the txCellMemoryAvailable attribute decreases to the second 
      value, the txCellMemoryCongestionState changes from 3 to 2. In 
      congestion state 2, traffic with discard priority (DP) = 3 is 
      discarded. This threshold is set approximately at 25 percent of the 
      first value, the total transmit cell memory size.
      
      When the txCellMemoryAvailable attribute decreases to the third 
      value, the txCellMemoryCongestionState changes from 2 to 1. In 
      congestion state 1, traffic with discard priority (DP) >= 2 is 
      discarded. This threshold is set approximately at 20 percent of the 
      first value, the total transmit cell memory size.
      
      When the txCellMemoryAvailable attribute decreases to the fourth 
      value, the txCellMemoryCongestionState changes from 1 to 0. In 
      congestion state 0, traffic with discard priority (DP) >= 1 is 
      discarded. This threshold is set approximately at 10 percent of the 
      first value, the total transmit cell memory size.
      
      The opposite effect occurs when the txCellMemoryAvailable 
      attribute increases (txCellMemoryCongestionState increases from 0 
      to 3 accordingly)"
::= { mscLpEngArcAqm 448 }

mscLpEngArcAqmTxCellThreshEntry OBJECT-TYPE
   SYNTAX     MscLpEngArcAqmTxCellThreshEntry
   ACCESS     not-accessible
   STATUS     mandatory
   DESCRIPTION
     "An entry in the mscLpEngArcAqmTxCellThreshTable."
   INDEX {
      mscLpIndex,
      mscLpEngIndex,
      mscLpEngArcIndex,
      mscLpEngArcAqmIndex,
      mscLpEngArcAqmTxCellThreshIndex }
::= { mscLpEngArcAqmTxCellThreshTable 1 }

MscLpEngArcAqmTxCellThreshEntry ::= SEQUENCE {
   mscLpEngArcAqmTxCellThreshIndex
      Integer32,
   mscLpEngArcAqmTxCellThreshValue
      Unsigned32 }

mscLpEngArcAqmTxCellThreshIndex OBJECT-TYPE
   SYNTAX     Integer32 (0..3)
   ACCESS     not-accessible
   STATUS     mandatory
   DESCRIPTION
     "This variable represents the mscLpEngArcAqmTxCellThreshTable
      specific index for the mscLpEngArcAqmTxCellThreshTable."
::= { mscLpEngArcAqmTxCellThreshEntry 1 }

mscLpEngArcAqmTxCellThreshValue OBJECT-TYPE
   SYNTAX     Unsigned32 (0..163839)
   ACCESS     read-only
   STATUS     mandatory
   DESCRIPTION
     "This variable represents an individual value for the
      mscLpEngArcAqmTxCellThreshTable."
::= { mscLpEngArcAqmTxCellThreshEntry 2 }


-- Lp/n Eng Arc Aqm/n Override
-- The Aqm Override component is used to configure the usage of 
-- ATM-specific resources for a specific AQM on a Logical Processor 
-- running ATM services. (This component is only permitted under 
-- Logical Processors which are linked to ATM card types.)

mscLpEngArcAqmOv OBJECT IDENTIFIER ::= { mscLpEngArcAqm 2 }



mscLpEngArcAqmOvRowStatusTable OBJECT-TYPE
   SYNTAX     SEQUENCE OF MscLpEngArcAqmOvRowStatusEntry
   ACCESS     not-accessible
   STATUS     mandatory
   DESCRIPTION
     "This entry controls the addition and deletion of 
      mscLpEngArcAqmOv components."
::= { mscLpEngArcAqmOv 1 }

mscLpEngArcAqmOvRowStatusEntry OBJECT-TYPE
   SYNTAX     MscLpEngArcAqmOvRowStatusEntry
   ACCESS     not-accessible
   STATUS     mandatory
   DESCRIPTION
     "A single entry in the table represents a single 
      mscLpEngArcAqmOv component."
   INDEX {
      mscLpIndex,
      mscLpEngIndex,
      mscLpEngArcIndex,
      mscLpEngArcAqmIndex,
      mscLpEngArcAqmOvIndex }
::= { mscLpEngArcAqmOvRowStatusTable 1 }

MscLpEngArcAqmOvRowStatusEntry ::= SEQUENCE {
   mscLpEngArcAqmOvRowStatus
      RowStatus,
   mscLpEngArcAqmOvComponentName
      DisplayString,
   mscLpEngArcAqmOvStorageType
      StorageType,
   mscLpEngArcAqmOvIndex
      NonReplicated }

mscLpEngArcAqmOvRowStatus OBJECT-TYPE
   SYNTAX     RowStatus 
   ACCESS     read-only
   STATUS     mandatory
   DESCRIPTION
     "This variable is used as the basis for SNMP naming of
      mscLpEngArcAqmOv components.
      These components cannot be added nor deleted."
::= { mscLpEngArcAqmOvRowStatusEntry 1 }

mscLpEngArcAqmOvComponentName OBJECT-TYPE
   SYNTAX     DisplayString 
   ACCESS     read-only
   STATUS     mandatory
   DESCRIPTION
     "This variable provides the component's string name for
      use with the ASCII Console Interface"
::= { mscLpEngArcAqmOvRowStatusEntry 2 }

mscLpEngArcAqmOvStorageType OBJECT-TYPE
   SYNTAX     StorageType 
   ACCESS     read-only
   STATUS     mandatory
   DESCRIPTION
     "This variable represents the storage type value for the
      mscLpEngArcAqmOv tables."
::= { mscLpEngArcAqmOvRowStatusEntry 4 }

mscLpEngArcAqmOvIndex OBJECT-TYPE
   SYNTAX     NonReplicated 
   ACCESS     not-accessible
   STATUS     mandatory
   DESCRIPTION
     "This variable represents the index for the mscLpEngArcAqmOv tables."
::= { mscLpEngArcAqmOvRowStatusEntry 10 }

mscLpEngArcAqmOvProvTable OBJECT-TYPE
   SYNTAX     SEQUENCE OF MscLpEngArcAqmOvProvEntry
   ACCESS     not-accessible
   STATUS     mandatory
   DESCRIPTION
     "This group specifies the configuration of processor-wide ATM-
      specific resources on a Logical Processor running ATM services on 
      CQC based cards. Note that altering any of these parameters will 
      result in a card reboot."
::= { mscLpEngArcAqmOv 10 }

mscLpEngArcAqmOvProvEntry OBJECT-TYPE
   SYNTAX     MscLpEngArcAqmOvProvEntry
   ACCESS     not-accessible
   STATUS     mandatory
   DESCRIPTION
     "An entry in the mscLpEngArcAqmOvProvTable."
   INDEX {
      mscLpIndex,
      mscLpEngIndex,
      mscLpEngArcIndex,
      mscLpEngArcAqmIndex,
      mscLpEngArcAqmOvIndex }
::= { mscLpEngArcAqmOvProvTable 1 }

MscLpEngArcAqmOvProvEntry ::= SEQUENCE {
   mscLpEngArcAqmOvConnectionPoolCapacity
      Unsigned32,
   mscLpEngArcAqmOvHighPriorityEpdOffset
      Unsigned32,
   mscLpEngArcAqmOvLowPriorityEpdOffset
      Unsigned32,
   mscLpEngArcAqmOvPortCongestionPolicy
      INTEGER }

mscLpEngArcAqmOvConnectionPoolCapacity OBJECT-TYPE
   SYNTAX     Unsigned32 (0 | 1..16000)
   ACCESS     read-write
   STATUS     mandatory
   DESCRIPTION
     "This attribute specifies the maximum number of connections 
      (VCC, VPC and VPT) that can be configured on the AQM 
      instance of the LogicalProcessor. 
      
      The value of the attribute restricts the sum of the (maxVccs + 
      maxVpcs +(maxVpts * 3)) across all AtmIfs bound to this AQM 
      instance. Note that 3 connections are used for each standard Vpt and 
      2 for each basic Vpt.
      
      The value of this attribute should be less than than or equal to 
      totalConnectionPoolCapacity of the Arc component.
      
      The default value derivedFromArc is obtained using the following 
      equation: 
      
      totalConnectionPoolCapacity / number of AQM component on FP.

      VALUES (

      0 = derivedFromArc

      )"
   DEFVAL     { 0 }
::= { mscLpEngArcAqmOvProvEntry 1 }

mscLpEngArcAqmOvHighPriorityEpdOffset OBJECT-TYPE
   SYNTAX     Unsigned32 (5..1024)
   ACCESS     read-write
   STATUS     mandatory
   DESCRIPTION
     "This attribute specifies the high priority Early Packet Discard (EPD) 
      offset for connection queues. On ATM IP FPs a given connection 
      queue is associated with one of eight emission priorities (EP). These 
      include six unshaped EPs, one exclusive VBR shaper EP and one 
      ABR/VBR shaper EP. This attribute specifies the EPD offset for the 
      exclusive VBR shaper EP and the first four (higher priority) 
      unshaped EPs.
      
      This offset is used to derive a connection EPD threshold for a given 
      Congestion Control (CC) level by subtracting the offset from the 
      All Packet Discard (APD) threshold at the same CC level. The APD 
      thresholds are themselves derived from the transmit queue limit.
      
      The EPD threshold only applies to a connection if the 
      txPacketWiseDiscard feature is requested. The 
      txPacketWiseDiscard feature can be enabled only if the transmit 
      queue limit is at least 5.71 times the EPD offset. This ensures that 
      the derived EPD threshold will never be less than 17.5 % of the 
      transmit queue limit. If this condition is not satisfied, 
      txPacketWiseDiscard for the connection will be automatically 
      disabled.
      
      Due to the above constraint, if the operator wishes to decrease the 
      transmit queue limit and still have txPacketWiseDiscard enabled on 
      the connection then this offset must be set to a lower value that 
      meets the above requirement.
      
      Due to hardware granularity the actual value of the EPD offset may 
      not match exactly the value provisioned. The actual value is 
      displayed under the ATM Connection Administrator service 
      category subcomponents on ATM IP FPs.
      
      This attribute does not apply to CQC FPs."
   DEFVAL     { 28 }
::= { mscLpEngArcAqmOvProvEntry 2 }

mscLpEngArcAqmOvLowPriorityEpdOffset OBJECT-TYPE
   SYNTAX     Unsigned32 (5..1024)
   ACCESS     read-write
   STATUS     mandatory
   DESCRIPTION
     "This attribute specifies the low priority Early Packet Discard (EPD) 
      offset for connection queues. On ATM IP FPs a given connection 
      queue is associated with one of eight emission priorities (EP). These 
      include six unshaped EPs, one exclusive VBR shaper EP and one 
      ABR/VBR shaper EP. This attribute specifies the EPD offset for the 
      exclusive ABR/VBR shaper EP and the last two (lower priority) 
      unshaped EPs.
      
      This offset is used to derive a connection EPD threshold for a given 
      Congestion Control (CC) level by subtracting the offset from the 
      All Packet Discard (APD) threshold at the same CC level. The APD 
      thresholds are themselves derived from the transmit queue limit.
      
      The EPD threshold only applies to a connection if the 
      txPacketWiseDiscard feature is requested. The 
      txPacketWiseDiscard feature can be enabled only if the transmit 
      queue limit is at least 5.71 times the EPD offset. This ensures that 
      the derived EPD threshold will never be less than 17.5 % of the 
      transmit queue limit. If this condition is not satisfied, 
      txPacketWiseDiscard for the connection will be automatically 
      disabled.
      
      Due to the above constraint, if the operator wishes to decrease the 
      transmit queue limit and still have txPacketWiseDiscard enabled on 
      the connection then this offset must be set to a lower value that 
      meets the above requirement.
      
      Due to hardware granularity the actual value of the EPD offset may 
      not match exactly the value provisioned. The actual value is 
      displayed under the ATM Connection Administrator service 
      category subcomponents on ATM IP FPs.
      
      This attribute does not apply to CQC FPs."
   DEFVAL     { 200 }
::= { mscLpEngArcAqmOvProvEntry 3 }

mscLpEngArcAqmOvPortCongestionPolicy OBJECT-TYPE
   SYNTAX     INTEGER  {
                 aggregate(0),
                 individualQueue(1) }
   ACCESS     read-write
   STATUS     mandatory
   DESCRIPTION
     "This attribute specifies the congestion behavior of all ports on this 
      FP. It applies only to transmit traffic and does not apply to the CBR 
      service category. 
      
      When the value is aggregate, the enqueue decision of cells or 
      frames to a queue is based upon the congestion state of the entire 
      port to which the queue belongs. A port is defined to be as 
      congested as the most congested queue amongst all its queues. 
      Thus, for example, if a nrtVBR queue is congested, the rtVBR 
      queue also experiences discards even though the rtVBR queue may 
      itself not be congested. Setting this attribute to aggregate assures 
      that the low priority queues are also serviced in the event of 
      congestion. If this attribute is set to aggregate then rtVBR must not 
      be configured to do common queueing and its emissionPriority 
      should be set to a number numerically smaller than or equal to 3. 
      Another impact of setting this attribute to aggregate is that the per 
      connection queue limits for nrtVBR and UBR connections will be 
      increased to the link pool size and their discard thresholds will be 
      modified to be aligned with the free list discard thresholds.
      
      When the value of this attribute is set to individualQueue, 
      the enqueue decision of cells or frames to a queue is based solely 
      upon the congestion state of that queue, not the port. This setting 
      assures that the absolute priority of the traffic is taken into account, 
      regardless of whether the lower priority queues are being served. On 
      3pOC3SmAtm2 and 3pOC3MmAtm2 cards, if more than one 
      override component exists, they must have the same setting for this 
      attribute. Otherwise, setting the attribute under one override 
      component applies to the entire card."
   DEFVAL     { individualQueue }
::= { mscLpEngArcAqmOvProvEntry 4 }


-- Lp/n Eng FrameCoreResourceControl
-- This component is used to view the usage of frame specific 
-- resources on a LogicalProcessor running Frame based services.

mscLpEngFcrc OBJECT IDENTIFIER ::= { mscLpEng 6 }



mscLpEngFcrcRowStatusTable OBJECT-TYPE
   SYNTAX     SEQUENCE OF MscLpEngFcrcRowStatusEntry
   ACCESS     not-accessible
   STATUS     mandatory
   DESCRIPTION
     "This entry controls the addition and deletion of 
      mscLpEngFcrc components."
::= { mscLpEngFcrc 1 }

mscLpEngFcrcRowStatusEntry OBJECT-TYPE
   SYNTAX     MscLpEngFcrcRowStatusEntry
   ACCESS     not-accessible
   STATUS     mandatory
   DESCRIPTION
     "A single entry in the table represents a single 
      mscLpEngFcrc component."
   INDEX {
      mscLpIndex,
      mscLpEngIndex,
      mscLpEngFcrcIndex }
::= { mscLpEngFcrcRowStatusTable 1 }

MscLpEngFcrcRowStatusEntry ::= SEQUENCE {
   mscLpEngFcrcRowStatus
      RowStatus,
   mscLpEngFcrcComponentName
      DisplayString,
   mscLpEngFcrcStorageType
      StorageType,
   mscLpEngFcrcIndex
      NonReplicated }

mscLpEngFcrcRowStatus OBJECT-TYPE
   SYNTAX     RowStatus 
   ACCESS     read-write
   STATUS     mandatory
   DESCRIPTION
     "This variable is used as the basis for SNMP naming of
      mscLpEngFcrc components.
      These components can be added and deleted."
::= { mscLpEngFcrcRowStatusEntry 1 }

mscLpEngFcrcComponentName OBJECT-TYPE
   SYNTAX     DisplayString 
   ACCESS     read-only
   STATUS     mandatory
   DESCRIPTION
     "This variable provides the component's string name for
      use with the ASCII Console Interface"
::= { mscLpEngFcrcRowStatusEntry 2 }

mscLpEngFcrcStorageType OBJECT-TYPE
   SYNTAX     StorageType 
   ACCESS     read-only
   STATUS     mandatory
   DESCRIPTION
     "This variable represents the storage type value for the
      mscLpEngFcrc tables."
::= { mscLpEngFcrcRowStatusEntry 4 }

mscLpEngFcrcIndex OBJECT-TYPE
   SYNTAX     NonReplicated 
   ACCESS     not-accessible
   STATUS     mandatory
   DESCRIPTION
     "This variable represents the index for the mscLpEngFcrc tables."
::= { mscLpEngFcrcRowStatusEntry 10 }

mscLpEngFcrcOperTable OBJECT-TYPE
   SYNTAX     SEQUENCE OF MscLpEngFcrcOperEntry
   ACCESS     not-accessible
   STATUS     mandatory
   DESCRIPTION
     "This group indicates the configuration of processor-wide frame 
      specific resources on a LogicalProcessor."
::= { mscLpEngFcrc 10 }

mscLpEngFcrcOperEntry OBJECT-TYPE
   SYNTAX     MscLpEngFcrcOperEntry
   ACCESS     not-accessible
   STATUS     mandatory
   DESCRIPTION
     "An entry in the mscLpEngFcrcOperTable."
   INDEX {
      mscLpIndex,
      mscLpEngIndex,
      mscLpEngFcrcIndex }
::= { mscLpEngFcrcOperTable 1 }

MscLpEngFcrcOperEntry ::= SEQUENCE {
   mscLpEngFcrcSubConnectionPoolAvailable
      Unsigned32,
   mscLpEngFcrcSubConnectionPoolUsage
      Unsigned32,
   mscLpEngFcrcLnnConnectionPoolAvailable
      Unsigned32,
   mscLpEngFcrcLnnConnectionPoolUsage
      Unsigned32,
   mscLpEngFcrcTxFrameMemoryAvailable
      Gauge32,
   mscLpEngFcrcTxFrameMemoryMinAvailable
      Gauge32,
   mscLpEngFcrcTxFrameMemoryCongestionState
      Gauge32,
   mscLpEngFcrcRxFrameMemoryAvailable
      Gauge32,
   mscLpEngFcrcRxFrameMemoryMinAvailable
      Gauge32,
   mscLpEngFcrcRxFrameMemoryCongestionState
      Gauge32 }

mscLpEngFcrcSubConnectionPoolAvailable OBJECT-TYPE
   SYNTAX     Unsigned32 (0..49152)
   ACCESS     read-only
   STATUS     mandatory
   DESCRIPTION
     "This attribute indicates the number of sub-connections available for 
      the LogicalProcessor. 
      
      A sub-connection is used for interworking the ATM services with 
      the frame oriented services such as Frame Relay and Path Oriented 
      Routing System (PORS). When a frame is received at a sub-
      connection, the frame header is modified to be compatible with the 
      service it is to be forwarded to. 
      
      This pool is used for connection oriented services only. Each of the 
      following components uses one sub-connection from this pool: 
      FrAtm/n Dlci/n Siwf
      McsMgr Frf5EpG/n Frf5Ep/n Lmi
      McsMgr Frf5EpG/n Frf5Ep/n Dlci/n
      
      Note: When the value of this attribute reaches zero, no more 
      connections are accepted for any of the services which utilize this 
      pool. To increase the size of this pool, use the Lp Eng Fcrc Ov 
      subConnectionPoolCapacity attribute."
::= { mscLpEngFcrcOperEntry 1 }

mscLpEngFcrcSubConnectionPoolUsage OBJECT-TYPE
   SYNTAX     Unsigned32 (0..49152)
   ACCESS     read-only
   STATUS     mandatory
   DESCRIPTION
     "This attribute indicates the number of sub-connections being 
      utilized by the LogicalProcessor.
      
      A sub-connection is used for interworking the ATM services with 
      the frame oriented services such as Frame Relay and Path Oriented 
      Routing System (PORS). When a frame is received at a sub-
      connection, the frame header is modified to be compatible with the 
      service it is to be forwarded to.
      
      This pool is used for connection oriented services only. Each of the 
      following components uses one sub-connection from this pool: 
      FrAtm/n Dlci/n Siwf
      McsMgr Frf5EpG/n Frf5Ep/n Lmi
      McsMgr Frf5EpG/n Frf5Ep/n Dlci/n"
::= { mscLpEngFcrcOperEntry 2 }

mscLpEngFcrcLnnConnectionPoolAvailable OBJECT-TYPE
   SYNTAX     Unsigned32 (0..2048)
   ACCESS     read-only
   STATUS     mandatory
   DESCRIPTION
     "This attribute indicates the number of resource records available for 
      the connections which utilize Logical Network Number (LNN) on 
      the LogicalProcessor.
      
      A logical network is a subset of Passport modules together with a 
      subset of trunks that interconnect those modules. It carries the 
      traffic for a defined set of network protocols. An LNN is used to 
      identify a logical network. The connectionless services which 
      utilize the logical networks require some processing at the 
      intermediate nodes. This pool is allocated at the intermediate nodes 
      to sustain these connectionless services.
      
      If the McsMgr DprsMcsEpG/n Ep/n EpD 
      transportConnectionPreference attribute is set to atmOnly, each 
      instance of the McsMgr DprsMcsEpG/n Ep/n component uses one 
      resource record from this pool, otherwise it does not use this pool.
      
      When the value of this attribute reaches zero, no more connections 
      are accepted for any of the services which utilize this pool. To 
      increase the size of this pool, use the Fcrc Ov 
      lnnConnectionPoolCapacity attribute."
::= { mscLpEngFcrcOperEntry 3 }

mscLpEngFcrcLnnConnectionPoolUsage OBJECT-TYPE
   SYNTAX     Unsigned32 (0..2048)
   ACCESS     read-only
   STATUS     mandatory
   DESCRIPTION
     "This attribute indicates the number of resource records being 
      utilized for the connections which use Logical Network Number 
      (LNN) on the LogicalProcessor.
      
      A logical network is a subset of Passport modules together with a 
      subset of trunks that interconnect those modules. It carries the 
      traffic for a defined set of network protocols. An LNN is used to 
      identify a logical network. The connectionless services which 
      utilize the logical networks require some processing at the 
      intermediate nodes. This pool is applied at the intermediate nodes to 
      sustain these connectionless services.
      
      If the McsMgr DprsMcsEpG/n Ep/n EpD 
      transportConnectionPreference attribute is set to atmOnly, each 
      instance of the McsMgr DprsMcsEpG/n Ep/n component uses one 
      resource record from this pool, otherwise it does not use this pool."
::= { mscLpEngFcrcOperEntry 4 }

mscLpEngFcrcTxFrameMemoryAvailable OBJECT-TYPE
   SYNTAX     Gauge32 (0..32767)
   ACCESS     read-only
   STATUS     mandatory
   DESCRIPTION
     "This attribute indicates the current availability of the transmit frame 
      memory (in units of frames). 
      
      The transmit frame memory is the memory available for storing 
      frames to be transmitted by this FP."
::= { mscLpEngFcrcOperEntry 5 }

mscLpEngFcrcTxFrameMemoryMinAvailable OBJECT-TYPE
   SYNTAX     Gauge32 (0..32767)
   ACCESS     read-only
   STATUS     mandatory
   DESCRIPTION
     "This attribute indicates the lowest availability of the transmit PQC/
      CQC frame memory (in units of frames). 
      
      The transmit frame memory is the memory available for storing 
      frames to be transmitted by this FP.
      
      This value is reset every 15 minutes and when the card is reset."
::= { mscLpEngFcrcOperEntry 6 }

mscLpEngFcrcTxFrameMemoryCongestionState OBJECT-TYPE
   SYNTAX     Gauge32 (0..3)
   ACCESS     read-only
   STATUS     mandatory
   DESCRIPTION
     "This attribute indicates the congestion state of the transmit frame 
      memory on this FP. 
      
      The congestion state of memory is indicated by a numeric value 
      ranging from 0 to 3. When memory is in a congested state 'x', only 
      traffic with discard priority (DP) 0 to 'x' is processed. Traffic with 
      DP > 'x' is discarded. 
      
      Therefore, if the congestion state is 3, there is no congestion and all 
      traffic is processed. Likewise, when the congestion state is 0, there 
      is maximum congestion and only traffic with DP=0 is processed."
::= { mscLpEngFcrcOperEntry 7 }

mscLpEngFcrcRxFrameMemoryAvailable OBJECT-TYPE
   SYNTAX     Gauge32 (0..32767)
   ACCESS     read-only
   STATUS     mandatory
   DESCRIPTION
     "This attribute indicates the current availability of the receive frame 
      memory (in units of frames). 
      
      The receive frame memory is the memory available for storing 
      frames received by this FP."
::= { mscLpEngFcrcOperEntry 8 }

mscLpEngFcrcRxFrameMemoryMinAvailable OBJECT-TYPE
   SYNTAX     Gauge32 (0..32767)
   ACCESS     read-only
   STATUS     mandatory
   DESCRIPTION
     "This attribute indicates the lowest availability of the receive frame 
      memory (in units of frames).
      
      The receive frame memory is the memory available for storing 
      frames received by this FP.
      
      This value is reset every 15 minutes and when the card is reset."
::= { mscLpEngFcrcOperEntry 9 }

mscLpEngFcrcRxFrameMemoryCongestionState OBJECT-TYPE
   SYNTAX     Gauge32 (0..3)
   ACCESS     read-only
   STATUS     mandatory
   DESCRIPTION
     "This attribute indicates the congestion state of the receive frame 
      memory on this FP. 
      
      The congestion state of memory is indicated by a numeric value 
      ranging from 0 to 3. When memory is in a congested state 'x', only 
      traffic with discard priority (DP) 0 to 'x' is processed. Traffic with 
      DP > 'x' is discarded. 
      
      Therefore, if the congestion state is 3, there is no congestion and all 
      traffic is stored. Likewise, when the congestion state is 0, there is 
      maximum congestion and only traffic with DP=0 is stored."
::= { mscLpEngFcrcOperEntry 10 }

mscLpEngFcrcTxFrThreshTable OBJECT-TYPE
   SYNTAX     SEQUENCE OF MscLpEngFcrcTxFrThreshEntry
   ACCESS     not-accessible
   STATUS     mandatory
   DESCRIPTION
     "This attribute indicates the total transmit frame memory size and the 
      discard thresholds of the transmit frame memory. The transmit 
      frame memory is the memory (in units of frames) used for storing 
      frames to be transmitted by this FP.
      
      The first parameter indicates the total size of the transmit frame 
      memory. This is derived from the connectionPoolCapacity and the 
      txCellMemoryAllocation under the ARC component.
      
      When the txFrameMemoryAvailable attribute decreases to the 
      second value, the txFrameMemoryCongestionState changes from 3 
      to 2. In congestion state 2, traffic with discard priority (DP) = 3 is 
      discarded. This threshold is set approximately at 25 percent of the 
      first value, the total transmit frame memory size.
      
      When the txFrameMemoryAvailable attribute decreases to the third 
      value, the txFrameMemoryCongestionState changes from 2 to 1. In 
      congestion state 1, traffic with discard priority (DP) >= 2 is 
      discarded. This threshold is set approximately at 20 percent of the 
      first value, the total transmit frame memory size.
      
      When the txFrameMemoryAvailable attribute decreases to the 
      fourth value, the txFrameMemoryCongestionState changes from 1 
      to 0. In congestion state 0, traffic with discard priority (DP) >= 1 is 
      discarded. This threshold is set approximately at 10 percent of the 
      first value, the total transmit frame memory size.
      
      The opposite effect occurs when the txFrameMemoryAvailable 
      attribute increases (txFrameMemoryCongestionState increases from 
      0 to 3 accordingly)."
::= { mscLpEngFcrc 442 }

mscLpEngFcrcTxFrThreshEntry OBJECT-TYPE
   SYNTAX     MscLpEngFcrcTxFrThreshEntry
   ACCESS     not-accessible
   STATUS     mandatory
   DESCRIPTION
     "An entry in the mscLpEngFcrcTxFrThreshTable."
   INDEX {
      mscLpIndex,
      mscLpEngIndex,
      mscLpEngFcrcIndex,
      mscLpEngFcrcTxFrThreshIndex }
::= { mscLpEngFcrcTxFrThreshTable 1 }

MscLpEngFcrcTxFrThreshEntry ::= SEQUENCE {
   mscLpEngFcrcTxFrThreshIndex
      Integer32,
   mscLpEngFcrcTxFrThreshValue
      Unsigned32 }

mscLpEngFcrcTxFrThreshIndex OBJECT-TYPE
   SYNTAX     Integer32 (0..3)
   ACCESS     not-accessible
   STATUS     mandatory
   DESCRIPTION
     "This variable represents the mscLpEngFcrcTxFrThreshTable
      specific index for the mscLpEngFcrcTxFrThreshTable."
::= { mscLpEngFcrcTxFrThreshEntry 1 }

mscLpEngFcrcTxFrThreshValue OBJECT-TYPE
   SYNTAX     Unsigned32 (0..32767)
   ACCESS     read-only
   STATUS     mandatory
   DESCRIPTION
     "This variable represents an individual value for the
      mscLpEngFcrcTxFrThreshTable."
::= { mscLpEngFcrcTxFrThreshEntry 2 }

mscLpEngFcrcRxFrThreshTable OBJECT-TYPE
   SYNTAX     SEQUENCE OF MscLpEngFcrcRxFrThreshEntry
   ACCESS     not-accessible
   STATUS     mandatory
   DESCRIPTION
     "This attribute indicates the total received frame memory size and 
      the discard thresholds of the receive frame memory. The receive 
      frame memory is the memory (in units of frames) used for storing 
      frames received by this FP.
      
      The first parameter indicates the total size of the receive frame 
      memory. This is derived from the connectionPoolCapacity and the 
      rxFrameMemoryAllocation under the ARC component.
      
      When the rxFrameMemoryAvailable attribute decreases to the 
      second value, the rxFrameMemoryCongestionState changes from 3 
      to 2. In congestion state 2, traffic with discard priority (DP) = 3 is 
      discarded. This threshold is set approximately at 25 percent of the 
      first value, the total received frame memory size.
      
      When the rxFrameMemoryAvailable attribute decreases to the third 
      value, the rxFrameMemoryCongestionState changes from 2 to 1. In 
      congestion state 1, traffic with discard priority (DP) >= 2 is 
      discarded. This threshold is set approximately at 20 percent of the 
      first value, the total received frame memory size.
      
      When the rxFrameMemoryAvailable attribute decreases to the 
      fourth value, the rxFrameMemoryCongestionState changes from 1 
      to 0. In congestion state 0, traffic with discard priority (DP) >= 1 is 
      discarded. This threshold is set approximately at 10 percent of the 
      first value, the total received frame memory size.
      
      The opposite effect occurs when the rxFrameMemoryAvailable 
      attribute increases (rxFrameMemoryCongestionState increases from 
      0 to 3 accordingly)."
::= { mscLpEngFcrc 446 }

mscLpEngFcrcRxFrThreshEntry OBJECT-TYPE
   SYNTAX     MscLpEngFcrcRxFrThreshEntry
   ACCESS     not-accessible
   STATUS     mandatory
   DESCRIPTION
     "An entry in the mscLpEngFcrcRxFrThreshTable."
   INDEX {
      mscLpIndex,
      mscLpEngIndex,
      mscLpEngFcrcIndex,
      mscLpEngFcrcRxFrThreshIndex }
::= { mscLpEngFcrcRxFrThreshTable 1 }

MscLpEngFcrcRxFrThreshEntry ::= SEQUENCE {
   mscLpEngFcrcRxFrThreshIndex
      Integer32,
   mscLpEngFcrcRxFrThreshValue
      Unsigned32 }

mscLpEngFcrcRxFrThreshIndex OBJECT-TYPE
   SYNTAX     Integer32 (0..3)
   ACCESS     not-accessible
   STATUS     mandatory
   DESCRIPTION
     "This variable represents the mscLpEngFcrcRxFrThreshTable
      specific index for the mscLpEngFcrcRxFrThreshTable."
::= { mscLpEngFcrcRxFrThreshEntry 1 }

mscLpEngFcrcRxFrThreshValue OBJECT-TYPE
   SYNTAX     Unsigned32 (0..32767)
   ACCESS     read-only
   STATUS     mandatory
   DESCRIPTION
     "This variable represents an individual value for the
      mscLpEngFcrcRxFrThreshTable."
::= { mscLpEngFcrcRxFrThreshEntry 2 }


-- Lp Eng Fcrc Override
-- This component holds provisionable engineering parameters used 
-- by frame services on this LogicalProcessor.

mscLpEngFcrcOv OBJECT IDENTIFIER ::= { mscLpEngFcrc 2 }



mscLpEngFcrcOvRowStatusTable OBJECT-TYPE
   SYNTAX     SEQUENCE OF MscLpEngFcrcOvRowStatusEntry
   ACCESS     not-accessible
   STATUS     mandatory
   DESCRIPTION
     "This entry controls the addition and deletion of 
      mscLpEngFcrcOv components."
::= { mscLpEngFcrcOv 1 }

mscLpEngFcrcOvRowStatusEntry OBJECT-TYPE
   SYNTAX     MscLpEngFcrcOvRowStatusEntry
   ACCESS     not-accessible
   STATUS     mandatory
   DESCRIPTION
     "A single entry in the table represents a single 
      mscLpEngFcrcOv component."
   INDEX {
      mscLpIndex,
      mscLpEngIndex,
      mscLpEngFcrcIndex,
      mscLpEngFcrcOvIndex }
::= { mscLpEngFcrcOvRowStatusTable 1 }

MscLpEngFcrcOvRowStatusEntry ::= SEQUENCE {
   mscLpEngFcrcOvRowStatus
      RowStatus,
   mscLpEngFcrcOvComponentName
      DisplayString,
   mscLpEngFcrcOvStorageType
      StorageType,
   mscLpEngFcrcOvIndex
      NonReplicated }

mscLpEngFcrcOvRowStatus OBJECT-TYPE
   SYNTAX     RowStatus 
   ACCESS     read-write
   STATUS     mandatory
   DESCRIPTION
     "This variable is used as the basis for SNMP naming of
      mscLpEngFcrcOv components.
      These components can be added and deleted."
::= { mscLpEngFcrcOvRowStatusEntry 1 }

mscLpEngFcrcOvComponentName OBJECT-TYPE
   SYNTAX     DisplayString 
   ACCESS     read-only
   STATUS     mandatory
   DESCRIPTION
     "This variable provides the component's string name for
      use with the ASCII Console Interface"
::= { mscLpEngFcrcOvRowStatusEntry 2 }

mscLpEngFcrcOvStorageType OBJECT-TYPE
   SYNTAX     StorageType 
   ACCESS     read-only
   STATUS     mandatory
   DESCRIPTION
     "This variable represents the storage type value for the
      mscLpEngFcrcOv tables."
::= { mscLpEngFcrcOvRowStatusEntry 4 }

mscLpEngFcrcOvIndex OBJECT-TYPE
   SYNTAX     NonReplicated 
   ACCESS     not-accessible
   STATUS     mandatory
   DESCRIPTION
     "This variable represents the index for the mscLpEngFcrcOv tables."
::= { mscLpEngFcrcOvRowStatusEntry 10 }

mscLpEngFcrcOvProvTable OBJECT-TYPE
   SYNTAX     SEQUENCE OF MscLpEngFcrcOvProvEntry
   ACCESS     not-accessible
   STATUS     mandatory
   DESCRIPTION
     "This group contains frame services provisionable engineering 
      parameters for this LogicalProcessor. Note that altering any of 
      these parameters will result in a card reset."
::= { mscLpEngFcrcOv 10 }

mscLpEngFcrcOvProvEntry OBJECT-TYPE
   SYNTAX     MscLpEngFcrcOvProvEntry
   ACCESS     not-accessible
   STATUS     mandatory
   DESCRIPTION
     "An entry in the mscLpEngFcrcOvProvTable."
   INDEX {
      mscLpIndex,
      mscLpEngIndex,
      mscLpEngFcrcIndex,
      mscLpEngFcrcOvIndex }
::= { mscLpEngFcrcOvProvTable 1 }

MscLpEngFcrcOvProvEntry ::= SEQUENCE {
   mscLpEngFcrcOvSubConnectionPoolCapacity
      Unsigned32,
   mscLpEngFcrcOvLnnConnectionPoolCapacity
      Unsigned32 }

mscLpEngFcrcOvSubConnectionPoolCapacity OBJECT-TYPE
   SYNTAX     Unsigned32 (0..49152 | 65535)
   ACCESS     read-write
   STATUS     mandatory
   DESCRIPTION
     "This attribute indicates the maximum number of sub-connections 
      for the LogicalProcessor. 
      
      A sub-connection is used for interworking the ATM services with 
      the frame oriented services such as Frame Relay and Path Oriented 
      Routing System (PORS). When a frame is received at a sub-
      connection, the frame header is modified to be compatible with the 
      service it is to be forwarded to.
      
      Due to limited resources, not all of the sub-connections requested 
      by this attribute may be allocated. The desired number of sub-
      connections allocated is indicated by the sum of fcrc 
      subConnectionPoolAvailable and fcrc subConnectionPoolUsage 
      attributes. 
      
      This pool is used for connection oriented services only. Each of the 
      following components uses one sub-connection from this pool: 
      FrAtm/n Dlci/n Siwf
      McsMgr Frf5EpG/n Frf5Ep/n Lmi
      McsMgr Frf5EpG/n Frf5Ep/n Dlci/n
      
      When the sub-connection pool is exhausted, no more connections 
      are accepted from the services which utilize this pool.
      
      Note: Ip Routing entries also compete for this memory.
      
      The maximum size of this pool is 8192 for CQC based cards. The 
      default cardDependent has the effect of setting 
      subConnectionPoolCapacity to 1024 for both CQC cards and 
      SGAF cards.

      VALUES (

      65535 = cardDependent

      )"
   DEFVAL     { 65535 }
::= { mscLpEngFcrcOvProvEntry 1 }

mscLpEngFcrcOvLnnConnectionPoolCapacity OBJECT-TYPE
   SYNTAX     Unsigned32 (0 | 1..2048)
   ACCESS     read-write
   STATUS     mandatory
   DESCRIPTION
     "This attribute indicates the maximum number of resource records 
      for the connections which utilize Logical Network Number (LNN) 
      on the LogicalProcessor.
      
      A logical network is a subset of passport modules together with a 
      subset of trunks that interconnect those modules. It carries the 
      traffic for a defined set of network protocols. An LNN is used to 
      identify a logical network. The connectionless services which 
      utilize the logical networks require some processing at the 
      intermediate nodes. This pool is allocated at the intermediate nodes 
      to sustain these connectionless services.
      
      If the McsMgr DprsMcsEpG/n Ep/n EpD 
      transportConnectionPreference attribute is set to atmOnly, each 
      instance of the McsMgr DprsMcsEpG/n Ep/n component uses one 
      resource record from this pool, otherwise it does not use this pool.
      
      Note: Frame and Cell queues also compete for this memory.
      
      Each DPRS instance requires two resource records and each VNS 
      instance requires one resource records from this pool. (A VNS 
      instance is an lnn combined with a trunk).
      
      The maximum size of this pool is 256 for CQC based cards. The 
      default cardDependent has the effect of setting 
      lnnConnectionPoolCapacity to 128 for CQC cards and 256 for 
      SGAF cards.

      VALUES (

      0 = cardDependent

      )"
   DEFVAL     { 0 }
::= { mscLpEngFcrcOvProvEntry 2 }


-- Lp Eng Fcrc Pqc
-- This component is used to view the usage of resources specific to 
-- frame services on a PQC based FP.

mscLpEngFcrcPqc OBJECT IDENTIFIER ::= { mscLpEngFcrc 3 }



mscLpEngFcrcPqcRowStatusTable OBJECT-TYPE
   SYNTAX     SEQUENCE OF MscLpEngFcrcPqcRowStatusEntry
   ACCESS     not-accessible
   STATUS     mandatory
   DESCRIPTION
     "This entry controls the addition and deletion of 
      mscLpEngFcrcPqc components."
::= { mscLpEngFcrcPqc 1 }

mscLpEngFcrcPqcRowStatusEntry OBJECT-TYPE
   SYNTAX     MscLpEngFcrcPqcRowStatusEntry
   ACCESS     not-accessible
   STATUS     mandatory
   DESCRIPTION
     "A single entry in the table represents a single 
      mscLpEngFcrcPqc component."
   INDEX {
      mscLpIndex,
      mscLpEngIndex,
      mscLpEngFcrcIndex,
      mscLpEngFcrcPqcIndex }
::= { mscLpEngFcrcPqcRowStatusTable 1 }

MscLpEngFcrcPqcRowStatusEntry ::= SEQUENCE {
   mscLpEngFcrcPqcRowStatus
      RowStatus,
   mscLpEngFcrcPqcComponentName
      DisplayString,
   mscLpEngFcrcPqcStorageType
      StorageType,
   mscLpEngFcrcPqcIndex
      NonReplicated }

mscLpEngFcrcPqcRowStatus OBJECT-TYPE
   SYNTAX     RowStatus 
   ACCESS     read-write
   STATUS     mandatory
   DESCRIPTION
     "This variable is used as the basis for SNMP naming of
      mscLpEngFcrcPqc components.
      These components can be added and deleted."
::= { mscLpEngFcrcPqcRowStatusEntry 1 }

mscLpEngFcrcPqcComponentName OBJECT-TYPE
   SYNTAX     DisplayString 
   ACCESS     read-only
   STATUS     mandatory
   DESCRIPTION
     "This variable provides the component's string name for
      use with the ASCII Console Interface"
::= { mscLpEngFcrcPqcRowStatusEntry 2 }

mscLpEngFcrcPqcStorageType OBJECT-TYPE
   SYNTAX     StorageType 
   ACCESS     read-only
   STATUS     mandatory
   DESCRIPTION
     "This variable represents the storage type value for the
      mscLpEngFcrcPqc tables."
::= { mscLpEngFcrcPqcRowStatusEntry 4 }

mscLpEngFcrcPqcIndex OBJECT-TYPE
   SYNTAX     NonReplicated 
   ACCESS     not-accessible
   STATUS     mandatory
   DESCRIPTION
     "This variable represents the index for the mscLpEngFcrcPqc tables."
::= { mscLpEngFcrcPqcRowStatusEntry 10 }

mscLpEngFcrcPqcOperTable OBJECT-TYPE
   SYNTAX     SEQUENCE OF MscLpEngFcrcPqcOperEntry
   ACCESS     not-accessible
   STATUS     mandatory
   DESCRIPTION
     "This group describes the usage of resources specific to frame 
      services on a PQC based FP."
::= { mscLpEngFcrcPqc 10 }

mscLpEngFcrcPqcOperEntry OBJECT-TYPE
   SYNTAX     MscLpEngFcrcPqcOperEntry
   ACCESS     not-accessible
   STATUS     mandatory
   DESCRIPTION
     "An entry in the mscLpEngFcrcPqcOperTable."
   INDEX {
      mscLpIndex,
      mscLpEngIndex,
      mscLpEngFcrcIndex,
      mscLpEngFcrcPqcIndex }
::= { mscLpEngFcrcPqcOperTable 1 }

MscLpEngFcrcPqcOperEntry ::= SEQUENCE {
   mscLpEngFcrcPqcIpRoutesPoolSize
      Gauge32,
   mscLpEngFcrcPqcIpRoutesPoolUsage
      Gauge32,
   mscLpEngFcrcPqcIpRoutesPoolAvailableEst
      Gauge32 }

mscLpEngFcrcPqcIpRoutesPoolSize OBJECT-TYPE
   SYNTAX     Gauge32 (0..100000)
   ACCESS     read-only
   STATUS     mandatory
   DESCRIPTION
     "This attribute indicates the number of IP routing entries permitted 
      on the Logical Processor. If there are enough resources on the card, 
      this value is equal to the provisioned attribute (in Fcrc Pqc Ov) 
      ipRoutesPoolCapacity."
::= { mscLpEngFcrcPqcOperEntry 1 }

mscLpEngFcrcPqcIpRoutesPoolUsage OBJECT-TYPE
   SYNTAX     Gauge32 (0..100000)
   ACCESS     read-only
   STATUS     mandatory
   DESCRIPTION
     "This attribute represents the current number of IP routing entries 
      that are in use."
::= { mscLpEngFcrcPqcOperEntry 2 }

mscLpEngFcrcPqcIpRoutesPoolAvailableEst OBJECT-TYPE
   SYNTAX     Gauge32 (0..100000)
   ACCESS     read-only
   STATUS     mandatory
   DESCRIPTION
     "Each IP routing resource can hold between one and three IP 
      routing entries. Therefore, it is not possible to know exactly 
      how many more IP routing entries can be added to the IP 
      routing table. This attribute specifies the estimated number of 
      IP routing entries that are available on the Logical Processor. 
      It is an approximation based on the current average number 
      of IP routing entries per IP routing resource."
::= { mscLpEngFcrcPqcOperEntry 3 }


-- Lp Eng Fcrc Pqc Ov
-- This component is used to configure resources specific to frame 
-- services on a PQC based Logical Processor.

mscLpEngFcrcPqcOv OBJECT IDENTIFIER ::= { mscLpEngFcrcPqc 2 }



mscLpEngFcrcPqcOvRowStatusTable OBJECT-TYPE
   SYNTAX     SEQUENCE OF MscLpEngFcrcPqcOvRowStatusEntry
   ACCESS     not-accessible
   STATUS     mandatory
   DESCRIPTION
     "This entry controls the addition and deletion of 
      mscLpEngFcrcPqcOv components."
::= { mscLpEngFcrcPqcOv 1 }

mscLpEngFcrcPqcOvRowStatusEntry OBJECT-TYPE
   SYNTAX     MscLpEngFcrcPqcOvRowStatusEntry
   ACCESS     not-accessible
   STATUS     mandatory
   DESCRIPTION
     "A single entry in the table represents a single 
      mscLpEngFcrcPqcOv component."
   INDEX {
      mscLpIndex,
      mscLpEngIndex,
      mscLpEngFcrcIndex,
      mscLpEngFcrcPqcIndex,
      mscLpEngFcrcPqcOvIndex }
::= { mscLpEngFcrcPqcOvRowStatusTable 1 }

MscLpEngFcrcPqcOvRowStatusEntry ::= SEQUENCE {
   mscLpEngFcrcPqcOvRowStatus
      RowStatus,
   mscLpEngFcrcPqcOvComponentName
      DisplayString,
   mscLpEngFcrcPqcOvStorageType
      StorageType,
   mscLpEngFcrcPqcOvIndex
      NonReplicated }

mscLpEngFcrcPqcOvRowStatus OBJECT-TYPE
   SYNTAX     RowStatus 
   ACCESS     read-only
   STATUS     mandatory
   DESCRIPTION
     "This variable is used as the basis for SNMP naming of
      mscLpEngFcrcPqcOv components.
      These components cannot be added nor deleted."
::= { mscLpEngFcrcPqcOvRowStatusEntry 1 }

mscLpEngFcrcPqcOvComponentName OBJECT-TYPE
   SYNTAX     DisplayString 
   ACCESS     read-only
   STATUS     mandatory
   DESCRIPTION
     "This variable provides the component's string name for
      use with the ASCII Console Interface"
::= { mscLpEngFcrcPqcOvRowStatusEntry 2 }

mscLpEngFcrcPqcOvStorageType OBJECT-TYPE
   SYNTAX     StorageType 
   ACCESS     read-only
   STATUS     mandatory
   DESCRIPTION
     "This variable represents the storage type value for the
      mscLpEngFcrcPqcOv tables."
::= { mscLpEngFcrcPqcOvRowStatusEntry 4 }

mscLpEngFcrcPqcOvIndex OBJECT-TYPE
   SYNTAX     NonReplicated 
   ACCESS     not-accessible
   STATUS     mandatory
   DESCRIPTION
     "This variable represents the index for the mscLpEngFcrcPqcOv tables."
::= { mscLpEngFcrcPqcOvRowStatusEntry 10 }

mscLpEngFcrcPqcOvProvTable OBJECT-TYPE
   SYNTAX     SEQUENCE OF MscLpEngFcrcPqcOvProvEntry
   ACCESS     not-accessible
   STATUS     mandatory
   DESCRIPTION
     "This group is used for fine tuning resource configuration of frame 
      services on a PQC based Logical Processor."
::= { mscLpEngFcrcPqcOv 10 }

mscLpEngFcrcPqcOvProvEntry OBJECT-TYPE
   SYNTAX     MscLpEngFcrcPqcOvProvEntry
   ACCESS     not-accessible
   STATUS     mandatory
   DESCRIPTION
     "An entry in the mscLpEngFcrcPqcOvProvTable."
   INDEX {
      mscLpIndex,
      mscLpEngIndex,
      mscLpEngFcrcIndex,
      mscLpEngFcrcPqcIndex,
      mscLpEngFcrcPqcOvIndex }
::= { mscLpEngFcrcPqcOvProvTable 1 }

MscLpEngFcrcPqcOvProvEntry ::= SEQUENCE {
   mscLpEngFcrcPqcOvIpRoutesPoolCapacity
      Unsigned32 }

mscLpEngFcrcPqcOvIpRoutesPoolCapacity OBJECT-TYPE
   SYNTAX     Unsigned32 (0..100000)
   ACCESS     read-write
   STATUS     mandatory
   DESCRIPTION
     "This attribute indicates the number of desired IP routing entries for 
      the Logical Processor. It is used to determine the number of IP 
      routing resources to be allocated on the card. 
      
      Each IP routing resource can hold between one and three IP routing 
      entries. To calculate the number of IP routing resources required, an 
      average of 2 IP routing entries per IP routing resource is used.
      
      If there are not enough resources on the card, a smaller pool is 
      allocated. Operational attribute (in Fcrc Pqc) ipRoutesPoolSize 
      indicates the actual size of the pool."
   DEFVAL     { 4096 }
::= { mscLpEngFcrcPqcOvProvEntry 1 }




-- 
-- Version and Compliance statements
-- 



-- Object-Group Statement:
-- A list of all current accessible leaf objects.

-- OBJECTS { mscLpEngFcrcSubConnectionPoolUsage,
--           mscLpEngArcAqmStorageType,
--           mscLpEngFcrcRxFrameMemoryMinAvailable,
--           mscLpEngFcrcTxFrThreshValue,
--           mscLpEngArcCqcOvPerVcQueueInterfaces,
--           mscLpEngArcTotalConnectionPoolAvailable,
--           mscLpEngArcOvComponentName,
--           mscLpEngArcCqcOvPortCongestionPolicy,
--           mscLpEngFcrcPqcOvStorageType,
--           mscLpEngFcrcPqcOvIpRoutesPoolCapacity,
--           mscLpEngArcStorageType,
--           mscLpEngArcOvTotalConnectionPoolCapacity,
--           mscLpEngArcCqcOvCdvReduction,
--           mscLpEngFcrcOvStorageType,
--           mscLpEngArcCqcOvComponentName,
--           mscLpEngFcrcOvRowStatus,
--           mscLpEngArcOvRxCellMemoryAllocation,
--           mscLpEngArcCqcOvRowStatus,
--           mscLpEngFcrcSubConnectionPoolAvailable,
--           mscLpEngArcMulticastBranchesUsage,
--           mscLpEngArcAqmOvConnectionPoolCapacity,
--           mscLpEngArcAqmRowStatus,
--           mscLpEngFcrcPqcIpRoutesPoolAvailableEst,
--           mscLpEngArcAqmTxCellMemoryAvailable,
--           mscLpEngFcrcLnnConnectionPoolUsage,
--           mscLpEngArcAqmConnectionPoolUsage,
--           mscLpEngFcrcPqcOvRowStatus,
--           mscLpEngArcAqmOvPortCongestionPolicy,
--           mscLpEngFcrcPqcIpRoutesPoolUsage,
--           mscLpEngArcRowStatus,
--           mscLpEngArcCqcStorageType,
--           mscLpEngArcTxCellMemoryAvailable,
--           mscLpEngArcTxCellMemoryAllocation,
--           mscLpEngFcrcTxFrameMemoryAvailable,
--           mscLpEngFcrcRxFrThreshValue,
--           mscLpEngArcTxCellMemoryCongestionState,
--           mscLpEngFcrcPqcRowStatus,
--           mscLpEngArcAqmTxCellMemoryMinAvailable,
--           mscLpEngFcrcStorageType,
--           mscLpEngArcAqmComponentName,
--           mscLpEngArcAqmOvLowPriorityEpdOffset,
--           mscLpEngArcMulticastBranchesAvailable,
--           mscLpEngArcCqcRowStatus,
--           mscLpEngArcAqmTxCellThreshValue,
--           mscLpEngArcAqmOvStorageType,
--           mscLpEngFcrcPqcOvComponentName,
--           mscLpEngArcTxCellMemoryMinAvailable,
--           mscLpEngArcOvMulticastBranchesCapacity,
--           mscLpEngArcComponentName,
--           mscLpEngFcrcRowStatus,
--           mscLpEngFcrcPqcStorageType,
--           mscLpEngFcrcOvLnnConnectionPoolCapacity,
--           mscLpEngFcrcTxFrameMemoryCongestionState,
--           mscLpEngArcTxCellThreshValue,
--           mscLpEngArcOvStorageType,
--           mscLpEngArcCqcCdvReduction,
--           mscLpEngArcCqcOvShapingScalingFactor,
--           mscLpEngArcCqcComponentName,
--           mscLpEngFcrcPqcIpRoutesPoolSize,
--           mscLpEngArcRxCellMemoryAvailable,
--           mscLpEngArcRxCellMemoryAllocation,
--           mscLpEngArcCqcOvStorageType,
--           mscLpEngFcrcOvSubConnectionPoolCapacity,
--           mscLpEngArcRxCellMemoryCongestionState,
--           mscLpEngFcrcOvComponentName,
--           mscLpEngArcCqcOvConnCapValue,
--           mscLpEngArcAqmOvRowStatus,
--           mscLpEngFcrcLnnConnectionPoolAvailable,
--           mscLpEngArcTotalConnectionPoolUsage,
--           mscLpEngArcRxCellMemoryMinAvailable,
--           mscLpEngFcrcRxFrameMemoryAvailable,
--           mscLpEngFcrcComponentName,
--           mscLpEngArcOvRowStatus,
--           mscLpEngFcrcPqcComponentName,
--           mscLpEngArcAqmOvHighPriorityEpdOffset,
--           mscLpEngArcAqmConnectionPoolAvailable,
--           mscLpEngArcRxCellThreshValue,
--           mscLpEngFcrcTxFrameMemoryMinAvailable,
--           mscLpEngArcAqmTxCellMemoryCongestionState,
--           mscLpEngFcrcRxFrameMemoryCongestionState,
--           mscLpEngArcAqmOvComponentName,
--           mscLpEngArcOvTxCellMemoryAllocation }
-- STATUS  mandatory
-- DESCRIPTION
--   "A list of all current accessible leaf objects."

atmBaseGroup OBJECT IDENTIFIER ::= { atmBaseMIB 1 }
atmBaseGroupCA OBJECT IDENTIFIER ::= { atmBaseGroup 1 }
atmBaseGroupCA02 OBJECT IDENTIFIER ::= { atmBaseGroupCA 3 }
atmBaseGroupCA02A OBJECT IDENTIFIER ::= { atmBaseGroupCA02 2 }



-- Agent-Capabilities Statement:

-- PRODUCT-RELEASE "MscPassport Release 1.2 AtmBase."
-- STATUS          mandatory
-- DESCRIPTION     "Carrier Passport AtmBase MIB: MIB Version CA02A,
--                  Software Version CA02S9C."
-- SUPPORTS        Nortel-MsCarrier-MscPassport-AtmBaseMIB
--    INCLUDES     { atmBaseGroupCA02A }

atmBaseCapabilities OBJECT IDENTIFIER ::= { atmBaseMIB 3 }
atmBaseCapabilitiesCA OBJECT IDENTIFIER ::= { atmBaseCapabilities 1 }
atmBaseCapabilitiesCA02 OBJECT IDENTIFIER ::= { atmBaseCapabilitiesCA 3 }
atmBaseCapabilitiesCA02A OBJECT IDENTIFIER ::= { atmBaseCapabilitiesCA02 2 }





END
