Nortel-MsCarrier-MscPassport-VncsCallServerMIB
DEFINITIONS ::= BEGIN



IMPORTS

      OBJECT-TYPE
   FROM RFC-1212

      mscPassportMIBs,
      mscComponents
   FROM Nortel-MsCarrier-MscPassport-UsefulDefinitionsMIB

      Counter32,
      RowPointer,
      DisplayString,
      StorageType,
      RowStatus,
      Integer32,
      Unsigned32
   FROM Nortel-MsCarrier-MscPassport-StandardTextualConventionsMIB

      AsciiString,
      DigitString,
      FixedPoint1,
      Link,
      WildcardedDigitString
   FROM Nortel-MsCarrier-MscPassport-TextualConventionsMIB;




-- LAST-UPDATED   "9909010000Z"
-- ORGANIZATION   "Nortel Networks"
-- CONTACT-INFO   "
--         Nortel Carrier Data Network Management
--         
--         Postal:       P.O. Box 3511, Station C 
--                       Ottawa, Ontario 
--                       Canada  K1Y 4H7
--         
--         via the WEB:  http://www.nortelnetworks.com  
--                       select 'Contact Us' from the menu
--          
--         via phone:    1-800-4NORTEL"
-- DESCRIPTION
--    "The module describing the Nortel MsCarrier MscPassport
--     VncsCallServer Enterprise MIB."

vncsCallServerMIB OBJECT IDENTIFIER ::= { mscPassportMIBs 66 }










-- Vncs/n		
-- The Vncs component provides the information to the Path Oriented 
-- Routing System (PORS) required during switched voice call 
-- establishment. It translates the directory number prefix into the 
-- routing information and the voice service profile parameters. Each 
-- instance of this component represents one numbering plan.

mscVncs OBJECT IDENTIFIER ::= { mscComponents 44 }



mscVncsRowStatusTable OBJECT-TYPE
   SYNTAX     SEQUENCE OF MscVncsRowStatusEntry
   ACCESS     not-accessible
   STATUS     mandatory
   DESCRIPTION
     "This entry controls the addition and deletion of 
      mscVncs components."
::= { mscVncs 1 }

mscVncsRowStatusEntry OBJECT-TYPE
   SYNTAX     MscVncsRowStatusEntry
   ACCESS     not-accessible
   STATUS     mandatory
   DESCRIPTION
     "A single entry in the table represents a single 
      mscVncs component."
   INDEX {
      mscVncsIndex }
::= { mscVncsRowStatusTable 1 }

MscVncsRowStatusEntry ::= SEQUENCE {
   mscVncsRowStatus
      RowStatus,
   mscVncsComponentName
      DisplayString,
   mscVncsStorageType
      StorageType,
   mscVncsIndex
      Integer32 }

mscVncsRowStatus OBJECT-TYPE
   SYNTAX     RowStatus 
   ACCESS     read-write
   STATUS     mandatory
   DESCRIPTION
     "This variable is used as the basis for SNMP naming of
      mscVncs components.
      These components can be added and deleted."
::= { mscVncsRowStatusEntry 1 }

mscVncsComponentName OBJECT-TYPE
   SYNTAX     DisplayString 
   ACCESS     read-only
   STATUS     mandatory
   DESCRIPTION
     "This variable provides the component's string name for
      use with the ASCII Console Interface"
::= { mscVncsRowStatusEntry 2 }

mscVncsStorageType OBJECT-TYPE
   SYNTAX     StorageType 
   ACCESS     read-only
   STATUS     mandatory
   DESCRIPTION
     "This variable represents the storage type value for the
      mscVncs tables."
::= { mscVncsRowStatusEntry 4 }

mscVncsIndex OBJECT-TYPE
   SYNTAX     Integer32 (1..16)
   ACCESS     not-accessible
   STATUS     mandatory
   DESCRIPTION
     "This variable represents the index for the mscVncs tables."
::= { mscVncsRowStatusEntry 10 }

mscVncsProvTable OBJECT-TYPE
   SYNTAX     SEQUENCE OF MscVncsProvEntry
   ACCESS     not-accessible
   STATUS     mandatory
   DESCRIPTION
     "This group represents the provisionable attributes of the VNCS 
      server."
::= { mscVncs 10 }

mscVncsProvEntry OBJECT-TYPE
   SYNTAX     MscVncsProvEntry
   ACCESS     not-accessible
   STATUS     mandatory
   DESCRIPTION
     "An entry in the mscVncsProvTable."
   INDEX {
      mscVncsIndex }
::= { mscVncsProvTable 1 }

MscVncsProvEntry ::= SEQUENCE {
   mscVncsCommentText
      AsciiString }

mscVncsCommentText OBJECT-TYPE
   SYNTAX     AsciiString (SIZE (0..40))
   ACCESS     read-write
   STATUS     mandatory
   DESCRIPTION
     "This attribute specifies the name of the customer that is using this 
      VNCS server. Typical use of this attribute is to store customer 
      name."
::= { mscVncsProvEntry 1 }

mscVncsStatsTable OBJECT-TYPE
   SYNTAX     SEQUENCE OF MscVncsStatsEntry
   ACCESS     not-accessible
   STATUS     mandatory
   DESCRIPTION
     "This group provides data for the Vncs component."
::= { mscVncs 11 }

mscVncsStatsEntry OBJECT-TYPE
   SYNTAX     MscVncsStatsEntry
   ACCESS     not-accessible
   STATUS     mandatory
   DESCRIPTION
     "An entry in the mscVncsStatsTable."
   INDEX {
      mscVncsIndex }
::= { mscVncsStatsTable 1 }

MscVncsStatsEntry ::= SEQUENCE {
   mscVncsTotalTranslations
      Counter32 }

mscVncsTotalTranslations OBJECT-TYPE
   SYNTAX     Counter32 
   ACCESS     read-only
   STATUS     mandatory
   DESCRIPTION
     "This attribute counts the total number of translation requests 
      received by VNCS. This counter wraps to zero when it reaches its 
      maximum value."
::= { mscVncsStatsEntry 1 }

mscVncsVRoutesTable OBJECT-TYPE
   SYNTAX     SEQUENCE OF MscVncsVRoutesEntry
   ACCESS     not-accessible
   STATUS     mandatory
   DESCRIPTION
     "This attribute indicates which VoiceRoute components are using 
      this Vncs."
::= { mscVncs 305 }

mscVncsVRoutesEntry OBJECT-TYPE
   SYNTAX     MscVncsVRoutesEntry
   ACCESS     not-accessible
   STATUS     mandatory
   DESCRIPTION
     "An entry in the mscVncsVRoutesTable."
   INDEX {
      mscVncsIndex,
      mscVncsVRoutesValue }
::= { mscVncsVRoutesTable 1 }

MscVncsVRoutesEntry ::= SEQUENCE {
   mscVncsVRoutesValue
      Link }

mscVncsVRoutesValue OBJECT-TYPE
   SYNTAX     Link 
   ACCESS     read-only
   STATUS     mandatory
   DESCRIPTION
     "This variable represents both the value and the index for the
      mscVncsVRoutesTable."
::= { mscVncsVRoutesEntry 1 }


-- Vncs/n diallingPlan/x		
-- The DiallingPlan subcomponent contains part of the Voice 
-- Networking Call Server database that belongs under one dialling 
-- plan. There are three dialling plans supported, dialling plan 0, 
-- dialling plan 1 and dialling plan 2.

mscVncsDP OBJECT IDENTIFIER ::= { mscVncs 2 }



mscVncsDPRowStatusTable OBJECT-TYPE
   SYNTAX     SEQUENCE OF MscVncsDPRowStatusEntry
   ACCESS     not-accessible
   STATUS     mandatory
   DESCRIPTION
     "This entry controls the addition and deletion of 
      mscVncsDP components."
::= { mscVncsDP 1 }

mscVncsDPRowStatusEntry OBJECT-TYPE
   SYNTAX     MscVncsDPRowStatusEntry
   ACCESS     not-accessible
   STATUS     mandatory
   DESCRIPTION
     "A single entry in the table represents a single 
      mscVncsDP component."
   INDEX {
      mscVncsIndex,
      mscVncsDPIndex }
::= { mscVncsDPRowStatusTable 1 }

MscVncsDPRowStatusEntry ::= SEQUENCE {
   mscVncsDPRowStatus
      RowStatus,
   mscVncsDPComponentName
      DisplayString,
   mscVncsDPStorageType
      StorageType,
   mscVncsDPIndex
      Integer32 }

mscVncsDPRowStatus OBJECT-TYPE
   SYNTAX     RowStatus 
   ACCESS     read-write
   STATUS     mandatory
   DESCRIPTION
     "This variable is used as the basis for SNMP naming of
      mscVncsDP components.
      These components can be added."
::= { mscVncsDPRowStatusEntry 1 }

mscVncsDPComponentName OBJECT-TYPE
   SYNTAX     DisplayString 
   ACCESS     read-only
   STATUS     mandatory
   DESCRIPTION
     "This variable provides the component's string name for
      use with the ASCII Console Interface"
::= { mscVncsDPRowStatusEntry 2 }

mscVncsDPStorageType OBJECT-TYPE
   SYNTAX     StorageType 
   ACCESS     read-only
   STATUS     mandatory
   DESCRIPTION
     "This variable represents the storage type value for the
      mscVncsDP tables."
::= { mscVncsDPRowStatusEntry 4 }

mscVncsDPIndex OBJECT-TYPE
   SYNTAX     Integer32 (0..2)
   ACCESS     not-accessible
   STATUS     mandatory
   DESCRIPTION
     "This variable represents the index for the mscVncsDP tables."
::= { mscVncsDPRowStatusEntry 10 }

mscVncsDPStatsTable OBJECT-TYPE
   SYNTAX     SEQUENCE OF MscVncsDPStatsEntry
   ACCESS     not-accessible
   STATUS     mandatory
   DESCRIPTION
     "This group provides the operational components for the AccessCode 
      component. It displays total DirectoryNumber components under 
      this access code, total translation requests received and total 
      requests failed under this access code."
::= { mscVncsDP 10 }

mscVncsDPStatsEntry OBJECT-TYPE
   SYNTAX     MscVncsDPStatsEntry
   ACCESS     not-accessible
   STATUS     mandatory
   DESCRIPTION
     "An entry in the mscVncsDPStatsTable."
   INDEX {
      mscVncsIndex,
      mscVncsDPIndex }
::= { mscVncsDPStatsTable 1 }

MscVncsDPStatsEntry ::= SEQUENCE {
   mscVncsDPCompleteTranslations
      Counter32,
   mscVncsDPIncompleteTranslations
      Counter32,
   mscVncsDPFailedTranslations
      Counter32 }

mscVncsDPCompleteTranslations OBJECT-TYPE
   SYNTAX     Counter32 
   ACCESS     read-only
   STATUS     mandatory
   DESCRIPTION
     "This attribute counts the total number of complete translations 
      handled under this AccessCode component. The complete 
      translations are the one that resulted in the return by VNCS server 
      of the reply message with the routing information and voice profile 
      parameters associated with the directory number prefix supplied in 
      the translation request message. This counter wraps to zero when it 
      reaches its maximum value."
::= { mscVncsDPStatsEntry 1 }

mscVncsDPIncompleteTranslations OBJECT-TYPE
   SYNTAX     Counter32 
   ACCESS     read-only
   STATUS     mandatory
   DESCRIPTION
     "This attribute counts the total number of incomplete translations 
      handled under this AccessCode component. The incomplete 
      translations are the one that require more digits in the directory 
      number prefix to uniquely identify routing attributes. This counter 
      wraps to zero when it reaches its maximum value."
::= { mscVncsDPStatsEntry 2 }

mscVncsDPFailedTranslations OBJECT-TYPE
   SYNTAX     Counter32 
   ACCESS     read-only
   STATUS     mandatory
   DESCRIPTION
     "This attribute counts the total number of failed translations handled 
      under this AccessCode component. The failed translations are the 
      one for which the directory number prefix could not be found in the 
      database. the value wraps up when it reaches maximum."
::= { mscVncsDPStatsEntry 3 }


-- Vncs/n DP/x 	DirectoryNumber/x
-- The DirectoryNumber subcomponent represents a prefix directory 
-- number excluding the access code. The instance value must be 1 to 
-- 40 digits each of value 0 through 9 or wildcard digit. The wildcard 
-- digit is represented by "?". It is used to indicate to VNCS that the 
-- digit in that position should be ignored for routing purposes. 
-- Wildcard inconsistencies must not exist. If a prefix directory 
-- number already exists with a digit in a particular position, a new 
-- prefix may not be added with a wild card in that position and if the 
-- prefix already exists with a wild card in the particular position, a 
-- new prefix may not be added with a specific digit in the same 
-- position.

mscVncsDPDn OBJECT IDENTIFIER ::= { mscVncsDP 2 }



mscVncsDPDnRowStatusTable OBJECT-TYPE
   SYNTAX     SEQUENCE OF MscVncsDPDnRowStatusEntry
   ACCESS     not-accessible
   STATUS     mandatory
   DESCRIPTION
     "This entry controls the addition and deletion of 
      mscVncsDPDn components."
::= { mscVncsDPDn 1 }

mscVncsDPDnRowStatusEntry OBJECT-TYPE
   SYNTAX     MscVncsDPDnRowStatusEntry
   ACCESS     not-accessible
   STATUS     mandatory
   DESCRIPTION
     "A single entry in the table represents a single 
      mscVncsDPDn component."
   INDEX {
      mscVncsIndex,
      mscVncsDPIndex,
      mscVncsDPDnIndex }
::= { mscVncsDPDnRowStatusTable 1 }

MscVncsDPDnRowStatusEntry ::= SEQUENCE {
   mscVncsDPDnRowStatus
      RowStatus,
   mscVncsDPDnComponentName
      DisplayString,
   mscVncsDPDnStorageType
      StorageType,
   mscVncsDPDnIndex
      WildcardedDigitString }

mscVncsDPDnRowStatus OBJECT-TYPE
   SYNTAX     RowStatus 
   ACCESS     read-write
   STATUS     mandatory
   DESCRIPTION
     "This variable is used as the basis for SNMP naming of
      mscVncsDPDn components.
      These components can be added and deleted."
::= { mscVncsDPDnRowStatusEntry 1 }

mscVncsDPDnComponentName OBJECT-TYPE
   SYNTAX     DisplayString 
   ACCESS     read-only
   STATUS     mandatory
   DESCRIPTION
     "This variable provides the component's string name for
      use with the ASCII Console Interface"
::= { mscVncsDPDnRowStatusEntry 2 }

mscVncsDPDnStorageType OBJECT-TYPE
   SYNTAX     StorageType 
   ACCESS     read-only
   STATUS     mandatory
   DESCRIPTION
     "This variable represents the storage type value for the
      mscVncsDPDn tables."
::= { mscVncsDPDnRowStatusEntry 4 }

mscVncsDPDnIndex OBJECT-TYPE
   SYNTAX     WildcardedDigitString (SIZE (1..40))
   ACCESS     not-accessible
   STATUS     mandatory
   DESCRIPTION
     "This variable represents the index for the mscVncsDPDn tables."
::= { mscVncsDPDnRowStatusEntry 10 }

mscVncsDPDnProvTable OBJECT-TYPE
   SYNTAX     SEQUENCE OF MscVncsDPDnProvEntry
   ACCESS     not-accessible
   STATUS     mandatory
   DESCRIPTION
     "This group represents attributes that the prefix directory number 
      maps to."
::= { mscVncsDPDn 10 }

mscVncsDPDnProvEntry OBJECT-TYPE
   SYNTAX     MscVncsDPDnProvEntry
   ACCESS     not-accessible
   STATUS     mandatory
   DESCRIPTION
     "An entry in the mscVncsDPDnProvTable."
   INDEX {
      mscVncsIndex,
      mscVncsDPIndex,
      mscVncsDPDnIndex }
::= { mscVncsDPDnProvTable 1 }

MscVncsDPDnProvEntry ::= SEQUENCE {
   mscVncsDPDnDestinationNodeId
      Unsigned32,
   mscVncsDPDnDestinationComponentId
      RowPointer,
   mscVncsDPDnVoiceProfileNumber
      Unsigned32,
   mscVncsDPDnNumberingPlanIndicator
      INTEGER,
   mscVncsDPDnDataNetworkAddress
      DigitString }

mscVncsDPDnDestinationNodeId OBJECT-TYPE
   SYNTAX     Unsigned32 (0..4095)
   ACCESS     read-write
   STATUS     mandatory
   DESCRIPTION
     "This attribute in conjunction with the destinationComponentId 
      attribute identifies the destination of a voice connection. 
      The destinationNodeId and the destinationComponentId attributes 
      are being replaced by the DataNetworkAddress (Dna) attribute.
      For the migration procedure consult NTP 241-7001-410 'Passport 
      Voice Networking User Guide'.
      If the destinationComponentId, the destinationNodeId and the Dna 
      attributes are all set, the call routing is based on the 
      destinationNodeId and the destinationComponentId, unless the call 
      is initiated from the Magellan Passport Access (MPA) module, 
      which will use the Dna attribute.
      The valid destination call identifier settings are:
      1. destinationNodeId and destinationNodeId attributes set
      2. destinationNodeId, destinationNodeId and Dna attributes set
      3. Dna attribute set
      For calls initiated from the MPA, only options 2 and 3 are valid."
   DEFVAL     { 0 }
::= { mscVncsDPDnProvEntry 1 }

mscVncsDPDnDestinationComponentId OBJECT-TYPE
   SYNTAX     RowPointer 
   ACCESS     read-write
   STATUS     mandatory
   DESCRIPTION
     "This attribute in conjunction with the destinationNodeId attribute 
      identifies the destination of a voice connection. The only valid 
      component name for this attribute value is vroute.
      The destinationNodeId and the destinationComponentId attributes 
      are being replaced by the DataNetworkAddress (Dna) attribute.
      For the migration procedure consult NTP 241-7001-410 'Passport 
      Voice Networking User Guide'.
      If the destinationComponentId, the destinationNodeId and the Dna 
      attributes are all set, the call routing is based on the 
      destinationNodeId and the destinationComponentId, unless the call 
      is initiated from the Magellan Passport Access (MPA) module, 
      which will use the Dna attribute.
      The valid destination call identifier settings are:
      1. destinationNodeId and destinationNodeId attributes set
      2. destinationNodeId, destinationNodeId and Dna attributes set
      3. Dna attribute set
      For calls initiated from the MPA, only options 2 and 3 are valid."
::= { mscVncsDPDnProvEntry 2 }

mscVncsDPDnVoiceProfileNumber OBJECT-TYPE
   SYNTAX     Unsigned32 (1..16)
   ACCESS     read-write
   STATUS     mandatory
   DESCRIPTION
     "This attribute identifies the voice profile number."
   DEFVAL     { 1 }
::= { mscVncsDPDnProvEntry 3 }

mscVncsDPDnNumberingPlanIndicator OBJECT-TYPE
   SYNTAX     INTEGER  {
                 x121(0),
                 e164(1) }
   ACCESS     read-write
   STATUS     mandatory
   DESCRIPTION
     "This attribute indicates the Numbering Plan Indicator (NPI) of the 
      Dna of the destination component. An address may belong to the 
      X.121 or E.164 numbering plans. X.121 is used in packet switched 
      data networks."
   DEFVAL     { e164 }
::= { mscVncsDPDnProvEntry 4 }

mscVncsDPDnDataNetworkAddress OBJECT-TYPE
   SYNTAX     DigitString (SIZE (0..15))
   ACCESS     read-write
   STATUS     mandatory
   DESCRIPTION
     "The Dna attribute contains digits which form a unique identifier of 
      the destination of a voice connection.
      This attribute is used instead of the destinationNodeId and 
      destinationComponentId attributes to identify the destination of the 
      voice connection.
      This attribute is only used if the destinationNodeId and the 
      destinationComponentId attributes are not set or if the call is 
      initiated from the Magellan Passport Access (MPA) module."
::= { mscVncsDPDnProvEntry 5 }


-- Vncs/n VoiceProfile/n
-- A VoiceProfile component contains all provisionable logical 
-- connection attributes and framer attributes used to set up a virtual 
-- circuit. Directory-number prefixes are mapped to VoiceProfile 
-- instances by the Vncs Dp Dn component. Many directory-number 
-- prefixes use the same profile.

mscVncsVp OBJECT IDENTIFIER ::= { mscVncs 3 }



mscVncsVpRowStatusTable OBJECT-TYPE
   SYNTAX     SEQUENCE OF MscVncsVpRowStatusEntry
   ACCESS     not-accessible
   STATUS     mandatory
   DESCRIPTION
     "This entry controls the addition and deletion of 
      mscVncsVp components."
::= { mscVncsVp 1 }

mscVncsVpRowStatusEntry OBJECT-TYPE
   SYNTAX     MscVncsVpRowStatusEntry
   ACCESS     not-accessible
   STATUS     mandatory
   DESCRIPTION
     "A single entry in the table represents a single 
      mscVncsVp component."
   INDEX {
      mscVncsIndex,
      mscVncsVpIndex }
::= { mscVncsVpRowStatusTable 1 }

MscVncsVpRowStatusEntry ::= SEQUENCE {
   mscVncsVpRowStatus
      RowStatus,
   mscVncsVpComponentName
      DisplayString,
   mscVncsVpStorageType
      StorageType,
   mscVncsVpIndex
      Integer32 }

mscVncsVpRowStatus OBJECT-TYPE
   SYNTAX     RowStatus 
   ACCESS     read-write
   STATUS     mandatory
   DESCRIPTION
     "This variable is used as the basis for SNMP naming of
      mscVncsVp components.
      These components can be added and deleted."
::= { mscVncsVpRowStatusEntry 1 }

mscVncsVpComponentName OBJECT-TYPE
   SYNTAX     DisplayString 
   ACCESS     read-only
   STATUS     mandatory
   DESCRIPTION
     "This variable provides the component's string name for
      use with the ASCII Console Interface"
::= { mscVncsVpRowStatusEntry 2 }

mscVncsVpStorageType OBJECT-TYPE
   SYNTAX     StorageType 
   ACCESS     read-only
   STATUS     mandatory
   DESCRIPTION
     "This variable represents the storage type value for the
      mscVncsVp tables."
::= { mscVncsVpRowStatusEntry 4 }

mscVncsVpIndex OBJECT-TYPE
   SYNTAX     Integer32 (1..16)
   ACCESS     not-accessible
   STATUS     mandatory
   DESCRIPTION
     "This variable represents the index for the mscVncsVp tables."
::= { mscVncsVpRowStatusEntry 10 }

mscVncsVpLCOpsTable OBJECT-TYPE
   SYNTAX     SEQUENCE OF MscVncsVpLCOpsEntry
   ACCESS     not-accessible
   STATUS     mandatory
   DESCRIPTION
     "The attributes of this group collectively form part of a template used 
      to describe and set up a switched logical connection. The attributes 
      of a switched logical connection are similar to the attributes of a 
      permanent logical connection."
::= { mscVncsVp 2 }

mscVncsVpLCOpsEntry OBJECT-TYPE
   SYNTAX     MscVncsVpLCOpsEntry
   ACCESS     not-accessible
   STATUS     mandatory
   DESCRIPTION
     "An entry in the mscVncsVpLCOpsTable."
   INDEX {
      mscVncsIndex,
      mscVncsVpIndex }
::= { mscVncsVpLCOpsTable 1 }

MscVncsVpLCOpsEntry ::= SEQUENCE {
   mscVncsVpSetupPriority
      Unsigned32,
   mscVncsVpHoldingPriority
      Unsigned32,
   mscVncsVpBumpPreference
      INTEGER,
   mscVncsVpRequiredTrafficType
      INTEGER,
   mscVncsVpPermittedTrunkTypes
      OCTET STRING,
   mscVncsVpRequiredSecurity
      Unsigned32,
   mscVncsVpRequiredCustomerParm
      Unsigned32,
   mscVncsVpPathAttributeToMinimize
      INTEGER,
   mscVncsVpMaximumAcceptableCost
      Unsigned32,
   mscVncsVpMaximumAcceptableDelay
      Unsigned32,
   mscVncsVpEmissionPriority
      Unsigned32,
   mscVncsVpDiscardPriority
      Unsigned32,
   mscVncsVpPathFailureAction
      INTEGER,
   mscVncsVpOptimization
      INTEGER,
   mscVncsVpMaximumAcceptableGatewayCost
      Unsigned32 }

mscVncsVpSetupPriority OBJECT-TYPE
   SYNTAX     Unsigned32 (0..4)
   ACCESS     read-write
   STATUS     mandatory
   DESCRIPTION
     "This attribute specifies the priority at which a path is established. 
      Zero is the highest priority and four is the lowest. When PORS 
      establishes a path through the network, it uses the setupPriority 
      attribute to determine its potential for bumping established paths to 
      acquire their bandwidth. The holdingPriority, a complementary 
      attribute of this attribute, indicates the priority a path maintains 
      once it is established. A new path can bump an existing path if the 
      new path's setupPriority is higher (numerically less) than the 
      existing path's holdingPriority."
   DEFVAL     { 2 }
::= { mscVncsVpLCOpsEntry 1 }

mscVncsVpHoldingPriority OBJECT-TYPE
   SYNTAX     Unsigned32 (0..4)
   ACCESS     read-write
   STATUS     mandatory
   DESCRIPTION
     "This attribute specifies the priority that a path holds once it is 
      established. Zero is the highest priority and four is the lowest. A 
      path's holdingPriority determines its likelihood of being bumped by 
      a new path to acquire its bandwidth. The setupPriority, a 
      complementary attribute, indicates the priority of a path at 
      establishment time. A new path can bump an existing path if the 
      new path's setupPriority is higher (numerically less) than the 
      existing path's holdingPriority."
   DEFVAL     { 2 }
::= { mscVncsVpLCOpsEntry 2 }

mscVncsVpBumpPreference OBJECT-TYPE
   SYNTAX     INTEGER  {
                 bumpWhenNecessary(0),
                 bumpToObtainBestRoute(1) }
   ACCESS     read-write
   STATUS     mandatory
   DESCRIPTION
     "This attribute specifies when bumping occurs in the route selection 
      process. A connection with higher (numerically less) setupPriority 
      may bump a connection with lower (numerically higher) 
      setupPriority in order to acquire its bandwidth and be established. 
      By default, bumping occurs only when it is necessary. That is, a 
      connection will bump another connection only if there is no other 
      way for the connection to be established. A connection may be set 
      to bump in order to use the best available route it may have."
   DEFVAL     { bumpWhenNecessary }
::= { mscVncsVpLCOpsEntry 3 }

mscVncsVpRequiredTrafficType OBJECT-TYPE
   SYNTAX     INTEGER  {
                 voice(0),
                 data(1),
                 video(2),
                 trafficType1(3),
                 trafficType2(4),
                 trafficType3(5),
                 trafficType4(6),
                 trafficType5(7) }
   ACCESS     read-write
   STATUS     mandatory
   DESCRIPTION
     "This attribute specifies the type of traffic transmitted over the path. 
      There are eight possible traffic types, and the path can transmit only 
      one of them. The originating end of the connection determines the 
      type. These are arbitrary designations for traffic type. The voice, 
      data and video traffic types are defined, and five other arbitrary 
      traffic types can be defined by the network administration. This 
      attribute is used in the route selection process to restrict the route to 
      trunks that support this traffic type. The supportedTrafficType trunk 
      attribute lists all the types of traffic allowed on the trunk. For 
      example, if requiredTrafficType is specified as trafficType1, then 
      only trunks that include trafficType1 in supportedTrafficType will 
      be candidates for this connection."
   DEFVAL     { voice }
::= { mscVncsVpLCOpsEntry 6 }

mscVncsVpPermittedTrunkTypes OBJECT-TYPE
   SYNTAX     OCTET STRING (SIZE (1))
   ACCESS     read-write
   STATUS     mandatory
   DESCRIPTION
     "This attribute specifies up to eight types of trunks that can be used 
      on the route. The terrestrial and satellite trunk types have been 
      defined, leaving six remaining arbitrary types that can be defined by 
      the network administration. The trunk's type is indicated in the 
      trunkType attribute of the Trunk component. When selecting a 
      route, PORS chooses only trunks whose trunkTypes are in the 
      permittedTrunkTypes for the path.

      Description of bits:
      terrestrial(0)
      satellite(1)
      trunkType1(2)
      trunkType2(3)
      trunkType3(4)
      trunkType4(5)
      trunkType5(6)
      trunkType6(7)"
   DEFVAL     { 'f8'H }
::= { mscVncsVpLCOpsEntry 7 }

mscVncsVpRequiredSecurity OBJECT-TYPE
   SYNTAX     Unsigned32 (0..7)
   ACCESS     read-write
   STATUS     mandatory
   DESCRIPTION
     "This attribute specifies the required minimum level of security of 
      the trunks on the route. Zero represents the most secure and seven 
      represents the least secure. The trunk's security is indicated by the 
      trunkSecurity attribute of the Trunk component, and has values 
      identical in range and meaning to the requiredSecurity attribute. 
      PORS ensures that any route selected does not contain a trunk 
      whose trunkSecurity attribute is numerically greater than the 
      requiredSecurity."
   DEFVAL     { 4 }
::= { mscVncsVpLCOpsEntry 8 }

mscVncsVpRequiredCustomerParm OBJECT-TYPE
   SYNTAX     Unsigned32 (0..7)
   ACCESS     read-write
   STATUS     mandatory
   DESCRIPTION
     "This attribute specifies the allowed customer defined parameter of 
      the trunks on the route. Its value, a number from zero to seven, is 
      chosen by network administration to have a meaning specific to 
      their network, thus allowing them to customize the use of their 
      trunks. A complementary trunk attribute, customerParameter, also 
      has a value from zero to seven. The route selection process does not 
      consider trunks whose customerParameter is greater than the 
      requiredCustomerParameter of the path."
   DEFVAL     { 4 }
::= { mscVncsVpLCOpsEntry 9 }

mscVncsVpPathAttributeToMinimize OBJECT-TYPE
   SYNTAX     INTEGER  {
                 cost(0),
                 delay(1) }
   ACCESS     read-write
   STATUS     mandatory
   DESCRIPTION
     "This attribute specifies whether a route is selected on the basis of 
      minimizing the cost or the delay. Each trunk has a cost and a delay 
      metric associated with it. The cost of a selected route is the sum of 
      the trunk cost metrics for all trunks included in the route. The delay 
      of a selected route is the sum of the trunk delay metric for all trunks 
      included in the route."
   DEFVAL     { cost }
::= { mscVncsVpLCOpsEntry 10 }

mscVncsVpMaximumAcceptableCost OBJECT-TYPE
   SYNTAX     Unsigned32 (0..65535)
   ACCESS     read-write
   STATUS     mandatory
   DESCRIPTION
     "This attribute specifies an upper bound on the cost metric of a route, 
      which is the sum of the cost metrics of all trunks on the route. The 
      cost metric is the trunkCost attribute of the Trunk component. If for 
      any trunk the trunkCost is larger than the maximumAcceptableCost, 
      then that trunk is not considered during the route selection. While a 
      shortest route is being selected, the route cost is being compared 
      with the maximumAcceptableCost attribute, and this is done for any 
      minimization criterion. No route is selected if the cost metric of the 
      shortest route is larger than the maximumAcceptableCost."
   DEFVAL     { 1280 }
::= { mscVncsVpLCOpsEntry 11 }

mscVncsVpMaximumAcceptableDelay OBJECT-TYPE
   SYNTAX     Unsigned32 (0..100000)
   ACCESS     read-write
   STATUS     mandatory
   DESCRIPTION
     "This attribute specifies an upper bound on the delay of a route, 
      which is the sum of the delays of all trunks on the route. It should 
      be provisioned with a reasonable maximum acceptable delay for the 
      end to end one way delay of a 512-byte packet. Remember, that the 
      trunk during its staging measures a measuredRoundTripDelay. This 
      delay is divided by two and truncated to an integer number of 
      milliseconds to provide a one way delay which is used to populate 
      the delay in this trunk object in the topological database. The value 
      includes emission, propagation, and queuing delays. A 512-byte 
      packet is used to perform the measurement. 
      If for any trunk the half of the trunk's measuredRoundTripDelay is 
      larger than the maximumAcceptableDelay, then that trunk is not 
      considered during the route selection.
      While a shortest route is being selected, the route delay is being 
      compared with the maximumAcceptableDelay attribute, and this is 
      done for any minimization criterion. No route is selected if the 
      delay metric of the shortest route is larger than the 
      maximumAcceptableDelay."
   DEFVAL     { 100000 }
::= { mscVncsVpLCOpsEntry 12 }

mscVncsVpEmissionPriority OBJECT-TYPE
   SYNTAX     Unsigned32 (0..2)
   ACCESS     read-write
   STATUS     mandatory
   DESCRIPTION
     "This attribute specifies the urgency with which packets on the path 
      are emitted by the trunks on the route. EmissionPriority of zero 
      indicates the highest emission priority, while two indicates the 
      lowest emission priority. Packets with a higher emissionPriority (or 
      numerically less) are serviced and sent out before the packets of 
      lower emissionPriority (or numerically higher)."
   DEFVAL     { 0 }
::= { mscVncsVpLCOpsEntry 13 }

mscVncsVpDiscardPriority OBJECT-TYPE
   SYNTAX     Unsigned32 (1..3)
   ACCESS     read-write
   STATUS     mandatory
   DESCRIPTION
     "This attribute specifies the importance of the packets on the path. 
      One is used for paths carrying the most important traffic, and three 
      is used for paths carrying the least important traffic. Packets with 
      lower discardPriority(numerically lower) are discarded after 
      packets with a higher discardPriority(numerically higher)."
   DEFVAL     { 1 }
::= { mscVncsVpLCOpsEntry 14 }

mscVncsVpPathFailureAction OBJECT-TYPE
   SYNTAX     INTEGER  {
                 disconnectConnection(0),
                 reRoutePath(1) }
   ACCESS     read-write
   STATUS     mandatory
   DESCRIPTION
     "This attribute specifies whether the application can tolerate 
      momentary interruption of a path while a new path is selected. If 
      disconnectConnection is chosen, the application is informed as 
      soon as possible about a failure by disconnection. If the attribute is 
      set to reRoutePath, the path may attempt an immediate reroute, 
      provided the failure is a recoverable failure. If rerouting fails, the 
      application is informed of the failure. 
      With this option set to reRoutePath, the LCo may wait up to 30 
      seconds before informing the service of complete disconnection in 
      order to allow both ends to attempt to reconnect. Note that if PLC 
      components are different at both ends only the calling end is 
      allowed to reconnect.
      All pathTypes respect this attribute. Also on a manualPath with 
      both ends provisioned with independent paths (at least with respect 
      to the failure) this option will have the desired effect that the path is 
      rerouted without complete disconnection at both ends."
   DEFVAL     { reRoutePath }
::= { mscVncsVpLCOpsEntry 15 }

mscVncsVpOptimization OBJECT-TYPE
   SYNTAX     INTEGER  {
                 disabled(0),
                 enabled(1) }
   ACCESS     read-write
   STATUS     mandatory
   DESCRIPTION
     "This attribute specifies whether this connection should attempt to 
      optimize its path when requested by the Rtg Pors component. Every 
      path is optimal when it is established, but as network traffic patterns 
      and configurations change this path may no longer be optimal. The 
      PORS connection manager on a module requests circuits to 
      optimize at the optimizationInterval."
   DEFVAL     { enabled }
::= { mscVncsVpLCOpsEntry 16 }

mscVncsVpMaximumAcceptableGatewayCost OBJECT-TYPE
   SYNTAX     Unsigned32 (0..65535)
   ACCESS     read-write
   STATUS     mandatory
   DESCRIPTION
     "This attribute indicates an upper bound on the gateway cost metric 
      of a route, which is the sum of the gateway cost metrics of all 
      gateway links on the route. It has the same semantics as the 
      maximumAcceptableCost except that gateway cost metrics are used 
      instead of trunk cost metrics. Gateway cost metrics are provisioned 
      under Trunk Address component of a gateway link specifying a 
      gateway costs of reaching an address through the link."
   DEFVAL     { 2048 }
::= { mscVncsVpLCOpsEntry 17 }

mscVncsVpFrOpsTable OBJECT-TYPE
   SYNTAX     SEQUENCE OF MscVncsVpFrOpsEntry
   ACCESS     not-accessible
   STATUS     mandatory
   DESCRIPTION
     "This group contains attributes which define how audio data is 
      carried across the Passport network."
::= { mscVncsVp 3 }

mscVncsVpFrOpsEntry OBJECT-TYPE
   SYNTAX     MscVncsVpFrOpsEntry
   ACCESS     not-accessible
   STATUS     mandatory
   DESCRIPTION
     "An entry in the mscVncsVpFrOpsTable."
   INDEX {
      mscVncsIndex,
      mscVncsVpIndex }
::= { mscVncsVpFrOpsTable 1 }

MscVncsVpFrOpsEntry ::= SEQUENCE {
   mscVncsVpMaxVoiceBitRate
      INTEGER,
   mscVncsVpMinVoiceBitRate
      INTEGER,
   mscVncsVpMaxModemBitRate
      INTEGER,
   mscVncsVpMinModemBitRate
      INTEGER,
   mscVncsVpAudioGain
      INTEGER,
   mscVncsVpSilenceSuppression
      INTEGER,
   mscVncsVpEchoCancellation
      INTEGER,
   mscVncsVpSilenceSuppressionFactor
      Unsigned32,
   mscVncsVpDataCallsAccepted
      INTEGER,
   mscVncsVpFaxIdleSuppressionG711G726
      INTEGER,
   mscVncsVpInsertedOutputDelay
      INTEGER,
   mscVncsVpVoiceTrafficOptimization
      INTEGER,
   mscVncsVpDtmfRegeneration
      INTEGER,
   mscVncsVpV17EncodedAsG711G726
      INTEGER }

mscVncsVpMaxVoiceBitRate OBJECT-TYPE
   SYNTAX     INTEGER  {
                 n64(0),
                 n32(1),
                 n24(2),
                 n16(3) }
   ACCESS     read-write
   STATUS     obsolete
   DESCRIPTION
     "This attribute specifies the maximum encoding bit rate (minimum 
      compression rate) that will be used for voice data.
      
      This attribute was migrated to the max element of the g711G726 
      row of the voiceRates attribute."
   DEFVAL     { n64 }
::= { mscVncsVpFrOpsEntry 1 }

mscVncsVpMinVoiceBitRate OBJECT-TYPE
   SYNTAX     INTEGER  {
                 n64(0),
                 n32(1),
                 n24(2),
                 n16(3) }
   ACCESS     read-write
   STATUS     obsolete
   DESCRIPTION
     "This attribute specifies the minimum encoding bit rate (maximum 
      compression rate) that will be used for voice data.
      
      Migration information:
      
      If minVoiceBitRate is 64 kbit/s, it means that the user did not accept 
      any compression. To get the same effect with the 	current 
      provisioning, we set Vncs/m Vp/n voiceEncodingChoice 	first = 
      g711Only, second = none and third = none.
      
      If minVoiceBitRate is 16, 24 or 32 kbit/s, it means that the user 	did 
      accept compression. To get the same effect with the current	
      provisioning, we set the minimum g711G726 rate in Vncs/m 
      VoiceProfile/n 	voiceRates to minVoiceBitRate and leave 
      voiceEncodingChoice with 	its default values."
   DEFVAL     { n16 }
::= { mscVncsVpFrOpsEntry 2 }

mscVncsVpMaxModemBitRate OBJECT-TYPE
   SYNTAX     INTEGER  {
                 n64(0),
                 n32(1),
                 n24(2),
                 n16(3) }
   ACCESS     read-write
   STATUS     obsolete
   DESCRIPTION
     "This attribute was migrated to the max element of the g711G726 
      row of the modemFaxRates attribute.
      DESCRIPTION"
   DEFVAL     { n64 }
::= { mscVncsVpFrOpsEntry 3 }

mscVncsVpMinModemBitRate OBJECT-TYPE
   SYNTAX     INTEGER  {
                 n64(0),
                 n32(1),
                 n24(2),
                 n16(3) }
   ACCESS     read-write
   STATUS     obsolete
   DESCRIPTION
     "This attribute has been obsoleted. Migration information is as 
      follows:
      
      If minModemBitRate is 64 kbit/s, it means that the user did not 
      accept any compression. To get the same effect with the current 
      provisioning, we set Vncs/m Vp/n modemFaxEncodingChoice first 
      = g711Only, second = none and third = none.
      
      If minModemBitRate is 16, 24 or 32 kbit/s, it means that the user 
      did accept compression. To get the same effect with the current 
      provisioning, we set the minimum g711G726 rate in Vncs/m 
      VoiceProfile/n modemFaxRates to minModemBitRate and leave 
      modemFaxEncodingChoice with its default values.
      DESCRIPTION"
   DEFVAL     { n32 }
::= { mscVncsVpFrOpsEntry 4 }

mscVncsVpAudioGain OBJECT-TYPE
   SYNTAX     INTEGER  {
                 minus6(0),
                 minus4(1),
                 minus2(2),
                 n0(3),
                 n2(4),
                 n4(5),
                 n6(6) }
   ACCESS     read-write
   STATUS     obsolete
   DESCRIPTION
     "This attribute has been migrated to VRoute Interface 
      egressAudioGain."
   DEFVAL     { n0 }
::= { mscVncsVpFrOpsEntry 5 }

mscVncsVpSilenceSuppression OBJECT-TYPE
   SYNTAX     INTEGER  {
                 off(0),
                 on(1),
                 congested(2),
                 slow(3),
                 slowAndCongested(4) }
   ACCESS     read-write
   STATUS     mandatory
   DESCRIPTION
     "This attribute specifies when silence suppression is desired during 
      voice traffic on an audio call.
      
      If silenceSuppression is off, silence suppression is never desired.
      If silenceSuppression is on, silence suppression is always desired.
      If silenceSuppression is congested, silence suppression is desired 
      only when the network is congested. 
      If silenceSuppression is slow, silence suppression is desired only 
      after 20 seconds without audio.
      If silenceSuppression is slowAndCongested, both the slow and 
      congested options are desired.
      
      The negotiated silence suppression is available in Vsr Svs Framer 
      negotiatedSilenceSuppression."
   DEFVAL     { on }
::= { mscVncsVpFrOpsEntry 6 }

mscVncsVpEchoCancellation OBJECT-TYPE
   SYNTAX     INTEGER  {
                 off(0),
                 on(1) }
   ACCESS     read-write
   STATUS     obsolete
   DESCRIPTION
     "This attribute has been migrated to VRoute Interface 
      echoCancellation."
   DEFVAL     { on }
::= { mscVncsVpFrOpsEntry 7 }

mscVncsVpSilenceSuppressionFactor OBJECT-TYPE
   SYNTAX     Unsigned32 (0..60)
   ACCESS     read-write
   STATUS     mandatory
   DESCRIPTION
     "This attribute specifies the expected savings (percent reduction) in 
      required bandwidth if silence suppression is used. If silence 
      suppression is used, the bandwidth required for the connection will 
      be lower than if silence suppression is not used. However, the 
      routing system will not be aware of the unused bandwidth unless 
      that bandwidth is specified by this attribute. 
      If the value specified for the expected savings is too low, then some 
      bandwidth made available by the use of silence suppression will be 
      wasted. If the value specified for the expected savings is too high, 
      then some connections may fail to set up because the routing system 
      will over-calculate the amount of bandwidth available.
      The effectiveness of silence suppression can be influenced by 
      language related speech patterns."
   DEFVAL     { 40 }
::= { mscVncsVpFrOpsEntry 8 }

mscVncsVpDataCallsAccepted OBJECT-TYPE
   SYNTAX     INTEGER  {
                 no(0),
                 yes(1) }
   ACCESS     read-write
   STATUS     mandatory
   DESCRIPTION
     "This attribute specifies whether data calls are allowed if this profile 
      is used."
   DEFVAL     { yes }
::= { mscVncsVpFrOpsEntry 9 }

mscVncsVpFaxIdleSuppressionG711G726 OBJECT-TYPE
   SYNTAX     INTEGER  {
                 off(0),
                 on(1) }
   ACCESS     read-write
   STATUS     mandatory
   DESCRIPTION
     "This attribute specifies the fax idle suppression parameter used 
      during negotiation with the remote end across the subnet. It applies 
      only to fax traffic, not voice or modem traffic.
      
      The negotiated G.711/G.726 fax idle suppression is available in Vsr 
      Svs Framer negotiatedFisG711G726."
   DEFVAL     { on }
::= { mscVncsVpFrOpsEntry 15 }

mscVncsVpInsertedOutputDelay OBJECT-TYPE
   SYNTAX     INTEGER  {
                 n5(5),
                 n15(15),
                 n22(22),
                 n30(30),
                 n35(35),
                 n40(40),
                 n45(45),
                 n50(50),
                 n75(75),
                 n100(100),
                 n125(125),
                 n150(150) }
   ACCESS     read-write
   STATUS     mandatory
   DESCRIPTION
     "This attribute specifies the amount of added output delay used to 
      compensate for cross network delay variations. It applies to voice, 
      modem and fax traffic. It is required to add output delay so that the 
      statistical variation in the transit time of cells crossing the network 
      does not cause gaps in speech. Backbone networks where high 
      priority traffic consumes a high percentage of trunk bandwidth will 
      require a higher insertedOutputDelay to compensate for the greater 
      cell delay variation (CDV).
      
      This attribute is ignored if this call runs on a 1pDS1V or 1pE1V 
      card."
   DEFVAL     { n22 }
::= { mscVncsVpFrOpsEntry 17 }

mscVncsVpVoiceTrafficOptimization OBJECT-TYPE
   SYNTAX     INTEGER  {
                 bandwidth(0),
                 delay(1) }
   ACCESS     read-write
   STATUS     obsolete
   DESCRIPTION
     "This attribute is not supported now.
      This attribute specifies how to optimize voice traffic. Setting 
      voiceTrafficOptimization to bandwidth specifies that voice traffic 
      should be optimized to preserve bandwidth. Setting 
      voiceTrafficOptimization to delay specifies that voice traffic should 
      be optimized to minimize delay."
   DEFVAL     { bandwidth }
::= { mscVncsVpFrOpsEntry 18 }

mscVncsVpDtmfRegeneration OBJECT-TYPE
   SYNTAX     INTEGER  {
                 off(0),
                 on(1) }
   ACCESS     read-write
   STATUS     mandatory
   DESCRIPTION
     "This attribute specifies the DTMF regeneration parameter used 
      during negotiation with the remote end across the subnet. 
      
      If dtmfRegeneration is on, it is desired that DTMF tones received 
      from the link are first converted to digits before being sent to the 
      subnet. When a digit is received from the subnet, its respective 
      DTMF tone is desired to be generated before being sent to the link.
      
      If dtmfRegeneration is off, it is desired that DTMF tones are 
      transported transparently as audio.
      
      DTMF regeneration is not supported on 1pDS1V, 1pE1V, and 
      J2MV cards. On these cards, the value of dtmfRegeneration is 
      ignored.
      
      The negotiated DTMF regeneration is available in Vsr Svs Framer 
      negotiatedDtmfRegeneration."
   DEFVAL     { off }
::= { mscVncsVpFrOpsEntry 19 }

mscVncsVpV17EncodedAsG711G726 OBJECT-TYPE
   SYNTAX     INTEGER  {
                 no(0),
                 yes(1) }
   ACCESS     read-write
   STATUS     mandatory
   DESCRIPTION
     "This attribute specifies how services using this VoiceProfile 
      negotiate with V.17 fax machines. This attribute is not used unless 
      the negotiated fax encoding, available in Vsr Svs Framer 
      negotiatedEncoding, is v29V27Relay and the negotiated 
      modemFax encoding, available in Vsr Svs Framer 
      negotiatedEncoding, is g711, g726 or g711G726.
      
      If v17EncodedAsG711G726 is no, it is desired that V.17 fax 
      machines be instructed to use V.29 so that V.29 fax traffic sent by 
      fax machines can be demodulated and encoded using fax relay.
      
      If v17EncodedAsG711G726 is yes, it is desired that V.17 fax 
      machines be permitted to use V.17 so that V.17 fax traffic sent by 
      fax machines can be encoded using G.711 or G.726. The actual 
      encoding performed depends on the negotiated minimum and 
      maximum modemFax rates, available in Vsr Svs Framer 
      negotiatedRates.
      
      The actual negotiation between services using this VoiceProfile and 
      V.17 fax machines is available in Vsr Svs Framer 
      negotiatedV17AsG711G726."
   DEFVAL     { no }
::= { mscVncsVpFrOpsEntry 20 }

mscVncsVpStatsTable OBJECT-TYPE
   SYNTAX     SEQUENCE OF MscVncsVpStatsEntry
   ACCESS     not-accessible
   STATUS     mandatory
   DESCRIPTION
     "This group contains the operational statistics data for a Voice 
      Networking profile component."
::= { mscVncsVp 4 }

mscVncsVpStatsEntry OBJECT-TYPE
   SYNTAX     MscVncsVpStatsEntry
   ACCESS     not-accessible
   STATUS     mandatory
   DESCRIPTION
     "An entry in the mscVncsVpStatsTable."
   INDEX {
      mscVncsIndex,
      mscVncsVpIndex }
::= { mscVncsVpStatsTable 1 }

MscVncsVpStatsEntry ::= SEQUENCE {
   mscVncsVpUsageCount
      Unsigned32 }

mscVncsVpUsageCount OBJECT-TYPE
   SYNTAX     Unsigned32 (0..4294967295)
   ACCESS     read-only
   STATUS     mandatory
   DESCRIPTION
     "This attribute counts the number of times this VoiceProfile is 
      accessed to set up a connection. This counter wraps to 0 when it 
      reaches its maximum value."
::= { mscVncsVpStatsEntry 1 }

mscVncsVpVoiceRatesTable OBJECT-TYPE
   SYNTAX     SEQUENCE OF MscVncsVpVoiceRatesEntry
   ACCESS     not-accessible
   STATUS     obsolete
   DESCRIPTION
     "This attribute has been migrated to voiceRates."
::= { mscVncsVp 322 }

mscVncsVpVoiceRatesEntry OBJECT-TYPE
   SYNTAX     MscVncsVpVoiceRatesEntry
   ACCESS     not-accessible
   STATUS     obsolete
   DESCRIPTION
     "An entry in the mscVncsVpVoiceRatesTable."
   INDEX {
      mscVncsIndex,
      mscVncsVpIndex,
      mscVncsVpVoiceRatesEncodingIndex,
      mscVncsVpVoiceRatesRateIndex }
::= { mscVncsVpVoiceRatesTable 1 }

MscVncsVpVoiceRatesEntry ::= SEQUENCE {
   mscVncsVpVoiceRatesEncodingIndex
      INTEGER,
   mscVncsVpVoiceRatesRateIndex
      INTEGER,
   mscVncsVpVoiceRatesValue
      FixedPoint1 }

mscVncsVpVoiceRatesEncodingIndex OBJECT-TYPE
   SYNTAX     INTEGER  {
                 g711Only(0),
                 g711G726(1),
                 g728Only(2),
                 g729Only(3) }
   ACCESS     not-accessible
   STATUS     obsolete
   DESCRIPTION
     "This variable represents the next to last index for the 
      mscVncsVpVoiceRatesTable."
::= { mscVncsVpVoiceRatesEntry 1 }

mscVncsVpVoiceRatesRateIndex OBJECT-TYPE
   SYNTAX     INTEGER  {
                 min(0),
                 max(1) }
   ACCESS     not-accessible
   STATUS     obsolete
   DESCRIPTION
     "This variable represents the final index for the 
      mscVncsVpVoiceRatesTable."
::= { mscVncsVpVoiceRatesEntry 2 }

mscVncsVpVoiceRatesValue OBJECT-TYPE
   SYNTAX     FixedPoint1 (80 | 160 | 240 | 320 | 640)
   ACCESS     read-write
   STATUS     obsolete
   DESCRIPTION
     "This variable represents an individual value for the
      mscVncsVpVoiceRatesTable."
::= { mscVncsVpVoiceRatesEntry 3 }

mscVncsVpVoiceEncodingChoiceTable OBJECT-TYPE
   SYNTAX     SEQUENCE OF MscVncsVpVoiceEncodingChoiceEntry
   ACCESS     not-accessible
   STATUS     obsolete
   DESCRIPTION
     "This attribute has been migrated to voiceEncodingChoice."
::= { mscVncsVp 323 }

mscVncsVpVoiceEncodingChoiceEntry OBJECT-TYPE
   SYNTAX     MscVncsVpVoiceEncodingChoiceEntry
   ACCESS     not-accessible
   STATUS     obsolete
   DESCRIPTION
     "An entry in the mscVncsVpVoiceEncodingChoiceTable."
   INDEX {
      mscVncsIndex,
      mscVncsVpIndex,
      mscVncsVpVoiceEncodingChoiceIndex }
::= { mscVncsVpVoiceEncodingChoiceTable 1 }

MscVncsVpVoiceEncodingChoiceEntry ::= SEQUENCE {
   mscVncsVpVoiceEncodingChoiceIndex
      INTEGER,
   mscVncsVpVoiceEncodingChoiceValue
      INTEGER }

mscVncsVpVoiceEncodingChoiceIndex OBJECT-TYPE
   SYNTAX     INTEGER  {
                 first(0),
                 second(1),
                 third(2) }
   ACCESS     not-accessible
   STATUS     obsolete
   DESCRIPTION
     "This variable represents the mscVncsVpVoiceEncodingChoiceTable
      specific index for the mscVncsVpVoiceEncodingChoiceTable."
::= { mscVncsVpVoiceEncodingChoiceEntry 1 }

mscVncsVpVoiceEncodingChoiceValue OBJECT-TYPE
   SYNTAX     INTEGER  {
                 g711Only(0),
                 g711G726(1),
                 g728Only(2),
                 g729Only(3),
                 none(4) }
   ACCESS     read-write
   STATUS     obsolete
   DESCRIPTION
     "This variable represents an individual value for the
      mscVncsVpVoiceEncodingChoiceTable."
::= { mscVncsVpVoiceEncodingChoiceEntry 2 }

mscVncsVpModemFaxRatesTable OBJECT-TYPE
   SYNTAX     SEQUENCE OF MscVncsVpModemFaxRatesEntry
   ACCESS     not-accessible
   STATUS     obsolete
   DESCRIPTION
     "This attribute has been migrated to modemFaxRates."
::= { mscVncsVp 324 }

mscVncsVpModemFaxRatesEntry OBJECT-TYPE
   SYNTAX     MscVncsVpModemFaxRatesEntry
   ACCESS     not-accessible
   STATUS     obsolete
   DESCRIPTION
     "An entry in the mscVncsVpModemFaxRatesTable."
   INDEX {
      mscVncsIndex,
      mscVncsVpIndex,
      mscVncsVpModemFaxRatesEncodingIndex,
      mscVncsVpModemFaxRatesRateIndex }
::= { mscVncsVpModemFaxRatesTable 1 }

MscVncsVpModemFaxRatesEntry ::= SEQUENCE {
   mscVncsVpModemFaxRatesEncodingIndex
      INTEGER,
   mscVncsVpModemFaxRatesRateIndex
      INTEGER,
   mscVncsVpModemFaxRatesValue
      FixedPoint1 }

mscVncsVpModemFaxRatesEncodingIndex OBJECT-TYPE
   SYNTAX     INTEGER  {
                 g711Only(0),
                 g711G726(1),
                 relay(2) }
   ACCESS     not-accessible
   STATUS     obsolete
   DESCRIPTION
     "This variable represents the next to last index for the 
      mscVncsVpModemFaxRatesTable."
::= { mscVncsVpModemFaxRatesEntry 1 }

mscVncsVpModemFaxRatesRateIndex OBJECT-TYPE
   SYNTAX     INTEGER  {
                 min(0),
                 max(1) }
   ACCESS     not-accessible
   STATUS     obsolete
   DESCRIPTION
     "This variable represents the final index for the 
      mscVncsVpModemFaxRatesTable."
::= { mscVncsVpModemFaxRatesEntry 2 }

mscVncsVpModemFaxRatesValue OBJECT-TYPE
   SYNTAX     FixedPoint1 (3 | 12 | 24 | 48 | 72 | 96 | 120 | 144 | 160 | 240 | 320 | 640)
   ACCESS     read-write
   STATUS     obsolete
   DESCRIPTION
     "This variable represents an individual value for the
      mscVncsVpModemFaxRatesTable."
::= { mscVncsVpModemFaxRatesEntry 3 }

mscVncsVpModemFaxEncodingChoiceTable OBJECT-TYPE
   SYNTAX     SEQUENCE OF MscVncsVpModemFaxEncodingChoiceEntry
   ACCESS     not-accessible
   STATUS     obsolete
   DESCRIPTION
     "This attribute has been migrated to modemFaxEncodingChoice.
      
      The faxRelay feature must be present to include a setting of relay."
::= { mscVncsVp 325 }

mscVncsVpModemFaxEncodingChoiceEntry OBJECT-TYPE
   SYNTAX     MscVncsVpModemFaxEncodingChoiceEntry
   ACCESS     not-accessible
   STATUS     obsolete
   DESCRIPTION
     "An entry in the mscVncsVpModemFaxEncodingChoiceTable."
   INDEX {
      mscVncsIndex,
      mscVncsVpIndex,
      mscVncsVpModemFaxEncodingChoiceIndex }
::= { mscVncsVpModemFaxEncodingChoiceTable 1 }

MscVncsVpModemFaxEncodingChoiceEntry ::= SEQUENCE {
   mscVncsVpModemFaxEncodingChoiceIndex
      INTEGER,
   mscVncsVpModemFaxEncodingChoiceValue
      INTEGER }

mscVncsVpModemFaxEncodingChoiceIndex OBJECT-TYPE
   SYNTAX     INTEGER  {
                 first(0),
                 second(1),
                 third(2) }
   ACCESS     not-accessible
   STATUS     obsolete
   DESCRIPTION
     "This variable represents the mscVncsVpModemFaxEncodingChoiceTable
      specific index for the mscVncsVpModemFaxEncodingChoiceTable."
::= { mscVncsVpModemFaxEncodingChoiceEntry 1 }

mscVncsVpModemFaxEncodingChoiceValue OBJECT-TYPE
   SYNTAX     INTEGER  {
                 g711Only(0),
                 g711G726(1),
                 relay(2),
                 none(3) }
   ACCESS     read-write
   STATUS     obsolete
   DESCRIPTION
     "This variable represents an individual value for the
      mscVncsVpModemFaxEncodingChoiceTable."
::= { mscVncsVpModemFaxEncodingChoiceEntry 2 }

mscVncsVpNewVoiceRatesTable OBJECT-TYPE
   SYNTAX     SEQUENCE OF MscVncsVpNewVoiceRatesEntry
   ACCESS     not-accessible
   STATUS     mandatory
   DESCRIPTION
     "This attribute specifies the minimum and maximum voice rate 
      parameters used during negotiation with the remote end across the 
      subnet. For g711G726 encoding, rates can change during voice 
      traffic due to congestion in the network. Therefore, you can have 
      differing minimum and maximum rates for g711G726 encoding. All 
      other encodings have a fixed rate for the duration of voice traffic 
      and so their minimum and maximum rates can not be modified.
      
      The negotiated minimum and maximum voice rates are available in 
      Vsr Svs Framer negotiatedRates."
::= { mscVncsVp 381 }

mscVncsVpNewVoiceRatesEntry OBJECT-TYPE
   SYNTAX     MscVncsVpNewVoiceRatesEntry
   ACCESS     not-accessible
   STATUS     mandatory
   DESCRIPTION
     "An entry in the mscVncsVpNewVoiceRatesTable."
   INDEX {
      mscVncsIndex,
      mscVncsVpIndex,
      mscVncsVpNewVoiceRatesEncodingIndex,
      mscVncsVpNewVoiceRatesRateIndex }
::= { mscVncsVpNewVoiceRatesTable 1 }

MscVncsVpNewVoiceRatesEntry ::= SEQUENCE {
   mscVncsVpNewVoiceRatesEncodingIndex
      INTEGER,
   mscVncsVpNewVoiceRatesRateIndex
      INTEGER,
   mscVncsVpNewVoiceRatesValue
      FixedPoint1 }

mscVncsVpNewVoiceRatesEncodingIndex OBJECT-TYPE
   SYNTAX     INTEGER  {
                 g711Only(0),
                 g711G726(1),
                 g728Only(2),
                 g729Only(3) }
   ACCESS     not-accessible
   STATUS     mandatory
   DESCRIPTION
     "This variable represents the next to last index for the 
      mscVncsVpNewVoiceRatesTable."
::= { mscVncsVpNewVoiceRatesEntry 1 }

mscVncsVpNewVoiceRatesRateIndex OBJECT-TYPE
   SYNTAX     INTEGER  {
                 min(0),
                 max(1) }
   ACCESS     not-accessible
   STATUS     mandatory
   DESCRIPTION
     "This variable represents the final index for the 
      mscVncsVpNewVoiceRatesTable."
::= { mscVncsVpNewVoiceRatesEntry 2 }

mscVncsVpNewVoiceRatesValue OBJECT-TYPE
   SYNTAX     FixedPoint1 (80 | 160 | 240 | 320 | 640)
   ACCESS     read-write
   STATUS     mandatory
   DESCRIPTION
     "This variable represents an individual value for the
      mscVncsVpNewVoiceRatesTable."
::= { mscVncsVpNewVoiceRatesEntry 3 }

mscVncsVpNewVoiceEncodingChoiceTable OBJECT-TYPE
   SYNTAX     SEQUENCE OF MscVncsVpNewVoiceEncodingChoiceEntry
   ACCESS     not-accessible
   STATUS     mandatory
   DESCRIPTION
     "This attribute specifies preferences regarding the encoding of voice 
      traffic. During the setup of an audio call, the local and remote ends 
      negotiate a common encoding to use. The local end's ordered list of 
      preferred encodings is given by all voiceEncodingChoice elements 
      that are not set to none. Prior to negotiation, the local end removes 
      encodings from its list that it cannot use for a particular call. For 
      example, the card for a particular call may not support certain 
      encodings. After this local check, the local end sends its voice 
      encoding preferences to the remote end. The remote end chooses 
      the most preferred encoding that it can support from the list and this 
      encoding is the one used during voice traffic. If the remote end 
      cannot support any encodings on the local end's list, a call does not 
      proceed and an alarm is issued.
      
      The current encoding and encoding rate are available in Vsr Svs 
      currentEncoding and Vsr Svs currentRate.
      
      The encoding choice g711Only specifies that pulse code modulation 
      (PCM) defined by ITU-T G.711 should be performed to encode 
      voice traffic for calls using this profile. In this case, all voice traffic 
      is carried uncompressed at 64 kbit/s.
      
      The encoding choice g711G726 specifies that either pulse code 
      modulation (PCM) defined by ITU-T G.711 or adaptive differential 
      pulse code modulation (ADPCM) defined by ITU-T G.726 should 
      be performed to encode voice traffic for calls using this profile. The 
      actual encoding performed depends on congestion in the network 
      and the settings of the g711G726 row of the voiceRates attribute.
      
      The encoding choice of g728Only specifies that the Low Delay 
      Coded Excited Linear Predictive Coder (LD-CELP) algorithm 
      defined by ITU-T G.728 should be performed to encode voice 
      traffic for calls using this profile. In this case, all voice traffic is 
      carried at 16 kbit/s.
      
      The encoding choice of g729Only specifies that the Conjugated 
      Structure Algebraic Code Excited Linear Predictive Coder 
      (CS-ACELP) algorithm defined by ITU-T G.729 should be 
      performed to encode voice traffic for calls using this profile. In this 
      case, all voice traffic is carried at 8 kbit/s.
      
      The encoding choice of none specifies the end of the encoding 
      choice list. No other encoding choice can appear after none, and 
      none cannot appear as the first choice. The only encoding choice 
      that can appear more than once in voiceEncodingChoice is none.
      
      G.728 and G.729 encoding cannot be performed on a 1pDS1V, 
      1pE1V or J2MV card. 
      
      The negotiated voice encoding is available in Vsr Svs Framer 
      negotiatedEncoding."
::= { mscVncsVp 382 }

mscVncsVpNewVoiceEncodingChoiceEntry OBJECT-TYPE
   SYNTAX     MscVncsVpNewVoiceEncodingChoiceEntry
   ACCESS     not-accessible
   STATUS     mandatory
   DESCRIPTION
     "An entry in the mscVncsVpNewVoiceEncodingChoiceTable."
   INDEX {
      mscVncsIndex,
      mscVncsVpIndex,
      mscVncsVpNewVoiceEncodingChoiceIndex }
::= { mscVncsVpNewVoiceEncodingChoiceTable 1 }

MscVncsVpNewVoiceEncodingChoiceEntry ::= SEQUENCE {
   mscVncsVpNewVoiceEncodingChoiceIndex
      INTEGER,
   mscVncsVpNewVoiceEncodingChoiceValue
      INTEGER }

mscVncsVpNewVoiceEncodingChoiceIndex OBJECT-TYPE
   SYNTAX     INTEGER  {
                 first(0),
                 second(1),
                 third(2) }
   ACCESS     not-accessible
   STATUS     mandatory
   DESCRIPTION
     "This variable represents the mscVncsVpNewVoiceEncodingChoiceTable
      specific index for the mscVncsVpNewVoiceEncodingChoiceTable."
::= { mscVncsVpNewVoiceEncodingChoiceEntry 1 }

mscVncsVpNewVoiceEncodingChoiceValue OBJECT-TYPE
   SYNTAX     INTEGER  {
                 g711Only(0),
                 g711G726(1),
                 g728Only(2),
                 g729Only(3),
                 none(4) }
   ACCESS     read-write
   STATUS     mandatory
   DESCRIPTION
     "This variable represents an individual value for the
      mscVncsVpNewVoiceEncodingChoiceTable."
::= { mscVncsVpNewVoiceEncodingChoiceEntry 2 }

mscVncsVpNewModemFaxRatesTable OBJECT-TYPE
   SYNTAX     SEQUENCE OF MscVncsVpNewModemFaxRatesEntry
   ACCESS     not-accessible
   STATUS     mandatory
   DESCRIPTION
     "This attribute specifies the minimum and maximum modemFax and 
      fax rate parameters used during negotiation with the remote end 
      across the subnet.
      
      For g711Only encoding, all modem/fax traffic is carried 
      uncompressed at 64 kbit/s, so this row of modemFaxRates cannot 
      be changed.
      
      For g711G726 encoding, rates can change during modemFax and 
      fax traffic due to congestion in the network. The minimum and 
      maximum rates that can occur during the modemFax traffic are 
      specified by the g711G726 row of modemFaxRates.
      
      The relay row of modemFaxRates specifies the minimum and 
      maximum rates of sending fax machines that are allowed for fax 
      relay. relay does not apply to modem calls.
      
      The negotiated minimum and maximum modemFax and fax rates 
      are available in Vsr Svs Framer negotiatedRates."
::= { mscVncsVp 383 }

mscVncsVpNewModemFaxRatesEntry OBJECT-TYPE
   SYNTAX     MscVncsVpNewModemFaxRatesEntry
   ACCESS     not-accessible
   STATUS     mandatory
   DESCRIPTION
     "An entry in the mscVncsVpNewModemFaxRatesTable."
   INDEX {
      mscVncsIndex,
      mscVncsVpIndex,
      mscVncsVpNewModemFaxRatesEncodingIndex,
      mscVncsVpNewModemFaxRatesRateIndex }
::= { mscVncsVpNewModemFaxRatesTable 1 }

MscVncsVpNewModemFaxRatesEntry ::= SEQUENCE {
   mscVncsVpNewModemFaxRatesEncodingIndex
      INTEGER,
   mscVncsVpNewModemFaxRatesRateIndex
      INTEGER,
   mscVncsVpNewModemFaxRatesValue
      FixedPoint1 }

mscVncsVpNewModemFaxRatesEncodingIndex OBJECT-TYPE
   SYNTAX     INTEGER  {
                 g711Only(0),
                 g711G726(1),
                 relay(2) }
   ACCESS     not-accessible
   STATUS     mandatory
   DESCRIPTION
     "This variable represents the next to last index for the 
      mscVncsVpNewModemFaxRatesTable."
::= { mscVncsVpNewModemFaxRatesEntry 1 }

mscVncsVpNewModemFaxRatesRateIndex OBJECT-TYPE
   SYNTAX     INTEGER  {
                 min(0),
                 max(1) }
   ACCESS     not-accessible
   STATUS     mandatory
   DESCRIPTION
     "This variable represents the final index for the 
      mscVncsVpNewModemFaxRatesTable."
::= { mscVncsVpNewModemFaxRatesEntry 2 }

mscVncsVpNewModemFaxRatesValue OBJECT-TYPE
   SYNTAX     FixedPoint1 (0 | 3 | 12 | 24 | 48 | 72 | 96 | 120 | 144 | 160 | 240 | 320 | 640)
   ACCESS     read-write
   STATUS     mandatory
   DESCRIPTION
     "This variable represents an individual value for the
      mscVncsVpNewModemFaxRatesTable."
::= { mscVncsVpNewModemFaxRatesEntry 3 }

mscVncsVpNewModemFaxEncodingChoiceTable OBJECT-TYPE
   SYNTAX     SEQUENCE OF MscVncsVpNewModemFaxEncodingChoiceEntry
   ACCESS     not-accessible
   STATUS     mandatory
   DESCRIPTION
     "This attribute specifies preferences regarding the encoding of 
      modemFax and fax traffic. During the setup of an audio call, the 
      local and remote ends negotiate one common encoding to use 
      during modemFax traffic and one common encoding to use during 
      fax traffic. The local end's ordered list of preferred encodings is 
      given by all modemFaxEncodingChoice elements that are not set to 
      none. Prior to negotiation, the local end removes encodings from its 
      list that it cannot use for a particular call. For example, the card for 
      a particular call may not be able to support certain encodings, or in 
      the case of relay, the rate of the sending machine may not be 
      supported. After this local check, the local end sends its modem/fax 
      encoding preferences to the remote end. The remote end uses the 
      two most preferred encodings that it can support from the list to 
      determine the encoding used during modemFax traffic and the 
      encoding used during fax traffic. If the remote end cannot support 
      any encodings on the local end's list, a call does not proceed and an 
      alarm is issued.
      
      The current encoding and encoding rate are available in Vsr Svs 
      currentEncoding and Vsr Svs currentRate.
      
      The encoding choice g711Only specifies that pulse code modulation 
      (PCM) defined by ITU-T G.711 should be performed to encode 
      modem/fax traffic for calls using this profile. In this case, all 
      modem/fax traffic is carried uncompressed at 64 kbit/s.
      
      The encoding choice g711G726 specifies that either pulse code 
      modulation (PCM) defined by ITU-T G.711 or adaptive differential 
      pulse code modulation (ADPCM) defined by ITU-T G.726 should 
      be performed to encode modem/fax traffic for calls using this 
      profile. The actual encoding performed depends on congestion in 
      the network and the settings of the g711G726 row of the 
      modemFaxRates attribute.
      
      The encoding choice of relay specifies that modulated modem/fax 
      traffic is demodulated and sent through the network as Passport 
      cells at the base rate of the sending machine. The types of 
      modulation/demodulation supported are V.29 up to 9.6 kbit/s and 
      V.27 up to 4.8 kbit/s. Only fax traffic can use relay.
      
      If modemFaxEncodingChoice is relay, none, none, modem traffic 
      is not supported. If modemFaxEncodingChoice is none, none, 
      none, all traffic is treated like voice traffic.
      
      Fax relay cannot be performed on 1pDS1V, 1pE1V or J2MV cards.
      
      The negotiated modemFax and fax encodings are available in Vsr 
      Svs Framer negotiatedEncoding."
::= { mscVncsVp 384 }

mscVncsVpNewModemFaxEncodingChoiceEntry OBJECT-TYPE
   SYNTAX     MscVncsVpNewModemFaxEncodingChoiceEntry
   ACCESS     not-accessible
   STATUS     mandatory
   DESCRIPTION
     "An entry in the mscVncsVpNewModemFaxEncodingChoiceTable."
   INDEX {
      mscVncsIndex,
      mscVncsVpIndex,
      mscVncsVpNewModemFaxEncodingChoiceIndex }
::= { mscVncsVpNewModemFaxEncodingChoiceTable 1 }

MscVncsVpNewModemFaxEncodingChoiceEntry ::= SEQUENCE {
   mscVncsVpNewModemFaxEncodingChoiceIndex
      INTEGER,
   mscVncsVpNewModemFaxEncodingChoiceValue
      INTEGER }

mscVncsVpNewModemFaxEncodingChoiceIndex OBJECT-TYPE
   SYNTAX     INTEGER  {
                 first(0),
                 second(1),
                 third(2) }
   ACCESS     not-accessible
   STATUS     mandatory
   DESCRIPTION
     "This variable represents the mscVncsVpNewModemFaxEncodingChoiceTable
      specific index for the mscVncsVpNewModemFaxEncodingChoiceTable."
::= { mscVncsVpNewModemFaxEncodingChoiceEntry 1 }

mscVncsVpNewModemFaxEncodingChoiceValue OBJECT-TYPE
   SYNTAX     INTEGER  {
                 g711Only(0),
                 g711G726(1),
                 relay(2),
                 none(3) }
   ACCESS     read-write
   STATUS     mandatory
   DESCRIPTION
     "This variable represents an individual value for the
      mscVncsVpNewModemFaxEncodingChoiceTable."
::= { mscVncsVpNewModemFaxEncodingChoiceEntry 2 }




-- 
-- Version and Compliance statements
-- 



-- Object-Group Statement:
-- A list of all current accessible leaf objects.

-- OBJECTS { mscVncsVpNewVoiceRatesValue,
--           mscVncsVpRequiredTrafficType,
--           mscVncsVpHoldingPriority,
--           mscVncsVpEmissionPriority,
--           mscVncsVpMaximumAcceptableDelay,
--           mscVncsRowStatus,
--           mscVncsVpMaximumAcceptableCost,
--           mscVncsDPIncompleteTranslations,
--           mscVncsDPDnDestinationComponentId,
--           mscVncsDPRowStatus,
--           mscVncsDPDnNumberingPlanIndicator,
--           mscVncsVpComponentName,
--           mscVncsVpSilenceSuppression,
--           mscVncsVpNewVoiceEncodingChoiceValue,
--           mscVncsVpRequiredCustomerParm,
--           mscVncsDPCompleteTranslations,
--           mscVncsCommentText,
--           mscVncsDPDnDataNetworkAddress,
--           mscVncsVpDiscardPriority,
--           mscVncsDPDnVoiceProfileNumber,
--           mscVncsDPFailedTranslations,
--           mscVncsVpDataCallsAccepted,
--           mscVncsComponentName,
--           mscVncsVpBumpPreference,
--           mscVncsVpPermittedTrunkTypes,
--           mscVncsDPComponentName,
--           mscVncsVpOptimization,
--           mscVncsVpSilenceSuppressionFactor,
--           mscVncsStorageType,
--           mscVncsVpSetupPriority,
--           mscVncsDPDnComponentName,
--           mscVncsVpV17EncodedAsG711G726,
--           mscVncsDPStorageType,
--           mscVncsVpNewModemFaxEncodingChoiceValue,
--           mscVncsVRoutesValue,
--           mscVncsVpRequiredSecurity,
--           mscVncsVpInsertedOutputDelay,
--           mscVncsTotalTranslations,
--           mscVncsVpMaximumAcceptableGatewayCost,
--           mscVncsVpStorageType,
--           mscVncsVpDtmfRegeneration,
--           mscVncsVpNewModemFaxRatesValue,
--           mscVncsDPDnRowStatus,
--           mscVncsVpRowStatus,
--           mscVncsVpPathAttributeToMinimize,
--           mscVncsVpUsageCount,
--           mscVncsDPDnDestinationNodeId,
--           mscVncsDPDnStorageType,
--           mscVncsVpPathFailureAction,
--           mscVncsVpFaxIdleSuppressionG711G726 }
-- STATUS  mandatory
-- DESCRIPTION
--   "A list of all current accessible leaf objects."

vncsCallServerGroup OBJECT IDENTIFIER ::= { vncsCallServerMIB 1 }
vncsCallServerGroupCA OBJECT IDENTIFIER ::= { vncsCallServerGroup 1 }
vncsCallServerGroupCA02 OBJECT IDENTIFIER ::= { vncsCallServerGroupCA 3 }
vncsCallServerGroupCA02A OBJECT IDENTIFIER ::= { vncsCallServerGroupCA02 2 }



-- Agent-Capabilities Statement:

-- PRODUCT-RELEASE "MscPassport Release 1.2 VncsCallServer."
-- STATUS          mandatory
-- DESCRIPTION     "Carrier Passport VncsCallServer MIB: MIB Version CA02A,
--                  Software Version CA02S9C."
-- SUPPORTS        Nortel-MsCarrier-MscPassport-VncsCallServerMIB
--    INCLUDES     { vncsCallServerGroupCA02A }

vncsCallServerCapabilities OBJECT IDENTIFIER ::= { vncsCallServerMIB 3 }
vncsCallServerCapabilitiesCA OBJECT IDENTIFIER ::= { vncsCallServerCapabilities 1 }
vncsCallServerCapabilitiesCA02 OBJECT IDENTIFIER ::= { vncsCallServerCapabilitiesCA 3 }
vncsCallServerCapabilitiesCA02A OBJECT IDENTIFIER ::= { vncsCallServerCapabilitiesCA02 2 }





END
