Nortel-MsCarrier-MscPassport-ImaMIB
DEFINITIONS ::= BEGIN



IMPORTS

      OBJECT-TYPE
   FROM RFC-1212

      mscPassportMIBs
   FROM Nortel-MsCarrier-MscPassport-UsefulDefinitionsMIB

      Counter32,
      DisplayString,
      StorageType,
      RowStatus,
      Gauge32,
      Integer32,
      Unsigned32
   FROM Nortel-MsCarrier-MscPassport-StandardTextualConventionsMIB

      AsciiString,
      Hex,
      NonReplicated,
      PassportCounter64,
      Link
   FROM Nortel-MsCarrier-MscPassport-TextualConventionsMIB

      mscLpIndex,
      mscLpDS3Index,
      mscLp,
      mscLpDS3
   FROM Nortel-MsCarrier-MscPassport-LogicalProcessorMIB;




-- LAST-UPDATED   "9909010000Z"
-- ORGANIZATION   "Nortel Networks"
-- CONTACT-INFO   "
--         Nortel Carrier Data Network Management
--         
--         Postal:       P.O. Box 3511, Station C 
--                       Ottawa, Ontario 
--                       Canada  K1Y 4H7
--         
--         via the WEB:  http://www.nortelnetworks.com  
--                       select 'Contact Us' from the menu
--          
--         via phone:    1-800-4NORTEL"
-- DESCRIPTION
--    "The module describing the Nortel MsCarrier MscPassport
--     Ima Enterprise MIB."

imaMIB OBJECT IDENTIFIER ::= { mscPassportMIBs 115 }










-- Lp/n InverseMultiplexerAtm/n
-- Lp/n Ds3/n InverseMultiplexerAtm/n
-- 
-- This component is used to define an inverse multiplexing for ATM 
-- (IMA) group. IMA provides a data rate greater than DS1 E1 in 
-- increments of DS1 E1. To use IMA on an 8pDS1E1 function 
-- processor, add Lp/n InverseMultiplexerAtm/n. To use IMA on a 
-- 4pDS3ChAtm function processor, add Lp/n Ds3/n 
-- InverseMultiplexerAtm/n.
-- 
-- The instance range 0..29 applies to Multi-Service Access cards, and 
-- the instance range 0..7 applies to all other cards.
-- The instance number of an IMA group must not be the same as the 
-- instance number of a DS1/E1 "ATM UNI port" under the same Lp. 
-- An "ATM UNI port" is a DS1 or E1 component with a single Chan 
-- whose applicationFramer attribute is linked to an AtmIf component.
-- On a Multi-Service Access card, ports that are used as IMA links 
-- have two immiscible sub-ranges: 0..15 and 16..31. The instance 
-- number of an IMA group must be in the same sub-range as all of its 
-- ports.

mscLpDS3Ima OBJECT IDENTIFIER ::= { mscLpDS3 7 }



mscLpDS3ImaRowStatusTable OBJECT-TYPE
   SYNTAX     SEQUENCE OF MscLpDS3ImaRowStatusEntry
   ACCESS     not-accessible
   STATUS     mandatory
   DESCRIPTION
     "This entry controls the addition and deletion of 
      mscLpDS3Ima components."
::= { mscLpDS3Ima 1 }

mscLpDS3ImaRowStatusEntry OBJECT-TYPE
   SYNTAX     MscLpDS3ImaRowStatusEntry
   ACCESS     not-accessible
   STATUS     mandatory
   DESCRIPTION
     "A single entry in the table represents a single 
      mscLpDS3Ima component."
   INDEX {
      mscLpIndex,
      mscLpDS3Index,
      mscLpDS3ImaIndex }
::= { mscLpDS3ImaRowStatusTable 1 }

MscLpDS3ImaRowStatusEntry ::= SEQUENCE {
   mscLpDS3ImaRowStatus
      RowStatus,
   mscLpDS3ImaComponentName
      DisplayString,
   mscLpDS3ImaStorageType
      StorageType,
   mscLpDS3ImaIndex
      Integer32 }

mscLpDS3ImaRowStatus OBJECT-TYPE
   SYNTAX     RowStatus 
   ACCESS     read-write
   STATUS     mandatory
   DESCRIPTION
     "This variable is used as the basis for SNMP naming of
      mscLpDS3Ima components.
      These components can be added and deleted."
::= { mscLpDS3ImaRowStatusEntry 1 }

mscLpDS3ImaComponentName OBJECT-TYPE
   SYNTAX     DisplayString 
   ACCESS     read-only
   STATUS     mandatory
   DESCRIPTION
     "This variable provides the component's string name for
      use with the ASCII Console Interface"
::= { mscLpDS3ImaRowStatusEntry 2 }

mscLpDS3ImaStorageType OBJECT-TYPE
   SYNTAX     StorageType 
   ACCESS     read-only
   STATUS     mandatory
   DESCRIPTION
     "This variable represents the storage type value for the
      mscLpDS3Ima tables."
::= { mscLpDS3ImaRowStatusEntry 4 }

mscLpDS3ImaIndex OBJECT-TYPE
   SYNTAX     Integer32 (0..13)
   ACCESS     not-accessible
   STATUS     mandatory
   DESCRIPTION
     "This variable represents the index for the mscLpDS3Ima tables."
::= { mscLpDS3ImaRowStatusEntry 10 }

mscLpDS3ImaProvTable OBJECT-TYPE
   SYNTAX     SEQUENCE OF MscLpDS3ImaProvEntry
   ACCESS     not-accessible
   STATUS     mandatory
   DESCRIPTION
     "This group contains the provisionable attributes for the Ima 
      component.
      The default values of linkSelectionCriterion and linkRetryTimeout 
      depend on card type."
::= { mscLpDS3Ima 10 }

mscLpDS3ImaProvEntry OBJECT-TYPE
   SYNTAX     MscLpDS3ImaProvEntry
   ACCESS     not-accessible
   STATUS     mandatory
   DESCRIPTION
     "An entry in the mscLpDS3ImaProvTable."
   INDEX {
      mscLpIndex,
      mscLpDS3Index,
      mscLpDS3ImaIndex }
::= { mscLpDS3ImaProvTable 1 }

MscLpDS3ImaProvEntry ::= SEQUENCE {
   mscLpDS3ImaLinkSelectionCriterion
      INTEGER,
   mscLpDS3ImaMaxDiffDelay
      Unsigned32,
   mscLpDS3ImaLinkRetryTimeout
      Unsigned32,
   mscLpDS3ImaApplicationFramerName
      Link,
   mscLpDS3ImaTransmitClockMode
      INTEGER,
   mscLpDS3ImaProtocol
      INTEGER }

mscLpDS3ImaLinkSelectionCriterion OBJECT-TYPE
   SYNTAX     INTEGER  {
                 leastDelay(0),
                 maxBandwidth(1) }
   ACCESS     read-write
   STATUS     mandatory
   DESCRIPTION
     "This attribute specifies the method to be used by the IMA group 
      when selecting links to be activated. This comes into effect only 
      when the configured links do not respect the maximum differential 
      delay (otherwise all links are accepted).
      
      If leastDelay is chosen, first the link having the smallest delay is 
      selected as the reference link. The IMA group includes all links 
      which respect the maximum differential delay relative to the 
      reference link.
      
      If maxBandwidth is chosen, the IMA group selects the maximum 
      possible number of links, with each selected link respecting the 
      maximum differential delay relative to every other selected link. 
      When more than one possibility exists, the combination which 
      offers the least delay isselected.
      
      The default value for Multi-Service Access cards is leastDelay, and 
      for all other cards is maxBandwidth. On Multi-Service Access 
      cards leastDelay is the only acceptable provisionable value."
::= { mscLpDS3ImaProvEntry 1 }

mscLpDS3ImaMaxDiffDelay OBJECT-TYPE
   SYNTAX     Unsigned32 (1..100)
   ACCESS     read-write
   STATUS     mandatory
   DESCRIPTION
     "This attribute specifies the maximum differential delay between 
      links acceptable in the IMA group. If a link violates that maximum 
      differential delay, it will not be active in the IMA group and an 
      alarm will be generated."
   DEFVAL     { 25 }
::= { mscLpDS3ImaProvEntry 2 }

mscLpDS3ImaLinkRetryTimeout OBJECT-TYPE
   SYNTAX     Unsigned32 (0..1000)
   ACCESS     read-write
   STATUS     mandatory
   DESCRIPTION
     "This attribute specifies the amount of time before reactivation of a 
      link is attempted after it recovers from a failure condition.
      
      The default value for Multi-Service Access cards is 1, and for all 
      other cards is 10. On Multi-Service Access cards 1 is the only 
      acceptable provisionable value."
::= { mscLpDS3ImaProvEntry 3 }

mscLpDS3ImaApplicationFramerName OBJECT-TYPE
   SYNTAX     Link 
   ACCESS     read-write
   STATUS     mandatory
   DESCRIPTION
     "This attribute defines the link to the AtmIf component using the Ima. 
      An example is AtmIf/31."
::= { mscLpDS3ImaProvEntry 4 }

mscLpDS3ImaTransmitClockMode OBJECT-TYPE
   SYNTAX     INTEGER  {
                 itc(0),
                 ctc(1) }
   ACCESS     read-write
   STATUS     mandatory
   DESCRIPTION
     "This attribute specifies the transmit clocking mode.
      If itc (Independent Transmit Clock) is chosen, the physical ports 
      used by the IMA group may have different clocking sources.
      If ctc (Common Transmit Clock) is chosen, it is recommended that 
      the physical ports used by the IMA group have the same clocking 
      source. However, if the physical ports have different clocking 
      sources, the operator should ensure that all the clocking sources 
      have the same rate."
   DEFVAL     { itc }
::= { mscLpDS3ImaProvEntry 5 }

mscLpDS3ImaProtocol OBJECT-TYPE
   SYNTAX     INTEGER  {
                 atmForum10(0),
                 proprietary(1) }
   ACCESS     read-write
   STATUS     mandatory
   DESCRIPTION
     "This attribute specifies what protocol the component should run.
      If atmForum10 is chosen, the ATM Forum's IMA protocol (version 
      1.0) will be used and signalled in outgoing IMA Control Protocol 
      (ICP) cells. This protocol is specified in version 1.1 of the ATM 
      Forum IMA specification. The IMA group will come up only if the 
      far end IMA also uses the ATM Forum's IMA protocol.
      If proprietary is chosen, Nortel's proprietary IMA protocol will be 
      used. The IMA group will come up only if the far end IMA also 
      uses Nortel's proprietary IMA protocol. This IMA group will not 
      inter-operate with IMA implementations from other vendors. 
      Feature ima must be provisioned on the LP for this protocol to be 
      used."
   DEFVAL     { atmForum10 }
::= { mscLpDS3ImaProvEntry 6 }

mscLpDS3ImaOperTable OBJECT-TYPE
   SYNTAX     SEQUENCE OF MscLpDS3ImaOperEntry
   ACCESS     not-accessible
   STATUS     mandatory
   DESCRIPTION
     "This group contains the operational attributes for the Ima 
      component."
::= { mscLpDS3Ima 11 }

mscLpDS3ImaOperEntry OBJECT-TYPE
   SYNTAX     MscLpDS3ImaOperEntry
   ACCESS     not-accessible
   STATUS     mandatory
   DESCRIPTION
     "An entry in the mscLpDS3ImaOperTable."
   INDEX {
      mscLpIndex,
      mscLpDS3Index,
      mscLpDS3ImaIndex }
::= { mscLpDS3ImaOperTable 1 }

MscLpDS3ImaOperEntry ::= SEQUENCE {
   mscLpDS3ImaFailureCause
      INTEGER,
   mscLpDS3ImaRemoteDefect
      INTEGER,
   mscLpDS3ImaRemoteLidsConfig
      OCTET STRING,
   mscLpDS3ImaRemoteLidsActive
      OCTET STRING,
   mscLpDS3ImaCellCapacity
      Unsigned32,
   mscLpDS3ImaRemoteGid
      Unsigned32,
   mscLpDS3ImaClockingModeMismatch
      INTEGER }

mscLpDS3ImaFailureCause OBJECT-TYPE
   SYNTAX     INTEGER  {
                 noFailure(0),
                 noGoodLinksInStartup(1),
                 badGidInStartup(2),
                 badLidInStartup(3),
                 unsupportedFrameLengthInStartup(4),
                 timeoutInStartup(5),
                 noGoodLinks(6),
                 remoteFailure(7),
                 unsupportedSymmetryInStartup(8) }
   ACCESS     read-only
   STATUS     mandatory
   DESCRIPTION
     "This attribute indicates the cause of the current local end failure 
      experienced by the IMA group. The failure may have occurred 
      during a start-up procedure or during normal operation. Possible 
      values are:
      noFailure: no local end failure.
      noGoodLinksInStartup: no good links were available during IMA 
      start-up.
      badGidInStartup: during start-up, different group identifiers (GIDs) 
      were received on the links.
      badLidInStartup: during start-up, duplicate link identifiers (LIDs) 
      were received on the links.
      unsupportedFrameLengthInStartup: during start-up, an 
      unsupported frame length was received.
      timeoutInStartup: a time-out has occurred during start-up.
      noGoodLinks: no good links are available in the IMA group.
      remoteFailure: the far end is down.
      unsupportedSymmetryInStartup: the symmetry proposed by the far 
      end is not supported on the near-end. This value will occur when 
      the IMA group is running the ATM Forum protocol and the far end 
      is proposing a group symmetry other than 'symmetric configuration 
      and operation'."
::= { mscLpDS3ImaOperEntry 1 }

mscLpDS3ImaRemoteDefect OBJECT-TYPE
   SYNTAX     INTEGER  {
                 noDefect(0),
                 noGoodLinksInStartup(1),
                 badGidInStartup(2),
                 badLidInStartup(3),
                 unsupportedFrameLengthInStartup(4),
                 timeoutInStartup(5),
                 noGoodLinks(6),
                 locked(7),
                 unsupportedSymmetryInStartup(8),
                 otherAbortStartup(9),
                 insufficientLinks(10),
                 blocked(11) }
   ACCESS     read-only
   STATUS     mandatory
   DESCRIPTION
     "This attribute indicates the cause of the current far end defect 
      experienced by the IMA group.
      For the ATM Forum IMA protocol, possible values are:
      noDefect: no defect.
      unsupportedFrameLengthInStartup: during the far end's start-up, 
      an unsupported frame length was received.
      unsupportedSymmetryInStartup: during the far end's start-up, an 
      unsupported symmetry configuration was received.
      otherAbortStartup: the far end has aborted its start-up for another 
      reason. This could be because different Gids were received on the 
      links or if duplicate link identifiers (LIDs) were received.
      insufficientLinks: the far end does not have sufficient links active. 
      This value will be displayed if the far end IMA group is locked.
      blocked: the far end IMA group is blocked.
      
      For the proprietary IMA protocol, possible values are:
      noDefect: no defect.
      noGoodLinksInStartup: no good links were available during the far 
      end's start-up.
      badGidInStartup: during the far end's start-up, different GIDs were 
      received on the links.
      badLidInStartup: during the far end's start-up, duplicate link 
      identifiers (LIDs) were received on the links.
      unsupportedFrameLengthInStartup: during the far end's start-up, 
      an unsupported frame length was received.
      timeoutInStartup: a time out has occurred during the far end's start-
      up.
      noGoodLinks: no good links are available in the far end IMA 
      group.
      locked: the far end IMA group is locked."
::= { mscLpDS3ImaOperEntry 2 }

mscLpDS3ImaRemoteLidsConfig OBJECT-TYPE
   SYNTAX     OCTET STRING (SIZE (4))
   ACCESS     read-only
   STATUS     mandatory
   DESCRIPTION
     "This attribute indicates all the links which have been configured in 
      the remote IMA group. For example, if links 1, 3 and 5 have been 
      configured in the remote IMA group, this attribute would contain 1 
      3 5.

      Description of bits:
      n0(0)
      n1(1)
      n2(2)
      n3(3)
      n4(4)
      n5(5)
      n6(6)
      n7(7)
      n8(8)
      n9(9)
      n10(10)
      n11(11)
      n12(12)
      n13(13)
      n14(14)
      n15(15)
      n16(16)
      n17(17)
      n18(18)
      n19(19)
      n20(20)
      n21(21)
      n22(22)
      n23(23)
      n24(24)
      n25(25)
      n26(26)
      n27(27)
      n28(28)
      n29(29)
      n30(30)
      n31(31)"
::= { mscLpDS3ImaOperEntry 3 }

mscLpDS3ImaRemoteLidsActive OBJECT-TYPE
   SYNTAX     OCTET STRING (SIZE (4))
   ACCESS     read-only
   STATUS     mandatory
   DESCRIPTION
     "This attribute indicates all the links which are active in the remote 
      IMA group. For example, if links 1 and 5 are active in the remote 
      IMA, this attribute would contain 1 5.

      Description of bits:
      n0(0)
      n1(1)
      n2(2)
      n3(3)
      n4(4)
      n5(5)
      n6(6)
      n7(7)
      n8(8)
      n9(9)
      n10(10)
      n11(11)
      n12(12)
      n13(13)
      n14(14)
      n15(15)
      n16(16)
      n17(17)
      n18(18)
      n19(19)
      n20(20)
      n21(21)
      n22(22)
      n23(23)
      n24(24)
      n25(25)
      n26(26)
      n27(27)
      n28(28)
      n29(29)
      n30(30)
      n31(31)"
::= { mscLpDS3ImaOperEntry 4 }

mscLpDS3ImaCellCapacity OBJECT-TYPE
   SYNTAX     Unsigned32 (0..4294967295)
   ACCESS     read-only
   STATUS     mandatory
   DESCRIPTION
     "This attribute indicates the total cell capacity (in cells per second) 
      which is provided to the ATM layer. This cell capacity takes into 
      account the physical and IMA level overheads."
::= { mscLpDS3ImaOperEntry 5 }

mscLpDS3ImaRemoteGid OBJECT-TYPE
   SYNTAX     Unsigned32 (0..255)
   ACCESS     read-only
   STATUS     mandatory
   DESCRIPTION
     "This attribute indicates the IMA group identifier (GID) used by the 
      remote IMA. A value of 0 will be displayed if the group is not 
      receiving IMA Control Protocol (ICP) cells.
      This attribute will always have a value of 0 if the protocol for the 
      IMA group is proprietary."
::= { mscLpDS3ImaOperEntry 6 }

mscLpDS3ImaClockingModeMismatch OBJECT-TYPE
   SYNTAX     INTEGER  {
                 no(0),
                 yes(1) }
   ACCESS     read-only
   STATUS     mandatory
   DESCRIPTION
     "This attribute indicates whether or not both ends of the IMA group 
      are using the same transmit clocking mode (itc/ctc). Its value will be 
      yes if both ends are not using the same transmit clocking mode. A 
      clocking mode mismatch does not prevent an IMA group from 
      coming up and can be corrected by using the same clocking mode at 
      both ends.
      This attribute will always have a value of no if the protocol for the 
      IMA group is proprietary."
::= { mscLpDS3ImaOperEntry 7 }

mscLpDS3ImaStatsTable OBJECT-TYPE
   SYNTAX     SEQUENCE OF MscLpDS3ImaStatsEntry
   ACCESS     not-accessible
   STATUS     mandatory
   DESCRIPTION
     "This group contains the statistics data for the Ima component."
::= { mscLpDS3Ima 12 }

mscLpDS3ImaStatsEntry OBJECT-TYPE
   SYNTAX     MscLpDS3ImaStatsEntry
   ACCESS     not-accessible
   STATUS     mandatory
   DESCRIPTION
     "An entry in the mscLpDS3ImaStatsTable."
   INDEX {
      mscLpIndex,
      mscLpDS3Index,
      mscLpDS3ImaIndex }
::= { mscLpDS3ImaStatsTable 1 }

MscLpDS3ImaStatsEntry ::= SEQUENCE {
   mscLpDS3ImaRunningTime
      Unsigned32,
   mscLpDS3ImaUnavailSecs
      Unsigned32,
   mscLpDS3ImaFailures
      Unsigned32,
   mscLpDS3ImaReceiveCellUtilization
      Gauge32,
   mscLpDS3ImaTransmitCellUtilization
      Gauge32 }

mscLpDS3ImaRunningTime OBJECT-TYPE
   SYNTAX     Unsigned32 (0..4294967295)
   ACCESS     read-only
   STATUS     mandatory
   DESCRIPTION
     "This attribute indicates the length of time (in seconds) for which the 
      Ima component has been in the unlocked state or has been used for 
      operational testing."
::= { mscLpDS3ImaStatsEntry 1 }

mscLpDS3ImaUnavailSecs OBJECT-TYPE
   SYNTAX     Unsigned32 (0..4294967295)
   ACCESS     read-only
   STATUS     mandatory
   DESCRIPTION
     "This attribute indicates the number of one second intervals during 
      which the Ima component has been unlocked and out of service."
::= { mscLpDS3ImaStatsEntry 2 }

mscLpDS3ImaFailures OBJECT-TYPE
   SYNTAX     Unsigned32 (0..4294967295)
   ACCESS     read-only
   STATUS     mandatory
   DESCRIPTION
     "This attribute indicates the number of complete failures, during 
      start-up or normal operation, that the Ima component has 
      experienced since being added. It must be noted that a service 
      degradation, such as 1 of the 3 links in an IMA group being down, 
      is not counted as a failure. If an Ima component is in a failure loop 
      and does not come up, this count will only increase by 1."
::= { mscLpDS3ImaStatsEntry 3 }

mscLpDS3ImaReceiveCellUtilization OBJECT-TYPE
   SYNTAX     Gauge32 (0..100)
   ACCESS     read-only
   STATUS     mandatory
   DESCRIPTION
     "This attribute indicates the ratio of the number of valid, assigned 
      user cells received on the IMA group to the IMA cell capacity 
      (based on the number of active links). The utilization is calculated 
      over a one minute period.
      
      This attribute will always have a value of 0 if the protocol for the 
      IMA group is proprietary."
::= { mscLpDS3ImaStatsEntry 4 }

mscLpDS3ImaTransmitCellUtilization OBJECT-TYPE
   SYNTAX     Gauge32 (0..100)
   ACCESS     read-only
   STATUS     mandatory
   DESCRIPTION
     "This attribute indicates the ratio of the number of user cells 
      transmitted on the IMA group to the IMA cell capacity (based on 
      the number of active links). The utilization is calculated over a one 
      minute period.
      
      This attribute will always have a value of 0 if the protocol for the 
      IMA group is proprietary."
::= { mscLpDS3ImaStatsEntry 5 }

mscLpDS3ImaCidDataTable OBJECT-TYPE
   SYNTAX     SEQUENCE OF MscLpDS3ImaCidDataEntry
   ACCESS     not-accessible
   STATUS     mandatory
   DESCRIPTION
     "This group contains the attribute for a component's Customer 
      Identifier (CID). Refer to the attribute description for a detailed 
      explanation of CIDs."
::= { mscLpDS3Ima 13 }

mscLpDS3ImaCidDataEntry OBJECT-TYPE
   SYNTAX     MscLpDS3ImaCidDataEntry
   ACCESS     not-accessible
   STATUS     mandatory
   DESCRIPTION
     "An entry in the mscLpDS3ImaCidDataTable."
   INDEX {
      mscLpIndex,
      mscLpDS3Index,
      mscLpDS3ImaIndex }
::= { mscLpDS3ImaCidDataTable 1 }

MscLpDS3ImaCidDataEntry ::= SEQUENCE {
   mscLpDS3ImaCustomerIdentifier
      Unsigned32 }

mscLpDS3ImaCustomerIdentifier OBJECT-TYPE
   SYNTAX     Unsigned32 (0 | 1..8191)
   ACCESS     read-write
   STATUS     mandatory
   DESCRIPTION
     "This attribute holds the Customer Identifier (CID).
      
      Every component has a CID. If a component has a cid attribute, the 
      component's CID is the provisioned value of that attribute; 
      otherwise the component inherits the CID of its parent. The top-
      level component has a CID of 0.
      
      Every operator session also has a CID, which is the CID 
      provisioned for the operator's user ID. An operator will see only the 
      stream data for components having a matching CID. Also, the 
      operator will be allowed to issue commands for only those 
      components which have a matching CID.
      
      An operator CID of 0 is used to identify the Network Manager 
      (referred to as 'NetMan' in DPN). This CID matches the CID of 
      any component. Values 1 to 8191 inclusive (equivalent to 'basic 
      CIDs' in DPN) may be assigned to specific customers."
   DEFVAL     { 0 }
::= { mscLpDS3ImaCidDataEntry 1 }

mscLpDS3ImaStateTable OBJECT-TYPE
   SYNTAX     SEQUENCE OF MscLpDS3ImaStateEntry
   ACCESS     not-accessible
   STATUS     mandatory
   DESCRIPTION
     "This group contains the three OSI State attributes and the six OSI 
      Status attributes. The descriptions generically indicate what each 
      attribute implies about the component. Note that not all the values 
      and state combinations described here are supported by every 
      component which uses this group. For component-specific 
      information and the valid state combinations, refer to NTP 241-
      7001-150, Passport Operations and Maintenance Guide."
::= { mscLpDS3Ima 14 }

mscLpDS3ImaStateEntry OBJECT-TYPE
   SYNTAX     MscLpDS3ImaStateEntry
   ACCESS     not-accessible
   STATUS     mandatory
   DESCRIPTION
     "An entry in the mscLpDS3ImaStateTable."
   INDEX {
      mscLpIndex,
      mscLpDS3Index,
      mscLpDS3ImaIndex }
::= { mscLpDS3ImaStateTable 1 }

MscLpDS3ImaStateEntry ::= SEQUENCE {
   mscLpDS3ImaAdminState
      INTEGER,
   mscLpDS3ImaOperationalState
      INTEGER,
   mscLpDS3ImaUsageState
      INTEGER,
   mscLpDS3ImaAvailabilityStatus
      OCTET STRING,
   mscLpDS3ImaProceduralStatus
      OCTET STRING,
   mscLpDS3ImaControlStatus
      OCTET STRING,
   mscLpDS3ImaAlarmStatus
      OCTET STRING,
   mscLpDS3ImaStandbyStatus
      INTEGER,
   mscLpDS3ImaUnknownStatus
      INTEGER }

mscLpDS3ImaAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component.
      
      The OSI Status attributes, if supported by the component, may 
      provide more details, qualifying the state of the component."
   DEFVAL     { unlocked }
::= { mscLpDS3ImaStateEntry 1 }

mscLpDS3ImaOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle.
      
      The OSI Status attributes, if supported by the component, may 
      provide more details, qualifying the state of the component."
   DEFVAL     { disabled }
::= { mscLpDS3ImaStateEntry 2 }

mscLpDS3ImaUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time.
      
      The OSI Status attributes, if supported by the component, may 
      provide more details, qualifying the state of the component."
   DEFVAL     { idle }
::= { mscLpDS3ImaStateEntry 3 }

mscLpDS3ImaAvailabilityStatus OBJECT-TYPE
   SYNTAX     OCTET STRING (SIZE (2))
   ACCESS     read-only
   STATUS     mandatory
   DESCRIPTION
     "If supported by the component, this attribute indicates the OSI 
      Availability status of the component. Note that, even though it is 
      defined as a multi-valued set, at most one value is shown to the user.
      
      When no values are in the set, this indicates that either the attribute 
      is not supported or that none of the status conditions described 
      below are present.
      
      The value inTest indicates that the resource is undergoing a test 
      procedure. If adminState is locked or shuttingDown, the normal 
      users are precluded from using the resource and controlStatus is 
      reservedForTest. Tests that do not exclude additional users can be 
      present in any operational or administrative state but the 
      reservedForTest condition should not be present.
      
      The value failed indicates that the component has an internal fault 
      that prevents it from operating. The operationalState is disabled.
      
      The value dependency indicates that the component cannot operate 
      because some other resource on which it depends is unavailable. 
      The operationalState is disabled.
      
      The value powerOff indicates the resource requires power to be 
      applied and it is not powered on. The operationalState is disabled.
      
      The value offLine indicates the resource requires a routine 
      operation (either manual, automatic, or both) to be performed to 
      place it on-line and make it available for use. The operationalState 
      is disabled.
      
      The value offDuty indicates the resource is inactive in accordance 
      with a predetermined time schedule. In the absence of other 
      disabling conditions, the operationalState is enabled or disabled.
      
      The value degraded indicates the service provided by the 
      component is degraded in some way, such as in speed or operating 
      capacity. However, the resource remains available for service. The 
      operationalState is enabled.
      
      The value notInstalled indicates the resource is not present. The 
      operationalState is disabled.
      
      The value logFull is not used.

      Description of bits:
      inTest(0)
      failed(1)
      powerOff(2)
      offLine(3)
      offDuty(4)
      dependency(5)
      degraded(6)
      notInstalled(7)
      logFull(8)"
::= { mscLpDS3ImaStateEntry 4 }

mscLpDS3ImaProceduralStatus OBJECT-TYPE
   SYNTAX     OCTET STRING (SIZE (1))
   ACCESS     read-only
   STATUS     mandatory
   DESCRIPTION
     "If supported by the component, this attribute indicates the OSI 
      Procedural status of the component. Note that, even though it is 
      defined as a multi-valued set, at most one value is shown to the user.
      
      When no values are in the set, this indicates that either the attribute 
      is not supported or that none of the status conditions described 
      below are present.
      
      The value initializationRequired indicates (for a resource which 
      doesn't initialize autonomously) that initialization is required before 
      it can perform its normal functions, and this procedure has not been 
      initiated. The operationalState is disabled.
      
      The value notInitialized indicates (for a resource which does 
      initialize autonomously) that initialization is required before it can 
      perform its normal functions, and this procedure has not been 
      initiated. The operationalState may be enabled or disabled.
      
      The value initializing indicates that initialization has been initiated 
      but is not yet complete. The operationalState may be enabled or 
      disabled.
      
      The value reporting indicates the resource has completed some 
      processing operation and is notifying the results. The 
      operationalState is enabled.
      
      The value terminating indicates the component is in a termination 
      phase. If the resource doesn't reinitialize autonomously, 
      operationalState is disabled; otherwise it is enabled or disabled.

      Description of bits:
      initializationRequired(0)
      notInitialized(1)
      initializing(2)
      reporting(3)
      terminating(4)"
::= { mscLpDS3ImaStateEntry 5 }

mscLpDS3ImaControlStatus OBJECT-TYPE
   SYNTAX     OCTET STRING (SIZE (1))
   ACCESS     read-only
   STATUS     mandatory
   DESCRIPTION
     "If supported by the component, this attribute indicates the OSI 
      Control status of the component. Note that, even though it is defined 
      as a multi-valued set, at most one value is shown to the user.
      
      When no values are in the set, this indicates that either the attribute 
      is not supported or that none of the status conditions described 
      below are present.
      
      The value subjectToTest indicates the resource is available but tests 
      may be conducted simultaneously at unpredictable times, which 
      may cause it to exhibit unusual characteristics.
      
      The value partOfServicesLocked indicates that part of the service is 
      restricted from users of a resource. The adminState is unlocked.
      
      The value reservedForTest indicates that the component is 
      administratively unavailable because it is undergoing a test 
      procedure. The adminState is locked.
      
      The value suspended indicates that the service has been 
      administratively suspended.

      Description of bits:
      subjectToTest(0)
      partOfServicesLocked(1)
      reservedForTest(2)
      suspended(3)"
::= { mscLpDS3ImaStateEntry 6 }

mscLpDS3ImaAlarmStatus OBJECT-TYPE
   SYNTAX     OCTET STRING (SIZE (1))
   ACCESS     read-only
   STATUS     mandatory
   DESCRIPTION
     "If supported by the component, this attribute indicates the OSI 
      Alarm status of the component. Note that, even though it is defined 
      as a multi-valued set, at most one value is shown to the user.
      
      When no values are in the set, this indicates that either the attribute 
      is not supported or that none of the status conditions described 
      below are present.
      
      The value underRepair indicates the component is currently being 
      repaired. The operationalState is enabled or disabled.
      
      The value critical indicates one or more critical alarms are 
      outstanding against the component. Other, less severe, alarms may 
      also be outstanding. The operationalState is enabled or disabled.
      
      The value major indicates one or more major alarms are 
      outstanding against the component. Other, less severe, alarms may 
      also be outstanding. The operationalState is enabled or disabled.
      
      The value minor indicates one or more minor alarms are 
      outstanding against the component. Other, less severe, alarms may 
      also be outstanding. The operationalState is enabled or disabled.
      
      The value alarmOutstanding generically indicates that an alarm of 
      some severity is outstanding against the component.

      Description of bits:
      underRepair(0)
      critical(1)
      major(2)
      minor(3)
      alarmOutstanding(4)"
::= { mscLpDS3ImaStateEntry 7 }

mscLpDS3ImaStandbyStatus OBJECT-TYPE
   SYNTAX     INTEGER  {
                 hotStandby(0),
                 coldStandby(1),
                 providingService(2),
                 notSet(15) }
   ACCESS     read-only
   STATUS     mandatory
   DESCRIPTION
     "If supported by the component, this attribute indicates the OSI 
      Standby status of the component.
      
      The value notSet indicates that either the attribute is not supported 
      or that none of the status conditions described below are present. 
      Note that this is a non-standard value, used because the original 
      specification indicated this attribute was set-valued and thus, did not 
      provide a value to indicate that none of the other three are 
      applicable.
      
      The value hotStandby indicates that the resource is not providing 
      service but will be immediately able to take over the role of the 
      resource to be backed up, without initialization activity, and 
      containing the same information as the resource to be backed up.
      
      The value coldStandby indicates the resource is a backup for 
      another resource but will not be immediately able to take over the 
      role of the backed up resource and will require some initialization 
      activity.
      
      The value providingService indicates that this component, as a 
      backup resource, is currently backing up another resource."
   DEFVAL     { notSet }
::= { mscLpDS3ImaStateEntry 8 }

mscLpDS3ImaUnknownStatus OBJECT-TYPE
   SYNTAX     INTEGER  {
                 false(0),
                 true(1) }
   ACCESS     read-only
   STATUS     mandatory
   DESCRIPTION
     "This attribute indicates the OSI Unknown status of the component.
      
      The value false indicates that all of the other OSI State and Status 
      attribute values can be considered accurate.
      
      The value true indicates that the actual state of the component is not 
      known for sure."
   DEFVAL     { false }
::= { mscLpDS3ImaStateEntry 9 }


-- 
-- The Test component is configured to control a hardware facility test 
-- on a physical (V35, X21, DS1, E1, DS3, E3 etc.) or a logical port.

mscLpDS3ImaTest OBJECT IDENTIFIER ::= { mscLpDS3Ima 2 }



mscLpDS3ImaTestRowStatusTable OBJECT-TYPE
   SYNTAX     SEQUENCE OF MscLpDS3ImaTestRowStatusEntry
   ACCESS     not-accessible
   STATUS     mandatory
   DESCRIPTION
     "This entry controls the addition and deletion of 
      mscLpDS3ImaTest components."
::= { mscLpDS3ImaTest 1 }

mscLpDS3ImaTestRowStatusEntry OBJECT-TYPE
   SYNTAX     MscLpDS3ImaTestRowStatusEntry
   ACCESS     not-accessible
   STATUS     mandatory
   DESCRIPTION
     "A single entry in the table represents a single 
      mscLpDS3ImaTest component."
   INDEX {
      mscLpIndex,
      mscLpDS3Index,
      mscLpDS3ImaIndex,
      mscLpDS3ImaTestIndex }
::= { mscLpDS3ImaTestRowStatusTable 1 }

MscLpDS3ImaTestRowStatusEntry ::= SEQUENCE {
   mscLpDS3ImaTestRowStatus
      RowStatus,
   mscLpDS3ImaTestComponentName
      DisplayString,
   mscLpDS3ImaTestStorageType
      StorageType,
   mscLpDS3ImaTestIndex
      NonReplicated }

mscLpDS3ImaTestRowStatus OBJECT-TYPE
   SYNTAX     RowStatus 
   ACCESS     read-only
   STATUS     mandatory
   DESCRIPTION
     "This variable is used as the basis for SNMP naming of
      mscLpDS3ImaTest components.
      These components cannot be added nor deleted."
::= { mscLpDS3ImaTestRowStatusEntry 1 }

mscLpDS3ImaTestComponentName OBJECT-TYPE
   SYNTAX     DisplayString 
   ACCESS     read-only
   STATUS     mandatory
   DESCRIPTION
     "This variable provides the component's string name for
      use with the ASCII Console Interface"
::= { mscLpDS3ImaTestRowStatusEntry 2 }

mscLpDS3ImaTestStorageType OBJECT-TYPE
   SYNTAX     StorageType 
   ACCESS     read-only
   STATUS     mandatory
   DESCRIPTION
     "This variable represents the storage type value for the
      mscLpDS3ImaTest tables."
::= { mscLpDS3ImaTestRowStatusEntry 4 }

mscLpDS3ImaTestIndex OBJECT-TYPE
   SYNTAX     NonReplicated 
   ACCESS     not-accessible
   STATUS     mandatory
   DESCRIPTION
     "This variable represents the index for the mscLpDS3ImaTest tables."
::= { mscLpDS3ImaTestRowStatusEntry 10 }

mscLpDS3ImaTestStateTable OBJECT-TYPE
   SYNTAX     SEQUENCE OF MscLpDS3ImaTestStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscLpDS3ImaTest 10 }

mscLpDS3ImaTestStateEntry OBJECT-TYPE
   SYNTAX     MscLpDS3ImaTestStateEntry
   ACCESS     not-accessible
   STATUS     mandatory
   DESCRIPTION
     "An entry in the mscLpDS3ImaTestStateTable."
   INDEX {
      mscLpIndex,
      mscLpDS3Index,
      mscLpDS3ImaIndex,
      mscLpDS3ImaTestIndex }
::= { mscLpDS3ImaTestStateTable 1 }

MscLpDS3ImaTestStateEntry ::= SEQUENCE {
   mscLpDS3ImaTestAdminState
      INTEGER,
   mscLpDS3ImaTestOperationalState
      INTEGER,
   mscLpDS3ImaTestUsageState
      INTEGER }

mscLpDS3ImaTestAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscLpDS3ImaTestStateEntry 1 }

mscLpDS3ImaTestOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscLpDS3ImaTestStateEntry 2 }

mscLpDS3ImaTestUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscLpDS3ImaTestStateEntry 3 }

mscLpDS3ImaTestSetupTable OBJECT-TYPE
   SYNTAX     SEQUENCE OF MscLpDS3ImaTestSetupEntry
   ACCESS     not-accessible
   STATUS     mandatory
   DESCRIPTION
     "This group contains all of the operational data for a Test 
      component."
::= { mscLpDS3ImaTest 11 }

mscLpDS3ImaTestSetupEntry OBJECT-TYPE
   SYNTAX     MscLpDS3ImaTestSetupEntry
   ACCESS     not-accessible
   STATUS     mandatory
   DESCRIPTION
     "An entry in the mscLpDS3ImaTestSetupTable."
   INDEX {
      mscLpIndex,
      mscLpDS3Index,
      mscLpDS3ImaIndex,
      mscLpDS3ImaTestIndex }
::= { mscLpDS3ImaTestSetupTable 1 }

MscLpDS3ImaTestSetupEntry ::= SEQUENCE {
   mscLpDS3ImaTestPurpose
      AsciiString,
   mscLpDS3ImaTestType
      INTEGER,
   mscLpDS3ImaTestFrmSize
      Unsigned32,
   mscLpDS3ImaTestFrmPatternType
      INTEGER,
   mscLpDS3ImaTestCustomizedPattern
      Hex,
   mscLpDS3ImaTestDataStartDelay
      Unsigned32,
   mscLpDS3ImaTestDisplayInterval
      Unsigned32,
   mscLpDS3ImaTestDuration
      Unsigned32 }

mscLpDS3ImaTestPurpose OBJECT-TYPE
   SYNTAX     AsciiString (SIZE (0..40))
   ACCESS     read-write
   STATUS     mandatory
   DESCRIPTION
     "This attribute records the purpose of the test so that the test results 
      can be associated and properly analyzed."
::= { mscLpDS3ImaTestSetupEntry 1 }

mscLpDS3ImaTestType OBJECT-TYPE
   SYNTAX     INTEGER  {
                 card(0),
                 manual(1),
                 localLoop(2),
                 remoteLoop(3),
                 externalLoop(4),
                 payloadLoop(5),
                 remoteLoopThisTrib(6),
                 v54RemoteLoop(7),
                 pn127RemoteLoop(8) }
   ACCESS     read-write
   STATUS     mandatory
   DESCRIPTION
     "This attribute is the type of test to be run. The available test types 
      include the following:
      card test sets up an internal loop on the board and runs a bit error 
      rate test.
      manual test assumes the line is looped back externally and a bit 
      error rate test is performed.
      localLoop test loops back the local modem and performs a bit error 
      rate test.
      remoteLoop test loops back the remote modem (or CSU) and 
      performs a bit error rate test.
      externalLoop test loops back the line to the far end.
      payloadLoop test only loops back the payload data received from 
      the incoming line.
      remoteLoopThisTrib loops this particular tributary back at the far 
      end, using services provided by the parent.
      v54RemoteLoop initiates a V.54 Remote Loopback test.
      pn127RemoteLoop initiates a PN127 Remote Loopback test.
      Note that not all test types are not supported by all function 
      processors."
   DEFVAL     { card }
::= { mscLpDS3ImaTestSetupEntry 2 }

mscLpDS3ImaTestFrmSize OBJECT-TYPE
   SYNTAX     Unsigned32 (4..4096)
   ACCESS     read-write
   STATUS     mandatory
   DESCRIPTION
     "This attribute defines the size of the test data frames in number of 
      bytes."
   DEFVAL     { 1024 }
::= { mscLpDS3ImaTestSetupEntry 3 }

mscLpDS3ImaTestFrmPatternType OBJECT-TYPE
   SYNTAX     INTEGER  {
                 ccitt32kBitPattern(0),
                 ccitt8MBitPattern(1),
                 customizedPattern(2) }
   ACCESS     read-write
   STATUS     mandatory
   DESCRIPTION
     "This attribute defines the type of data pattern generation to use. The 
      following lists the available pattern types:
      ccitt32kBitPattern is a pseudo-random sequence of 32 kbit.
      ccitt8MBitPattern is a pseudo-random sequence of 8Mbit.
      customizedPattern is the pattern defined in the customizedPattern 
      attribute."
   DEFVAL     { ccitt32kBitPattern }
::= { mscLpDS3ImaTestSetupEntry 4 }

mscLpDS3ImaTestCustomizedPattern OBJECT-TYPE
   SYNTAX     Hex (0..4294967295)
   ACCESS     read-write
   STATUS     mandatory
   DESCRIPTION
     "This attribute allows a customized 32 bit pattern to be defined for 
      use in the test data frames. This attribute is used when the attribute 
      frmPatternType is set to CustomizedPattern. Note that a 55 hex 
      pattern is an alternating 1 and 0 pattern."
   DEFVAL     { 1431655765 }
::= { mscLpDS3ImaTestSetupEntry 5 }

mscLpDS3ImaTestDataStartDelay OBJECT-TYPE
   SYNTAX     Unsigned32 (0..1814400)
   ACCESS     read-write
   STATUS     mandatory
   DESCRIPTION
     "This attribute specifies the time delay (in seconds) between when 
      the test expects the loop to have been set up, to when the test data 
      actually starts to be transmitted. This attribute is to accommodate 
      some non-standard equipment that requires extra time for setting up 
      a requested loop.
      This attribute is ignored when the test type is set to externalLoop."
   DEFVAL     { 0 }
::= { mscLpDS3ImaTestSetupEntry 6 }

mscLpDS3ImaTestDisplayInterval OBJECT-TYPE
   SYNTAX     Unsigned32 (0..30240)
   ACCESS     read-write
   STATUS     mandatory
   DESCRIPTION
     "This attribute defines the interval (in minutes) between which 
      interim test results are to be displayed. Results are displayed at the 
      operator console at which the test was started. When the test type is 
      set to externalLoop, this attribute is ignored. There will be no 
      display of results if displayInterval is set to 0. This attribute can be 
      changed anytime."
   DEFVAL     { 5 }
::= { mscLpDS3ImaTestSetupEntry 7 }

mscLpDS3ImaTestDuration OBJECT-TYPE
   SYNTAX     Unsigned32 (1..30240)
   ACCESS     read-write
   STATUS     mandatory
   DESCRIPTION
     "This attribute is the duration (in minutes) that test data will be 
      transmitted. In the case of an externalLoop, this is the time that the 
      loop is in effect. Note that dataStartDelay does not apply to the 
      externalLoop."
   DEFVAL     { 1 }
::= { mscLpDS3ImaTestSetupEntry 8 }

mscLpDS3ImaTestResultsTable OBJECT-TYPE
   SYNTAX     SEQUENCE OF MscLpDS3ImaTestResultsEntry
   ACCESS     not-accessible
   STATUS     mandatory
   DESCRIPTION
     "This group contains all the statistics related attributes of the Test 
      component."
::= { mscLpDS3ImaTest 12 }

mscLpDS3ImaTestResultsEntry OBJECT-TYPE
   SYNTAX     MscLpDS3ImaTestResultsEntry
   ACCESS     not-accessible
   STATUS     mandatory
   DESCRIPTION
     "An entry in the mscLpDS3ImaTestResultsTable."
   INDEX {
      mscLpIndex,
      mscLpDS3Index,
      mscLpDS3ImaIndex,
      mscLpDS3ImaTestIndex }
::= { mscLpDS3ImaTestResultsTable 1 }

MscLpDS3ImaTestResultsEntry ::= SEQUENCE {
   mscLpDS3ImaTestElapsedTime
      Counter32,
   mscLpDS3ImaTestTimeRemaining
      Unsigned32,
   mscLpDS3ImaTestCauseOfTermination
      INTEGER,
   mscLpDS3ImaTestBitsTx
      PassportCounter64,
   mscLpDS3ImaTestBytesTx
      PassportCounter64,
   mscLpDS3ImaTestFrmTx
      PassportCounter64,
   mscLpDS3ImaTestBitsRx
      PassportCounter64,
   mscLpDS3ImaTestBytesRx
      PassportCounter64,
   mscLpDS3ImaTestFrmRx
      PassportCounter64,
   mscLpDS3ImaTestErroredFrmRx
      PassportCounter64,
   mscLpDS3ImaTestBitErrorRate
      AsciiString }

mscLpDS3ImaTestElapsedTime OBJECT-TYPE
   SYNTAX     Counter32 
   ACCESS     read-only
   STATUS     mandatory
   DESCRIPTION
     "This attribute is the number of minutes elapsed since the test started 
      for an externalLoop test. For a data test, this is the time since test 
      data was first transmitted."
::= { mscLpDS3ImaTestResultsEntry 1 }

mscLpDS3ImaTestTimeRemaining OBJECT-TYPE
   SYNTAX     Unsigned32 (0..4294967295)
   ACCESS     read-only
   STATUS     mandatory
   DESCRIPTION
     "This attribute is the number of minutes remaining before the test is 
      to be stopped according to the duration attribute."
   DEFVAL     { 0 }
::= { mscLpDS3ImaTestResultsEntry 2 }

mscLpDS3ImaTestCauseOfTermination OBJECT-TYPE
   SYNTAX     INTEGER  {
                 testTimeExpired(0),
                 stoppedByOperator(1),
                 unknown(2),
                 neverStarted(3),
                 testRunning(4),
                 hardwareReconfigured(5),
                 loopCodeSyncFailed(6),
                 patternSyncFailed(7),
                 patternSyncLost(8) }
   ACCESS     read-only
   STATUS     mandatory
   DESCRIPTION
     "This attribute indicates either the status of the test or the cause of 
      the test's termination:
      
      neverStarted indicates that the test has not yet been started.
      
      testRunning indicates that the test has been started.
      
      stoppedByOperator indicates that the operator issued a stop 
      command on a test that was running.
      
      testTimeExpired indicates that the test ran for the time specified by 
      the test's duration.
      
      loopCodeSyncFailed indicates that the local end failed to 
      synchronize to the loopCode pattern. The local end transmits the 
      loopCode pattern to cause the remote end to apply a loopback, after 
      which the local end should receive the loopCode pattern. The exact 
      pattern used to request loopCode depends on the test type. This 
      failure indicates a high rate of transmission errors, or that the 
      remote end has failed to apply the loopback.
      
      patternSyncFailed indicates that the local end failed to synchronize 
      to the frmPatternType test pattern, that should have been looped 
      back at the remote end. This failure indicates a high rate of 
      transmission errors or the absence of a loopback.
      
      patternSyncLost indicates that the local end gained and then lost 
      synchronization to the returned frmPatternType test pattern. This 
      failure indicates a sudden increase in transmission errors, frame 
      slippage, or the removal of an existing loopback.
      
      unknown is set when a reason to terminate other than those listed 
      here is encountered.
      
      Note: Only MSA cards support recognition of the failures 
      loopCodeSyncFailed, patternSyncFailed and patternSyncLost. 
      Other cards will not terminate the test under the conditions 
      described by these values."
   DEFVAL     { neverStarted }
::= { mscLpDS3ImaTestResultsEntry 3 }

mscLpDS3ImaTestBitsTx OBJECT-TYPE
   SYNTAX     PassportCounter64 
   ACCESS     read-only
   STATUS     mandatory
   DESCRIPTION
     "This attribute is the total number of bits sent during the test period. 
      As long as the line speed of the hardware interface is less than 
      70 Mbit/s, this counter is not expected to reach the maximum value."
::= { mscLpDS3ImaTestResultsEntry 4 }

mscLpDS3ImaTestBytesTx OBJECT-TYPE
   SYNTAX     PassportCounter64 
   ACCESS     read-only
   STATUS     mandatory
   DESCRIPTION
     "This attribute is the total number of bytes sent during the test 
      period. This counter is not expected to reach its maximum value."
::= { mscLpDS3ImaTestResultsEntry 5 }

mscLpDS3ImaTestFrmTx OBJECT-TYPE
   SYNTAX     PassportCounter64 
   ACCESS     read-only
   STATUS     mandatory
   DESCRIPTION
     "This attribute is the total number of frames sent during the test 
      period. This counter is not expected to reach its maximum value."
::= { mscLpDS3ImaTestResultsEntry 6 }

mscLpDS3ImaTestBitsRx OBJECT-TYPE
   SYNTAX     PassportCounter64 
   ACCESS     read-only
   STATUS     mandatory
   DESCRIPTION
     "This attribute is the total number of bits received during the test 
      period. This counter is not expected to reach its maximum value. 
      The counter will wrap around to 0 if it does reach the maximum 
      value."
::= { mscLpDS3ImaTestResultsEntry 7 }

mscLpDS3ImaTestBytesRx OBJECT-TYPE
   SYNTAX     PassportCounter64 
   ACCESS     read-only
   STATUS     mandatory
   DESCRIPTION
     "This attribute is the total number of bytes received during the test 
      period. This counter is not expected to reach its maximum value. 
      The counter will wrap around to 0 if it does reach its maximum 
      value."
::= { mscLpDS3ImaTestResultsEntry 8 }

mscLpDS3ImaTestFrmRx OBJECT-TYPE
   SYNTAX     PassportCounter64 
   ACCESS     read-only
   STATUS     mandatory
   DESCRIPTION
     "This attribute is the total number of frames received during the test 
      period. This counter is not expected to reach its maximum value. 
      The counter will wrap around to 0 if it does reach its maximum 
      value."
::= { mscLpDS3ImaTestResultsEntry 9 }

mscLpDS3ImaTestErroredFrmRx OBJECT-TYPE
   SYNTAX     PassportCounter64 
   ACCESS     read-only
   STATUS     mandatory
   DESCRIPTION
     "This attribute is not displayed for ATM cards because the physical 
      layer drops all errored frames at the controller interface. 
      
      For all other card types, this attribute is the total number of errored 
      frames received during the test period. This counter is not expected 
      to reach its maximum value. The counter will wrap around to 0 if it 
      does reach its maximum value."
::= { mscLpDS3ImaTestResultsEntry 10 }

mscLpDS3ImaTestBitErrorRate OBJECT-TYPE
   SYNTAX     AsciiString (SIZE (5))
   ACCESS     read-only
   STATUS     mandatory
   DESCRIPTION
     "This attribute is not displayed for ATM cards because the physical 
      layer drops all errored frames at the controller interface. 
      
      For all other card types, this attribute is the calculated bit error rate 
      on the link. Test data are generated and sent in frames of a preset 
      size (frameSize). The Test component will try to estimate the 
      number of bit errors in any errored frame which is identifiable. The 
      statistics will be updated accordingly. A lost frame (may be due to 
      an error on the flag sequence) will be discarded for the bit error rate 
      calculation. The result is presented in the form of xEsyy, where x is 
      the mantissa, syy is the exponent, for example 0E+00, 2E-09.
      Note that the bitErrorRate is an estimate only. For more reliable test 
      results, the test should be done over a long period. Multiple tests 
      would also improve the confidence level of the test results."
::= { mscLpDS3ImaTestResultsEntry 11 }


-- Lp/n Ima/n Link/n	
-- Lp/n Ds3/n Ima/n Link/n
-- 
-- This component is used to define a DS1/E1 link belonging to an 
-- IMA group. The instance number of the Link subcomponent 
-- corresponds to the link identifier (LID) used by the link in IMA 
-- Control Protocol (ICP) cells. To use Ima on an 8pDS1E1 function 
-- processor, add Lp/n Ima/n Link/n. To use Ima on a 4pDS3ChAtm 
-- function processor, add Lp/n Ds3/n Ima/n Link/n.

mscLpDS3ImaLk OBJECT IDENTIFIER ::= { mscLpDS3Ima 3 }



mscLpDS3ImaLkRowStatusTable OBJECT-TYPE
   SYNTAX     SEQUENCE OF MscLpDS3ImaLkRowStatusEntry
   ACCESS     not-accessible
   STATUS     mandatory
   DESCRIPTION
     "This entry controls the addition and deletion of 
      mscLpDS3ImaLk components."
::= { mscLpDS3ImaLk 1 }

mscLpDS3ImaLkRowStatusEntry OBJECT-TYPE
   SYNTAX     MscLpDS3ImaLkRowStatusEntry
   ACCESS     not-accessible
   STATUS     mandatory
   DESCRIPTION
     "A single entry in the table represents a single 
      mscLpDS3ImaLk component."
   INDEX {
      mscLpIndex,
      mscLpDS3Index,
      mscLpDS3ImaIndex,
      mscLpDS3ImaLkIndex }
::= { mscLpDS3ImaLkRowStatusTable 1 }

MscLpDS3ImaLkRowStatusEntry ::= SEQUENCE {
   mscLpDS3ImaLkRowStatus
      RowStatus,
   mscLpDS3ImaLkComponentName
      DisplayString,
   mscLpDS3ImaLkStorageType
      StorageType,
   mscLpDS3ImaLkIndex
      Integer32 }

mscLpDS3ImaLkRowStatus OBJECT-TYPE
   SYNTAX     RowStatus 
   ACCESS     read-write
   STATUS     mandatory
   DESCRIPTION
     "This variable is used as the basis for SNMP naming of
      mscLpDS3ImaLk components.
      These components can be added and deleted."
::= { mscLpDS3ImaLkRowStatusEntry 1 }

mscLpDS3ImaLkComponentName OBJECT-TYPE
   SYNTAX     DisplayString 
   ACCESS     read-only
   STATUS     mandatory
   DESCRIPTION
     "This variable provides the component's string name for
      use with the ASCII Console Interface"
::= { mscLpDS3ImaLkRowStatusEntry 2 }

mscLpDS3ImaLkStorageType OBJECT-TYPE
   SYNTAX     StorageType 
   ACCESS     read-only
   STATUS     mandatory
   DESCRIPTION
     "This variable represents the storage type value for the
      mscLpDS3ImaLk tables."
::= { mscLpDS3ImaLkRowStatusEntry 4 }

mscLpDS3ImaLkIndex OBJECT-TYPE
   SYNTAX     Integer32 (0..31)
   ACCESS     not-accessible
   STATUS     mandatory
   DESCRIPTION
     "This variable represents the index for the mscLpDS3ImaLk tables."
::= { mscLpDS3ImaLkRowStatusEntry 10 }

mscLpDS3ImaLkProvTable OBJECT-TYPE
   SYNTAX     SEQUENCE OF MscLpDS3ImaLkProvEntry
   ACCESS     not-accessible
   STATUS     mandatory
   DESCRIPTION
     "This group contains the provisionable attributes for the Link 
      subcomponent."
::= { mscLpDS3ImaLk 10 }

mscLpDS3ImaLkProvEntry OBJECT-TYPE
   SYNTAX     MscLpDS3ImaLkProvEntry
   ACCESS     not-accessible
   STATUS     mandatory
   DESCRIPTION
     "An entry in the mscLpDS3ImaLkProvTable."
   INDEX {
      mscLpIndex,
      mscLpDS3Index,
      mscLpDS3ImaIndex,
      mscLpDS3ImaLkIndex }
::= { mscLpDS3ImaLkProvTable 1 }

MscLpDS3ImaLkProvEntry ::= SEQUENCE {
   mscLpDS3ImaLkInterfaceName
      Link }

mscLpDS3ImaLkInterfaceName OBJECT-TYPE
   SYNTAX     Link 
   ACCESS     read-write
   STATUS     mandatory
   DESCRIPTION
     "This attribute associates the Link subcomponent with a specific 
      interface on a function processor, for example Lp/5 E1/3 Chan/0.
      If IMA groups and independent links coexist on a card running 
      IMA and per-VC queueing is enabled, plan the selection of DS1 or 
      E1 ports to be used by the IMA group carefully. For a 
      4pDS3ChAtm function processor there is no per-VC queueing."
::= { mscLpDS3ImaLkProvEntry 1 }

mscLpDS3ImaLkOperTable OBJECT-TYPE
   SYNTAX     SEQUENCE OF MscLpDS3ImaLkOperEntry
   ACCESS     not-accessible
   STATUS     mandatory
   DESCRIPTION
     "This group contains the operational attributes for the Link 
      subcomponent."
::= { mscLpDS3ImaLk 11 }

mscLpDS3ImaLkOperEntry OBJECT-TYPE
   SYNTAX     MscLpDS3ImaLkOperEntry
   ACCESS     not-accessible
   STATUS     mandatory
   DESCRIPTION
     "An entry in the mscLpDS3ImaLkOperTable."
   INDEX {
      mscLpIndex,
      mscLpDS3Index,
      mscLpDS3ImaIndex,
      mscLpDS3ImaLkIndex }
::= { mscLpDS3ImaLkOperTable 1 }

MscLpDS3ImaLkOperEntry ::= SEQUENCE {
   mscLpDS3ImaLkFailureCause
      INTEGER,
   mscLpDS3ImaLkRemoteDefect
      INTEGER,
   mscLpDS3ImaLkRemoteLid
      Unsigned32,
   mscLpDS3ImaLkRelativeDelay
      Unsigned32,
   mscLpDS3ImaLkLastOifCause
      INTEGER }

mscLpDS3ImaLkFailureCause OBJECT-TYPE
   SYNTAX     INTEGER  {
                 noFailure(0),
                 interfaceDown(1),
                 lif(2),
                 lods(3),
                 protocolError(4),
                 remoteFailure(5),
                 misconnected(6),
                 unsupportedFrameLength(7),
                 unsupportedSymmetry(8),
                 noIcp(9) }
   ACCESS     read-only
   STATUS     mandatory
   DESCRIPTION
     "This attribute indicates the failure cause on this link. Possible values 
      are:
      noFailure: there is no failure on this link.
      interfaceDown: the physical port used by the link is down.
      lif: the link is in loss of IMA frame (LIF) state.
      lods: the link is in loss of delay synchronization (LODS) state; that 
      is, it has exhibited a differential delay which is greater than the 
      maximum differential delay tolerated by the IMA group. It must be 
      noted that hysteresis is used for the LODS condition.
      protocolError: the link is down because of a time-out or because 
      bad values are being received in IMA Control Protocol (ICP) cells.
      remoteFailure: the far end link is down.
      misconnected: the link is down because the IMA group has 
      declared, after using its transmit test pattern procedure, that this link 
      is not properly connected. This value can occur only if the protocol 
      for the IMA group is atmForum10.
      unsupportedFrameLength: the link is down because it is receiving 
      from the far end a frame length which is not supported by the local 
      IMA group. This value can occur only if the protocol for the IMA 
      group is atmForum10.
      unsupportedSymmetry: the link is down because it is receiving 
      from the far end a group symmetry which is not supported by the 
      local IMA group. This value can occur only if the protocol for the 
      IMA group is atmForum10.
      noIcp: the link is down because it is not receiving IMA Control 
      Protocol (ICP) cells. This value can occur only if the protocol for 
      the IMA group is atmForum10."
::= { mscLpDS3ImaLkOperEntry 1 }

mscLpDS3ImaLkRemoteDefect OBJECT-TYPE
   SYNTAX     INTEGER  {
                 noDefect(0),
                 physicalLayerDefect(1),
                 lif(2),
                 lods(3),
                 interfaceDown(4) }
   ACCESS     read-only
   STATUS     mandatory
   DESCRIPTION
     "This attribute indicates the IMA remote defect indicator (RDI) 
      currently being received on this link. Possible values are:
      noDefect: no defect.
      physicalLayerDefect: the interface used by the remote link has a 
      physical layer defect. This value can occur only if the protocol for 
      the IMA group is atmForum10.
      interfaceDown: the physical interface used by the remote link is 
      down.This value can occur only if the protocol for the IMA group is 
      proprietary.
      lif: the remote link has a loss of IMA frame (LIF) defect.
      lods: the remote link has a loss of delay synchronization (LODS) 
      defect; that is, it has exhibited a differential delay which is greater 
      than the maximum differential delay tolerated by the IMA group."
::= { mscLpDS3ImaLkOperEntry 2 }

mscLpDS3ImaLkRemoteLid OBJECT-TYPE
   SYNTAX     Unsigned32 (0..31)
   ACCESS     read-only
   STATUS     mandatory
   DESCRIPTION
     "This attribute indicates the link identifier (LID) used by the remote 
      IMA group on the physical link. A value of 0 will be displayed if 
      the link is not receiving IMA Control Protocol (ICP) cells or if the 
      physical layer is down."
::= { mscLpDS3ImaLkOperEntry 3 }

mscLpDS3ImaLkRelativeDelay OBJECT-TYPE
   SYNTAX     Unsigned32 (0..4294967295)
   ACCESS     read-only
   STATUS     mandatory
   DESCRIPTION
     "This attribute indicates the latest measured differential delay 
      (rounded up in milliseconds) between this link and the link, in the 
      same IMA group, having the least delay. A value of 4294967295 
      indicates that the relative delay could not be measured. This can be 
      due to physical layer problems or to no IMA Control Protocol (ICP) 
      cells being received on the link."
::= { mscLpDS3ImaLkOperEntry 4 }

mscLpDS3ImaLkLastOifCause OBJECT-TYPE
   SYNTAX     INTEGER  {
                 noOif(0),
                 badFrameLength(1),
                 badGid(2),
                 badLid(3),
                 badOffset(4),
                 badSequenceNumber(5),
                 stuffError(6),
                 missingIcp(7),
                 unexpectedIcp(8),
                 erroredIcp(9),
                 noCells(10),
                 idleCell(11) }
   ACCESS     read-only
   STATUS     mandatory
   DESCRIPTION
     "This attribute indicates the cause of the last out of IMA frame (OIF) 
      anomaly on the link. It will always have a value of noOif if the 
      protocol for the IMA group is proprietary. 
      Possible values are:
      noOif: no OIF was detected.
      badFrameLength: an IMA Control Protocol (ICP) cell with an 
      unexpected frame length was received.
      badGid: an ICP cell with an unexpected group identifier (GID) was 
      received.
      badLid: an ICP cell with an unexpected link identifier (LID) was 
      received.
      badOffset: an ICP cell with an unexpected cell offset was received.
      badSequenceNumber: an ICP cell with an unexpected frame 
      sequence number was received.
      stuffError: an illegal stuffing sequence was received.
      missingIcp: an expected ICP cell was not received.
      unexpectedIcp: an unexpected ICP cell was received.
      erroredIcp: two consecutive errored ICP cells were received.
      noCells: no cells are being received on the link.
      idleCell: an idle cell was received on the link."
::= { mscLpDS3ImaLkOperEntry 5 }

mscLpDS3ImaLkStatsTable OBJECT-TYPE
   SYNTAX     SEQUENCE OF MscLpDS3ImaLkStatsEntry
   ACCESS     not-accessible
   STATUS     mandatory
   DESCRIPTION
     "This group contains the statistics data for the Link subcomponent."
::= { mscLpDS3ImaLk 12 }

mscLpDS3ImaLkStatsEntry OBJECT-TYPE
   SYNTAX     MscLpDS3ImaLkStatsEntry
   ACCESS     not-accessible
   STATUS     mandatory
   DESCRIPTION
     "An entry in the mscLpDS3ImaLkStatsTable."
   INDEX {
      mscLpIndex,
      mscLpDS3Index,
      mscLpDS3ImaIndex,
      mscLpDS3ImaLkIndex }
::= { mscLpDS3ImaLkStatsTable 1 }

MscLpDS3ImaLkStatsEntry ::= SEQUENCE {
   mscLpDS3ImaLkRunningTime
      Unsigned32,
   mscLpDS3ImaLkUnavailSecs
      Unsigned32,
   mscLpDS3ImaLkFailures
      Unsigned32,
   mscLpDS3ImaLkUnusableSec
      Counter32,
   mscLpDS3ImaLkSevErroredSec
      Counter32,
   mscLpDS3ImaLkFarEndUnusableSec
      Counter32,
   mscLpDS3ImaLkFarEndSevErroredSec
      Counter32,
   mscLpDS3ImaLkFarEndUnavailSec
      Counter32,
   mscLpDS3ImaLkIcpViolations
      Counter32,
   mscLpDS3ImaLkTxStuffEvents
      Counter32,
   mscLpDS3ImaLkRxStuffEvents
      Counter32,
   mscLpDS3ImaLkIdleCellSec
      Counter32 }

mscLpDS3ImaLkRunningTime OBJECT-TYPE
   SYNTAX     Unsigned32 (0..4294967295)
   ACCESS     read-only
   STATUS     mandatory
   DESCRIPTION
     "This attribute counts the length of time (in seconds) for which the 
      Link component has been running."
::= { mscLpDS3ImaLkStatsEntry 1 }

mscLpDS3ImaLkUnavailSecs OBJECT-TYPE
   SYNTAX     Unsigned32 (0..4294967295)
   ACCESS     read-only
   STATUS     mandatory
   DESCRIPTION
     "For an IMA group whose protocol is atmForum10, this attribute 
      counts the number of unavailable seconds. Unavailability begins at 
      the start of 10 contiguous severely errored seconds (SES) and ends 
      at the start of 10 contiguous seconds with no SES.
      For an IMA group whose protocol is proprietary, this attribute 
      counts the number of one second intervals during which the Link 
      component has been out of service."
::= { mscLpDS3ImaLkStatsEntry 2 }

mscLpDS3ImaLkFailures OBJECT-TYPE
   SYNTAX     Unsigned32 (0..4294967295)
   ACCESS     read-only
   STATUS     mandatory
   DESCRIPTION
     "This attribute counts the number of failures, during link addition or 
      normal operation, that the link has experienced."
::= { mscLpDS3ImaLkStatsEntry 3 }

mscLpDS3ImaLkUnusableSec OBJECT-TYPE
   SYNTAX     Counter32 
   ACCESS     read-only
   STATUS     mandatory
   DESCRIPTION
     "This attribute counts the number of one second intervals during 
      which the near end has been in an unusable state.
      This attribute will always have a value of 0 if the protocol for the 
      IMA group is proprietary."
::= { mscLpDS3ImaLkStatsEntry 4 }

mscLpDS3ImaLkSevErroredSec OBJECT-TYPE
   SYNTAX     Counter32 
   ACCESS     read-only
   STATUS     mandatory
   DESCRIPTION
     "This attribute counts the number of one second intervals in which at 
      least 30 percent of the IMA Control Protocol (ICP) cells were 
      counted as ICP violations or at least one link defect (physical layer, 
      LIF and LODS defects) was detected. This attribute will not 
      increment during UAS (Unavailable Second) conditions.
      This attribute will always have a value of 0 if the protocol for the 
      IMA group is proprietary."
::= { mscLpDS3ImaLkStatsEntry 5 }

mscLpDS3ImaLkFarEndUnusableSec OBJECT-TYPE
   SYNTAX     Counter32 
   ACCESS     read-only
   STATUS     mandatory
   DESCRIPTION
     "This attribute counts the number of one second intervals during 
      which the 'Tx/Rx Unusable' condition has been received from the 
      far end.
      This attribute will always have a value of 0 if the protocol for the 
      IMA group is proprietary."
::= { mscLpDS3ImaLkStatsEntry 6 }

mscLpDS3ImaLkFarEndSevErroredSec OBJECT-TYPE
   SYNTAX     Counter32 
   ACCESS     read-only
   STATUS     mandatory
   DESCRIPTION
     "This attribute counts the number of one second intervals containing 
      one or more RDI defects. This attribute will not increment during 
      FEUAS (Far-End Unavailable Second) conditions.
      This attribute will always have a value of 0 if the protocol for the 
      IMA group is proprietary."
::= { mscLpDS3ImaLkStatsEntry 7 }

mscLpDS3ImaLkFarEndUnavailSec OBJECT-TYPE
   SYNTAX     Counter32 
   ACCESS     read-only
   STATUS     mandatory
   DESCRIPTION
     "This attribute counts the number of unavailable seconds at the far 
      end. Unavailability begins at the start of 10 contiguous severely 
      errored seconds (SES) at the far end and ends at the start of 10 
      contiguous seconds at the far end with no SES.
      This attribute will always have a value of 0 if the protocol for the 
      IMA group is proprietary."
::= { mscLpDS3ImaLkStatsEntry 8 }

mscLpDS3ImaLkIcpViolations OBJECT-TYPE
   SYNTAX     Counter32 
   ACCESS     read-only
   STATUS     mandatory
   DESCRIPTION
     "This attribute counts the number of errored, invalid or missing IMA 
      Control Protocol (ICP) cells during non-SES (Severely Errored 
      Second) and non-UAS (Unavailable Seconds) conditions.
      This attribute will always have a value of 0 if the protocol for the 
      IMA group is proprietary."
::= { mscLpDS3ImaLkStatsEntry 9 }

mscLpDS3ImaLkTxStuffEvents OBJECT-TYPE
   SYNTAX     Counter32 
   ACCESS     read-only
   STATUS     mandatory
   DESCRIPTION
     "This attribute counts the number of Stuff events transmitted during 
      non-SES (Severely Errored Second) and non-UAS (Unavailable 
      Seconds) conditions.
      This attribute will always have a value of 0 if the protocol for the 
      IMA group is proprietary."
::= { mscLpDS3ImaLkStatsEntry 10 }

mscLpDS3ImaLkRxStuffEvents OBJECT-TYPE
   SYNTAX     Counter32 
   ACCESS     read-only
   STATUS     mandatory
   DESCRIPTION
     "This attribute counts the number of Stuff events received during 
      non-SES (Severely Errored Second) and non-UAS (Unavailable 
      Seconds) conditions.
      This attribute will always have a value of 0 if the protocol for the 
      IMA group is proprietary."
::= { mscLpDS3ImaLkStatsEntry 11 }

mscLpDS3ImaLkIdleCellSec OBJECT-TYPE
   SYNTAX     Counter32 
   ACCESS     read-only
   STATUS     mandatory
   DESCRIPTION
     "This attributes counts the number of one second intervals during 
      which one or more idle cells was received. The reception of idle 
      cells is an abnormal condition which could be caused by the remote 
      IMA using the Common Transmit Clock mode with ports whose 
      clock sources are not synchronized.
      This attribute will always have a value of 0 if the protocol for the 
      IMA group is proprietary."
::= { mscLpDS3ImaLkStatsEntry 12 }

mscLpDS3ImaLkStateTable OBJECT-TYPE
   SYNTAX     SEQUENCE OF MscLpDS3ImaLkStateEntry
   ACCESS     not-accessible
   STATUS     mandatory
   DESCRIPTION
     "This group contains the three OSI State attributes and the six OSI 
      Status attributes. The descriptions generically indicate what each 
      attribute implies about the component. Note that not all the values 
      and state combinations described here are supported by every 
      component which uses this group. For component-specific 
      information and the valid state combinations, refer to NTP 241-
      7001-150, Passport Operations and Maintenance Guide."
::= { mscLpDS3ImaLk 13 }

mscLpDS3ImaLkStateEntry OBJECT-TYPE
   SYNTAX     MscLpDS3ImaLkStateEntry
   ACCESS     not-accessible
   STATUS     mandatory
   DESCRIPTION
     "An entry in the mscLpDS3ImaLkStateTable."
   INDEX {
      mscLpIndex,
      mscLpDS3Index,
      mscLpDS3ImaIndex,
      mscLpDS3ImaLkIndex }
::= { mscLpDS3ImaLkStateTable 1 }

MscLpDS3ImaLkStateEntry ::= SEQUENCE {
   mscLpDS3ImaLkAdminState
      INTEGER,
   mscLpDS3ImaLkOperationalState
      INTEGER,
   mscLpDS3ImaLkUsageState
      INTEGER,
   mscLpDS3ImaLkAvailabilityStatus
      OCTET STRING,
   mscLpDS3ImaLkProceduralStatus
      OCTET STRING,
   mscLpDS3ImaLkControlStatus
      OCTET STRING,
   mscLpDS3ImaLkAlarmStatus
      OCTET STRING,
   mscLpDS3ImaLkStandbyStatus
      INTEGER,
   mscLpDS3ImaLkUnknownStatus
      INTEGER }

mscLpDS3ImaLkAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component.
      
      The OSI Status attributes, if supported by the component, may 
      provide more details, qualifying the state of the component."
   DEFVAL     { unlocked }
::= { mscLpDS3ImaLkStateEntry 1 }

mscLpDS3ImaLkOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle.
      
      The OSI Status attributes, if supported by the component, may 
      provide more details, qualifying the state of the component."
   DEFVAL     { disabled }
::= { mscLpDS3ImaLkStateEntry 2 }

mscLpDS3ImaLkUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time.
      
      The OSI Status attributes, if supported by the component, may 
      provide more details, qualifying the state of the component."
   DEFVAL     { idle }
::= { mscLpDS3ImaLkStateEntry 3 }

mscLpDS3ImaLkAvailabilityStatus OBJECT-TYPE
   SYNTAX     OCTET STRING (SIZE (2))
   ACCESS     read-only
   STATUS     mandatory
   DESCRIPTION
     "If supported by the component, this attribute indicates the OSI 
      Availability status of the component. Note that, even though it is 
      defined as a multi-valued set, at most one value is shown to the user.
      
      When no values are in the set, this indicates that either the attribute 
      is not supported or that none of the status conditions described 
      below are present.
      
      The value inTest indicates that the resource is undergoing a test 
      procedure. If adminState is locked or shuttingDown, the normal 
      users are precluded from using the resource and controlStatus is 
      reservedForTest. Tests that do not exclude additional users can be 
      present in any operational or administrative state but the 
      reservedForTest condition should not be present.
      
      The value failed indicates that the component has an internal fault 
      that prevents it from operating. The operationalState is disabled.
      
      The value dependency indicates that the component cannot operate 
      because some other resource on which it depends is unavailable. 
      The operationalState is disabled.
      
      The value powerOff indicates the resource requires power to be 
      applied and it is not powered on. The operationalState is disabled.
      
      The value offLine indicates the resource requires a routine 
      operation (either manual, automatic, or both) to be performed to 
      place it on-line and make it available for use. The operationalState 
      is disabled.
      
      The value offDuty indicates the resource is inactive in accordance 
      with a predetermined time schedule. In the absence of other 
      disabling conditions, the operationalState is enabled or disabled.
      
      The value degraded indicates the service provided by the 
      component is degraded in some way, such as in speed or operating 
      capacity. However, the resource remains available for service. The 
      operationalState is enabled.
      
      The value notInstalled indicates the resource is not present. The 
      operationalState is disabled.
      
      The value logFull is not used.

      Description of bits:
      inTest(0)
      failed(1)
      powerOff(2)
      offLine(3)
      offDuty(4)
      dependency(5)
      degraded(6)
      notInstalled(7)
      logFull(8)"
::= { mscLpDS3ImaLkStateEntry 4 }

mscLpDS3ImaLkProceduralStatus OBJECT-TYPE
   SYNTAX     OCTET STRING (SIZE (1))
   ACCESS     read-only
   STATUS     mandatory
   DESCRIPTION
     "If supported by the component, this attribute indicates the OSI 
      Procedural status of the component. Note that, even though it is 
      defined as a multi-valued set, at most one value is shown to the user.
      
      When no values are in the set, this indicates that either the attribute 
      is not supported or that none of the status conditions described 
      below are present.
      
      The value initializationRequired indicates (for a resource which 
      doesn't initialize autonomously) that initialization is required before 
      it can perform its normal functions, and this procedure has not been 
      initiated. The operationalState is disabled.
      
      The value notInitialized indicates (for a resource which does 
      initialize autonomously) that initialization is required before it can 
      perform its normal functions, and this procedure has not been 
      initiated. The operationalState may be enabled or disabled.
      
      The value initializing indicates that initialization has been initiated 
      but is not yet complete. The operationalState may be enabled or 
      disabled.
      
      The value reporting indicates the resource has completed some 
      processing operation and is notifying the results. The 
      operationalState is enabled.
      
      The value terminating indicates the component is in a termination 
      phase. If the resource doesn't reinitialize autonomously, 
      operationalState is disabled; otherwise it is enabled or disabled.

      Description of bits:
      initializationRequired(0)
      notInitialized(1)
      initializing(2)
      reporting(3)
      terminating(4)"
::= { mscLpDS3ImaLkStateEntry 5 }

mscLpDS3ImaLkControlStatus OBJECT-TYPE
   SYNTAX     OCTET STRING (SIZE (1))
   ACCESS     read-only
   STATUS     mandatory
   DESCRIPTION
     "If supported by the component, this attribute indicates the OSI 
      Control status of the component. Note that, even though it is defined 
      as a multi-valued set, at most one value is shown to the user.
      
      When no values are in the set, this indicates that either the attribute 
      is not supported or that none of the status conditions described 
      below are present.
      
      The value subjectToTest indicates the resource is available but tests 
      may be conducted simultaneously at unpredictable times, which 
      may cause it to exhibit unusual characteristics.
      
      The value partOfServicesLocked indicates that part of the service is 
      restricted from users of a resource. The adminState is unlocked.
      
      The value reservedForTest indicates that the component is 
      administratively unavailable because it is undergoing a test 
      procedure. The adminState is locked.
      
      The value suspended indicates that the service has been 
      administratively suspended.

      Description of bits:
      subjectToTest(0)
      partOfServicesLocked(1)
      reservedForTest(2)
      suspended(3)"
::= { mscLpDS3ImaLkStateEntry 6 }

mscLpDS3ImaLkAlarmStatus OBJECT-TYPE
   SYNTAX     OCTET STRING (SIZE (1))
   ACCESS     read-only
   STATUS     mandatory
   DESCRIPTION
     "If supported by the component, this attribute indicates the OSI 
      Alarm status of the component. Note that, even though it is defined 
      as a multi-valued set, at most one value is shown to the user.
      
      When no values are in the set, this indicates that either the attribute 
      is not supported or that none of the status conditions described 
      below are present.
      
      The value underRepair indicates the component is currently being 
      repaired. The operationalState is enabled or disabled.
      
      The value critical indicates one or more critical alarms are 
      outstanding against the component. Other, less severe, alarms may 
      also be outstanding. The operationalState is enabled or disabled.
      
      The value major indicates one or more major alarms are 
      outstanding against the component. Other, less severe, alarms may 
      also be outstanding. The operationalState is enabled or disabled.
      
      The value minor indicates one or more minor alarms are 
      outstanding against the component. Other, less severe, alarms may 
      also be outstanding. The operationalState is enabled or disabled.
      
      The value alarmOutstanding generically indicates that an alarm of 
      some severity is outstanding against the component.

      Description of bits:
      underRepair(0)
      critical(1)
      major(2)
      minor(3)
      alarmOutstanding(4)"
::= { mscLpDS3ImaLkStateEntry 7 }

mscLpDS3ImaLkStandbyStatus OBJECT-TYPE
   SYNTAX     INTEGER  {
                 hotStandby(0),
                 coldStandby(1),
                 providingService(2),
                 notSet(15) }
   ACCESS     read-only
   STATUS     mandatory
   DESCRIPTION
     "If supported by the component, this attribute indicates the OSI 
      Standby status of the component.
      
      The value notSet indicates that either the attribute is not supported 
      or that none of the status conditions described below are present. 
      Note that this is a non-standard value, used because the original 
      specification indicated this attribute was set-valued and thus, did not 
      provide a value to indicate that none of the other three are 
      applicable.
      
      The value hotStandby indicates that the resource is not providing 
      service but will be immediately able to take over the role of the 
      resource to be backed up, without initialization activity, and 
      containing the same information as the resource to be backed up.
      
      The value coldStandby indicates the resource is a backup for 
      another resource but will not be immediately able to take over the 
      role of the backed up resource and will require some initialization 
      activity.
      
      The value providingService indicates that this component, as a 
      backup resource, is currently backing up another resource."
   DEFVAL     { notSet }
::= { mscLpDS3ImaLkStateEntry 8 }

mscLpDS3ImaLkUnknownStatus OBJECT-TYPE
   SYNTAX     INTEGER  {
                 false(0),
                 true(1) }
   ACCESS     read-only
   STATUS     mandatory
   DESCRIPTION
     "This attribute indicates the OSI Unknown status of the component.
      
      The value false indicates that all of the other OSI State and Status 
      attribute values can be considered accurate.
      
      The value true indicates that the actual state of the component is not 
      known for sure."
   DEFVAL     { false }
::= { mscLpDS3ImaLkStateEntry 9 }


-- Lp/n InverseMultiplexerAtm/n
-- Lp/n Ds3/n InverseMultiplexerAtm/n
-- 
-- This component is used to define an inverse multiplexing for ATM 
-- (IMA) group. IMA provides a data rate greater than DS1 E1 in 
-- increments of DS1 E1. To use IMA on an 8pDS1E1 function 
-- processor, add Lp/n InverseMultiplexerAtm/n. To use IMA on a 
-- 4pDS3ChAtm function processor, add Lp/n Ds3/n 
-- InverseMultiplexerAtm/n.
-- 
-- The instance range 0..29 applies to Multi-Service Access cards, and 
-- the instance range 0..7 applies to all other cards.
-- The instance number of an IMA group must not be the same as the 
-- instance number of a DS1/E1 "ATM UNI port" under the same Lp. 
-- An "ATM UNI port" is a DS1 or E1 component with a single Chan 
-- whose applicationFramer attribute is linked to an AtmIf component.
-- On a Multi-Service Access card, ports that are used as IMA links 
-- have two immiscible sub-ranges: 0..15 and 16..31. The instance 
-- number of an IMA group must be in the same sub-range as all of its 
-- ports.

mscLpIma OBJECT IDENTIFIER ::= { mscLp 22 }



mscLpImaRowStatusTable OBJECT-TYPE
   SYNTAX     SEQUENCE OF MscLpImaRowStatusEntry
   ACCESS     not-accessible
   STATUS     mandatory
   DESCRIPTION
     "This entry controls the addition and deletion of 
      mscLpIma components."
::= { mscLpIma 1 }

mscLpImaRowStatusEntry OBJECT-TYPE
   SYNTAX     MscLpImaRowStatusEntry
   ACCESS     not-accessible
   STATUS     mandatory
   DESCRIPTION
     "A single entry in the table represents a single 
      mscLpIma component."
   INDEX {
      mscLpIndex,
      mscLpImaIndex }
::= { mscLpImaRowStatusTable 1 }

MscLpImaRowStatusEntry ::= SEQUENCE {
   mscLpImaRowStatus
      RowStatus,
   mscLpImaComponentName
      DisplayString,
   mscLpImaStorageType
      StorageType,
   mscLpImaIndex
      Integer32 }

mscLpImaRowStatus OBJECT-TYPE
   SYNTAX     RowStatus 
   ACCESS     read-write
   STATUS     mandatory
   DESCRIPTION
     "This variable is used as the basis for SNMP naming of
      mscLpIma components.
      These components can be added and deleted."
::= { mscLpImaRowStatusEntry 1 }

mscLpImaComponentName OBJECT-TYPE
   SYNTAX     DisplayString 
   ACCESS     read-only
   STATUS     mandatory
   DESCRIPTION
     "This variable provides the component's string name for
      use with the ASCII Console Interface"
::= { mscLpImaRowStatusEntry 2 }

mscLpImaStorageType OBJECT-TYPE
   SYNTAX     StorageType 
   ACCESS     read-only
   STATUS     mandatory
   DESCRIPTION
     "This variable represents the storage type value for the
      mscLpIma tables."
::= { mscLpImaRowStatusEntry 4 }

mscLpImaIndex OBJECT-TYPE
   SYNTAX     Integer32 (0..29)
   ACCESS     not-accessible
   STATUS     mandatory
   DESCRIPTION
     "This variable represents the index for the mscLpIma tables."
::= { mscLpImaRowStatusEntry 10 }

mscLpImaProvTable OBJECT-TYPE
   SYNTAX     SEQUENCE OF MscLpImaProvEntry
   ACCESS     not-accessible
   STATUS     mandatory
   DESCRIPTION
     "This group contains the provisionable attributes for the Ima 
      component.
      The default values of linkSelectionCriterion and linkRetryTimeout 
      depend on card type."
::= { mscLpIma 10 }

mscLpImaProvEntry OBJECT-TYPE
   SYNTAX     MscLpImaProvEntry
   ACCESS     not-accessible
   STATUS     mandatory
   DESCRIPTION
     "An entry in the mscLpImaProvTable."
   INDEX {
      mscLpIndex,
      mscLpImaIndex }
::= { mscLpImaProvTable 1 }

MscLpImaProvEntry ::= SEQUENCE {
   mscLpImaLinkSelectionCriterion
      INTEGER,
   mscLpImaMaxDiffDelay
      Unsigned32,
   mscLpImaLinkRetryTimeout
      Unsigned32,
   mscLpImaApplicationFramerName
      Link,
   mscLpImaTransmitClockMode
      INTEGER,
   mscLpImaProtocol
      INTEGER }

mscLpImaLinkSelectionCriterion OBJECT-TYPE
   SYNTAX     INTEGER  {
                 leastDelay(0),
                 maxBandwidth(1) }
   ACCESS     read-write
   STATUS     mandatory
   DESCRIPTION
     "This attribute specifies the method to be used by the IMA group 
      when selecting links to be activated. This comes into effect only 
      when the configured links do not respect the maximum differential 
      delay (otherwise all links are accepted).
      
      If leastDelay is chosen, first the link having the smallest delay is 
      selected as the reference link. The IMA group includes all links 
      which respect the maximum differential delay relative to the 
      reference link.
      
      If maxBandwidth is chosen, the IMA group selects the maximum 
      possible number of links, with each selected link respecting the 
      maximum differential delay relative to every other selected link. 
      When more than one possibility exists, the combination which 
      offers the least delay isselected.
      
      The default value for Multi-Service Access cards is leastDelay, and 
      for all other cards is maxBandwidth. On Multi-Service Access 
      cards leastDelay is the only acceptable provisionable value."
::= { mscLpImaProvEntry 1 }

mscLpImaMaxDiffDelay OBJECT-TYPE
   SYNTAX     Unsigned32 (1..100)
   ACCESS     read-write
   STATUS     mandatory
   DESCRIPTION
     "This attribute specifies the maximum differential delay between 
      links acceptable in the IMA group. If a link violates that maximum 
      differential delay, it will not be active in the IMA group and an 
      alarm will be generated."
   DEFVAL     { 25 }
::= { mscLpImaProvEntry 2 }

mscLpImaLinkRetryTimeout OBJECT-TYPE
   SYNTAX     Unsigned32 (0..1000)
   ACCESS     read-write
   STATUS     mandatory
   DESCRIPTION
     "This attribute specifies the amount of time before reactivation of a 
      link is attempted after it recovers from a failure condition.
      
      The default value for Multi-Service Access cards is 1, and for all 
      other cards is 10. On Multi-Service Access cards 1 is the only 
      acceptable provisionable value."
::= { mscLpImaProvEntry 3 }

mscLpImaApplicationFramerName OBJECT-TYPE
   SYNTAX     Link 
   ACCESS     read-write
   STATUS     mandatory
   DESCRIPTION
     "This attribute defines the link to the AtmIf component using the Ima. 
      An example is AtmIf/31."
::= { mscLpImaProvEntry 4 }

mscLpImaTransmitClockMode OBJECT-TYPE
   SYNTAX     INTEGER  {
                 itc(0),
                 ctc(1) }
   ACCESS     read-write
   STATUS     mandatory
   DESCRIPTION
     "This attribute specifies the transmit clocking mode.
      If itc (Independent Transmit Clock) is chosen, the physical ports 
      used by the IMA group may have different clocking sources.
      If ctc (Common Transmit Clock) is chosen, it is recommended that 
      the physical ports used by the IMA group have the same clocking 
      source. However, if the physical ports have different clocking 
      sources, the operator should ensure that all the clocking sources 
      have the same rate."
   DEFVAL     { itc }
::= { mscLpImaProvEntry 5 }

mscLpImaProtocol OBJECT-TYPE
   SYNTAX     INTEGER  {
                 atmForum10(0),
                 proprietary(1) }
   ACCESS     read-write
   STATUS     mandatory
   DESCRIPTION
     "This attribute specifies what protocol the component should run.
      If atmForum10 is chosen, the ATM Forum's IMA protocol (version 
      1.0) will be used and signalled in outgoing IMA Control Protocol 
      (ICP) cells. This protocol is specified in version 1.1 of the ATM 
      Forum IMA specification. The IMA group will come up only if the 
      far end IMA also uses the ATM Forum's IMA protocol.
      If proprietary is chosen, Nortel's proprietary IMA protocol will be 
      used. The IMA group will come up only if the far end IMA also 
      uses Nortel's proprietary IMA protocol. This IMA group will not 
      inter-operate with IMA implementations from other vendors. 
      Feature ima must be provisioned on the LP for this protocol to be 
      used."
   DEFVAL     { atmForum10 }
::= { mscLpImaProvEntry 6 }

mscLpImaOperTable OBJECT-TYPE
   SYNTAX     SEQUENCE OF MscLpImaOperEntry
   ACCESS     not-accessible
   STATUS     mandatory
   DESCRIPTION
     "This group contains the operational attributes for the Ima 
      component."
::= { mscLpIma 11 }

mscLpImaOperEntry OBJECT-TYPE
   SYNTAX     MscLpImaOperEntry
   ACCESS     not-accessible
   STATUS     mandatory
   DESCRIPTION
     "An entry in the mscLpImaOperTable."
   INDEX {
      mscLpIndex,
      mscLpImaIndex }
::= { mscLpImaOperTable 1 }

MscLpImaOperEntry ::= SEQUENCE {
   mscLpImaFailureCause
      INTEGER,
   mscLpImaRemoteDefect
      INTEGER,
   mscLpImaRemoteLidsConfig
      OCTET STRING,
   mscLpImaRemoteLidsActive
      OCTET STRING,
   mscLpImaCellCapacity
      Unsigned32,
   mscLpImaRemoteGid
      Unsigned32,
   mscLpImaClockingModeMismatch
      INTEGER }

mscLpImaFailureCause OBJECT-TYPE
   SYNTAX     INTEGER  {
                 noFailure(0),
                 noGoodLinksInStartup(1),
                 badGidInStartup(2),
                 badLidInStartup(3),
                 unsupportedFrameLengthInStartup(4),
                 timeoutInStartup(5),
                 noGoodLinks(6),
                 remoteFailure(7),
                 unsupportedSymmetryInStartup(8) }
   ACCESS     read-only
   STATUS     mandatory
   DESCRIPTION
     "This attribute indicates the cause of the current local end failure 
      experienced by the IMA group. The failure may have occurred 
      during a start-up procedure or during normal operation. Possible 
      values are:
      noFailure: no local end failure.
      noGoodLinksInStartup: no good links were available during IMA 
      start-up.
      badGidInStartup: during start-up, different group identifiers (GIDs) 
      were received on the links.
      badLidInStartup: during start-up, duplicate link identifiers (LIDs) 
      were received on the links.
      unsupportedFrameLengthInStartup: during start-up, an 
      unsupported frame length was received.
      timeoutInStartup: a time-out has occurred during start-up.
      noGoodLinks: no good links are available in the IMA group.
      remoteFailure: the far end is down.
      unsupportedSymmetryInStartup: the symmetry proposed by the far 
      end is not supported on the near-end. This value will occur when 
      the IMA group is running the ATM Forum protocol and the far end 
      is proposing a group symmetry other than 'symmetric configuration 
      and operation'."
::= { mscLpImaOperEntry 1 }

mscLpImaRemoteDefect OBJECT-TYPE
   SYNTAX     INTEGER  {
                 noDefect(0),
                 noGoodLinksInStartup(1),
                 badGidInStartup(2),
                 badLidInStartup(3),
                 unsupportedFrameLengthInStartup(4),
                 timeoutInStartup(5),
                 noGoodLinks(6),
                 locked(7),
                 unsupportedSymmetryInStartup(8),
                 otherAbortStartup(9),
                 insufficientLinks(10),
                 blocked(11) }
   ACCESS     read-only
   STATUS     mandatory
   DESCRIPTION
     "This attribute indicates the cause of the current far end defect 
      experienced by the IMA group.
      For the ATM Forum IMA protocol, possible values are:
      noDefect: no defect.
      unsupportedFrameLengthInStartup: during the far end's start-up, 
      an unsupported frame length was received.
      unsupportedSymmetryInStartup: during the far end's start-up, an 
      unsupported symmetry configuration was received.
      otherAbortStartup: the far end has aborted its start-up for another 
      reason. This could be because different Gids were received on the 
      links or if duplicate link identifiers (LIDs) were received.
      insufficientLinks: the far end does not have sufficient links active. 
      This value will be displayed if the far end IMA group is locked.
      blocked: the far end IMA group is blocked.
      
      For the proprietary IMA protocol, possible values are:
      noDefect: no defect.
      noGoodLinksInStartup: no good links were available during the far 
      end's start-up.
      badGidInStartup: during the far end's start-up, different GIDs were 
      received on the links.
      badLidInStartup: during the far end's start-up, duplicate link 
      identifiers (LIDs) were received on the links.
      unsupportedFrameLengthInStartup: during the far end's start-up, 
      an unsupported frame length was received.
      timeoutInStartup: a time out has occurred during the far end's start-
      up.
      noGoodLinks: no good links are available in the far end IMA 
      group.
      locked: the far end IMA group is locked."
::= { mscLpImaOperEntry 2 }

mscLpImaRemoteLidsConfig OBJECT-TYPE
   SYNTAX     OCTET STRING (SIZE (4))
   ACCESS     read-only
   STATUS     mandatory
   DESCRIPTION
     "This attribute indicates all the links which have been configured in 
      the remote IMA group. For example, if links 1, 3 and 5 have been 
      configured in the remote IMA group, this attribute would contain 1 
      3 5.

      Description of bits:
      n0(0)
      n1(1)
      n2(2)
      n3(3)
      n4(4)
      n5(5)
      n6(6)
      n7(7)
      n8(8)
      n9(9)
      n10(10)
      n11(11)
      n12(12)
      n13(13)
      n14(14)
      n15(15)
      n16(16)
      n17(17)
      n18(18)
      n19(19)
      n20(20)
      n21(21)
      n22(22)
      n23(23)
      n24(24)
      n25(25)
      n26(26)
      n27(27)
      n28(28)
      n29(29)
      n30(30)
      n31(31)"
::= { mscLpImaOperEntry 3 }

mscLpImaRemoteLidsActive OBJECT-TYPE
   SYNTAX     OCTET STRING (SIZE (4))
   ACCESS     read-only
   STATUS     mandatory
   DESCRIPTION
     "This attribute indicates all the links which are active in the remote 
      IMA group. For example, if links 1 and 5 are active in the remote 
      IMA, this attribute would contain 1 5.

      Description of bits:
      n0(0)
      n1(1)
      n2(2)
      n3(3)
      n4(4)
      n5(5)
      n6(6)
      n7(7)
      n8(8)
      n9(9)
      n10(10)
      n11(11)
      n12(12)
      n13(13)
      n14(14)
      n15(15)
      n16(16)
      n17(17)
      n18(18)
      n19(19)
      n20(20)
      n21(21)
      n22(22)
      n23(23)
      n24(24)
      n25(25)
      n26(26)
      n27(27)
      n28(28)
      n29(29)
      n30(30)
      n31(31)"
::= { mscLpImaOperEntry 4 }

mscLpImaCellCapacity OBJECT-TYPE
   SYNTAX     Unsigned32 (0..4294967295)
   ACCESS     read-only
   STATUS     mandatory
   DESCRIPTION
     "This attribute indicates the total cell capacity (in cells per second) 
      which is provided to the ATM layer. This cell capacity takes into 
      account the physical and IMA level overheads."
::= { mscLpImaOperEntry 5 }

mscLpImaRemoteGid OBJECT-TYPE
   SYNTAX     Unsigned32 (0..255)
   ACCESS     read-only
   STATUS     mandatory
   DESCRIPTION
     "This attribute indicates the IMA group identifier (GID) used by the 
      remote IMA. A value of 0 will be displayed if the group is not 
      receiving IMA Control Protocol (ICP) cells.
      This attribute will always have a value of 0 if the protocol for the 
      IMA group is proprietary."
::= { mscLpImaOperEntry 6 }

mscLpImaClockingModeMismatch OBJECT-TYPE
   SYNTAX     INTEGER  {
                 no(0),
                 yes(1) }
   ACCESS     read-only
   STATUS     mandatory
   DESCRIPTION
     "This attribute indicates whether or not both ends of the IMA group 
      are using the same transmit clocking mode (itc/ctc). Its value will be 
      yes if both ends are not using the same transmit clocking mode. A 
      clocking mode mismatch does not prevent an IMA group from 
      coming up and can be corrected by using the same clocking mode at 
      both ends.
      This attribute will always have a value of no if the protocol for the 
      IMA group is proprietary."
::= { mscLpImaOperEntry 7 }

mscLpImaStatsTable OBJECT-TYPE
   SYNTAX     SEQUENCE OF MscLpImaStatsEntry
   ACCESS     not-accessible
   STATUS     mandatory
   DESCRIPTION
     "This group contains the statistics data for the Ima component."
::= { mscLpIma 12 }

mscLpImaStatsEntry OBJECT-TYPE
   SYNTAX     MscLpImaStatsEntry
   ACCESS     not-accessible
   STATUS     mandatory
   DESCRIPTION
     "An entry in the mscLpImaStatsTable."
   INDEX {
      mscLpIndex,
      mscLpImaIndex }
::= { mscLpImaStatsTable 1 }

MscLpImaStatsEntry ::= SEQUENCE {
   mscLpImaRunningTime
      Unsigned32,
   mscLpImaUnavailSecs
      Unsigned32,
   mscLpImaFailures
      Unsigned32,
   mscLpImaReceiveCellUtilization
      Gauge32,
   mscLpImaTransmitCellUtilization
      Gauge32 }

mscLpImaRunningTime OBJECT-TYPE
   SYNTAX     Unsigned32 (0..4294967295)
   ACCESS     read-only
   STATUS     mandatory
   DESCRIPTION
     "This attribute indicates the length of time (in seconds) for which the 
      Ima component has been in the unlocked state or has been used for 
      operational testing."
::= { mscLpImaStatsEntry 1 }

mscLpImaUnavailSecs OBJECT-TYPE
   SYNTAX     Unsigned32 (0..4294967295)
   ACCESS     read-only
   STATUS     mandatory
   DESCRIPTION
     "This attribute indicates the number of one second intervals during 
      which the Ima component has been unlocked and out of service."
::= { mscLpImaStatsEntry 2 }

mscLpImaFailures OBJECT-TYPE
   SYNTAX     Unsigned32 (0..4294967295)
   ACCESS     read-only
   STATUS     mandatory
   DESCRIPTION
     "This attribute indicates the number of complete failures, during 
      start-up or normal operation, that the Ima component has 
      experienced since being added. It must be noted that a service 
      degradation, such as 1 of the 3 links in an IMA group being down, 
      is not counted as a failure. If an Ima component is in a failure loop 
      and does not come up, this count will only increase by 1."
::= { mscLpImaStatsEntry 3 }

mscLpImaReceiveCellUtilization OBJECT-TYPE
   SYNTAX     Gauge32 (0..100)
   ACCESS     read-only
   STATUS     mandatory
   DESCRIPTION
     "This attribute indicates the ratio of the number of valid, assigned 
      user cells received on the IMA group to the IMA cell capacity 
      (based on the number of active links). The utilization is calculated 
      over a one minute period.
      
      This attribute will always have a value of 0 if the protocol for the 
      IMA group is proprietary."
::= { mscLpImaStatsEntry 4 }

mscLpImaTransmitCellUtilization OBJECT-TYPE
   SYNTAX     Gauge32 (0..100)
   ACCESS     read-only
   STATUS     mandatory
   DESCRIPTION
     "This attribute indicates the ratio of the number of user cells 
      transmitted on the IMA group to the IMA cell capacity (based on 
      the number of active links). The utilization is calculated over a one 
      minute period.
      
      This attribute will always have a value of 0 if the protocol for the 
      IMA group is proprietary."
::= { mscLpImaStatsEntry 5 }

mscLpImaCidDataTable OBJECT-TYPE
   SYNTAX     SEQUENCE OF MscLpImaCidDataEntry
   ACCESS     not-accessible
   STATUS     mandatory
   DESCRIPTION
     "This group contains the attribute for a component's Customer 
      Identifier (CID). Refer to the attribute description for a detailed 
      explanation of CIDs."
::= { mscLpIma 13 }

mscLpImaCidDataEntry OBJECT-TYPE
   SYNTAX     MscLpImaCidDataEntry
   ACCESS     not-accessible
   STATUS     mandatory
   DESCRIPTION
     "An entry in the mscLpImaCidDataTable."
   INDEX {
      mscLpIndex,
      mscLpImaIndex }
::= { mscLpImaCidDataTable 1 }

MscLpImaCidDataEntry ::= SEQUENCE {
   mscLpImaCustomerIdentifier
      Unsigned32 }

mscLpImaCustomerIdentifier OBJECT-TYPE
   SYNTAX     Unsigned32 (0 | 1..8191)
   ACCESS     read-write
   STATUS     mandatory
   DESCRIPTION
     "This attribute holds the Customer Identifier (CID).
      
      Every component has a CID. If a component has a cid attribute, the 
      component's CID is the provisioned value of that attribute; 
      otherwise the component inherits the CID of its parent. The top-
      level component has a CID of 0.
      
      Every operator session also has a CID, which is the CID 
      provisioned for the operator's user ID. An operator will see only the 
      stream data for components having a matching CID. Also, the 
      operator will be allowed to issue commands for only those 
      components which have a matching CID.
      
      An operator CID of 0 is used to identify the Network Manager 
      (referred to as 'NetMan' in DPN). This CID matches the CID of 
      any component. Values 1 to 8191 inclusive (equivalent to 'basic 
      CIDs' in DPN) may be assigned to specific customers."
   DEFVAL     { 0 }
::= { mscLpImaCidDataEntry 1 }

mscLpImaStateTable OBJECT-TYPE
   SYNTAX     SEQUENCE OF MscLpImaStateEntry
   ACCESS     not-accessible
   STATUS     mandatory
   DESCRIPTION
     "This group contains the three OSI State attributes and the six OSI 
      Status attributes. The descriptions generically indicate what each 
      attribute implies about the component. Note that not all the values 
      and state combinations described here are supported by every 
      component which uses this group. For component-specific 
      information and the valid state combinations, refer to NTP 241-
      7001-150, Passport Operations and Maintenance Guide."
::= { mscLpIma 14 }

mscLpImaStateEntry OBJECT-TYPE
   SYNTAX     MscLpImaStateEntry
   ACCESS     not-accessible
   STATUS     mandatory
   DESCRIPTION
     "An entry in the mscLpImaStateTable."
   INDEX {
      mscLpIndex,
      mscLpImaIndex }
::= { mscLpImaStateTable 1 }

MscLpImaStateEntry ::= SEQUENCE {
   mscLpImaAdminState
      INTEGER,
   mscLpImaOperationalState
      INTEGER,
   mscLpImaUsageState
      INTEGER,
   mscLpImaAvailabilityStatus
      OCTET STRING,
   mscLpImaProceduralStatus
      OCTET STRING,
   mscLpImaControlStatus
      OCTET STRING,
   mscLpImaAlarmStatus
      OCTET STRING,
   mscLpImaStandbyStatus
      INTEGER,
   mscLpImaUnknownStatus
      INTEGER }

mscLpImaAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component.
      
      The OSI Status attributes, if supported by the component, may 
      provide more details, qualifying the state of the component."
   DEFVAL     { unlocked }
::= { mscLpImaStateEntry 1 }

mscLpImaOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle.
      
      The OSI Status attributes, if supported by the component, may 
      provide more details, qualifying the state of the component."
   DEFVAL     { disabled }
::= { mscLpImaStateEntry 2 }

mscLpImaUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time.
      
      The OSI Status attributes, if supported by the component, may 
      provide more details, qualifying the state of the component."
   DEFVAL     { idle }
::= { mscLpImaStateEntry 3 }

mscLpImaAvailabilityStatus OBJECT-TYPE
   SYNTAX     OCTET STRING (SIZE (2))
   ACCESS     read-only
   STATUS     mandatory
   DESCRIPTION
     "If supported by the component, this attribute indicates the OSI 
      Availability status of the component. Note that, even though it is 
      defined as a multi-valued set, at most one value is shown to the user.
      
      When no values are in the set, this indicates that either the attribute 
      is not supported or that none of the status conditions described 
      below are present.
      
      The value inTest indicates that the resource is undergoing a test 
      procedure. If adminState is locked or shuttingDown, the normal 
      users are precluded from using the resource and controlStatus is 
      reservedForTest. Tests that do not exclude additional users can be 
      present in any operational or administrative state but the 
      reservedForTest condition should not be present.
      
      The value failed indicates that the component has an internal fault 
      that prevents it from operating. The operationalState is disabled.
      
      The value dependency indicates that the component cannot operate 
      because some other resource on which it depends is unavailable. 
      The operationalState is disabled.
      
      The value powerOff indicates the resource requires power to be 
      applied and it is not powered on. The operationalState is disabled.
      
      The value offLine indicates the resource requires a routine 
      operation (either manual, automatic, or both) to be performed to 
      place it on-line and make it available for use. The operationalState 
      is disabled.
      
      The value offDuty indicates the resource is inactive in accordance 
      with a predetermined time schedule. In the absence of other 
      disabling conditions, the operationalState is enabled or disabled.
      
      The value degraded indicates the service provided by the 
      component is degraded in some way, such as in speed or operating 
      capacity. However, the resource remains available for service. The 
      operationalState is enabled.
      
      The value notInstalled indicates the resource is not present. The 
      operationalState is disabled.
      
      The value logFull is not used.

      Description of bits:
      inTest(0)
      failed(1)
      powerOff(2)
      offLine(3)
      offDuty(4)
      dependency(5)
      degraded(6)
      notInstalled(7)
      logFull(8)"
::= { mscLpImaStateEntry 4 }

mscLpImaProceduralStatus OBJECT-TYPE
   SYNTAX     OCTET STRING (SIZE (1))
   ACCESS     read-only
   STATUS     mandatory
   DESCRIPTION
     "If supported by the component, this attribute indicates the OSI 
      Procedural status of the component. Note that, even though it is 
      defined as a multi-valued set, at most one value is shown to the user.
      
      When no values are in the set, this indicates that either the attribute 
      is not supported or that none of the status conditions described 
      below are present.
      
      The value initializationRequired indicates (for a resource which 
      doesn't initialize autonomously) that initialization is required before 
      it can perform its normal functions, and this procedure has not been 
      initiated. The operationalState is disabled.
      
      The value notInitialized indicates (for a resource which does 
      initialize autonomously) that initialization is required before it can 
      perform its normal functions, and this procedure has not been 
      initiated. The operationalState may be enabled or disabled.
      
      The value initializing indicates that initialization has been initiated 
      but is not yet complete. The operationalState may be enabled or 
      disabled.
      
      The value reporting indicates the resource has completed some 
      processing operation and is notifying the results. The 
      operationalState is enabled.
      
      The value terminating indicates the component is in a termination 
      phase. If the resource doesn't reinitialize autonomously, 
      operationalState is disabled; otherwise it is enabled or disabled.

      Description of bits:
      initializationRequired(0)
      notInitialized(1)
      initializing(2)
      reporting(3)
      terminating(4)"
::= { mscLpImaStateEntry 5 }

mscLpImaControlStatus OBJECT-TYPE
   SYNTAX     OCTET STRING (SIZE (1))
   ACCESS     read-only
   STATUS     mandatory
   DESCRIPTION
     "If supported by the component, this attribute indicates the OSI 
      Control status of the component. Note that, even though it is defined 
      as a multi-valued set, at most one value is shown to the user.
      
      When no values are in the set, this indicates that either the attribute 
      is not supported or that none of the status conditions described 
      below are present.
      
      The value subjectToTest indicates the resource is available but tests 
      may be conducted simultaneously at unpredictable times, which 
      may cause it to exhibit unusual characteristics.
      
      The value partOfServicesLocked indicates that part of the service is 
      restricted from users of a resource. The adminState is unlocked.
      
      The value reservedForTest indicates that the component is 
      administratively unavailable because it is undergoing a test 
      procedure. The adminState is locked.
      
      The value suspended indicates that the service has been 
      administratively suspended.

      Description of bits:
      subjectToTest(0)
      partOfServicesLocked(1)
      reservedForTest(2)
      suspended(3)"
::= { mscLpImaStateEntry 6 }

mscLpImaAlarmStatus OBJECT-TYPE
   SYNTAX     OCTET STRING (SIZE (1))
   ACCESS     read-only
   STATUS     mandatory
   DESCRIPTION
     "If supported by the component, this attribute indicates the OSI 
      Alarm status of the component. Note that, even though it is defined 
      as a multi-valued set, at most one value is shown to the user.
      
      When no values are in the set, this indicates that either the attribute 
      is not supported or that none of the status conditions described 
      below are present.
      
      The value underRepair indicates the component is currently being 
      repaired. The operationalState is enabled or disabled.
      
      The value critical indicates one or more critical alarms are 
      outstanding against the component. Other, less severe, alarms may 
      also be outstanding. The operationalState is enabled or disabled.
      
      The value major indicates one or more major alarms are 
      outstanding against the component. Other, less severe, alarms may 
      also be outstanding. The operationalState is enabled or disabled.
      
      The value minor indicates one or more minor alarms are 
      outstanding against the component. Other, less severe, alarms may 
      also be outstanding. The operationalState is enabled or disabled.
      
      The value alarmOutstanding generically indicates that an alarm of 
      some severity is outstanding against the component.

      Description of bits:
      underRepair(0)
      critical(1)
      major(2)
      minor(3)
      alarmOutstanding(4)"
::= { mscLpImaStateEntry 7 }

mscLpImaStandbyStatus OBJECT-TYPE
   SYNTAX     INTEGER  {
                 hotStandby(0),
                 coldStandby(1),
                 providingService(2),
                 notSet(15) }
   ACCESS     read-only
   STATUS     mandatory
   DESCRIPTION
     "If supported by the component, this attribute indicates the OSI 
      Standby status of the component.
      
      The value notSet indicates that either the attribute is not supported 
      or that none of the status conditions described below are present. 
      Note that this is a non-standard value, used because the original 
      specification indicated this attribute was set-valued and thus, did not 
      provide a value to indicate that none of the other three are 
      applicable.
      
      The value hotStandby indicates that the resource is not providing 
      service but will be immediately able to take over the role of the 
      resource to be backed up, without initialization activity, and 
      containing the same information as the resource to be backed up.
      
      The value coldStandby indicates the resource is a backup for 
      another resource but will not be immediately able to take over the 
      role of the backed up resource and will require some initialization 
      activity.
      
      The value providingService indicates that this component, as a 
      backup resource, is currently backing up another resource."
   DEFVAL     { notSet }
::= { mscLpImaStateEntry 8 }

mscLpImaUnknownStatus OBJECT-TYPE
   SYNTAX     INTEGER  {
                 false(0),
                 true(1) }
   ACCESS     read-only
   STATUS     mandatory
   DESCRIPTION
     "This attribute indicates the OSI Unknown status of the component.
      
      The value false indicates that all of the other OSI State and Status 
      attribute values can be considered accurate.
      
      The value true indicates that the actual state of the component is not 
      known for sure."
   DEFVAL     { false }
::= { mscLpImaStateEntry 9 }


-- 
-- The Test component is configured to control a hardware facility test 
-- on a physical (V35, X21, DS1, E1, DS3, E3 etc.) or a logical port.

mscLpImaTest OBJECT IDENTIFIER ::= { mscLpIma 2 }



mscLpImaTestRowStatusTable OBJECT-TYPE
   SYNTAX     SEQUENCE OF MscLpImaTestRowStatusEntry
   ACCESS     not-accessible
   STATUS     mandatory
   DESCRIPTION
     "This entry controls the addition and deletion of 
      mscLpImaTest components."
::= { mscLpImaTest 1 }

mscLpImaTestRowStatusEntry OBJECT-TYPE
   SYNTAX     MscLpImaTestRowStatusEntry
   ACCESS     not-accessible
   STATUS     mandatory
   DESCRIPTION
     "A single entry in the table represents a single 
      mscLpImaTest component."
   INDEX {
      mscLpIndex,
      mscLpImaIndex,
      mscLpImaTestIndex }
::= { mscLpImaTestRowStatusTable 1 }

MscLpImaTestRowStatusEntry ::= SEQUENCE {
   mscLpImaTestRowStatus
      RowStatus,
   mscLpImaTestComponentName
      DisplayString,
   mscLpImaTestStorageType
      StorageType,
   mscLpImaTestIndex
      NonReplicated }

mscLpImaTestRowStatus OBJECT-TYPE
   SYNTAX     RowStatus 
   ACCESS     read-only
   STATUS     mandatory
   DESCRIPTION
     "This variable is used as the basis for SNMP naming of
      mscLpImaTest components.
      These components cannot be added nor deleted."
::= { mscLpImaTestRowStatusEntry 1 }

mscLpImaTestComponentName OBJECT-TYPE
   SYNTAX     DisplayString 
   ACCESS     read-only
   STATUS     mandatory
   DESCRIPTION
     "This variable provides the component's string name for
      use with the ASCII Console Interface"
::= { mscLpImaTestRowStatusEntry 2 }

mscLpImaTestStorageType OBJECT-TYPE
   SYNTAX     StorageType 
   ACCESS     read-only
   STATUS     mandatory
   DESCRIPTION
     "This variable represents the storage type value for the
      mscLpImaTest tables."
::= { mscLpImaTestRowStatusEntry 4 }

mscLpImaTestIndex OBJECT-TYPE
   SYNTAX     NonReplicated 
   ACCESS     not-accessible
   STATUS     mandatory
   DESCRIPTION
     "This variable represents the index for the mscLpImaTest tables."
::= { mscLpImaTestRowStatusEntry 10 }

mscLpImaTestStateTable OBJECT-TYPE
   SYNTAX     SEQUENCE OF MscLpImaTestStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscLpImaTest 10 }

mscLpImaTestStateEntry OBJECT-TYPE
   SYNTAX     MscLpImaTestStateEntry
   ACCESS     not-accessible
   STATUS     mandatory
   DESCRIPTION
     "An entry in the mscLpImaTestStateTable."
   INDEX {
      mscLpIndex,
      mscLpImaIndex,
      mscLpImaTestIndex }
::= { mscLpImaTestStateTable 1 }

MscLpImaTestStateEntry ::= SEQUENCE {
   mscLpImaTestAdminState
      INTEGER,
   mscLpImaTestOperationalState
      INTEGER,
   mscLpImaTestUsageState
      INTEGER }

mscLpImaTestAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscLpImaTestStateEntry 1 }

mscLpImaTestOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscLpImaTestStateEntry 2 }

mscLpImaTestUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscLpImaTestStateEntry 3 }

mscLpImaTestSetupTable OBJECT-TYPE
   SYNTAX     SEQUENCE OF MscLpImaTestSetupEntry
   ACCESS     not-accessible
   STATUS     mandatory
   DESCRIPTION
     "This group contains all of the operational data for a Test 
      component."
::= { mscLpImaTest 11 }

mscLpImaTestSetupEntry OBJECT-TYPE
   SYNTAX     MscLpImaTestSetupEntry
   ACCESS     not-accessible
   STATUS     mandatory
   DESCRIPTION
     "An entry in the mscLpImaTestSetupTable."
   INDEX {
      mscLpIndex,
      mscLpImaIndex,
      mscLpImaTestIndex }
::= { mscLpImaTestSetupTable 1 }

MscLpImaTestSetupEntry ::= SEQUENCE {
   mscLpImaTestPurpose
      AsciiString,
   mscLpImaTestType
      INTEGER,
   mscLpImaTestFrmSize
      Unsigned32,
   mscLpImaTestFrmPatternType
      INTEGER,
   mscLpImaTestCustomizedPattern
      Hex,
   mscLpImaTestDataStartDelay
      Unsigned32,
   mscLpImaTestDisplayInterval
      Unsigned32,
   mscLpImaTestDuration
      Unsigned32 }

mscLpImaTestPurpose OBJECT-TYPE
   SYNTAX     AsciiString (SIZE (0..40))
   ACCESS     read-write
   STATUS     mandatory
   DESCRIPTION
     "This attribute records the purpose of the test so that the test results 
      can be associated and properly analyzed."
::= { mscLpImaTestSetupEntry 1 }

mscLpImaTestType OBJECT-TYPE
   SYNTAX     INTEGER  {
                 card(0),
                 manual(1),
                 localLoop(2),
                 remoteLoop(3),
                 externalLoop(4),
                 payloadLoop(5),
                 remoteLoopThisTrib(6),
                 v54RemoteLoop(7),
                 pn127RemoteLoop(8) }
   ACCESS     read-write
   STATUS     mandatory
   DESCRIPTION
     "This attribute is the type of test to be run. The available test types 
      include the following:
      card test sets up an internal loop on the board and runs a bit error 
      rate test.
      manual test assumes the line is looped back externally and a bit 
      error rate test is performed.
      localLoop test loops back the local modem and performs a bit error 
      rate test.
      remoteLoop test loops back the remote modem (or CSU) and 
      performs a bit error rate test.
      externalLoop test loops back the line to the far end.
      payloadLoop test only loops back the payload data received from 
      the incoming line.
      remoteLoopThisTrib loops this particular tributary back at the far 
      end, using services provided by the parent.
      v54RemoteLoop initiates a V.54 Remote Loopback test.
      pn127RemoteLoop initiates a PN127 Remote Loopback test.
      Note that not all test types are not supported by all function 
      processors."
   DEFVAL     { card }
::= { mscLpImaTestSetupEntry 2 }

mscLpImaTestFrmSize OBJECT-TYPE
   SYNTAX     Unsigned32 (4..4096)
   ACCESS     read-write
   STATUS     mandatory
   DESCRIPTION
     "This attribute defines the size of the test data frames in number of 
      bytes."
   DEFVAL     { 1024 }
::= { mscLpImaTestSetupEntry 3 }

mscLpImaTestFrmPatternType OBJECT-TYPE
   SYNTAX     INTEGER  {
                 ccitt32kBitPattern(0),
                 ccitt8MBitPattern(1),
                 customizedPattern(2) }
   ACCESS     read-write
   STATUS     mandatory
   DESCRIPTION
     "This attribute defines the type of data pattern generation to use. The 
      following lists the available pattern types:
      ccitt32kBitPattern is a pseudo-random sequence of 32 kbit.
      ccitt8MBitPattern is a pseudo-random sequence of 8Mbit.
      customizedPattern is the pattern defined in the customizedPattern 
      attribute."
   DEFVAL     { ccitt32kBitPattern }
::= { mscLpImaTestSetupEntry 4 }

mscLpImaTestCustomizedPattern OBJECT-TYPE
   SYNTAX     Hex (0..4294967295)
   ACCESS     read-write
   STATUS     mandatory
   DESCRIPTION
     "This attribute allows a customized 32 bit pattern to be defined for 
      use in the test data frames. This attribute is used when the attribute 
      frmPatternType is set to CustomizedPattern. Note that a 55 hex 
      pattern is an alternating 1 and 0 pattern."
   DEFVAL     { 1431655765 }
::= { mscLpImaTestSetupEntry 5 }

mscLpImaTestDataStartDelay OBJECT-TYPE
   SYNTAX     Unsigned32 (0..1814400)
   ACCESS     read-write
   STATUS     mandatory
   DESCRIPTION
     "This attribute specifies the time delay (in seconds) between when 
      the test expects the loop to have been set up, to when the test data 
      actually starts to be transmitted. This attribute is to accommodate 
      some non-standard equipment that requires extra time for setting up 
      a requested loop.
      This attribute is ignored when the test type is set to externalLoop."
   DEFVAL     { 0 }
::= { mscLpImaTestSetupEntry 6 }

mscLpImaTestDisplayInterval OBJECT-TYPE
   SYNTAX     Unsigned32 (0..30240)
   ACCESS     read-write
   STATUS     mandatory
   DESCRIPTION
     "This attribute defines the interval (in minutes) between which 
      interim test results are to be displayed. Results are displayed at the 
      operator console at which the test was started. When the test type is 
      set to externalLoop, this attribute is ignored. There will be no 
      display of results if displayInterval is set to 0. This attribute can be 
      changed anytime."
   DEFVAL     { 5 }
::= { mscLpImaTestSetupEntry 7 }

mscLpImaTestDuration OBJECT-TYPE
   SYNTAX     Unsigned32 (1..30240)
   ACCESS     read-write
   STATUS     mandatory
   DESCRIPTION
     "This attribute is the duration (in minutes) that test data will be 
      transmitted. In the case of an externalLoop, this is the time that the 
      loop is in effect. Note that dataStartDelay does not apply to the 
      externalLoop."
   DEFVAL     { 1 }
::= { mscLpImaTestSetupEntry 8 }

mscLpImaTestResultsTable OBJECT-TYPE
   SYNTAX     SEQUENCE OF MscLpImaTestResultsEntry
   ACCESS     not-accessible
   STATUS     mandatory
   DESCRIPTION
     "This group contains all the statistics related attributes of the Test 
      component."
::= { mscLpImaTest 12 }

mscLpImaTestResultsEntry OBJECT-TYPE
   SYNTAX     MscLpImaTestResultsEntry
   ACCESS     not-accessible
   STATUS     mandatory
   DESCRIPTION
     "An entry in the mscLpImaTestResultsTable."
   INDEX {
      mscLpIndex,
      mscLpImaIndex,
      mscLpImaTestIndex }
::= { mscLpImaTestResultsTable 1 }

MscLpImaTestResultsEntry ::= SEQUENCE {
   mscLpImaTestElapsedTime
      Counter32,
   mscLpImaTestTimeRemaining
      Unsigned32,
   mscLpImaTestCauseOfTermination
      INTEGER,
   mscLpImaTestBitsTx
      PassportCounter64,
   mscLpImaTestBytesTx
      PassportCounter64,
   mscLpImaTestFrmTx
      PassportCounter64,
   mscLpImaTestBitsRx
      PassportCounter64,
   mscLpImaTestBytesRx
      PassportCounter64,
   mscLpImaTestFrmRx
      PassportCounter64,
   mscLpImaTestErroredFrmRx
      PassportCounter64,
   mscLpImaTestBitErrorRate
      AsciiString }

mscLpImaTestElapsedTime OBJECT-TYPE
   SYNTAX     Counter32 
   ACCESS     read-only
   STATUS     mandatory
   DESCRIPTION
     "This attribute is the number of minutes elapsed since the test started 
      for an externalLoop test. For a data test, this is the time since test 
      data was first transmitted."
::= { mscLpImaTestResultsEntry 1 }

mscLpImaTestTimeRemaining OBJECT-TYPE
   SYNTAX     Unsigned32 (0..4294967295)
   ACCESS     read-only
   STATUS     mandatory
   DESCRIPTION
     "This attribute is the number of minutes remaining before the test is 
      to be stopped according to the duration attribute."
   DEFVAL     { 0 }
::= { mscLpImaTestResultsEntry 2 }

mscLpImaTestCauseOfTermination OBJECT-TYPE
   SYNTAX     INTEGER  {
                 testTimeExpired(0),
                 stoppedByOperator(1),
                 unknown(2),
                 neverStarted(3),
                 testRunning(4),
                 hardwareReconfigured(5),
                 loopCodeSyncFailed(6),
                 patternSyncFailed(7),
                 patternSyncLost(8) }
   ACCESS     read-only
   STATUS     mandatory
   DESCRIPTION
     "This attribute indicates either the status of the test or the cause of 
      the test's termination:
      
      neverStarted indicates that the test has not yet been started.
      
      testRunning indicates that the test has been started.
      
      stoppedByOperator indicates that the operator issued a stop 
      command on a test that was running.
      
      testTimeExpired indicates that the test ran for the time specified by 
      the test's duration.
      
      loopCodeSyncFailed indicates that the local end failed to 
      synchronize to the loopCode pattern. The local end transmits the 
      loopCode pattern to cause the remote end to apply a loopback, after 
      which the local end should receive the loopCode pattern. The exact 
      pattern used to request loopCode depends on the test type. This 
      failure indicates a high rate of transmission errors, or that the 
      remote end has failed to apply the loopback.
      
      patternSyncFailed indicates that the local end failed to synchronize 
      to the frmPatternType test pattern, that should have been looped 
      back at the remote end. This failure indicates a high rate of 
      transmission errors or the absence of a loopback.
      
      patternSyncLost indicates that the local end gained and then lost 
      synchronization to the returned frmPatternType test pattern. This 
      failure indicates a sudden increase in transmission errors, frame 
      slippage, or the removal of an existing loopback.
      
      unknown is set when a reason to terminate other than those listed 
      here is encountered.
      
      Note: Only MSA cards support recognition of the failures 
      loopCodeSyncFailed, patternSyncFailed and patternSyncLost. 
      Other cards will not terminate the test under the conditions 
      described by these values."
   DEFVAL     { neverStarted }
::= { mscLpImaTestResultsEntry 3 }

mscLpImaTestBitsTx OBJECT-TYPE
   SYNTAX     PassportCounter64 
   ACCESS     read-only
   STATUS     mandatory
   DESCRIPTION
     "This attribute is the total number of bits sent during the test period. 
      As long as the line speed of the hardware interface is less than 
      70 Mbit/s, this counter is not expected to reach the maximum value."
::= { mscLpImaTestResultsEntry 4 }

mscLpImaTestBytesTx OBJECT-TYPE
   SYNTAX     PassportCounter64 
   ACCESS     read-only
   STATUS     mandatory
   DESCRIPTION
     "This attribute is the total number of bytes sent during the test 
      period. This counter is not expected to reach its maximum value."
::= { mscLpImaTestResultsEntry 5 }

mscLpImaTestFrmTx OBJECT-TYPE
   SYNTAX     PassportCounter64 
   ACCESS     read-only
   STATUS     mandatory
   DESCRIPTION
     "This attribute is the total number of frames sent during the test 
      period. This counter is not expected to reach its maximum value."
::= { mscLpImaTestResultsEntry 6 }

mscLpImaTestBitsRx OBJECT-TYPE
   SYNTAX     PassportCounter64 
   ACCESS     read-only
   STATUS     mandatory
   DESCRIPTION
     "This attribute is the total number of bits received during the test 
      period. This counter is not expected to reach its maximum value. 
      The counter will wrap around to 0 if it does reach the maximum 
      value."
::= { mscLpImaTestResultsEntry 7 }

mscLpImaTestBytesRx OBJECT-TYPE
   SYNTAX     PassportCounter64 
   ACCESS     read-only
   STATUS     mandatory
   DESCRIPTION
     "This attribute is the total number of bytes received during the test 
      period. This counter is not expected to reach its maximum value. 
      The counter will wrap around to 0 if it does reach its maximum 
      value."
::= { mscLpImaTestResultsEntry 8 }

mscLpImaTestFrmRx OBJECT-TYPE
   SYNTAX     PassportCounter64 
   ACCESS     read-only
   STATUS     mandatory
   DESCRIPTION
     "This attribute is the total number of frames received during the test 
      period. This counter is not expected to reach its maximum value. 
      The counter will wrap around to 0 if it does reach its maximum 
      value."
::= { mscLpImaTestResultsEntry 9 }

mscLpImaTestErroredFrmRx OBJECT-TYPE
   SYNTAX     PassportCounter64 
   ACCESS     read-only
   STATUS     mandatory
   DESCRIPTION
     "This attribute is not displayed for ATM cards because the physical 
      layer drops all errored frames at the controller interface. 
      
      For all other card types, this attribute is the total number of errored 
      frames received during the test period. This counter is not expected 
      to reach its maximum value. The counter will wrap around to 0 if it 
      does reach its maximum value."
::= { mscLpImaTestResultsEntry 10 }

mscLpImaTestBitErrorRate OBJECT-TYPE
   SYNTAX     AsciiString (SIZE (5))
   ACCESS     read-only
   STATUS     mandatory
   DESCRIPTION
     "This attribute is not displayed for ATM cards because the physical 
      layer drops all errored frames at the controller interface. 
      
      For all other card types, this attribute is the calculated bit error rate 
      on the link. Test data are generated and sent in frames of a preset 
      size (frameSize). The Test component will try to estimate the 
      number of bit errors in any errored frame which is identifiable. The 
      statistics will be updated accordingly. A lost frame (may be due to 
      an error on the flag sequence) will be discarded for the bit error rate 
      calculation. The result is presented in the form of xEsyy, where x is 
      the mantissa, syy is the exponent, for example 0E+00, 2E-09.
      Note that the bitErrorRate is an estimate only. For more reliable test 
      results, the test should be done over a long period. Multiple tests 
      would also improve the confidence level of the test results."
::= { mscLpImaTestResultsEntry 11 }


-- Lp/n Ima/n Link/n	
-- Lp/n Ds3/n Ima/n Link/n
-- 
-- This component is used to define a DS1/E1 link belonging to an 
-- IMA group. The instance number of the Link subcomponent 
-- corresponds to the link identifier (LID) used by the link in IMA 
-- Control Protocol (ICP) cells. To use Ima on an 8pDS1E1 function 
-- processor, add Lp/n Ima/n Link/n. To use Ima on a 4pDS3ChAtm 
-- function processor, add Lp/n Ds3/n Ima/n Link/n.

mscLpImaLk OBJECT IDENTIFIER ::= { mscLpIma 3 }



mscLpImaLkRowStatusTable OBJECT-TYPE
   SYNTAX     SEQUENCE OF MscLpImaLkRowStatusEntry
   ACCESS     not-accessible
   STATUS     mandatory
   DESCRIPTION
     "This entry controls the addition and deletion of 
      mscLpImaLk components."
::= { mscLpImaLk 1 }

mscLpImaLkRowStatusEntry OBJECT-TYPE
   SYNTAX     MscLpImaLkRowStatusEntry
   ACCESS     not-accessible
   STATUS     mandatory
   DESCRIPTION
     "A single entry in the table represents a single 
      mscLpImaLk component."
   INDEX {
      mscLpIndex,
      mscLpImaIndex,
      mscLpImaLkIndex }
::= { mscLpImaLkRowStatusTable 1 }

MscLpImaLkRowStatusEntry ::= SEQUENCE {
   mscLpImaLkRowStatus
      RowStatus,
   mscLpImaLkComponentName
      DisplayString,
   mscLpImaLkStorageType
      StorageType,
   mscLpImaLkIndex
      Integer32 }

mscLpImaLkRowStatus OBJECT-TYPE
   SYNTAX     RowStatus 
   ACCESS     read-write
   STATUS     mandatory
   DESCRIPTION
     "This variable is used as the basis for SNMP naming of
      mscLpImaLk components.
      These components can be added and deleted."
::= { mscLpImaLkRowStatusEntry 1 }

mscLpImaLkComponentName OBJECT-TYPE
   SYNTAX     DisplayString 
   ACCESS     read-only
   STATUS     mandatory
   DESCRIPTION
     "This variable provides the component's string name for
      use with the ASCII Console Interface"
::= { mscLpImaLkRowStatusEntry 2 }

mscLpImaLkStorageType OBJECT-TYPE
   SYNTAX     StorageType 
   ACCESS     read-only
   STATUS     mandatory
   DESCRIPTION
     "This variable represents the storage type value for the
      mscLpImaLk tables."
::= { mscLpImaLkRowStatusEntry 4 }

mscLpImaLkIndex OBJECT-TYPE
   SYNTAX     Integer32 (0..31)
   ACCESS     not-accessible
   STATUS     mandatory
   DESCRIPTION
     "This variable represents the index for the mscLpImaLk tables."
::= { mscLpImaLkRowStatusEntry 10 }

mscLpImaLkProvTable OBJECT-TYPE
   SYNTAX     SEQUENCE OF MscLpImaLkProvEntry
   ACCESS     not-accessible
   STATUS     mandatory
   DESCRIPTION
     "This group contains the provisionable attributes for the Link 
      subcomponent."
::= { mscLpImaLk 10 }

mscLpImaLkProvEntry OBJECT-TYPE
   SYNTAX     MscLpImaLkProvEntry
   ACCESS     not-accessible
   STATUS     mandatory
   DESCRIPTION
     "An entry in the mscLpImaLkProvTable."
   INDEX {
      mscLpIndex,
      mscLpImaIndex,
      mscLpImaLkIndex }
::= { mscLpImaLkProvTable 1 }

MscLpImaLkProvEntry ::= SEQUENCE {
   mscLpImaLkInterfaceName
      Link }

mscLpImaLkInterfaceName OBJECT-TYPE
   SYNTAX     Link 
   ACCESS     read-write
   STATUS     mandatory
   DESCRIPTION
     "This attribute associates the Link subcomponent with a specific 
      interface on a function processor, for example Lp/5 E1/3 Chan/0.
      If IMA groups and independent links coexist on a card running 
      IMA and per-VC queueing is enabled, plan the selection of DS1 or 
      E1 ports to be used by the IMA group carefully. For a 
      4pDS3ChAtm function processor there is no per-VC queueing."
::= { mscLpImaLkProvEntry 1 }

mscLpImaLkOperTable OBJECT-TYPE
   SYNTAX     SEQUENCE OF MscLpImaLkOperEntry
   ACCESS     not-accessible
   STATUS     mandatory
   DESCRIPTION
     "This group contains the operational attributes for the Link 
      subcomponent."
::= { mscLpImaLk 11 }

mscLpImaLkOperEntry OBJECT-TYPE
   SYNTAX     MscLpImaLkOperEntry
   ACCESS     not-accessible
   STATUS     mandatory
   DESCRIPTION
     "An entry in the mscLpImaLkOperTable."
   INDEX {
      mscLpIndex,
      mscLpImaIndex,
      mscLpImaLkIndex }
::= { mscLpImaLkOperTable 1 }

MscLpImaLkOperEntry ::= SEQUENCE {
   mscLpImaLkFailureCause
      INTEGER,
   mscLpImaLkRemoteDefect
      INTEGER,
   mscLpImaLkRemoteLid
      Unsigned32,
   mscLpImaLkRelativeDelay
      Unsigned32,
   mscLpImaLkLastOifCause
      INTEGER }

mscLpImaLkFailureCause OBJECT-TYPE
   SYNTAX     INTEGER  {
                 noFailure(0),
                 interfaceDown(1),
                 lif(2),
                 lods(3),
                 protocolError(4),
                 remoteFailure(5),
                 misconnected(6),
                 unsupportedFrameLength(7),
                 unsupportedSymmetry(8),
                 noIcp(9) }
   ACCESS     read-only
   STATUS     mandatory
   DESCRIPTION
     "This attribute indicates the failure cause on this link. Possible values 
      are:
      noFailure: there is no failure on this link.
      interfaceDown: the physical port used by the link is down.
      lif: the link is in loss of IMA frame (LIF) state.
      lods: the link is in loss of delay synchronization (LODS) state; that 
      is, it has exhibited a differential delay which is greater than the 
      maximum differential delay tolerated by the IMA group. It must be 
      noted that hysteresis is used for the LODS condition.
      protocolError: the link is down because of a time-out or because 
      bad values are being received in IMA Control Protocol (ICP) cells.
      remoteFailure: the far end link is down.
      misconnected: the link is down because the IMA group has 
      declared, after using its transmit test pattern procedure, that this link 
      is not properly connected. This value can occur only if the protocol 
      for the IMA group is atmForum10.
      unsupportedFrameLength: the link is down because it is receiving 
      from the far end a frame length which is not supported by the local 
      IMA group. This value can occur only if the protocol for the IMA 
      group is atmForum10.
      unsupportedSymmetry: the link is down because it is receiving 
      from the far end a group symmetry which is not supported by the 
      local IMA group. This value can occur only if the protocol for the 
      IMA group is atmForum10.
      noIcp: the link is down because it is not receiving IMA Control 
      Protocol (ICP) cells. This value can occur only if the protocol for 
      the IMA group is atmForum10."
::= { mscLpImaLkOperEntry 1 }

mscLpImaLkRemoteDefect OBJECT-TYPE
   SYNTAX     INTEGER  {
                 noDefect(0),
                 physicalLayerDefect(1),
                 lif(2),
                 lods(3),
                 interfaceDown(4) }
   ACCESS     read-only
   STATUS     mandatory
   DESCRIPTION
     "This attribute indicates the IMA remote defect indicator (RDI) 
      currently being received on this link. Possible values are:
      noDefect: no defect.
      physicalLayerDefect: the interface used by the remote link has a 
      physical layer defect. This value can occur only if the protocol for 
      the IMA group is atmForum10.
      interfaceDown: the physical interface used by the remote link is 
      down.This value can occur only if the protocol for the IMA group is 
      proprietary.
      lif: the remote link has a loss of IMA frame (LIF) defect.
      lods: the remote link has a loss of delay synchronization (LODS) 
      defect; that is, it has exhibited a differential delay which is greater 
      than the maximum differential delay tolerated by the IMA group."
::= { mscLpImaLkOperEntry 2 }

mscLpImaLkRemoteLid OBJECT-TYPE
   SYNTAX     Unsigned32 (0..31)
   ACCESS     read-only
   STATUS     mandatory
   DESCRIPTION
     "This attribute indicates the link identifier (LID) used by the remote 
      IMA group on the physical link. A value of 0 will be displayed if 
      the link is not receiving IMA Control Protocol (ICP) cells or if the 
      physical layer is down."
::= { mscLpImaLkOperEntry 3 }

mscLpImaLkRelativeDelay OBJECT-TYPE
   SYNTAX     Unsigned32 (0..4294967295)
   ACCESS     read-only
   STATUS     mandatory
   DESCRIPTION
     "This attribute indicates the latest measured differential delay 
      (rounded up in milliseconds) between this link and the link, in the 
      same IMA group, having the least delay. A value of 4294967295 
      indicates that the relative delay could not be measured. This can be 
      due to physical layer problems or to no IMA Control Protocol (ICP) 
      cells being received on the link."
::= { mscLpImaLkOperEntry 4 }

mscLpImaLkLastOifCause OBJECT-TYPE
   SYNTAX     INTEGER  {
                 noOif(0),
                 badFrameLength(1),
                 badGid(2),
                 badLid(3),
                 badOffset(4),
                 badSequenceNumber(5),
                 stuffError(6),
                 missingIcp(7),
                 unexpectedIcp(8),
                 erroredIcp(9),
                 noCells(10),
                 idleCell(11) }
   ACCESS     read-only
   STATUS     mandatory
   DESCRIPTION
     "This attribute indicates the cause of the last out of IMA frame (OIF) 
      anomaly on the link. It will always have a value of noOif if the 
      protocol for the IMA group is proprietary. 
      Possible values are:
      noOif: no OIF was detected.
      badFrameLength: an IMA Control Protocol (ICP) cell with an 
      unexpected frame length was received.
      badGid: an ICP cell with an unexpected group identifier (GID) was 
      received.
      badLid: an ICP cell with an unexpected link identifier (LID) was 
      received.
      badOffset: an ICP cell with an unexpected cell offset was received.
      badSequenceNumber: an ICP cell with an unexpected frame 
      sequence number was received.
      stuffError: an illegal stuffing sequence was received.
      missingIcp: an expected ICP cell was not received.
      unexpectedIcp: an unexpected ICP cell was received.
      erroredIcp: two consecutive errored ICP cells were received.
      noCells: no cells are being received on the link.
      idleCell: an idle cell was received on the link."
::= { mscLpImaLkOperEntry 5 }

mscLpImaLkStatsTable OBJECT-TYPE
   SYNTAX     SEQUENCE OF MscLpImaLkStatsEntry
   ACCESS     not-accessible
   STATUS     mandatory
   DESCRIPTION
     "This group contains the statistics data for the Link subcomponent."
::= { mscLpImaLk 12 }

mscLpImaLkStatsEntry OBJECT-TYPE
   SYNTAX     MscLpImaLkStatsEntry
   ACCESS     not-accessible
   STATUS     mandatory
   DESCRIPTION
     "An entry in the mscLpImaLkStatsTable."
   INDEX {
      mscLpIndex,
      mscLpImaIndex,
      mscLpImaLkIndex }
::= { mscLpImaLkStatsTable 1 }

MscLpImaLkStatsEntry ::= SEQUENCE {
   mscLpImaLkRunningTime
      Unsigned32,
   mscLpImaLkUnavailSecs
      Unsigned32,
   mscLpImaLkFailures
      Unsigned32,
   mscLpImaLkUnusableSec
      Counter32,
   mscLpImaLkSevErroredSec
      Counter32,
   mscLpImaLkFarEndUnusableSec
      Counter32,
   mscLpImaLkFarEndSevErroredSec
      Counter32,
   mscLpImaLkFarEndUnavailSec
      Counter32,
   mscLpImaLkIcpViolations
      Counter32,
   mscLpImaLkTxStuffEvents
      Counter32,
   mscLpImaLkRxStuffEvents
      Counter32,
   mscLpImaLkIdleCellSec
      Counter32 }

mscLpImaLkRunningTime OBJECT-TYPE
   SYNTAX     Unsigned32 (0..4294967295)
   ACCESS     read-only
   STATUS     mandatory
   DESCRIPTION
     "This attribute counts the length of time (in seconds) for which the 
      Link component has been running."
::= { mscLpImaLkStatsEntry 1 }

mscLpImaLkUnavailSecs OBJECT-TYPE
   SYNTAX     Unsigned32 (0..4294967295)
   ACCESS     read-only
   STATUS     mandatory
   DESCRIPTION
     "For an IMA group whose protocol is atmForum10, this attribute 
      counts the number of unavailable seconds. Unavailability begins at 
      the start of 10 contiguous severely errored seconds (SES) and ends 
      at the start of 10 contiguous seconds with no SES.
      For an IMA group whose protocol is proprietary, this attribute 
      counts the number of one second intervals during which the Link 
      component has been out of service."
::= { mscLpImaLkStatsEntry 2 }

mscLpImaLkFailures OBJECT-TYPE
   SYNTAX     Unsigned32 (0..4294967295)
   ACCESS     read-only
   STATUS     mandatory
   DESCRIPTION
     "This attribute counts the number of failures, during link addition or 
      normal operation, that the link has experienced."
::= { mscLpImaLkStatsEntry 3 }

mscLpImaLkUnusableSec OBJECT-TYPE
   SYNTAX     Counter32 
   ACCESS     read-only
   STATUS     mandatory
   DESCRIPTION
     "This attribute counts the number of one second intervals during 
      which the near end has been in an unusable state.
      This attribute will always have a value of 0 if the protocol for the 
      IMA group is proprietary."
::= { mscLpImaLkStatsEntry 4 }

mscLpImaLkSevErroredSec OBJECT-TYPE
   SYNTAX     Counter32 
   ACCESS     read-only
   STATUS     mandatory
   DESCRIPTION
     "This attribute counts the number of one second intervals in which at 
      least 30 percent of the IMA Control Protocol (ICP) cells were 
      counted as ICP violations or at least one link defect (physical layer, 
      LIF and LODS defects) was detected. This attribute will not 
      increment during UAS (Unavailable Second) conditions.
      This attribute will always have a value of 0 if the protocol for the 
      IMA group is proprietary."
::= { mscLpImaLkStatsEntry 5 }

mscLpImaLkFarEndUnusableSec OBJECT-TYPE
   SYNTAX     Counter32 
   ACCESS     read-only
   STATUS     mandatory
   DESCRIPTION
     "This attribute counts the number of one second intervals during 
      which the 'Tx/Rx Unusable' condition has been received from the 
      far end.
      This attribute will always have a value of 0 if the protocol for the 
      IMA group is proprietary."
::= { mscLpImaLkStatsEntry 6 }

mscLpImaLkFarEndSevErroredSec OBJECT-TYPE
   SYNTAX     Counter32 
   ACCESS     read-only
   STATUS     mandatory
   DESCRIPTION
     "This attribute counts the number of one second intervals containing 
      one or more RDI defects. This attribute will not increment during 
      FEUAS (Far-End Unavailable Second) conditions.
      This attribute will always have a value of 0 if the protocol for the 
      IMA group is proprietary."
::= { mscLpImaLkStatsEntry 7 }

mscLpImaLkFarEndUnavailSec OBJECT-TYPE
   SYNTAX     Counter32 
   ACCESS     read-only
   STATUS     mandatory
   DESCRIPTION
     "This attribute counts the number of unavailable seconds at the far 
      end. Unavailability begins at the start of 10 contiguous severely 
      errored seconds (SES) at the far end and ends at the start of 10 
      contiguous seconds at the far end with no SES.
      This attribute will always have a value of 0 if the protocol for the 
      IMA group is proprietary."
::= { mscLpImaLkStatsEntry 8 }

mscLpImaLkIcpViolations OBJECT-TYPE
   SYNTAX     Counter32 
   ACCESS     read-only
   STATUS     mandatory
   DESCRIPTION
     "This attribute counts the number of errored, invalid or missing IMA 
      Control Protocol (ICP) cells during non-SES (Severely Errored 
      Second) and non-UAS (Unavailable Seconds) conditions.
      This attribute will always have a value of 0 if the protocol for the 
      IMA group is proprietary."
::= { mscLpImaLkStatsEntry 9 }

mscLpImaLkTxStuffEvents OBJECT-TYPE
   SYNTAX     Counter32 
   ACCESS     read-only
   STATUS     mandatory
   DESCRIPTION
     "This attribute counts the number of Stuff events transmitted during 
      non-SES (Severely Errored Second) and non-UAS (Unavailable 
      Seconds) conditions.
      This attribute will always have a value of 0 if the protocol for the 
      IMA group is proprietary."
::= { mscLpImaLkStatsEntry 10 }

mscLpImaLkRxStuffEvents OBJECT-TYPE
   SYNTAX     Counter32 
   ACCESS     read-only
   STATUS     mandatory
   DESCRIPTION
     "This attribute counts the number of Stuff events received during 
      non-SES (Severely Errored Second) and non-UAS (Unavailable 
      Seconds) conditions.
      This attribute will always have a value of 0 if the protocol for the 
      IMA group is proprietary."
::= { mscLpImaLkStatsEntry 11 }

mscLpImaLkIdleCellSec OBJECT-TYPE
   SYNTAX     Counter32 
   ACCESS     read-only
   STATUS     mandatory
   DESCRIPTION
     "This attributes counts the number of one second intervals during 
      which one or more idle cells was received. The reception of idle 
      cells is an abnormal condition which could be caused by the remote 
      IMA using the Common Transmit Clock mode with ports whose 
      clock sources are not synchronized.
      This attribute will always have a value of 0 if the protocol for the 
      IMA group is proprietary."
::= { mscLpImaLkStatsEntry 12 }

mscLpImaLkStateTable OBJECT-TYPE
   SYNTAX     SEQUENCE OF MscLpImaLkStateEntry
   ACCESS     not-accessible
   STATUS     mandatory
   DESCRIPTION
     "This group contains the three OSI State attributes and the six OSI 
      Status attributes. The descriptions generically indicate what each 
      attribute implies about the component. Note that not all the values 
      and state combinations described here are supported by every 
      component which uses this group. For component-specific 
      information and the valid state combinations, refer to NTP 241-
      7001-150, Passport Operations and Maintenance Guide."
::= { mscLpImaLk 13 }

mscLpImaLkStateEntry OBJECT-TYPE
   SYNTAX     MscLpImaLkStateEntry
   ACCESS     not-accessible
   STATUS     mandatory
   DESCRIPTION
     "An entry in the mscLpImaLkStateTable."
   INDEX {
      mscLpIndex,
      mscLpImaIndex,
      mscLpImaLkIndex }
::= { mscLpImaLkStateTable 1 }

MscLpImaLkStateEntry ::= SEQUENCE {
   mscLpImaLkAdminState
      INTEGER,
   mscLpImaLkOperationalState
      INTEGER,
   mscLpImaLkUsageState
      INTEGER,
   mscLpImaLkAvailabilityStatus
      OCTET STRING,
   mscLpImaLkProceduralStatus
      OCTET STRING,
   mscLpImaLkControlStatus
      OCTET STRING,
   mscLpImaLkAlarmStatus
      OCTET STRING,
   mscLpImaLkStandbyStatus
      INTEGER,
   mscLpImaLkUnknownStatus
      INTEGER }

mscLpImaLkAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component.
      
      The OSI Status attributes, if supported by the component, may 
      provide more details, qualifying the state of the component."
   DEFVAL     { unlocked }
::= { mscLpImaLkStateEntry 1 }

mscLpImaLkOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle.
      
      The OSI Status attributes, if supported by the component, may 
      provide more details, qualifying the state of the component."
   DEFVAL     { disabled }
::= { mscLpImaLkStateEntry 2 }

mscLpImaLkUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time.
      
      The OSI Status attributes, if supported by the component, may 
      provide more details, qualifying the state of the component."
   DEFVAL     { idle }
::= { mscLpImaLkStateEntry 3 }

mscLpImaLkAvailabilityStatus OBJECT-TYPE
   SYNTAX     OCTET STRING (SIZE (2))
   ACCESS     read-only
   STATUS     mandatory
   DESCRIPTION
     "If supported by the component, this attribute indicates the OSI 
      Availability status of the component. Note that, even though it is 
      defined as a multi-valued set, at most one value is shown to the user.
      
      When no values are in the set, this indicates that either the attribute 
      is not supported or that none of the status conditions described 
      below are present.
      
      The value inTest indicates that the resource is undergoing a test 
      procedure. If adminState is locked or shuttingDown, the normal 
      users are precluded from using the resource and controlStatus is 
      reservedForTest. Tests that do not exclude additional users can be 
      present in any operational or administrative state but the 
      reservedForTest condition should not be present.
      
      The value failed indicates that the component has an internal fault 
      that prevents it from operating. The operationalState is disabled.
      
      The value dependency indicates that the component cannot operate 
      because some other resource on which it depends is unavailable. 
      The operationalState is disabled.
      
      The value powerOff indicates the resource requires power to be 
      applied and it is not powered on. The operationalState is disabled.
      
      The value offLine indicates the resource requires a routine 
      operation (either manual, automatic, or both) to be performed to 
      place it on-line and make it available for use. The operationalState 
      is disabled.
      
      The value offDuty indicates the resource is inactive in accordance 
      with a predetermined time schedule. In the absence of other 
      disabling conditions, the operationalState is enabled or disabled.
      
      The value degraded indicates the service provided by the 
      component is degraded in some way, such as in speed or operating 
      capacity. However, the resource remains available for service. The 
      operationalState is enabled.
      
      The value notInstalled indicates the resource is not present. The 
      operationalState is disabled.
      
      The value logFull is not used.

      Description of bits:
      inTest(0)
      failed(1)
      powerOff(2)
      offLine(3)
      offDuty(4)
      dependency(5)
      degraded(6)
      notInstalled(7)
      logFull(8)"
::= { mscLpImaLkStateEntry 4 }

mscLpImaLkProceduralStatus OBJECT-TYPE
   SYNTAX     OCTET STRING (SIZE (1))
   ACCESS     read-only
   STATUS     mandatory
   DESCRIPTION
     "If supported by the component, this attribute indicates the OSI 
      Procedural status of the component. Note that, even though it is 
      defined as a multi-valued set, at most one value is shown to the user.
      
      When no values are in the set, this indicates that either the attribute 
      is not supported or that none of the status conditions described 
      below are present.
      
      The value initializationRequired indicates (for a resource which 
      doesn't initialize autonomously) that initialization is required before 
      it can perform its normal functions, and this procedure has not been 
      initiated. The operationalState is disabled.
      
      The value notInitialized indicates (for a resource which does 
      initialize autonomously) that initialization is required before it can 
      perform its normal functions, and this procedure has not been 
      initiated. The operationalState may be enabled or disabled.
      
      The value initializing indicates that initialization has been initiated 
      but is not yet complete. The operationalState may be enabled or 
      disabled.
      
      The value reporting indicates the resource has completed some 
      processing operation and is notifying the results. The 
      operationalState is enabled.
      
      The value terminating indicates the component is in a termination 
      phase. If the resource doesn't reinitialize autonomously, 
      operationalState is disabled; otherwise it is enabled or disabled.

      Description of bits:
      initializationRequired(0)
      notInitialized(1)
      initializing(2)
      reporting(3)
      terminating(4)"
::= { mscLpImaLkStateEntry 5 }

mscLpImaLkControlStatus OBJECT-TYPE
   SYNTAX     OCTET STRING (SIZE (1))
   ACCESS     read-only
   STATUS     mandatory
   DESCRIPTION
     "If supported by the component, this attribute indicates the OSI 
      Control status of the component. Note that, even though it is defined 
      as a multi-valued set, at most one value is shown to the user.
      
      When no values are in the set, this indicates that either the attribute 
      is not supported or that none of the status conditions described 
      below are present.
      
      The value subjectToTest indicates the resource is available but tests 
      may be conducted simultaneously at unpredictable times, which 
      may cause it to exhibit unusual characteristics.
      
      The value partOfServicesLocked indicates that part of the service is 
      restricted from users of a resource. The adminState is unlocked.
      
      The value reservedForTest indicates that the component is 
      administratively unavailable because it is undergoing a test 
      procedure. The adminState is locked.
      
      The value suspended indicates that the service has been 
      administratively suspended.

      Description of bits:
      subjectToTest(0)
      partOfServicesLocked(1)
      reservedForTest(2)
      suspended(3)"
::= { mscLpImaLkStateEntry 6 }

mscLpImaLkAlarmStatus OBJECT-TYPE
   SYNTAX     OCTET STRING (SIZE (1))
   ACCESS     read-only
   STATUS     mandatory
   DESCRIPTION
     "If supported by the component, this attribute indicates the OSI 
      Alarm status of the component. Note that, even though it is defined 
      as a multi-valued set, at most one value is shown to the user.
      
      When no values are in the set, this indicates that either the attribute 
      is not supported or that none of the status conditions described 
      below are present.
      
      The value underRepair indicates the component is currently being 
      repaired. The operationalState is enabled or disabled.
      
      The value critical indicates one or more critical alarms are 
      outstanding against the component. Other, less severe, alarms may 
      also be outstanding. The operationalState is enabled or disabled.
      
      The value major indicates one or more major alarms are 
      outstanding against the component. Other, less severe, alarms may 
      also be outstanding. The operationalState is enabled or disabled.
      
      The value minor indicates one or more minor alarms are 
      outstanding against the component. Other, less severe, alarms may 
      also be outstanding. The operationalState is enabled or disabled.
      
      The value alarmOutstanding generically indicates that an alarm of 
      some severity is outstanding against the component.

      Description of bits:
      underRepair(0)
      critical(1)
      major(2)
      minor(3)
      alarmOutstanding(4)"
::= { mscLpImaLkStateEntry 7 }

mscLpImaLkStandbyStatus OBJECT-TYPE
   SYNTAX     INTEGER  {
                 hotStandby(0),
                 coldStandby(1),
                 providingService(2),
                 notSet(15) }
   ACCESS     read-only
   STATUS     mandatory
   DESCRIPTION
     "If supported by the component, this attribute indicates the OSI 
      Standby status of the component.
      
      The value notSet indicates that either the attribute is not supported 
      or that none of the status conditions described below are present. 
      Note that this is a non-standard value, used because the original 
      specification indicated this attribute was set-valued and thus, did not 
      provide a value to indicate that none of the other three are 
      applicable.
      
      The value hotStandby indicates that the resource is not providing 
      service but will be immediately able to take over the role of the 
      resource to be backed up, without initialization activity, and 
      containing the same information as the resource to be backed up.
      
      The value coldStandby indicates the resource is a backup for 
      another resource but will not be immediately able to take over the 
      role of the backed up resource and will require some initialization 
      activity.
      
      The value providingService indicates that this component, as a 
      backup resource, is currently backing up another resource."
   DEFVAL     { notSet }
::= { mscLpImaLkStateEntry 8 }

mscLpImaLkUnknownStatus OBJECT-TYPE
   SYNTAX     INTEGER  {
                 false(0),
                 true(1) }
   ACCESS     read-only
   STATUS     mandatory
   DESCRIPTION
     "This attribute indicates the OSI Unknown status of the component.
      
      The value false indicates that all of the other OSI State and Status 
      attribute values can be considered accurate.
      
      The value true indicates that the actual state of the component is not 
      known for sure."
   DEFVAL     { false }
::= { mscLpImaLkStateEntry 9 }




-- 
-- Version and Compliance statements
-- 



-- Object-Group Statement:
-- A list of all current accessible leaf objects.

-- OBJECTS { mscLpImaTestTimeRemaining,
--           mscLpImaLkIdleCellSec,
--           mscLpImaLkRowStatus,
--           mscLpImaUnavailSecs,
--           mscLpDS3ImaFailureCause,
--           mscLpDS3ImaLkFailures,
--           mscLpImaLkFarEndUnusableSec,
--           mscLpImaTestOperationalState,
--           mscLpDS3ImaLkComponentName,
--           mscLpDS3ImaRunningTime,
--           mscLpDS3ImaLkLastOifCause,
--           mscLpDS3ImaTestOperationalState,
--           mscLpImaTestBytesTx,
--           mscLpDS3ImaRemoteLidsConfig,
--           mscLpImaLkSevErroredSec,
--           mscLpImaRunningTime,
--           mscLpImaTestFrmTx,
--           mscLpDS3ImaTestComponentName,
--           mscLpDS3ImaTestDisplayInterval,
--           mscLpDS3ImaRemoteGid,
--           mscLpDS3ImaTestFrmPatternType,
--           mscLpImaUnknownStatus,
--           mscLpImaStandbyStatus,
--           mscLpImaLkFarEndSevErroredSec,
--           mscLpImaLkUsageState,
--           mscLpImaProtocol,
--           mscLpImaStorageType,
--           mscLpImaLkRemoteLid,
--           mscLpDS3ImaRemoteDefect,
--           mscLpImaLinkRetryTimeout,
--           mscLpDS3ImaUsageState,
--           mscLpDS3ImaTestBitErrorRate,
--           mscLpDS3ImaLkUnavailSecs,
--           mscLpImaLkInterfaceName,
--           mscLpImaControlStatus,
--           mscLpDS3ImaTestFrmTx,
--           mscLpDS3ImaTestErroredFrmRx,
--           mscLpImaTestBytesRx,
--           mscLpImaLkOperationalState,
--           mscLpDS3ImaFailures,
--           mscLpImaAdminState,
--           mscLpImaTestFrmRx,
--           mscLpImaRemoteLidsActive,
--           mscLpImaLkTxStuffEvents,
--           mscLpDS3ImaComponentName,
--           mscLpDS3ImaLkRxStuffEvents,
--           mscLpDS3ImaLinkSelectionCriterion,
--           mscLpImaApplicationFramerName,
--           mscLpDS3ImaLkFarEndUnavailSec,
--           mscLpImaTestDataStartDelay,
--           mscLpImaTestDuration,
--           mscLpImaTestPurpose,
--           mscLpDS3ImaLkUnknownStatus,
--           mscLpDS3ImaTestCauseOfTermination,
--           mscLpDS3ImaTestPurpose,
--           mscLpImaLkAlarmStatus,
--           mscLpDS3ImaTestTimeRemaining,
--           mscLpDS3ImaTransmitCellUtilization,
--           mscLpImaReceiveCellUtilization,
--           mscLpImaLkStorageType,
--           mscLpDS3ImaTestType,
--           mscLpDS3ImaProceduralStatus,
--           mscLpImaUsageState,
--           mscLpImaCustomerIdentifier,
--           mscLpDS3ImaClockingModeMismatch,
--           mscLpImaTestBitsTx,
--           mscLpImaTransmitClockMode,
--           mscLpDS3ImaUnavailSecs,
--           mscLpDS3ImaLkFarEndSevErroredSec,
--           mscLpImaTestStorageType,
--           mscLpDS3ImaTestAdminState,
--           mscLpDS3ImaLkControlStatus,
--           mscLpDS3ImaLkAdminState,
--           mscLpImaLkFailureCause,
--           mscLpImaOperationalState,
--           mscLpDS3ImaTestBytesTx,
--           mscLpDS3ImaTestRowStatus,
--           mscLpImaCellCapacity,
--           mscLpDS3ImaLkRowStatus,
--           mscLpImaLkRunningTime,
--           mscLpImaRemoteGid,
--           mscLpDS3ImaLkUnusableSec,
--           mscLpImaTestFrmSize,
--           mscLpImaLkIcpViolations,
--           mscLpImaTestRowStatus,
--           mscLpDS3ImaTestCustomizedPattern,
--           mscLpImaLkStandbyStatus,
--           mscLpDS3ImaUnknownStatus,
--           mscLpDS3ImaStandbyStatus,
--           mscLpImaTestElapsedTime,
--           mscLpDS3ImaLkUsageState,
--           mscLpDS3ImaProtocol,
--           mscLpDS3ImaStorageType,
--           mscLpDS3ImaLkRemoteLid,
--           mscLpImaLkControlStatus,
--           mscLpDS3ImaLkFarEndUnusableSec,
--           mscLpDS3ImaLinkRetryTimeout,
--           mscLpDS3ImaLkSevErroredSec,
--           mscLpDS3ImaTestFrmRx,
--           mscLpDS3ImaReceiveCellUtilization,
--           mscLpImaLkRemoteDefect,
--           mscLpDS3ImaLkInterfaceName,
--           mscLpImaTestCauseOfTermination,
--           mscLpImaLkProceduralStatus,
--           mscLpImaAlarmStatus,
--           mscLpImaTestUsageState,
--           mscLpDS3ImaTestBytesRx,
--           mscLpDS3ImaLkOperationalState,
--           mscLpDS3ImaControlStatus,
--           mscLpDS3ImaAdminState,
--           mscLpImaFailureCause,
--           mscLpDS3ImaRemoteLidsActive,
--           mscLpImaLkLastOifCause,
--           mscLpImaLkFailures,
--           mscLpDS3ImaApplicationFramerName,
--           mscLpDS3ImaRowStatus,
--           mscLpImaRowStatus,
--           mscLpDS3ImaTestDuration,
--           mscLpImaTestComponentName,
--           mscLpImaLkComponentName,
--           mscLpDS3ImaLkTxStuffEvents,
--           mscLpImaTestCustomizedPattern,
--           mscLpImaRemoteLidsConfig,
--           mscLpImaLkAdminState,
--           mscLpImaAvailabilityStatus,
--           mscLpImaRemoteDefect,
--           mscLpDS3ImaLkRelativeDelay,
--           mscLpImaTestDisplayInterval,
--           mscLpDS3ImaLkAvailabilityStatus,
--           mscLpImaTestFrmPatternType,
--           mscLpImaLkUnavailSecs,
--           mscLpDS3ImaTestBitsTx,
--           mscLpDS3ImaTransmitClockMode,
--           mscLpDS3ImaLkAlarmStatus,
--           mscLpDS3ImaTestDataStartDelay,
--           mscLpDS3ImaTestStorageType,
--           mscLpDS3ImaCellCapacity,
--           mscLpImaProceduralStatus,
--           mscLpDS3ImaLkFailureCause,
--           mscLpDS3ImaOperationalState,
--           mscLpDS3ImaMaxDiffDelay,
--           mscLpImaLkRelativeDelay,
--           mscLpImaTestErroredFrmRx,
--           mscLpDS3ImaLkStorageType,
--           mscLpDS3ImaLkRunningTime,
--           mscLpImaFailures,
--           mscLpDS3ImaLkStandbyStatus,
--           mscLpDS3ImaTestFrmSize,
--           mscLpImaMaxDiffDelay,
--           mscLpImaComponentName,
--           mscLpImaLkRxStuffEvents,
--           mscLpImaLinkSelectionCriterion,
--           mscLpImaLkFarEndUnavailSec,
--           mscLpDS3ImaTestElapsedTime,
--           mscLpImaTestBitErrorRate,
--           mscLpDS3ImaTestBitsRx,
--           mscLpImaLkUnknownStatus,
--           mscLpDS3ImaLkIcpViolations,
--           mscLpDS3ImaCustomerIdentifier,
--           mscLpDS3ImaLkIdleCellSec,
--           mscLpImaTestBitsRx,
--           mscLpDS3ImaAvailabilityStatus,
--           mscLpImaTransmitCellUtilization,
--           mscLpDS3ImaLkRemoteDefect,
--           mscLpImaTestType,
--           mscLpImaLkAvailabilityStatus,
--           mscLpImaLkUnusableSec,
--           mscLpImaTestAdminState,
--           mscLpDS3ImaLkProceduralStatus,
--           mscLpDS3ImaAlarmStatus,
--           mscLpDS3ImaTestUsageState,
--           mscLpImaClockingModeMismatch }
-- STATUS  mandatory
-- DESCRIPTION
--   "A list of all current accessible leaf objects."

imaGroup OBJECT IDENTIFIER ::= { imaMIB 1 }
imaGroupCA OBJECT IDENTIFIER ::= { imaGroup 1 }
imaGroupCA02 OBJECT IDENTIFIER ::= { imaGroupCA 3 }
imaGroupCA02A OBJECT IDENTIFIER ::= { imaGroupCA02 2 }



-- Agent-Capabilities Statement:

-- PRODUCT-RELEASE "MscPassport Release 1.2 Ima."
-- STATUS          mandatory
-- DESCRIPTION     "Carrier Passport Ima MIB: MIB Version CA02A,
--                  Software Version CA02S9C."
-- SUPPORTS        Nortel-MsCarrier-MscPassport-ImaMIB
--    INCLUDES     { imaGroupCA02A }

imaCapabilities OBJECT IDENTIFIER ::= { imaMIB 3 }
imaCapabilitiesCA OBJECT IDENTIFIER ::= { imaCapabilities 1 }
imaCapabilitiesCA02 OBJECT IDENTIFIER ::= { imaCapabilitiesCA 3 }
imaCapabilitiesCA02A OBJECT IDENTIFIER ::= { imaCapabilitiesCA02 2 }





END
