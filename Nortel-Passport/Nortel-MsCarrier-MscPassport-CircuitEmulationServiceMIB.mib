Nortel-MsCarrier-MscPassport-CircuitEmulationServiceMIB
DEFINITIONS ::= BEGIN



IMPORTS

      OBJECT-TYPE
   FROM RFC-1212

      mscPassportMIBs,
      mscComponents
   FROM Nortel-MsCarrier-MscPassport-UsefulDefinitionsMIB

      Counter32,
      RowPointer,
      DisplayString,
      StorageType,
      RowStatus,
      Gauge32,
      Integer32,
      Unsigned32
   FROM Nortel-MsCarrier-MscPassport-StandardTextualConventionsMIB

      AsciiString,
      Hex,
      NonReplicated,
      EnterpriseDateAndTime,
      PassportCounter64,
      Link,
      IntegerSequence,
      FixedPoint2
   FROM Nortel-MsCarrier-MscPassport-TextualConventionsMIB;




-- LAST-UPDATED   "9909010000Z"
-- ORGANIZATION   "Nortel Networks"
-- CONTACT-INFO   "
--         Nortel Carrier Data Network Management
--         
--         Postal:       P.O. Box 3511, Station C 
--                       Ottawa, Ontario 
--                       Canada  K1Y 4H7
--         
--         via the WEB:  http://www.nortelnetworks.com  
--                       select 'Contact Us' from the menu
--          
--         via phone:    1-800-4NORTEL"
-- DESCRIPTION
--    "The module describing the Nortel MsCarrier MscPassport
--     CircuitEmulationService Enterprise MIB."

circuitEmulationServiceMIB OBJECT IDENTIFIER ::= { mscPassportMIBs 55 }










-- Aal11CircuitEmulationService/n
-- 
-- An Aal1Ces component identifies an instance of the AAL1 Circuit 
-- Emulation Service provided by Passport.
-- 
-- A separate instance of this component is required for each logical 
-- channel of a port which is offering a constant bit rate service to a 
-- customer.
-- 
-- Instance numbers, which are used to uniquely identify Aal1Ces 
-- component instances, are arbitrary.

mscAal1Ces OBJECT IDENTIFIER ::= { mscComponents 119 }



mscAal1CesRowStatusTable OBJECT-TYPE
   SYNTAX     SEQUENCE OF MscAal1CesRowStatusEntry
   ACCESS     not-accessible
   STATUS     mandatory
   DESCRIPTION
     "This entry controls the addition and deletion of 
      mscAal1Ces components."
::= { mscAal1Ces 1 }

mscAal1CesRowStatusEntry OBJECT-TYPE
   SYNTAX     MscAal1CesRowStatusEntry
   ACCESS     not-accessible
   STATUS     mandatory
   DESCRIPTION
     "A single entry in the table represents a single 
      mscAal1Ces component."
   INDEX {
      mscAal1CesIndex }
::= { mscAal1CesRowStatusTable 1 }

MscAal1CesRowStatusEntry ::= SEQUENCE {
   mscAal1CesRowStatus
      RowStatus,
   mscAal1CesComponentName
      DisplayString,
   mscAal1CesStorageType
      StorageType,
   mscAal1CesIndex
      Integer32 }

mscAal1CesRowStatus OBJECT-TYPE
   SYNTAX     RowStatus 
   ACCESS     read-write
   STATUS     mandatory
   DESCRIPTION
     "This variable is used as the basis for SNMP naming of
      mscAal1Ces components.
      These components can be added and deleted."
::= { mscAal1CesRowStatusEntry 1 }

mscAal1CesComponentName OBJECT-TYPE
   SYNTAX     DisplayString 
   ACCESS     read-only
   STATUS     mandatory
   DESCRIPTION
     "This variable provides the component's string name for
      use with the ASCII Console Interface"
::= { mscAal1CesRowStatusEntry 2 }

mscAal1CesStorageType OBJECT-TYPE
   SYNTAX     StorageType 
   ACCESS     read-only
   STATUS     mandatory
   DESCRIPTION
     "This variable represents the storage type value for the
      mscAal1Ces tables."
::= { mscAal1CesRowStatusEntry 4 }

mscAal1CesIndex OBJECT-TYPE
   SYNTAX     Integer32 (1..16383)
   ACCESS     not-accessible
   STATUS     mandatory
   DESCRIPTION
     "This variable represents the index for the mscAal1Ces tables."
::= { mscAal1CesRowStatusEntry 10 }

mscAal1CesCidDataTable OBJECT-TYPE
   SYNTAX     SEQUENCE OF MscAal1CesCidDataEntry
   ACCESS     not-accessible
   STATUS     mandatory
   DESCRIPTION
     "This group contains the attribute for a component's Customer 
      Identifier (CID). Refer to the attribute description for a detailed 
      explanation of CIDs."
::= { mscAal1Ces 10 }

mscAal1CesCidDataEntry OBJECT-TYPE
   SYNTAX     MscAal1CesCidDataEntry
   ACCESS     not-accessible
   STATUS     mandatory
   DESCRIPTION
     "An entry in the mscAal1CesCidDataTable."
   INDEX {
      mscAal1CesIndex }
::= { mscAal1CesCidDataTable 1 }

MscAal1CesCidDataEntry ::= SEQUENCE {
   mscAal1CesCustomerIdentifier
      Unsigned32 }

mscAal1CesCustomerIdentifier OBJECT-TYPE
   SYNTAX     Unsigned32 (0 | 1..8191)
   ACCESS     read-write
   STATUS     mandatory
   DESCRIPTION
     "This attribute holds the Customer Identifier (CID).
      
      Every component has a CID. If a component has a cid attribute, the 
      component's CID is the provisioned value of that attribute; 
      otherwise the component inherits the CID of its parent. The top-
      level component has a CID of 0.
      
      Every operator session also has a CID, which is the CID 
      provisioned for the operator's user ID. An operator will see only the 
      stream data for components having a matching CID. Also, the 
      operator will be allowed to issue commands for only those 
      components which have a matching CID.
      
      An operator CID of 0 is used to identify the Network Manager 
      (referred to as 'NetMan' in DPN). This CID matches the CID of 
      any component. Values 1 to 8191 inclusive (equivalent to 'basic 
      CIDs' in DPN) may be assigned to specific customers."
   DEFVAL     { 0 }
::= { mscAal1CesCidDataEntry 1 }

mscAal1CesProvTable OBJECT-TYPE
   SYNTAX     SEQUENCE OF MscAal1CesProvEntry
   ACCESS     not-accessible
   STATUS     mandatory
   DESCRIPTION
     "This group contains basic provisioning data for the AAL1 Circuit 
      Emulation Service."
::= { mscAal1Ces 11 }

mscAal1CesProvEntry OBJECT-TYPE
   SYNTAX     MscAal1CesProvEntry
   ACCESS     not-accessible
   STATUS     mandatory
   DESCRIPTION
     "An entry in the mscAal1CesProvTable."
   INDEX {
      mscAal1CesIndex }
::= { mscAal1CesProvTable 1 }

MscAal1CesProvEntry ::= SEQUENCE {
   mscAal1CesServiceType
      INTEGER,
   mscAal1CesBufferSize
      Unsigned32,
   mscAal1CesCellLossIntegrationPeriod
      Unsigned32,
   mscAal1CesInterfaceName
      Link,
   mscAal1CesPartialFill
      Unsigned32,
   mscAal1CesIdleSuppression
      INTEGER,
   mscAal1CesIdlePattern
      Hex,
   mscAal1CesCellLossRecoveryPeriod
      Unsigned32,
   mscAal1CesDummyDataByte
      Hex,
   mscAal1CesMaximumBufferDelay
      FixedPoint2,
   mscAal1CesDp2CellDelayVariationTolerance
      FixedPoint2 }

mscAal1CesServiceType OBJECT-TYPE
   SYNTAX     INTEGER  {
                 unstructured(0),
                 basicStructured(1),
                 casStructured(2) }
   ACCESS     read-write
   STATUS     mandatory
   DESCRIPTION
     "This attribute specifies the service type for the CES.
      
      In an unstructured service, the entire data stream at the service 
      interface (including any framing bits which may be present) is 
      passed across the network transparently.
      
      The unstructured service uses the Unstructured Data Transfer 
      (UDT) mode of AAL1.
      
      In a structured service, an Nx64kbit/s fraction of the data stream at 
      the service interface is passed across the network. Two modes of 
      structured service are supported: basicStructured and casStructured. 
      In a casStructured service, the Channel Associated Signalling 
      (CAS) bits are carried in a separate data structure from the Nx64 
      payload; in a basicStructured service they are not.
      
      The structured service uses the Structured Data Transfer (SDT) 
      mode as defined in ITU-T Recommendation I.363.1.
      
      The serviceType attributes at both ends of a connection must be the 
      same."
   DEFVAL     { unstructured }
::= { mscAal1CesProvEntry 1 }

mscAal1CesBufferSize OBJECT-TYPE
   SYNTAX     Unsigned32 (0 | 94..15651)
   ACCESS     read-write
   STATUS     mandatory
   DESCRIPTION
     "On 4pDS1Aal1 and 4pE1Aal1 cards, this attribute specifies the size 
      of the AAL1 receive segment reassembly buffer in bytes. On 
      initialization the buffer is filled to a level determined by 
      cellDelayVariationTolerance. Thereafter the buffer is emptied as 
      TDM frames are transmitted, and is filled as ATM cells are 
      received. If the buffer overflows, sufficient data is discarded to bring 
      the level down to that set after initialization. The cause of a buffer 
      overflow may be one or a combination of any of the following: cell-
      arrival-jitter, initialization with delayed ATM cells, or TDM clock 
      difference or wander. 
      
      On 4pDS1Aal1 and 4pE1Aal1 cards, if this attribute is 
      autoConfigure, the buffer size applied is equivalent to two times 
      cellDelayVariationTolerance. A provisioned numeric value of 
      bufferSize must be higher than the equivalent 
      cellDelayVariationTolerance, plus an allowance of one ATM Cell 
      for the quantization of data in cells, and an allowance, if applicable, 
      for the ATM overheads of structured CES.
      
      On MSA cards this attribute's value must be autoConfigure, to 
      acknowledge that maximumBufferDelay is provisioned instead of 
      this attribute.
      
      Setting this attribute too low allows traffic with normal CDV to 
      cause unnecessary loss of data on the service interface. Setting this 
      attribute too high permits the buffer to introduce an unnecessarily 
      high propagation delay.

      VALUES (

      0 = autoConfigure

      )"
   DEFVAL     { 0 }
::= { mscAal1CesProvEntry 2 }

mscAal1CesCellLossIntegrationPeriod OBJECT-TYPE
   SYNTAX     Unsigned32 (1000..60000)
   ACCESS     read-write
   STATUS     mandatory
   DESCRIPTION
     "This attribute specifies the cell loss integration period. This period 
      defines the interval of time (in milliseconds) for which a loss of 
      cells condition must persist before a buffer underflow alarm is 
      raised. A loss of cells condition occurs when the flow of cells to the 
      AAL1 reassembly buffer stops, causing a buffer underflow or 
      starvation condition.
      
      The operational attribute cellLossStatus will be set to loss when the 
      buffer underflow alarm is raised, and noLoss when it is cleared."
   DEFVAL     { 2000 }
::= { mscAal1CesProvEntry 4 }

mscAal1CesInterfaceName OBJECT-TYPE
   SYNTAX     Link 
   ACCESS     read-write
   STATUS     mandatory
   DESCRIPTION
     "This attribute identifies the instance of Chan to which an instance of 
      Aal1Ces is linked."
::= { mscAal1CesProvEntry 5 }

mscAal1CesPartialFill OBJECT-TYPE
   SYNTAX     Unsigned32 (8..47)
   ACCESS     read-write
   STATUS     mandatory
   DESCRIPTION
     "A significant source of delay in a structured service is the amount of 
      time it takes to collect enough data to fill a cell. This period of time 
      can be reduced by sending cells that are only partially filled with 
      data (idlePattern octets are added to the ATM payload beyond the 
      partial fill level).
      
      This attribute specifies the number of payload octets to fill with 
      data. It is applicable to structured services only, and must be set to 
      47 for unstructured services.
      
      On a given AAL1 Function Processor, the maximum cell rate that 
      can be sustained is dependent upon the combined bandwidths of the 
      provisioned services, and (for structured services) the levels of 
      partialFill. The smaller the partialFill level, the greater the cell rate 
      and hence the fewer the services that can be sustained at that fill 
      level."
   DEFVAL     { 47 }
::= { mscAal1CesProvEntry 6 }

mscAal1CesIdleSuppression OBJECT-TYPE
   SYNTAX     INTEGER  {
                 off(0),
                 on(1) }
   ACCESS     read-write
   STATUS     mandatory
   DESCRIPTION
     "This attribute controls the suppression of idle cells. An idle cell is 
      one in which the bytes of the ATM payload (up to the partialFill 
      level) match the idlePattern.
      
      If idleSuppression is off, idle cells are not suppressed.
      
      If idleSuppression is on, at least 75% of cells are suppressed under 
      idle conditions.
      
      The strategy is as follows: the first idle cell after a sequence of non-
      idle cells is always sent; those that follow are suppressed. Note, 
      however, that at least one cell in eight is always sent (to allow the 
      receive end to regenerate the suppressed cells) and more often than 
      not, two cells are sent (the cell containing the AAL1 pointer, which 
      will almost always fail to match, and the one after that)."
   DEFVAL     { off }
::= { mscAal1CesProvEntry 7 }

mscAal1CesIdlePattern OBJECT-TYPE
   SYNTAX     Hex (0..255)
   ACCESS     read-write
   STATUS     mandatory
   DESCRIPTION
     "This attribute specifies the pattern which the bytes of an ATM 
      payload, up to the partialFill level, must match in order for the cell 
      to be classified as idle. Payload bytes beyond the partialFill level 
      are not checked.
      
      The suppression of idle cells is controlled by the attribute 
      idleSuppression. If idleSuppression is on, at least 75% of cells are 
      suppressed under idle conditions."
   DEFVAL     { 126 }
::= { mscAal1CesProvEntry 8 }

mscAal1CesCellLossRecoveryPeriod OBJECT-TYPE
   SYNTAX     Unsigned32 (0..60)
   ACCESS     read-write
   STATUS     mandatory
   DESCRIPTION
     "This attribute specifies the cell loss recovery period. This period 
      defines the interval of time (in seconds) for which a loss of cells 
      condition must desist before the buffer underflow alarm is cleared.
      
      The operational attribute cellLossStatus will be set to noLoss when 
      the buffer underflow alarm is cleared."
   DEFVAL     { 20 }
::= { mscAal1CesProvEntry 9 }

mscAal1CesDummyDataByte OBJECT-TYPE
   SYNTAX     Hex (0..255)
   ACCESS     read-write
   STATUS     mandatory
   DESCRIPTION
     "This attribute specifies the pattern which is played out onto the 
      service interface to maintain bit integrity when data is unavailable 
      from the ATM network.
      
      For an unstructured service (serviceType is set to unstructured), 
      dummyDataByte must be set to FF."
   DEFVAL     { 255 }
::= { mscAal1CesProvEntry 10 }

mscAal1CesMaximumBufferDelay OBJECT-TYPE
   SYNTAX     FixedPoint2 (0 | 1..65500)
   ACCESS     read-write
   STATUS     mandatory
   DESCRIPTION
     "This attribute specifies the maximum delay that a Cell Delay 
      Variation buffer is permitted to add to the egress stream. The delay 
      in the buffer is modified in response to variation in the egress cell 
      stream. At the point that the delay would be modified in excess of 
      the maximum, sufficient data is discarded that the delay returns to 
      cellDelayVariationTolerance.
      
      Setting this attribute too low allows traffic with normal CDV to 
      cause unnecessary loss of data on the service interface. Setting this 
      attribute too high permits the buffer to introduce an unnecessarily 
      high propagation delay.
      
      If this attribute is autoConfigure, the maximum delay tolerated in 
      the buffer is two times cellDelayVariationTolerance. On MSA 
      cards, 'best-effort' applies on a channel with high 
      cellDelayVariationTolerance and low ATM bandwidth. The value 
      applied is the same as the range limit on provisioned 
      maximumBufferDelay on that channel.
      
      On MSA cards this attribute's value is rounded up to the nearest 
      multiple of 0.125ms when applied to the buffer. The range is 
      nominally 0.12..63.62ms, but the upper limit may be reduced by up 
      to 6ms one a channel with high cellDelayVariationTolerance and 
      low ATM bandwidth.
      
      On 4pDS1Aal1 and 4pE1Aal1 cards this attribute's value is rounded 
      up to the nearest multiple of 1ms when applied to the buffer. The 
      upper limit is roughly inverse- proportional to the ATM bandwidth 
      of the channel.

      VALUES (

      0 = autoConfigure

      )"
   DEFVAL     { 0 }
::= { mscAal1CesProvEntry 11 }

mscAal1CesDp2CellDelayVariationTolerance OBJECT-TYPE
   SYNTAX     FixedPoint2 (1..65500)
   ACCESS     read-write
   STATUS     mandatory
   DESCRIPTION
     "This attribute specifies the maximum time that a cell may arrive 
      late, compared to a nominal time established at buffer initialization, 
      without producing errors on the service interface. The nominal time 
      of a cell's arrival is predicted according to the time interval required 
      to transmit a cell's worth of data on the service interface.
      
      This attribute's value is the delay that the Cell Delay Variation 
      Tolerance buffer adds to the egress stream immediately after the 
      buffer initializes. The buffer absorbs variation in the arrival time of 
      cells from the network, so that a steady stream of data appears on 
      the service interface. If the buffer underflows, due to a late cell, fill-
      in data is output on the service interface while the buffer re-
      initializes. When the buffer has re-initialized, normal data is output 
      on the service interface and the delay in the buffer is restored to the 
      value of this attribute.
      
      This attribute must have a value lower than a numeric value of 
      maximumBufferDelay. The relationship between this attribute and 
      bufferSize is described under that attribute.
      
      Setting this attribute too low allows traffic with normal CDV to 
      cause unnecessary loss of data on the service interface. Setting this 
      attribute too high imposes an unnecessarily high propagation delay 
      on the egress stream.
      
      On MSA cards this attribute's provisionable range is 0.01..32ms and 
      the value applied is rounded up to the nearest multiple of 0.125ms.
      
      On 4pDS1Aal1 and 4pE1Aal1 cards, this attribute's provisionable 
      range is strongly dependent on the bandwidth of the channel, and 
      the value applied is rounded up to the nearest whole number of 
      milliseconds, then rounded down to the equivalent number of cells."
   DEFVAL     { 100 }
::= { mscAal1CesProvEntry 12 }

mscAal1CesStateTable OBJECT-TYPE
   SYNTAX     SEQUENCE OF MscAal1CesStateEntry
   ACCESS     not-accessible
   STATUS     mandatory
   DESCRIPTION
     "This group contains the three OSI State attributes and the six OSI 
      Status attributes. The descriptions generically indicate what each 
      attribute implies about the component. Note that not all the values 
      and state combinations described here are supported by every 
      component which uses this group. For component-specific 
      information and the valid state combinations, refer to NTP 241-
      7001-150, Passport Operations and Maintenance Guide."
::= { mscAal1Ces 12 }

mscAal1CesStateEntry OBJECT-TYPE
   SYNTAX     MscAal1CesStateEntry
   ACCESS     not-accessible
   STATUS     mandatory
   DESCRIPTION
     "An entry in the mscAal1CesStateTable."
   INDEX {
      mscAal1CesIndex }
::= { mscAal1CesStateTable 1 }

MscAal1CesStateEntry ::= SEQUENCE {
   mscAal1CesAdminState
      INTEGER,
   mscAal1CesOperationalState
      INTEGER,
   mscAal1CesUsageState
      INTEGER,
   mscAal1CesAvailabilityStatus
      OCTET STRING,
   mscAal1CesProceduralStatus
      OCTET STRING,
   mscAal1CesControlStatus
      OCTET STRING,
   mscAal1CesAlarmStatus
      OCTET STRING,
   mscAal1CesStandbyStatus
      INTEGER,
   mscAal1CesUnknownStatus
      INTEGER }

mscAal1CesAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component.
      
      The OSI Status attributes, if supported by the component, may 
      provide more details, qualifying the state of the component."
   DEFVAL     { unlocked }
::= { mscAal1CesStateEntry 1 }

mscAal1CesOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle.
      
      The OSI Status attributes, if supported by the component, may 
      provide more details, qualifying the state of the component."
   DEFVAL     { disabled }
::= { mscAal1CesStateEntry 2 }

mscAal1CesUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time.
      
      The OSI Status attributes, if supported by the component, may 
      provide more details, qualifying the state of the component."
   DEFVAL     { idle }
::= { mscAal1CesStateEntry 3 }

mscAal1CesAvailabilityStatus OBJECT-TYPE
   SYNTAX     OCTET STRING (SIZE (2))
   ACCESS     read-only
   STATUS     mandatory
   DESCRIPTION
     "If supported by the component, this attribute indicates the OSI 
      Availability status of the component. Note that, even though it is 
      defined as a multi-valued set, at most one value is shown to the user.
      
      When no values are in the set, this indicates that either the attribute 
      is not supported or that none of the status conditions described 
      below are present.
      
      The value inTest indicates that the resource is undergoing a test 
      procedure. If adminState is locked or shuttingDown, the normal 
      users are precluded from using the resource and controlStatus is 
      reservedForTest. Tests that do not exclude additional users can be 
      present in any operational or administrative state but the 
      reservedForTest condition should not be present.
      
      The value failed indicates that the component has an internal fault 
      that prevents it from operating. The operationalState is disabled.
      
      The value dependency indicates that the component cannot operate 
      because some other resource on which it depends is unavailable. 
      The operationalState is disabled.
      
      The value powerOff indicates the resource requires power to be 
      applied and it is not powered on. The operationalState is disabled.
      
      The value offLine indicates the resource requires a routine 
      operation (either manual, automatic, or both) to be performed to 
      place it on-line and make it available for use. The operationalState 
      is disabled.
      
      The value offDuty indicates the resource is inactive in accordance 
      with a predetermined time schedule. In the absence of other 
      disabling conditions, the operationalState is enabled or disabled.
      
      The value degraded indicates the service provided by the 
      component is degraded in some way, such as in speed or operating 
      capacity. However, the resource remains available for service. The 
      operationalState is enabled.
      
      The value notInstalled indicates the resource is not present. The 
      operationalState is disabled.
      
      The value logFull is not used.

      Description of bits:
      inTest(0)
      failed(1)
      powerOff(2)
      offLine(3)
      offDuty(4)
      dependency(5)
      degraded(6)
      notInstalled(7)
      logFull(8)"
::= { mscAal1CesStateEntry 4 }

mscAal1CesProceduralStatus OBJECT-TYPE
   SYNTAX     OCTET STRING (SIZE (1))
   ACCESS     read-only
   STATUS     mandatory
   DESCRIPTION
     "If supported by the component, this attribute indicates the OSI 
      Procedural status of the component. Note that, even though it is 
      defined as a multi-valued set, at most one value is shown to the user.
      
      When no values are in the set, this indicates that either the attribute 
      is not supported or that none of the status conditions described 
      below are present.
      
      The value initializationRequired indicates (for a resource which 
      doesn't initialize autonomously) that initialization is required before 
      it can perform its normal functions, and this procedure has not been 
      initiated. The operationalState is disabled.
      
      The value notInitialized indicates (for a resource which does 
      initialize autonomously) that initialization is required before it can 
      perform its normal functions, and this procedure has not been 
      initiated. The operationalState may be enabled or disabled.
      
      The value initializing indicates that initialization has been initiated 
      but is not yet complete. The operationalState may be enabled or 
      disabled.
      
      The value reporting indicates the resource has completed some 
      processing operation and is notifying the results. The 
      operationalState is enabled.
      
      The value terminating indicates the component is in a termination 
      phase. If the resource doesn't reinitialize autonomously, 
      operationalState is disabled; otherwise it is enabled or disabled.

      Description of bits:
      initializationRequired(0)
      notInitialized(1)
      initializing(2)
      reporting(3)
      terminating(4)"
::= { mscAal1CesStateEntry 5 }

mscAal1CesControlStatus OBJECT-TYPE
   SYNTAX     OCTET STRING (SIZE (1))
   ACCESS     read-only
   STATUS     mandatory
   DESCRIPTION
     "If supported by the component, this attribute indicates the OSI 
      Control status of the component. Note that, even though it is defined 
      as a multi-valued set, at most one value is shown to the user.
      
      When no values are in the set, this indicates that either the attribute 
      is not supported or that none of the status conditions described 
      below are present.
      
      The value subjectToTest indicates the resource is available but tests 
      may be conducted simultaneously at unpredictable times, which 
      may cause it to exhibit unusual characteristics.
      
      The value partOfServicesLocked indicates that part of the service is 
      restricted from users of a resource. The adminState is unlocked.
      
      The value reservedForTest indicates that the component is 
      administratively unavailable because it is undergoing a test 
      procedure. The adminState is locked.
      
      The value suspended indicates that the service has been 
      administratively suspended.

      Description of bits:
      subjectToTest(0)
      partOfServicesLocked(1)
      reservedForTest(2)
      suspended(3)"
::= { mscAal1CesStateEntry 6 }

mscAal1CesAlarmStatus OBJECT-TYPE
   SYNTAX     OCTET STRING (SIZE (1))
   ACCESS     read-only
   STATUS     mandatory
   DESCRIPTION
     "If supported by the component, this attribute indicates the OSI 
      Alarm status of the component. Note that, even though it is defined 
      as a multi-valued set, at most one value is shown to the user.
      
      When no values are in the set, this indicates that either the attribute 
      is not supported or that none of the status conditions described 
      below are present.
      
      The value underRepair indicates the component is currently being 
      repaired. The operationalState is enabled or disabled.
      
      The value critical indicates one or more critical alarms are 
      outstanding against the component. Other, less severe, alarms may 
      also be outstanding. The operationalState is enabled or disabled.
      
      The value major indicates one or more major alarms are 
      outstanding against the component. Other, less severe, alarms may 
      also be outstanding. The operationalState is enabled or disabled.
      
      The value minor indicates one or more minor alarms are 
      outstanding against the component. Other, less severe, alarms may 
      also be outstanding. The operationalState is enabled or disabled.
      
      The value alarmOutstanding generically indicates that an alarm of 
      some severity is outstanding against the component.

      Description of bits:
      underRepair(0)
      critical(1)
      major(2)
      minor(3)
      alarmOutstanding(4)"
::= { mscAal1CesStateEntry 7 }

mscAal1CesStandbyStatus OBJECT-TYPE
   SYNTAX     INTEGER  {
                 hotStandby(0),
                 coldStandby(1),
                 providingService(2),
                 notSet(15) }
   ACCESS     read-only
   STATUS     mandatory
   DESCRIPTION
     "If supported by the component, this attribute indicates the OSI 
      Standby status of the component.
      
      The value notSet indicates that either the attribute is not supported 
      or that none of the status conditions described below are present. 
      Note that this is a non-standard value, used because the original 
      specification indicated this attribute was set-valued and thus, did not 
      provide a value to indicate that none of the other three are 
      applicable.
      
      The value hotStandby indicates that the resource is not providing 
      service but will be immediately able to take over the role of the 
      resource to be backed up, without initialization activity, and 
      containing the same information as the resource to be backed up.
      
      The value coldStandby indicates the resource is a backup for 
      another resource but will not be immediately able to take over the 
      role of the backed up resource and will require some initialization 
      activity.
      
      The value providingService indicates that this component, as a 
      backup resource, is currently backing up another resource."
   DEFVAL     { notSet }
::= { mscAal1CesStateEntry 8 }

mscAal1CesUnknownStatus OBJECT-TYPE
   SYNTAX     INTEGER  {
                 false(0),
                 true(1) }
   ACCESS     read-only
   STATUS     mandatory
   DESCRIPTION
     "This attribute indicates the OSI Unknown status of the component.
      
      The value false indicates that all of the other OSI State and Status 
      attribute values can be considered accurate.
      
      The value true indicates that the actual state of the component is not 
      known for sure."
   DEFVAL     { false }
::= { mscAal1CesStateEntry 9 }

mscAal1CesOperTable OBJECT-TYPE
   SYNTAX     SEQUENCE OF MscAal1CesOperEntry
   ACCESS     not-accessible
   STATUS     mandatory
   DESCRIPTION
     "This group contains status information about the AAL1 Circuit 
      Emulation Service."
::= { mscAal1Ces 13 }

mscAal1CesOperEntry OBJECT-TYPE
   SYNTAX     MscAal1CesOperEntry
   ACCESS     not-accessible
   STATUS     mandatory
   DESCRIPTION
     "An entry in the mscAal1CesOperTable."
   INDEX {
      mscAal1CesIndex }
::= { mscAal1CesOperTable 1 }

MscAal1CesOperEntry ::= SEQUENCE {
   mscAal1CesCellLossStatus
      INTEGER,
   mscAal1CesAal1LayerLossStatus
      INTEGER,
   mscAal1CesConnectionStatus
      INTEGER }

mscAal1CesCellLossStatus OBJECT-TYPE
   SYNTAX     INTEGER  {
                 noLoss(0),
                 loss(1) }
   ACCESS     read-only
   STATUS     mandatory
   DESCRIPTION
     "This attribute is set to loss when a buffer underflow alarm is raised 
      (see cellLossIntegrationPeriod), and noLoss when it is clear."
   DEFVAL     { noLoss }
::= { mscAal1CesOperEntry 1 }

mscAal1CesAal1LayerLossStatus OBJECT-TYPE
   SYNTAX     INTEGER  {
                 noLoss(0),
                 loss(1) }
   ACCESS     read-only
   STATUS     mandatory
   DESCRIPTION
     "This attribute is set to loss when an AAL1 layer alarm is raised, and 
      noLoss when it is clear."
   DEFVAL     { noLoss }
::= { mscAal1CesOperEntry 2 }

mscAal1CesConnectionStatus OBJECT-TYPE
   SYNTAX     INTEGER  {
                 connected(0),
                 channelNotReady(1),
                 atmNotReady(2),
                 atmNotConfigured(3) }
   ACCESS     read-only
   STATUS     mandatory
   DESCRIPTION
     "This attribute indicates whether a service is non-operational because 
      of a problem with the service interface side of the service (in which 
      case, it is set to channelNotReady) or because of a problem with the 
      ATM side of the service (in which case, it is set to 
      atmNotConfigured or atmNotReady).
      
      When this attribute is set to channelNotReady, it is an indication 
      that the corresponding Chan component (as defined by the attribute 
      interfaceName) or the Chan component's parent port component 
      (Lp/n Ds1/m or Lp/n E1/m) is locked.
      
      When this attribute is set to atmNotConfigured, it is an indication 
      that no sub-component has been provisioned, and thus no ATM 
      connection has been configured for the service.
      
      When this attribute is set to atmNotReady, it is an indication that the 
      ATM connection with which the service is associated (as defined by 
      a sub-component) has been lost or that it is currently unable to carry 
      CES data.
      
      This attribute is set to connected when a service is operational (that 
      is, the OSI attribute operationalState is enabled.)"
   DEFVAL     { channelNotReady }
::= { mscAal1CesOperEntry 3 }

mscAal1CesStatsTable OBJECT-TYPE
   SYNTAX     SEQUENCE OF MscAal1CesStatsEntry
   ACCESS     not-accessible
   STATUS     mandatory
   DESCRIPTION
     "This group contains statistical data for an AAL1 Circuit Emulation 
      Service."
::= { mscAal1Ces 14 }

mscAal1CesStatsEntry OBJECT-TYPE
   SYNTAX     MscAal1CesStatsEntry
   ACCESS     not-accessible
   STATUS     mandatory
   DESCRIPTION
     "An entry in the mscAal1CesStatsTable."
   INDEX {
      mscAal1CesIndex }
::= { mscAal1CesStatsTable 1 }

MscAal1CesStatsEntry ::= SEQUENCE {
   mscAal1CesCellsTransmitted
      PassportCounter64,
   mscAal1CesCellsReceived
      PassportCounter64,
   mscAal1CesLostCells
      Counter32,
   mscAal1CesBufferUnderflows
      Counter32,
   mscAal1CesBufferOverflows
      Counter32,
   mscAal1CesReassembledCells
      PassportCounter64,
   mscAal1CesHeaderErrors
      Counter32,
   mscAal1CesPointerReframes
      Counter32,
   mscAal1CesPointerParityErrors
      Counter32,
   mscAal1CesAal1SequenceErrors
      Counter32,
   mscAal1CesMisinsertedCells
      Counter32 }

mscAal1CesCellsTransmitted OBJECT-TYPE
   SYNTAX     PassportCounter64 
   ACCESS     read-only
   STATUS     mandatory
   DESCRIPTION
     "This attribute counts the total number of cells transmitted to the 
      backplane (ingress direction). This includes cells containing CBR 
      data, trunk conditioning cells (structured services), and unframed 
      AIS cells (unstructured services).
      
      The counter wraps when the maximum value is exceeded."
::= { mscAal1CesStatsEntry 1 }

mscAal1CesCellsReceived OBJECT-TYPE
   SYNTAX     PassportCounter64 
   ACCESS     read-only
   STATUS     mandatory
   DESCRIPTION
     "This attribute counts the total number of cells received from the 
      backplane (egress direction). This includes CBR user data cells, 
      cells with AAL1 header errors (correctable and non-correctable) 
      and cells with AAL1 sequencing errors. The counter wraps when 
      the maximum value is exceeded."
::= { mscAal1CesStatsEntry 2 }

mscAal1CesLostCells OBJECT-TYPE
   SYNTAX     Counter32 
   ACCESS     read-only
   STATUS     mandatory
   DESCRIPTION
     "This attribute counts the number of cells declared as never received 
      by the AAL1 protocol layer. The counter wraps when the maximum 
      value is exceeded."
::= { mscAal1CesStatsEntry 3 }

mscAal1CesBufferUnderflows OBJECT-TYPE
   SYNTAX     Counter32 
   ACCESS     read-only
   STATUS     mandatory
   DESCRIPTION
     "This attribute counts the number of times the AAL1 reassembly 
      buffer underflows. In the case of a continuous buffer starvation, a 
      single buffer underflow event will be counted. The counter wraps 
      when the maximum value is exceeded."
::= { mscAal1CesStatsEntry 4 }

mscAal1CesBufferOverflows OBJECT-TYPE
   SYNTAX     Counter32 
   ACCESS     read-only
   STATUS     mandatory
   DESCRIPTION
     "This attribute counts the number of times the AAL1 reassembly 
      buffer overflows. Buffer overflows occur when AAL1 cells arrive at 
      a rate above that which is expected. Occurrences of this condition 
      may be reduced by increasing the value of the attribute bufferSize or 
      maximumBufferDelay. The buffer overflow counter wraps when the 
      maximum value is exceeded."
::= { mscAal1CesStatsEntry 5 }

mscAal1CesReassembledCells OBJECT-TYPE
   SYNTAX     PassportCounter64 
   ACCESS     read-only
   STATUS     mandatory
   DESCRIPTION
     "This attribute counts the number of received cells whose payload 
      has been played out to the service interface. The counter wraps 
      when the maximum value is exceeded."
::= { mscAal1CesStatsEntry 6 }

mscAal1CesHeaderErrors OBJECT-TYPE
   SYNTAX     Counter32 
   ACCESS     read-only
   STATUS     mandatory
   DESCRIPTION
     "This attribute counts the number of cells received with AAL1 
      header errors. The counter wraps when the maximum value is 
      exceeded."
::= { mscAal1CesStatsEntry 7 }

mscAal1CesPointerReframes OBJECT-TYPE
   SYNTAX     Counter32 
   ACCESS     read-only
   STATUS     mandatory
   DESCRIPTION
     "This attribute counts the number of times that the AAL1 reassembly 
      unit found an SDT pointer where it was not expected to be, and as a 
      result had to reacquire it. Errors of this kind can occur because of 
      problems at the far end.
      
      This attribute is meaningful for structured services only, and will be 
      0 for unstructured services.
      
      This counter wraps when the maximum value is exceeded."
::= { mscAal1CesStatsEntry 8 }

mscAal1CesPointerParityErrors OBJECT-TYPE
   SYNTAX     Counter32 
   ACCESS     read-only
   STATUS     mandatory
   DESCRIPTION
     "This attribute counts the number of times that the AAL1 reassembly 
      unit detects a parity check failure at the point where an SDT pointer 
      is expected. Errors of this kind can occur because of problems at the 
      far end.
      
      This attribute is meaningful for structured services only, and will be 
      0 for unstructured services.
      
      This counter wraps when the maximum value is exceeded."
::= { mscAal1CesStatsEntry 9 }

mscAal1CesAal1SequenceErrors OBJECT-TYPE
   SYNTAX     Counter32 
   ACCESS     read-only
   STATUS     mandatory
   DESCRIPTION
     "This attribute counts the number of times that the sequence number 
      of an incoming AAL1 Type 1 SAR-PDU gets out of 
      synchronisation, as defined by ITU-T Recommendation I.363.1.
      
      This counter wraps when the maximum value is exceeded."
::= { mscAal1CesStatsEntry 10 }

mscAal1CesMisinsertedCells OBJECT-TYPE
   SYNTAX     Counter32 
   ACCESS     read-only
   STATUS     mandatory
   DESCRIPTION
     "This attribute counts the number of AAL1 sequence violations 
      which the AAL convergence sublayer interprets as misinserted 
      cells, as defined by ITU-T I.363.1.
      
      This counter wraps when the maximum value is exceeded."
::= { mscAal1CesStatsEntry 11 }


-- Aal1Ces/n NailedUpAdaptationPoint
-- 
-- A NailedUpAdaptationPoint is a nailed-up point which straddles 
-- the CBR/ATM domains and which is associated with the adaptation 
-- of CBR data to/from ATM cells.
-- 
-- If a NailedUpAdaptationPoint component is provisioned under an 
-- Aal1Ces component, no other components may be provisioned 
-- under the same Aal1Ces component.

mscAal1CesNap OBJECT IDENTIFIER ::= { mscAal1Ces 2 }



mscAal1CesNapRowStatusTable OBJECT-TYPE
   SYNTAX     SEQUENCE OF MscAal1CesNapRowStatusEntry
   ACCESS     not-accessible
   STATUS     mandatory
   DESCRIPTION
     "This entry controls the addition and deletion of 
      mscAal1CesNap components."
::= { mscAal1CesNap 1 }

mscAal1CesNapRowStatusEntry OBJECT-TYPE
   SYNTAX     MscAal1CesNapRowStatusEntry
   ACCESS     not-accessible
   STATUS     mandatory
   DESCRIPTION
     "A single entry in the table represents a single 
      mscAal1CesNap component."
   INDEX {
      mscAal1CesIndex,
      mscAal1CesNapIndex }
::= { mscAal1CesNapRowStatusTable 1 }

MscAal1CesNapRowStatusEntry ::= SEQUENCE {
   mscAal1CesNapRowStatus
      RowStatus,
   mscAal1CesNapComponentName
      DisplayString,
   mscAal1CesNapStorageType
      StorageType,
   mscAal1CesNapIndex
      NonReplicated }

mscAal1CesNapRowStatus OBJECT-TYPE
   SYNTAX     RowStatus 
   ACCESS     read-write
   STATUS     mandatory
   DESCRIPTION
     "This variable is used as the basis for SNMP naming of
      mscAal1CesNap components.
      These components can be added and deleted."
::= { mscAal1CesNapRowStatusEntry 1 }

mscAal1CesNapComponentName OBJECT-TYPE
   SYNTAX     DisplayString 
   ACCESS     read-only
   STATUS     mandatory
   DESCRIPTION
     "This variable provides the component's string name for
      use with the ASCII Console Interface"
::= { mscAal1CesNapRowStatusEntry 2 }

mscAal1CesNapStorageType OBJECT-TYPE
   SYNTAX     StorageType 
   ACCESS     read-only
   STATUS     mandatory
   DESCRIPTION
     "This variable represents the storage type value for the
      mscAal1CesNap tables."
::= { mscAal1CesNapRowStatusEntry 4 }

mscAal1CesNapIndex OBJECT-TYPE
   SYNTAX     NonReplicated 
   ACCESS     not-accessible
   STATUS     mandatory
   DESCRIPTION
     "This variable represents the index for the mscAal1CesNap tables."
::= { mscAal1CesNapRowStatusEntry 10 }

mscAal1CesNapProvTable OBJECT-TYPE
   SYNTAX     SEQUENCE OF MscAal1CesNapProvEntry
   ACCESS     not-accessible
   STATUS     mandatory
   DESCRIPTION
     "This group contains the provisioning data for the 
      NailedUpAdaptationPoint component."
::= { mscAal1CesNap 10 }

mscAal1CesNapProvEntry OBJECT-TYPE
   SYNTAX     MscAal1CesNapProvEntry
   ACCESS     not-accessible
   STATUS     mandatory
   DESCRIPTION
     "An entry in the mscAal1CesNapProvTable."
   INDEX {
      mscAal1CesIndex,
      mscAal1CesNapIndex }
::= { mscAal1CesNapProvTable 1 }

MscAal1CesNapProvEntry ::= SEQUENCE {
   mscAal1CesNapAtmConnection
      Link }

mscAal1CesNapAtmConnection OBJECT-TYPE
   SYNTAX     Link 
   ACCESS     read-write
   STATUS     mandatory
   DESCRIPTION
     "This attribute specifies the identity of the component to which the 
      NailedUpAdaptationPoint is linked. This is an AtmIf Vcc 
      NailedUpEndPoint or an AtmIf Vpt Vcc NailedUpEndPoint (the 
      AAL1 cells are transported off the switch over an ATM UNI, where 
      they are routed to the appropriate AAL1 entity at the other end by 
      the ATM bearer service)."
::= { mscAal1CesNapProvEntry 1 }


-- Aal1Ces/n ActiveEndPoint
-- 
-- The ActiveEndPoint component attempts to set up a switched 
-- virtual circuit automatically between two Passport CES 
-- components.
-- 
-- The ActiveEndPoint component will make connection setup 
-- attempts periodically whenever a connection has not been 
-- established. The component will cease connection setup attempts 
-- after a number of consecutive failed attempts, as specified by the 
-- retryLimit attribute.
-- 
-- The ActiveEndPoint component may also accept an incoming setup 
-- request if a connection is not already established. To be accepted, an 
-- incoming connection setup request must have originated from 
-- remoteAddress. Additionally, either connection attempts must have 
-- been ceased due to retryLimit consecutive failures, or the 
-- localAddress of the incoming connection setup request must be 
-- smaller than the remoteAddress of the request.
-- 
-- If an ActiveEndPoint component is provisioned under an Aal1Ces 
-- component, no other components may be provisioned under the 
-- same Aal1Ces component.

mscAal1CesAep OBJECT IDENTIFIER ::= { mscAal1Ces 3 }



mscAal1CesAepRowStatusTable OBJECT-TYPE
   SYNTAX     SEQUENCE OF MscAal1CesAepRowStatusEntry
   ACCESS     not-accessible
   STATUS     mandatory
   DESCRIPTION
     "This entry controls the addition and deletion of 
      mscAal1CesAep components."
::= { mscAal1CesAep 1 }

mscAal1CesAepRowStatusEntry OBJECT-TYPE
   SYNTAX     MscAal1CesAepRowStatusEntry
   ACCESS     not-accessible
   STATUS     mandatory
   DESCRIPTION
     "A single entry in the table represents a single 
      mscAal1CesAep component."
   INDEX {
      mscAal1CesIndex,
      mscAal1CesAepIndex }
::= { mscAal1CesAepRowStatusTable 1 }

MscAal1CesAepRowStatusEntry ::= SEQUENCE {
   mscAal1CesAepRowStatus
      RowStatus,
   mscAal1CesAepComponentName
      DisplayString,
   mscAal1CesAepStorageType
      StorageType,
   mscAal1CesAepIndex
      NonReplicated }

mscAal1CesAepRowStatus OBJECT-TYPE
   SYNTAX     RowStatus 
   ACCESS     read-write
   STATUS     mandatory
   DESCRIPTION
     "This variable is used as the basis for SNMP naming of
      mscAal1CesAep components.
      These components can be added and deleted."
::= { mscAal1CesAepRowStatusEntry 1 }

mscAal1CesAepComponentName OBJECT-TYPE
   SYNTAX     DisplayString 
   ACCESS     read-only
   STATUS     mandatory
   DESCRIPTION
     "This variable provides the component's string name for
      use with the ASCII Console Interface"
::= { mscAal1CesAepRowStatusEntry 2 }

mscAal1CesAepStorageType OBJECT-TYPE
   SYNTAX     StorageType 
   ACCESS     read-only
   STATUS     mandatory
   DESCRIPTION
     "This variable represents the storage type value for the
      mscAal1CesAep tables."
::= { mscAal1CesAepRowStatusEntry 4 }

mscAal1CesAepIndex OBJECT-TYPE
   SYNTAX     NonReplicated 
   ACCESS     not-accessible
   STATUS     mandatory
   DESCRIPTION
     "This variable represents the index for the mscAal1CesAep tables."
::= { mscAal1CesAepRowStatusEntry 10 }

mscAal1CesAepProvEndPointAddrTable OBJECT-TYPE
   SYNTAX     SEQUENCE OF MscAal1CesAepProvEndPointAddrEntry
   ACCESS     not-accessible
   STATUS     mandatory
   DESCRIPTION
     "This group contains NSAP address provisioning data for 
      components using switched virtual circuits."
::= { mscAal1CesAep 10 }

mscAal1CesAepProvEndPointAddrEntry OBJECT-TYPE
   SYNTAX     MscAal1CesAepProvEndPointAddrEntry
   ACCESS     not-accessible
   STATUS     mandatory
   DESCRIPTION
     "An entry in the mscAal1CesAepProvEndPointAddrTable."
   INDEX {
      mscAal1CesIndex,
      mscAal1CesAepIndex }
::= { mscAal1CesAepProvEndPointAddrTable 1 }

MscAal1CesAepProvEndPointAddrEntry ::= SEQUENCE {
   mscAal1CesAepExpectedRemoteAddress
      AsciiString,
   mscAal1CesAepLocalAddress
      AsciiString }

mscAal1CesAepExpectedRemoteAddress OBJECT-TYPE
   SYNTAX     AsciiString (SIZE (0..40))
   ACCESS     read-write
   STATUS     mandatory
   DESCRIPTION
     "This attribute specifies the expected remote address prefix for an 
      incoming connection setup request.
      
      If expectedRemoteAddress is not empty, only matching connections 
      will be considered for acceptance. If expectedRemoteAddress is 40 
      characters long, the remote address must match exactly to be 
      accepted. If expectedRemoteAddress is less than 40 characters long, 
      the remote address must begin with expectedRemoteAddress to be 
      accepted.
      
      If expectedRemoteAddress is empty, the component will process 
      connection requests from any remote address."
   DEFVAL     { ''H }  -- ""
::= { mscAal1CesAepProvEndPointAddrEntry 1 }

mscAal1CesAepLocalAddress OBJECT-TYPE
   SYNTAX     AsciiString (SIZE (40))
   ACCESS     read-write
   STATUS     mandatory
   DESCRIPTION
     "This attribute specifies the local NSAP address.
      
      If the switch prefix (the nodePrefix attribute of the ModuleData 
      component) has been provisioned, a default value for localAddress 
      based on nodePrefix will be provided.
      
      If ModuleData nodePrefix has not been provisioned and one or 
      more alternate switch prefixes (the alternatePorsPrefixes attribute 
      of the ModuleData component) have been provisioned, a default 
      value for localAddress based on the first provisioned 
      alternatePorsPrefix value will be provided.
      
      If no switch prefixes have been provisioned, localAddress will 
      default to an empty string. To obtain a valid default localAddress in 
      this case, either or both of the ModuleData nodePrefix and 
      ModuleData alternatePorsPrefixes attributes must be provisioned, 
      and this end point component must then be deleted and re-added."
::= { mscAal1CesAepProvEndPointAddrEntry 2 }

mscAal1CesAepProvTable OBJECT-TYPE
   SYNTAX     SEQUENCE OF MscAal1CesAepProvEntry
   ACCESS     not-accessible
   STATUS     mandatory
   DESCRIPTION
     "This group contains the provisioning data specific to the 
      ActiveEndPoint component."
::= { mscAal1CesAep 11 }

mscAal1CesAepProvEntry OBJECT-TYPE
   SYNTAX     MscAal1CesAepProvEntry
   ACCESS     not-accessible
   STATUS     mandatory
   DESCRIPTION
     "An entry in the mscAal1CesAepProvTable."
   INDEX {
      mscAal1CesIndex,
      mscAal1CesAepIndex }
::= { mscAal1CesAepProvTable 1 }

MscAal1CesAepProvEntry ::= SEQUENCE {
   mscAal1CesAepAddressToCall
      AsciiString,
   mscAal1CesAepRoutingOption
      INTEGER,
   mscAal1CesAepProfile
      Link,
   mscAal1CesAepFirstRetryInterval
      Unsigned32,
   mscAal1CesAepRetryLimit
      Unsigned32,
   mscAal1CesAepActiveEndPointType
      INTEGER,
   mscAal1CesAepCalledVpiVci
      IntegerSequence }

mscAal1CesAepAddressToCall OBJECT-TYPE
   SYNTAX     AsciiString (SIZE (40))
   ACCESS     read-write
   STATUS     mandatory
   DESCRIPTION
     "This attribute specifies the remote NSAP address which this 
      ActiveEndPoint will call."
::= { mscAal1CesAepProvEntry 1 }

mscAal1CesAepRoutingOption OBJECT-TYPE
   SYNTAX     INTEGER  {
                 porsOnly(0),
                 atmOnly(1),
                 porsFirst(2),
                 atmFirst(3) }
   ACCESS     read-write
   STATUS     mandatory
   DESCRIPTION
     "This attribute specifies the type of routing to use for establishing the 
      connection:
      
      AAL1 cards accept only porsOnly.
      Multi-Service Access cards accept all four options. 
      
      porsOnly means that only the Path Oriented Routing System may 
      be used in establishing a connection.
      
      atmOnly means that only the native ATM Routing may be used in 
      establishing a connection.
      
      porsFirst means that the switch tries to establish a connection using 
      the Path Oriented Routing System first, and, if the connection 
      cannot be established, it tries native ATM Routing instead.
      
      atmFirst means that the switch tries to establish a connection using 
      native ATM Routing first, and, if the connection cannot be 
      established, it tries the Path Oriented Routing System instead."
   DEFVAL     { porsOnly }
::= { mscAal1CesAepProvEntry 2 }

mscAal1CesAepProfile OBJECT-TYPE
   SYNTAX     Link 
   ACCESS     read-write
   STATUS     mandatory
   DESCRIPTION
     "This attribute specifies the PORS routing profile to use for this 
      connection.
      
      If profile is empty, PORS will provide a default profile."
::= { mscAal1CesAepProvEntry 3 }

mscAal1CesAepFirstRetryInterval OBJECT-TYPE
   SYNTAX     Unsigned32 (1..3600)
   ACCESS     read-write
   STATUS     mandatory
   DESCRIPTION
     "This attribute specifies the time to wait, in seconds, before 
      attempting to establish the connection after the first failed attempt.
      
      The time to wait between subsequent call attempts will generally 
      differ due to a backoff scheme."
   DEFVAL     { 10 }
::= { mscAal1CesAepProvEntry 4 }

mscAal1CesAepRetryLimit OBJECT-TYPE
   SYNTAX     Unsigned32 (0..65535)
   ACCESS     read-write
   STATUS     mandatory
   DESCRIPTION
     "retryLimit specifies the maximum number of consecutive 
      unsuccessful connection setup attempts that may be made before 
      further attempts are abandoned.
      
      If this limit is reached, the Restart verb may be used to restart 
      connection attempts.
      
      If retryLimit is 0, there is no limit; attempts will continue 
      indefinitely until a successful connection is established."
   DEFVAL     { 0 }
::= { mscAal1CesAepProvEntry 5 }

mscAal1CesAepActiveEndPointType OBJECT-TYPE
   SYNTAX     INTEGER  {
                 svc(0),
                 softPVC(1) }
   ACCESS     read-write
   STATUS     mandatory
   DESCRIPTION
     "activeEndPointType specifies the type of end point: svc or softPvc. 
      The default is svc.
      
      When activeEndPointType is svc, calledVpiVci is not relevant.
      When activeEndPointType is softPVC, routingOption must be 
      atmOnly, and profile, firstRetryInterval, and retryLimit are not 
      relevant."
   DEFVAL     { svc }
::= { mscAal1CesAepProvEntry 6 }

mscAal1CesAepCalledVpiVci OBJECT-TYPE
   SYNTAX     IntegerSequence (SIZE (3..10))
   ACCESS     read-write
   STATUS     mandatory
   DESCRIPTION
     "calledVpiVci specifies the identity of the PVC at the remote ATM 
      node on which the softPVC connection terminates. 
      
      calledVpiVci is relevant only when activeEndPointType is set to 
      softPVC. 
      
      The default value is 0.1"
::= { mscAal1CesAepProvEntry 7 }

mscAal1CesAepEpOperTable OBJECT-TYPE
   SYNTAX     SEQUENCE OF MscAal1CesAepEpOperEntry
   ACCESS     not-accessible
   STATUS     mandatory
   DESCRIPTION
     "This group contains general operational attributes for components 
      using switched virtual circuits."
::= { mscAal1CesAep 12 }

mscAal1CesAepEpOperEntry OBJECT-TYPE
   SYNTAX     MscAal1CesAepEpOperEntry
   ACCESS     not-accessible
   STATUS     mandatory
   DESCRIPTION
     "An entry in the mscAal1CesAepEpOperTable."
   INDEX {
      mscAal1CesIndex,
      mscAal1CesAepIndex }
::= { mscAal1CesAepEpOperTable 1 }

MscAal1CesAepEpOperEntry ::= SEQUENCE {
   mscAal1CesAepRemoteAddress
      AsciiString,
   mscAal1CesAepLastTearDownCause
      Unsigned32,
   mscAal1CesAepLastTearDownDiagnostic
      AsciiString }

mscAal1CesAepRemoteAddress OBJECT-TYPE
   SYNTAX     AsciiString (SIZE (7..40))
   ACCESS     read-only
   STATUS     mandatory
   DESCRIPTION
     "remoteAddress is the address of the remote end point.
      
      If a connection is currently established, remoteAddress will contain 
      the address of the remote end point.
      
      If a connection is not established, remoteAddress will be Unknown."
::= { mscAal1CesAepEpOperEntry 1 }

mscAal1CesAepLastTearDownCause OBJECT-TYPE
   SYNTAX     Unsigned32 (0..255)
   ACCESS     read-only
   STATUS     mandatory
   DESCRIPTION
     "lastTearDownCause indicates the cause of the last connection tear 
      down.
      
      The values are as defined in the ATM Forum ATM User-Network 
      Interface (UNI) Specification."
::= { mscAal1CesAepEpOperEntry 2 }

mscAal1CesAepLastTearDownDiagnostic OBJECT-TYPE
   SYNTAX     AsciiString (SIZE (0..8))
   ACCESS     read-only
   STATUS     mandatory
   DESCRIPTION
     "lastTearDownDiagnostic provides a diagnostic to supplement the 
      lastTearDownCause attribute."
::= { mscAal1CesAepEpOperEntry 3 }

mscAal1CesAepOutTable OBJECT-TYPE
   SYNTAX     SEQUENCE OF MscAal1CesAepOutEntry
   ACCESS     not-accessible
   STATUS     mandatory
   DESCRIPTION
     "This group contains status information about the AAL1 Circuit 
      Emulation Service ActiveEndPoint component."
::= { mscAal1CesAep 13 }

mscAal1CesAepOutEntry OBJECT-TYPE
   SYNTAX     MscAal1CesAepOutEntry
   ACCESS     not-accessible
   STATUS     mandatory
   DESCRIPTION
     "An entry in the mscAal1CesAepOutTable."
   INDEX {
      mscAal1CesIndex,
      mscAal1CesAepIndex }
::= { mscAal1CesAepOutTable 1 }

MscAal1CesAepOutEntry ::= SEQUENCE {
   mscAal1CesAepSvcStatus
      INTEGER,
   mscAal1CesAepLastSetupFailureCause
      Unsigned32,
   mscAal1CesAepLastSetupFailureDiagnostic
      AsciiString,
   mscAal1CesAepRetryTimeRemaining
      Counter32,
   mscAal1CesAepRetryFailures
      Counter32 }

mscAal1CesAepSvcStatus OBJECT-TYPE
   SYNTAX     INTEGER  {
                 initialising(0),
                 connecting(1),
                 connected(2),
                 idle(3),
                 retriesExhausted(4),
                 failed(5) }
   ACCESS     read-only
   STATUS     mandatory
   DESCRIPTION
     "svcStatus indicates the status of the incoming and outgoing 
      connections.
      
      When this attribute has the value initialising, it indicates that the 
      component is initialising when first created; a connection has not 
      been established, and no incoming setup requests will be processed.
      
      When this attribute has the value connecting, it indicates that a 
      connection has not yet been established, but that incoming setup 
      requests will be processed.
      
      When this attribute has the value connected, it indicates that a 
      connection has been established.
      
      When this attribute has the value retriesExhausted, it indicates that 
      retryLimit consecutive connection setup attempts have failed, and 
      the connection procedure has been aborted.
      
      When this attribute has the value idle, it indicates that a connection 
      has not been established, and that no incoming setup requests will 
      be processed.
      
      When this attribute has the value failed, it indicates that the 
      connections is in a state other than those described above."
::= { mscAal1CesAepOutEntry 1 }

mscAal1CesAepLastSetupFailureCause OBJECT-TYPE
   SYNTAX     Unsigned32 (0..255)
   ACCESS     read-only
   STATUS     mandatory
   DESCRIPTION
     "lastSetupFailureCause indicates the cause of the last connection 
      setup failure.
      
      The values are as defined in the ATM Forum ATM User-
      Network Interface (UNI) Specification."
::= { mscAal1CesAepOutEntry 2 }

mscAal1CesAepLastSetupFailureDiagnostic OBJECT-TYPE
   SYNTAX     AsciiString (SIZE (0..8))
   ACCESS     read-only
   STATUS     mandatory
   DESCRIPTION
     "lastSetupFailureDiagnostic provides a diagnostic to supplement the 
      lastSetupFailureCause attribute."
::= { mscAal1CesAepOutEntry 3 }

mscAal1CesAepRetryTimeRemaining OBJECT-TYPE
   SYNTAX     Counter32 
   ACCESS     read-only
   STATUS     mandatory
   DESCRIPTION
     "retryTimerValue is the current value of the retry timer for this 
      connection; it indicates the number of seconds before the next 
      connection attempt will be made. retryTimerValue is initialized 
      when a connection attempt fails.
      
      When retryTimerValue reaches 0, an attempt will be made to 
      establish the connection.
      
      When the timer is not running, for example when the connection 
      has been established, retryTimerValue will be 0."
::= { mscAal1CesAepOutEntry 4 }

mscAal1CesAepRetryFailures OBJECT-TYPE
   SYNTAX     Counter32 
   ACCESS     read-only
   STATUS     mandatory
   DESCRIPTION
     "retryFailures counts the number of consecutive failed connection 
      attempts.
      
      retryFailures is reset to 0 whenever a connection is successfully 
      established, or the connection is restarted using the Restart verb. 
      The counter wraps when the maximum value is exceeded."
::= { mscAal1CesAepOutEntry 5 }


-- Aal1Ces/n PassiveEndPoint
-- 
-- The PassiveEndPoint component provides a passive end point for a 
-- switched virtual connection between two applications.
-- 
-- A PassiveEndPoint awaits incoming connection setup requests. A 
-- setup request will only be accepted if a connection is not already 
-- established, and the request originated from 
-- expectedRemoteAddress.
-- 
-- If a PassiveEndPoint component is provisioned under an Aal1Ces 
-- component, no other components may be provisioned under the 
-- same Aal1Ces component.

mscAal1CesPep OBJECT IDENTIFIER ::= { mscAal1Ces 4 }



mscAal1CesPepRowStatusTable OBJECT-TYPE
   SYNTAX     SEQUENCE OF MscAal1CesPepRowStatusEntry
   ACCESS     not-accessible
   STATUS     mandatory
   DESCRIPTION
     "This entry controls the addition and deletion of 
      mscAal1CesPep components."
::= { mscAal1CesPep 1 }

mscAal1CesPepRowStatusEntry OBJECT-TYPE
   SYNTAX     MscAal1CesPepRowStatusEntry
   ACCESS     not-accessible
   STATUS     mandatory
   DESCRIPTION
     "A single entry in the table represents a single 
      mscAal1CesPep component."
   INDEX {
      mscAal1CesIndex,
      mscAal1CesPepIndex }
::= { mscAal1CesPepRowStatusTable 1 }

MscAal1CesPepRowStatusEntry ::= SEQUENCE {
   mscAal1CesPepRowStatus
      RowStatus,
   mscAal1CesPepComponentName
      DisplayString,
   mscAal1CesPepStorageType
      StorageType,
   mscAal1CesPepIndex
      NonReplicated }

mscAal1CesPepRowStatus OBJECT-TYPE
   SYNTAX     RowStatus 
   ACCESS     read-write
   STATUS     mandatory
   DESCRIPTION
     "This variable is used as the basis for SNMP naming of
      mscAal1CesPep components.
      These components can be added and deleted."
::= { mscAal1CesPepRowStatusEntry 1 }

mscAal1CesPepComponentName OBJECT-TYPE
   SYNTAX     DisplayString 
   ACCESS     read-only
   STATUS     mandatory
   DESCRIPTION
     "This variable provides the component's string name for
      use with the ASCII Console Interface"
::= { mscAal1CesPepRowStatusEntry 2 }

mscAal1CesPepStorageType OBJECT-TYPE
   SYNTAX     StorageType 
   ACCESS     read-only
   STATUS     mandatory
   DESCRIPTION
     "This variable represents the storage type value for the
      mscAal1CesPep tables."
::= { mscAal1CesPepRowStatusEntry 4 }

mscAal1CesPepIndex OBJECT-TYPE
   SYNTAX     NonReplicated 
   ACCESS     not-accessible
   STATUS     mandatory
   DESCRIPTION
     "This variable represents the index for the mscAal1CesPep tables."
::= { mscAal1CesPepRowStatusEntry 10 }

mscAal1CesPepProvEndPointAddrTable OBJECT-TYPE
   SYNTAX     SEQUENCE OF MscAal1CesPepProvEndPointAddrEntry
   ACCESS     not-accessible
   STATUS     mandatory
   DESCRIPTION
     "This group contains NSAP address provisioning data for 
      components using switched virtual circuits."
::= { mscAal1CesPep 10 }

mscAal1CesPepProvEndPointAddrEntry OBJECT-TYPE
   SYNTAX     MscAal1CesPepProvEndPointAddrEntry
   ACCESS     not-accessible
   STATUS     mandatory
   DESCRIPTION
     "An entry in the mscAal1CesPepProvEndPointAddrTable."
   INDEX {
      mscAal1CesIndex,
      mscAal1CesPepIndex }
::= { mscAal1CesPepProvEndPointAddrTable 1 }

MscAal1CesPepProvEndPointAddrEntry ::= SEQUENCE {
   mscAal1CesPepExpectedRemoteAddress
      AsciiString,
   mscAal1CesPepLocalAddress
      AsciiString }

mscAal1CesPepExpectedRemoteAddress OBJECT-TYPE
   SYNTAX     AsciiString (SIZE (0..40))
   ACCESS     read-write
   STATUS     mandatory
   DESCRIPTION
     "This attribute specifies the expected remote address prefix for an 
      incoming connection setup request.
      
      If expectedRemoteAddress is not empty, only matching connections 
      will be considered for acceptance. If expectedRemoteAddress is 40 
      characters long, the remote address must match exactly to be 
      accepted. If expectedRemoteAddress is less than 40 characters long, 
      the remote address must begin with expectedRemoteAddress to be 
      accepted.
      
      If expectedRemoteAddress is empty, the component will process 
      connection requests from any remote address."
   DEFVAL     { ''H }  -- ""
::= { mscAal1CesPepProvEndPointAddrEntry 1 }

mscAal1CesPepLocalAddress OBJECT-TYPE
   SYNTAX     AsciiString (SIZE (40))
   ACCESS     read-write
   STATUS     mandatory
   DESCRIPTION
     "This attribute specifies the local NSAP address.
      
      If the switch prefix (the nodePrefix attribute of the ModuleData 
      component) has been provisioned, a default value for localAddress 
      based on nodePrefix will be provided.
      
      If ModuleData nodePrefix has not been provisioned and one or 
      more alternate switch prefixes (the alternatePorsPrefixes attribute 
      of the ModuleData component) have been provisioned, a default 
      value for localAddress based on the first provisioned 
      alternatePorsPrefix value will be provided.
      
      If no switch prefixes have been provisioned, localAddress will 
      default to an empty string. To obtain a valid default localAddress in 
      this case, either or both of the ModuleData nodePrefix and 
      ModuleData alternatePorsPrefixes attributes must be provisioned, 
      and this end point component must then be deleted and re-added."
::= { mscAal1CesPepProvEndPointAddrEntry 2 }

mscAal1CesPepEpOperTable OBJECT-TYPE
   SYNTAX     SEQUENCE OF MscAal1CesPepEpOperEntry
   ACCESS     not-accessible
   STATUS     mandatory
   DESCRIPTION
     "This group contains general operational attributes for components 
      using switched virtual circuits."
::= { mscAal1CesPep 11 }

mscAal1CesPepEpOperEntry OBJECT-TYPE
   SYNTAX     MscAal1CesPepEpOperEntry
   ACCESS     not-accessible
   STATUS     mandatory
   DESCRIPTION
     "An entry in the mscAal1CesPepEpOperTable."
   INDEX {
      mscAal1CesIndex,
      mscAal1CesPepIndex }
::= { mscAal1CesPepEpOperTable 1 }

MscAal1CesPepEpOperEntry ::= SEQUENCE {
   mscAal1CesPepRemoteAddress
      AsciiString,
   mscAal1CesPepLastTearDownCause
      Unsigned32,
   mscAal1CesPepLastTearDownDiagnostic
      AsciiString }

mscAal1CesPepRemoteAddress OBJECT-TYPE
   SYNTAX     AsciiString (SIZE (7..40))
   ACCESS     read-only
   STATUS     mandatory
   DESCRIPTION
     "remoteAddress is the address of the remote end point.
      
      If a connection is currently established, remoteAddress will contain 
      the address of the remote end point.
      
      If a connection is not established, remoteAddress will be Unknown."
::= { mscAal1CesPepEpOperEntry 1 }

mscAal1CesPepLastTearDownCause OBJECT-TYPE
   SYNTAX     Unsigned32 (0..255)
   ACCESS     read-only
   STATUS     mandatory
   DESCRIPTION
     "lastTearDownCause indicates the cause of the last connection tear 
      down.
      
      The values are as defined in the ATM Forum ATM User-Network 
      Interface (UNI) Specification."
::= { mscAal1CesPepEpOperEntry 2 }

mscAal1CesPepLastTearDownDiagnostic OBJECT-TYPE
   SYNTAX     AsciiString (SIZE (0..8))
   ACCESS     read-only
   STATUS     mandatory
   DESCRIPTION
     "lastTearDownDiagnostic provides a diagnostic to supplement the 
      lastTearDownCause attribute."
::= { mscAal1CesPepEpOperEntry 3 }

mscAal1CesPepPassiveOperTable OBJECT-TYPE
   SYNTAX     SEQUENCE OF MscAal1CesPepPassiveOperEntry
   ACCESS     not-accessible
   STATUS     mandatory
   DESCRIPTION
     "This group contains status information about the AAL1 Circuit 
      Emulation Service PassiveEndPoint component."
::= { mscAal1CesPep 12 }

mscAal1CesPepPassiveOperEntry OBJECT-TYPE
   SYNTAX     MscAal1CesPepPassiveOperEntry
   ACCESS     not-accessible
   STATUS     mandatory
   DESCRIPTION
     "An entry in the mscAal1CesPepPassiveOperTable."
   INDEX {
      mscAal1CesIndex,
      mscAal1CesPepIndex }
::= { mscAal1CesPepPassiveOperTable 1 }

MscAal1CesPepPassiveOperEntry ::= SEQUENCE {
   mscAal1CesPepSvcStatus
      INTEGER }

mscAal1CesPepSvcStatus OBJECT-TYPE
   SYNTAX     INTEGER  {
                 initialising(0),
                 connecting(1),
                 connected(2),
                 idle(3),
                 failed(5) }
   ACCESS     read-only
   STATUS     mandatory
   DESCRIPTION
     "svcStatus indicates the status of the incoming connection.
      
      When this attribute has the value initialising, it indicates that the 
      component is initialising when first created; a connection has not 
      been established, and no incoming setup requests will be processed.
      
      When this attribute has the value connecting, it indicates that a 
      connection has not yet been establised, but that incoming setup 
      requests will be processed.
      
      When this attribute has the value connected, it indicates that a 
      connection has been established.
      
      When this attribute has the value idle, it indicates that a connection 
      has not been established, and that no incoming setup requests will 
      be processed.
      
      When this attribute has the value failed, it indicates that the 
      connections is in a state other than those described above."
::= { mscAal1CesPepPassiveOperEntry 1 }


-- ...Lc
-- This component contains all of the operation attributes for a Path 
-- Oriented Logical Connection.

mscAal1CesLCo OBJECT IDENTIFIER ::= { mscAal1Ces 5 }



mscAal1CesLCoRowStatusTable OBJECT-TYPE
   SYNTAX     SEQUENCE OF MscAal1CesLCoRowStatusEntry
   ACCESS     not-accessible
   STATUS     mandatory
   DESCRIPTION
     "This entry controls the addition and deletion of 
      mscAal1CesLCo components."
::= { mscAal1CesLCo 1 }

mscAal1CesLCoRowStatusEntry OBJECT-TYPE
   SYNTAX     MscAal1CesLCoRowStatusEntry
   ACCESS     not-accessible
   STATUS     mandatory
   DESCRIPTION
     "A single entry in the table represents a single 
      mscAal1CesLCo component."
   INDEX {
      mscAal1CesIndex,
      mscAal1CesLCoIndex }
::= { mscAal1CesLCoRowStatusTable 1 }

MscAal1CesLCoRowStatusEntry ::= SEQUENCE {
   mscAal1CesLCoRowStatus
      RowStatus,
   mscAal1CesLCoComponentName
      DisplayString,
   mscAal1CesLCoStorageType
      StorageType,
   mscAal1CesLCoIndex
      NonReplicated }

mscAal1CesLCoRowStatus OBJECT-TYPE
   SYNTAX     RowStatus 
   ACCESS     read-only
   STATUS     mandatory
   DESCRIPTION
     "This variable is used as the basis for SNMP naming of
      mscAal1CesLCo components.
      These components cannot be added nor deleted."
::= { mscAal1CesLCoRowStatusEntry 1 }

mscAal1CesLCoComponentName OBJECT-TYPE
   SYNTAX     DisplayString 
   ACCESS     read-only
   STATUS     mandatory
   DESCRIPTION
     "This variable provides the component's string name for
      use with the ASCII Console Interface"
::= { mscAal1CesLCoRowStatusEntry 2 }

mscAal1CesLCoStorageType OBJECT-TYPE
   SYNTAX     StorageType 
   ACCESS     read-only
   STATUS     mandatory
   DESCRIPTION
     "This variable represents the storage type value for the
      mscAal1CesLCo tables."
::= { mscAal1CesLCoRowStatusEntry 4 }

mscAal1CesLCoIndex OBJECT-TYPE
   SYNTAX     NonReplicated 
   ACCESS     not-accessible
   STATUS     mandatory
   DESCRIPTION
     "This variable represents the index for the mscAal1CesLCo tables."
::= { mscAal1CesLCoRowStatusEntry 10 }

mscAal1CesLCoPathDataTable OBJECT-TYPE
   SYNTAX     SEQUENCE OF MscAal1CesLCoPathDataEntry
   ACCESS     not-accessible
   STATUS     mandatory
   DESCRIPTION
     "This group contains all operational attributes for the path oriented 
      LCo."
::= { mscAal1CesLCo 10 }

mscAal1CesLCoPathDataEntry OBJECT-TYPE
   SYNTAX     MscAal1CesLCoPathDataEntry
   ACCESS     not-accessible
   STATUS     mandatory
   DESCRIPTION
     "An entry in the mscAal1CesLCoPathDataTable."
   INDEX {
      mscAal1CesIndex,
      mscAal1CesLCoIndex }
::= { mscAal1CesLCoPathDataTable 1 }

MscAal1CesLCoPathDataEntry ::= SEQUENCE {
   mscAal1CesLCoState
      INTEGER,
   mscAal1CesLCoOverrideRemoteName
      AsciiString,
   mscAal1CesLCoEnd
      INTEGER,
   mscAal1CesLCoCostMetric
      Unsigned32,
   mscAal1CesLCoDelayMetric
      Unsigned32,
   mscAal1CesLCoRoundTripDelay
      Unsigned32,
   mscAal1CesLCoSetupPriority
      Unsigned32,
   mscAal1CesLCoHoldingPriority
      Unsigned32,
   mscAal1CesLCoRequiredTxBandwidth
      Gauge32,
   mscAal1CesLCoRequiredRxBandwidth
      Gauge32,
   mscAal1CesLCoRequiredTrafficType
      INTEGER,
   mscAal1CesLCoPermittedTrunkTypes
      OCTET STRING,
   mscAal1CesLCoRequiredSecurity
      Unsigned32,
   mscAal1CesLCoRequiredCustomerParameter
      Unsigned32,
   mscAal1CesLCoEmissionPriority
      Unsigned32,
   mscAal1CesLCoDiscardPriority
      Unsigned32,
   mscAal1CesLCoPathType
      INTEGER,
   mscAal1CesLCoRetryCount
      Unsigned32,
   mscAal1CesLCoPathFailureCount
      Unsigned32,
   mscAal1CesLCoReasonForNoRoute
      INTEGER,
   mscAal1CesLCoLastTearDownReason
      INTEGER,
   mscAal1CesLCoPathFailureAction
      INTEGER,
   mscAal1CesLCoBumpPreference
      INTEGER,
   mscAal1CesLCoOptimization
      INTEGER,
   mscAal1CesLCoPathUpDateTime
      EnterpriseDateAndTime }

mscAal1CesLCoState OBJECT-TYPE
   SYNTAX     INTEGER  {
                 pathDown(0),
                 selectingRoute(1),
                 connecting(2),
                 pathUp(3),
                 pathDownRetrying(4) }
   ACCESS     read-only
   STATUS     mandatory
   DESCRIPTION
     "This attribute reflects the current state of the connection. The 
      pathDown state indicates a connection that has no remote end 
      provisioned or the application has not yet signalled for a path. The 
      selectingRoute state occurs when a request has been sent to route 
      selector and it has not yet responded. The connectingState occurs 
      while a path is being established. The pathUp state is the normal 
      operational state of a path. The pathDownRetrying state indicates a 
      path that attempted route selection but received no route and is now 
      waiting to retry route selection again."
::= { mscAal1CesLCoPathDataEntry 1 }

mscAal1CesLCoOverrideRemoteName OBJECT-TYPE
   SYNTAX     AsciiString (SIZE (0..40))
   ACCESS     read-write
   STATUS     mandatory
   DESCRIPTION
     "If set and the current PLC remoteName is blank this remoteName 
      will override the blank PLC remoteName. Usually you would set 
      this attribute and then lock/unlock the service component which 
      will result in this new overrideRemoteName being used as if it had 
      been provisioned into the PLC remoteName. The advantage of this 
      attribute is that the connection's remoteName can be changed 
      immediately without having to 'activate prov' but the disadvantage 
      is that the overrideRemoteName is not permanent and if the card or 
      switch is reset the override will be lost."
::= { mscAal1CesLCoPathDataEntry 2 }

mscAal1CesLCoEnd OBJECT-TYPE
   SYNTAX     INTEGER  {
                 calling(0),
                 called(1) }
   ACCESS     read-only
   STATUS     mandatory
   DESCRIPTION
     "This attribute identifies whether this is the calling or called end of 
      the path."
::= { mscAal1CesLCoPathDataEntry 3 }

mscAal1CesLCoCostMetric OBJECT-TYPE
   SYNTAX     Unsigned32 (0..65535)
   ACCESS     read-only
   STATUS     mandatory
   DESCRIPTION
     "This attribute gives the route's total cost metric. It is calculated as 
      the sum of the cost metric of all trunks in the path at the time the 
      connection was established. The cost metric of a trunk is defined by 
      the trunkCost attribute of the Trunk component. The costMetric for 
      an LCo that is originated and terminated on the same module is 0."
::= { mscAal1CesLCoPathDataEntry 4 }

mscAal1CesLCoDelayMetric OBJECT-TYPE
   SYNTAX     Unsigned32 (0..100000)
   ACCESS     read-only
   STATUS     mandatory
   DESCRIPTION
     "This attribute gives the total delay of the route as the one way delay 
      for a 512 byte packet. It is calculated as the sum of the delays of all 
      trunks in the path stored in topology at the time the connection was 
      established. The delay for an LCo that is originated and terminated 
      on the same module is 0."
::= { mscAal1CesLCoPathDataEntry 5 }

mscAal1CesLCoRoundTripDelay OBJECT-TYPE
   SYNTAX     Unsigned32 (0..200000)
   ACCESS     read-only
   STATUS     mandatory
   DESCRIPTION
     "This attribute contains the time taken for a packet (cell) of 44 bytes 
      to be transmitted to the remote LCo and return to this LCo. The 
      number reported is given in milliseconds to the nearest millisecond. 
      A value of one millisecond is reported if the time is less than 1 
      millisecond even though the delay may be less than 1 Millisecond 
      when the LCo is originated and terminated on the same module."
::= { mscAal1CesLCoPathDataEntry 6 }

mscAal1CesLCoSetupPriority OBJECT-TYPE
   SYNTAX     Unsigned32 (0..4)
   ACCESS     read-only
   STATUS     mandatory
   DESCRIPTION
     "This attribute gives the priority at which the current path is 
      established. Zero is the highest priority and four is the lowest. The 
      holdingPriority, a complementary attribute of this component, 
      indicates the priority a path maintains once it is established."
::= { mscAal1CesLCoPathDataEntry 7 }

mscAal1CesLCoHoldingPriority OBJECT-TYPE
   SYNTAX     Unsigned32 (0..4)
   ACCESS     read-only
   STATUS     mandatory
   DESCRIPTION
     "This attribute gives the priority at which a path holds its current 
      path once the path is established. Zero is the highest priority and 
      four is the lowest. The setupPriority, a complementary attribute, 
      indicates the priority of a path at establishment time."
::= { mscAal1CesLCoPathDataEntry 8 }

mscAal1CesLCoRequiredTxBandwidth OBJECT-TYPE
   SYNTAX     Gauge32 (0..4294967295)
   ACCESS     read-only
   STATUS     mandatory
   DESCRIPTION
     "This attribute gives the actual bandwidth (in bits per second) 
      reserved by this path on each of the trunks of its route. This attribute 
      represents the bandwidth for traffic outgoing to the remote end 
      point. The originating end of the connection determines this value."
::= { mscAal1CesLCoPathDataEntry 9 }

mscAal1CesLCoRequiredRxBandwidth OBJECT-TYPE
   SYNTAX     Gauge32 (0..4294967295)
   ACCESS     read-only
   STATUS     mandatory
   DESCRIPTION
     "This attribute gives the actual bandwidth (in bits per second) 
      reserved by this path on each of trunks of its route. This attribute 
      represents the bandwidth for traffic incoming from the remote end 
      point. The originating end of the connection determines this value"
::= { mscAal1CesLCoPathDataEntry 10 }

mscAal1CesLCoRequiredTrafficType OBJECT-TYPE
   SYNTAX     INTEGER  {
                 voice(0),
                 data(1),
                 video(2),
                 trafficType1(3),
                 trafficType2(4),
                 trafficType3(5),
                 trafficType4(6),
                 trafficType5(7) }
   ACCESS     read-only
   STATUS     mandatory
   DESCRIPTION
     "This operational attribute indicates the type of traffic transmitted 
      over the path. There are eight possible traffic types, and the path can 
      transmit only one of them. The originating end of the connection 
      determines the type. These are arbitrary designations for traffic 
      type. The voice, data and video traffic types are defined, and five 
      other arbitrary traffic types can be defined by the network 
      administration. This attribute is used in the route selection process 
      to restrict the route to trunks that support this traffic type. The 
      supportedTrafficType trunk attribute lists all the types of traffic 
      allowed on the trunk. For example, if requiredTrafficType is 
      specified as trafficType1 then only trunks that include trafficType1 
      in supportedTrafficType, will be candidates for this connection."
::= { mscAal1CesLCoPathDataEntry 11 }

mscAal1CesLCoPermittedTrunkTypes OBJECT-TYPE
   SYNTAX     OCTET STRING (SIZE (1))
   ACCESS     read-only
   STATUS     mandatory
   DESCRIPTION
     "This operational attribute lists up to eight types of trunk that can be 
      used on the route. The originating end of the connection determines 
      the types. The terrestrial and satellite trunk types have been 
      defined, leaving six remaining arbitrary types that can be defined by 
      the network administration. The trunk's type is indicated in the 
      trunkType attribute of the Trunk component. When selecting a 
      route, PORS only chooses trunks whose trunkType are in the 
      permittedTrunkTypes for the path.

      Description of bits:
      terrestrial(0)
      satellite(1)
      trunkType1(2)
      trunkType2(3)
      trunkType3(4)
      trunkType4(5)
      trunkType5(6)
      trunkType6(7)"
::= { mscAal1CesLCoPathDataEntry 12 }

mscAal1CesLCoRequiredSecurity OBJECT-TYPE
   SYNTAX     Unsigned32 (0..7)
   ACCESS     read-only
   STATUS     mandatory
   DESCRIPTION
     "This attribute indicates the required minimum level of security of 
      the trunks on the route. Zero represents the most secure and seven 
      represents the least secure. The trunk's security is indicated by the 
      trunkSecurity attribute of the Trunk component, and has values 
      identical in range and meaning to the requiredSecurity attribute. 
      PORS ensures that any route selected does not contain a trunk 
      whose trunkSecurity attribute is numerically greater than the 
      requiredSecurity."
::= { mscAal1CesLCoPathDataEntry 13 }

mscAal1CesLCoRequiredCustomerParameter OBJECT-TYPE
   SYNTAX     Unsigned32 (0..7)
   ACCESS     read-only
   STATUS     mandatory
   DESCRIPTION
     "This attribute indicates the allowed customer defined parameter of 
      the trunks on the route.The originating end of the connection 
      determines the customer defined parameter. Its value, a number 
      from zero to seven, is chosen by a network administration to have a 
      meaning specific to their network, thus allowing them to customize 
      the use of their trunks. A complementary trunk attribute, 
      customerParameter, also has a value from zero to seven. The route 
      selection process does not consider trunks whose 
      customerParameter is greater than the requiredCustomerParameter 
      of the path."
::= { mscAal1CesLCoPathDataEntry 14 }

mscAal1CesLCoEmissionPriority OBJECT-TYPE
   SYNTAX     Unsigned32 (0..2)
   ACCESS     read-only
   STATUS     mandatory
   DESCRIPTION
     "This attribute indicates the urgency with which packets on the path 
      are emitted by the trunks on the route. The originating end of the 
      connection selects the emissionPriority. EmissionPriority of zero 
      indicates the highest emission priority, while two indicates the 
      lowest emission priority. Packets with a higher emissionPriority (or 
      numerically less) are serviced and sent out before the packets of 
      lower emissionPriority (or numerically higher)."
::= { mscAal1CesLCoPathDataEntry 15 }

mscAal1CesLCoDiscardPriority OBJECT-TYPE
   SYNTAX     Unsigned32 (1..3)
   ACCESS     read-only
   STATUS     mandatory
   DESCRIPTION
     "This attribute indicates the importance of the packets on the 
      path.The originating end of the connection sets discardPriority. One 
      is used for paths carrying the most important traffic, and three is 
      used for paths carrying the least important traffic. Packets with 
      lower discardPriority(numerically lower) are discarded after 
      packets with a higher discardPriority(numerically higher)."
::= { mscAal1CesLCoPathDataEntry 16 }

mscAal1CesLCoPathType OBJECT-TYPE
   SYNTAX     INTEGER  {
                 normal(0),
                 manual(1),
                 forced(2) }
   ACCESS     read-only
   STATUS     mandatory
   DESCRIPTION
     "This attribute indicates whether the path for this PLC was 
      determined automatically or by static provisioning. Normal 
      pathTypes are selected automatically by Route Selector.The other 
      pathTypes are both manual pathTypes where the operator must 
      specify, through provisioning, a static route termed the manualPath. 
      A manual pathType connection is nearly identical to a normal path 
      type connection with the exception that the route is pre-provisioned. 
      For a manual pathType, bandwidth reservations are respected along 
      the path exactly as in a normal path. The last type, the forced 
      pathType, is also a manual path but regardless of the bandwidth 
      available the route is granted provided the trunks are operational 
      and there are sufficient Logical Channels (LChs).
      
      The forced pathType could result in over committing the reserved 
      bandwidth allowed on a trunk. A better way to achieve the effects of 
      a forced pathType is to use a manual pathType with setupPriority = 
      0 and holdingPriority = 0. In this manner the path will reserve 
      correct bandwidth and it will bump other paths if required while not 
      being bumped itself."
::= { mscAal1CesLCoPathDataEntry 17 }

mscAal1CesLCoRetryCount OBJECT-TYPE
   SYNTAX     Unsigned32 (0..255)
   ACCESS     read-only
   STATUS     mandatory
   DESCRIPTION
     "This attribute is the count of the number of times the path chosen 
      during route selection could not be instantiated. This count should 
      be three or below if the network is performing adequately. A high 
      value indicates that the route selection is often performed using an 
      out-of-date view of available network bandwidth and/or topology.
      This attribute will only increase at the calling end of the connection.
      This attribute is reset each time a path reconnects and stops 
      counting when it reaches its maximum value."
::= { mscAal1CesLCoPathDataEntry 18 }

mscAal1CesLCoPathFailureCount OBJECT-TYPE
   SYNTAX     Unsigned32 (0..65535)
   ACCESS     read-only
   STATUS     mandatory
   DESCRIPTION
     "This attribute is the count of the number of times the path has 
      successfully connected. It is set to zero the first time the path is up. 
      If a path fails anytime after connecting this count will be 
      incremented when the path is up again. Failed route requests do not 
      count in this statistic. See retryCount above. This attribute stops 
      counting at its maximum value."
::= { mscAal1CesLCoPathDataEntry 19 }

mscAal1CesLCoReasonForNoRoute OBJECT-TYPE
   SYNTAX     INTEGER  {
                 none(0),
                 destinationNameTooLong(1),
                 destinationNotSpecified(2),
                 unknownDestinationName(3),
                 incorrectDestination(4),
                 incorrectDestinationEndPoint(5),
                 unknownSource(6),
                 unknownDestination(7),
                 sameNode(8),
                 routeCostTooMuch(9),
                 routesDelayTooLong(10),
                 attributesNotMet(11),
                 anError(12),
                 attributeProfileProblem(13),
                 manualPathIndexProblem(14) }
   ACCESS     read-only
   STATUS     mandatory
   DESCRIPTION
     "This attribute is the route selection's reasonForNoRoute and 
      provides a brief reason for which a route was not selected. The 
      reasons are essentially self-explanatory. Perhaps two reasons for no 
      route require some explanation. The reason 
      unknownRemoteNodeName is issued when the remote node name 
      is not in the topological database. The reason plcAttributesNotMet 
      is issued when there is no network connectivity at a level specified 
      by the PLC attributes. This reason is also issued when there is no 
      physical connectivity between two end nodes."
   DEFVAL     { none }
::= { mscAal1CesLCoPathDataEntry 20 }

mscAal1CesLCoLastTearDownReason OBJECT-TYPE
   SYNTAX     INTEGER  {
                 none(0),
                 normalShutDown(1),
                 insufficientTxLcOrBandwidth(2),
                 insufficientRxLcOrBandwidth(3),
                 trunkFailure(4),
                 trunkCardFailure(5),
                 operatorForced(6),
                 lostLcnClash(7),
                 networkCongestion(8),
                 trunkNotFound(9),
                 farEndNotFound(10),
                 wrongModuleReached(11),
                 farEndBusy(12),
                 callLoopedBack(13),
                 unknownReason(14),
                 farEndNotReady(15),
                 remoteNameMismatch(16),
                 serviceTypeMismatch(17),
                 reconnectFromFarEnd(18),
                 bumped(19),
                 accessCardFailure(20),
                 optimized(21),
                 overrideRemoteName(22),
                 trunkOrFarEndDidNotSupportMode(23) }
   ACCESS     read-only
   STATUS     mandatory
   DESCRIPTION
     "This attribute reflects the last tear down reason for a connection 
      (LCo). In many cases this displays the reason for a momentary 
      service interruption. This attribute applies to the last path failure 
      only. If a path is no longer up, this may give an indication to the 
      reason that the path has failed. In many cases an alarm will also be 
      generated with more specific information. The following is a brief 
      description of the reasons:
      none - This path has no information for the teardown this is typical 
      of a path provisioned with no remoteName that has not been up.
      normalShutDown - This path has gone down due to normal call 
      termination.
      insufficientTxLcOrBandwidth - At present there is either no 
      available bandwidth or logical channel numbers available on one or 
      more of the trunks for this path in the transmit direction.
      insufficientRxLcOrBandwidth - At present there is either no 
      available bandwidth or logical channel numbers available on one or 
      more of the trunks for this path in the receive direction.
      trunkFailure- A trunk on the path has failed or has gone down due 
      to a provisioning change of a critical attribute.
      trunkCardFailure- A trunk FP card has failed along the path.
      accessCardFailure- The FP on which the peer access service was 
      running has failed.
      operatorForced- The path has terminated due to the operator 
      locking a trunk along the path.
      lostLcnClash- The path has terminated because the PA's at both 
      ends of an intermediate trunk have allocated the same LC to 
      different calls. When this happens both calls must go down and then 
      try to come up again a fraction of a second later (effectively 
      ensuring that they will now be assigned different LC's). It is normal 
      to get the odd clash especially when the PA's usedLC is 
      approaching the PA's maxLC.
      networkCongestion - The path has failed due to control information 
      being lost and not recoverable.
      trunkNotFound - Occurs on a manual path usually. Check for 
      trunks not up or names provisioned incorrectly.
      farEndNotFound - The far end is not provisioned or is not up. 
      Check remote Name.
      wrongModuleReached - This may occur on a manual path. Check 
      provisioning for correct trunk and service names. For a normal 
      path, the network Topology may be changing check remoteName.
      farEndBusy - The far end has been reached but it is busy. Check 
      remoteName and remote end provisioning.
      callLoopedBack - This LCo is provisioned to call itself. Re-
      provision since this is invalid.
      unknownReason - The failure was not resolved.
      farEndNotReady - The remote end was reached but the connection 
      was refused due to the remote end not being enabled.
      remoteNameMismatch - The remote end has alarmed and rejected 
      this setup due to remoteName provisioning.
      serviceTypeMismatch - The remote Service Type does not match 
      this service type. Check provisioning.
      reconnectFromFarEnd - The remote end re-established this 
      connection. Check the remote end lastTearDownReason to 
      determine the real reason.
      bumped - Another call bumped this path from a trunk to get 
      bandwidth (or an LC) which it required to come up. This other path 
      had a higher setupPriority than this path's holdingPriority hence it 
      was allowed to steal the bandwidth (or LC) from this path.
      optimized - This call has been rerouted due to the optimization 
      feature. The call is still active this just indicates why the path 
      changed.
      trunkOrFarEndDidNotSupportMode - This call was unable to 
      complete because a mode required by the service was not supported 
      by one of the trunks the route went through or by the far end service 
      it connected to. Currently the only mode that this applies to is the 
      map/mux mode on TRUNK PA ATM component. Map mode was 
      required by the application (CES/FrAtm etc.) but was not available 
      on the TRUNK PA ATM component through which the call was 
      routed or the far end CES/FrAtm component did not specify the 
      same mode."
   DEFVAL     { none }
::= { mscAal1CesLCoPathDataEntry 21 }

mscAal1CesLCoPathFailureAction OBJECT-TYPE
   SYNTAX     INTEGER  {
                 disconnectConnection(0),
                 reRoutePath(1) }
   ACCESS     read-only
   STATUS     mandatory
   DESCRIPTION
     "This attribute displays whether the application is set to tolerate 
      momentary interruption of a path while a new path is selected. If 
      disconnectConnection is displayed, the application is informed as 
      soon as possible about a failure by disconnection. If the attribute 
      displays reRoutePath, the path may attempt an immediate reroute, 
      provided the failure is a recoverable failure. If rerouting fails the 
      application is informed of the failure. 
      With this option set to reRoutePath the LCo may wait up to 30 
      seconds before informing the service of complete disconnection in 
      order to allow both ends to attempt to reconnect. Note that if PLC 
      components are different at both ends only the calling end is 
      allowed to reconnect.
      
      All pathTypes respect this attribute. Also on a manualPath with 
      both ends provisioned with independent paths (at least with respect 
      to the failure) this option will have the desired effect that the path is 
      rerouted without complete disconnection at both ends"
::= { mscAal1CesLCoPathDataEntry 22 }

mscAal1CesLCoBumpPreference OBJECT-TYPE
   SYNTAX     INTEGER  {
                 bumpWhenNecessary(0),
                 bumpToObtainBestRoute(1) }
   ACCESS     read-only
   STATUS     mandatory
   DESCRIPTION
     "This attribute specifies when bumping will occur during route 
      selection process. Bumping may occur when necessary or always. It 
      will be necessary for a connection to bump if there is not enough 
      resources for the connection to be established and these resources 
      are occupied by a connection whose setupPriority is lower 
      (numerically higher) than the connection's setupPriority. A 
      connection may also always bump in order to obtain the best route."
::= { mscAal1CesLCoPathDataEntry 23 }

mscAal1CesLCoOptimization OBJECT-TYPE
   SYNTAX     INTEGER  {
                 disabled(0),
                 enabled(1) }
   ACCESS     read-only
   STATUS     mandatory
   DESCRIPTION
     "This attribute is used to specify whether this connection should 
      attempt to optimize its path when requested by the routing PORS 
      component. Every path is as optimal as it can be when it is 
      established, but as network traffic patterns and configurations 
      change this path may no longer be as optimal as it could be. The 
      PORS connection manager on a module requests circuits to 
      optimize at the optimization interval."
::= { mscAal1CesLCoPathDataEntry 24 }

mscAal1CesLCoPathUpDateTime OBJECT-TYPE
   SYNTAX     EnterpriseDateAndTime (SIZE (0 | 19))
   ACCESS     read-only
   STATUS     mandatory
   DESCRIPTION
     "This is the time stamp when the current path was established or 
      reestablished."
::= { mscAal1CesLCoPathDataEntry 25 }

mscAal1CesLCoStatsTable OBJECT-TYPE
   SYNTAX     SEQUENCE OF MscAal1CesLCoStatsEntry
   ACCESS     not-accessible
   STATUS     mandatory
   DESCRIPTION
     "This group contains the operational statistics attributes for the path 
      oriented LCo."
::= { mscAal1CesLCo 11 }

mscAal1CesLCoStatsEntry OBJECT-TYPE
   SYNTAX     MscAal1CesLCoStatsEntry
   ACCESS     not-accessible
   STATUS     mandatory
   DESCRIPTION
     "An entry in the mscAal1CesLCoStatsTable."
   INDEX {
      mscAal1CesIndex,
      mscAal1CesLCoIndex }
::= { mscAal1CesLCoStatsTable 1 }

MscAal1CesLCoStatsEntry ::= SEQUENCE {
   mscAal1CesLCoPktsToNetwork
      PassportCounter64,
   mscAal1CesLCoBytesToNetwork
      PassportCounter64,
   mscAal1CesLCoPktsFromNetwork
      PassportCounter64,
   mscAal1CesLCoBytesFromNetwork
      PassportCounter64 }

mscAal1CesLCoPktsToNetwork OBJECT-TYPE
   SYNTAX     PassportCounter64 
   ACCESS     read-only
   STATUS     mandatory
   DESCRIPTION
     "This attribute counts the number of packets transmitted to the 
      network over this Logical Connection."
::= { mscAal1CesLCoStatsEntry 1 }

mscAal1CesLCoBytesToNetwork OBJECT-TYPE
   SYNTAX     PassportCounter64 
   ACCESS     read-only
   STATUS     mandatory
   DESCRIPTION
     "This attribute counts the number of bytes sent to the network over 
      this Logical Connection."
::= { mscAal1CesLCoStatsEntry 2 }

mscAal1CesLCoPktsFromNetwork OBJECT-TYPE
   SYNTAX     PassportCounter64 
   ACCESS     read-only
   STATUS     mandatory
   DESCRIPTION
     "This attribute counts the number of packets received from the 
      remote LCo via the network."
::= { mscAal1CesLCoStatsEntry 3 }

mscAal1CesLCoBytesFromNetwork OBJECT-TYPE
   SYNTAX     PassportCounter64 
   ACCESS     read-only
   STATUS     mandatory
   DESCRIPTION
     "This attribute counts the number of bytes received from the remote 
      LCo via the network."
::= { mscAal1CesLCoStatsEntry 4 }

mscAal1CesLCoPathTable OBJECT-TYPE
   SYNTAX     SEQUENCE OF MscAal1CesLCoPathEntry
   ACCESS     not-accessible
   STATUS     mandatory
   DESCRIPTION
     "This attribute contains the trunk component names over which the 
      path has been instantiated and the remote end point name 
      terminating the path."
::= { mscAal1CesLCo 264 }

mscAal1CesLCoPathEntry OBJECT-TYPE
   SYNTAX     MscAal1CesLCoPathEntry
   ACCESS     not-accessible
   STATUS     mandatory
   DESCRIPTION
     "An entry in the mscAal1CesLCoPathTable."
   INDEX {
      mscAal1CesIndex,
      mscAal1CesLCoIndex,
      mscAal1CesLCoPathValue }
::= { mscAal1CesLCoPathTable 1 }

MscAal1CesLCoPathEntry ::= SEQUENCE {
   mscAal1CesLCoPathValue
      AsciiString }

mscAal1CesLCoPathValue OBJECT-TYPE
   SYNTAX     AsciiString (SIZE (0..40))
   ACCESS     read-only
   STATUS     mandatory
   DESCRIPTION
     "This variable represents both the value and the index for the
      mscAal1CesLCoPathTable."
::= { mscAal1CesLCoPathEntry 1 }


-- An AtmConnection component is created for each ATM connection 
-- established by an application. It shows where the data traffic for this 
-- connection is directed.

mscAal1CesAtmCon OBJECT IDENTIFIER ::= { mscAal1Ces 6 }



mscAal1CesAtmConRowStatusTable OBJECT-TYPE
   SYNTAX     SEQUENCE OF MscAal1CesAtmConRowStatusEntry
   ACCESS     not-accessible
   STATUS     mandatory
   DESCRIPTION
     "This entry controls the addition and deletion of 
      mscAal1CesAtmCon components."
::= { mscAal1CesAtmCon 1 }

mscAal1CesAtmConRowStatusEntry OBJECT-TYPE
   SYNTAX     MscAal1CesAtmConRowStatusEntry
   ACCESS     not-accessible
   STATUS     mandatory
   DESCRIPTION
     "A single entry in the table represents a single 
      mscAal1CesAtmCon component."
   INDEX {
      mscAal1CesIndex,
      mscAal1CesAtmConIndex }
::= { mscAal1CesAtmConRowStatusTable 1 }

MscAal1CesAtmConRowStatusEntry ::= SEQUENCE {
   mscAal1CesAtmConRowStatus
      RowStatus,
   mscAal1CesAtmConComponentName
      DisplayString,
   mscAal1CesAtmConStorageType
      StorageType,
   mscAal1CesAtmConIndex
      NonReplicated }

mscAal1CesAtmConRowStatus OBJECT-TYPE
   SYNTAX     RowStatus 
   ACCESS     read-only
   STATUS     mandatory
   DESCRIPTION
     "This variable is used as the basis for SNMP naming of
      mscAal1CesAtmCon components.
      These components cannot be added nor deleted."
::= { mscAal1CesAtmConRowStatusEntry 1 }

mscAal1CesAtmConComponentName OBJECT-TYPE
   SYNTAX     DisplayString 
   ACCESS     read-only
   STATUS     mandatory
   DESCRIPTION
     "This variable provides the component's string name for
      use with the ASCII Console Interface"
::= { mscAal1CesAtmConRowStatusEntry 2 }

mscAal1CesAtmConStorageType OBJECT-TYPE
   SYNTAX     StorageType 
   ACCESS     read-only
   STATUS     mandatory
   DESCRIPTION
     "This variable represents the storage type value for the
      mscAal1CesAtmCon tables."
::= { mscAal1CesAtmConRowStatusEntry 4 }

mscAal1CesAtmConIndex OBJECT-TYPE
   SYNTAX     NonReplicated 
   ACCESS     not-accessible
   STATUS     mandatory
   DESCRIPTION
     "This variable represents the index for the mscAal1CesAtmCon tables."
::= { mscAal1CesAtmConRowStatusEntry 10 }

mscAal1CesAtmConOperTable OBJECT-TYPE
   SYNTAX     SEQUENCE OF MscAal1CesAtmConOperEntry
   ACCESS     not-accessible
   STATUS     mandatory
   DESCRIPTION
     "This attribute group contains the operational attributes for the 
      NapAtmConnection component."
::= { mscAal1CesAtmCon 10 }

mscAal1CesAtmConOperEntry OBJECT-TYPE
   SYNTAX     MscAal1CesAtmConOperEntry
   ACCESS     not-accessible
   STATUS     mandatory
   DESCRIPTION
     "An entry in the mscAal1CesAtmConOperTable."
   INDEX {
      mscAal1CesIndex,
      mscAal1CesAtmConIndex }
::= { mscAal1CesAtmConOperTable 1 }

MscAal1CesAtmConOperEntry ::= SEQUENCE {
   mscAal1CesAtmConNextHop
      RowPointer }

mscAal1CesAtmConNextHop OBJECT-TYPE
   SYNTAX     RowPointer 
   ACCESS     read-only
   STATUS     mandatory
   DESCRIPTION
     "This attribute shows the component name of the AtmIf Vcc Ep or 
      AtmCon component to which this switched connection is 
      established."
::= { mscAal1CesAtmConOperEntry 1 }


-- MaintenanceMonitorTx/n
-- 
-- A MaintenanceMonitorTx component identifies an instance of the 
-- MaintenanceMonitor AAL1 Circuit Emulation Service. The service 
-- that is used to transport the copy of the monitored traffic to a local 
-- or remote observer is basic structured AAL1 CES. This stream is 
-- mono directional from the monitor point to the observer. Any ATM 
-- traffic that is received from the observer (which may occur if the 
-- observer uses a standard AAL1 CES service) is discarded at the 
-- monitoring point.
-- 
-- A separate instance of this component is required for each 
-- monitored channel.
-- 
-- Instance numbers, which are used to uniquely identify 
-- MaintenanceMonitorTx component instances, are arbitrary.
-- 
-- Only one instance of MaintenanceMonitorTx may be linked to a 
-- particular LogicalProcessor.
-- 

mscMmTx OBJECT IDENTIFIER ::= { mscComponents 151 }



mscMmTxRowStatusTable OBJECT-TYPE
   SYNTAX     SEQUENCE OF MscMmTxRowStatusEntry
   ACCESS     not-accessible
   STATUS     mandatory
   DESCRIPTION
     "This entry controls the addition and deletion of 
      mscMmTx components."
::= { mscMmTx 1 }

mscMmTxRowStatusEntry OBJECT-TYPE
   SYNTAX     MscMmTxRowStatusEntry
   ACCESS     not-accessible
   STATUS     mandatory
   DESCRIPTION
     "A single entry in the table represents a single 
      mscMmTx component."
   INDEX {
      mscMmTxIndex }
::= { mscMmTxRowStatusTable 1 }

MscMmTxRowStatusEntry ::= SEQUENCE {
   mscMmTxRowStatus
      RowStatus,
   mscMmTxComponentName
      DisplayString,
   mscMmTxStorageType
      StorageType,
   mscMmTxIndex
      Integer32 }

mscMmTxRowStatus OBJECT-TYPE
   SYNTAX     RowStatus 
   ACCESS     read-write
   STATUS     mandatory
   DESCRIPTION
     "This variable is used as the basis for SNMP naming of
      mscMmTx components.
      These components can be added and deleted."
::= { mscMmTxRowStatusEntry 1 }

mscMmTxComponentName OBJECT-TYPE
   SYNTAX     DisplayString 
   ACCESS     read-only
   STATUS     mandatory
   DESCRIPTION
     "This variable provides the component's string name for
      use with the ASCII Console Interface"
::= { mscMmTxRowStatusEntry 2 }

mscMmTxStorageType OBJECT-TYPE
   SYNTAX     StorageType 
   ACCESS     read-only
   STATUS     mandatory
   DESCRIPTION
     "This variable represents the storage type value for the
      mscMmTx tables."
::= { mscMmTxRowStatusEntry 4 }

mscMmTxIndex OBJECT-TYPE
   SYNTAX     Integer32 (1..15)
   ACCESS     not-accessible
   STATUS     mandatory
   DESCRIPTION
     "This variable represents the index for the mscMmTx tables."
::= { mscMmTxRowStatusEntry 10 }

mscMmTxCidDataTable OBJECT-TYPE
   SYNTAX     SEQUENCE OF MscMmTxCidDataEntry
   ACCESS     not-accessible
   STATUS     mandatory
   DESCRIPTION
     "This group contains the attribute for a component's Customer 
      Identifier (CID). Refer to the attribute description for a detailed 
      explanation of CIDs."
::= { mscMmTx 10 }

mscMmTxCidDataEntry OBJECT-TYPE
   SYNTAX     MscMmTxCidDataEntry
   ACCESS     not-accessible
   STATUS     mandatory
   DESCRIPTION
     "An entry in the mscMmTxCidDataTable."
   INDEX {
      mscMmTxIndex }
::= { mscMmTxCidDataTable 1 }

MscMmTxCidDataEntry ::= SEQUENCE {
   mscMmTxCustomerIdentifier
      Unsigned32 }

mscMmTxCustomerIdentifier OBJECT-TYPE
   SYNTAX     Unsigned32 (0 | 1..8191)
   ACCESS     read-write
   STATUS     mandatory
   DESCRIPTION
     "This attribute holds the Customer Identifier (CID).
      
      Every component has a CID. If a component has a cid attribute, the 
      component's CID is the provisioned value of that attribute; 
      otherwise the component inherits the CID of its parent. The top-
      level component has a CID of 0.
      
      Every operator session also has a CID, which is the CID 
      provisioned for the operator's user ID. An operator will see only the 
      stream data for components having a matching CID. Also, the 
      operator will be allowed to issue commands for only those 
      components which have a matching CID.
      
      An operator CID of 0 is used to identify the Network Manager 
      (referred to as 'NetMan' in DPN). This CID matches the CID of 
      any component. Values 1 to 8191 inclusive (equivalent to 'basic 
      CIDs' in DPN) may be assigned to specific customers."
   DEFVAL     { 0 }
::= { mscMmTxCidDataEntry 1 }

mscMmTxProvTable OBJECT-TYPE
   SYNTAX     SEQUENCE OF MscMmTxProvEntry
   ACCESS     not-accessible
   STATUS     mandatory
   DESCRIPTION
     "This group contains basic provisioning data for the Maintenance 
      Monitor Transmitter (MmTx). A MmTx represents a mono-
      directional AAL1 Circuit Emulation Service. AAL1 CES attributes 
      in this group are essential information to the operator about the 
      AAL1 CES service that must be matched in the Aal1Ces component 
      that receives the monitored stream.
      
      The check escape checks that only one instance of a 
      MaintenanceMonitorTx is linked to any one Lp."
::= { mscMmTx 11 }

mscMmTxProvEntry OBJECT-TYPE
   SYNTAX     MscMmTxProvEntry
   ACCESS     not-accessible
   STATUS     mandatory
   DESCRIPTION
     "An entry in the mscMmTxProvTable."
   INDEX {
      mscMmTxIndex }
::= { mscMmTxProvTable 1 }

MscMmTxProvEntry ::= SEQUENCE {
   mscMmTxLinkToLogicalProcessor
      Link,
   mscMmTxMonitoredDirection
      INTEGER,
   mscMmTxServiceType
      INTEGER,
   mscMmTxPartialFill
      Unsigned32,
   mscMmTxIdleSuppression
      INTEGER }

mscMmTxLinkToLogicalProcessor OBJECT-TYPE
   SYNTAX     Link 
   ACCESS     read-write
   STATUS     mandatory
   DESCRIPTION
     "This attribute specifies the instance of a hardware component to 
      which an instance of this component is linked. Only Lp 
      components may be linked"
::= { mscMmTxProvEntry 3 }

mscMmTxMonitoredDirection OBJECT-TYPE
   SYNTAX     INTEGER  {
                 ingress(0) }
   ACCESS     read-write
   STATUS     mandatory
   DESCRIPTION
     "monitoredDirection specifies the direction of the monitored traffic.
      
      The default and only value is ingress."
   DEFVAL     { ingress }
::= { mscMmTxProvEntry 4 }

mscMmTxServiceType OBJECT-TYPE
   SYNTAX     INTEGER  {
                 basicStructured(1) }
   ACCESS     read-write
   STATUS     mandatory
   DESCRIPTION
     "serviceType specifies the service type of the CES. 
      
      The serviceType attribute in the receiving Aal1Ces component must 
      have the same value as this attribute.
      The default and only value is basicStructured."
   DEFVAL     { basicStructured }
::= { mscMmTxProvEntry 5 }

mscMmTxPartialFill OBJECT-TYPE
   SYNTAX     Unsigned32 (47)
   ACCESS     read-write
   STATUS     mandatory
   DESCRIPTION
     "partialFill specifies the number of octets that are carried in an ATM 
      cell by the AAL1 CES service. A full cell contains 47 octets. 
      
      The partialFill attribute in the receiving Aal1Ces component must 
      have the same value as this attribute.
      
      The default and only value is 47.
      DESCRIPTION"
   DEFVAL     { 47 }
::= { mscMmTxProvEntry 6 }

mscMmTxIdleSuppression OBJECT-TYPE
   SYNTAX     INTEGER  {
                 off(0) }
   ACCESS     read-write
   STATUS     mandatory
   DESCRIPTION
     "idleSuppression controls the suppression of idle cells. An idle cell is 
      one in which the bytes of the ATM payload (up to the partialFill 
      level) match the idlePattern.
      
      If idleSuppression is off, idle cells are not suppressed.
      
      If idleSuppression is on, at least 75% of cells are suppressed under 
      idle conditions.
      
      The idleSuppression attribute in the receiving Aal1Ces component 
      must have the same value as this attribute 
      
      The default and only value is off."
   DEFVAL     { off }
::= { mscMmTxProvEntry 7 }

mscMmTxStateTable OBJECT-TYPE
   SYNTAX     SEQUENCE OF MscMmTxStateEntry
   ACCESS     not-accessible
   STATUS     mandatory
   DESCRIPTION
     "This group contains the three OSI State attributes and the six OSI 
      Status attributes. The descriptions generically indicate what each 
      attribute implies about the component. Note that not all the values 
      and state combinations described here are supported by every 
      component which uses this group. For component-specific 
      information and the valid state combinations, refer to NTP 241-
      7001-150, Passport Operations and Maintenance Guide."
::= { mscMmTx 12 }

mscMmTxStateEntry OBJECT-TYPE
   SYNTAX     MscMmTxStateEntry
   ACCESS     not-accessible
   STATUS     mandatory
   DESCRIPTION
     "An entry in the mscMmTxStateTable."
   INDEX {
      mscMmTxIndex }
::= { mscMmTxStateTable 1 }

MscMmTxStateEntry ::= SEQUENCE {
   mscMmTxAdminState
      INTEGER,
   mscMmTxOperationalState
      INTEGER,
   mscMmTxUsageState
      INTEGER,
   mscMmTxAvailabilityStatus
      OCTET STRING,
   mscMmTxProceduralStatus
      OCTET STRING,
   mscMmTxControlStatus
      OCTET STRING,
   mscMmTxAlarmStatus
      OCTET STRING,
   mscMmTxStandbyStatus
      INTEGER,
   mscMmTxUnknownStatus
      INTEGER }

mscMmTxAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component.
      
      The OSI Status attributes, if supported by the component, may 
      provide more details, qualifying the state of the component."
   DEFVAL     { unlocked }
::= { mscMmTxStateEntry 1 }

mscMmTxOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle.
      
      The OSI Status attributes, if supported by the component, may 
      provide more details, qualifying the state of the component."
   DEFVAL     { disabled }
::= { mscMmTxStateEntry 2 }

mscMmTxUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time.
      
      The OSI Status attributes, if supported by the component, may 
      provide more details, qualifying the state of the component."
   DEFVAL     { idle }
::= { mscMmTxStateEntry 3 }

mscMmTxAvailabilityStatus OBJECT-TYPE
   SYNTAX     OCTET STRING (SIZE (2))
   ACCESS     read-only
   STATUS     mandatory
   DESCRIPTION
     "If supported by the component, this attribute indicates the OSI 
      Availability status of the component. Note that, even though it is 
      defined as a multi-valued set, at most one value is shown to the user.
      
      When no values are in the set, this indicates that either the attribute 
      is not supported or that none of the status conditions described 
      below are present.
      
      The value inTest indicates that the resource is undergoing a test 
      procedure. If adminState is locked or shuttingDown, the normal 
      users are precluded from using the resource and controlStatus is 
      reservedForTest. Tests that do not exclude additional users can be 
      present in any operational or administrative state but the 
      reservedForTest condition should not be present.
      
      The value failed indicates that the component has an internal fault 
      that prevents it from operating. The operationalState is disabled.
      
      The value dependency indicates that the component cannot operate 
      because some other resource on which it depends is unavailable. 
      The operationalState is disabled.
      
      The value powerOff indicates the resource requires power to be 
      applied and it is not powered on. The operationalState is disabled.
      
      The value offLine indicates the resource requires a routine 
      operation (either manual, automatic, or both) to be performed to 
      place it on-line and make it available for use. The operationalState 
      is disabled.
      
      The value offDuty indicates the resource is inactive in accordance 
      with a predetermined time schedule. In the absence of other 
      disabling conditions, the operationalState is enabled or disabled.
      
      The value degraded indicates the service provided by the 
      component is degraded in some way, such as in speed or operating 
      capacity. However, the resource remains available for service. The 
      operationalState is enabled.
      
      The value notInstalled indicates the resource is not present. The 
      operationalState is disabled.
      
      The value logFull is not used.

      Description of bits:
      inTest(0)
      failed(1)
      powerOff(2)
      offLine(3)
      offDuty(4)
      dependency(5)
      degraded(6)
      notInstalled(7)
      logFull(8)"
::= { mscMmTxStateEntry 4 }

mscMmTxProceduralStatus OBJECT-TYPE
   SYNTAX     OCTET STRING (SIZE (1))
   ACCESS     read-only
   STATUS     mandatory
   DESCRIPTION
     "If supported by the component, this attribute indicates the OSI 
      Procedural status of the component. Note that, even though it is 
      defined as a multi-valued set, at most one value is shown to the user.
      
      When no values are in the set, this indicates that either the attribute 
      is not supported or that none of the status conditions described 
      below are present.
      
      The value initializationRequired indicates (for a resource which 
      doesn't initialize autonomously) that initialization is required before 
      it can perform its normal functions, and this procedure has not been 
      initiated. The operationalState is disabled.
      
      The value notInitialized indicates (for a resource which does 
      initialize autonomously) that initialization is required before it can 
      perform its normal functions, and this procedure has not been 
      initiated. The operationalState may be enabled or disabled.
      
      The value initializing indicates that initialization has been initiated 
      but is not yet complete. The operationalState may be enabled or 
      disabled.
      
      The value reporting indicates the resource has completed some 
      processing operation and is notifying the results. The 
      operationalState is enabled.
      
      The value terminating indicates the component is in a termination 
      phase. If the resource doesn't reinitialize autonomously, 
      operationalState is disabled; otherwise it is enabled or disabled.

      Description of bits:
      initializationRequired(0)
      notInitialized(1)
      initializing(2)
      reporting(3)
      terminating(4)"
::= { mscMmTxStateEntry 5 }

mscMmTxControlStatus OBJECT-TYPE
   SYNTAX     OCTET STRING (SIZE (1))
   ACCESS     read-only
   STATUS     mandatory
   DESCRIPTION
     "If supported by the component, this attribute indicates the OSI 
      Control status of the component. Note that, even though it is defined 
      as a multi-valued set, at most one value is shown to the user.
      
      When no values are in the set, this indicates that either the attribute 
      is not supported or that none of the status conditions described 
      below are present.
      
      The value subjectToTest indicates the resource is available but tests 
      may be conducted simultaneously at unpredictable times, which 
      may cause it to exhibit unusual characteristics.
      
      The value partOfServicesLocked indicates that part of the service is 
      restricted from users of a resource. The adminState is unlocked.
      
      The value reservedForTest indicates that the component is 
      administratively unavailable because it is undergoing a test 
      procedure. The adminState is locked.
      
      The value suspended indicates that the service has been 
      administratively suspended.

      Description of bits:
      subjectToTest(0)
      partOfServicesLocked(1)
      reservedForTest(2)
      suspended(3)"
::= { mscMmTxStateEntry 6 }

mscMmTxAlarmStatus OBJECT-TYPE
   SYNTAX     OCTET STRING (SIZE (1))
   ACCESS     read-only
   STATUS     mandatory
   DESCRIPTION
     "If supported by the component, this attribute indicates the OSI 
      Alarm status of the component. Note that, even though it is defined 
      as a multi-valued set, at most one value is shown to the user.
      
      When no values are in the set, this indicates that either the attribute 
      is not supported or that none of the status conditions described 
      below are present.
      
      The value underRepair indicates the component is currently being 
      repaired. The operationalState is enabled or disabled.
      
      The value critical indicates one or more critical alarms are 
      outstanding against the component. Other, less severe, alarms may 
      also be outstanding. The operationalState is enabled or disabled.
      
      The value major indicates one or more major alarms are 
      outstanding against the component. Other, less severe, alarms may 
      also be outstanding. The operationalState is enabled or disabled.
      
      The value minor indicates one or more minor alarms are 
      outstanding against the component. Other, less severe, alarms may 
      also be outstanding. The operationalState is enabled or disabled.
      
      The value alarmOutstanding generically indicates that an alarm of 
      some severity is outstanding against the component.

      Description of bits:
      underRepair(0)
      critical(1)
      major(2)
      minor(3)
      alarmOutstanding(4)"
::= { mscMmTxStateEntry 7 }

mscMmTxStandbyStatus OBJECT-TYPE
   SYNTAX     INTEGER  {
                 hotStandby(0),
                 coldStandby(1),
                 providingService(2),
                 notSet(15) }
   ACCESS     read-only
   STATUS     mandatory
   DESCRIPTION
     "If supported by the component, this attribute indicates the OSI 
      Standby status of the component.
      
      The value notSet indicates that either the attribute is not supported 
      or that none of the status conditions described below are present. 
      Note that this is a non-standard value, used because the original 
      specification indicated this attribute was set-valued and thus, did not 
      provide a value to indicate that none of the other three are 
      applicable.
      
      The value hotStandby indicates that the resource is not providing 
      service but will be immediately able to take over the role of the 
      resource to be backed up, without initialization activity, and 
      containing the same information as the resource to be backed up.
      
      The value coldStandby indicates the resource is a backup for 
      another resource but will not be immediately able to take over the 
      role of the backed up resource and will require some initialization 
      activity.
      
      The value providingService indicates that this component, as a 
      backup resource, is currently backing up another resource."
   DEFVAL     { notSet }
::= { mscMmTxStateEntry 8 }

mscMmTxUnknownStatus OBJECT-TYPE
   SYNTAX     INTEGER  {
                 false(0),
                 true(1) }
   ACCESS     read-only
   STATUS     mandatory
   DESCRIPTION
     "This attribute indicates the OSI Unknown status of the component.
      
      The value false indicates that all of the other OSI State and Status 
      attribute values can be considered accurate.
      
      The value true indicates that the actual state of the component is not 
      known for sure."
   DEFVAL     { false }
::= { mscMmTxStateEntry 9 }

mscMmTxOperTable OBJECT-TYPE
   SYNTAX     SEQUENCE OF MscMmTxOperEntry
   ACCESS     not-accessible
   STATUS     mandatory
   DESCRIPTION
     "This group contains status information about the AAL1 Circuit 
      Emulation Service and the related ATM service, and the means to 
      specify the Channel to be monitor."
::= { mscMmTx 13 }

mscMmTxOperEntry OBJECT-TYPE
   SYNTAX     MscMmTxOperEntry
   ACCESS     not-accessible
   STATUS     mandatory
   DESCRIPTION
     "An entry in the mscMmTxOperTable."
   INDEX {
      mscMmTxIndex }
::= { mscMmTxOperTable 1 }

MscMmTxOperEntry ::= SEQUENCE {
   mscMmTxConnectionStatus
      INTEGER,
   mscMmTxChanToMonitor
      RowPointer }

mscMmTxConnectionStatus OBJECT-TYPE
   SYNTAX     INTEGER  {
                 connected(0),
                 channelNotReady(1),
                 atmNotReady(2),
                 atmNotConfigured(3),
                 channelNotSpecified(4) }
   ACCESS     read-only
   STATUS     mandatory
   DESCRIPTION
     "This attribute indicates whether a service is non-operational because 
      of a problem with the service interface side of the service (in which 
      case, it is set to channelNotReady) or because of a problem with the 
      ATM side of the service (in which case, it is set to 
      atmNotConfigured or atmNotReady).
      
      When this attribute is set to channelNotReady, it is an indication 
      that the corresponding Chan component (as defined by the attribute 
      interfaceName) or the Chan component's parent port component 
      (Lp/n Ds1/m or Lp/n E1/m) is locked.
      
      When this attribute is set to atmNotConfigured, it is an indication 
      that no sub-component has been provisioned, and thus no ATM 
      connection has been configured for the service.
      
      When this attribute is set to atmNotReady, it is an indication that the 
      ATM connection with which the service is associated (as defined by 
      a sub-component) has been lost or that it is currently unable to carry 
      CES data.
      
      When this attribute is set to channelNotSpecified, it is an indication 
      that the chanToMonitor attribute is not set to a valid channel.
      
      This attribute is set to connected when a service is operational (that 
      is, the OSI attribute operationalState is enabled.)"
   DEFVAL     { channelNotReady }
::= { mscMmTxOperEntry 3 }

mscMmTxChanToMonitor OBJECT-TYPE
   SYNTAX     RowPointer 
   ACCESS     read-write
   STATUS     mandatory
   DESCRIPTION
     "chanToMonitor specifies the LP, port (E1 or DS1), and channel to 
      monitor. The LP must be the same LP specified in the provisionable 
      attribute linkToLogicalProcessor. This attribute's value is of the 
      form Lp/x E1/y Chan/z or Lp/x DS1/y Chan/z."
::= { mscMmTxOperEntry 4 }


-- Aal1Ces/n NailedUpAdaptationPoint
-- 
-- A NailedUpAdaptationPoint is a nailed-up point which straddles 
-- the CBR/ATM domains and which is associated with the adaptation 
-- of CBR data to/from ATM cells.
-- 
-- If a NailedUpAdaptationPoint component is provisioned under an 
-- Aal1Ces component, no other components may be provisioned 
-- under the same Aal1Ces component.

mscMmTxNap OBJECT IDENTIFIER ::= { mscMmTx 2 }



mscMmTxNapRowStatusTable OBJECT-TYPE
   SYNTAX     SEQUENCE OF MscMmTxNapRowStatusEntry
   ACCESS     not-accessible
   STATUS     mandatory
   DESCRIPTION
     "This entry controls the addition and deletion of 
      mscMmTxNap components."
::= { mscMmTxNap 1 }

mscMmTxNapRowStatusEntry OBJECT-TYPE
   SYNTAX     MscMmTxNapRowStatusEntry
   ACCESS     not-accessible
   STATUS     mandatory
   DESCRIPTION
     "A single entry in the table represents a single 
      mscMmTxNap component."
   INDEX {
      mscMmTxIndex,
      mscMmTxNapIndex }
::= { mscMmTxNapRowStatusTable 1 }

MscMmTxNapRowStatusEntry ::= SEQUENCE {
   mscMmTxNapRowStatus
      RowStatus,
   mscMmTxNapComponentName
      DisplayString,
   mscMmTxNapStorageType
      StorageType,
   mscMmTxNapIndex
      NonReplicated }

mscMmTxNapRowStatus OBJECT-TYPE
   SYNTAX     RowStatus 
   ACCESS     read-write
   STATUS     mandatory
   DESCRIPTION
     "This variable is used as the basis for SNMP naming of
      mscMmTxNap components.
      These components can be added and deleted."
::= { mscMmTxNapRowStatusEntry 1 }

mscMmTxNapComponentName OBJECT-TYPE
   SYNTAX     DisplayString 
   ACCESS     read-only
   STATUS     mandatory
   DESCRIPTION
     "This variable provides the component's string name for
      use with the ASCII Console Interface"
::= { mscMmTxNapRowStatusEntry 2 }

mscMmTxNapStorageType OBJECT-TYPE
   SYNTAX     StorageType 
   ACCESS     read-only
   STATUS     mandatory
   DESCRIPTION
     "This variable represents the storage type value for the
      mscMmTxNap tables."
::= { mscMmTxNapRowStatusEntry 4 }

mscMmTxNapIndex OBJECT-TYPE
   SYNTAX     NonReplicated 
   ACCESS     not-accessible
   STATUS     mandatory
   DESCRIPTION
     "This variable represents the index for the mscMmTxNap tables."
::= { mscMmTxNapRowStatusEntry 10 }

mscMmTxNapProvTable OBJECT-TYPE
   SYNTAX     SEQUENCE OF MscMmTxNapProvEntry
   ACCESS     not-accessible
   STATUS     mandatory
   DESCRIPTION
     "This group contains the provisioning data for the 
      NailedUpAdaptationPoint component."
::= { mscMmTxNap 10 }

mscMmTxNapProvEntry OBJECT-TYPE
   SYNTAX     MscMmTxNapProvEntry
   ACCESS     not-accessible
   STATUS     mandatory
   DESCRIPTION
     "An entry in the mscMmTxNapProvTable."
   INDEX {
      mscMmTxIndex,
      mscMmTxNapIndex }
::= { mscMmTxNapProvTable 1 }

MscMmTxNapProvEntry ::= SEQUENCE {
   mscMmTxNapAtmConnection
      Link }

mscMmTxNapAtmConnection OBJECT-TYPE
   SYNTAX     Link 
   ACCESS     read-write
   STATUS     mandatory
   DESCRIPTION
     "This attribute specifies the identity of the component to which the 
      NailedUpAdaptationPoint is linked. This is an AtmIf Vcc 
      NailedUpEndPoint or an AtmIf Vpt Vcc NailedUpEndPoint (the 
      AAL1 cells are transported off the switch over an ATM UNI, where 
      they are routed to the appropriate AAL1 entity at the other end by 
      the ATM bearer service)."
::= { mscMmTxNapProvEntry 1 }


-- An AtmConnection component is created for each ATM connection 
-- established by an application. It shows where the data traffic for this 
-- connection is directed.

mscMmTxAtmCon OBJECT IDENTIFIER ::= { mscMmTx 6 }



mscMmTxAtmConRowStatusTable OBJECT-TYPE
   SYNTAX     SEQUENCE OF MscMmTxAtmConRowStatusEntry
   ACCESS     not-accessible
   STATUS     mandatory
   DESCRIPTION
     "This entry controls the addition and deletion of 
      mscMmTxAtmCon components."
::= { mscMmTxAtmCon 1 }

mscMmTxAtmConRowStatusEntry OBJECT-TYPE
   SYNTAX     MscMmTxAtmConRowStatusEntry
   ACCESS     not-accessible
   STATUS     mandatory
   DESCRIPTION
     "A single entry in the table represents a single 
      mscMmTxAtmCon component."
   INDEX {
      mscMmTxIndex,
      mscMmTxAtmConIndex }
::= { mscMmTxAtmConRowStatusTable 1 }

MscMmTxAtmConRowStatusEntry ::= SEQUENCE {
   mscMmTxAtmConRowStatus
      RowStatus,
   mscMmTxAtmConComponentName
      DisplayString,
   mscMmTxAtmConStorageType
      StorageType,
   mscMmTxAtmConIndex
      NonReplicated }

mscMmTxAtmConRowStatus OBJECT-TYPE
   SYNTAX     RowStatus 
   ACCESS     read-only
   STATUS     mandatory
   DESCRIPTION
     "This variable is used as the basis for SNMP naming of
      mscMmTxAtmCon components.
      These components cannot be added nor deleted."
::= { mscMmTxAtmConRowStatusEntry 1 }

mscMmTxAtmConComponentName OBJECT-TYPE
   SYNTAX     DisplayString 
   ACCESS     read-only
   STATUS     mandatory
   DESCRIPTION
     "This variable provides the component's string name for
      use with the ASCII Console Interface"
::= { mscMmTxAtmConRowStatusEntry 2 }

mscMmTxAtmConStorageType OBJECT-TYPE
   SYNTAX     StorageType 
   ACCESS     read-only
   STATUS     mandatory
   DESCRIPTION
     "This variable represents the storage type value for the
      mscMmTxAtmCon tables."
::= { mscMmTxAtmConRowStatusEntry 4 }

mscMmTxAtmConIndex OBJECT-TYPE
   SYNTAX     NonReplicated 
   ACCESS     not-accessible
   STATUS     mandatory
   DESCRIPTION
     "This variable represents the index for the mscMmTxAtmCon tables."
::= { mscMmTxAtmConRowStatusEntry 10 }

mscMmTxAtmConOperTable OBJECT-TYPE
   SYNTAX     SEQUENCE OF MscMmTxAtmConOperEntry
   ACCESS     not-accessible
   STATUS     mandatory
   DESCRIPTION
     "This attribute group contains the operational attributes for the 
      NapAtmConnection component."
::= { mscMmTxAtmCon 10 }

mscMmTxAtmConOperEntry OBJECT-TYPE
   SYNTAX     MscMmTxAtmConOperEntry
   ACCESS     not-accessible
   STATUS     mandatory
   DESCRIPTION
     "An entry in the mscMmTxAtmConOperTable."
   INDEX {
      mscMmTxIndex,
      mscMmTxAtmConIndex }
::= { mscMmTxAtmConOperTable 1 }

MscMmTxAtmConOperEntry ::= SEQUENCE {
   mscMmTxAtmConNextHop
      RowPointer }

mscMmTxAtmConNextHop OBJECT-TYPE
   SYNTAX     RowPointer 
   ACCESS     read-only
   STATUS     mandatory
   DESCRIPTION
     "This attribute shows the component name of the AtmIf Vcc Ep or 
      AtmCon component to which this switched connection is 
      established."
::= { mscMmTxAtmConOperEntry 1 }




-- 
-- Version and Compliance statements
-- 



-- Object-Group Statement:
-- A list of all current accessible leaf objects.

-- OBJECTS { mscAal1CesAepStorageType,
--           mscAal1CesRowStatus,
--           mscAal1CesPepRowStatus,
--           mscAal1CesAepSvcStatus,
--           mscAal1CesCustomerIdentifier,
--           mscMmTxControlStatus,
--           mscAal1CesNapComponentName,
--           mscAal1CesAepRowStatus,
--           mscAal1CesServiceType,
--           mscAal1CesPepLastTearDownDiagnostic,
--           mscAal1CesMaximumBufferDelay,
--           mscAal1CesLCoDelayMetric,
--           mscAal1CesUsageState,
--           mscAal1CesLCoCostMetric,
--           mscMmTxPartialFill,
--           mscAal1CesAepLocalAddress,
--           mscMmTxComponentName,
--           mscAal1CesLCoPathValue,
--           mscAal1CesAtmConNextHop,
--           mscAal1CesInterfaceName,
--           mscMmTxProceduralStatus,
--           mscAal1CesLCoOverrideRemoteName,
--           mscAal1CesBufferSize,
--           mscAal1CesDummyDataByte,
--           mscAal1CesOperationalState,
--           mscAal1CesIdleSuppression,
--           mscAal1CesAepLastTearDownDiagnostic,
--           mscAal1CesLCoRequiredTxBandwidth,
--           mscAal1CesAepProfile,
--           mscMmTxServiceType,
--           mscAal1CesNapAtmConnection,
--           mscAal1CesAtmConComponentName,
--           mscAal1CesLCoComponentName,
--           mscAal1CesCellLossStatus,
--           mscMmTxAtmConRowStatus,
--           mscAal1CesLCoReasonForNoRoute,
--           mscMmTxConnectionStatus,
--           mscAal1CesAepLastSetupFailureDiagnostic,
--           mscAal1CesLCoRequiredCustomerParameter,
--           mscMmTxIdleSuppression,
--           mscAal1CesLCoState,
--           mscAal1CesAepLastSetupFailureCause,
--           mscMmTxNapAtmConnection,
--           mscAal1CesAlarmStatus,
--           mscAal1CesNapStorageType,
--           mscAal1CesLCoRequiredRxBandwidth,
--           mscAal1CesAal1LayerLossStatus,
--           mscAal1CesPepSvcStatus,
--           mscAal1CesPointerParityErrors,
--           mscAal1CesHeaderErrors,
--           mscAal1CesAepRetryTimeRemaining,
--           mscAal1CesLCoStorageType,
--           mscAal1CesBufferUnderflows,
--           mscAal1CesCellLossRecoveryPeriod,
--           mscAal1CesLCoHoldingPriority,
--           mscAal1CesLCoBumpPreference,
--           mscMmTxAvailabilityStatus,
--           mscAal1CesNapRowStatus,
--           mscMmTxUnknownStatus,
--           mscAal1CesLCoOptimization,
--           mscAal1CesPartialFill,
--           mscAal1CesAtmConStorageType,
--           mscMmTxRowStatus,
--           mscMmTxNapRowStatus,
--           mscAal1CesLCoRowStatus,
--           mscAal1CesProceduralStatus,
--           mscAal1CesCellsReceived,
--           mscAal1CesLCoEnd,
--           mscMmTxLinkToLogicalProcessor,
--           mscAal1CesLCoRetryCount,
--           mscAal1CesAepRetryFailures,
--           mscAal1CesMisinsertedCells,
--           mscAal1CesPointerReframes,
--           mscAal1CesLCoPermittedTrunkTypes,
--           mscAal1CesComponentName,
--           mscAal1CesPepComponentName,
--           mscAal1CesAtmConRowStatus,
--           mscAal1CesCellLossIntegrationPeriod,
--           mscAal1CesLCoPathType,
--           mscAal1CesLCoBytesToNetwork,
--           mscMmTxCustomerIdentifier,
--           mscAal1CesConnectionStatus,
--           mscAal1CesLCoDiscardPriority,
--           mscMmTxNapComponentName,
--           mscAal1CesPepExpectedRemoteAddress,
--           mscAal1CesPepLastTearDownCause,
--           mscAal1CesLCoSetupPriority,
--           mscMmTxUsageState,
--           mscAal1CesLCoPathUpDateTime,
--           mscAal1CesAepCalledVpiVci,
--           mscAal1CesAepActiveEndPointType,
--           mscAal1CesAepComponentName,
--           mscMmTxAtmConNextHop,
--           mscAal1CesAepFirstRetryInterval,
--           mscAal1CesLCoLastTearDownReason,
--           mscAal1CesLCoPktsToNetwork,
--           mscAal1CesLCoRequiredSecurity,
--           mscAal1CesLCoPathFailureCount,
--           mscAal1CesBufferOverflows,
--           mscMmTxAtmConStorageType,
--           mscMmTxOperationalState,
--           mscAal1CesAal1SequenceErrors,
--           mscAal1CesAepExpectedRemoteAddress,
--           mscAal1CesAepLastTearDownCause,
--           mscAal1CesLCoEmissionPriority,
--           mscMmTxAtmConComponentName,
--           mscAal1CesLCoPathFailureAction,
--           mscMmTxNapStorageType,
--           mscAal1CesAepAddressToCall,
--           mscAal1CesLCoRequiredTrafficType,
--           mscAal1CesPepRemoteAddress,
--           mscAal1CesUnknownStatus,
--           mscAal1CesLCoRoundTripDelay,
--           mscAal1CesStandbyStatus,
--           mscMmTxMonitoredDirection,
--           mscAal1CesLCoBytesFromNetwork,
--           mscAal1CesAepRemoteAddress,
--           mscAal1CesAvailabilityStatus,
--           mscAal1CesStorageType,
--           mscAal1CesIdlePattern,
--           mscAal1CesAepRetryLimit,
--           mscMmTxStorageType,
--           mscAal1CesLostCells,
--           mscAal1CesReassembledCells,
--           mscAal1CesDp2CellDelayVariationTolerance,
--           mscAal1CesPepStorageType,
--           mscMmTxStandbyStatus,
--           mscAal1CesAepRoutingOption,
--           mscMmTxAlarmStatus,
--           mscAal1CesCellsTransmitted,
--           mscMmTxChanToMonitor,
--           mscAal1CesPepLocalAddress,
--           mscAal1CesControlStatus,
--           mscAal1CesAdminState,
--           mscMmTxAdminState,
--           mscAal1CesLCoPktsFromNetwork }
-- STATUS  mandatory
-- DESCRIPTION
--   "A list of all current accessible leaf objects."

circuitEmulationServiceGroup OBJECT IDENTIFIER ::= { circuitEmulationServiceMIB 1 }
circuitEmulationServiceGroupCA OBJECT IDENTIFIER ::= { circuitEmulationServiceGroup 1 }
circuitEmulationServiceGroupCA02 OBJECT IDENTIFIER ::= { circuitEmulationServiceGroupCA 3 }
circuitEmulationServiceGroupCA02A OBJECT IDENTIFIER ::= { circuitEmulationServiceGroupCA02 2 }



-- Agent-Capabilities Statement:

-- PRODUCT-RELEASE "MscPassport Release 1.2 CircuitEmulationService."
-- STATUS          mandatory
-- DESCRIPTION     "Carrier Passport CircuitEmulationService MIB: MIB Version CA02A,
--                  Software Version CA02S9C."
-- SUPPORTS        Nortel-MsCarrier-MscPassport-CircuitEmulationServiceMIB
--    INCLUDES     { circuitEmulationServiceGroupCA02A }

circuitEmulationServiceCapabilities OBJECT IDENTIFIER ::= { circuitEmulationServiceMIB 3 }
circuitEmulationServiceCapabilitiesCA OBJECT IDENTIFIER ::= { circuitEmulationServiceCapabilities 1 }
circuitEmulationServiceCapabilitiesCA02 OBJECT IDENTIFIER ::= { circuitEmulationServiceCapabilitiesCA 3 }
circuitEmulationServiceCapabilitiesCA02A OBJECT IDENTIFIER ::= { circuitEmulationServiceCapabilitiesCA02 2 }





END
