Nortel-MsCarrier-MscPassport-BusMIB
DEFINITIONS ::= BEGIN



IMPORTS

      OBJECT-TYPE
   FROM RFC-1212

      mscPassportMIBs
   FROM Nortel-MsCarrier-MscPassport-UsefulDefinitionsMIB

      DisplayString,
      StorageType,
      RowStatus,
      Integer32,
      Unsigned32
   FROM Nortel-MsCarrier-MscPassport-StandardTextualConventionsMIB

      NonReplicated
   FROM Nortel-MsCarrier-MscPassport-TextualConventionsMIB

      mscShelfCard,
      mscShelfIndex,
      mscShelf,
      mscShelfCardIndex
   FROM Nortel-MsCarrier-MscPassport-BaseShelfMIB;




-- LAST-UPDATED   "9909010000Z"
-- ORGANIZATION   "Nortel Networks"
-- CONTACT-INFO   "
--         Nortel Carrier Data Network Management
--         
--         Postal:       P.O. Box 3511, Station C 
--                       Ottawa, Ontario 
--                       Canada  K1Y 4H7
--         
--         via the WEB:  http://www.nortelnetworks.com  
--                       select 'Contact Us' from the menu
--          
--         via phone:    1-800-4NORTEL"
-- DESCRIPTION
--    "The module describing the Nortel MsCarrier MscPassport
--     Bus Enterprise MIB."

busMIB OBJECT IDENTIFIER ::= { mscPassportMIBs 144 }










-- Shelf Card/n BusTap/b
-- A BusTap component represents a physical bus tap on a card. A bus 
-- tap is a card's interface to a bus; it provides a pathway for the card 
-- to send cells over the bus to the other cards in the module, and to 
-- receive cells sent to it over the bus by the other cards in the module.
-- A card's BusTap components are created automatically whenver the 
-- card begins acting as an active or standby LP, and remain in 
-- existence as long as the card remains operational; BusTap 
-- components cannot be added or deleted.

mscShelfCardBusTap OBJECT IDENTIFIER ::= { mscShelfCard 2 }



mscShelfCardBusTapRowStatusTable OBJECT-TYPE
   SYNTAX     SEQUENCE OF MscShelfCardBusTapRowStatusEntry
   ACCESS     not-accessible
   STATUS     mandatory
   DESCRIPTION
     "This entry controls the addition and deletion of 
      mscShelfCardBusTap components."
::= { mscShelfCardBusTap 1 }

mscShelfCardBusTapRowStatusEntry OBJECT-TYPE
   SYNTAX     MscShelfCardBusTapRowStatusEntry
   ACCESS     not-accessible
   STATUS     mandatory
   DESCRIPTION
     "A single entry in the table represents a single 
      mscShelfCardBusTap component."
   INDEX {
      mscShelfIndex,
      mscShelfCardIndex,
      mscShelfCardBusTapIndex }
::= { mscShelfCardBusTapRowStatusTable 1 }

MscShelfCardBusTapRowStatusEntry ::= SEQUENCE {
   mscShelfCardBusTapRowStatus
      RowStatus,
   mscShelfCardBusTapComponentName
      DisplayString,
   mscShelfCardBusTapStorageType
      StorageType,
   mscShelfCardBusTapIndex
      INTEGER }

mscShelfCardBusTapRowStatus OBJECT-TYPE
   SYNTAX     RowStatus 
   ACCESS     read-only
   STATUS     mandatory
   DESCRIPTION
     "This variable is used as the basis for SNMP naming of
      mscShelfCardBusTap components.
      These components cannot be added nor deleted."
::= { mscShelfCardBusTapRowStatusEntry 1 }

mscShelfCardBusTapComponentName OBJECT-TYPE
   SYNTAX     DisplayString 
   ACCESS     read-only
   STATUS     mandatory
   DESCRIPTION
     "This variable provides the component's string name for
      use with the ASCII Console Interface"
::= { mscShelfCardBusTapRowStatusEntry 2 }

mscShelfCardBusTapStorageType OBJECT-TYPE
   SYNTAX     StorageType 
   ACCESS     read-only
   STATUS     mandatory
   DESCRIPTION
     "This variable represents the storage type value for the
      mscShelfCardBusTap tables."
::= { mscShelfCardBusTapRowStatusEntry 4 }

mscShelfCardBusTapIndex OBJECT-TYPE
   SYNTAX     INTEGER  {
                 x(0),
                 y(1) }
   ACCESS     not-accessible
   STATUS     mandatory
   DESCRIPTION
     "This variable represents the index for the mscShelfCardBusTap tables."
::= { mscShelfCardBusTapRowStatusEntry 10 }

mscShelfCardBusTapStateTable OBJECT-TYPE
   SYNTAX     SEQUENCE OF MscShelfCardBusTapStateEntry
   ACCESS     not-accessible
   STATUS     mandatory
   DESCRIPTION
     "This group contains the three OSI State attributes and the six OSI 
      Status attributes. The descriptions generically indicate what each 
      attribute implies about the component. Note that not all the values 
      and state combinations described here are supported by every 
      component which uses this group. For component-specific 
      information and the valid state combinations, refer to NTP 241-
      7001-150, Passport Operations and Maintenance Guide."
::= { mscShelfCardBusTap 10 }

mscShelfCardBusTapStateEntry OBJECT-TYPE
   SYNTAX     MscShelfCardBusTapStateEntry
   ACCESS     not-accessible
   STATUS     mandatory
   DESCRIPTION
     "An entry in the mscShelfCardBusTapStateTable."
   INDEX {
      mscShelfIndex,
      mscShelfCardIndex,
      mscShelfCardBusTapIndex }
::= { mscShelfCardBusTapStateTable 1 }

MscShelfCardBusTapStateEntry ::= SEQUENCE {
   mscShelfCardBusTapAdminState
      INTEGER,
   mscShelfCardBusTapOperationalState
      INTEGER,
   mscShelfCardBusTapUsageState
      INTEGER,
   mscShelfCardBusTapAvailabilityStatus
      OCTET STRING,
   mscShelfCardBusTapProceduralStatus
      OCTET STRING,
   mscShelfCardBusTapControlStatus
      OCTET STRING,
   mscShelfCardBusTapAlarmStatus
      OCTET STRING,
   mscShelfCardBusTapStandbyStatus
      INTEGER,
   mscShelfCardBusTapUnknownStatus
      INTEGER }

mscShelfCardBusTapAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component.
      
      The OSI Status attributes, if supported by the component, may 
      provide more details, qualifying the state of the component."
   DEFVAL     { unlocked }
::= { mscShelfCardBusTapStateEntry 1 }

mscShelfCardBusTapOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle.
      
      The OSI Status attributes, if supported by the component, may 
      provide more details, qualifying the state of the component."
   DEFVAL     { disabled }
::= { mscShelfCardBusTapStateEntry 2 }

mscShelfCardBusTapUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time.
      
      The OSI Status attributes, if supported by the component, may 
      provide more details, qualifying the state of the component."
   DEFVAL     { idle }
::= { mscShelfCardBusTapStateEntry 3 }

mscShelfCardBusTapAvailabilityStatus OBJECT-TYPE
   SYNTAX     OCTET STRING (SIZE (2))
   ACCESS     read-only
   STATUS     mandatory
   DESCRIPTION
     "If supported by the component, this attribute indicates the OSI 
      Availability status of the component. Note that, even though it is 
      defined as a multi-valued set, at most one value is shown to the user.
      
      When no values are in the set, this indicates that either the attribute 
      is not supported or that none of the status conditions described 
      below are present.
      
      The value inTest indicates that the resource is undergoing a test 
      procedure. If adminState is locked or shuttingDown, the normal 
      users are precluded from using the resource and controlStatus is 
      reservedForTest. Tests that do not exclude additional users can be 
      present in any operational or administrative state but the 
      reservedForTest condition should not be present.
      
      The value failed indicates that the component has an internal fault 
      that prevents it from operating. The operationalState is disabled.
      
      The value dependency indicates that the component cannot operate 
      because some other resource on which it depends is unavailable. 
      The operationalState is disabled.
      
      The value powerOff indicates the resource requires power to be 
      applied and it is not powered on. The operationalState is disabled.
      
      The value offLine indicates the resource requires a routine 
      operation (either manual, automatic, or both) to be performed to 
      place it on-line and make it available for use. The operationalState 
      is disabled.
      
      The value offDuty indicates the resource is inactive in accordance 
      with a predetermined time schedule. In the absence of other 
      disabling conditions, the operationalState is enabled or disabled.
      
      The value degraded indicates the service provided by the 
      component is degraded in some way, such as in speed or operating 
      capacity. However, the resource remains available for service. The 
      operationalState is enabled.
      
      The value notInstalled indicates the resource is not present. The 
      operationalState is disabled.
      
      The value logFull is not used.

      Description of bits:
      inTest(0)
      failed(1)
      powerOff(2)
      offLine(3)
      offDuty(4)
      dependency(5)
      degraded(6)
      notInstalled(7)
      logFull(8)"
::= { mscShelfCardBusTapStateEntry 4 }

mscShelfCardBusTapProceduralStatus OBJECT-TYPE
   SYNTAX     OCTET STRING (SIZE (1))
   ACCESS     read-only
   STATUS     mandatory
   DESCRIPTION
     "If supported by the component, this attribute indicates the OSI 
      Procedural status of the component. Note that, even though it is 
      defined as a multi-valued set, at most one value is shown to the user.
      
      When no values are in the set, this indicates that either the attribute 
      is not supported or that none of the status conditions described 
      below are present.
      
      The value initializationRequired indicates (for a resource which 
      doesn't initialize autonomously) that initialization is required before 
      it can perform its normal functions, and this procedure has not been 
      initiated. The operationalState is disabled.
      
      The value notInitialized indicates (for a resource which does 
      initialize autonomously) that initialization is required before it can 
      perform its normal functions, and this procedure has not been 
      initiated. The operationalState may be enabled or disabled.
      
      The value initializing indicates that initialization has been initiated 
      but is not yet complete. The operationalState may be enabled or 
      disabled.
      
      The value reporting indicates the resource has completed some 
      processing operation and is notifying the results. The 
      operationalState is enabled.
      
      The value terminating indicates the component is in a termination 
      phase. If the resource doesn't reinitialize autonomously, 
      operationalState is disabled; otherwise it is enabled or disabled.

      Description of bits:
      initializationRequired(0)
      notInitialized(1)
      initializing(2)
      reporting(3)
      terminating(4)"
::= { mscShelfCardBusTapStateEntry 5 }

mscShelfCardBusTapControlStatus OBJECT-TYPE
   SYNTAX     OCTET STRING (SIZE (1))
   ACCESS     read-only
   STATUS     mandatory
   DESCRIPTION
     "If supported by the component, this attribute indicates the OSI 
      Control status of the component. Note that, even though it is defined 
      as a multi-valued set, at most one value is shown to the user.
      
      When no values are in the set, this indicates that either the attribute 
      is not supported or that none of the status conditions described 
      below are present.
      
      The value subjectToTest indicates the resource is available but tests 
      may be conducted simultaneously at unpredictable times, which 
      may cause it to exhibit unusual characteristics.
      
      The value partOfServicesLocked indicates that part of the service is 
      restricted from users of a resource. The adminState is unlocked.
      
      The value reservedForTest indicates that the component is 
      administratively unavailable because it is undergoing a test 
      procedure. The adminState is locked.
      
      The value suspended indicates that the service has been 
      administratively suspended.

      Description of bits:
      subjectToTest(0)
      partOfServicesLocked(1)
      reservedForTest(2)
      suspended(3)"
::= { mscShelfCardBusTapStateEntry 6 }

mscShelfCardBusTapAlarmStatus OBJECT-TYPE
   SYNTAX     OCTET STRING (SIZE (1))
   ACCESS     read-only
   STATUS     mandatory
   DESCRIPTION
     "If supported by the component, this attribute indicates the OSI 
      Alarm status of the component. Note that, even though it is defined 
      as a multi-valued set, at most one value is shown to the user.
      
      When no values are in the set, this indicates that either the attribute 
      is not supported or that none of the status conditions described 
      below are present.
      
      The value underRepair indicates the component is currently being 
      repaired. The operationalState is enabled or disabled.
      
      The value critical indicates one or more critical alarms are 
      outstanding against the component. Other, less severe, alarms may 
      also be outstanding. The operationalState is enabled or disabled.
      
      The value major indicates one or more major alarms are 
      outstanding against the component. Other, less severe, alarms may 
      also be outstanding. The operationalState is enabled or disabled.
      
      The value minor indicates one or more minor alarms are 
      outstanding against the component. Other, less severe, alarms may 
      also be outstanding. The operationalState is enabled or disabled.
      
      The value alarmOutstanding generically indicates that an alarm of 
      some severity is outstanding against the component.

      Description of bits:
      underRepair(0)
      critical(1)
      major(2)
      minor(3)
      alarmOutstanding(4)"
::= { mscShelfCardBusTapStateEntry 7 }

mscShelfCardBusTapStandbyStatus OBJECT-TYPE
   SYNTAX     INTEGER  {
                 hotStandby(0),
                 coldStandby(1),
                 providingService(2),
                 notSet(15) }
   ACCESS     read-only
   STATUS     mandatory
   DESCRIPTION
     "If supported by the component, this attribute indicates the OSI 
      Standby status of the component.
      
      The value notSet indicates that either the attribute is not supported 
      or that none of the status conditions described below are present. 
      Note that this is a non-standard value, used because the original 
      specification indicated this attribute was set-valued and thus, did not 
      provide a value to indicate that none of the other three are 
      applicable.
      
      The value hotStandby indicates that the resource is not providing 
      service but will be immediately able to take over the role of the 
      resource to be backed up, without initialization activity, and 
      containing the same information as the resource to be backed up.
      
      The value coldStandby indicates the resource is a backup for 
      another resource but will not be immediately able to take over the 
      role of the backed up resource and will require some initialization 
      activity.
      
      The value providingService indicates that this component, as a 
      backup resource, is currently backing up another resource."
   DEFVAL     { notSet }
::= { mscShelfCardBusTapStateEntry 8 }

mscShelfCardBusTapUnknownStatus OBJECT-TYPE
   SYNTAX     INTEGER  {
                 false(0),
                 true(1) }
   ACCESS     read-only
   STATUS     mandatory
   DESCRIPTION
     "This attribute indicates the OSI Unknown status of the component.
      
      The value false indicates that all of the other OSI State and Status 
      attribute values can be considered accurate.
      
      The value true indicates that the actual state of the component is not 
      known for sure."
   DEFVAL     { false }
::= { mscShelfCardBusTapStateEntry 9 }

mscShelfCardBusTapOperTable OBJECT-TYPE
   SYNTAX     SEQUENCE OF MscShelfCardBusTapOperEntry
   ACCESS     not-accessible
   STATUS     mandatory
   DESCRIPTION
     "This attribute group contains operational attributes of a bus tap. This 
      information outlines what the bus tap is doing and why it is doing it, 
      and is primarily intended for use in diagnosing the cause of a bus-
      related problem reported by the module."
::= { mscShelfCardBusTap 11 }

mscShelfCardBusTapOperEntry OBJECT-TYPE
   SYNTAX     MscShelfCardBusTapOperEntry
   ACCESS     not-accessible
   STATUS     mandatory
   DESCRIPTION
     "An entry in the mscShelfCardBusTapOperTable."
   INDEX {
      mscShelfIndex,
      mscShelfCardIndex,
      mscShelfCardBusTapIndex }
::= { mscShelfCardBusTapOperTable 1 }

MscShelfCardBusTapOperEntry ::= SEQUENCE {
   mscShelfCardBusTapFailuresInEffect
      OCTET STRING,
   mscShelfCardBusTapDependenciesInEffect
      OCTET STRING,
   mscShelfCardBusTapCardsAvailable
      OCTET STRING,
   mscShelfCardBusTapCardsTxTo
      OCTET STRING }

mscShelfCardBusTapFailuresInEffect OBJECT-TYPE
   SYNTAX     OCTET STRING (SIZE (1))
   ACCESS     read-only
   STATUS     mandatory
   DESCRIPTION
     "This attribute records the hardware problems that prevent the bus 
      tap from using the associated bus. It may contain any combination 
      of the following values.
      selfTest: the bus tap has failed its self-test
      clockSignal: the bus tap is not receiving clock signals from the bus
      parityError: the bus tap has detected too many parity errors on the 
      bus

      Description of bits:
      selfTest(0)
      clockSignal(1)
      parityError(2)"
::= { mscShelfCardBusTapOperEntry 1 }

mscShelfCardBusTapDependenciesInEffect OBJECT-TYPE
   SYNTAX     OCTET STRING (SIZE (1))
   ACCESS     read-only
   STATUS     mandatory
   DESCRIPTION
     "This attribute records the non-hardware problems that prevent the 
      bus tap from using the associated bus. It may contain any 
      combination of the following values.
      busLocked: the bus is locked
      busDisabled: the bus is disabled

      Description of bits:
      busLocked(0)
      busDisabled(1)"
::= { mscShelfCardBusTapOperEntry 2 }

mscShelfCardBusTapCardsAvailable OBJECT-TYPE
   SYNTAX     OCTET STRING (SIZE (2))
   ACCESS     read-only
   STATUS     mandatory
   DESCRIPTION
     "This attribute records the slot numbers of the cards that the bus tap 
      considers available on the busthat is, the cards that have an 
      operational bus tap connected to the bus. The value of this attribute 
      is determined automatically by the bus tap by monitoring signals 
      generated by each bus tap on the bus; it cannot be changed by the 
      operator. Normally, every card in the module signals its availability 
      on both buses; if a card does not signal its availability on a bus this 
      indicates that the card is not present or that its bus tap has failed. By 
      examining this attribute for both of a card's BusTap components, it 
      is possible to determine which cards are present in the module and 
      which buses each can use.
      Note: If failuresInEffect contains either selfTest or clockSignal the 
      bus tap is unable to monitor the availability of the bus taps on the 
      bus; cardsAvailable will indicate that no bus taps are available on 
      the bus.

      Description of bits:
      n0(0)
      n1(1)
      n2(2)
      n3(3)
      n4(4)
      n5(5)
      n6(6)
      n7(7)
      n8(8)
      n9(9)
      n10(10)
      n11(11)
      n12(12)
      n13(13)
      n14(14)
      n15(15)"
::= { mscShelfCardBusTapOperEntry 3 }

mscShelfCardBusTapCardsTxTo OBJECT-TYPE
   SYNTAX     OCTET STRING (SIZE (2))
   ACCESS     read-only
   STATUS     mandatory
   DESCRIPTION
     "This attribute records the slot numbers of the cards which the bus 
      tap is currently configured to transmit cells to. This configuration is 
      managed automatically, and cannot be changed by the operator. By 
      examining this attribute for both of a card's BusTap components, it 
      is possible to determine which bus (if any) the card uses when it 
      needs to transmits cells to a specific card in the module.

      Description of bits:
      n0(0)
      n1(1)
      n2(2)
      n3(3)
      n4(4)
      n5(5)
      n6(6)
      n7(7)
      n8(8)
      n9(9)
      n10(10)
      n11(11)
      n12(12)
      n13(13)
      n14(14)
      n15(15)"
::= { mscShelfCardBusTapOperEntry 4 }

mscShelfCardBusTapErrorsTable OBJECT-TYPE
   SYNTAX     SEQUENCE OF MscShelfCardBusTapErrorsEntry
   ACCESS     not-accessible
   STATUS     mandatory
   DESCRIPTION
     "This attribute group records errors that the bus tap has detected 
      since the card was last rebooted. This information is intended for 
      use in detecting and diagnosing bus-related problems within a 
      module."
::= { mscShelfCardBusTap 12 }

mscShelfCardBusTapErrorsEntry OBJECT-TYPE
   SYNTAX     MscShelfCardBusTapErrorsEntry
   ACCESS     not-accessible
   STATUS     mandatory
   DESCRIPTION
     "An entry in the mscShelfCardBusTapErrorsTable."
   INDEX {
      mscShelfIndex,
      mscShelfCardIndex,
      mscShelfCardBusTapIndex }
::= { mscShelfCardBusTapErrorsTable 1 }

MscShelfCardBusTapErrorsEntry ::= SEQUENCE {
   mscShelfCardBusTapSelfTestErrorCode
      Unsigned32,
   mscShelfCardBusTapClockErrors
      Unsigned32,
   mscShelfCardBusTapEndOfCellErrors
      Unsigned32,
   mscShelfCardBusTapParityErrors
      Unsigned32,
   mscShelfCardBusTapFrmCongestionErrors
      Unsigned32,
   mscShelfCardBusTapFrmCollisionErrors
      Unsigned32,
   mscShelfCardBusTapFrmTimeoutErrors
      Unsigned32,
   mscShelfCardBusTapFrmDeliveryErrors
      Unsigned32,
   mscShelfCardBusTapFrmSizeErrors
      Unsigned32 }

mscShelfCardBusTapSelfTestErrorCode OBJECT-TYPE
   SYNTAX     Unsigned32 (0..4294967295)
   ACCESS     read-only
   STATUS     mandatory
   DESCRIPTION
     "This attribute records the error code generated by the most recent 
      self-test of the bus tap. The value zero indicates that the self-test 
      was successful. A non-zero value indicates that the self-test failed, 
      and is used by the service technician when a defective card is 
      returned for repair."
::= { mscShelfCardBusTapErrorsEntry 1 }

mscShelfCardBusTapClockErrors OBJECT-TYPE
   SYNTAX     Unsigned32 (0..4294967295)
   ACCESS     read-only
   STATUS     mandatory
   DESCRIPTION
     "This attribute records the number of times that the bus tap has 
      detected a loss of the fundamental clock signal used by the bus. 
      Each occurrence may result in the loss of one or more cells or 
      frames. This type of event may occur during normal operation of 
      the module, for example when switching from one of the bus's 
      clock sources to the other; it may also be caused by a hardware 
      fault.
      The attribute's value wraps around to zero when it exceeds the 
      maximum permitted value."
::= { mscShelfCardBusTapErrorsEntry 2 }

mscShelfCardBusTapEndOfCellErrors OBJECT-TYPE
   SYNTAX     Unsigned32 (0..4294967295)
   ACCESS     read-only
   STATUS     mandatory
   DESCRIPTION
     "This attribute records the number of times that the bus tap has 
      detected a loss of the end-of-cell timing signal used by the bus. 
      Each occurrence may result in the loss of one or more cells or 
      frames. This type of event may occur during normal operation of 
      the module, for example switching the bus's clock source from one 
      card to another; it may also be caused by a hardware fault.
      The attribute's value wraps around to zero when it exceeds the 
      maximum permitted value."
::= { mscShelfCardBusTapErrorsEntry 3 }

mscShelfCardBusTapParityErrors OBJECT-TYPE
   SYNTAX     Unsigned32 (0..4294967295)
   ACCESS     read-only
   STATUS     mandatory
   DESCRIPTION
     "This attribute records the number of times that the bus tap has 
      detected a cell with invalid parity on the bus. Each occurrence may 
      result in the loss of one or more cells or frames. This type of event 
      may occur during normal operation of the module, for example 
      when a card is inserted, removed, or reboots; it may also be caused 
      by a hardware fault.
      The attribute's value wraps around to zero when it exceeds the 
      maximum permitted value."
::= { mscShelfCardBusTapErrorsEntry 4 }

mscShelfCardBusTapFrmCongestionErrors OBJECT-TYPE
   SYNTAX     Unsigned32 (0..4294967295)
   ACCESS     read-only
   STATUS     mandatory
   DESCRIPTION
     "This attribute records the number of times that the bus tap was 
      unable to receive a frame from the bus because all of its bus receive 
      channels were in use. Each occurrence results in the loss of the 
      frame. This type of event may occur during normal operation of the 
      module, for example when the module is operating in single bus 
      mode; it may also be caused by a hardware fault.
      The attribute's value wraps around to zero when it exceeds the 
      maximum permitted value."
::= { mscShelfCardBusTapErrorsEntry 5 }

mscShelfCardBusTapFrmCollisionErrors OBJECT-TYPE
   SYNTAX     Unsigned32 (0..4294967295)
   ACCESS     read-only
   STATUS     mandatory
   DESCRIPTION
     "This attribute records the number of times that the bus tap was 
      unable to receive a frame from the bus because it did not receive the 
      last cell of the frame before the first cell of the following frame 
      from the same source. Each occurrence results in the loss of both 
      frames. This type of event may occur during normal operation of 
      the module, for example when a card reboots; it may also be caused 
      by a hardware fault.
      The attribute's value wraps around to zero when it exceeds the 
      maximum permitted value."
::= { mscShelfCardBusTapErrorsEntry 6 }

mscShelfCardBusTapFrmTimeoutErrors OBJECT-TYPE
   SYNTAX     Unsigned32 (0..4294967295)
   ACCESS     read-only
   STATUS     mandatory
   DESCRIPTION
     "This attribute records the number of times that the bus tap was 
      unable to receive a frame from the bus because the delay between 
      two successive cells in that frame exceeded the maximum allowable 
      duration. Each occurrence results in the loss of the frame. This type 
      of event may occur during normal operation of the module, for 
      example when the module changes bus mode; it may also be caused 
      by a hardware fault.
      The attribute's value wraps around to zero when it exceeds the 
      maximum permitted value."
::= { mscShelfCardBusTapErrorsEntry 7 }

mscShelfCardBusTapFrmDeliveryErrors OBJECT-TYPE
   SYNTAX     Unsigned32 (0..4294967295)
   ACCESS     read-only
   STATUS     mandatory
   DESCRIPTION
     "This attribute records the number of times that the bus tap was 
      unable to receive a frame from the bus because it was destined for a 
      bus transmit queue; that is, the frame would have been immediately 
      retransmitted over a bus. Each occurrence results in the loss of the 
      frame. This type of event should never occur during normal 
      operation of the module and indicates the occurrence of a hardware 
      or software fault.
      The attribute's value wraps around to zero when it exceeds the 
      maximum permitted value."
::= { mscShelfCardBusTapErrorsEntry 8 }

mscShelfCardBusTapFrmSizeErrors OBJECT-TYPE
   SYNTAX     Unsigned32 (0..4294967295)
   ACCESS     read-only
   STATUS     mandatory
   DESCRIPTION
     "This attribute records the number of times that the bus tap was 
      unable to receive a frame from the bus because it required more 
      than 255 blocks of shared memory. Each occurrence results in the 
      loss of the frame. This type of event should never occur during 
      normal operation of the module and indicates improper 
      configuration of the card or the occurrence of a hardware or 
      software fault.
      The attribute's value wraps around to zero when it exceeds the 
      maximum permitted value."
::= { mscShelfCardBusTapErrorsEntry 9 }


-- Shelf Bus/b
-- A Bus component respresents a hardware resource within a module 
-- that cards can use to communicate with each other. Each frame (or 
-- other data) to be transferred between cards is broken up into one or 
-- more cells by the sending card, placed on the bus, and reassembled 
-- by the receiving card(s).
-- A module's Bus components are created automatically, and cannot 
-- be added or deleted.

mscShelfBus OBJECT IDENTIFIER ::= { mscShelf 3 }



mscShelfBusRowStatusTable OBJECT-TYPE
   SYNTAX     SEQUENCE OF MscShelfBusRowStatusEntry
   ACCESS     not-accessible
   STATUS     mandatory
   DESCRIPTION
     "This entry controls the addition and deletion of 
      mscShelfBus components."
::= { mscShelfBus 1 }

mscShelfBusRowStatusEntry OBJECT-TYPE
   SYNTAX     MscShelfBusRowStatusEntry
   ACCESS     not-accessible
   STATUS     mandatory
   DESCRIPTION
     "A single entry in the table represents a single 
      mscShelfBus component."
   INDEX {
      mscShelfIndex,
      mscShelfBusIndex }
::= { mscShelfBusRowStatusTable 1 }

MscShelfBusRowStatusEntry ::= SEQUENCE {
   mscShelfBusRowStatus
      RowStatus,
   mscShelfBusComponentName
      DisplayString,
   mscShelfBusStorageType
      StorageType,
   mscShelfBusIndex
      INTEGER }

mscShelfBusRowStatus OBJECT-TYPE
   SYNTAX     RowStatus 
   ACCESS     read-only
   STATUS     mandatory
   DESCRIPTION
     "This variable is used as the basis for SNMP naming of
      mscShelfBus components.
      These components cannot be added nor deleted."
::= { mscShelfBusRowStatusEntry 1 }

mscShelfBusComponentName OBJECT-TYPE
   SYNTAX     DisplayString 
   ACCESS     read-only
   STATUS     mandatory
   DESCRIPTION
     "This variable provides the component's string name for
      use with the ASCII Console Interface"
::= { mscShelfBusRowStatusEntry 2 }

mscShelfBusStorageType OBJECT-TYPE
   SYNTAX     StorageType 
   ACCESS     read-only
   STATUS     mandatory
   DESCRIPTION
     "This variable represents the storage type value for the
      mscShelfBus tables."
::= { mscShelfBusRowStatusEntry 4 }

mscShelfBusIndex OBJECT-TYPE
   SYNTAX     INTEGER  {
                 x(0),
                 y(1) }
   ACCESS     not-accessible
   STATUS     mandatory
   DESCRIPTION
     "This variable represents the index for the mscShelfBus tables."
::= { mscShelfBusRowStatusEntry 10 }

mscShelfBusStateTable OBJECT-TYPE
   SYNTAX     SEQUENCE OF MscShelfBusStateEntry
   ACCESS     not-accessible
   STATUS     mandatory
   DESCRIPTION
     "This group contains the three OSI State attributes and the six OSI 
      Status attributes. The descriptions generically indicate what each 
      attribute implies about the component. Note that not all the values 
      and state combinations described here are supported by every 
      component which uses this group. For component-specific 
      information and the valid state combinations, refer to NTP 241-
      7001-150, Passport Operations and Maintenance Guide."
::= { mscShelfBus 10 }

mscShelfBusStateEntry OBJECT-TYPE
   SYNTAX     MscShelfBusStateEntry
   ACCESS     not-accessible
   STATUS     mandatory
   DESCRIPTION
     "An entry in the mscShelfBusStateTable."
   INDEX {
      mscShelfIndex,
      mscShelfBusIndex }
::= { mscShelfBusStateTable 1 }

MscShelfBusStateEntry ::= SEQUENCE {
   mscShelfBusAdminState
      INTEGER,
   mscShelfBusOperationalState
      INTEGER,
   mscShelfBusUsageState
      INTEGER,
   mscShelfBusAvailabilityStatus
      OCTET STRING,
   mscShelfBusProceduralStatus
      OCTET STRING,
   mscShelfBusControlStatus
      OCTET STRING,
   mscShelfBusAlarmStatus
      OCTET STRING,
   mscShelfBusStandbyStatus
      INTEGER,
   mscShelfBusUnknownStatus
      INTEGER }

mscShelfBusAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component.
      
      The OSI Status attributes, if supported by the component, may 
      provide more details, qualifying the state of the component."
   DEFVAL     { unlocked }
::= { mscShelfBusStateEntry 1 }

mscShelfBusOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle.
      
      The OSI Status attributes, if supported by the component, may 
      provide more details, qualifying the state of the component."
   DEFVAL     { disabled }
::= { mscShelfBusStateEntry 2 }

mscShelfBusUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time.
      
      The OSI Status attributes, if supported by the component, may 
      provide more details, qualifying the state of the component."
   DEFVAL     { idle }
::= { mscShelfBusStateEntry 3 }

mscShelfBusAvailabilityStatus OBJECT-TYPE
   SYNTAX     OCTET STRING (SIZE (2))
   ACCESS     read-only
   STATUS     mandatory
   DESCRIPTION
     "If supported by the component, this attribute indicates the OSI 
      Availability status of the component. Note that, even though it is 
      defined as a multi-valued set, at most one value is shown to the user.
      
      When no values are in the set, this indicates that either the attribute 
      is not supported or that none of the status conditions described 
      below are present.
      
      The value inTest indicates that the resource is undergoing a test 
      procedure. If adminState is locked or shuttingDown, the normal 
      users are precluded from using the resource and controlStatus is 
      reservedForTest. Tests that do not exclude additional users can be 
      present in any operational or administrative state but the 
      reservedForTest condition should not be present.
      
      The value failed indicates that the component has an internal fault 
      that prevents it from operating. The operationalState is disabled.
      
      The value dependency indicates that the component cannot operate 
      because some other resource on which it depends is unavailable. 
      The operationalState is disabled.
      
      The value powerOff indicates the resource requires power to be 
      applied and it is not powered on. The operationalState is disabled.
      
      The value offLine indicates the resource requires a routine 
      operation (either manual, automatic, or both) to be performed to 
      place it on-line and make it available for use. The operationalState 
      is disabled.
      
      The value offDuty indicates the resource is inactive in accordance 
      with a predetermined time schedule. In the absence of other 
      disabling conditions, the operationalState is enabled or disabled.
      
      The value degraded indicates the service provided by the 
      component is degraded in some way, such as in speed or operating 
      capacity. However, the resource remains available for service. The 
      operationalState is enabled.
      
      The value notInstalled indicates the resource is not present. The 
      operationalState is disabled.
      
      The value logFull is not used.

      Description of bits:
      inTest(0)
      failed(1)
      powerOff(2)
      offLine(3)
      offDuty(4)
      dependency(5)
      degraded(6)
      notInstalled(7)
      logFull(8)"
::= { mscShelfBusStateEntry 4 }

mscShelfBusProceduralStatus OBJECT-TYPE
   SYNTAX     OCTET STRING (SIZE (1))
   ACCESS     read-only
   STATUS     mandatory
   DESCRIPTION
     "If supported by the component, this attribute indicates the OSI 
      Procedural status of the component. Note that, even though it is 
      defined as a multi-valued set, at most one value is shown to the user.
      
      When no values are in the set, this indicates that either the attribute 
      is not supported or that none of the status conditions described 
      below are present.
      
      The value initializationRequired indicates (for a resource which 
      doesn't initialize autonomously) that initialization is required before 
      it can perform its normal functions, and this procedure has not been 
      initiated. The operationalState is disabled.
      
      The value notInitialized indicates (for a resource which does 
      initialize autonomously) that initialization is required before it can 
      perform its normal functions, and this procedure has not been 
      initiated. The operationalState may be enabled or disabled.
      
      The value initializing indicates that initialization has been initiated 
      but is not yet complete. The operationalState may be enabled or 
      disabled.
      
      The value reporting indicates the resource has completed some 
      processing operation and is notifying the results. The 
      operationalState is enabled.
      
      The value terminating indicates the component is in a termination 
      phase. If the resource doesn't reinitialize autonomously, 
      operationalState is disabled; otherwise it is enabled or disabled.

      Description of bits:
      initializationRequired(0)
      notInitialized(1)
      initializing(2)
      reporting(3)
      terminating(4)"
::= { mscShelfBusStateEntry 5 }

mscShelfBusControlStatus OBJECT-TYPE
   SYNTAX     OCTET STRING (SIZE (1))
   ACCESS     read-only
   STATUS     mandatory
   DESCRIPTION
     "If supported by the component, this attribute indicates the OSI 
      Control status of the component. Note that, even though it is defined 
      as a multi-valued set, at most one value is shown to the user.
      
      When no values are in the set, this indicates that either the attribute 
      is not supported or that none of the status conditions described 
      below are present.
      
      The value subjectToTest indicates the resource is available but tests 
      may be conducted simultaneously at unpredictable times, which 
      may cause it to exhibit unusual characteristics.
      
      The value partOfServicesLocked indicates that part of the service is 
      restricted from users of a resource. The adminState is unlocked.
      
      The value reservedForTest indicates that the component is 
      administratively unavailable because it is undergoing a test 
      procedure. The adminState is locked.
      
      The value suspended indicates that the service has been 
      administratively suspended.

      Description of bits:
      subjectToTest(0)
      partOfServicesLocked(1)
      reservedForTest(2)
      suspended(3)"
::= { mscShelfBusStateEntry 6 }

mscShelfBusAlarmStatus OBJECT-TYPE
   SYNTAX     OCTET STRING (SIZE (1))
   ACCESS     read-only
   STATUS     mandatory
   DESCRIPTION
     "If supported by the component, this attribute indicates the OSI 
      Alarm status of the component. Note that, even though it is defined 
      as a multi-valued set, at most one value is shown to the user.
      
      When no values are in the set, this indicates that either the attribute 
      is not supported or that none of the status conditions described 
      below are present.
      
      The value underRepair indicates the component is currently being 
      repaired. The operationalState is enabled or disabled.
      
      The value critical indicates one or more critical alarms are 
      outstanding against the component. Other, less severe, alarms may 
      also be outstanding. The operationalState is enabled or disabled.
      
      The value major indicates one or more major alarms are 
      outstanding against the component. Other, less severe, alarms may 
      also be outstanding. The operationalState is enabled or disabled.
      
      The value minor indicates one or more minor alarms are 
      outstanding against the component. Other, less severe, alarms may 
      also be outstanding. The operationalState is enabled or disabled.
      
      The value alarmOutstanding generically indicates that an alarm of 
      some severity is outstanding against the component.

      Description of bits:
      underRepair(0)
      critical(1)
      major(2)
      minor(3)
      alarmOutstanding(4)"
::= { mscShelfBusStateEntry 7 }

mscShelfBusStandbyStatus OBJECT-TYPE
   SYNTAX     INTEGER  {
                 hotStandby(0),
                 coldStandby(1),
                 providingService(2),
                 notSet(15) }
   ACCESS     read-only
   STATUS     mandatory
   DESCRIPTION
     "If supported by the component, this attribute indicates the OSI 
      Standby status of the component.
      
      The value notSet indicates that either the attribute is not supported 
      or that none of the status conditions described below are present. 
      Note that this is a non-standard value, used because the original 
      specification indicated this attribute was set-valued and thus, did not 
      provide a value to indicate that none of the other three are 
      applicable.
      
      The value hotStandby indicates that the resource is not providing 
      service but will be immediately able to take over the role of the 
      resource to be backed up, without initialization activity, and 
      containing the same information as the resource to be backed up.
      
      The value coldStandby indicates the resource is a backup for 
      another resource but will not be immediately able to take over the 
      role of the backed up resource and will require some initialization 
      activity.
      
      The value providingService indicates that this component, as a 
      backup resource, is currently backing up another resource."
   DEFVAL     { notSet }
::= { mscShelfBusStateEntry 8 }

mscShelfBusUnknownStatus OBJECT-TYPE
   SYNTAX     INTEGER  {
                 false(0),
                 true(1) }
   ACCESS     read-only
   STATUS     mandatory
   DESCRIPTION
     "This attribute indicates the OSI Unknown status of the component.
      
      The value false indicates that all of the other OSI State and Status 
      attribute values can be considered accurate.
      
      The value true indicates that the actual state of the component is not 
      known for sure."
   DEFVAL     { false }
::= { mscShelfBusStateEntry 9 }

mscShelfBusOperTable OBJECT-TYPE
   SYNTAX     SEQUENCE OF MscShelfBusOperEntry
   ACCESS     not-accessible
   STATUS     mandatory
   DESCRIPTION
     "This attribute group contains operational attributes of a bus."
::= { mscShelfBus 11 }

mscShelfBusOperEntry OBJECT-TYPE
   SYNTAX     MscShelfBusOperEntry
   ACCESS     not-accessible
   STATUS     mandatory
   DESCRIPTION
     "An entry in the mscShelfBusOperTable."
   INDEX {
      mscShelfIndex,
      mscShelfBusIndex }
::= { mscShelfBusOperTable 1 }

MscShelfBusOperEntry ::= SEQUENCE {
   mscShelfBusClockSource
      INTEGER,
   mscShelfBusUtilization
      Unsigned32 }

mscShelfBusClockSource OBJECT-TYPE
   SYNTAX     INTEGER  {
                 activeCP(0),
                 alternate(1) }
   ACCESS     read-only
   STATUS     mandatory
   DESCRIPTION
     "This attribute records the source of the fundamental clock signal 
      and end-of-cell synchronization signal used by the bus. It contains 
      one of the following values.
      activeCP: the card which is the active control processor (CP) is 
      providing clock signals
      alternate: the card at the opposite end of the module from the active 
      CP is providing clock signals"
::= { mscShelfBusOperEntry 1 }

mscShelfBusUtilization OBJECT-TYPE
   SYNTAX     Unsigned32 (0..100)
   ACCESS     read-only
   STATUS     mandatory
   DESCRIPTION
     "This attribute records how much of the available bus bandwidth was 
      actually used during the most recently sampled 1 second interval. 
      The value is expressed as a percentage."
::= { mscShelfBusOperEntry 2 }

mscShelfBusBusTapStatusTable OBJECT-TYPE
   SYNTAX     SEQUENCE OF MscShelfBusBusTapStatusEntry
   ACCESS     not-accessible
   STATUS     mandatory
   DESCRIPTION
     "This attribute records the operability of each bus tap on the bus, as 
      reported by the associated BusTap component; the entries are 
      indexed by slot number of the card. Each entry contains one of the 
      following values.
      ok: the bus tap is operational
      failed: the bus tap has failed
      none: the bus tap status is not availablethe associated BusTap 
      component does not currently exist"
::= { mscShelfBus 246 }

mscShelfBusBusTapStatusEntry OBJECT-TYPE
   SYNTAX     MscShelfBusBusTapStatusEntry
   ACCESS     not-accessible
   STATUS     mandatory
   DESCRIPTION
     "An entry in the mscShelfBusBusTapStatusTable."
   INDEX {
      mscShelfIndex,
      mscShelfBusIndex,
      mscShelfBusBusTapStatusIndex }
::= { mscShelfBusBusTapStatusTable 1 }

MscShelfBusBusTapStatusEntry ::= SEQUENCE {
   mscShelfBusBusTapStatusIndex
      Integer32,
   mscShelfBusBusTapStatusValue
      INTEGER }

mscShelfBusBusTapStatusIndex OBJECT-TYPE
   SYNTAX     Integer32 (0..15)
   ACCESS     not-accessible
   STATUS     mandatory
   DESCRIPTION
     "This variable represents the mscShelfBusBusTapStatusTable
      specific index for the mscShelfBusBusTapStatusTable."
::= { mscShelfBusBusTapStatusEntry 1 }

mscShelfBusBusTapStatusValue OBJECT-TYPE
   SYNTAX     INTEGER  {
                 ok(0),
                 failed(1),
                 none(2) }
   ACCESS     read-only
   STATUS     mandatory
   DESCRIPTION
     "This variable represents an individual value for the
      mscShelfBusBusTapStatusTable."
::= { mscShelfBusBusTapStatusEntry 2 }

mscShelfBusClockSourceStatusTable OBJECT-TYPE
   SYNTAX     SEQUENCE OF MscShelfBusClockSourceStatusEntry
   ACCESS     not-accessible
   STATUS     mandatory
   DESCRIPTION
     "This vector attribute, indexed with activeCP or alternate, represents 
      the state of the bus clock sources. It can be set to one of the 
      following values:
      ok: all operational cards can receive signals from the clock source.
      failed: at least one operational card is unable to receive signals from 
      the clock source.
      unknown: status of a clock source is unknown. To determine the 
      status of the clock source, a test must be run.
      testInProgress: the clock source is currently being tested.
      notApplicable: the LP state of the clock source's card is down or 
      not provisioned."
::= { mscShelfBus 247 }

mscShelfBusClockSourceStatusEntry OBJECT-TYPE
   SYNTAX     MscShelfBusClockSourceStatusEntry
   ACCESS     not-accessible
   STATUS     mandatory
   DESCRIPTION
     "An entry in the mscShelfBusClockSourceStatusTable."
   INDEX {
      mscShelfIndex,
      mscShelfBusIndex,
      mscShelfBusClockSourceStatusIndex }
::= { mscShelfBusClockSourceStatusTable 1 }

MscShelfBusClockSourceStatusEntry ::= SEQUENCE {
   mscShelfBusClockSourceStatusIndex
      INTEGER,
   mscShelfBusClockSourceStatusValue
      INTEGER }

mscShelfBusClockSourceStatusIndex OBJECT-TYPE
   SYNTAX     INTEGER  {
                 activeCP(0),
                 alternate(1) }
   ACCESS     not-accessible
   STATUS     mandatory
   DESCRIPTION
     "This variable represents the mscShelfBusClockSourceStatusTable
      specific index for the mscShelfBusClockSourceStatusTable."
::= { mscShelfBusClockSourceStatusEntry 1 }

mscShelfBusClockSourceStatusValue OBJECT-TYPE
   SYNTAX     INTEGER  {
                 ok(0),
                 failed(1),
                 unknown(2),
                 testInProgress(3),
                 notApplicable(4) }
   ACCESS     read-only
   STATUS     mandatory
   DESCRIPTION
     "This variable represents an individual value for the
      mscShelfBusClockSourceStatusTable."
::= { mscShelfBusClockSourceStatusEntry 2 }


-- Shelf Bus/b Test
-- The Test component is used to verify the operation of a bus. A bus 
-- test may be run as part of a regular maintenance program, or to 
-- diagnose the cause of a bus-related problem. The Test component is 
-- created automatically, and cannot be added or deleted.
-- 
-- The bus test ensures that the bus taps on a specific bus are 
-- functioning properly at minimal utilization rates. The bus to be 
-- tested must be locked while testing is in progress. The test only 
-- involves bus taps on operational cards (active and standby LPs). If 
-- an operational card becomes non-operational or fails to respond 
-- during the test, it is dropped from the test and is not allowed to 
-- rejoin; however, the results of any tests on its bus tap up to that 
-- point are preserved. The results of the test can help to determine 
-- which portions of the bus system are faulty, if any.
-- 
-- A bus test is composed of several different tests. The tests are 
-- performed in the following order.
-- 1) Bus tap self-test: Each bus tap executes its self-test.
-- 2) Clock source test: Each bus tap ensures that it can receive clock 
-- signals from the active control processor clock source and the 
-- alternate clock source (if present).
-- 3) Broadcast test: Each bus tap ensures that it can receive a 
-- broadcast frame over the backplane from every operational card 
-- (including itself).
-- 4) Ping test: Each bus tap ensures that it can receive a low priority 
-- non-broadcast frame over the backplane from every operational 
-- card (including itself).
-- Once all of the tests have been performed, the ping test is repeated 
-- continuously until the bus test is terminated; this repetition helps to 
-- detect transient bus faults. The bus test stops automatically after a 
-- specified time interval, or if it detects a bus tap self-test failure, an 
-- active control processor clock source test failure, or a broadcast test 
-- failure.

mscShelfBusTest OBJECT IDENTIFIER ::= { mscShelfBus 2 }



mscShelfBusTestRowStatusTable OBJECT-TYPE
   SYNTAX     SEQUENCE OF MscShelfBusTestRowStatusEntry
   ACCESS     not-accessible
   STATUS     mandatory
   DESCRIPTION
     "This entry controls the addition and deletion of 
      mscShelfBusTest components."
::= { mscShelfBusTest 1 }

mscShelfBusTestRowStatusEntry OBJECT-TYPE
   SYNTAX     MscShelfBusTestRowStatusEntry
   ACCESS     not-accessible
   STATUS     mandatory
   DESCRIPTION
     "A single entry in the table represents a single 
      mscShelfBusTest component."
   INDEX {
      mscShelfIndex,
      mscShelfBusIndex,
      mscShelfBusTestIndex }
::= { mscShelfBusTestRowStatusTable 1 }

MscShelfBusTestRowStatusEntry ::= SEQUENCE {
   mscShelfBusTestRowStatus
      RowStatus,
   mscShelfBusTestComponentName
      DisplayString,
   mscShelfBusTestStorageType
      StorageType,
   mscShelfBusTestIndex
      NonReplicated }

mscShelfBusTestRowStatus OBJECT-TYPE
   SYNTAX     RowStatus 
   ACCESS     read-only
   STATUS     mandatory
   DESCRIPTION
     "This variable is used as the basis for SNMP naming of
      mscShelfBusTest components.
      These components cannot be added nor deleted."
::= { mscShelfBusTestRowStatusEntry 1 }

mscShelfBusTestComponentName OBJECT-TYPE
   SYNTAX     DisplayString 
   ACCESS     read-only
   STATUS     mandatory
   DESCRIPTION
     "This variable provides the component's string name for
      use with the ASCII Console Interface"
::= { mscShelfBusTestRowStatusEntry 2 }

mscShelfBusTestStorageType OBJECT-TYPE
   SYNTAX     StorageType 
   ACCESS     read-only
   STATUS     mandatory
   DESCRIPTION
     "This variable represents the storage type value for the
      mscShelfBusTest tables."
::= { mscShelfBusTestRowStatusEntry 4 }

mscShelfBusTestIndex OBJECT-TYPE
   SYNTAX     NonReplicated 
   ACCESS     not-accessible
   STATUS     mandatory
   DESCRIPTION
     "This variable represents the index for the mscShelfBusTest tables."
::= { mscShelfBusTestRowStatusEntry 10 }

mscShelfBusTestStateTable OBJECT-TYPE
   SYNTAX     SEQUENCE OF MscShelfBusTestStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscShelfBusTest 10 }

mscShelfBusTestStateEntry OBJECT-TYPE
   SYNTAX     MscShelfBusTestStateEntry
   ACCESS     not-accessible
   STATUS     mandatory
   DESCRIPTION
     "An entry in the mscShelfBusTestStateTable."
   INDEX {
      mscShelfIndex,
      mscShelfBusIndex,
      mscShelfBusTestIndex }
::= { mscShelfBusTestStateTable 1 }

MscShelfBusTestStateEntry ::= SEQUENCE {
   mscShelfBusTestAdminState
      INTEGER,
   mscShelfBusTestOperationalState
      INTEGER,
   mscShelfBusTestUsageState
      INTEGER }

mscShelfBusTestAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscShelfBusTestStateEntry 1 }

mscShelfBusTestOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscShelfBusTestStateEntry 2 }

mscShelfBusTestUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscShelfBusTestStateEntry 3 }

mscShelfBusTestSetupTable OBJECT-TYPE
   SYNTAX     SEQUENCE OF MscShelfBusTestSetupEntry
   ACCESS     not-accessible
   STATUS     mandatory
   DESCRIPTION
     "This attribute group contains the attributes that govern the operation 
      of a bus test. These attributes cannot be changed while the bus test 
      is running."
::= { mscShelfBusTest 11 }

mscShelfBusTestSetupEntry OBJECT-TYPE
   SYNTAX     MscShelfBusTestSetupEntry
   ACCESS     not-accessible
   STATUS     mandatory
   DESCRIPTION
     "An entry in the mscShelfBusTestSetupTable."
   INDEX {
      mscShelfIndex,
      mscShelfBusIndex,
      mscShelfBusTestIndex }
::= { mscShelfBusTestSetupTable 1 }

MscShelfBusTestSetupEntry ::= SEQUENCE {
   mscShelfBusTestDuration
      Unsigned32 }

mscShelfBusTestDuration OBJECT-TYPE
   SYNTAX     Unsigned32 (1..43200)
   ACCESS     read-write
   STATUS     mandatory
   DESCRIPTION
     "This attribute specifies the maximum length of time that the bus test 
      is allowed to run. The value is expressed in minutes. The maximum 
      allowed value permits the bus test to be run for up to 30 days."
   DEFVAL     { 1 }
::= { mscShelfBusTestSetupEntry 1 }

mscShelfBusTestResultsTable OBJECT-TYPE
   SYNTAX     SEQUENCE OF MscShelfBusTestResultsEntry
   ACCESS     not-accessible
   STATUS     mandatory
   DESCRIPTION
     "This attribute group contains the results of the bus test that is 
      currently running; if no bus test is running, the attribute group 
      contains the results of the most recently completed bus test. The 
      attributes of the Results group are reset to their initial values 
      whenever a bus test is started or any attribute in the Setup group is 
      set."
::= { mscShelfBusTest 12 }

mscShelfBusTestResultsEntry OBJECT-TYPE
   SYNTAX     MscShelfBusTestResultsEntry
   ACCESS     not-accessible
   STATUS     mandatory
   DESCRIPTION
     "An entry in the mscShelfBusTestResultsTable."
   INDEX {
      mscShelfIndex,
      mscShelfBusIndex,
      mscShelfBusTestIndex }
::= { mscShelfBusTestResultsTable 1 }

MscShelfBusTestResultsEntry ::= SEQUENCE {
   mscShelfBusTestElapsedTime
      Unsigned32,
   mscShelfBusTestTimeRemaining
      Unsigned32,
   mscShelfBusTestCauseOfTermination
      INTEGER,
   mscShelfBusTestTestsDone
      OCTET STRING }

mscShelfBusTestElapsedTime OBJECT-TYPE
   SYNTAX     Unsigned32 (0..43200)
   ACCESS     read-only
   STATUS     mandatory
   DESCRIPTION
     "This attribute records the length of time (in minutes) that the bus 
      test has been running."
::= { mscShelfBusTestResultsEntry 1 }

mscShelfBusTestTimeRemaining OBJECT-TYPE
   SYNTAX     Unsigned32 (0..43200)
   ACCESS     read-only
   STATUS     mandatory
   DESCRIPTION
     "This attribute records the maximum length of time (in minutes) that 
      the bus test will continue to run before stopping."
::= { mscShelfBusTestResultsEntry 2 }

mscShelfBusTestCauseOfTermination OBJECT-TYPE
   SYNTAX     INTEGER  {
                 neverStarted(0),
                 testRunning(1),
                 testTimeExpired(2),
                 stoppedByOperator(3),
                 selfTestFailure(4),
                 clockSourceFailure(5),
                 broadcastFailure(6) }
   ACCESS     read-only
   STATUS     mandatory
   DESCRIPTION
     "This attribute records the reason the bus test ended. It contains one 
      of the following values.
      neverStarted: the bus test has not been started
      testRunning: the bus test is currently running
      testTimeExpired: the bus test ran for the specified duration
      stoppedByOperator: a STOP command was issued
      selfTestFailure: a failure was detected during the bus tap self-test
      clockSourceFailure: a failure was detected during the test of the 
      active control processor (CP) clock source
      broadcastFailure: a failure was detected during the broadcast test"
::= { mscShelfBusTestResultsEntry 3 }

mscShelfBusTestTestsDone OBJECT-TYPE
   SYNTAX     OCTET STRING (SIZE (1))
   ACCESS     read-only
   STATUS     mandatory
   DESCRIPTION
     "This attribute records the tests that have been performed during the 
      bus test. It may contain zero or more of the following values.
      selfTest: the bus tap self-test has been performed
      clockSourceTest: the clock source test has been performed
      broadcastTest: the broadcast test has been performed
      pingTest: at least one ping test has been performed

      Description of bits:
      selfTest(0)
      clockSourceTest(1)
      broadcastTest(2)
      pingTest(3)"
::= { mscShelfBusTestResultsEntry 4 }

mscShelfBusTestSelfTestResultsTable OBJECT-TYPE
   SYNTAX     SEQUENCE OF MscShelfBusTestSelfTestResultsEntry
   ACCESS     not-accessible
   STATUS     mandatory
   DESCRIPTION
     "This attribute records the results of the bus tap self-test, indexed by 
      the slot number of the card containing the bus tap tested. Each entry 
      contains one of the following values.
      +: the bus tap passed its self-test
      X: the bus tap failed its self-test
      .: the bus tap was not tested
      The bus test terminates automatically if a failure is detected."
::= { mscShelfBusTest 248 }

mscShelfBusTestSelfTestResultsEntry OBJECT-TYPE
   SYNTAX     MscShelfBusTestSelfTestResultsEntry
   ACCESS     not-accessible
   STATUS     mandatory
   DESCRIPTION
     "An entry in the mscShelfBusTestSelfTestResultsTable."
   INDEX {
      mscShelfIndex,
      mscShelfBusIndex,
      mscShelfBusTestIndex,
      mscShelfBusTestSelfTestResultsIndex }
::= { mscShelfBusTestSelfTestResultsTable 1 }

MscShelfBusTestSelfTestResultsEntry ::= SEQUENCE {
   mscShelfBusTestSelfTestResultsIndex
      Integer32,
   mscShelfBusTestSelfTestResultsValue
      INTEGER }

mscShelfBusTestSelfTestResultsIndex OBJECT-TYPE
   SYNTAX     Integer32 (0..15)
   ACCESS     not-accessible
   STATUS     mandatory
   DESCRIPTION
     "This variable represents the mscShelfBusTestSelfTestResultsTable
      specific index for the mscShelfBusTestSelfTestResultsTable."
::= { mscShelfBusTestSelfTestResultsEntry 1 }

mscShelfBusTestSelfTestResultsValue OBJECT-TYPE
   SYNTAX     INTEGER  {
                 x(0),
                 n1(1),
                 n2(2) }
   ACCESS     read-only
   STATUS     mandatory
   DESCRIPTION
     "This variable represents an individual value for the
      mscShelfBusTestSelfTestResultsTable."
::= { mscShelfBusTestSelfTestResultsEntry 2 }

mscShelfBusTestClockSourceTestResultsTable OBJECT-TYPE
   SYNTAX     SEQUENCE OF MscShelfBusTestClockSourceTestResultsEntry
   ACCESS     not-accessible
   STATUS     mandatory
   DESCRIPTION
     "This attribute records the results of the clock source test, indexed by 
      the clock source and the slot number of the card containing the bus 
      tap tested. Each entry contains one of the following values.
      +: the bus tap was able to receive clock signals from the clock 
      source
      X: the bus tap was unable to receive clock signals from the clock 
      source
      .: the bus tap was not tested against the clock source
      The bus test terminates automatically if a failure is detected 
      involving the active control processor (CP) clock source."
::= { mscShelfBusTest 249 }

mscShelfBusTestClockSourceTestResultsEntry OBJECT-TYPE
   SYNTAX     MscShelfBusTestClockSourceTestResultsEntry
   ACCESS     not-accessible
   STATUS     mandatory
   DESCRIPTION
     "An entry in the mscShelfBusTestClockSourceTestResultsTable."
   INDEX {
      mscShelfIndex,
      mscShelfBusIndex,
      mscShelfBusTestIndex,
      mscShelfBusTestClockSourceTestResultsSourceIndex,
      mscShelfBusTestClockSourceTestResultsCardIndex }
::= { mscShelfBusTestClockSourceTestResultsTable 1 }

MscShelfBusTestClockSourceTestResultsEntry ::= SEQUENCE {
   mscShelfBusTestClockSourceTestResultsSourceIndex
      INTEGER,
   mscShelfBusTestClockSourceTestResultsCardIndex
      Integer32,
   mscShelfBusTestClockSourceTestResultsValue
      INTEGER }

mscShelfBusTestClockSourceTestResultsSourceIndex OBJECT-TYPE
   SYNTAX     INTEGER  {
                 activeCP(0),
                 alternate(1) }
   ACCESS     not-accessible
   STATUS     mandatory
   DESCRIPTION
     "This variable represents the next to last index for the 
      mscShelfBusTestClockSourceTestResultsTable."
::= { mscShelfBusTestClockSourceTestResultsEntry 1 }

mscShelfBusTestClockSourceTestResultsCardIndex OBJECT-TYPE
   SYNTAX     Integer32 (0..15)
   ACCESS     not-accessible
   STATUS     mandatory
   DESCRIPTION
     "This variable represents the final index for the 
      mscShelfBusTestClockSourceTestResultsTable."
::= { mscShelfBusTestClockSourceTestResultsEntry 2 }

mscShelfBusTestClockSourceTestResultsValue OBJECT-TYPE
   SYNTAX     INTEGER  {
                 x(0),
                 n1(1),
                 n2(2) }
   ACCESS     read-only
   STATUS     mandatory
   DESCRIPTION
     "This variable represents an individual value for the
      mscShelfBusTestClockSourceTestResultsTable."
::= { mscShelfBusTestClockSourceTestResultsEntry 3 }

mscShelfBusTestBroadcastTestResultsTable OBJECT-TYPE
   SYNTAX     SEQUENCE OF MscShelfBusTestBroadcastTestResultsEntry
   ACCESS     not-accessible
   STATUS     mandatory
   DESCRIPTION
     "This attribute records the results of the broadcast test, indexed by 
      the slot numbers of the cards containing the bus taps tested. Each 
      entry contains one of the following values.
      +: a broadcast message was successfully sent from the transmitting 
      bus tap to the receiving bus tap 
      X: a broadcast message was not successfully sent from the 
      transmitting bus tap to the receiving bus tap
      .: the associated pair of bus taps was not tested 
      The bus test terminates automatically if a failure is detected."
::= { mscShelfBusTest 250 }

mscShelfBusTestBroadcastTestResultsEntry OBJECT-TYPE
   SYNTAX     MscShelfBusTestBroadcastTestResultsEntry
   ACCESS     not-accessible
   STATUS     mandatory
   DESCRIPTION
     "An entry in the mscShelfBusTestBroadcastTestResultsTable."
   INDEX {
      mscShelfIndex,
      mscShelfBusIndex,
      mscShelfBusTestIndex,
      mscShelfBusTestBroadcastTestResultsTxCardIndex,
      mscShelfBusTestBroadcastTestResultsRxCardIndex }
::= { mscShelfBusTestBroadcastTestResultsTable 1 }

MscShelfBusTestBroadcastTestResultsEntry ::= SEQUENCE {
   mscShelfBusTestBroadcastTestResultsTxCardIndex
      Integer32,
   mscShelfBusTestBroadcastTestResultsRxCardIndex
      Integer32,
   mscShelfBusTestBroadcastTestResultsValue
      INTEGER }

mscShelfBusTestBroadcastTestResultsTxCardIndex OBJECT-TYPE
   SYNTAX     Integer32 (0..15)
   ACCESS     not-accessible
   STATUS     mandatory
   DESCRIPTION
     "This variable represents the next to last index for the 
      mscShelfBusTestBroadcastTestResultsTable."
::= { mscShelfBusTestBroadcastTestResultsEntry 1 }

mscShelfBusTestBroadcastTestResultsRxCardIndex OBJECT-TYPE
   SYNTAX     Integer32 (0..15)
   ACCESS     not-accessible
   STATUS     mandatory
   DESCRIPTION
     "This variable represents the final index for the 
      mscShelfBusTestBroadcastTestResultsTable."
::= { mscShelfBusTestBroadcastTestResultsEntry 2 }

mscShelfBusTestBroadcastTestResultsValue OBJECT-TYPE
   SYNTAX     INTEGER  {
                 x(0),
                 n1(1),
                 n2(2) }
   ACCESS     read-only
   STATUS     mandatory
   DESCRIPTION
     "This variable represents an individual value for the
      mscShelfBusTestBroadcastTestResultsTable."
::= { mscShelfBusTestBroadcastTestResultsEntry 3 }

mscShelfBusTestPingTestsTable OBJECT-TYPE
   SYNTAX     SEQUENCE OF MscShelfBusTestPingTestsEntry
   ACCESS     not-accessible
   STATUS     mandatory
   DESCRIPTION
     "This attribute records the number of ping tests performed, indexed 
      by the slot numbers of the cards containing the bus taps involved. 
      Each test attempts to transmit a single low-priority frame from the 
      transmitting bus tap to the receiving bus tap."
::= { mscShelfBusTest 251 }

mscShelfBusTestPingTestsEntry OBJECT-TYPE
   SYNTAX     MscShelfBusTestPingTestsEntry
   ACCESS     not-accessible
   STATUS     mandatory
   DESCRIPTION
     "An entry in the mscShelfBusTestPingTestsTable."
   INDEX {
      mscShelfIndex,
      mscShelfBusIndex,
      mscShelfBusTestIndex,
      mscShelfBusTestPingTestsTxCardIndex,
      mscShelfBusTestPingTestsRxCardIndex }
::= { mscShelfBusTestPingTestsTable 1 }

MscShelfBusTestPingTestsEntry ::= SEQUENCE {
   mscShelfBusTestPingTestsTxCardIndex
      Integer32,
   mscShelfBusTestPingTestsRxCardIndex
      Integer32,
   mscShelfBusTestPingTestsValue
      Unsigned32 }

mscShelfBusTestPingTestsTxCardIndex OBJECT-TYPE
   SYNTAX     Integer32 (0..15)
   ACCESS     not-accessible
   STATUS     mandatory
   DESCRIPTION
     "This variable represents the next to last index for the 
      mscShelfBusTestPingTestsTable."
::= { mscShelfBusTestPingTestsEntry 1 }

mscShelfBusTestPingTestsRxCardIndex OBJECT-TYPE
   SYNTAX     Integer32 (0..15)
   ACCESS     not-accessible
   STATUS     mandatory
   DESCRIPTION
     "This variable represents the final index for the 
      mscShelfBusTestPingTestsTable."
::= { mscShelfBusTestPingTestsEntry 2 }

mscShelfBusTestPingTestsValue OBJECT-TYPE
   SYNTAX     Unsigned32 (0..4294967295)
   ACCESS     read-only
   STATUS     mandatory
   DESCRIPTION
     "This variable represents an individual value for the
      mscShelfBusTestPingTestsTable."
::= { mscShelfBusTestPingTestsEntry 3 }

mscShelfBusTestPingFailuresTable OBJECT-TYPE
   SYNTAX     SEQUENCE OF MscShelfBusTestPingFailuresEntry
   ACCESS     not-accessible
   STATUS     mandatory
   DESCRIPTION
     "This attribute records the number of ping test failures detected, 
      indexed by the slot numbers of the cards containing the bus taps 
      involved. Each failure represents a single low-priority frame that 
      was not successfully transmitted from the transmitting bus tap to the 
      receiving bus tap. The bus test does not terminate automatically if a 
      failure is detected."
::= { mscShelfBusTest 252 }

mscShelfBusTestPingFailuresEntry OBJECT-TYPE
   SYNTAX     MscShelfBusTestPingFailuresEntry
   ACCESS     not-accessible
   STATUS     mandatory
   DESCRIPTION
     "An entry in the mscShelfBusTestPingFailuresTable."
   INDEX {
      mscShelfIndex,
      mscShelfBusIndex,
      mscShelfBusTestIndex,
      mscShelfBusTestPingFailuresTxCardIndex,
      mscShelfBusTestPingFailuresRxCardIndex }
::= { mscShelfBusTestPingFailuresTable 1 }

MscShelfBusTestPingFailuresEntry ::= SEQUENCE {
   mscShelfBusTestPingFailuresTxCardIndex
      Integer32,
   mscShelfBusTestPingFailuresRxCardIndex
      Integer32,
   mscShelfBusTestPingFailuresValue
      Unsigned32 }

mscShelfBusTestPingFailuresTxCardIndex OBJECT-TYPE
   SYNTAX     Integer32 (0..15)
   ACCESS     not-accessible
   STATUS     mandatory
   DESCRIPTION
     "This variable represents the next to last index for the 
      mscShelfBusTestPingFailuresTable."
::= { mscShelfBusTestPingFailuresEntry 1 }

mscShelfBusTestPingFailuresRxCardIndex OBJECT-TYPE
   SYNTAX     Integer32 (0..15)
   ACCESS     not-accessible
   STATUS     mandatory
   DESCRIPTION
     "This variable represents the final index for the 
      mscShelfBusTestPingFailuresTable."
::= { mscShelfBusTestPingFailuresEntry 2 }

mscShelfBusTestPingFailuresValue OBJECT-TYPE
   SYNTAX     Unsigned32 (0..4294967295)
   ACCESS     read-only
   STATUS     mandatory
   DESCRIPTION
     "This variable represents an individual value for the
      mscShelfBusTestPingFailuresTable."
::= { mscShelfBusTestPingFailuresEntry 3 }


-- PcsTest
-- The PcsTest component allows automated tests of the Shelf to be 
-- controlled for regular execution.

mscShelfTest OBJECT IDENTIFIER ::= { mscShelf 4 }



mscShelfTestRowStatusTable OBJECT-TYPE
   SYNTAX     SEQUENCE OF MscShelfTestRowStatusEntry
   ACCESS     not-accessible
   STATUS     mandatory
   DESCRIPTION
     "This entry controls the addition and deletion of 
      mscShelfTest components."
::= { mscShelfTest 1 }

mscShelfTestRowStatusEntry OBJECT-TYPE
   SYNTAX     MscShelfTestRowStatusEntry
   ACCESS     not-accessible
   STATUS     mandatory
   DESCRIPTION
     "A single entry in the table represents a single 
      mscShelfTest component."
   INDEX {
      mscShelfIndex,
      mscShelfTestIndex }
::= { mscShelfTestRowStatusTable 1 }

MscShelfTestRowStatusEntry ::= SEQUENCE {
   mscShelfTestRowStatus
      RowStatus,
   mscShelfTestComponentName
      DisplayString,
   mscShelfTestStorageType
      StorageType,
   mscShelfTestIndex
      NonReplicated }

mscShelfTestRowStatus OBJECT-TYPE
   SYNTAX     RowStatus 
   ACCESS     read-only
   STATUS     mandatory
   DESCRIPTION
     "This variable is used as the basis for SNMP naming of
      mscShelfTest components.
      These components cannot be added nor deleted."
::= { mscShelfTestRowStatusEntry 1 }

mscShelfTestComponentName OBJECT-TYPE
   SYNTAX     DisplayString 
   ACCESS     read-only
   STATUS     mandatory
   DESCRIPTION
     "This variable provides the component's string name for
      use with the ASCII Console Interface"
::= { mscShelfTestRowStatusEntry 2 }

mscShelfTestStorageType OBJECT-TYPE
   SYNTAX     StorageType 
   ACCESS     read-only
   STATUS     mandatory
   DESCRIPTION
     "This variable represents the storage type value for the
      mscShelfTest tables."
::= { mscShelfTestRowStatusEntry 4 }

mscShelfTestIndex OBJECT-TYPE
   SYNTAX     NonReplicated 
   ACCESS     not-accessible
   STATUS     mandatory
   DESCRIPTION
     "This variable represents the index for the mscShelfTest tables."
::= { mscShelfTestRowStatusEntry 10 }

mscShelfTestProvTable OBJECT-TYPE
   SYNTAX     SEQUENCE OF MscShelfTestProvEntry
   ACCESS     not-accessible
   STATUS     mandatory
   DESCRIPTION
     "This group contains provisionable attributes of the Test component."
::= { mscShelfTest 10 }

mscShelfTestProvEntry OBJECT-TYPE
   SYNTAX     MscShelfTestProvEntry
   ACCESS     not-accessible
   STATUS     mandatory
   DESCRIPTION
     "An entry in the mscShelfTestProvTable."
   INDEX {
      mscShelfIndex,
      mscShelfTestIndex }
::= { mscShelfTestProvTable 1 }

MscShelfTestProvEntry ::= SEQUENCE {
   mscShelfTestAutomaticBusClockTest
      INTEGER }

mscShelfTestAutomaticBusClockTest OBJECT-TYPE
   SYNTAX     INTEGER  {
                 enabled(0),
                 disabled(1) }
   ACCESS     read-write
   STATUS     mandatory
   DESCRIPTION
     "This attribute specifies whether or not a bus clock source test is 
      automatically executed after a clock source's LP state changes, and 
      after failure or recovery of the active CP bus clock source. Since 
      tests of an alternate bus clock source may cause a minor loss of 
      traffic, the attribute is set to disabled by default.
      If set to enabled, a bus clock source test is automatically executed. 
      If the status of the corresponding Shelf Bus clockSourceStatus is 
      changed after the test, an alarm is issued if the status is one of the 
      following: ok, failed, or unknown.
      If set to disabled, no bus clock source test is automatically 
      executed. However, a test can be executed by the RUN command. If 
      the status is changed after the test, an alarm is issued if the status is 
      one of the following: ok, or failed."
   DEFVAL     { disabled }
::= { mscShelfTestProvEntry 1 }

mscShelfTestSetupTable OBJECT-TYPE
   SYNTAX     SEQUENCE OF MscShelfTestSetupEntry
   ACCESS     not-accessible
   STATUS     mandatory
   DESCRIPTION
     "This attribute group contains the attributes that govern the operation 
      of a shelf test."
::= { mscShelfTest 11 }

mscShelfTestSetupEntry OBJECT-TYPE
   SYNTAX     MscShelfTestSetupEntry
   ACCESS     not-accessible
   STATUS     mandatory
   DESCRIPTION
     "An entry in the mscShelfTestSetupTable."
   INDEX {
      mscShelfIndex,
      mscShelfTestIndex }
::= { mscShelfTestSetupTable 1 }

MscShelfTestSetupEntry ::= SEQUENCE {
   mscShelfTestType
      INTEGER }

mscShelfTestType OBJECT-TYPE
   SYNTAX     INTEGER  {
                 busClock(0) }
   ACCESS     read-write
   STATUS     mandatory
   DESCRIPTION
     "type
      The attribute determines the test to be executed when the RUN
      command is applied to the component. Note that running a 
      busClock test may cause a minor loss of traffic."
   DEFVAL     { busClock }
::= { mscShelfTestSetupEntry 1 }

mscShelfTestResultsTable OBJECT-TYPE
   SYNTAX     SEQUENCE OF MscShelfTestResultsEntry
   ACCESS     not-accessible
   STATUS     mandatory
   DESCRIPTION
     "This attribute group contains the results of the Shelf Test that is 
      currently running; if no test is running, the attribute group contains 
      the results of the most recently completed Shelf Test. The attributes 
      of the Results group are reset to their initial values whenever a 
      corresponding Shelf Test is run or the corresponding attribute of the 
      Setup group is set."
::= { mscShelfTest 12 }

mscShelfTestResultsEntry OBJECT-TYPE
   SYNTAX     MscShelfTestResultsEntry
   ACCESS     not-accessible
   STATUS     mandatory
   DESCRIPTION
     "An entry in the mscShelfTestResultsTable."
   INDEX {
      mscShelfIndex,
      mscShelfTestIndex }
::= { mscShelfTestResultsTable 1 }

MscShelfTestResultsEntry ::= SEQUENCE {
   mscShelfTestBusClockTestResult
      INTEGER }

mscShelfTestBusClockTestResult OBJECT-TYPE
   SYNTAX     INTEGER  {
                 noTest(0),
                 fail(1),
                 pass(2) }
   ACCESS     read-only
   STATUS     mandatory
   DESCRIPTION
     "busClockTestResult
      This attribute records the result of the bus clock manual test. The 
      result can be one of the following values.
      pass     : the test passed
      fail       : the test failed
      noTest  : the test was not executed when RUN command is issued, 
      because the shelf was in single bus mode."
::= { mscShelfTestResultsEntry 1 }




-- 
-- Version and Compliance statements
-- 



-- Object-Group Statement:
-- A list of all current accessible leaf objects.

-- OBJECTS { mscShelfBusTestDuration,
--           mscShelfBusProceduralStatus,
--           mscShelfCardBusTapFrmCongestionErrors,
--           mscShelfCardBusTapControlStatus,
--           mscShelfCardBusTapAdminState,
--           mscShelfCardBusTapEndOfCellErrors,
--           mscShelfTestType,
--           mscShelfBusClockSourceStatusValue,
--           mscShelfBusUsageState,
--           mscShelfCardBusTapRowStatus,
--           mscShelfCardBusTapFrmDeliveryErrors,
--           mscShelfCardBusTapProceduralStatus,
--           mscShelfCardBusTapFailuresInEffect,
--           mscShelfCardBusTapFrmTimeoutErrors,
--           mscShelfTestRowStatus,
--           mscShelfBusTestStorageType,
--           mscShelfCardBusTapFrmSizeErrors,
--           mscShelfBusTestPingFailuresValue,
--           mscShelfBusTestCauseOfTermination,
--           mscShelfCardBusTapUsageState,
--           mscShelfCardBusTapFrmCollisionErrors,
--           mscShelfBusOperationalState,
--           mscShelfBusTestTimeRemaining,
--           mscShelfCardBusTapComponentName,
--           mscShelfBusComponentName,
--           mscShelfBusTestAdminState,
--           mscShelfBusTestSelfTestResultsValue,
--           mscShelfCardBusTapOperationalState,
--           mscShelfBusTestElapsedTime,
--           mscShelfBusTestRowStatus,
--           mscShelfTestBusClockTestResult,
--           mscShelfBusBusTapStatusValue,
--           mscShelfBusAvailabilityStatus,
--           mscShelfCardBusTapSelfTestErrorCode,
--           mscShelfCardBusTapStandbyStatus,
--           mscShelfBusClockSource,
--           mscShelfTestComponentName,
--           mscShelfBusTestClockSourceTestResultsValue,
--           mscShelfBusAlarmStatus,
--           mscShelfBusTestUsageState,
--           mscShelfCardBusTapDependenciesInEffect,
--           mscShelfBusTestComponentName,
--           mscShelfBusStandbyStatus,
--           mscShelfCardBusTapAvailabilityStatus,
--           mscShelfBusStorageType,
--           mscShelfTestAutomaticBusClockTest,
--           mscShelfCardBusTapAlarmStatus,
--           mscShelfCardBusTapParityErrors,
--           mscShelfBusTestOperationalState,
--           mscShelfBusRowStatus,
--           mscShelfCardBusTapUnknownStatus,
--           mscShelfBusTestTestsDone,
--           mscShelfBusTestBroadcastTestResultsValue,
--           mscShelfBusUnknownStatus,
--           mscShelfCardBusTapStorageType,
--           mscShelfCardBusTapCardsTxTo,
--           mscShelfBusControlStatus,
--           mscShelfBusAdminState,
--           mscShelfCardBusTapCardsAvailable,
--           mscShelfBusTestPingTestsValue,
--           mscShelfCardBusTapClockErrors,
--           mscShelfTestStorageType,
--           mscShelfBusUtilization }
-- STATUS  mandatory
-- DESCRIPTION
--   "A list of all current accessible leaf objects."

busGroup OBJECT IDENTIFIER ::= { busMIB 1 }
busGroupCA OBJECT IDENTIFIER ::= { busGroup 1 }
busGroupCA02 OBJECT IDENTIFIER ::= { busGroupCA 3 }
busGroupCA02A OBJECT IDENTIFIER ::= { busGroupCA02 2 }



-- Agent-Capabilities Statement:

-- PRODUCT-RELEASE "MscPassport Release 1.2 Bus."
-- STATUS          mandatory
-- DESCRIPTION     "Carrier Passport Bus MIB: MIB Version CA02A,
--                  Software Version CA02S9C."
-- SUPPORTS        Nortel-MsCarrier-MscPassport-BusMIB
--    INCLUDES     { busGroupCA02A }

busCapabilities OBJECT IDENTIFIER ::= { busMIB 3 }
busCapabilitiesCA OBJECT IDENTIFIER ::= { busCapabilities 1 }
busCapabilitiesCA02 OBJECT IDENTIFIER ::= { busCapabilitiesCA 3 }
busCapabilitiesCA02A OBJECT IDENTIFIER ::= { busCapabilitiesCA02 2 }





END
