Nortel-MsCarrier-MscPassport-AtmPnniMIB
DEFINITIONS ::= BEGIN



IMPORTS

      OBJECT-TYPE
   FROM RFC-1212

      mscPassportMIBs
   FROM Nortel-MsCarrier-MscPassport-UsefulDefinitionsMIB

      Counter32,
      DisplayString,
      StorageType,
      RowStatus,
      Gauge32,
      Integer32,
      Unsigned32
   FROM Nortel-MsCarrier-MscPassport-StandardTextualConventionsMIB

      Hex,
      NonReplicated,
      HexString,
      FixedPoint1,
      AsciiStringIndex
   FROM Nortel-MsCarrier-MscPassport-TextualConventionsMIB

      mscAtmIf,
      mscAtmIfVptIndex,
      mscAtmIfVpt,
      mscAtmIfIndex
   FROM Nortel-MsCarrier-MscPassport-AtmCoreMIB;




-- LAST-UPDATED   "9909010000Z"
-- ORGANIZATION   "Nortel Networks"
-- CONTACT-INFO   "
--         Nortel Carrier Data Network Management
--         
--         Postal:       P.O. Box 3511, Station C 
--                       Ottawa, Ontario 
--                       Canada  K1Y 4H7
--         
--         via the WEB:  http://www.nortelnetworks.com  
--                       select 'Contact Us' from the menu
--          
--         via phone:    1-800-4NORTEL"
-- DESCRIPTION
--    "The module describing the Nortel MsCarrier MscPassport
--     AtmPnni Enterprise MIB."

atmPnniMIB OBJECT IDENTIFIER ::= { mscPassportMIBs 72 }










-- AtmIf/n VirtualPathTerminator/m Pnni
-- This component represents a virtual ATM Private Network-
-- Network Interface (PNNI) interface. If this component is 
-- provisioned, neither a Uni nor a Iisp component can be provisioned 
-- under the same Vpt component. Also, the ARtg Pnni component and 
-- the ConfiguredNode component corresponding to the participation 
-- of this node in a lowest level peer group must both exist if a Pnni 
-- component is to be provisioned under a Vpt component. If this 
-- component is deleted, then all associated Vcc components are 
-- deleted.

mscAtmIfVptPnni OBJECT IDENTIFIER ::= { mscAtmIfVpt 7 }



mscAtmIfVptPnniRowStatusTable OBJECT-TYPE
   SYNTAX     SEQUENCE OF MscAtmIfVptPnniRowStatusEntry
   ACCESS     not-accessible
   STATUS     mandatory
   DESCRIPTION
     "This entry controls the addition and deletion of 
      mscAtmIfVptPnni components."
::= { mscAtmIfVptPnni 1 }

mscAtmIfVptPnniRowStatusEntry OBJECT-TYPE
   SYNTAX     MscAtmIfVptPnniRowStatusEntry
   ACCESS     not-accessible
   STATUS     mandatory
   DESCRIPTION
     "A single entry in the table represents a single 
      mscAtmIfVptPnni component."
   INDEX {
      mscAtmIfIndex,
      mscAtmIfVptIndex,
      mscAtmIfVptPnniIndex }
::= { mscAtmIfVptPnniRowStatusTable 1 }

MscAtmIfVptPnniRowStatusEntry ::= SEQUENCE {
   mscAtmIfVptPnniRowStatus
      RowStatus,
   mscAtmIfVptPnniComponentName
      DisplayString,
   mscAtmIfVptPnniStorageType
      StorageType,
   mscAtmIfVptPnniIndex
      NonReplicated }

mscAtmIfVptPnniRowStatus OBJECT-TYPE
   SYNTAX     RowStatus 
   ACCESS     read-write
   STATUS     mandatory
   DESCRIPTION
     "This variable is used as the basis for SNMP naming of
      mscAtmIfVptPnni components.
      These components can be added and deleted."
::= { mscAtmIfVptPnniRowStatusEntry 1 }

mscAtmIfVptPnniComponentName OBJECT-TYPE
   SYNTAX     DisplayString 
   ACCESS     read-only
   STATUS     mandatory
   DESCRIPTION
     "This variable provides the component's string name for
      use with the ASCII Console Interface"
::= { mscAtmIfVptPnniRowStatusEntry 2 }

mscAtmIfVptPnniStorageType OBJECT-TYPE
   SYNTAX     StorageType 
   ACCESS     read-only
   STATUS     mandatory
   DESCRIPTION
     "This variable represents the storage type value for the
      mscAtmIfVptPnni tables."
::= { mscAtmIfVptPnniRowStatusEntry 4 }

mscAtmIfVptPnniIndex OBJECT-TYPE
   SYNTAX     NonReplicated 
   ACCESS     not-accessible
   STATUS     mandatory
   DESCRIPTION
     "This variable represents the index for the mscAtmIfVptPnni tables."
::= { mscAtmIfVptPnniRowStatusEntry 10 }

mscAtmIfVptPnniProvTable OBJECT-TYPE
   SYNTAX     SEQUENCE OF MscAtmIfVptPnniProvEntry
   ACCESS     not-accessible
   STATUS     mandatory
   DESCRIPTION
     "This group contains the provisionable attributes for the Pnni
      component."
::= { mscAtmIfVptPnni 10 }

mscAtmIfVptPnniProvEntry OBJECT-TYPE
   SYNTAX     MscAtmIfVptPnniProvEntry
   ACCESS     not-accessible
   STATUS     mandatory
   DESCRIPTION
     "An entry in the mscAtmIfVptPnniProvTable."
   INDEX {
      mscAtmIfIndex,
      mscAtmIfVptIndex,
      mscAtmIfVptPnniIndex }
::= { mscAtmIfVptPnniProvTable 1 }

MscAtmIfVptPnniProvEntry ::= SEQUENCE {
   mscAtmIfVptPnniSoftPvcRetryPeriod
      Unsigned32,
   mscAtmIfVptPnniSoftPvpAndPvcRetryPeriod
      Unsigned32,
   mscAtmIfVptPnniSoftPvpAndPvcHoldOffTime
      Unsigned32 }

mscAtmIfVptPnniSoftPvcRetryPeriod OBJECT-TYPE
   SYNTAX     Unsigned32 (20..999999)
   ACCESS     read-write
   STATUS     obsolete
   DESCRIPTION
     "This attribute represents the time in seconds to wait between call 
      setup retries. The resolution is to the nearest 10 seconds. 
      This attribute has been obsoleted and is replaced by the 
      softPvpAndPvcRetryPeriod attribute."
   DEFVAL     { 60 }
::= { mscAtmIfVptPnniProvEntry 1 }

mscAtmIfVptPnniSoftPvpAndPvcRetryPeriod OBJECT-TYPE
   SYNTAX     Unsigned32 (20..999999)
   ACCESS     read-write
   STATUS     mandatory
   DESCRIPTION
     "This attribute represents the time in seconds to wait between soft 
      PVP or soft PVC call  setup retries. The resolution is to the nearest 
      10 seconds."
   DEFVAL     { 60 }
::= { mscAtmIfVptPnniProvEntry 2 }

mscAtmIfVptPnniSoftPvpAndPvcHoldOffTime OBJECT-TYPE
   SYNTAX     Unsigned32 (0 | 50..20000)
   ACCESS     read-write
   STATUS     mandatory
   DESCRIPTION
     "This attribute specifies how long to hold off retries following a 
      release or the connection. The resolution is to the nearest 50 ms."
   DEFVAL     { 0 }
::= { mscAtmIfVptPnniProvEntry 5 }

mscAtmIfVptPnniAdminWeightsTable OBJECT-TYPE
   SYNTAX     SEQUENCE OF MscAtmIfVptPnniAdminWeightsEntry
   ACCESS     not-accessible
   STATUS     mandatory
   DESCRIPTION
     "This group contains the provisionable administrative weights for the 
      Pnni component. These weights will be used by Generic 
      Connection Admission Control (GCAC) if administrative weight is 
      the selected optimization criterion."
::= { mscAtmIfVptPnni 11 }

mscAtmIfVptPnniAdminWeightsEntry OBJECT-TYPE
   SYNTAX     MscAtmIfVptPnniAdminWeightsEntry
   ACCESS     not-accessible
   STATUS     mandatory
   DESCRIPTION
     "An entry in the mscAtmIfVptPnniAdminWeightsTable."
   INDEX {
      mscAtmIfIndex,
      mscAtmIfVptIndex,
      mscAtmIfVptPnniIndex }
::= { mscAtmIfVptPnniAdminWeightsTable 1 }

MscAtmIfVptPnniAdminWeightsEntry ::= SEQUENCE {
   mscAtmIfVptPnniCbrWeight
      Unsigned32,
   mscAtmIfVptPnniRtVbrWeight
      Unsigned32,
   mscAtmIfVptPnniNrtVbrWeight
      Unsigned32,
   mscAtmIfVptPnniUbrWeight
      Unsigned32 }

mscAtmIfVptPnniCbrWeight OBJECT-TYPE
   SYNTAX     Unsigned32 (0..4294967295)
   ACCESS     read-write
   STATUS     mandatory
   DESCRIPTION
     "This attribute specifies the administrative weight assigned for 
      setting up switched calls with a service category of Constant Bit 
      Rate (CBR) for this PNNI interface. The value specified will be 
      used by Generic Connection Admission Control (GCAC) if 
      administrative weight is the selected optimization criterion; the 
      higher the value, the less desirable the link will be in path selection."
   DEFVAL     { 5040 }
::= { mscAtmIfVptPnniAdminWeightsEntry 1 }

mscAtmIfVptPnniRtVbrWeight OBJECT-TYPE
   SYNTAX     Unsigned32 (0..4294967295)
   ACCESS     read-write
   STATUS     mandatory
   DESCRIPTION
     "This attribute specifies the administrative weight assigned for 
      setting up switched calls with a service category of Real-Time 
      Variable Bit Rate (RT-VBR) for this PNNI interface. The value 
      specified will be used by Generic Connection Admission Control 
      (GCAC) if administrative weight is the selected optimization 
      criterion; the higher the value, the less desirable the link will be in 
      path selection."
   DEFVAL     { 5040 }
::= { mscAtmIfVptPnniAdminWeightsEntry 2 }

mscAtmIfVptPnniNrtVbrWeight OBJECT-TYPE
   SYNTAX     Unsigned32 (0..4294967295)
   ACCESS     read-write
   STATUS     mandatory
   DESCRIPTION
     "This attribute specifies the administrative weight assigned for 
      setting up switched calls with a service category of Non Real-Time 
      Variable Bit Rate (NRT-VBR) for this PNNI interface. The value 
      specified will be used by Generic Connection Admission Control 
      (GCAC) if administrative weight is the selected optimization 
      criterion; the higher the value, the less desirable the link will be in 
      path selection."
   DEFVAL     { 5040 }
::= { mscAtmIfVptPnniAdminWeightsEntry 3 }

mscAtmIfVptPnniUbrWeight OBJECT-TYPE
   SYNTAX     Unsigned32 (0..4294967295)
   ACCESS     read-write
   STATUS     mandatory
   DESCRIPTION
     "This attribute specifies the administrative weight assigned for 
      setting up switched calls with a service category of Unspecified Bit 
      Rate (UBR) for this PNNI interface. The value specified will be 
      used by Generic Connection Admission Control (GCAC) if 
      administrative weight is the selected optimization criterion; the 
      higher the value, the less desirable the link will be in path selection."
   DEFVAL     { 5040 }
::= { mscAtmIfVptPnniAdminWeightsEntry 4 }

mscAtmIfVptPnniAcctOptTable OBJECT-TYPE
   SYNTAX     SEQUENCE OF MscAtmIfVptPnniAcctOptEntry
   ACCESS     not-accessible
   STATUS     mandatory
   DESCRIPTION
     "This group contains the provisionable attributes for accounting."
::= { mscAtmIfVptPnni 12 }

mscAtmIfVptPnniAcctOptEntry OBJECT-TYPE
   SYNTAX     MscAtmIfVptPnniAcctOptEntry
   ACCESS     not-accessible
   STATUS     mandatory
   DESCRIPTION
     "An entry in the mscAtmIfVptPnniAcctOptTable."
   INDEX {
      mscAtmIfIndex,
      mscAtmIfVptIndex,
      mscAtmIfVptPnniIndex }
::= { mscAtmIfVptPnniAcctOptTable 1 }

MscAtmIfVptPnniAcctOptEntry ::= SEQUENCE {
   mscAtmIfVptPnniAccountCollection
      OCTET STRING,
   mscAtmIfVptPnniAccountConnectionType
      INTEGER,
   mscAtmIfVptPnniAccountClass
      Unsigned32,
   mscAtmIfVptPnniServiceExchange
      Unsigned32 }

mscAtmIfVptPnniAccountCollection OBJECT-TYPE
   SYNTAX     OCTET STRING (SIZE (1))
   ACCESS     read-write
   STATUS     mandatory
   DESCRIPTION
     "This attribute is used to turn accounting on or off for SVC and 
      SPVC connections. It also specifies the reason(s) for which 
      accounting data is collected: billing, test, study, audit, or force.
      
      If the set of reasons is not empty then accounting records will be 
      generated by this interface in the following situations:
      - on a TODA changeover if TODA is enabled;
      - every 12 hours (per connection) if TODA is disabled;
      - on every call clear (a call record with final cell counts).
      
      If none of the reasons is present, then accounting will be 
      suppressed.
      
      The reason for collection is recorded in the accounting record, in 
      the attribute callingCollectReason or calledCollectReason as 
      appropriate.

      Description of bits:
      bill(0)
      test(1)
      study(2)
      audit(3)
      force(4)"
::= { mscAtmIfVptPnniAcctOptEntry 1 }

mscAtmIfVptPnniAccountConnectionType OBJECT-TYPE
   SYNTAX     INTEGER  {
                 origTerm(0),
                 intermediate(1) }
   ACCESS     read-write
   STATUS     mandatory
   DESCRIPTION
     "This attribute specifies whether accounting records generated by 
      this interface should be marked as originating, terminating or 
      intermediate. This attribute, in combination with the direction of the 
      call, determines the value of attribute connPointType of the 
      accounting record and may be used by downstream accounting 
      processes to correlate the records.
      
      If the value is origTerm then records generated for incoming calls 
      will be marked as originating and records generated for outgoing 
      calls will be marked as terminating.
      
      If the value is intermediate then records generated for all calls will 
      be marked as intermediate."
   DEFVAL     { intermediate }
::= { mscAtmIfVptPnniAcctOptEntry 2 }

mscAtmIfVptPnniAccountClass OBJECT-TYPE
   SYNTAX     Unsigned32 (0..255)
   ACCESS     read-write
   STATUS     mandatory
   DESCRIPTION
     "This attribute specifies the accounting class associated with the 
      interface. Its meaning is determined by the network operator.
      
      Its value is simply recorded in the accounting records generated by 
      this interface, in the attribute callingServiceType or 
      calledServiceType as appropriate."
   DEFVAL     { 0 }
::= { mscAtmIfVptPnniAcctOptEntry 3 }

mscAtmIfVptPnniServiceExchange OBJECT-TYPE
   SYNTAX     Unsigned32 (0..255)
   ACCESS     read-write
   STATUS     mandatory
   DESCRIPTION
     "This attribute specifies the data service exchange associated with 
      this interface. Its meaning is determined by the network operator.
      
      Its value is simply recorded in the accounting records generated by 
      this interface, in the attribute callingDse or calledDse as 
      appropriate."
   DEFVAL     { 0 }
::= { mscAtmIfVptPnniAcctOptEntry 4 }

mscAtmIfVptPnniOperationalTable OBJECT-TYPE
   SYNTAX     SEQUENCE OF MscAtmIfVptPnniOperationalEntry
   ACCESS     not-accessible
   STATUS     mandatory
   DESCRIPTION
     "This group contains the operational attributes for a Pnni component."
::= { mscAtmIfVptPnni 13 }

mscAtmIfVptPnniOperationalEntry OBJECT-TYPE
   SYNTAX     MscAtmIfVptPnniOperationalEntry
   ACCESS     not-accessible
   STATUS     mandatory
   DESCRIPTION
     "An entry in the mscAtmIfVptPnniOperationalTable."
   INDEX {
      mscAtmIfIndex,
      mscAtmIfVptIndex,
      mscAtmIfVptPnniIndex }
::= { mscAtmIfVptPnniOperationalTable 1 }

MscAtmIfVptPnniOperationalEntry ::= SEQUENCE {
   mscAtmIfVptPnniPortId
      Unsigned32 }

mscAtmIfVptPnniPortId OBJECT-TYPE
   SYNTAX     Unsigned32 (0..4294967295)
   ACCESS     read-only
   STATUS     mandatory
   DESCRIPTION
     "This attribute indicates the port id of the PNNI interface, which is 
      the parent AtmIf's instance number."
::= { mscAtmIfVptPnniOperationalEntry 1 }

mscAtmIfVptPnniVProvTable OBJECT-TYPE
   SYNTAX     SEQUENCE OF MscAtmIfVptPnniVProvEntry
   ACCESS     not-accessible
   STATUS     mandatory
   DESCRIPTION
     "This group contains the provisionable attributes for the Pnni 
      component which are specific to virtual PNNI interfaces."
::= { mscAtmIfVptPnni 14 }

mscAtmIfVptPnniVProvEntry OBJECT-TYPE
   SYNTAX     MscAtmIfVptPnniVProvEntry
   ACCESS     not-accessible
   STATUS     mandatory
   DESCRIPTION
     "An entry in the mscAtmIfVptPnniVProvTable."
   INDEX {
      mscAtmIfIndex,
      mscAtmIfVptIndex,
      mscAtmIfVptPnniIndex }
::= { mscAtmIfVptPnniVProvTable 1 }

MscAtmIfVptPnniVProvEntry ::= SEQUENCE {
   mscAtmIfVptPnniVpci
      Unsigned32 }

mscAtmIfVptPnniVpci OBJECT-TYPE
   SYNTAX     Unsigned32 (0..255)
   ACCESS     read-write
   STATUS     mandatory
   DESCRIPTION
     "This attribute specifies the Virtual Path Connection Identifier 
      (VPCI) to be used between this signalling entity and its peer. The 
      VPCI of the peer virtual PNNI must have the same value for 
      switched connections to be set up across the interface."
   DEFVAL     { 0 }
::= { mscAtmIfVptPnniVProvEntry 1 }


-- AtmIf/n Iisp Signalling
-- AtmIf/n Uni Signalling
-- AtmIf/n Pnni Signalling
-- AtmIf/n Vpt/m Iisp Signalling
-- AtmIf/n Vpt/m Uni Signalling
-- AtmIf/n Vpt/m Pnni Signalling
-- 
-- This component represents the signalling entities for the interface.

mscAtmIfVptPnniSig OBJECT IDENTIFIER ::= { mscAtmIfVptPnni 2 }



mscAtmIfVptPnniSigRowStatusTable OBJECT-TYPE
   SYNTAX     SEQUENCE OF MscAtmIfVptPnniSigRowStatusEntry
   ACCESS     not-accessible
   STATUS     mandatory
   DESCRIPTION
     "This entry controls the addition and deletion of 
      mscAtmIfVptPnniSig components."
::= { mscAtmIfVptPnniSig 1 }

mscAtmIfVptPnniSigRowStatusEntry OBJECT-TYPE
   SYNTAX     MscAtmIfVptPnniSigRowStatusEntry
   ACCESS     not-accessible
   STATUS     mandatory
   DESCRIPTION
     "A single entry in the table represents a single 
      mscAtmIfVptPnniSig component."
   INDEX {
      mscAtmIfIndex,
      mscAtmIfVptIndex,
      mscAtmIfVptPnniIndex,
      mscAtmIfVptPnniSigIndex }
::= { mscAtmIfVptPnniSigRowStatusTable 1 }

MscAtmIfVptPnniSigRowStatusEntry ::= SEQUENCE {
   mscAtmIfVptPnniSigRowStatus
      RowStatus,
   mscAtmIfVptPnniSigComponentName
      DisplayString,
   mscAtmIfVptPnniSigStorageType
      StorageType,
   mscAtmIfVptPnniSigIndex
      NonReplicated }

mscAtmIfVptPnniSigRowStatus OBJECT-TYPE
   SYNTAX     RowStatus 
   ACCESS     read-only
   STATUS     mandatory
   DESCRIPTION
     "This variable is used as the basis for SNMP naming of
      mscAtmIfVptPnniSig components.
      These components cannot be added nor deleted."
::= { mscAtmIfVptPnniSigRowStatusEntry 1 }

mscAtmIfVptPnniSigComponentName OBJECT-TYPE
   SYNTAX     DisplayString 
   ACCESS     read-only
   STATUS     mandatory
   DESCRIPTION
     "This variable provides the component's string name for
      use with the ASCII Console Interface"
::= { mscAtmIfVptPnniSigRowStatusEntry 2 }

mscAtmIfVptPnniSigStorageType OBJECT-TYPE
   SYNTAX     StorageType 
   ACCESS     read-only
   STATUS     mandatory
   DESCRIPTION
     "This variable represents the storage type value for the
      mscAtmIfVptPnniSig tables."
::= { mscAtmIfVptPnniSigRowStatusEntry 4 }

mscAtmIfVptPnniSigIndex OBJECT-TYPE
   SYNTAX     NonReplicated 
   ACCESS     not-accessible
   STATUS     mandatory
   DESCRIPTION
     "This variable represents the index for the mscAtmIfVptPnniSig tables."
::= { mscAtmIfVptPnniSigRowStatusEntry 10 }

mscAtmIfVptPnniSigProvTable OBJECT-TYPE
   SYNTAX     SEQUENCE OF MscAtmIfVptPnniSigProvEntry
   ACCESS     not-accessible
   STATUS     mandatory
   DESCRIPTION
     "This attribute group contains the provisionable attributes for the 
      Signalling component."
::= { mscAtmIfVptPnniSig 10 }

mscAtmIfVptPnniSigProvEntry OBJECT-TYPE
   SYNTAX     MscAtmIfVptPnniSigProvEntry
   ACCESS     not-accessible
   STATUS     mandatory
   DESCRIPTION
     "An entry in the mscAtmIfVptPnniSigProvTable."
   INDEX {
      mscAtmIfIndex,
      mscAtmIfVptIndex,
      mscAtmIfVptPnniIndex,
      mscAtmIfVptPnniSigIndex }
::= { mscAtmIfVptPnniSigProvTable 1 }

MscAtmIfVptPnniSigProvEntry ::= SEQUENCE {
   mscAtmIfVptPnniSigVci
      Unsigned32,
   mscAtmIfVptPnniSigAddressConversion
      INTEGER,
   mscAtmIfVptPnniSigOperatingMode
      INTEGER }

mscAtmIfVptPnniSigVci OBJECT-TYPE
   SYNTAX     Unsigned32 (0..65535)
   ACCESS     read-write
   STATUS     mandatory
   DESCRIPTION
     "This attribute specifies the signalling channel number."
   DEFVAL     { 5 }
::= { mscAtmIfVptPnniSigProvEntry 1 }

mscAtmIfVptPnniSigAddressConversion OBJECT-TYPE
   SYNTAX     INTEGER  {
                 none(0),
                 nativeE164(1),
                 nsap(2) }
   ACCESS     read-write
   STATUS     mandatory
   DESCRIPTION
     "This attribute specifies the address conversion on the outgoing 
      signalling PDUs. The options are none, nativeE164, or nsap. The 
      none option is the default and if this option is chosen then nothing 
      is done to the address information element (IE) in the outgoing 
      signalling message. If nativeE164 option is chosen, then only 
      NSAP encapsulated E.164 addresses with zeros in the ESI are 
      converted to native E.164 format in the outgoing signalling 
      message. If the NSAP address is not encapsulated E.164 or the ESI 
      field is not zeros and the nativeE164 option is chosen, then the call 
      is cleared. If the nsap option is chosen, then native E.164 addresses 
      are converted to NSAP E.164 with zeros in the ESI field; otherwise 
      the address is in NSAP format and is not changed."
   DEFVAL     { none }
::= { mscAtmIfVptPnniSigProvEntry 2 }

mscAtmIfVptPnniSigOperatingMode OBJECT-TYPE
   SYNTAX     INTEGER  {
                 normal(0),
                 provisionedOnly(1) }
   ACCESS     read-write
   STATUS     mandatory
   DESCRIPTION
     "This attribute specifies the operating mode of the signaling channel. 				
      provisionedOnly indicates that only SPVCs and SPVPs are 
      supported on the interface and SVCs are not supported. This value 
      is permitted only on UNI interfaces.
      normal indicates that SVCs, SPVCs, and SPVPs are supported on 
      the interface."
   DEFVAL     { normal }
::= { mscAtmIfVptPnniSigProvEntry 3 }

mscAtmIfVptPnniSigStateTable OBJECT-TYPE
   SYNTAX     SEQUENCE OF MscAtmIfVptPnniSigStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscAtmIfVptPnniSig 11 }

mscAtmIfVptPnniSigStateEntry OBJECT-TYPE
   SYNTAX     MscAtmIfVptPnniSigStateEntry
   ACCESS     not-accessible
   STATUS     mandatory
   DESCRIPTION
     "An entry in the mscAtmIfVptPnniSigStateTable."
   INDEX {
      mscAtmIfIndex,
      mscAtmIfVptIndex,
      mscAtmIfVptPnniIndex,
      mscAtmIfVptPnniSigIndex }
::= { mscAtmIfVptPnniSigStateTable 1 }

MscAtmIfVptPnniSigStateEntry ::= SEQUENCE {
   mscAtmIfVptPnniSigAdminState
      INTEGER,
   mscAtmIfVptPnniSigOperationalState
      INTEGER,
   mscAtmIfVptPnniSigUsageState
      INTEGER }

mscAtmIfVptPnniSigAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscAtmIfVptPnniSigStateEntry 1 }

mscAtmIfVptPnniSigOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscAtmIfVptPnniSigStateEntry 2 }

mscAtmIfVptPnniSigUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscAtmIfVptPnniSigStateEntry 3 }

mscAtmIfVptPnniSigOperTable OBJECT-TYPE
   SYNTAX     SEQUENCE OF MscAtmIfVptPnniSigOperEntry
   ACCESS     not-accessible
   STATUS     mandatory
   DESCRIPTION
     "This attribute contains the operational attributes for the 
      AtmSignalling component."
::= { mscAtmIfVptPnniSig 12 }

mscAtmIfVptPnniSigOperEntry OBJECT-TYPE
   SYNTAX     MscAtmIfVptPnniSigOperEntry
   ACCESS     not-accessible
   STATUS     mandatory
   DESCRIPTION
     "An entry in the mscAtmIfVptPnniSigOperTable."
   INDEX {
      mscAtmIfIndex,
      mscAtmIfVptIndex,
      mscAtmIfVptPnniIndex,
      mscAtmIfVptPnniSigIndex }
::= { mscAtmIfVptPnniSigOperTable 1 }

MscAtmIfVptPnniSigOperEntry ::= SEQUENCE {
   mscAtmIfVptPnniSigLastTxCauseCode
      Unsigned32,
   mscAtmIfVptPnniSigLastTxDiagCode
      Hex,
   mscAtmIfVptPnniSigLastRxCauseCode
      Unsigned32,
   mscAtmIfVptPnniSigLastRxDiagCode
      Hex }

mscAtmIfVptPnniSigLastTxCauseCode OBJECT-TYPE
   SYNTAX     Unsigned32 (0..255)
   ACCESS     read-only
   STATUS     mandatory
   DESCRIPTION
     "This attribute indicates the cause code in the last transmitted 
      signalling message that contains the CAUSE information element. 
      The cause code is used to describe the reason for generating certain 
      signalling messages."
::= { mscAtmIfVptPnniSigOperEntry 1 }

mscAtmIfVptPnniSigLastTxDiagCode OBJECT-TYPE
   SYNTAX     Hex (0..255)
   ACCESS     read-only
   STATUS     mandatory
   DESCRIPTION
     "This attribute contains the diagnostic code in the last transmitted 
      signalling message. The diagnostic code is contained in the CAUSE 
      information element and identifies an information element type or 
      timer type. The diagnostic code is present only if a procedural error 
      is detected by the signalling protocol. A diagnostic code is always 
      accompanied by the cause code. If there is no failure, this attribute 
      is set to 0."
::= { mscAtmIfVptPnniSigOperEntry 2 }

mscAtmIfVptPnniSigLastRxCauseCode OBJECT-TYPE
   SYNTAX     Unsigned32 (0..255)
   ACCESS     read-only
   STATUS     mandatory
   DESCRIPTION
     "This attribute contains the cause code in the last received signalling 
      message that contains the CAUSE information element. The cause 
      code is used to describe the reason for generating certain signalling 
      messages."
::= { mscAtmIfVptPnniSigOperEntry 3 }

mscAtmIfVptPnniSigLastRxDiagCode OBJECT-TYPE
   SYNTAX     Hex (0..255)
   ACCESS     read-only
   STATUS     mandatory
   DESCRIPTION
     "This attribute contains the diagnostic code in the last received 
      signalling message. The diagnostic code is contained in the CAUSE 
      information element and identifies an information element type or 
      timer type. The diagnostic code is present only if a procedural error 
      is detected by the signalling protocol. A diagnostic code is always 
      accompanied by the cause code. If there is no failure, this attribute 
      is set to 0."
::= { mscAtmIfVptPnniSigOperEntry 4 }

mscAtmIfVptPnniSigStatsTable OBJECT-TYPE
   SYNTAX     SEQUENCE OF MscAtmIfVptPnniSigStatsEntry
   ACCESS     not-accessible
   STATUS     mandatory
   DESCRIPTION
     "This attribute group contains the statistics associated with the 
      AtmSignalling component."
::= { mscAtmIfVptPnniSig 13 }

mscAtmIfVptPnniSigStatsEntry OBJECT-TYPE
   SYNTAX     MscAtmIfVptPnniSigStatsEntry
   ACCESS     not-accessible
   STATUS     mandatory
   DESCRIPTION
     "An entry in the mscAtmIfVptPnniSigStatsTable."
   INDEX {
      mscAtmIfIndex,
      mscAtmIfVptIndex,
      mscAtmIfVptPnniIndex,
      mscAtmIfVptPnniSigIndex }
::= { mscAtmIfVptPnniSigStatsTable 1 }

MscAtmIfVptPnniSigStatsEntry ::= SEQUENCE {
   mscAtmIfVptPnniSigCurrentConnections
      Counter32,
   mscAtmIfVptPnniSigPeakConnections
      Gauge32,
   mscAtmIfVptPnniSigSuccessfulConnections
      Counter32,
   mscAtmIfVptPnniSigFailedConnections
      Counter32,
   mscAtmIfVptPnniSigTxPdus
      Counter32,
   mscAtmIfVptPnniSigRxPdus
      Counter32,
   mscAtmIfVptPnniSigCurrentPmpConnections
      Gauge32,
   mscAtmIfVptPnniSigPeakPmpConnections
      Gauge32,
   mscAtmIfVptPnniSigSuccessfulPmpConnections
      Counter32,
   mscAtmIfVptPnniSigFailedPmpConnections
      Counter32,
   mscAtmIfVptPnniSigNewCurrentConnections
      Gauge32 }

mscAtmIfVptPnniSigCurrentConnections OBJECT-TYPE
   SYNTAX     Counter32 
   ACCESS     read-only
   STATUS     obsolete
   DESCRIPTION
     "This attribute indicates the total number of currently active 
      connections."
::= { mscAtmIfVptPnniSigStatsEntry 1 }

mscAtmIfVptPnniSigPeakConnections OBJECT-TYPE
   SYNTAX     Gauge32 (0..4294967295)
   ACCESS     read-only
   STATUS     mandatory
   DESCRIPTION
     "This attribute indicates the high water mark of active point-to-
      point and point-to-multipoint connections."
::= { mscAtmIfVptPnniSigStatsEntry 2 }

mscAtmIfVptPnniSigSuccessfulConnections OBJECT-TYPE
   SYNTAX     Counter32 
   ACCESS     read-only
   STATUS     mandatory
   DESCRIPTION
     "This attribute counts the total number of switched point-to-
      point and point-to-multipoint connections that were successfully 
      established. The counter wraps to 0 when the maximum value is 
      exceeded."
::= { mscAtmIfVptPnniSigStatsEntry 3 }

mscAtmIfVptPnniSigFailedConnections OBJECT-TYPE
   SYNTAX     Counter32 
   ACCESS     read-only
   STATUS     mandatory
   DESCRIPTION
     "This attribute counts the total number of switched connections that 
      were not successfully established.The counter wraps to 0 when the 
      maximum value is exceeded."
::= { mscAtmIfVptPnniSigStatsEntry 4 }

mscAtmIfVptPnniSigTxPdus OBJECT-TYPE
   SYNTAX     Counter32 
   ACCESS     read-only
   STATUS     mandatory
   DESCRIPTION
     "This attribute counts the number of transmitted signalling 
      PDUs.The counter wraps to 0 when the maximum value is 
      exceeded."
::= { mscAtmIfVptPnniSigStatsEntry 5 }

mscAtmIfVptPnniSigRxPdus OBJECT-TYPE
   SYNTAX     Counter32 
   ACCESS     read-only
   STATUS     mandatory
   DESCRIPTION
     "This attribute counts the number of received signalling PDUs.The 
      counter wraps to 0 when the maximum value is exceeded."
::= { mscAtmIfVptPnniSigStatsEntry 6 }

mscAtmIfVptPnniSigCurrentPmpConnections OBJECT-TYPE
   SYNTAX     Gauge32 (0..4294967295)
   ACCESS     read-only
   STATUS     mandatory
   DESCRIPTION
     "This attribute indicates the number of currently active point-to-
      multipoint connections."
::= { mscAtmIfVptPnniSigStatsEntry 7 }

mscAtmIfVptPnniSigPeakPmpConnections OBJECT-TYPE
   SYNTAX     Gauge32 (0..4294967295)
   ACCESS     read-only
   STATUS     mandatory
   DESCRIPTION
     "This attribute indicates the high water mark of active point-to-
      multipoint connections."
::= { mscAtmIfVptPnniSigStatsEntry 8 }

mscAtmIfVptPnniSigSuccessfulPmpConnections OBJECT-TYPE
   SYNTAX     Counter32 
   ACCESS     read-only
   STATUS     mandatory
   DESCRIPTION
     "This attribute counts the total number of switched point-to-
      multipoint connections that were successfully established. 
      The counter wraps to 0 when the maximum value is 
      exceeded."
::= { mscAtmIfVptPnniSigStatsEntry 9 }

mscAtmIfVptPnniSigFailedPmpConnections OBJECT-TYPE
   SYNTAX     Counter32 
   ACCESS     read-only
   STATUS     mandatory
   DESCRIPTION
     "This attribute counts the number of switched point-to-
      multipoint connections that were not successfully 
      established.The counter wraps to 0 when the maximum value 
      is exceeded."
::= { mscAtmIfVptPnniSigStatsEntry 10 }

mscAtmIfVptPnniSigNewCurrentConnections OBJECT-TYPE
   SYNTAX     Gauge32 (0..4294967295)
   ACCESS     read-only
   STATUS     mandatory
   DESCRIPTION
     "This attribute indicates the total number of currently active point-to-
      point and point-to-multipoint connections."
::= { mscAtmIfVptPnniSigStatsEntry 11 }


-- AtmIf/n Uni Sig VirtualChannelDescriptor
-- AtmIf/n Uni Ilmi VirtualChannelDescriptor
-- AtmIf/n Iisp Sig VirtualChannelDescriptor
-- AtmIf/n Pnni Sig VirtualChannelDescriptor
-- AtmIf/n Pnni Rcc VirtualChannelDescriptor
-- AtmIf/n Vpt/m Uni Sig VirtualChannelDescriptor
-- AtmIf/n Vpt/m Iisp Sig VirtualChannelDescriptor
-- AtmIf/n Vpt/m Pnni Sig VirtualChannelDescriptor
-- AtmIf/n Vpt/m Pnni Rcc VirtualChannelDescriptor
-- 
-- This component contains the provisionable traffic parameters for a 
-- control channel (Sig, Ilmi or Rcc component).

mscAtmIfVptPnniSigVcd OBJECT IDENTIFIER ::= { mscAtmIfVptPnniSig 2 }



mscAtmIfVptPnniSigVcdRowStatusTable OBJECT-TYPE
   SYNTAX     SEQUENCE OF MscAtmIfVptPnniSigVcdRowStatusEntry
   ACCESS     not-accessible
   STATUS     mandatory
   DESCRIPTION
     "This entry controls the addition and deletion of 
      mscAtmIfVptPnniSigVcd components."
::= { mscAtmIfVptPnniSigVcd 1 }

mscAtmIfVptPnniSigVcdRowStatusEntry OBJECT-TYPE
   SYNTAX     MscAtmIfVptPnniSigVcdRowStatusEntry
   ACCESS     not-accessible
   STATUS     mandatory
   DESCRIPTION
     "A single entry in the table represents a single 
      mscAtmIfVptPnniSigVcd component."
   INDEX {
      mscAtmIfIndex,
      mscAtmIfVptIndex,
      mscAtmIfVptPnniIndex,
      mscAtmIfVptPnniSigIndex,
      mscAtmIfVptPnniSigVcdIndex }
::= { mscAtmIfVptPnniSigVcdRowStatusTable 1 }

MscAtmIfVptPnniSigVcdRowStatusEntry ::= SEQUENCE {
   mscAtmIfVptPnniSigVcdRowStatus
      RowStatus,
   mscAtmIfVptPnniSigVcdComponentName
      DisplayString,
   mscAtmIfVptPnniSigVcdStorageType
      StorageType,
   mscAtmIfVptPnniSigVcdIndex
      NonReplicated }

mscAtmIfVptPnniSigVcdRowStatus OBJECT-TYPE
   SYNTAX     RowStatus 
   ACCESS     read-write
   STATUS     mandatory
   DESCRIPTION
     "This variable is used as the basis for SNMP naming of
      mscAtmIfVptPnniSigVcd components.
      These components can be added and deleted."
::= { mscAtmIfVptPnniSigVcdRowStatusEntry 1 }

mscAtmIfVptPnniSigVcdComponentName OBJECT-TYPE
   SYNTAX     DisplayString 
   ACCESS     read-only
   STATUS     mandatory
   DESCRIPTION
     "This variable provides the component's string name for
      use with the ASCII Console Interface"
::= { mscAtmIfVptPnniSigVcdRowStatusEntry 2 }

mscAtmIfVptPnniSigVcdStorageType OBJECT-TYPE
   SYNTAX     StorageType 
   ACCESS     read-only
   STATUS     mandatory
   DESCRIPTION
     "This variable represents the storage type value for the
      mscAtmIfVptPnniSigVcd tables."
::= { mscAtmIfVptPnniSigVcdRowStatusEntry 4 }

mscAtmIfVptPnniSigVcdIndex OBJECT-TYPE
   SYNTAX     NonReplicated 
   ACCESS     not-accessible
   STATUS     mandatory
   DESCRIPTION
     "This variable represents the index for the mscAtmIfVptPnniSigVcd tables."
::= { mscAtmIfVptPnniSigVcdRowStatusEntry 10 }

mscAtmIfVptPnniSigVcdProvTable OBJECT-TYPE
   SYNTAX     SEQUENCE OF MscAtmIfVptPnniSigVcdProvEntry
   ACCESS     not-accessible
   STATUS     mandatory
   DESCRIPTION
     "This group contains the provisionable traffic attributes for a control 
      channel."
::= { mscAtmIfVptPnniSigVcd 10 }

mscAtmIfVptPnniSigVcdProvEntry OBJECT-TYPE
   SYNTAX     MscAtmIfVptPnniSigVcdProvEntry
   ACCESS     not-accessible
   STATUS     mandatory
   DESCRIPTION
     "An entry in the mscAtmIfVptPnniSigVcdProvTable."
   INDEX {
      mscAtmIfIndex,
      mscAtmIfVptIndex,
      mscAtmIfVptPnniIndex,
      mscAtmIfVptPnniSigIndex,
      mscAtmIfVptPnniSigVcdIndex }
::= { mscAtmIfVptPnniSigVcdProvTable 1 }

MscAtmIfVptPnniSigVcdProvEntry ::= SEQUENCE {
   mscAtmIfVptPnniSigVcdTrafficDescType
      INTEGER,
   mscAtmIfVptPnniSigVcdAtmServiceCategory
      INTEGER,
   mscAtmIfVptPnniSigVcdWeight
      Unsigned32,
   mscAtmIfVptPnniSigVcdQosClass
      INTEGER,
   mscAtmIfVptPnniSigVcdTrafficShaping
      INTEGER,
   mscAtmIfVptPnniSigVcdUnshapedTransmitQueueing
      INTEGER,
   mscAtmIfVptPnniSigVcdUsageParameterControl
      INTEGER }

mscAtmIfVptPnniSigVcdTrafficDescType OBJECT-TYPE
   SYNTAX     INTEGER  {
                 n3(3),
                 n6(6),
                 n7(7),
                 n8(8) }
   ACCESS     read-write
   STATUS     mandatory
   DESCRIPTION
     "This attribute specifies the type of traffic management which is 
      applied to both the transmit and receive direction of this connection 
      as defined in the ATM Forum. The trafficDescType determines the 
      number and meaning of the parameters in the trafficDescParm 
      attribute."
   DEFVAL     { n6 }
::= { mscAtmIfVptPnniSigVcdProvEntry 1 }

mscAtmIfVptPnniSigVcdAtmServiceCategory OBJECT-TYPE
   SYNTAX     INTEGER  {
                 unspecifiedBitRate(0),
                 constantBitRate(1),
                 rtVariableBitRate(2),
                 nrtVariableBitRate(3) }
   ACCESS     read-write
   STATUS     mandatory
   DESCRIPTION
     "This attribute specifies the ATM service category for both directions 
      of the connection. 
      
      The constantBitRate service category is intended for real time 
      applications, that is those requiring tightly constrained delay and 
      delay variation, as would be appropriate for voice and video 
      applications. The consistent availability of a fixed quantity of 
      bandwidth is considered appropriate for CBR service. Cells which 
      are delayed beyond the value specified by CellTransfer Delay are 
      assumed to be of significantly reduce value to the application.
      
      The rtVariableBitRate service category is intended for real time 
      applications, that is those requiring tightly constrained delay and 
      delay variation, as would be appropriate for voice and video 
      applications. Sources are expected to transmit at a rate which varies 
      with time. Equivalently, the source can be described as 'bursty'. 
      Cells which are delayed beyond the value specified by CTD are 
      assumed to be of significantly reduced value to the application. Real 
      time VBR service may support statistical multiplexing of real time 
      sources.
      
      The nrtVariableBitRate service category is intended for non-real 
      time applications which have bursty traffic characteristics and which 
      can be characterized in terms of a PCR, SCR, and MBS. For those 
      cells which are transferred within the traffic contract, the application 
      expects a low cell loss ratio. For all connections, it expects a bound 
      on the mean cell transfer delay. Non-real time VBR service may 
      support statistical multiplexing of connections.
      
      The unspecifiedBitRate service is intended for non-real time 
      applications; that is, those not requiring tightly constrained delay 
      and delay variation. UBR sources are expected to be bursty. UBR 
      service supports a high degree of statistical multiplexing among 
      sources. UBR service does not specify traffic related service 
      guarantees. No numerical commitments are made with respect to 
      the cell loss ratio experienced by a UBR connection, or as to the 
      cell transfer delay experienced by cells on the connection."
   DEFVAL     { rtVariableBitRate }
::= { mscAtmIfVptPnniSigVcdProvEntry 3 }

mscAtmIfVptPnniSigVcdWeight OBJECT-TYPE
   SYNTAX     Unsigned32 (0 | 1..4095 | 65535)
   ACCESS     read-write
   STATUS     mandatory
   DESCRIPTION
     "This attribute specifies an override for the weight of this unshaped 
      connection. This attribute is ignored for shaped connections, for 
      ABR connections, for connections on a CQC-based ATM FP and 
      basic VPTs. 
      
      When the value is set to sameAsCa, the weight is determined by the 
      weight policy attribute under the CA service category component 
      for all but standard VPT VCCs. For standard VPT VCCs, the 
      weight is determined by the VCC's service category, when the value 
      is set to sameAsCa.
      
      When this attribute is set to a value from 1 to 4095, that value is 
      used for the weight policy of this connection relative to other 
      connections. For all but standard VPT VCCs, weight policy 
      determines the proportion of transit cell opportunities which are 
      allocated to this connection, compared to other connections in the 
      same service category. For standard VPT VCCs, weight policy 
      determines the proportion of transmit cell opportunities which are 
      allocated to this connection, compared to other connections 
      associated with the VPT.
      
      When the value is set to upToQueueLimit, the weight policy is 
      limited only by the txQueueLimit.

      VALUES (

      0 = upToQueueLimit

      65535 = sameAsCa

      )"
   DEFVAL     { 65535 }
::= { mscAtmIfVptPnniSigVcdProvEntry 4 }

mscAtmIfVptPnniSigVcdQosClass OBJECT-TYPE
   SYNTAX     INTEGER  {
                 n0(0),
                 n1(1),
                 n2(2),
                 n3(3),
                 n4(4) }
   ACCESS     read-write
   STATUS     mandatory
   DESCRIPTION
     "This attribute specifies the quality of service for both the forward 
      and backward direction for this connection.
      
      Class 1 supports a QOS that meets Service Class A performance 
      requirements (Circuit emulation, constant bit rate video).
      
      Class 2 supports a QOS that meets Service Class B performance 
      requirements (Variable bit rate audio and video).
      
      Class 3 supports a QOS that meets Service Class C performance 
      requirements (Connection-Oriented Data Transfer).
      
      Class 4 supports a QOS that meets Service Class D performance 
      requirements (Connectionless Data Transfer).
      
      Class 0 is the unspecified bit rate QOS class; no objective is 
      specified for the performance parameters."
   DEFVAL     { n2 }
::= { mscAtmIfVptPnniSigVcdProvEntry 21 }

mscAtmIfVptPnniSigVcdTrafficShaping OBJECT-TYPE
   SYNTAX     INTEGER  {
                 disabled(1),
                 sameAsCa(2) }
   ACCESS     read-write
   STATUS     mandatory
   DESCRIPTION
     "This attribute specifies whether this connection uses traffic shaping 
      when transmitting traffic to the ATM interface.
      
      When sameAsCa is selected, traffic shaping for this connection is 
      based on the trafficShaping attribute of the connection's service 
      category component under the AtmIf CA. If the service category has 
      traffic shaping enabled, then traffic shaping is enabled for the 
      connection. Note that enabling traffic shaping may have no effect 
      under certain cases. These cases are listed in the description of the 
      trafficShaping operational attribute, which is under the Vcc Tm and 
      Vpc Tm components.
      
      When disabled is selected, traffic shaping for this connection is 
      disabled."
   DEFVAL     { disabled }
::= { mscAtmIfVptPnniSigVcdProvEntry 50 }

mscAtmIfVptPnniSigVcdUnshapedTransmitQueueing OBJECT-TYPE
   SYNTAX     INTEGER  {
                 common(1),
                 sameAsCa(3) }
   ACCESS     read-write
   STATUS     mandatory
   DESCRIPTION
     "This attribute only applies when this connection is unshaped. This 
      attribute specifies the transmit queueing method for this connection 
      if it is unshaped. Refer to the unshapedTransmitQueueing attribute 
      under the AtmIf CA service category subcomponent for more details 
      on the meaning of this attribute. 
      
      When this attribute is set to sameAsCa, the transmit queueing 
      method for the connection is based on the 
      unshapedTransmitQueueing attribute of the connection's service 
      category component under the ConnectionAdministrator. 
      
      When this attribute is set to common, transmit traffic on this 
      unshaped connection is destined for the common queue. 
      
      The value sameAsInterface is for migration from previous software 
      releases, but should no longer be used"
   DEFVAL     { sameAsCa }
::= { mscAtmIfVptPnniSigVcdProvEntry 60 }

mscAtmIfVptPnniSigVcdUsageParameterControl OBJECT-TYPE
   SYNTAX     INTEGER  {
                 disabled(1),
                 sameAsCa(2) }
   ACCESS     read-write
   STATUS     mandatory
   DESCRIPTION
     "This attribute specifies whether this connection enforces usage 
      parameter control when receiving traffic from the ATM interface.
      
      When sameAsCa is selected, UPC for the connection is based on 
      the usageParameterControl attribute of the connection's service 
      category component under the ConnectionAdministrator. If the 
      service category has UPC enabled, then UPC is enabled for the 
      connection. Note that enabling UPC may have no effect under 
      certain cases. These cases are listed in the description of the 
      usageParameterControl operational attribute, which is under the 
      Vcc Tm or Vpc Tm component.
      
      When disabled is selected, UPC for this connection is disabled.
      
      The value sameAsInterface is for migration from previous software 
      releases, but should no longer be used"
   DEFVAL     { disabled }
::= { mscAtmIfVptPnniSigVcdProvEntry 70 }

mscAtmIfVptPnniSigVcdTdpTable OBJECT-TYPE
   SYNTAX     SEQUENCE OF MscAtmIfVptPnniSigVcdTdpEntry
   ACCESS     not-accessible
   STATUS     mandatory
   DESCRIPTION
     "This attribute is a vector of five traffic parameters whose meanings 
      are defined by the trafficDescType attribute. The values of peak cell 
      rate (PCR), sustained cell rate (SCR) and requested shaping rate are 
      expressed in cell/s. Maximum burst size (MBS) is expressed in 
      cells. CDVT is expressed in microseconds. The values of PCR, 
      SCR, MBS and CDVT are used for connection admission control 
      (CAC). The value of CDVT is only used for connections where the 
      atmServiceCategory is constantBitRate. For all other values of 
      atmServiceCategory, CDVT is ignored. The values of PCR, SCR 
      and requested shaping rate are used to determine the actual shaping 
      rate where traffic shaping is enabled.
      
      When trafficDescType is 3, parameter 1 represents the PCR for CLP 
      equal to 0 and 1 traffic; parameter 4 represents the CDVT; and 
      parameter 5 represents the requested shaping rate. A non-zero value 
      in parameter 5 overrides any value in parameter 1. This result is 
      used as the PCR. Parameter 1 must be non-zero. Parameters 2 and 3 
      must be zero.
      
      When trafficDescType is 6, parameter 1 represents the PCR for CLP 
      equal to 0 and 1 traffic; parameter 2 represents the SCR for CLP 
      equal to 0 and 1 traffic; parameter 3 represents the MBS for CLP 
      equal to 0 and 1 traffic; parameter 4 represents the CDVT; and 
      parameter 5 represents the requested shaping rate. A non-zero value 
      in parameter 5 overrides any value in parameter 1. This result is 
      used as the PCR. Parameters 1, 2, and 3 must be non-zero. 
      Parameter 1 must be greater than or equal to parameter 2. Parameter 
      5 must either be zero (unused) or greater than or equal to parameter 
      2.
      
      When trafficDescType is 7, parameter 1 represents the PCR for CLP 
      equal to 0 and 1 traffic; parameter 2 represents the SCR for CLP 
      equal to 0 with cell discard; parameter 3 represents the MBS for 
      CLP equal to 0 traffic; parameter 4 represents the CDVT; and 
      parameter 5 represents the requested shaping rate. A non-zero value 
      in parameter 5 overrides any value in parameter 1. This result is 
      used as the PCR. Parameters 1, 2, and 3 must be non-zero. 
      Parameter 1 must be greater than or equal to parameter 2. Parameter 
      5 must either be zero (unused) or greater than or equal to parameter 
      2.
      
      When trafficDescType is 8, parameter 1 represents the PCR for CLP 
      equal to 0 and 1 traffic; parameter 2 represents the SCR for CLP 
      equal to 0 traffic with cell tagging; parameter 3 represents the MBS 
      for CLP equal to 0 traffic; parameter 4 represents the CDVT; and 
      parameter 5 represents the requested shaping rate. A non-zero value 
      in parameter 5 overrides any value in parameter 1. This result is 
      used as the PCR. Parameters 1, 2, and 3 must be non-zero. 
      Parameter 1 must be greater than or equal to parameter 2. Parameter 
      5 must either be zero (unused) or greater than or equal to parameter 
      2.
      
      Whenever it is valid for PCR to be specified, parameter 5 may also 
      be used to specify a requested shaping rate. A non-zero value in 
      parameter 5 overrides the value in parameter 1 and is used as the 
      peak cell rate in calculations of CAC and shaping rate.
      
      For trafficDescType 3 the traffic is shaped at the next rate less than 
      the PCR. 
      
      For trafficDescType 6, 7, and 8, the traffic is shaped at the highest 
      available rate which is between PCR and SCR. However, if there is 
      no available shaping rate between PCR and SCR, traffic is shaped at 
      the next rate above the PCR."
::= { mscAtmIfVptPnniSigVcd 387 }

mscAtmIfVptPnniSigVcdTdpEntry OBJECT-TYPE
   SYNTAX     MscAtmIfVptPnniSigVcdTdpEntry
   ACCESS     not-accessible
   STATUS     mandatory
   DESCRIPTION
     "An entry in the mscAtmIfVptPnniSigVcdTdpTable."
   INDEX {
      mscAtmIfIndex,
      mscAtmIfVptIndex,
      mscAtmIfVptPnniIndex,
      mscAtmIfVptPnniSigIndex,
      mscAtmIfVptPnniSigVcdIndex,
      mscAtmIfVptPnniSigVcdTdpIndex }
::= { mscAtmIfVptPnniSigVcdTdpTable 1 }

MscAtmIfVptPnniSigVcdTdpEntry ::= SEQUENCE {
   mscAtmIfVptPnniSigVcdTdpIndex
      Integer32,
   mscAtmIfVptPnniSigVcdTdpValue
      Unsigned32 }

mscAtmIfVptPnniSigVcdTdpIndex OBJECT-TYPE
   SYNTAX     Integer32 (1..5)
   ACCESS     not-accessible
   STATUS     mandatory
   DESCRIPTION
     "This variable represents the mscAtmIfVptPnniSigVcdTdpTable
      specific index for the mscAtmIfVptPnniSigVcdTdpTable."
::= { mscAtmIfVptPnniSigVcdTdpEntry 1 }

mscAtmIfVptPnniSigVcdTdpValue OBJECT-TYPE
   SYNTAX     Unsigned32 (0..2147483647)
   ACCESS     read-write
   STATUS     mandatory
   DESCRIPTION
     "This variable represents an individual value for the
      mscAtmIfVptPnniSigVcdTdpTable."
::= { mscAtmIfVptPnniSigVcdTdpEntry 2 }


-- AtmIf/n Pnni RoutingControlChannel
-- AtmIf/n Vpt/m Pnni RoutingControlChannel
-- 
-- This component represents the Routing Control Channel (RCC) 
-- associated with a PNNI interface. The RCC is used to exchange 
-- routing information between nodes in a peer group.

mscAtmIfVptPnniRcc OBJECT IDENTIFIER ::= { mscAtmIfVptPnni 3 }



mscAtmIfVptPnniRccRowStatusTable OBJECT-TYPE
   SYNTAX     SEQUENCE OF MscAtmIfVptPnniRccRowStatusEntry
   ACCESS     not-accessible
   STATUS     mandatory
   DESCRIPTION
     "This entry controls the addition and deletion of 
      mscAtmIfVptPnniRcc components."
::= { mscAtmIfVptPnniRcc 1 }

mscAtmIfVptPnniRccRowStatusEntry OBJECT-TYPE
   SYNTAX     MscAtmIfVptPnniRccRowStatusEntry
   ACCESS     not-accessible
   STATUS     mandatory
   DESCRIPTION
     "A single entry in the table represents a single 
      mscAtmIfVptPnniRcc component."
   INDEX {
      mscAtmIfIndex,
      mscAtmIfVptIndex,
      mscAtmIfVptPnniIndex,
      mscAtmIfVptPnniRccIndex }
::= { mscAtmIfVptPnniRccRowStatusTable 1 }

MscAtmIfVptPnniRccRowStatusEntry ::= SEQUENCE {
   mscAtmIfVptPnniRccRowStatus
      RowStatus,
   mscAtmIfVptPnniRccComponentName
      DisplayString,
   mscAtmIfVptPnniRccStorageType
      StorageType,
   mscAtmIfVptPnniRccIndex
      NonReplicated }

mscAtmIfVptPnniRccRowStatus OBJECT-TYPE
   SYNTAX     RowStatus 
   ACCESS     read-only
   STATUS     mandatory
   DESCRIPTION
     "This variable is used as the basis for SNMP naming of
      mscAtmIfVptPnniRcc components.
      These components cannot be added nor deleted."
::= { mscAtmIfVptPnniRccRowStatusEntry 1 }

mscAtmIfVptPnniRccComponentName OBJECT-TYPE
   SYNTAX     DisplayString 
   ACCESS     read-only
   STATUS     mandatory
   DESCRIPTION
     "This variable provides the component's string name for
      use with the ASCII Console Interface"
::= { mscAtmIfVptPnniRccRowStatusEntry 2 }

mscAtmIfVptPnniRccStorageType OBJECT-TYPE
   SYNTAX     StorageType 
   ACCESS     read-only
   STATUS     mandatory
   DESCRIPTION
     "This variable represents the storage type value for the
      mscAtmIfVptPnniRcc tables."
::= { mscAtmIfVptPnniRccRowStatusEntry 4 }

mscAtmIfVptPnniRccIndex OBJECT-TYPE
   SYNTAX     NonReplicated 
   ACCESS     not-accessible
   STATUS     mandatory
   DESCRIPTION
     "This variable represents the index for the mscAtmIfVptPnniRcc tables."
::= { mscAtmIfVptPnniRccRowStatusEntry 10 }

mscAtmIfVptPnniRccProvTable OBJECT-TYPE
   SYNTAX     SEQUENCE OF MscAtmIfVptPnniRccProvEntry
   ACCESS     not-accessible
   STATUS     mandatory
   DESCRIPTION
     "This group contains the generic provisionable attributes of an Rcc 
      component."
::= { mscAtmIfVptPnniRcc 10 }

mscAtmIfVptPnniRccProvEntry OBJECT-TYPE
   SYNTAX     MscAtmIfVptPnniRccProvEntry
   ACCESS     not-accessible
   STATUS     mandatory
   DESCRIPTION
     "An entry in the mscAtmIfVptPnniRccProvTable."
   INDEX {
      mscAtmIfIndex,
      mscAtmIfVptIndex,
      mscAtmIfVptPnniIndex,
      mscAtmIfVptPnniRccIndex }
::= { mscAtmIfVptPnniRccProvTable 1 }

MscAtmIfVptPnniRccProvEntry ::= SEQUENCE {
   mscAtmIfVptPnniRccVci
      Unsigned32 }

mscAtmIfVptPnniRccVci OBJECT-TYPE
   SYNTAX     Unsigned32 (0..65535)
   ACCESS     read-write
   STATUS     mandatory
   DESCRIPTION
     "This attribute specifies the VCI for the Routing Control Channel 
      (RCC). It is not recommended that the value be changed from the 
      default of 18 unless absolutely necessary. If a different VCI is 
      specified, ensure that the RCC at the far end is provisioned to use 
      the same VCI, otherwise the RCC will not come up."
   DEFVAL     { 18 }
::= { mscAtmIfVptPnniRccProvEntry 1 }

mscAtmIfVptPnniRccHlParmsTable OBJECT-TYPE
   SYNTAX     SEQUENCE OF MscAtmIfVptPnniRccHlParmsEntry
   ACCESS     not-accessible
   STATUS     mandatory
   DESCRIPTION
     "This group contains the provisionable Hello protocol parameters for 
      an Rcc component."
::= { mscAtmIfVptPnniRcc 11 }

mscAtmIfVptPnniRccHlParmsEntry OBJECT-TYPE
   SYNTAX     MscAtmIfVptPnniRccHlParmsEntry
   ACCESS     not-accessible
   STATUS     mandatory
   DESCRIPTION
     "An entry in the mscAtmIfVptPnniRccHlParmsTable."
   INDEX {
      mscAtmIfIndex,
      mscAtmIfVptIndex,
      mscAtmIfVptPnniIndex,
      mscAtmIfVptPnniRccIndex }
::= { mscAtmIfVptPnniRccHlParmsTable 1 }

MscAtmIfVptPnniRccHlParmsEntry ::= SEQUENCE {
   mscAtmIfVptPnniRccHelloHoldDown
      FixedPoint1,
   mscAtmIfVptPnniRccHelloInterval
      Unsigned32,
   mscAtmIfVptPnniRccHelloInactivityFactor
      Unsigned32 }

mscAtmIfVptPnniRccHelloHoldDown OBJECT-TYPE
   SYNTAX     FixedPoint1 (0..655350)
   ACCESS     read-write
   STATUS     mandatory
   DESCRIPTION
     "This attribute is used to limit the rate at which this node sends out 
      Hello packets. Specifically, it specifies the minimum time between 
      successive Hellos.
      
      A value of 0 specifies that the value provisioned for the 
      helloHoldDown attribute of the ARtg Pnni component should be 
      used."
   DEFVAL     { 0 }
::= { mscAtmIfVptPnniRccHlParmsEntry 1 }

mscAtmIfVptPnniRccHelloInterval OBJECT-TYPE
   SYNTAX     Unsigned32 (0..65535)
   ACCESS     read-write
   STATUS     mandatory
   DESCRIPTION
     "This attribute specifies the duration of the Hello Timer. Every 
      helloInterval seconds, this node will send out a Hello packet to the 
      neighbor node, subject to the helloHoldDown timer having expired 
      at least once since the last Hello packet was sent.
      
      A value of 0 specifies that the value provisioned for the 
      helloInterval attribute of the ARtg Pnni component should be used."
   DEFVAL     { 0 }
::= { mscAtmIfVptPnniRccHlParmsEntry 2 }

mscAtmIfVptPnniRccHelloInactivityFactor OBJECT-TYPE
   SYNTAX     Unsigned32 (0..65535)
   ACCESS     read-write
   STATUS     mandatory
   DESCRIPTION
     "This attribute specifies the number of Hello intervals allowed to 
      pass without receiving a Hello from the neighbor node, before an 
      attempt is made to re-stage. The hello inactivity timer is enabled in 
      the oneWayInside, twoWayInside, oneWayOutside, 
      twoWayOutside and commonOutside hello states (see the 
      helloState attribute on the Rcc component for a description of these 
      states). Note that the value for the Hello interval used in the 
      calculation is the one specified in the Hello packet from the 
      neighbor node.
      
      A value of 0 specifies that the value provisioned for the 
      helloInactivityFactor attribute of the ARtg Pnni component should 
      be used.
      DESCRIPTION"
   DEFVAL     { 0 }
::= { mscAtmIfVptPnniRccHlParmsEntry 3 }

mscAtmIfVptPnniRccStateTable OBJECT-TYPE
   SYNTAX     SEQUENCE OF MscAtmIfVptPnniRccStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscAtmIfVptPnniRcc 12 }

mscAtmIfVptPnniRccStateEntry OBJECT-TYPE
   SYNTAX     MscAtmIfVptPnniRccStateEntry
   ACCESS     not-accessible
   STATUS     mandatory
   DESCRIPTION
     "An entry in the mscAtmIfVptPnniRccStateTable."
   INDEX {
      mscAtmIfIndex,
      mscAtmIfVptIndex,
      mscAtmIfVptPnniIndex,
      mscAtmIfVptPnniRccIndex }
::= { mscAtmIfVptPnniRccStateTable 1 }

MscAtmIfVptPnniRccStateEntry ::= SEQUENCE {
   mscAtmIfVptPnniRccAdminState
      INTEGER,
   mscAtmIfVptPnniRccOperationalState
      INTEGER,
   mscAtmIfVptPnniRccUsageState
      INTEGER }

mscAtmIfVptPnniRccAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscAtmIfVptPnniRccStateEntry 1 }

mscAtmIfVptPnniRccOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscAtmIfVptPnniRccStateEntry 2 }

mscAtmIfVptPnniRccUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscAtmIfVptPnniRccStateEntry 3 }

mscAtmIfVptPnniRccOperTable OBJECT-TYPE
   SYNTAX     SEQUENCE OF MscAtmIfVptPnniRccOperEntry
   ACCESS     not-accessible
   STATUS     mandatory
   DESCRIPTION
     "This group contains the operational attributes for an Rcc 
      component."
::= { mscAtmIfVptPnniRcc 13 }

mscAtmIfVptPnniRccOperEntry OBJECT-TYPE
   SYNTAX     MscAtmIfVptPnniRccOperEntry
   ACCESS     not-accessible
   STATUS     mandatory
   DESCRIPTION
     "An entry in the mscAtmIfVptPnniRccOperTable."
   INDEX {
      mscAtmIfIndex,
      mscAtmIfVptIndex,
      mscAtmIfVptPnniIndex,
      mscAtmIfVptPnniRccIndex }
::= { mscAtmIfVptPnniRccOperTable 1 }

MscAtmIfVptPnniRccOperEntry ::= SEQUENCE {
   mscAtmIfVptPnniRccType
      INTEGER,
   mscAtmIfVptPnniRccNegotiatedVersion
      INTEGER,
   mscAtmIfVptPnniRccHelloState
      INTEGER,
   mscAtmIfVptPnniRccRemoteNodeId
      HexString,
   mscAtmIfVptPnniRccRemotePortId
      Unsigned32 }

mscAtmIfVptPnniRccType OBJECT-TYPE
   SYNTAX     INTEGER  {
                 unknown(0),
                 lowestLevelHorizLink(1),
                 lowestLevelOutsideLink(2),
                 horizontalLinkToLGN(3),
                 uplink(4) }
   ACCESS     read-only
   STATUS     mandatory
   DESCRIPTION
     "This attribute indicates the role of this link in the PNNI hierarchy.
      The following values are possible:
      
      unknown: the Hello protocol has not yet determined the role of the 
      link.
      
      lowestLevelHorizLink: the link is a horizontal link between two 
      lowest level nodes.
      
      lowestLevelOutsideLink: the link is an outside link between two 
      border nodes.
      
      horizontalLinkToLgn: the link is a horizontal link to a Logical 
      Group Node (LGN).
      
      uplink: the link is a uplink to a higher level LGN."
::= { mscAtmIfVptPnniRccOperEntry 1 }

mscAtmIfVptPnniRccNegotiatedVersion OBJECT-TYPE
   SYNTAX     INTEGER  {
                 unsupported(0),
                 version1point0(1) }
   ACCESS     read-only
   STATUS     mandatory
   DESCRIPTION
     "This attribute indicates the PNNI version negotiated with the 
      neighbor node."
::= { mscAtmIfVptPnniRccOperEntry 2 }

mscAtmIfVptPnniRccHelloState OBJECT-TYPE
   SYNTAX     INTEGER  {
                 notApplicable(0),
                 down(1),
                 attempt(2),
                 oneWayInside(3),
                 twoWayInside(4),
                 oneWayOutside(5),
                 twoWayOutside(6),
                 commonOutside(7) }
   ACCESS     read-only
   STATUS     mandatory
   DESCRIPTION
     "This attribute indicates the state of the Hello protocol exchange over 
      this link. The following are the possible values for this attribute:
      
      down: the link is down; no PNNI routing packets will be sent over 
      or received over such a link. This is the initial state of the Hello 
      Finite State Machine, and can also be reached when lower-level 
      protocols have indicated that the link is not usable.
      
      attempt: no Hello packets or Hello packets, with mismatch 
      information, have been received recently from the neighbor. 
      Attempts are made to contact the neighbor node by sending out 
      Hello packets every helloInterval seconds.
      
      oneWayInside: Hello packets have been recently received from the 
      neighbor and it has been established that both nodes are members of 
      the same peer group, but the remote node ID and remote port ID in 
      the neighbor's Hello packets were set to zero. A Hello packet is sent 
      to the neighbor and the Hello timer is restarted.
      
      twoWayInside: Bidirectional communication over this link between 
      this node and the neighbor node has been achieved.
      
      oneWayOutside: Hello packets have been recently received from 
      the neighbor and it has been established that both nodes are 
      members of a different peer group, but the remote node ID and 
      remote port ID in the neighbor's Hello packets were set to zero.
      
      twoWayOutside: Hellos have recently been received from the 
      neighbor indicating that the neighbor node belongs to a different 
      peer group. The correct remote node ID and remote port ID fields 
      were included in the Hello packet, but the nodal hierarchy list did 
      not include any common peer group. This state can also be reached 
      if a hierarchy mismatch occurs while in the commonOutside state.
      
      commonOutside: A common level of the routing hierarchy has been 
      found, in addition to achieving full bi-directional communication 
      between the two nodes."
::= { mscAtmIfVptPnniRccOperEntry 3 }

mscAtmIfVptPnniRccRemoteNodeId OBJECT-TYPE
   SYNTAX     HexString (SIZE (22))
   ACCESS     read-only
   STATUS     mandatory
   DESCRIPTION
     "This attribute indicates the neighbor node's node id."
::= { mscAtmIfVptPnniRccOperEntry 4 }

mscAtmIfVptPnniRccRemotePortId OBJECT-TYPE
   SYNTAX     Unsigned32 (0..4294967295)
   ACCESS     read-only
   STATUS     mandatory
   DESCRIPTION
     "This attribute indicates the neighbor node's port id."
::= { mscAtmIfVptPnniRccOperEntry 5 }

mscAtmIfVptPnniRccStatsTable OBJECT-TYPE
   SYNTAX     SEQUENCE OF MscAtmIfVptPnniRccStatsEntry
   ACCESS     not-accessible
   STATUS     mandatory
   DESCRIPTION
     "This group contains the statistical attributes for an Rcc component."
::= { mscAtmIfVptPnniRcc 14 }

mscAtmIfVptPnniRccStatsEntry OBJECT-TYPE
   SYNTAX     MscAtmIfVptPnniRccStatsEntry
   ACCESS     not-accessible
   STATUS     mandatory
   DESCRIPTION
     "An entry in the mscAtmIfVptPnniRccStatsTable."
   INDEX {
      mscAtmIfIndex,
      mscAtmIfVptIndex,
      mscAtmIfVptPnniIndex,
      mscAtmIfVptPnniRccIndex }
::= { mscAtmIfVptPnniRccStatsTable 1 }

MscAtmIfVptPnniRccStatsEntry ::= SEQUENCE {
   mscAtmIfVptPnniRccHelloPacketsRx
      Counter32,
   mscAtmIfVptPnniRccHelloPacketsTx
      Counter32,
   mscAtmIfVptPnniRccMismatchedHelloPacketsRx
      Counter32,
   mscAtmIfVptPnniRccBadHelloPacketsRx
      Counter32 }

mscAtmIfVptPnniRccHelloPacketsRx OBJECT-TYPE
   SYNTAX     Counter32 
   ACCESS     read-only
   STATUS     mandatory
   DESCRIPTION
     "This attribute counts the total number of Hello packets received 
      across this RCC, including bad and mismatched Hello packets. The 
      counter wraps when it exceeds the maximum value."
::= { mscAtmIfVptPnniRccStatsEntry 1 }

mscAtmIfVptPnniRccHelloPacketsTx OBJECT-TYPE
   SYNTAX     Counter32 
   ACCESS     read-only
   STATUS     mandatory
   DESCRIPTION
     "This attribute counts the total number of Hello packets transmitted 
      across this RCC. The counter wraps when it exceeds the maximum 
      value."
::= { mscAtmIfVptPnniRccStatsEntry 2 }

mscAtmIfVptPnniRccMismatchedHelloPacketsRx OBJECT-TYPE
   SYNTAX     Counter32 
   ACCESS     read-only
   STATUS     mandatory
   DESCRIPTION
     "This attribute counts the total number of mismatched Hello packets 
      received over this RCC. The counter wraps when it exceeds the 
      maximum value."
::= { mscAtmIfVptPnniRccStatsEntry 3 }

mscAtmIfVptPnniRccBadHelloPacketsRx OBJECT-TYPE
   SYNTAX     Counter32 
   ACCESS     read-only
   STATUS     mandatory
   DESCRIPTION
     "This attribute counts the total number of bad Hello packets received 
      over this RCC. The counter wraps when it exceeds the maximum 
      value."
::= { mscAtmIfVptPnniRccStatsEntry 4 }


-- AtmIf/n Uni Sig VirtualChannelDescriptor
-- AtmIf/n Uni Ilmi VirtualChannelDescriptor
-- AtmIf/n Iisp Sig VirtualChannelDescriptor
-- AtmIf/n Pnni Sig VirtualChannelDescriptor
-- AtmIf/n Pnni Rcc VirtualChannelDescriptor
-- AtmIf/n Vpt/m Uni Sig VirtualChannelDescriptor
-- AtmIf/n Vpt/m Iisp Sig VirtualChannelDescriptor
-- AtmIf/n Vpt/m Pnni Sig VirtualChannelDescriptor
-- AtmIf/n Vpt/m Pnni Rcc VirtualChannelDescriptor
-- 
-- This component contains the provisionable traffic parameters for a 
-- control channel (Sig, Ilmi or Rcc component).

mscAtmIfVptPnniRccVcd OBJECT IDENTIFIER ::= { mscAtmIfVptPnniRcc 2 }



mscAtmIfVptPnniRccVcdRowStatusTable OBJECT-TYPE
   SYNTAX     SEQUENCE OF MscAtmIfVptPnniRccVcdRowStatusEntry
   ACCESS     not-accessible
   STATUS     mandatory
   DESCRIPTION
     "This entry controls the addition and deletion of 
      mscAtmIfVptPnniRccVcd components."
::= { mscAtmIfVptPnniRccVcd 1 }

mscAtmIfVptPnniRccVcdRowStatusEntry OBJECT-TYPE
   SYNTAX     MscAtmIfVptPnniRccVcdRowStatusEntry
   ACCESS     not-accessible
   STATUS     mandatory
   DESCRIPTION
     "A single entry in the table represents a single 
      mscAtmIfVptPnniRccVcd component."
   INDEX {
      mscAtmIfIndex,
      mscAtmIfVptIndex,
      mscAtmIfVptPnniIndex,
      mscAtmIfVptPnniRccIndex,
      mscAtmIfVptPnniRccVcdIndex }
::= { mscAtmIfVptPnniRccVcdRowStatusTable 1 }

MscAtmIfVptPnniRccVcdRowStatusEntry ::= SEQUENCE {
   mscAtmIfVptPnniRccVcdRowStatus
      RowStatus,
   mscAtmIfVptPnniRccVcdComponentName
      DisplayString,
   mscAtmIfVptPnniRccVcdStorageType
      StorageType,
   mscAtmIfVptPnniRccVcdIndex
      NonReplicated }

mscAtmIfVptPnniRccVcdRowStatus OBJECT-TYPE
   SYNTAX     RowStatus 
   ACCESS     read-write
   STATUS     mandatory
   DESCRIPTION
     "This variable is used as the basis for SNMP naming of
      mscAtmIfVptPnniRccVcd components.
      These components can be added and deleted."
::= { mscAtmIfVptPnniRccVcdRowStatusEntry 1 }

mscAtmIfVptPnniRccVcdComponentName OBJECT-TYPE
   SYNTAX     DisplayString 
   ACCESS     read-only
   STATUS     mandatory
   DESCRIPTION
     "This variable provides the component's string name for
      use with the ASCII Console Interface"
::= { mscAtmIfVptPnniRccVcdRowStatusEntry 2 }

mscAtmIfVptPnniRccVcdStorageType OBJECT-TYPE
   SYNTAX     StorageType 
   ACCESS     read-only
   STATUS     mandatory
   DESCRIPTION
     "This variable represents the storage type value for the
      mscAtmIfVptPnniRccVcd tables."
::= { mscAtmIfVptPnniRccVcdRowStatusEntry 4 }

mscAtmIfVptPnniRccVcdIndex OBJECT-TYPE
   SYNTAX     NonReplicated 
   ACCESS     not-accessible
   STATUS     mandatory
   DESCRIPTION
     "This variable represents the index for the mscAtmIfVptPnniRccVcd tables."
::= { mscAtmIfVptPnniRccVcdRowStatusEntry 10 }

mscAtmIfVptPnniRccVcdProvTable OBJECT-TYPE
   SYNTAX     SEQUENCE OF MscAtmIfVptPnniRccVcdProvEntry
   ACCESS     not-accessible
   STATUS     mandatory
   DESCRIPTION
     "This group contains the provisionable traffic attributes for a control 
      channel."
::= { mscAtmIfVptPnniRccVcd 10 }

mscAtmIfVptPnniRccVcdProvEntry OBJECT-TYPE
   SYNTAX     MscAtmIfVptPnniRccVcdProvEntry
   ACCESS     not-accessible
   STATUS     mandatory
   DESCRIPTION
     "An entry in the mscAtmIfVptPnniRccVcdProvTable."
   INDEX {
      mscAtmIfIndex,
      mscAtmIfVptIndex,
      mscAtmIfVptPnniIndex,
      mscAtmIfVptPnniRccIndex,
      mscAtmIfVptPnniRccVcdIndex }
::= { mscAtmIfVptPnniRccVcdProvTable 1 }

MscAtmIfVptPnniRccVcdProvEntry ::= SEQUENCE {
   mscAtmIfVptPnniRccVcdTrafficDescType
      INTEGER,
   mscAtmIfVptPnniRccVcdAtmServiceCategory
      INTEGER,
   mscAtmIfVptPnniRccVcdWeight
      Unsigned32,
   mscAtmIfVptPnniRccVcdQosClass
      INTEGER,
   mscAtmIfVptPnniRccVcdTrafficShaping
      INTEGER,
   mscAtmIfVptPnniRccVcdUnshapedTransmitQueueing
      INTEGER,
   mscAtmIfVptPnniRccVcdUsageParameterControl
      INTEGER }

mscAtmIfVptPnniRccVcdTrafficDescType OBJECT-TYPE
   SYNTAX     INTEGER  {
                 n3(3),
                 n6(6),
                 n7(7),
                 n8(8) }
   ACCESS     read-write
   STATUS     mandatory
   DESCRIPTION
     "This attribute specifies the type of traffic management which is 
      applied to both the transmit and receive direction of this connection 
      as defined in the ATM Forum. The trafficDescType determines the 
      number and meaning of the parameters in the trafficDescParm 
      attribute."
   DEFVAL     { n6 }
::= { mscAtmIfVptPnniRccVcdProvEntry 1 }

mscAtmIfVptPnniRccVcdAtmServiceCategory OBJECT-TYPE
   SYNTAX     INTEGER  {
                 unspecifiedBitRate(0),
                 constantBitRate(1),
                 rtVariableBitRate(2),
                 nrtVariableBitRate(3) }
   ACCESS     read-write
   STATUS     mandatory
   DESCRIPTION
     "This attribute specifies the ATM service category for both directions 
      of the connection. 
      
      The constantBitRate service category is intended for real time 
      applications, that is those requiring tightly constrained delay and 
      delay variation, as would be appropriate for voice and video 
      applications. The consistent availability of a fixed quantity of 
      bandwidth is considered appropriate for CBR service. Cells which 
      are delayed beyond the value specified by CellTransfer Delay are 
      assumed to be of significantly reduce value to the application.
      
      The rtVariableBitRate service category is intended for real time 
      applications, that is those requiring tightly constrained delay and 
      delay variation, as would be appropriate for voice and video 
      applications. Sources are expected to transmit at a rate which varies 
      with time. Equivalently, the source can be described as 'bursty'. 
      Cells which are delayed beyond the value specified by CTD are 
      assumed to be of significantly reduced value to the application. Real 
      time VBR service may support statistical multiplexing of real time 
      sources.
      
      The nrtVariableBitRate service category is intended for non-real 
      time applications which have bursty traffic characteristics and which 
      can be characterized in terms of a PCR, SCR, and MBS. For those 
      cells which are transferred within the traffic contract, the application 
      expects a low cell loss ratio. For all connections, it expects a bound 
      on the mean cell transfer delay. Non-real time VBR service may 
      support statistical multiplexing of connections.
      
      The unspecifiedBitRate service is intended for non-real time 
      applications; that is, those not requiring tightly constrained delay 
      and delay variation. UBR sources are expected to be bursty. UBR 
      service supports a high degree of statistical multiplexing among 
      sources. UBR service does not specify traffic related service 
      guarantees. No numerical commitments are made with respect to 
      the cell loss ratio experienced by a UBR connection, or as to the 
      cell transfer delay experienced by cells on the connection."
   DEFVAL     { rtVariableBitRate }
::= { mscAtmIfVptPnniRccVcdProvEntry 3 }

mscAtmIfVptPnniRccVcdWeight OBJECT-TYPE
   SYNTAX     Unsigned32 (0 | 1..4095 | 65535)
   ACCESS     read-write
   STATUS     mandatory
   DESCRIPTION
     "This attribute specifies an override for the weight of this unshaped 
      connection. This attribute is ignored for shaped connections, for 
      ABR connections, for connections on a CQC-based ATM FP and 
      basic VPTs. 
      
      When the value is set to sameAsCa, the weight is determined by the 
      weight policy attribute under the CA service category component 
      for all but standard VPT VCCs. For standard VPT VCCs, the 
      weight is determined by the VCC's service category, when the value 
      is set to sameAsCa.
      
      When this attribute is set to a value from 1 to 4095, that value is 
      used for the weight policy of this connection relative to other 
      connections. For all but standard VPT VCCs, weight policy 
      determines the proportion of transit cell opportunities which are 
      allocated to this connection, compared to other connections in the 
      same service category. For standard VPT VCCs, weight policy 
      determines the proportion of transmit cell opportunities which are 
      allocated to this connection, compared to other connections 
      associated with the VPT.
      
      When the value is set to upToQueueLimit, the weight policy is 
      limited only by the txQueueLimit.

      VALUES (

      0 = upToQueueLimit

      65535 = sameAsCa

      )"
   DEFVAL     { 65535 }
::= { mscAtmIfVptPnniRccVcdProvEntry 4 }

mscAtmIfVptPnniRccVcdQosClass OBJECT-TYPE
   SYNTAX     INTEGER  {
                 n0(0),
                 n1(1),
                 n2(2),
                 n3(3),
                 n4(4) }
   ACCESS     read-write
   STATUS     mandatory
   DESCRIPTION
     "This attribute specifies the quality of service for both the forward 
      and backward direction for this connection.
      
      Class 1 supports a QOS that meets Service Class A performance 
      requirements (Circuit emulation, constant bit rate video).
      
      Class 2 supports a QOS that meets Service Class B performance 
      requirements (Variable bit rate audio and video).
      
      Class 3 supports a QOS that meets Service Class C performance 
      requirements (Connection-Oriented Data Transfer).
      
      Class 4 supports a QOS that meets Service Class D performance 
      requirements (Connectionless Data Transfer).
      
      Class 0 is the unspecified bit rate QOS class; no objective is 
      specified for the performance parameters."
   DEFVAL     { n2 }
::= { mscAtmIfVptPnniRccVcdProvEntry 21 }

mscAtmIfVptPnniRccVcdTrafficShaping OBJECT-TYPE
   SYNTAX     INTEGER  {
                 disabled(1),
                 sameAsCa(2) }
   ACCESS     read-write
   STATUS     mandatory
   DESCRIPTION
     "This attribute specifies whether this connection uses traffic shaping 
      when transmitting traffic to the ATM interface.
      
      When sameAsCa is selected, traffic shaping for this connection is 
      based on the trafficShaping attribute of the connection's service 
      category component under the AtmIf CA. If the service category has 
      traffic shaping enabled, then traffic shaping is enabled for the 
      connection. Note that enabling traffic shaping may have no effect 
      under certain cases. These cases are listed in the description of the 
      trafficShaping operational attribute, which is under the Vcc Tm and 
      Vpc Tm components.
      
      When disabled is selected, traffic shaping for this connection is 
      disabled."
   DEFVAL     { disabled }
::= { mscAtmIfVptPnniRccVcdProvEntry 50 }

mscAtmIfVptPnniRccVcdUnshapedTransmitQueueing OBJECT-TYPE
   SYNTAX     INTEGER  {
                 common(1),
                 sameAsCa(3) }
   ACCESS     read-write
   STATUS     mandatory
   DESCRIPTION
     "This attribute only applies when this connection is unshaped. This 
      attribute specifies the transmit queueing method for this connection 
      if it is unshaped. Refer to the unshapedTransmitQueueing attribute 
      under the AtmIf CA service category subcomponent for more details 
      on the meaning of this attribute. 
      
      When this attribute is set to sameAsCa, the transmit queueing 
      method for the connection is based on the 
      unshapedTransmitQueueing attribute of the connection's service 
      category component under the ConnectionAdministrator. 
      
      When this attribute is set to common, transmit traffic on this 
      unshaped connection is destined for the common queue. 
      
      The value sameAsInterface is for migration from previous software 
      releases, but should no longer be used"
   DEFVAL     { sameAsCa }
::= { mscAtmIfVptPnniRccVcdProvEntry 60 }

mscAtmIfVptPnniRccVcdUsageParameterControl OBJECT-TYPE
   SYNTAX     INTEGER  {
                 disabled(1),
                 sameAsCa(2) }
   ACCESS     read-write
   STATUS     mandatory
   DESCRIPTION
     "This attribute specifies whether this connection enforces usage 
      parameter control when receiving traffic from the ATM interface.
      
      When sameAsCa is selected, UPC for the connection is based on 
      the usageParameterControl attribute of the connection's service 
      category component under the ConnectionAdministrator. If the 
      service category has UPC enabled, then UPC is enabled for the 
      connection. Note that enabling UPC may have no effect under 
      certain cases. These cases are listed in the description of the 
      usageParameterControl operational attribute, which is under the 
      Vcc Tm or Vpc Tm component.
      
      When disabled is selected, UPC for this connection is disabled.
      
      The value sameAsInterface is for migration from previous software 
      releases, but should no longer be used"
   DEFVAL     { disabled }
::= { mscAtmIfVptPnniRccVcdProvEntry 70 }

mscAtmIfVptPnniRccVcdTdpTable OBJECT-TYPE
   SYNTAX     SEQUENCE OF MscAtmIfVptPnniRccVcdTdpEntry
   ACCESS     not-accessible
   STATUS     mandatory
   DESCRIPTION
     "This attribute is a vector of five traffic parameters whose meanings 
      are defined by the trafficDescType attribute. The values of peak cell 
      rate (PCR), sustained cell rate (SCR) and requested shaping rate are 
      expressed in cell/s. Maximum burst size (MBS) is expressed in 
      cells. CDVT is expressed in microseconds. The values of PCR, 
      SCR, MBS and CDVT are used for connection admission control 
      (CAC). The value of CDVT is only used for connections where the 
      atmServiceCategory is constantBitRate. For all other values of 
      atmServiceCategory, CDVT is ignored. The values of PCR, SCR 
      and requested shaping rate are used to determine the actual shaping 
      rate where traffic shaping is enabled.
      
      When trafficDescType is 3, parameter 1 represents the PCR for CLP 
      equal to 0 and 1 traffic; parameter 4 represents the CDVT; and 
      parameter 5 represents the requested shaping rate. A non-zero value 
      in parameter 5 overrides any value in parameter 1. This result is 
      used as the PCR. Parameter 1 must be non-zero. Parameters 2 and 3 
      must be zero.
      
      When trafficDescType is 6, parameter 1 represents the PCR for CLP 
      equal to 0 and 1 traffic; parameter 2 represents the SCR for CLP 
      equal to 0 and 1 traffic; parameter 3 represents the MBS for CLP 
      equal to 0 and 1 traffic; parameter 4 represents the CDVT; and 
      parameter 5 represents the requested shaping rate. A non-zero value 
      in parameter 5 overrides any value in parameter 1. This result is 
      used as the PCR. Parameters 1, 2, and 3 must be non-zero. 
      Parameter 1 must be greater than or equal to parameter 2. Parameter 
      5 must either be zero (unused) or greater than or equal to parameter 
      2.
      
      When trafficDescType is 7, parameter 1 represents the PCR for CLP 
      equal to 0 and 1 traffic; parameter 2 represents the SCR for CLP 
      equal to 0 with cell discard; parameter 3 represents the MBS for 
      CLP equal to 0 traffic; parameter 4 represents the CDVT; and 
      parameter 5 represents the requested shaping rate. A non-zero value 
      in parameter 5 overrides any value in parameter 1. This result is 
      used as the PCR. Parameters 1, 2, and 3 must be non-zero. 
      Parameter 1 must be greater than or equal to parameter 2. Parameter 
      5 must either be zero (unused) or greater than or equal to parameter 
      2.
      
      When trafficDescType is 8, parameter 1 represents the PCR for CLP 
      equal to 0 and 1 traffic; parameter 2 represents the SCR for CLP 
      equal to 0 traffic with cell tagging; parameter 3 represents the MBS 
      for CLP equal to 0 traffic; parameter 4 represents the CDVT; and 
      parameter 5 represents the requested shaping rate. A non-zero value 
      in parameter 5 overrides any value in parameter 1. This result is 
      used as the PCR. Parameters 1, 2, and 3 must be non-zero. 
      Parameter 1 must be greater than or equal to parameter 2. Parameter 
      5 must either be zero (unused) or greater than or equal to parameter 
      2.
      
      Whenever it is valid for PCR to be specified, parameter 5 may also 
      be used to specify a requested shaping rate. A non-zero value in 
      parameter 5 overrides the value in parameter 1 and is used as the 
      peak cell rate in calculations of CAC and shaping rate.
      
      For trafficDescType 3 the traffic is shaped at the next rate less than 
      the PCR. 
      
      For trafficDescType 6, 7, and 8, the traffic is shaped at the highest 
      available rate which is between PCR and SCR. However, if there is 
      no available shaping rate between PCR and SCR, traffic is shaped at 
      the next rate above the PCR."
::= { mscAtmIfVptPnniRccVcd 387 }

mscAtmIfVptPnniRccVcdTdpEntry OBJECT-TYPE
   SYNTAX     MscAtmIfVptPnniRccVcdTdpEntry
   ACCESS     not-accessible
   STATUS     mandatory
   DESCRIPTION
     "An entry in the mscAtmIfVptPnniRccVcdTdpTable."
   INDEX {
      mscAtmIfIndex,
      mscAtmIfVptIndex,
      mscAtmIfVptPnniIndex,
      mscAtmIfVptPnniRccIndex,
      mscAtmIfVptPnniRccVcdIndex,
      mscAtmIfVptPnniRccVcdTdpIndex }
::= { mscAtmIfVptPnniRccVcdTdpTable 1 }

MscAtmIfVptPnniRccVcdTdpEntry ::= SEQUENCE {
   mscAtmIfVptPnniRccVcdTdpIndex
      Integer32,
   mscAtmIfVptPnniRccVcdTdpValue
      Unsigned32 }

mscAtmIfVptPnniRccVcdTdpIndex OBJECT-TYPE
   SYNTAX     Integer32 (1..5)
   ACCESS     not-accessible
   STATUS     mandatory
   DESCRIPTION
     "This variable represents the mscAtmIfVptPnniRccVcdTdpTable
      specific index for the mscAtmIfVptPnniRccVcdTdpTable."
::= { mscAtmIfVptPnniRccVcdTdpEntry 1 }

mscAtmIfVptPnniRccVcdTdpValue OBJECT-TYPE
   SYNTAX     Unsigned32 (0..2147483647)
   ACCESS     read-write
   STATUS     mandatory
   DESCRIPTION
     "This variable represents an individual value for the
      mscAtmIfVptPnniRccVcdTdpTable."
::= { mscAtmIfVptPnniRccVcdTdpEntry 2 }


-- AtmIf/n Iisp Address/address,type
-- AtmIf/n Uni Address/address,type
-- AtmIf/n Pnni Address/address,type
-- AtmIf/n Vpt/m Iisp Address/address,type
-- AtmIf/n Vpt/m Uni Address/address,type
-- AtmIf/n Vpt/m Pnni Address/address,type
-- 
-- This component represents an address (dynamic or static) 
-- associated with the interface. The index is a string of 1 to 40 hex 
-- digits or a single wildcard ('?'), and a type. The type identifies 
-- whether the Address component is for a primary, alternate, 
-- registered, or default address. 
-- 
-- The types primary and alternate are used for provisioned addresses. 
-- The type registered is used for dynamic addresses registered 
-- through ILMI. The type default is used for Soft PVP and Soft PVC 
-- addresses.Virtual interfaces do not have addresses of 
-- type default.
-- 
-- The wildcard is only valid for provisioned addresses. If the address 
-- is a single wildcard, then that indicates that the interface supports 
-- all addresses. If there is no better match, then this interface may be 
-- chosen in the routing. If there is more than one interface with a 
-- single wildcard static address, then the choice is driven through a 
-- round robin algorithm. 
-- 
-- The round robin algorithm tries the primary routes and then the 
-- alternate routes if none of the primary routes succeed.
-- If this node participates in a PNNI hierarchy, then a PnniInfo 
-- subcomponent can be provisioned under the AtmAddress 
-- component to specify the level to which this address will be 
-- advertised.

mscAtmIfVptPnniAddr OBJECT IDENTIFIER ::= { mscAtmIfVptPnni 4 }



mscAtmIfVptPnniAddrRowStatusTable OBJECT-TYPE
   SYNTAX     SEQUENCE OF MscAtmIfVptPnniAddrRowStatusEntry
   ACCESS     not-accessible
   STATUS     mandatory
   DESCRIPTION
     "This entry controls the addition and deletion of 
      mscAtmIfVptPnniAddr components."
::= { mscAtmIfVptPnniAddr 1 }

mscAtmIfVptPnniAddrRowStatusEntry OBJECT-TYPE
   SYNTAX     MscAtmIfVptPnniAddrRowStatusEntry
   ACCESS     not-accessible
   STATUS     mandatory
   DESCRIPTION
     "A single entry in the table represents a single 
      mscAtmIfVptPnniAddr component."
   INDEX {
      mscAtmIfIndex,
      mscAtmIfVptIndex,
      mscAtmIfVptPnniIndex,
      mscAtmIfVptPnniAddrAddressIndex,
      mscAtmIfVptPnniAddrAddressTypeIndex }
::= { mscAtmIfVptPnniAddrRowStatusTable 1 }

MscAtmIfVptPnniAddrRowStatusEntry ::= SEQUENCE {
   mscAtmIfVptPnniAddrRowStatus
      RowStatus,
   mscAtmIfVptPnniAddrComponentName
      DisplayString,
   mscAtmIfVptPnniAddrStorageType
      StorageType,
   mscAtmIfVptPnniAddrAddressIndex
      AsciiStringIndex,
   mscAtmIfVptPnniAddrAddressTypeIndex
      INTEGER }

mscAtmIfVptPnniAddrRowStatus OBJECT-TYPE
   SYNTAX     RowStatus 
   ACCESS     read-write
   STATUS     mandatory
   DESCRIPTION
     "This variable is used as the basis for SNMP naming of
      mscAtmIfVptPnniAddr components.
      These components can be added and deleted."
::= { mscAtmIfVptPnniAddrRowStatusEntry 1 }

mscAtmIfVptPnniAddrComponentName OBJECT-TYPE
   SYNTAX     DisplayString 
   ACCESS     read-only
   STATUS     mandatory
   DESCRIPTION
     "This variable provides the component's string name for
      use with the ASCII Console Interface"
::= { mscAtmIfVptPnniAddrRowStatusEntry 2 }

mscAtmIfVptPnniAddrStorageType OBJECT-TYPE
   SYNTAX     StorageType 
   ACCESS     read-only
   STATUS     mandatory
   DESCRIPTION
     "This variable represents the storage type value for the
      mscAtmIfVptPnniAddr tables."
::= { mscAtmIfVptPnniAddrRowStatusEntry 4 }

mscAtmIfVptPnniAddrAddressIndex OBJECT-TYPE
   SYNTAX     AsciiStringIndex (SIZE (1..40))
   ACCESS     not-accessible
   STATUS     mandatory
   DESCRIPTION
     "This variable represents an index for the mscAtmIfVptPnniAddr tables."
::= { mscAtmIfVptPnniAddrRowStatusEntry 10 }

mscAtmIfVptPnniAddrAddressTypeIndex OBJECT-TYPE
   SYNTAX     INTEGER  {
                 primary(0),
                 alternate(1),
                 registered(2),
                 default(3) }
   ACCESS     not-accessible
   STATUS     mandatory
   DESCRIPTION
     "This variable represents an index for the mscAtmIfVptPnniAddr tables."
::= { mscAtmIfVptPnniAddrRowStatusEntry 11 }

mscAtmIfVptPnniAddrOperTable OBJECT-TYPE
   SYNTAX     SEQUENCE OF MscAtmIfVptPnniAddrOperEntry
   ACCESS     not-accessible
   STATUS     mandatory
   DESCRIPTION
     "This attribute group contains the operational attributes for the 
      Address component."
::= { mscAtmIfVptPnniAddr 10 }

mscAtmIfVptPnniAddrOperEntry OBJECT-TYPE
   SYNTAX     MscAtmIfVptPnniAddrOperEntry
   ACCESS     not-accessible
   STATUS     mandatory
   DESCRIPTION
     "An entry in the mscAtmIfVptPnniAddrOperTable."
   INDEX {
      mscAtmIfIndex,
      mscAtmIfVptIndex,
      mscAtmIfVptPnniIndex,
      mscAtmIfVptPnniAddrAddressIndex,
      mscAtmIfVptPnniAddrAddressTypeIndex }
::= { mscAtmIfVptPnniAddrOperTable 1 }

MscAtmIfVptPnniAddrOperEntry ::= SEQUENCE {
   mscAtmIfVptPnniAddrScope
      INTEGER,
   mscAtmIfVptPnniAddrReachability
      INTEGER }

mscAtmIfVptPnniAddrScope OBJECT-TYPE
   SYNTAX     INTEGER (-1..104)
   ACCESS     read-only
   STATUS     mandatory
   DESCRIPTION
     "This attribute indicates the scope of the ATM address, which is the 
      highest level to which this address will be advertised in the PNNI 
      hierarchy. If no PnniInfo subcomponent has been provisioned, then 
      the scope will default to the level of this node in the PNNI 
      hierarchy. If this node does not participate in a PNNI hierarchy, then 
      this attribute will have the value of -1."
::= { mscAtmIfVptPnniAddrOperEntry 1 }

mscAtmIfVptPnniAddrReachability OBJECT-TYPE
   SYNTAX     INTEGER  {
                 internal(0),
                 exterior(1) }
   ACCESS     read-only
   STATUS     mandatory
   DESCRIPTION
     "This attribute indicates whether the address is internal or exterior. 
      An internal reachable address is an address of a destination that is 
      directly attached to the logical node advertising the address. An 
      exterior reachable address is an address that can be reached 
      through a PNNI routing domain, but which is not located in that 
      PNNI routing domain."
::= { mscAtmIfVptPnniAddrOperEntry 2 }


-- AtmIf/n Iisp Address/address,type TerminateSPvpAndSPvc
-- AtmIf/n Uni Address/address,type TerminateSPvpAndSPvc
-- AtmIf/n Pnni Address/address,type TerminateSPvpAndSPvc
-- AtmIf/n Vpt/m Iisp Address/address,type TerminateSPvpAndSPvc
-- AtmIf/n Vpt/m Uni Address/address,type TerminateSPvpAndSPvc
-- AtmIf/n Vpt/m Pnni Address/address,type TerminateSPvpAndSPvc
-- 
-- The presence of this subcomponent indicates that SPvp and SPvc 
-- call setups terminate at this node if the destination address of the 
-- SPVP or SPVC matches the Address instance.

mscAtmIfVptPnniAddrTermSP OBJECT IDENTIFIER ::= { mscAtmIfVptPnniAddr 2 }



mscAtmIfVptPnniAddrTermSPRowStatusTable OBJECT-TYPE
   SYNTAX     SEQUENCE OF MscAtmIfVptPnniAddrTermSPRowStatusEntry
   ACCESS     not-accessible
   STATUS     mandatory
   DESCRIPTION
     "This entry controls the addition and deletion of 
      mscAtmIfVptPnniAddrTermSP components."
::= { mscAtmIfVptPnniAddrTermSP 1 }

mscAtmIfVptPnniAddrTermSPRowStatusEntry OBJECT-TYPE
   SYNTAX     MscAtmIfVptPnniAddrTermSPRowStatusEntry
   ACCESS     not-accessible
   STATUS     mandatory
   DESCRIPTION
     "A single entry in the table represents a single 
      mscAtmIfVptPnniAddrTermSP component."
   INDEX {
      mscAtmIfIndex,
      mscAtmIfVptIndex,
      mscAtmIfVptPnniIndex,
      mscAtmIfVptPnniAddrAddressIndex,
      mscAtmIfVptPnniAddrAddressTypeIndex,
      mscAtmIfVptPnniAddrTermSPIndex }
::= { mscAtmIfVptPnniAddrTermSPRowStatusTable 1 }

MscAtmIfVptPnniAddrTermSPRowStatusEntry ::= SEQUENCE {
   mscAtmIfVptPnniAddrTermSPRowStatus
      RowStatus,
   mscAtmIfVptPnniAddrTermSPComponentName
      DisplayString,
   mscAtmIfVptPnniAddrTermSPStorageType
      StorageType,
   mscAtmIfVptPnniAddrTermSPIndex
      NonReplicated }

mscAtmIfVptPnniAddrTermSPRowStatus OBJECT-TYPE
   SYNTAX     RowStatus 
   ACCESS     read-write
   STATUS     mandatory
   DESCRIPTION
     "This variable is used as the basis for SNMP naming of
      mscAtmIfVptPnniAddrTermSP components.
      These components can be added and deleted."
::= { mscAtmIfVptPnniAddrTermSPRowStatusEntry 1 }

mscAtmIfVptPnniAddrTermSPComponentName OBJECT-TYPE
   SYNTAX     DisplayString 
   ACCESS     read-only
   STATUS     mandatory
   DESCRIPTION
     "This variable provides the component's string name for
      use with the ASCII Console Interface"
::= { mscAtmIfVptPnniAddrTermSPRowStatusEntry 2 }

mscAtmIfVptPnniAddrTermSPStorageType OBJECT-TYPE
   SYNTAX     StorageType 
   ACCESS     read-only
   STATUS     mandatory
   DESCRIPTION
     "This variable represents the storage type value for the
      mscAtmIfVptPnniAddrTermSP tables."
::= { mscAtmIfVptPnniAddrTermSPRowStatusEntry 4 }

mscAtmIfVptPnniAddrTermSPIndex OBJECT-TYPE
   SYNTAX     NonReplicated 
   ACCESS     not-accessible
   STATUS     mandatory
   DESCRIPTION
     "This variable represents the index for the mscAtmIfVptPnniAddrTermSP tables."
::= { mscAtmIfVptPnniAddrTermSPRowStatusEntry 10 }


-- AtmIf/n Iisp Addr/address,type PnniInfo
-- AtmIf/n Uni Addr/address,type PnniInfo
-- AtmIf/n Pnni Addr/address,type PnniInfo
-- AtmIf/n Vpt/m Iisp Addr/address,type PnniInfo
-- AtmIf/n Vpt/m Uni Addr/address,type PnniInfo
-- AtmIf/n Vpt/m Pnni Addr/address,type PnniInfo
-- 
-- This component contains provisioned information associated with 
-- the ATM address related to PNNI. This component appears only 
-- under provisioned Address components.

mscAtmIfVptPnniAddrPnniInfo OBJECT IDENTIFIER ::= { mscAtmIfVptPnniAddr 3 }



mscAtmIfVptPnniAddrPnniInfoRowStatusTable OBJECT-TYPE
   SYNTAX     SEQUENCE OF MscAtmIfVptPnniAddrPnniInfoRowStatusEntry
   ACCESS     not-accessible
   STATUS     mandatory
   DESCRIPTION
     "This entry controls the addition and deletion of 
      mscAtmIfVptPnniAddrPnniInfo components."
::= { mscAtmIfVptPnniAddrPnniInfo 1 }

mscAtmIfVptPnniAddrPnniInfoRowStatusEntry OBJECT-TYPE
   SYNTAX     MscAtmIfVptPnniAddrPnniInfoRowStatusEntry
   ACCESS     not-accessible
   STATUS     mandatory
   DESCRIPTION
     "A single entry in the table represents a single 
      mscAtmIfVptPnniAddrPnniInfo component."
   INDEX {
      mscAtmIfIndex,
      mscAtmIfVptIndex,
      mscAtmIfVptPnniIndex,
      mscAtmIfVptPnniAddrAddressIndex,
      mscAtmIfVptPnniAddrAddressTypeIndex,
      mscAtmIfVptPnniAddrPnniInfoIndex }
::= { mscAtmIfVptPnniAddrPnniInfoRowStatusTable 1 }

MscAtmIfVptPnniAddrPnniInfoRowStatusEntry ::= SEQUENCE {
   mscAtmIfVptPnniAddrPnniInfoRowStatus
      RowStatus,
   mscAtmIfVptPnniAddrPnniInfoComponentName
      DisplayString,
   mscAtmIfVptPnniAddrPnniInfoStorageType
      StorageType,
   mscAtmIfVptPnniAddrPnniInfoIndex
      NonReplicated }

mscAtmIfVptPnniAddrPnniInfoRowStatus OBJECT-TYPE
   SYNTAX     RowStatus 
   ACCESS     read-write
   STATUS     mandatory
   DESCRIPTION
     "This variable is used as the basis for SNMP naming of
      mscAtmIfVptPnniAddrPnniInfo components.
      These components can be added and deleted."
::= { mscAtmIfVptPnniAddrPnniInfoRowStatusEntry 1 }

mscAtmIfVptPnniAddrPnniInfoComponentName OBJECT-TYPE
   SYNTAX     DisplayString 
   ACCESS     read-only
   STATUS     mandatory
   DESCRIPTION
     "This variable provides the component's string name for
      use with the ASCII Console Interface"
::= { mscAtmIfVptPnniAddrPnniInfoRowStatusEntry 2 }

mscAtmIfVptPnniAddrPnniInfoStorageType OBJECT-TYPE
   SYNTAX     StorageType 
   ACCESS     read-only
   STATUS     mandatory
   DESCRIPTION
     "This variable represents the storage type value for the
      mscAtmIfVptPnniAddrPnniInfo tables."
::= { mscAtmIfVptPnniAddrPnniInfoRowStatusEntry 4 }

mscAtmIfVptPnniAddrPnniInfoIndex OBJECT-TYPE
   SYNTAX     NonReplicated 
   ACCESS     not-accessible
   STATUS     mandatory
   DESCRIPTION
     "This variable represents the index for the mscAtmIfVptPnniAddrPnniInfo tables."
::= { mscAtmIfVptPnniAddrPnniInfoRowStatusEntry 10 }

mscAtmIfVptPnniAddrPnniInfoProvTable OBJECT-TYPE
   SYNTAX     SEQUENCE OF MscAtmIfVptPnniAddrPnniInfoProvEntry
   ACCESS     not-accessible
   STATUS     mandatory
   DESCRIPTION
     "This attribute group contains the provisioned attributes relating to 
      PNNI for a PnniInfo component."
::= { mscAtmIfVptPnniAddrPnniInfo 10 }

mscAtmIfVptPnniAddrPnniInfoProvEntry OBJECT-TYPE
   SYNTAX     MscAtmIfVptPnniAddrPnniInfoProvEntry
   ACCESS     not-accessible
   STATUS     mandatory
   DESCRIPTION
     "An entry in the mscAtmIfVptPnniAddrPnniInfoProvTable."
   INDEX {
      mscAtmIfIndex,
      mscAtmIfVptIndex,
      mscAtmIfVptPnniIndex,
      mscAtmIfVptPnniAddrAddressIndex,
      mscAtmIfVptPnniAddrAddressTypeIndex,
      mscAtmIfVptPnniAddrPnniInfoIndex }
::= { mscAtmIfVptPnniAddrPnniInfoProvTable 1 }

MscAtmIfVptPnniAddrPnniInfoProvEntry ::= SEQUENCE {
   mscAtmIfVptPnniAddrPnniInfoScope
      INTEGER,
   mscAtmIfVptPnniAddrPnniInfoReachability
      INTEGER }

mscAtmIfVptPnniAddrPnniInfoScope OBJECT-TYPE
   SYNTAX     INTEGER (-1..104)
   ACCESS     read-write
   STATUS     mandatory
   DESCRIPTION
     "This attribute specifies the scope of the ATM address, which is the 
      highest level up to which this address will be advertised in the 
      PNNI hierarchy. The scope must be set to a value numerically less 
      than or equal to the level of the lowest level peer group containing 
      this node. Setting the scope to 0 will cause the address to be 
      advertised globally within this PNNI routing domain."
   DEFVAL     { -1 }
::= { mscAtmIfVptPnniAddrPnniInfoProvEntry 1 }

mscAtmIfVptPnniAddrPnniInfoReachability OBJECT-TYPE
   SYNTAX     INTEGER  {
                 internal(0),
                 exterior(1) }
   ACCESS     read-write
   STATUS     mandatory
   DESCRIPTION
     "This attribute indicates whether the address is internal or exterior. 
      An internal reachable address is an address of a destination that is 
      directly attached to the logical node advertising the address. An 
      exterior reachable address is an address that can be reached 
      through a PNNI routing domain, but which is not located in that 
      PNNI routing domain."
   DEFVAL     { internal }
::= { mscAtmIfVptPnniAddrPnniInfoProvEntry 2 }


-- AtmIf/n Pnni
-- This component represents an ATM Private Network-Network 
-- Interface (PNNI) interface. If this component is provisioned, the 
-- Uni or Iisp component cannot be provisioned under the same AtmIf 
-- component. Also, the Artg Pnni component and the 
-- ConfiguredNode component corresponding to the participation of 
-- the this node in a lowest level peer group must already exist before 
-- provisioning Pnni under an AtmIf component. If this component is 
-- deleted, then all associated Vcc components are deleted.

mscAtmIfPnni OBJECT IDENTIFIER ::= { mscAtmIf 96 }



mscAtmIfPnniRowStatusTable OBJECT-TYPE
   SYNTAX     SEQUENCE OF MscAtmIfPnniRowStatusEntry
   ACCESS     not-accessible
   STATUS     mandatory
   DESCRIPTION
     "This entry controls the addition and deletion of 
      mscAtmIfPnni components."
::= { mscAtmIfPnni 1 }

mscAtmIfPnniRowStatusEntry OBJECT-TYPE
   SYNTAX     MscAtmIfPnniRowStatusEntry
   ACCESS     not-accessible
   STATUS     mandatory
   DESCRIPTION
     "A single entry in the table represents a single 
      mscAtmIfPnni component."
   INDEX {
      mscAtmIfIndex,
      mscAtmIfPnniIndex }
::= { mscAtmIfPnniRowStatusTable 1 }

MscAtmIfPnniRowStatusEntry ::= SEQUENCE {
   mscAtmIfPnniRowStatus
      RowStatus,
   mscAtmIfPnniComponentName
      DisplayString,
   mscAtmIfPnniStorageType
      StorageType,
   mscAtmIfPnniIndex
      NonReplicated }

mscAtmIfPnniRowStatus OBJECT-TYPE
   SYNTAX     RowStatus 
   ACCESS     read-write
   STATUS     mandatory
   DESCRIPTION
     "This variable is used as the basis for SNMP naming of
      mscAtmIfPnni components.
      These components can be added and deleted."
::= { mscAtmIfPnniRowStatusEntry 1 }

mscAtmIfPnniComponentName OBJECT-TYPE
   SYNTAX     DisplayString 
   ACCESS     read-only
   STATUS     mandatory
   DESCRIPTION
     "This variable provides the component's string name for
      use with the ASCII Console Interface"
::= { mscAtmIfPnniRowStatusEntry 2 }

mscAtmIfPnniStorageType OBJECT-TYPE
   SYNTAX     StorageType 
   ACCESS     read-only
   STATUS     mandatory
   DESCRIPTION
     "This variable represents the storage type value for the
      mscAtmIfPnni tables."
::= { mscAtmIfPnniRowStatusEntry 4 }

mscAtmIfPnniIndex OBJECT-TYPE
   SYNTAX     NonReplicated 
   ACCESS     not-accessible
   STATUS     mandatory
   DESCRIPTION
     "This variable represents the index for the mscAtmIfPnni tables."
::= { mscAtmIfPnniRowStatusEntry 10 }

mscAtmIfPnniProvTable OBJECT-TYPE
   SYNTAX     SEQUENCE OF MscAtmIfPnniProvEntry
   ACCESS     not-accessible
   STATUS     mandatory
   DESCRIPTION
     "This group contains the provisionable attributes for the Pnni
      component."
::= { mscAtmIfPnni 10 }

mscAtmIfPnniProvEntry OBJECT-TYPE
   SYNTAX     MscAtmIfPnniProvEntry
   ACCESS     not-accessible
   STATUS     mandatory
   DESCRIPTION
     "An entry in the mscAtmIfPnniProvTable."
   INDEX {
      mscAtmIfIndex,
      mscAtmIfPnniIndex }
::= { mscAtmIfPnniProvTable 1 }

MscAtmIfPnniProvEntry ::= SEQUENCE {
   mscAtmIfPnniSoftPvcRetryPeriod
      Unsigned32,
   mscAtmIfPnniSoftPvpAndPvcRetryPeriod
      Unsigned32,
   mscAtmIfPnniSoftPvpAndPvcHoldOffTime
      Unsigned32 }

mscAtmIfPnniSoftPvcRetryPeriod OBJECT-TYPE
   SYNTAX     Unsigned32 (20..999999)
   ACCESS     read-write
   STATUS     obsolete
   DESCRIPTION
     "This attribute represents the time in seconds to wait between call 
      setup retries. The resolution is to the nearest 10 seconds. 
      This attribute has been obsoleted and is replaced by the 
      softPvpAndPvcRetryPeriod attribute."
   DEFVAL     { 60 }
::= { mscAtmIfPnniProvEntry 1 }

mscAtmIfPnniSoftPvpAndPvcRetryPeriod OBJECT-TYPE
   SYNTAX     Unsigned32 (20..999999)
   ACCESS     read-write
   STATUS     mandatory
   DESCRIPTION
     "This attribute represents the time in seconds to wait between soft 
      PVP or soft PVC call  setup retries. The resolution is to the nearest 
      10 seconds."
   DEFVAL     { 60 }
::= { mscAtmIfPnniProvEntry 2 }

mscAtmIfPnniSoftPvpAndPvcHoldOffTime OBJECT-TYPE
   SYNTAX     Unsigned32 (0 | 50..20000)
   ACCESS     read-write
   STATUS     mandatory
   DESCRIPTION
     "This attribute specifies how long to hold off retries following a 
      release or the connection. The resolution is to the nearest 50 ms."
   DEFVAL     { 0 }
::= { mscAtmIfPnniProvEntry 5 }

mscAtmIfPnniAdminWeightsTable OBJECT-TYPE
   SYNTAX     SEQUENCE OF MscAtmIfPnniAdminWeightsEntry
   ACCESS     not-accessible
   STATUS     mandatory
   DESCRIPTION
     "This group contains the provisionable administrative weights for the 
      Pnni component. These weights will be used by Generic 
      Connection Admission Control (GCAC) if administrative weight is 
      the selected optimization criterion."
::= { mscAtmIfPnni 11 }

mscAtmIfPnniAdminWeightsEntry OBJECT-TYPE
   SYNTAX     MscAtmIfPnniAdminWeightsEntry
   ACCESS     not-accessible
   STATUS     mandatory
   DESCRIPTION
     "An entry in the mscAtmIfPnniAdminWeightsTable."
   INDEX {
      mscAtmIfIndex,
      mscAtmIfPnniIndex }
::= { mscAtmIfPnniAdminWeightsTable 1 }

MscAtmIfPnniAdminWeightsEntry ::= SEQUENCE {
   mscAtmIfPnniCbrWeight
      Unsigned32,
   mscAtmIfPnniRtVbrWeight
      Unsigned32,
   mscAtmIfPnniNrtVbrWeight
      Unsigned32,
   mscAtmIfPnniUbrWeight
      Unsigned32 }

mscAtmIfPnniCbrWeight OBJECT-TYPE
   SYNTAX     Unsigned32 (0..4294967295)
   ACCESS     read-write
   STATUS     mandatory
   DESCRIPTION
     "This attribute specifies the administrative weight assigned for 
      setting up switched calls with a service category of Constant Bit 
      Rate (CBR) for this PNNI interface. The value specified will be 
      used by Generic Connection Admission Control (GCAC) if 
      administrative weight is the selected optimization criterion; the 
      higher the value, the less desirable the link will be in path selection."
   DEFVAL     { 5040 }
::= { mscAtmIfPnniAdminWeightsEntry 1 }

mscAtmIfPnniRtVbrWeight OBJECT-TYPE
   SYNTAX     Unsigned32 (0..4294967295)
   ACCESS     read-write
   STATUS     mandatory
   DESCRIPTION
     "This attribute specifies the administrative weight assigned for 
      setting up switched calls with a service category of Real-Time 
      Variable Bit Rate (RT-VBR) for this PNNI interface. The value 
      specified will be used by Generic Connection Admission Control 
      (GCAC) if administrative weight is the selected optimization 
      criterion; the higher the value, the less desirable the link will be in 
      path selection."
   DEFVAL     { 5040 }
::= { mscAtmIfPnniAdminWeightsEntry 2 }

mscAtmIfPnniNrtVbrWeight OBJECT-TYPE
   SYNTAX     Unsigned32 (0..4294967295)
   ACCESS     read-write
   STATUS     mandatory
   DESCRIPTION
     "This attribute specifies the administrative weight assigned for 
      setting up switched calls with a service category of Non Real-Time 
      Variable Bit Rate (NRT-VBR) for this PNNI interface. The value 
      specified will be used by Generic Connection Admission Control 
      (GCAC) if administrative weight is the selected optimization 
      criterion; the higher the value, the less desirable the link will be in 
      path selection."
   DEFVAL     { 5040 }
::= { mscAtmIfPnniAdminWeightsEntry 3 }

mscAtmIfPnniUbrWeight OBJECT-TYPE
   SYNTAX     Unsigned32 (0..4294967295)
   ACCESS     read-write
   STATUS     mandatory
   DESCRIPTION
     "This attribute specifies the administrative weight assigned for 
      setting up switched calls with a service category of Unspecified Bit 
      Rate (UBR) for this PNNI interface. The value specified will be 
      used by Generic Connection Admission Control (GCAC) if 
      administrative weight is the selected optimization criterion; the 
      higher the value, the less desirable the link will be in path selection."
   DEFVAL     { 5040 }
::= { mscAtmIfPnniAdminWeightsEntry 4 }

mscAtmIfPnniAcctOptTable OBJECT-TYPE
   SYNTAX     SEQUENCE OF MscAtmIfPnniAcctOptEntry
   ACCESS     not-accessible
   STATUS     mandatory
   DESCRIPTION
     "This group contains the provisionable attributes for accounting."
::= { mscAtmIfPnni 12 }

mscAtmIfPnniAcctOptEntry OBJECT-TYPE
   SYNTAX     MscAtmIfPnniAcctOptEntry
   ACCESS     not-accessible
   STATUS     mandatory
   DESCRIPTION
     "An entry in the mscAtmIfPnniAcctOptTable."
   INDEX {
      mscAtmIfIndex,
      mscAtmIfPnniIndex }
::= { mscAtmIfPnniAcctOptTable 1 }

MscAtmIfPnniAcctOptEntry ::= SEQUENCE {
   mscAtmIfPnniAccountCollection
      OCTET STRING,
   mscAtmIfPnniAccountConnectionType
      INTEGER,
   mscAtmIfPnniAccountClass
      Unsigned32,
   mscAtmIfPnniServiceExchange
      Unsigned32 }

mscAtmIfPnniAccountCollection OBJECT-TYPE
   SYNTAX     OCTET STRING (SIZE (1))
   ACCESS     read-write
   STATUS     mandatory
   DESCRIPTION
     "This attribute is used to turn accounting on or off for SVC and 
      SPVC connections. It also specifies the reason(s) for which 
      accounting data is collected: billing, test, study, audit, or force.
      
      If the set of reasons is not empty then accounting records will be 
      generated by this interface in the following situations:
      - on a TODA changeover if TODA is enabled;
      - every 12 hours (per connection) if TODA is disabled;
      - on every call clear (a call record with final cell counts).
      
      If none of the reasons is present, then accounting will be 
      suppressed.
      
      The reason for collection is recorded in the accounting record, in 
      the attribute callingCollectReason or calledCollectReason as 
      appropriate.

      Description of bits:
      bill(0)
      test(1)
      study(2)
      audit(3)
      force(4)"
::= { mscAtmIfPnniAcctOptEntry 1 }

mscAtmIfPnniAccountConnectionType OBJECT-TYPE
   SYNTAX     INTEGER  {
                 origTerm(0),
                 intermediate(1) }
   ACCESS     read-write
   STATUS     mandatory
   DESCRIPTION
     "This attribute specifies whether accounting records generated by 
      this interface should be marked as originating, terminating or 
      intermediate. This attribute, in combination with the direction of the 
      call, determines the value of attribute connPointType of the 
      accounting record and may be used by downstream accounting 
      processes to correlate the records.
      
      If the value is origTerm then records generated for incoming calls 
      will be marked as originating and records generated for outgoing 
      calls will be marked as terminating.
      
      If the value is intermediate then records generated for all calls will 
      be marked as intermediate."
   DEFVAL     { intermediate }
::= { mscAtmIfPnniAcctOptEntry 2 }

mscAtmIfPnniAccountClass OBJECT-TYPE
   SYNTAX     Unsigned32 (0..255)
   ACCESS     read-write
   STATUS     mandatory
   DESCRIPTION
     "This attribute specifies the accounting class associated with the 
      interface. Its meaning is determined by the network operator.
      
      Its value is simply recorded in the accounting records generated by 
      this interface, in the attribute callingServiceType or 
      calledServiceType as appropriate."
   DEFVAL     { 0 }
::= { mscAtmIfPnniAcctOptEntry 3 }

mscAtmIfPnniServiceExchange OBJECT-TYPE
   SYNTAX     Unsigned32 (0..255)
   ACCESS     read-write
   STATUS     mandatory
   DESCRIPTION
     "This attribute specifies the data service exchange associated with 
      this interface. Its meaning is determined by the network operator.
      
      Its value is simply recorded in the accounting records generated by 
      this interface, in the attribute callingDse or calledDse as 
      appropriate."
   DEFVAL     { 0 }
::= { mscAtmIfPnniAcctOptEntry 4 }

mscAtmIfPnniOperationalTable OBJECT-TYPE
   SYNTAX     SEQUENCE OF MscAtmIfPnniOperationalEntry
   ACCESS     not-accessible
   STATUS     mandatory
   DESCRIPTION
     "This group contains the operational attributes for a Pnni component."
::= { mscAtmIfPnni 13 }

mscAtmIfPnniOperationalEntry OBJECT-TYPE
   SYNTAX     MscAtmIfPnniOperationalEntry
   ACCESS     not-accessible
   STATUS     mandatory
   DESCRIPTION
     "An entry in the mscAtmIfPnniOperationalTable."
   INDEX {
      mscAtmIfIndex,
      mscAtmIfPnniIndex }
::= { mscAtmIfPnniOperationalTable 1 }

MscAtmIfPnniOperationalEntry ::= SEQUENCE {
   mscAtmIfPnniPortId
      Unsigned32 }

mscAtmIfPnniPortId OBJECT-TYPE
   SYNTAX     Unsigned32 (0..4294967295)
   ACCESS     read-only
   STATUS     mandatory
   DESCRIPTION
     "This attribute indicates the port id of the PNNI interface, which is 
      the parent AtmIf's instance number."
::= { mscAtmIfPnniOperationalEntry 1 }


-- AtmIf/n Iisp Signalling
-- AtmIf/n Uni Signalling
-- AtmIf/n Pnni Signalling
-- AtmIf/n Vpt/m Iisp Signalling
-- AtmIf/n Vpt/m Uni Signalling
-- AtmIf/n Vpt/m Pnni Signalling
-- 
-- This component represents the signalling entities for the interface.

mscAtmIfPnniSig OBJECT IDENTIFIER ::= { mscAtmIfPnni 2 }



mscAtmIfPnniSigRowStatusTable OBJECT-TYPE
   SYNTAX     SEQUENCE OF MscAtmIfPnniSigRowStatusEntry
   ACCESS     not-accessible
   STATUS     mandatory
   DESCRIPTION
     "This entry controls the addition and deletion of 
      mscAtmIfPnniSig components."
::= { mscAtmIfPnniSig 1 }

mscAtmIfPnniSigRowStatusEntry OBJECT-TYPE
   SYNTAX     MscAtmIfPnniSigRowStatusEntry
   ACCESS     not-accessible
   STATUS     mandatory
   DESCRIPTION
     "A single entry in the table represents a single 
      mscAtmIfPnniSig component."
   INDEX {
      mscAtmIfIndex,
      mscAtmIfPnniIndex,
      mscAtmIfPnniSigIndex }
::= { mscAtmIfPnniSigRowStatusTable 1 }

MscAtmIfPnniSigRowStatusEntry ::= SEQUENCE {
   mscAtmIfPnniSigRowStatus
      RowStatus,
   mscAtmIfPnniSigComponentName
      DisplayString,
   mscAtmIfPnniSigStorageType
      StorageType,
   mscAtmIfPnniSigIndex
      NonReplicated }

mscAtmIfPnniSigRowStatus OBJECT-TYPE
   SYNTAX     RowStatus 
   ACCESS     read-only
   STATUS     mandatory
   DESCRIPTION
     "This variable is used as the basis for SNMP naming of
      mscAtmIfPnniSig components.
      These components cannot be added nor deleted."
::= { mscAtmIfPnniSigRowStatusEntry 1 }

mscAtmIfPnniSigComponentName OBJECT-TYPE
   SYNTAX     DisplayString 
   ACCESS     read-only
   STATUS     mandatory
   DESCRIPTION
     "This variable provides the component's string name for
      use with the ASCII Console Interface"
::= { mscAtmIfPnniSigRowStatusEntry 2 }

mscAtmIfPnniSigStorageType OBJECT-TYPE
   SYNTAX     StorageType 
   ACCESS     read-only
   STATUS     mandatory
   DESCRIPTION
     "This variable represents the storage type value for the
      mscAtmIfPnniSig tables."
::= { mscAtmIfPnniSigRowStatusEntry 4 }

mscAtmIfPnniSigIndex OBJECT-TYPE
   SYNTAX     NonReplicated 
   ACCESS     not-accessible
   STATUS     mandatory
   DESCRIPTION
     "This variable represents the index for the mscAtmIfPnniSig tables."
::= { mscAtmIfPnniSigRowStatusEntry 10 }

mscAtmIfPnniSigProvTable OBJECT-TYPE
   SYNTAX     SEQUENCE OF MscAtmIfPnniSigProvEntry
   ACCESS     not-accessible
   STATUS     mandatory
   DESCRIPTION
     "This attribute group contains the provisionable attributes for the 
      Signalling component."
::= { mscAtmIfPnniSig 10 }

mscAtmIfPnniSigProvEntry OBJECT-TYPE
   SYNTAX     MscAtmIfPnniSigProvEntry
   ACCESS     not-accessible
   STATUS     mandatory
   DESCRIPTION
     "An entry in the mscAtmIfPnniSigProvTable."
   INDEX {
      mscAtmIfIndex,
      mscAtmIfPnniIndex,
      mscAtmIfPnniSigIndex }
::= { mscAtmIfPnniSigProvTable 1 }

MscAtmIfPnniSigProvEntry ::= SEQUENCE {
   mscAtmIfPnniSigVci
      Unsigned32,
   mscAtmIfPnniSigAddressConversion
      INTEGER,
   mscAtmIfPnniSigOperatingMode
      INTEGER }

mscAtmIfPnniSigVci OBJECT-TYPE
   SYNTAX     Unsigned32 (0..65535)
   ACCESS     read-write
   STATUS     mandatory
   DESCRIPTION
     "This attribute specifies the signalling channel number."
   DEFVAL     { 5 }
::= { mscAtmIfPnniSigProvEntry 1 }

mscAtmIfPnniSigAddressConversion OBJECT-TYPE
   SYNTAX     INTEGER  {
                 none(0),
                 nativeE164(1),
                 nsap(2) }
   ACCESS     read-write
   STATUS     mandatory
   DESCRIPTION
     "This attribute specifies the address conversion on the outgoing 
      signalling PDUs. The options are none, nativeE164, or nsap. The 
      none option is the default and if this option is chosen then nothing 
      is done to the address information element (IE) in the outgoing 
      signalling message. If nativeE164 option is chosen, then only 
      NSAP encapsulated E.164 addresses with zeros in the ESI are 
      converted to native E.164 format in the outgoing signalling 
      message. If the NSAP address is not encapsulated E.164 or the ESI 
      field is not zeros and the nativeE164 option is chosen, then the call 
      is cleared. If the nsap option is chosen, then native E.164 addresses 
      are converted to NSAP E.164 with zeros in the ESI field; otherwise 
      the address is in NSAP format and is not changed."
   DEFVAL     { none }
::= { mscAtmIfPnniSigProvEntry 2 }

mscAtmIfPnniSigOperatingMode OBJECT-TYPE
   SYNTAX     INTEGER  {
                 normal(0),
                 provisionedOnly(1) }
   ACCESS     read-write
   STATUS     mandatory
   DESCRIPTION
     "This attribute specifies the operating mode of the signaling channel. 				
      provisionedOnly indicates that only SPVCs and SPVPs are 
      supported on the interface and SVCs are not supported. This value 
      is permitted only on UNI interfaces.
      normal indicates that SVCs, SPVCs, and SPVPs are supported on 
      the interface."
   DEFVAL     { normal }
::= { mscAtmIfPnniSigProvEntry 3 }

mscAtmIfPnniSigStateTable OBJECT-TYPE
   SYNTAX     SEQUENCE OF MscAtmIfPnniSigStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscAtmIfPnniSig 11 }

mscAtmIfPnniSigStateEntry OBJECT-TYPE
   SYNTAX     MscAtmIfPnniSigStateEntry
   ACCESS     not-accessible
   STATUS     mandatory
   DESCRIPTION
     "An entry in the mscAtmIfPnniSigStateTable."
   INDEX {
      mscAtmIfIndex,
      mscAtmIfPnniIndex,
      mscAtmIfPnniSigIndex }
::= { mscAtmIfPnniSigStateTable 1 }

MscAtmIfPnniSigStateEntry ::= SEQUENCE {
   mscAtmIfPnniSigAdminState
      INTEGER,
   mscAtmIfPnniSigOperationalState
      INTEGER,
   mscAtmIfPnniSigUsageState
      INTEGER }

mscAtmIfPnniSigAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscAtmIfPnniSigStateEntry 1 }

mscAtmIfPnniSigOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscAtmIfPnniSigStateEntry 2 }

mscAtmIfPnniSigUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscAtmIfPnniSigStateEntry 3 }

mscAtmIfPnniSigOperTable OBJECT-TYPE
   SYNTAX     SEQUENCE OF MscAtmIfPnniSigOperEntry
   ACCESS     not-accessible
   STATUS     mandatory
   DESCRIPTION
     "This attribute contains the operational attributes for the 
      AtmSignalling component."
::= { mscAtmIfPnniSig 12 }

mscAtmIfPnniSigOperEntry OBJECT-TYPE
   SYNTAX     MscAtmIfPnniSigOperEntry
   ACCESS     not-accessible
   STATUS     mandatory
   DESCRIPTION
     "An entry in the mscAtmIfPnniSigOperTable."
   INDEX {
      mscAtmIfIndex,
      mscAtmIfPnniIndex,
      mscAtmIfPnniSigIndex }
::= { mscAtmIfPnniSigOperTable 1 }

MscAtmIfPnniSigOperEntry ::= SEQUENCE {
   mscAtmIfPnniSigLastTxCauseCode
      Unsigned32,
   mscAtmIfPnniSigLastTxDiagCode
      Hex,
   mscAtmIfPnniSigLastRxCauseCode
      Unsigned32,
   mscAtmIfPnniSigLastRxDiagCode
      Hex }

mscAtmIfPnniSigLastTxCauseCode OBJECT-TYPE
   SYNTAX     Unsigned32 (0..255)
   ACCESS     read-only
   STATUS     mandatory
   DESCRIPTION
     "This attribute indicates the cause code in the last transmitted 
      signalling message that contains the CAUSE information element. 
      The cause code is used to describe the reason for generating certain 
      signalling messages."
::= { mscAtmIfPnniSigOperEntry 1 }

mscAtmIfPnniSigLastTxDiagCode OBJECT-TYPE
   SYNTAX     Hex (0..255)
   ACCESS     read-only
   STATUS     mandatory
   DESCRIPTION
     "This attribute contains the diagnostic code in the last transmitted 
      signalling message. The diagnostic code is contained in the CAUSE 
      information element and identifies an information element type or 
      timer type. The diagnostic code is present only if a procedural error 
      is detected by the signalling protocol. A diagnostic code is always 
      accompanied by the cause code. If there is no failure, this attribute 
      is set to 0."
::= { mscAtmIfPnniSigOperEntry 2 }

mscAtmIfPnniSigLastRxCauseCode OBJECT-TYPE
   SYNTAX     Unsigned32 (0..255)
   ACCESS     read-only
   STATUS     mandatory
   DESCRIPTION
     "This attribute contains the cause code in the last received signalling 
      message that contains the CAUSE information element. The cause 
      code is used to describe the reason for generating certain signalling 
      messages."
::= { mscAtmIfPnniSigOperEntry 3 }

mscAtmIfPnniSigLastRxDiagCode OBJECT-TYPE
   SYNTAX     Hex (0..255)
   ACCESS     read-only
   STATUS     mandatory
   DESCRIPTION
     "This attribute contains the diagnostic code in the last received 
      signalling message. The diagnostic code is contained in the CAUSE 
      information element and identifies an information element type or 
      timer type. The diagnostic code is present only if a procedural error 
      is detected by the signalling protocol. A diagnostic code is always 
      accompanied by the cause code. If there is no failure, this attribute 
      is set to 0."
::= { mscAtmIfPnniSigOperEntry 4 }

mscAtmIfPnniSigStatsTable OBJECT-TYPE
   SYNTAX     SEQUENCE OF MscAtmIfPnniSigStatsEntry
   ACCESS     not-accessible
   STATUS     mandatory
   DESCRIPTION
     "This attribute group contains the statistics associated with the 
      AtmSignalling component."
::= { mscAtmIfPnniSig 13 }

mscAtmIfPnniSigStatsEntry OBJECT-TYPE
   SYNTAX     MscAtmIfPnniSigStatsEntry
   ACCESS     not-accessible
   STATUS     mandatory
   DESCRIPTION
     "An entry in the mscAtmIfPnniSigStatsTable."
   INDEX {
      mscAtmIfIndex,
      mscAtmIfPnniIndex,
      mscAtmIfPnniSigIndex }
::= { mscAtmIfPnniSigStatsTable 1 }

MscAtmIfPnniSigStatsEntry ::= SEQUENCE {
   mscAtmIfPnniSigCurrentConnections
      Counter32,
   mscAtmIfPnniSigPeakConnections
      Gauge32,
   mscAtmIfPnniSigSuccessfulConnections
      Counter32,
   mscAtmIfPnniSigFailedConnections
      Counter32,
   mscAtmIfPnniSigTxPdus
      Counter32,
   mscAtmIfPnniSigRxPdus
      Counter32,
   mscAtmIfPnniSigCurrentPmpConnections
      Gauge32,
   mscAtmIfPnniSigPeakPmpConnections
      Gauge32,
   mscAtmIfPnniSigSuccessfulPmpConnections
      Counter32,
   mscAtmIfPnniSigFailedPmpConnections
      Counter32,
   mscAtmIfPnniSigNewCurrentConnections
      Gauge32 }

mscAtmIfPnniSigCurrentConnections OBJECT-TYPE
   SYNTAX     Counter32 
   ACCESS     read-only
   STATUS     obsolete
   DESCRIPTION
     "This attribute indicates the total number of currently active 
      connections."
::= { mscAtmIfPnniSigStatsEntry 1 }

mscAtmIfPnniSigPeakConnections OBJECT-TYPE
   SYNTAX     Gauge32 (0..4294967295)
   ACCESS     read-only
   STATUS     mandatory
   DESCRIPTION
     "This attribute indicates the high water mark of active point-to-
      point and point-to-multipoint connections."
::= { mscAtmIfPnniSigStatsEntry 2 }

mscAtmIfPnniSigSuccessfulConnections OBJECT-TYPE
   SYNTAX     Counter32 
   ACCESS     read-only
   STATUS     mandatory
   DESCRIPTION
     "This attribute counts the total number of switched point-to-
      point and point-to-multipoint connections that were successfully 
      established. The counter wraps to 0 when the maximum value is 
      exceeded."
::= { mscAtmIfPnniSigStatsEntry 3 }

mscAtmIfPnniSigFailedConnections OBJECT-TYPE
   SYNTAX     Counter32 
   ACCESS     read-only
   STATUS     mandatory
   DESCRIPTION
     "This attribute counts the total number of switched connections that 
      were not successfully established.The counter wraps to 0 when the 
      maximum value is exceeded."
::= { mscAtmIfPnniSigStatsEntry 4 }

mscAtmIfPnniSigTxPdus OBJECT-TYPE
   SYNTAX     Counter32 
   ACCESS     read-only
   STATUS     mandatory
   DESCRIPTION
     "This attribute counts the number of transmitted signalling 
      PDUs.The counter wraps to 0 when the maximum value is 
      exceeded."
::= { mscAtmIfPnniSigStatsEntry 5 }

mscAtmIfPnniSigRxPdus OBJECT-TYPE
   SYNTAX     Counter32 
   ACCESS     read-only
   STATUS     mandatory
   DESCRIPTION
     "This attribute counts the number of received signalling PDUs.The 
      counter wraps to 0 when the maximum value is exceeded."
::= { mscAtmIfPnniSigStatsEntry 6 }

mscAtmIfPnniSigCurrentPmpConnections OBJECT-TYPE
   SYNTAX     Gauge32 (0..4294967295)
   ACCESS     read-only
   STATUS     mandatory
   DESCRIPTION
     "This attribute indicates the number of currently active point-to-
      multipoint connections."
::= { mscAtmIfPnniSigStatsEntry 7 }

mscAtmIfPnniSigPeakPmpConnections OBJECT-TYPE
   SYNTAX     Gauge32 (0..4294967295)
   ACCESS     read-only
   STATUS     mandatory
   DESCRIPTION
     "This attribute indicates the high water mark of active point-to-
      multipoint connections."
::= { mscAtmIfPnniSigStatsEntry 8 }

mscAtmIfPnniSigSuccessfulPmpConnections OBJECT-TYPE
   SYNTAX     Counter32 
   ACCESS     read-only
   STATUS     mandatory
   DESCRIPTION
     "This attribute counts the total number of switched point-to-
      multipoint connections that were successfully established. 
      The counter wraps to 0 when the maximum value is 
      exceeded."
::= { mscAtmIfPnniSigStatsEntry 9 }

mscAtmIfPnniSigFailedPmpConnections OBJECT-TYPE
   SYNTAX     Counter32 
   ACCESS     read-only
   STATUS     mandatory
   DESCRIPTION
     "This attribute counts the number of switched point-to-
      multipoint connections that were not successfully 
      established.The counter wraps to 0 when the maximum value 
      is exceeded."
::= { mscAtmIfPnniSigStatsEntry 10 }

mscAtmIfPnniSigNewCurrentConnections OBJECT-TYPE
   SYNTAX     Gauge32 (0..4294967295)
   ACCESS     read-only
   STATUS     mandatory
   DESCRIPTION
     "This attribute indicates the total number of currently active point-to-
      point and point-to-multipoint connections."
::= { mscAtmIfPnniSigStatsEntry 11 }


-- AtmIf/n Uni Sig VirtualChannelDescriptor
-- AtmIf/n Uni Ilmi VirtualChannelDescriptor
-- AtmIf/n Iisp Sig VirtualChannelDescriptor
-- AtmIf/n Pnni Sig VirtualChannelDescriptor
-- AtmIf/n Pnni Rcc VirtualChannelDescriptor
-- AtmIf/n Vpt/m Uni Sig VirtualChannelDescriptor
-- AtmIf/n Vpt/m Iisp Sig VirtualChannelDescriptor
-- AtmIf/n Vpt/m Pnni Sig VirtualChannelDescriptor
-- AtmIf/n Vpt/m Pnni Rcc VirtualChannelDescriptor
-- 
-- This component contains the provisionable traffic parameters for a 
-- control channel (Sig, Ilmi or Rcc component).

mscAtmIfPnniSigVcd OBJECT IDENTIFIER ::= { mscAtmIfPnniSig 2 }



mscAtmIfPnniSigVcdRowStatusTable OBJECT-TYPE
   SYNTAX     SEQUENCE OF MscAtmIfPnniSigVcdRowStatusEntry
   ACCESS     not-accessible
   STATUS     mandatory
   DESCRIPTION
     "This entry controls the addition and deletion of 
      mscAtmIfPnniSigVcd components."
::= { mscAtmIfPnniSigVcd 1 }

mscAtmIfPnniSigVcdRowStatusEntry OBJECT-TYPE
   SYNTAX     MscAtmIfPnniSigVcdRowStatusEntry
   ACCESS     not-accessible
   STATUS     mandatory
   DESCRIPTION
     "A single entry in the table represents a single 
      mscAtmIfPnniSigVcd component."
   INDEX {
      mscAtmIfIndex,
      mscAtmIfPnniIndex,
      mscAtmIfPnniSigIndex,
      mscAtmIfPnniSigVcdIndex }
::= { mscAtmIfPnniSigVcdRowStatusTable 1 }

MscAtmIfPnniSigVcdRowStatusEntry ::= SEQUENCE {
   mscAtmIfPnniSigVcdRowStatus
      RowStatus,
   mscAtmIfPnniSigVcdComponentName
      DisplayString,
   mscAtmIfPnniSigVcdStorageType
      StorageType,
   mscAtmIfPnniSigVcdIndex
      NonReplicated }

mscAtmIfPnniSigVcdRowStatus OBJECT-TYPE
   SYNTAX     RowStatus 
   ACCESS     read-write
   STATUS     mandatory
   DESCRIPTION
     "This variable is used as the basis for SNMP naming of
      mscAtmIfPnniSigVcd components.
      These components can be added and deleted."
::= { mscAtmIfPnniSigVcdRowStatusEntry 1 }

mscAtmIfPnniSigVcdComponentName OBJECT-TYPE
   SYNTAX     DisplayString 
   ACCESS     read-only
   STATUS     mandatory
   DESCRIPTION
     "This variable provides the component's string name for
      use with the ASCII Console Interface"
::= { mscAtmIfPnniSigVcdRowStatusEntry 2 }

mscAtmIfPnniSigVcdStorageType OBJECT-TYPE
   SYNTAX     StorageType 
   ACCESS     read-only
   STATUS     mandatory
   DESCRIPTION
     "This variable represents the storage type value for the
      mscAtmIfPnniSigVcd tables."
::= { mscAtmIfPnniSigVcdRowStatusEntry 4 }

mscAtmIfPnniSigVcdIndex OBJECT-TYPE
   SYNTAX     NonReplicated 
   ACCESS     not-accessible
   STATUS     mandatory
   DESCRIPTION
     "This variable represents the index for the mscAtmIfPnniSigVcd tables."
::= { mscAtmIfPnniSigVcdRowStatusEntry 10 }

mscAtmIfPnniSigVcdProvTable OBJECT-TYPE
   SYNTAX     SEQUENCE OF MscAtmIfPnniSigVcdProvEntry
   ACCESS     not-accessible
   STATUS     mandatory
   DESCRIPTION
     "This group contains the provisionable traffic attributes for a control 
      channel."
::= { mscAtmIfPnniSigVcd 10 }

mscAtmIfPnniSigVcdProvEntry OBJECT-TYPE
   SYNTAX     MscAtmIfPnniSigVcdProvEntry
   ACCESS     not-accessible
   STATUS     mandatory
   DESCRIPTION
     "An entry in the mscAtmIfPnniSigVcdProvTable."
   INDEX {
      mscAtmIfIndex,
      mscAtmIfPnniIndex,
      mscAtmIfPnniSigIndex,
      mscAtmIfPnniSigVcdIndex }
::= { mscAtmIfPnniSigVcdProvTable 1 }

MscAtmIfPnniSigVcdProvEntry ::= SEQUENCE {
   mscAtmIfPnniSigVcdTrafficDescType
      INTEGER,
   mscAtmIfPnniSigVcdAtmServiceCategory
      INTEGER,
   mscAtmIfPnniSigVcdWeight
      Unsigned32,
   mscAtmIfPnniSigVcdQosClass
      INTEGER,
   mscAtmIfPnniSigVcdTrafficShaping
      INTEGER,
   mscAtmIfPnniSigVcdUnshapedTransmitQueueing
      INTEGER,
   mscAtmIfPnniSigVcdUsageParameterControl
      INTEGER }

mscAtmIfPnniSigVcdTrafficDescType OBJECT-TYPE
   SYNTAX     INTEGER  {
                 n3(3),
                 n6(6),
                 n7(7),
                 n8(8) }
   ACCESS     read-write
   STATUS     mandatory
   DESCRIPTION
     "This attribute specifies the type of traffic management which is 
      applied to both the transmit and receive direction of this connection 
      as defined in the ATM Forum. The trafficDescType determines the 
      number and meaning of the parameters in the trafficDescParm 
      attribute."
   DEFVAL     { n6 }
::= { mscAtmIfPnniSigVcdProvEntry 1 }

mscAtmIfPnniSigVcdAtmServiceCategory OBJECT-TYPE
   SYNTAX     INTEGER  {
                 unspecifiedBitRate(0),
                 constantBitRate(1),
                 rtVariableBitRate(2),
                 nrtVariableBitRate(3) }
   ACCESS     read-write
   STATUS     mandatory
   DESCRIPTION
     "This attribute specifies the ATM service category for both directions 
      of the connection. 
      
      The constantBitRate service category is intended for real time 
      applications, that is those requiring tightly constrained delay and 
      delay variation, as would be appropriate for voice and video 
      applications. The consistent availability of a fixed quantity of 
      bandwidth is considered appropriate for CBR service. Cells which 
      are delayed beyond the value specified by CellTransfer Delay are 
      assumed to be of significantly reduce value to the application.
      
      The rtVariableBitRate service category is intended for real time 
      applications, that is those requiring tightly constrained delay and 
      delay variation, as would be appropriate for voice and video 
      applications. Sources are expected to transmit at a rate which varies 
      with time. Equivalently, the source can be described as 'bursty'. 
      Cells which are delayed beyond the value specified by CTD are 
      assumed to be of significantly reduced value to the application. Real 
      time VBR service may support statistical multiplexing of real time 
      sources.
      
      The nrtVariableBitRate service category is intended for non-real 
      time applications which have bursty traffic characteristics and which 
      can be characterized in terms of a PCR, SCR, and MBS. For those 
      cells which are transferred within the traffic contract, the application 
      expects a low cell loss ratio. For all connections, it expects a bound 
      on the mean cell transfer delay. Non-real time VBR service may 
      support statistical multiplexing of connections.
      
      The unspecifiedBitRate service is intended for non-real time 
      applications; that is, those not requiring tightly constrained delay 
      and delay variation. UBR sources are expected to be bursty. UBR 
      service supports a high degree of statistical multiplexing among 
      sources. UBR service does not specify traffic related service 
      guarantees. No numerical commitments are made with respect to 
      the cell loss ratio experienced by a UBR connection, or as to the 
      cell transfer delay experienced by cells on the connection."
   DEFVAL     { rtVariableBitRate }
::= { mscAtmIfPnniSigVcdProvEntry 3 }

mscAtmIfPnniSigVcdWeight OBJECT-TYPE
   SYNTAX     Unsigned32 (0 | 1..4095 | 65535)
   ACCESS     read-write
   STATUS     mandatory
   DESCRIPTION
     "This attribute specifies an override for the weight of this unshaped 
      connection. This attribute is ignored for shaped connections, for 
      ABR connections, for connections on a CQC-based ATM FP and 
      basic VPTs. 
      
      When the value is set to sameAsCa, the weight is determined by the 
      weight policy attribute under the CA service category component 
      for all but standard VPT VCCs. For standard VPT VCCs, the 
      weight is determined by the VCC's service category, when the value 
      is set to sameAsCa.
      
      When this attribute is set to a value from 1 to 4095, that value is 
      used for the weight policy of this connection relative to other 
      connections. For all but standard VPT VCCs, weight policy 
      determines the proportion of transit cell opportunities which are 
      allocated to this connection, compared to other connections in the 
      same service category. For standard VPT VCCs, weight policy 
      determines the proportion of transmit cell opportunities which are 
      allocated to this connection, compared to other connections 
      associated with the VPT.
      
      When the value is set to upToQueueLimit, the weight policy is 
      limited only by the txQueueLimit.

      VALUES (

      0 = upToQueueLimit

      65535 = sameAsCa

      )"
   DEFVAL     { 65535 }
::= { mscAtmIfPnniSigVcdProvEntry 4 }

mscAtmIfPnniSigVcdQosClass OBJECT-TYPE
   SYNTAX     INTEGER  {
                 n0(0),
                 n1(1),
                 n2(2),
                 n3(3),
                 n4(4) }
   ACCESS     read-write
   STATUS     mandatory
   DESCRIPTION
     "This attribute specifies the quality of service for both the forward 
      and backward direction for this connection.
      
      Class 1 supports a QOS that meets Service Class A performance 
      requirements (Circuit emulation, constant bit rate video).
      
      Class 2 supports a QOS that meets Service Class B performance 
      requirements (Variable bit rate audio and video).
      
      Class 3 supports a QOS that meets Service Class C performance 
      requirements (Connection-Oriented Data Transfer).
      
      Class 4 supports a QOS that meets Service Class D performance 
      requirements (Connectionless Data Transfer).
      
      Class 0 is the unspecified bit rate QOS class; no objective is 
      specified for the performance parameters."
   DEFVAL     { n2 }
::= { mscAtmIfPnniSigVcdProvEntry 21 }

mscAtmIfPnniSigVcdTrafficShaping OBJECT-TYPE
   SYNTAX     INTEGER  {
                 disabled(1),
                 sameAsCa(2) }
   ACCESS     read-write
   STATUS     mandatory
   DESCRIPTION
     "This attribute specifies whether this connection uses traffic shaping 
      when transmitting traffic to the ATM interface.
      
      When sameAsCa is selected, traffic shaping for this connection is 
      based on the trafficShaping attribute of the connection's service 
      category component under the AtmIf CA. If the service category has 
      traffic shaping enabled, then traffic shaping is enabled for the 
      connection. Note that enabling traffic shaping may have no effect 
      under certain cases. These cases are listed in the description of the 
      trafficShaping operational attribute, which is under the Vcc Tm and 
      Vpc Tm components.
      
      When disabled is selected, traffic shaping for this connection is 
      disabled."
   DEFVAL     { disabled }
::= { mscAtmIfPnniSigVcdProvEntry 50 }

mscAtmIfPnniSigVcdUnshapedTransmitQueueing OBJECT-TYPE
   SYNTAX     INTEGER  {
                 common(1),
                 sameAsCa(3) }
   ACCESS     read-write
   STATUS     mandatory
   DESCRIPTION
     "This attribute only applies when this connection is unshaped. This 
      attribute specifies the transmit queueing method for this connection 
      if it is unshaped. Refer to the unshapedTransmitQueueing attribute 
      under the AtmIf CA service category subcomponent for more details 
      on the meaning of this attribute. 
      
      When this attribute is set to sameAsCa, the transmit queueing 
      method for the connection is based on the 
      unshapedTransmitQueueing attribute of the connection's service 
      category component under the ConnectionAdministrator. 
      
      When this attribute is set to common, transmit traffic on this 
      unshaped connection is destined for the common queue. 
      
      The value sameAsInterface is for migration from previous software 
      releases, but should no longer be used"
   DEFVAL     { sameAsCa }
::= { mscAtmIfPnniSigVcdProvEntry 60 }

mscAtmIfPnniSigVcdUsageParameterControl OBJECT-TYPE
   SYNTAX     INTEGER  {
                 disabled(1),
                 sameAsCa(2) }
   ACCESS     read-write
   STATUS     mandatory
   DESCRIPTION
     "This attribute specifies whether this connection enforces usage 
      parameter control when receiving traffic from the ATM interface.
      
      When sameAsCa is selected, UPC for the connection is based on 
      the usageParameterControl attribute of the connection's service 
      category component under the ConnectionAdministrator. If the 
      service category has UPC enabled, then UPC is enabled for the 
      connection. Note that enabling UPC may have no effect under 
      certain cases. These cases are listed in the description of the 
      usageParameterControl operational attribute, which is under the 
      Vcc Tm or Vpc Tm component.
      
      When disabled is selected, UPC for this connection is disabled.
      
      The value sameAsInterface is for migration from previous software 
      releases, but should no longer be used"
   DEFVAL     { disabled }
::= { mscAtmIfPnniSigVcdProvEntry 70 }

mscAtmIfPnniSigVcdTdpTable OBJECT-TYPE
   SYNTAX     SEQUENCE OF MscAtmIfPnniSigVcdTdpEntry
   ACCESS     not-accessible
   STATUS     mandatory
   DESCRIPTION
     "This attribute is a vector of five traffic parameters whose meanings 
      are defined by the trafficDescType attribute. The values of peak cell 
      rate (PCR), sustained cell rate (SCR) and requested shaping rate are 
      expressed in cell/s. Maximum burst size (MBS) is expressed in 
      cells. CDVT is expressed in microseconds. The values of PCR, 
      SCR, MBS and CDVT are used for connection admission control 
      (CAC). The value of CDVT is only used for connections where the 
      atmServiceCategory is constantBitRate. For all other values of 
      atmServiceCategory, CDVT is ignored. The values of PCR, SCR 
      and requested shaping rate are used to determine the actual shaping 
      rate where traffic shaping is enabled.
      
      When trafficDescType is 3, parameter 1 represents the PCR for CLP 
      equal to 0 and 1 traffic; parameter 4 represents the CDVT; and 
      parameter 5 represents the requested shaping rate. A non-zero value 
      in parameter 5 overrides any value in parameter 1. This result is 
      used as the PCR. Parameter 1 must be non-zero. Parameters 2 and 3 
      must be zero.
      
      When trafficDescType is 6, parameter 1 represents the PCR for CLP 
      equal to 0 and 1 traffic; parameter 2 represents the SCR for CLP 
      equal to 0 and 1 traffic; parameter 3 represents the MBS for CLP 
      equal to 0 and 1 traffic; parameter 4 represents the CDVT; and 
      parameter 5 represents the requested shaping rate. A non-zero value 
      in parameter 5 overrides any value in parameter 1. This result is 
      used as the PCR. Parameters 1, 2, and 3 must be non-zero. 
      Parameter 1 must be greater than or equal to parameter 2. Parameter 
      5 must either be zero (unused) or greater than or equal to parameter 
      2.
      
      When trafficDescType is 7, parameter 1 represents the PCR for CLP 
      equal to 0 and 1 traffic; parameter 2 represents the SCR for CLP 
      equal to 0 with cell discard; parameter 3 represents the MBS for 
      CLP equal to 0 traffic; parameter 4 represents the CDVT; and 
      parameter 5 represents the requested shaping rate. A non-zero value 
      in parameter 5 overrides any value in parameter 1. This result is 
      used as the PCR. Parameters 1, 2, and 3 must be non-zero. 
      Parameter 1 must be greater than or equal to parameter 2. Parameter 
      5 must either be zero (unused) or greater than or equal to parameter 
      2.
      
      When trafficDescType is 8, parameter 1 represents the PCR for CLP 
      equal to 0 and 1 traffic; parameter 2 represents the SCR for CLP 
      equal to 0 traffic with cell tagging; parameter 3 represents the MBS 
      for CLP equal to 0 traffic; parameter 4 represents the CDVT; and 
      parameter 5 represents the requested shaping rate. A non-zero value 
      in parameter 5 overrides any value in parameter 1. This result is 
      used as the PCR. Parameters 1, 2, and 3 must be non-zero. 
      Parameter 1 must be greater than or equal to parameter 2. Parameter 
      5 must either be zero (unused) or greater than or equal to parameter 
      2.
      
      Whenever it is valid for PCR to be specified, parameter 5 may also 
      be used to specify a requested shaping rate. A non-zero value in 
      parameter 5 overrides the value in parameter 1 and is used as the 
      peak cell rate in calculations of CAC and shaping rate.
      
      For trafficDescType 3 the traffic is shaped at the next rate less than 
      the PCR. 
      
      For trafficDescType 6, 7, and 8, the traffic is shaped at the highest 
      available rate which is between PCR and SCR. However, if there is 
      no available shaping rate between PCR and SCR, traffic is shaped at 
      the next rate above the PCR."
::= { mscAtmIfPnniSigVcd 387 }

mscAtmIfPnniSigVcdTdpEntry OBJECT-TYPE
   SYNTAX     MscAtmIfPnniSigVcdTdpEntry
   ACCESS     not-accessible
   STATUS     mandatory
   DESCRIPTION
     "An entry in the mscAtmIfPnniSigVcdTdpTable."
   INDEX {
      mscAtmIfIndex,
      mscAtmIfPnniIndex,
      mscAtmIfPnniSigIndex,
      mscAtmIfPnniSigVcdIndex,
      mscAtmIfPnniSigVcdTdpIndex }
::= { mscAtmIfPnniSigVcdTdpTable 1 }

MscAtmIfPnniSigVcdTdpEntry ::= SEQUENCE {
   mscAtmIfPnniSigVcdTdpIndex
      Integer32,
   mscAtmIfPnniSigVcdTdpValue
      Unsigned32 }

mscAtmIfPnniSigVcdTdpIndex OBJECT-TYPE
   SYNTAX     Integer32 (1..5)
   ACCESS     not-accessible
   STATUS     mandatory
   DESCRIPTION
     "This variable represents the mscAtmIfPnniSigVcdTdpTable
      specific index for the mscAtmIfPnniSigVcdTdpTable."
::= { mscAtmIfPnniSigVcdTdpEntry 1 }

mscAtmIfPnniSigVcdTdpValue OBJECT-TYPE
   SYNTAX     Unsigned32 (0..2147483647)
   ACCESS     read-write
   STATUS     mandatory
   DESCRIPTION
     "This variable represents an individual value for the
      mscAtmIfPnniSigVcdTdpTable."
::= { mscAtmIfPnniSigVcdTdpEntry 2 }


-- AtmIf/n Pnni RoutingControlChannel
-- AtmIf/n Vpt/m Pnni RoutingControlChannel
-- 
-- This component represents the Routing Control Channel (RCC) 
-- associated with a PNNI interface. The RCC is used to exchange 
-- routing information between nodes in a peer group.

mscAtmIfPnniRcc OBJECT IDENTIFIER ::= { mscAtmIfPnni 3 }



mscAtmIfPnniRccRowStatusTable OBJECT-TYPE
   SYNTAX     SEQUENCE OF MscAtmIfPnniRccRowStatusEntry
   ACCESS     not-accessible
   STATUS     mandatory
   DESCRIPTION
     "This entry controls the addition and deletion of 
      mscAtmIfPnniRcc components."
::= { mscAtmIfPnniRcc 1 }

mscAtmIfPnniRccRowStatusEntry OBJECT-TYPE
   SYNTAX     MscAtmIfPnniRccRowStatusEntry
   ACCESS     not-accessible
   STATUS     mandatory
   DESCRIPTION
     "A single entry in the table represents a single 
      mscAtmIfPnniRcc component."
   INDEX {
      mscAtmIfIndex,
      mscAtmIfPnniIndex,
      mscAtmIfPnniRccIndex }
::= { mscAtmIfPnniRccRowStatusTable 1 }

MscAtmIfPnniRccRowStatusEntry ::= SEQUENCE {
   mscAtmIfPnniRccRowStatus
      RowStatus,
   mscAtmIfPnniRccComponentName
      DisplayString,
   mscAtmIfPnniRccStorageType
      StorageType,
   mscAtmIfPnniRccIndex
      NonReplicated }

mscAtmIfPnniRccRowStatus OBJECT-TYPE
   SYNTAX     RowStatus 
   ACCESS     read-only
   STATUS     mandatory
   DESCRIPTION
     "This variable is used as the basis for SNMP naming of
      mscAtmIfPnniRcc components.
      These components cannot be added nor deleted."
::= { mscAtmIfPnniRccRowStatusEntry 1 }

mscAtmIfPnniRccComponentName OBJECT-TYPE
   SYNTAX     DisplayString 
   ACCESS     read-only
   STATUS     mandatory
   DESCRIPTION
     "This variable provides the component's string name for
      use with the ASCII Console Interface"
::= { mscAtmIfPnniRccRowStatusEntry 2 }

mscAtmIfPnniRccStorageType OBJECT-TYPE
   SYNTAX     StorageType 
   ACCESS     read-only
   STATUS     mandatory
   DESCRIPTION
     "This variable represents the storage type value for the
      mscAtmIfPnniRcc tables."
::= { mscAtmIfPnniRccRowStatusEntry 4 }

mscAtmIfPnniRccIndex OBJECT-TYPE
   SYNTAX     NonReplicated 
   ACCESS     not-accessible
   STATUS     mandatory
   DESCRIPTION
     "This variable represents the index for the mscAtmIfPnniRcc tables."
::= { mscAtmIfPnniRccRowStatusEntry 10 }

mscAtmIfPnniRccProvTable OBJECT-TYPE
   SYNTAX     SEQUENCE OF MscAtmIfPnniRccProvEntry
   ACCESS     not-accessible
   STATUS     mandatory
   DESCRIPTION
     "This group contains the generic provisionable attributes of an Rcc 
      component."
::= { mscAtmIfPnniRcc 10 }

mscAtmIfPnniRccProvEntry OBJECT-TYPE
   SYNTAX     MscAtmIfPnniRccProvEntry
   ACCESS     not-accessible
   STATUS     mandatory
   DESCRIPTION
     "An entry in the mscAtmIfPnniRccProvTable."
   INDEX {
      mscAtmIfIndex,
      mscAtmIfPnniIndex,
      mscAtmIfPnniRccIndex }
::= { mscAtmIfPnniRccProvTable 1 }

MscAtmIfPnniRccProvEntry ::= SEQUENCE {
   mscAtmIfPnniRccVci
      Unsigned32 }

mscAtmIfPnniRccVci OBJECT-TYPE
   SYNTAX     Unsigned32 (0..65535)
   ACCESS     read-write
   STATUS     mandatory
   DESCRIPTION
     "This attribute specifies the VCI for the Routing Control Channel 
      (RCC). It is not recommended that the value be changed from the 
      default of 18 unless absolutely necessary. If a different VCI is 
      specified, ensure that the RCC at the far end is provisioned to use 
      the same VCI, otherwise the RCC will not come up."
   DEFVAL     { 18 }
::= { mscAtmIfPnniRccProvEntry 1 }

mscAtmIfPnniRccHlParmsTable OBJECT-TYPE
   SYNTAX     SEQUENCE OF MscAtmIfPnniRccHlParmsEntry
   ACCESS     not-accessible
   STATUS     mandatory
   DESCRIPTION
     "This group contains the provisionable Hello protocol parameters for 
      an Rcc component."
::= { mscAtmIfPnniRcc 11 }

mscAtmIfPnniRccHlParmsEntry OBJECT-TYPE
   SYNTAX     MscAtmIfPnniRccHlParmsEntry
   ACCESS     not-accessible
   STATUS     mandatory
   DESCRIPTION
     "An entry in the mscAtmIfPnniRccHlParmsTable."
   INDEX {
      mscAtmIfIndex,
      mscAtmIfPnniIndex,
      mscAtmIfPnniRccIndex }
::= { mscAtmIfPnniRccHlParmsTable 1 }

MscAtmIfPnniRccHlParmsEntry ::= SEQUENCE {
   mscAtmIfPnniRccHelloHoldDown
      FixedPoint1,
   mscAtmIfPnniRccHelloInterval
      Unsigned32,
   mscAtmIfPnniRccHelloInactivityFactor
      Unsigned32 }

mscAtmIfPnniRccHelloHoldDown OBJECT-TYPE
   SYNTAX     FixedPoint1 (0..655350)
   ACCESS     read-write
   STATUS     mandatory
   DESCRIPTION
     "This attribute is used to limit the rate at which this node sends out 
      Hello packets. Specifically, it specifies the minimum time between 
      successive Hellos.
      
      A value of 0 specifies that the value provisioned for the 
      helloHoldDown attribute of the ARtg Pnni component should be 
      used."
   DEFVAL     { 0 }
::= { mscAtmIfPnniRccHlParmsEntry 1 }

mscAtmIfPnniRccHelloInterval OBJECT-TYPE
   SYNTAX     Unsigned32 (0..65535)
   ACCESS     read-write
   STATUS     mandatory
   DESCRIPTION
     "This attribute specifies the duration of the Hello Timer. Every 
      helloInterval seconds, this node will send out a Hello packet to the 
      neighbor node, subject to the helloHoldDown timer having expired 
      at least once since the last Hello packet was sent.
      
      A value of 0 specifies that the value provisioned for the 
      helloInterval attribute of the ARtg Pnni component should be used."
   DEFVAL     { 0 }
::= { mscAtmIfPnniRccHlParmsEntry 2 }

mscAtmIfPnniRccHelloInactivityFactor OBJECT-TYPE
   SYNTAX     Unsigned32 (0..65535)
   ACCESS     read-write
   STATUS     mandatory
   DESCRIPTION
     "This attribute specifies the number of Hello intervals allowed to 
      pass without receiving a Hello from the neighbor node, before an 
      attempt is made to re-stage. The hello inactivity timer is enabled in 
      the oneWayInside, twoWayInside, oneWayOutside, 
      twoWayOutside and commonOutside hello states (see the 
      helloState attribute on the Rcc component for a description of these 
      states). Note that the value for the Hello interval used in the 
      calculation is the one specified in the Hello packet from the 
      neighbor node.
      
      A value of 0 specifies that the value provisioned for the 
      helloInactivityFactor attribute of the ARtg Pnni component should 
      be used.
      DESCRIPTION"
   DEFVAL     { 0 }
::= { mscAtmIfPnniRccHlParmsEntry 3 }

mscAtmIfPnniRccStateTable OBJECT-TYPE
   SYNTAX     SEQUENCE OF MscAtmIfPnniRccStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscAtmIfPnniRcc 12 }

mscAtmIfPnniRccStateEntry OBJECT-TYPE
   SYNTAX     MscAtmIfPnniRccStateEntry
   ACCESS     not-accessible
   STATUS     mandatory
   DESCRIPTION
     "An entry in the mscAtmIfPnniRccStateTable."
   INDEX {
      mscAtmIfIndex,
      mscAtmIfPnniIndex,
      mscAtmIfPnniRccIndex }
::= { mscAtmIfPnniRccStateTable 1 }

MscAtmIfPnniRccStateEntry ::= SEQUENCE {
   mscAtmIfPnniRccAdminState
      INTEGER,
   mscAtmIfPnniRccOperationalState
      INTEGER,
   mscAtmIfPnniRccUsageState
      INTEGER }

mscAtmIfPnniRccAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscAtmIfPnniRccStateEntry 1 }

mscAtmIfPnniRccOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscAtmIfPnniRccStateEntry 2 }

mscAtmIfPnniRccUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscAtmIfPnniRccStateEntry 3 }

mscAtmIfPnniRccOperTable OBJECT-TYPE
   SYNTAX     SEQUENCE OF MscAtmIfPnniRccOperEntry
   ACCESS     not-accessible
   STATUS     mandatory
   DESCRIPTION
     "This group contains the operational attributes for an Rcc 
      component."
::= { mscAtmIfPnniRcc 13 }

mscAtmIfPnniRccOperEntry OBJECT-TYPE
   SYNTAX     MscAtmIfPnniRccOperEntry
   ACCESS     not-accessible
   STATUS     mandatory
   DESCRIPTION
     "An entry in the mscAtmIfPnniRccOperTable."
   INDEX {
      mscAtmIfIndex,
      mscAtmIfPnniIndex,
      mscAtmIfPnniRccIndex }
::= { mscAtmIfPnniRccOperTable 1 }

MscAtmIfPnniRccOperEntry ::= SEQUENCE {
   mscAtmIfPnniRccType
      INTEGER,
   mscAtmIfPnniRccNegotiatedVersion
      INTEGER,
   mscAtmIfPnniRccHelloState
      INTEGER,
   mscAtmIfPnniRccRemoteNodeId
      HexString,
   mscAtmIfPnniRccRemotePortId
      Unsigned32 }

mscAtmIfPnniRccType OBJECT-TYPE
   SYNTAX     INTEGER  {
                 unknown(0),
                 lowestLevelHorizLink(1),
                 lowestLevelOutsideLink(2),
                 horizontalLinkToLGN(3),
                 uplink(4) }
   ACCESS     read-only
   STATUS     mandatory
   DESCRIPTION
     "This attribute indicates the role of this link in the PNNI hierarchy.
      The following values are possible:
      
      unknown: the Hello protocol has not yet determined the role of the 
      link.
      
      lowestLevelHorizLink: the link is a horizontal link between two 
      lowest level nodes.
      
      lowestLevelOutsideLink: the link is an outside link between two 
      border nodes.
      
      horizontalLinkToLgn: the link is a horizontal link to a Logical 
      Group Node (LGN).
      
      uplink: the link is a uplink to a higher level LGN."
::= { mscAtmIfPnniRccOperEntry 1 }

mscAtmIfPnniRccNegotiatedVersion OBJECT-TYPE
   SYNTAX     INTEGER  {
                 unsupported(0),
                 version1point0(1) }
   ACCESS     read-only
   STATUS     mandatory
   DESCRIPTION
     "This attribute indicates the PNNI version negotiated with the 
      neighbor node."
::= { mscAtmIfPnniRccOperEntry 2 }

mscAtmIfPnniRccHelloState OBJECT-TYPE
   SYNTAX     INTEGER  {
                 notApplicable(0),
                 down(1),
                 attempt(2),
                 oneWayInside(3),
                 twoWayInside(4),
                 oneWayOutside(5),
                 twoWayOutside(6),
                 commonOutside(7) }
   ACCESS     read-only
   STATUS     mandatory
   DESCRIPTION
     "This attribute indicates the state of the Hello protocol exchange over 
      this link. The following are the possible values for this attribute:
      
      down: the link is down; no PNNI routing packets will be sent over 
      or received over such a link. This is the initial state of the Hello 
      Finite State Machine, and can also be reached when lower-level 
      protocols have indicated that the link is not usable.
      
      attempt: no Hello packets or Hello packets, with mismatch 
      information, have been received recently from the neighbor. 
      Attempts are made to contact the neighbor node by sending out 
      Hello packets every helloInterval seconds.
      
      oneWayInside: Hello packets have been recently received from the 
      neighbor and it has been established that both nodes are members of 
      the same peer group, but the remote node ID and remote port ID in 
      the neighbor's Hello packets were set to zero. A Hello packet is sent 
      to the neighbor and the Hello timer is restarted.
      
      twoWayInside: Bidirectional communication over this link between 
      this node and the neighbor node has been achieved.
      
      oneWayOutside: Hello packets have been recently received from 
      the neighbor and it has been established that both nodes are 
      members of a different peer group, but the remote node ID and 
      remote port ID in the neighbor's Hello packets were set to zero.
      
      twoWayOutside: Hellos have recently been received from the 
      neighbor indicating that the neighbor node belongs to a different 
      peer group. The correct remote node ID and remote port ID fields 
      were included in the Hello packet, but the nodal hierarchy list did 
      not include any common peer group. This state can also be reached 
      if a hierarchy mismatch occurs while in the commonOutside state.
      
      commonOutside: A common level of the routing hierarchy has been 
      found, in addition to achieving full bi-directional communication 
      between the two nodes."
::= { mscAtmIfPnniRccOperEntry 3 }

mscAtmIfPnniRccRemoteNodeId OBJECT-TYPE
   SYNTAX     HexString (SIZE (22))
   ACCESS     read-only
   STATUS     mandatory
   DESCRIPTION
     "This attribute indicates the neighbor node's node id."
::= { mscAtmIfPnniRccOperEntry 4 }

mscAtmIfPnniRccRemotePortId OBJECT-TYPE
   SYNTAX     Unsigned32 (0..4294967295)
   ACCESS     read-only
   STATUS     mandatory
   DESCRIPTION
     "This attribute indicates the neighbor node's port id."
::= { mscAtmIfPnniRccOperEntry 5 }

mscAtmIfPnniRccStatsTable OBJECT-TYPE
   SYNTAX     SEQUENCE OF MscAtmIfPnniRccStatsEntry
   ACCESS     not-accessible
   STATUS     mandatory
   DESCRIPTION
     "This group contains the statistical attributes for an Rcc component."
::= { mscAtmIfPnniRcc 14 }

mscAtmIfPnniRccStatsEntry OBJECT-TYPE
   SYNTAX     MscAtmIfPnniRccStatsEntry
   ACCESS     not-accessible
   STATUS     mandatory
   DESCRIPTION
     "An entry in the mscAtmIfPnniRccStatsTable."
   INDEX {
      mscAtmIfIndex,
      mscAtmIfPnniIndex,
      mscAtmIfPnniRccIndex }
::= { mscAtmIfPnniRccStatsTable 1 }

MscAtmIfPnniRccStatsEntry ::= SEQUENCE {
   mscAtmIfPnniRccHelloPacketsRx
      Counter32,
   mscAtmIfPnniRccHelloPacketsTx
      Counter32,
   mscAtmIfPnniRccMismatchedHelloPacketsRx
      Counter32,
   mscAtmIfPnniRccBadHelloPacketsRx
      Counter32 }

mscAtmIfPnniRccHelloPacketsRx OBJECT-TYPE
   SYNTAX     Counter32 
   ACCESS     read-only
   STATUS     mandatory
   DESCRIPTION
     "This attribute counts the total number of Hello packets received 
      across this RCC, including bad and mismatched Hello packets. The 
      counter wraps when it exceeds the maximum value."
::= { mscAtmIfPnniRccStatsEntry 1 }

mscAtmIfPnniRccHelloPacketsTx OBJECT-TYPE
   SYNTAX     Counter32 
   ACCESS     read-only
   STATUS     mandatory
   DESCRIPTION
     "This attribute counts the total number of Hello packets transmitted 
      across this RCC. The counter wraps when it exceeds the maximum 
      value."
::= { mscAtmIfPnniRccStatsEntry 2 }

mscAtmIfPnniRccMismatchedHelloPacketsRx OBJECT-TYPE
   SYNTAX     Counter32 
   ACCESS     read-only
   STATUS     mandatory
   DESCRIPTION
     "This attribute counts the total number of mismatched Hello packets 
      received over this RCC. The counter wraps when it exceeds the 
      maximum value."
::= { mscAtmIfPnniRccStatsEntry 3 }

mscAtmIfPnniRccBadHelloPacketsRx OBJECT-TYPE
   SYNTAX     Counter32 
   ACCESS     read-only
   STATUS     mandatory
   DESCRIPTION
     "This attribute counts the total number of bad Hello packets received 
      over this RCC. The counter wraps when it exceeds the maximum 
      value."
::= { mscAtmIfPnniRccStatsEntry 4 }


-- AtmIf/n Uni Sig VirtualChannelDescriptor
-- AtmIf/n Uni Ilmi VirtualChannelDescriptor
-- AtmIf/n Iisp Sig VirtualChannelDescriptor
-- AtmIf/n Pnni Sig VirtualChannelDescriptor
-- AtmIf/n Pnni Rcc VirtualChannelDescriptor
-- AtmIf/n Vpt/m Uni Sig VirtualChannelDescriptor
-- AtmIf/n Vpt/m Iisp Sig VirtualChannelDescriptor
-- AtmIf/n Vpt/m Pnni Sig VirtualChannelDescriptor
-- AtmIf/n Vpt/m Pnni Rcc VirtualChannelDescriptor
-- 
-- This component contains the provisionable traffic parameters for a 
-- control channel (Sig, Ilmi or Rcc component).

mscAtmIfPnniRccVcd OBJECT IDENTIFIER ::= { mscAtmIfPnniRcc 2 }



mscAtmIfPnniRccVcdRowStatusTable OBJECT-TYPE
   SYNTAX     SEQUENCE OF MscAtmIfPnniRccVcdRowStatusEntry
   ACCESS     not-accessible
   STATUS     mandatory
   DESCRIPTION
     "This entry controls the addition and deletion of 
      mscAtmIfPnniRccVcd components."
::= { mscAtmIfPnniRccVcd 1 }

mscAtmIfPnniRccVcdRowStatusEntry OBJECT-TYPE
   SYNTAX     MscAtmIfPnniRccVcdRowStatusEntry
   ACCESS     not-accessible
   STATUS     mandatory
   DESCRIPTION
     "A single entry in the table represents a single 
      mscAtmIfPnniRccVcd component."
   INDEX {
      mscAtmIfIndex,
      mscAtmIfPnniIndex,
      mscAtmIfPnniRccIndex,
      mscAtmIfPnniRccVcdIndex }
::= { mscAtmIfPnniRccVcdRowStatusTable 1 }

MscAtmIfPnniRccVcdRowStatusEntry ::= SEQUENCE {
   mscAtmIfPnniRccVcdRowStatus
      RowStatus,
   mscAtmIfPnniRccVcdComponentName
      DisplayString,
   mscAtmIfPnniRccVcdStorageType
      StorageType,
   mscAtmIfPnniRccVcdIndex
      NonReplicated }

mscAtmIfPnniRccVcdRowStatus OBJECT-TYPE
   SYNTAX     RowStatus 
   ACCESS     read-write
   STATUS     mandatory
   DESCRIPTION
     "This variable is used as the basis for SNMP naming of
      mscAtmIfPnniRccVcd components.
      These components can be added and deleted."
::= { mscAtmIfPnniRccVcdRowStatusEntry 1 }

mscAtmIfPnniRccVcdComponentName OBJECT-TYPE
   SYNTAX     DisplayString 
   ACCESS     read-only
   STATUS     mandatory
   DESCRIPTION
     "This variable provides the component's string name for
      use with the ASCII Console Interface"
::= { mscAtmIfPnniRccVcdRowStatusEntry 2 }

mscAtmIfPnniRccVcdStorageType OBJECT-TYPE
   SYNTAX     StorageType 
   ACCESS     read-only
   STATUS     mandatory
   DESCRIPTION
     "This variable represents the storage type value for the
      mscAtmIfPnniRccVcd tables."
::= { mscAtmIfPnniRccVcdRowStatusEntry 4 }

mscAtmIfPnniRccVcdIndex OBJECT-TYPE
   SYNTAX     NonReplicated 
   ACCESS     not-accessible
   STATUS     mandatory
   DESCRIPTION
     "This variable represents the index for the mscAtmIfPnniRccVcd tables."
::= { mscAtmIfPnniRccVcdRowStatusEntry 10 }

mscAtmIfPnniRccVcdProvTable OBJECT-TYPE
   SYNTAX     SEQUENCE OF MscAtmIfPnniRccVcdProvEntry
   ACCESS     not-accessible
   STATUS     mandatory
   DESCRIPTION
     "This group contains the provisionable traffic attributes for a control 
      channel."
::= { mscAtmIfPnniRccVcd 10 }

mscAtmIfPnniRccVcdProvEntry OBJECT-TYPE
   SYNTAX     MscAtmIfPnniRccVcdProvEntry
   ACCESS     not-accessible
   STATUS     mandatory
   DESCRIPTION
     "An entry in the mscAtmIfPnniRccVcdProvTable."
   INDEX {
      mscAtmIfIndex,
      mscAtmIfPnniIndex,
      mscAtmIfPnniRccIndex,
      mscAtmIfPnniRccVcdIndex }
::= { mscAtmIfPnniRccVcdProvTable 1 }

MscAtmIfPnniRccVcdProvEntry ::= SEQUENCE {
   mscAtmIfPnniRccVcdTrafficDescType
      INTEGER,
   mscAtmIfPnniRccVcdAtmServiceCategory
      INTEGER,
   mscAtmIfPnniRccVcdWeight
      Unsigned32,
   mscAtmIfPnniRccVcdQosClass
      INTEGER,
   mscAtmIfPnniRccVcdTrafficShaping
      INTEGER,
   mscAtmIfPnniRccVcdUnshapedTransmitQueueing
      INTEGER,
   mscAtmIfPnniRccVcdUsageParameterControl
      INTEGER }

mscAtmIfPnniRccVcdTrafficDescType OBJECT-TYPE
   SYNTAX     INTEGER  {
                 n3(3),
                 n6(6),
                 n7(7),
                 n8(8) }
   ACCESS     read-write
   STATUS     mandatory
   DESCRIPTION
     "This attribute specifies the type of traffic management which is 
      applied to both the transmit and receive direction of this connection 
      as defined in the ATM Forum. The trafficDescType determines the 
      number and meaning of the parameters in the trafficDescParm 
      attribute."
   DEFVAL     { n6 }
::= { mscAtmIfPnniRccVcdProvEntry 1 }

mscAtmIfPnniRccVcdAtmServiceCategory OBJECT-TYPE
   SYNTAX     INTEGER  {
                 unspecifiedBitRate(0),
                 constantBitRate(1),
                 rtVariableBitRate(2),
                 nrtVariableBitRate(3) }
   ACCESS     read-write
   STATUS     mandatory
   DESCRIPTION
     "This attribute specifies the ATM service category for both directions 
      of the connection. 
      
      The constantBitRate service category is intended for real time 
      applications, that is those requiring tightly constrained delay and 
      delay variation, as would be appropriate for voice and video 
      applications. The consistent availability of a fixed quantity of 
      bandwidth is considered appropriate for CBR service. Cells which 
      are delayed beyond the value specified by CellTransfer Delay are 
      assumed to be of significantly reduce value to the application.
      
      The rtVariableBitRate service category is intended for real time 
      applications, that is those requiring tightly constrained delay and 
      delay variation, as would be appropriate for voice and video 
      applications. Sources are expected to transmit at a rate which varies 
      with time. Equivalently, the source can be described as 'bursty'. 
      Cells which are delayed beyond the value specified by CTD are 
      assumed to be of significantly reduced value to the application. Real 
      time VBR service may support statistical multiplexing of real time 
      sources.
      
      The nrtVariableBitRate service category is intended for non-real 
      time applications which have bursty traffic characteristics and which 
      can be characterized in terms of a PCR, SCR, and MBS. For those 
      cells which are transferred within the traffic contract, the application 
      expects a low cell loss ratio. For all connections, it expects a bound 
      on the mean cell transfer delay. Non-real time VBR service may 
      support statistical multiplexing of connections.
      
      The unspecifiedBitRate service is intended for non-real time 
      applications; that is, those not requiring tightly constrained delay 
      and delay variation. UBR sources are expected to be bursty. UBR 
      service supports a high degree of statistical multiplexing among 
      sources. UBR service does not specify traffic related service 
      guarantees. No numerical commitments are made with respect to 
      the cell loss ratio experienced by a UBR connection, or as to the 
      cell transfer delay experienced by cells on the connection."
   DEFVAL     { rtVariableBitRate }
::= { mscAtmIfPnniRccVcdProvEntry 3 }

mscAtmIfPnniRccVcdWeight OBJECT-TYPE
   SYNTAX     Unsigned32 (0 | 1..4095 | 65535)
   ACCESS     read-write
   STATUS     mandatory
   DESCRIPTION
     "This attribute specifies an override for the weight of this unshaped 
      connection. This attribute is ignored for shaped connections, for 
      ABR connections, for connections on a CQC-based ATM FP and 
      basic VPTs. 
      
      When the value is set to sameAsCa, the weight is determined by the 
      weight policy attribute under the CA service category component 
      for all but standard VPT VCCs. For standard VPT VCCs, the 
      weight is determined by the VCC's service category, when the value 
      is set to sameAsCa.
      
      When this attribute is set to a value from 1 to 4095, that value is 
      used for the weight policy of this connection relative to other 
      connections. For all but standard VPT VCCs, weight policy 
      determines the proportion of transit cell opportunities which are 
      allocated to this connection, compared to other connections in the 
      same service category. For standard VPT VCCs, weight policy 
      determines the proportion of transmit cell opportunities which are 
      allocated to this connection, compared to other connections 
      associated with the VPT.
      
      When the value is set to upToQueueLimit, the weight policy is 
      limited only by the txQueueLimit.

      VALUES (

      0 = upToQueueLimit

      65535 = sameAsCa

      )"
   DEFVAL     { 65535 }
::= { mscAtmIfPnniRccVcdProvEntry 4 }

mscAtmIfPnniRccVcdQosClass OBJECT-TYPE
   SYNTAX     INTEGER  {
                 n0(0),
                 n1(1),
                 n2(2),
                 n3(3),
                 n4(4) }
   ACCESS     read-write
   STATUS     mandatory
   DESCRIPTION
     "This attribute specifies the quality of service for both the forward 
      and backward direction for this connection.
      
      Class 1 supports a QOS that meets Service Class A performance 
      requirements (Circuit emulation, constant bit rate video).
      
      Class 2 supports a QOS that meets Service Class B performance 
      requirements (Variable bit rate audio and video).
      
      Class 3 supports a QOS that meets Service Class C performance 
      requirements (Connection-Oriented Data Transfer).
      
      Class 4 supports a QOS that meets Service Class D performance 
      requirements (Connectionless Data Transfer).
      
      Class 0 is the unspecified bit rate QOS class; no objective is 
      specified for the performance parameters."
   DEFVAL     { n2 }
::= { mscAtmIfPnniRccVcdProvEntry 21 }

mscAtmIfPnniRccVcdTrafficShaping OBJECT-TYPE
   SYNTAX     INTEGER  {
                 disabled(1),
                 sameAsCa(2) }
   ACCESS     read-write
   STATUS     mandatory
   DESCRIPTION
     "This attribute specifies whether this connection uses traffic shaping 
      when transmitting traffic to the ATM interface.
      
      When sameAsCa is selected, traffic shaping for this connection is 
      based on the trafficShaping attribute of the connection's service 
      category component under the AtmIf CA. If the service category has 
      traffic shaping enabled, then traffic shaping is enabled for the 
      connection. Note that enabling traffic shaping may have no effect 
      under certain cases. These cases are listed in the description of the 
      trafficShaping operational attribute, which is under the Vcc Tm and 
      Vpc Tm components.
      
      When disabled is selected, traffic shaping for this connection is 
      disabled."
   DEFVAL     { disabled }
::= { mscAtmIfPnniRccVcdProvEntry 50 }

mscAtmIfPnniRccVcdUnshapedTransmitQueueing OBJECT-TYPE
   SYNTAX     INTEGER  {
                 common(1),
                 sameAsCa(3) }
   ACCESS     read-write
   STATUS     mandatory
   DESCRIPTION
     "This attribute only applies when this connection is unshaped. This 
      attribute specifies the transmit queueing method for this connection 
      if it is unshaped. Refer to the unshapedTransmitQueueing attribute 
      under the AtmIf CA service category subcomponent for more details 
      on the meaning of this attribute. 
      
      When this attribute is set to sameAsCa, the transmit queueing 
      method for the connection is based on the 
      unshapedTransmitQueueing attribute of the connection's service 
      category component under the ConnectionAdministrator. 
      
      When this attribute is set to common, transmit traffic on this 
      unshaped connection is destined for the common queue. 
      
      The value sameAsInterface is for migration from previous software 
      releases, but should no longer be used"
   DEFVAL     { sameAsCa }
::= { mscAtmIfPnniRccVcdProvEntry 60 }

mscAtmIfPnniRccVcdUsageParameterControl OBJECT-TYPE
   SYNTAX     INTEGER  {
                 disabled(1),
                 sameAsCa(2) }
   ACCESS     read-write
   STATUS     mandatory
   DESCRIPTION
     "This attribute specifies whether this connection enforces usage 
      parameter control when receiving traffic from the ATM interface.
      
      When sameAsCa is selected, UPC for the connection is based on 
      the usageParameterControl attribute of the connection's service 
      category component under the ConnectionAdministrator. If the 
      service category has UPC enabled, then UPC is enabled for the 
      connection. Note that enabling UPC may have no effect under 
      certain cases. These cases are listed in the description of the 
      usageParameterControl operational attribute, which is under the 
      Vcc Tm or Vpc Tm component.
      
      When disabled is selected, UPC for this connection is disabled.
      
      The value sameAsInterface is for migration from previous software 
      releases, but should no longer be used"
   DEFVAL     { disabled }
::= { mscAtmIfPnniRccVcdProvEntry 70 }

mscAtmIfPnniRccVcdTdpTable OBJECT-TYPE
   SYNTAX     SEQUENCE OF MscAtmIfPnniRccVcdTdpEntry
   ACCESS     not-accessible
   STATUS     mandatory
   DESCRIPTION
     "This attribute is a vector of five traffic parameters whose meanings 
      are defined by the trafficDescType attribute. The values of peak cell 
      rate (PCR), sustained cell rate (SCR) and requested shaping rate are 
      expressed in cell/s. Maximum burst size (MBS) is expressed in 
      cells. CDVT is expressed in microseconds. The values of PCR, 
      SCR, MBS and CDVT are used for connection admission control 
      (CAC). The value of CDVT is only used for connections where the 
      atmServiceCategory is constantBitRate. For all other values of 
      atmServiceCategory, CDVT is ignored. The values of PCR, SCR 
      and requested shaping rate are used to determine the actual shaping 
      rate where traffic shaping is enabled.
      
      When trafficDescType is 3, parameter 1 represents the PCR for CLP 
      equal to 0 and 1 traffic; parameter 4 represents the CDVT; and 
      parameter 5 represents the requested shaping rate. A non-zero value 
      in parameter 5 overrides any value in parameter 1. This result is 
      used as the PCR. Parameter 1 must be non-zero. Parameters 2 and 3 
      must be zero.
      
      When trafficDescType is 6, parameter 1 represents the PCR for CLP 
      equal to 0 and 1 traffic; parameter 2 represents the SCR for CLP 
      equal to 0 and 1 traffic; parameter 3 represents the MBS for CLP 
      equal to 0 and 1 traffic; parameter 4 represents the CDVT; and 
      parameter 5 represents the requested shaping rate. A non-zero value 
      in parameter 5 overrides any value in parameter 1. This result is 
      used as the PCR. Parameters 1, 2, and 3 must be non-zero. 
      Parameter 1 must be greater than or equal to parameter 2. Parameter 
      5 must either be zero (unused) or greater than or equal to parameter 
      2.
      
      When trafficDescType is 7, parameter 1 represents the PCR for CLP 
      equal to 0 and 1 traffic; parameter 2 represents the SCR for CLP 
      equal to 0 with cell discard; parameter 3 represents the MBS for 
      CLP equal to 0 traffic; parameter 4 represents the CDVT; and 
      parameter 5 represents the requested shaping rate. A non-zero value 
      in parameter 5 overrides any value in parameter 1. This result is 
      used as the PCR. Parameters 1, 2, and 3 must be non-zero. 
      Parameter 1 must be greater than or equal to parameter 2. Parameter 
      5 must either be zero (unused) or greater than or equal to parameter 
      2.
      
      When trafficDescType is 8, parameter 1 represents the PCR for CLP 
      equal to 0 and 1 traffic; parameter 2 represents the SCR for CLP 
      equal to 0 traffic with cell tagging; parameter 3 represents the MBS 
      for CLP equal to 0 traffic; parameter 4 represents the CDVT; and 
      parameter 5 represents the requested shaping rate. A non-zero value 
      in parameter 5 overrides any value in parameter 1. This result is 
      used as the PCR. Parameters 1, 2, and 3 must be non-zero. 
      Parameter 1 must be greater than or equal to parameter 2. Parameter 
      5 must either be zero (unused) or greater than or equal to parameter 
      2.
      
      Whenever it is valid for PCR to be specified, parameter 5 may also 
      be used to specify a requested shaping rate. A non-zero value in 
      parameter 5 overrides the value in parameter 1 and is used as the 
      peak cell rate in calculations of CAC and shaping rate.
      
      For trafficDescType 3 the traffic is shaped at the next rate less than 
      the PCR. 
      
      For trafficDescType 6, 7, and 8, the traffic is shaped at the highest 
      available rate which is between PCR and SCR. However, if there is 
      no available shaping rate between PCR and SCR, traffic is shaped at 
      the next rate above the PCR."
::= { mscAtmIfPnniRccVcd 387 }

mscAtmIfPnniRccVcdTdpEntry OBJECT-TYPE
   SYNTAX     MscAtmIfPnniRccVcdTdpEntry
   ACCESS     not-accessible
   STATUS     mandatory
   DESCRIPTION
     "An entry in the mscAtmIfPnniRccVcdTdpTable."
   INDEX {
      mscAtmIfIndex,
      mscAtmIfPnniIndex,
      mscAtmIfPnniRccIndex,
      mscAtmIfPnniRccVcdIndex,
      mscAtmIfPnniRccVcdTdpIndex }
::= { mscAtmIfPnniRccVcdTdpTable 1 }

MscAtmIfPnniRccVcdTdpEntry ::= SEQUENCE {
   mscAtmIfPnniRccVcdTdpIndex
      Integer32,
   mscAtmIfPnniRccVcdTdpValue
      Unsigned32 }

mscAtmIfPnniRccVcdTdpIndex OBJECT-TYPE
   SYNTAX     Integer32 (1..5)
   ACCESS     not-accessible
   STATUS     mandatory
   DESCRIPTION
     "This variable represents the mscAtmIfPnniRccVcdTdpTable
      specific index for the mscAtmIfPnniRccVcdTdpTable."
::= { mscAtmIfPnniRccVcdTdpEntry 1 }

mscAtmIfPnniRccVcdTdpValue OBJECT-TYPE
   SYNTAX     Unsigned32 (0..2147483647)
   ACCESS     read-write
   STATUS     mandatory
   DESCRIPTION
     "This variable represents an individual value for the
      mscAtmIfPnniRccVcdTdpTable."
::= { mscAtmIfPnniRccVcdTdpEntry 2 }


-- AtmIf/n Iisp Address/address,type
-- AtmIf/n Uni Address/address,type
-- AtmIf/n Pnni Address/address,type
-- AtmIf/n Vpt/m Iisp Address/address,type
-- AtmIf/n Vpt/m Uni Address/address,type
-- AtmIf/n Vpt/m Pnni Address/address,type
-- 
-- This component represents an address (dynamic or static) 
-- associated with the interface. The index is a string of 1 to 40 hex 
-- digits or a single wildcard ('?'), and a type. The type identifies 
-- whether the Address component is for a primary, alternate, 
-- registered, or default address. 
-- 
-- The types primary and alternate are used for provisioned addresses. 
-- The type registered is used for dynamic addresses registered 
-- through ILMI. The type default is used for Soft PVP and Soft PVC 
-- addresses.Virtual interfaces do not have addresses of 
-- type default.
-- 
-- The wildcard is only valid for provisioned addresses. If the address 
-- is a single wildcard, then that indicates that the interface supports 
-- all addresses. If there is no better match, then this interface may be 
-- chosen in the routing. If there is more than one interface with a 
-- single wildcard static address, then the choice is driven through a 
-- round robin algorithm. 
-- 
-- The round robin algorithm tries the primary routes and then the 
-- alternate routes if none of the primary routes succeed.
-- If this node participates in a PNNI hierarchy, then a PnniInfo 
-- subcomponent can be provisioned under the AtmAddress 
-- component to specify the level to which this address will be 
-- advertised.

mscAtmIfPnniAddr OBJECT IDENTIFIER ::= { mscAtmIfPnni 4 }



mscAtmIfPnniAddrRowStatusTable OBJECT-TYPE
   SYNTAX     SEQUENCE OF MscAtmIfPnniAddrRowStatusEntry
   ACCESS     not-accessible
   STATUS     mandatory
   DESCRIPTION
     "This entry controls the addition and deletion of 
      mscAtmIfPnniAddr components."
::= { mscAtmIfPnniAddr 1 }

mscAtmIfPnniAddrRowStatusEntry OBJECT-TYPE
   SYNTAX     MscAtmIfPnniAddrRowStatusEntry
   ACCESS     not-accessible
   STATUS     mandatory
   DESCRIPTION
     "A single entry in the table represents a single 
      mscAtmIfPnniAddr component."
   INDEX {
      mscAtmIfIndex,
      mscAtmIfPnniIndex,
      mscAtmIfPnniAddrAddressIndex,
      mscAtmIfPnniAddrAddressTypeIndex }
::= { mscAtmIfPnniAddrRowStatusTable 1 }

MscAtmIfPnniAddrRowStatusEntry ::= SEQUENCE {
   mscAtmIfPnniAddrRowStatus
      RowStatus,
   mscAtmIfPnniAddrComponentName
      DisplayString,
   mscAtmIfPnniAddrStorageType
      StorageType,
   mscAtmIfPnniAddrAddressIndex
      AsciiStringIndex,
   mscAtmIfPnniAddrAddressTypeIndex
      INTEGER }

mscAtmIfPnniAddrRowStatus OBJECT-TYPE
   SYNTAX     RowStatus 
   ACCESS     read-write
   STATUS     mandatory
   DESCRIPTION
     "This variable is used as the basis for SNMP naming of
      mscAtmIfPnniAddr components.
      These components can be added and deleted."
::= { mscAtmIfPnniAddrRowStatusEntry 1 }

mscAtmIfPnniAddrComponentName OBJECT-TYPE
   SYNTAX     DisplayString 
   ACCESS     read-only
   STATUS     mandatory
   DESCRIPTION
     "This variable provides the component's string name for
      use with the ASCII Console Interface"
::= { mscAtmIfPnniAddrRowStatusEntry 2 }

mscAtmIfPnniAddrStorageType OBJECT-TYPE
   SYNTAX     StorageType 
   ACCESS     read-only
   STATUS     mandatory
   DESCRIPTION
     "This variable represents the storage type value for the
      mscAtmIfPnniAddr tables."
::= { mscAtmIfPnniAddrRowStatusEntry 4 }

mscAtmIfPnniAddrAddressIndex OBJECT-TYPE
   SYNTAX     AsciiStringIndex (SIZE (1..40))
   ACCESS     not-accessible
   STATUS     mandatory
   DESCRIPTION
     "This variable represents an index for the mscAtmIfPnniAddr tables."
::= { mscAtmIfPnniAddrRowStatusEntry 10 }

mscAtmIfPnniAddrAddressTypeIndex OBJECT-TYPE
   SYNTAX     INTEGER  {
                 primary(0),
                 alternate(1),
                 registered(2),
                 default(3) }
   ACCESS     not-accessible
   STATUS     mandatory
   DESCRIPTION
     "This variable represents an index for the mscAtmIfPnniAddr tables."
::= { mscAtmIfPnniAddrRowStatusEntry 11 }

mscAtmIfPnniAddrOperTable OBJECT-TYPE
   SYNTAX     SEQUENCE OF MscAtmIfPnniAddrOperEntry
   ACCESS     not-accessible
   STATUS     mandatory
   DESCRIPTION
     "This attribute group contains the operational attributes for the 
      Address component."
::= { mscAtmIfPnniAddr 10 }

mscAtmIfPnniAddrOperEntry OBJECT-TYPE
   SYNTAX     MscAtmIfPnniAddrOperEntry
   ACCESS     not-accessible
   STATUS     mandatory
   DESCRIPTION
     "An entry in the mscAtmIfPnniAddrOperTable."
   INDEX {
      mscAtmIfIndex,
      mscAtmIfPnniIndex,
      mscAtmIfPnniAddrAddressIndex,
      mscAtmIfPnniAddrAddressTypeIndex }
::= { mscAtmIfPnniAddrOperTable 1 }

MscAtmIfPnniAddrOperEntry ::= SEQUENCE {
   mscAtmIfPnniAddrScope
      INTEGER,
   mscAtmIfPnniAddrReachability
      INTEGER }

mscAtmIfPnniAddrScope OBJECT-TYPE
   SYNTAX     INTEGER (-1..104)
   ACCESS     read-only
   STATUS     mandatory
   DESCRIPTION
     "This attribute indicates the scope of the ATM address, which is the 
      highest level to which this address will be advertised in the PNNI 
      hierarchy. If no PnniInfo subcomponent has been provisioned, then 
      the scope will default to the level of this node in the PNNI 
      hierarchy. If this node does not participate in a PNNI hierarchy, then 
      this attribute will have the value of -1."
::= { mscAtmIfPnniAddrOperEntry 1 }

mscAtmIfPnniAddrReachability OBJECT-TYPE
   SYNTAX     INTEGER  {
                 internal(0),
                 exterior(1) }
   ACCESS     read-only
   STATUS     mandatory
   DESCRIPTION
     "This attribute indicates whether the address is internal or exterior. 
      An internal reachable address is an address of a destination that is 
      directly attached to the logical node advertising the address. An 
      exterior reachable address is an address that can be reached 
      through a PNNI routing domain, but which is not located in that 
      PNNI routing domain."
::= { mscAtmIfPnniAddrOperEntry 2 }


-- AtmIf/n Iisp Address/address,type TerminateSPvpAndSPvc
-- AtmIf/n Uni Address/address,type TerminateSPvpAndSPvc
-- AtmIf/n Pnni Address/address,type TerminateSPvpAndSPvc
-- AtmIf/n Vpt/m Iisp Address/address,type TerminateSPvpAndSPvc
-- AtmIf/n Vpt/m Uni Address/address,type TerminateSPvpAndSPvc
-- AtmIf/n Vpt/m Pnni Address/address,type TerminateSPvpAndSPvc
-- 
-- The presence of this subcomponent indicates that SPvp and SPvc 
-- call setups terminate at this node if the destination address of the 
-- SPVP or SPVC matches the Address instance.

mscAtmIfPnniAddrTermSP OBJECT IDENTIFIER ::= { mscAtmIfPnniAddr 2 }



mscAtmIfPnniAddrTermSPRowStatusTable OBJECT-TYPE
   SYNTAX     SEQUENCE OF MscAtmIfPnniAddrTermSPRowStatusEntry
   ACCESS     not-accessible
   STATUS     mandatory
   DESCRIPTION
     "This entry controls the addition and deletion of 
      mscAtmIfPnniAddrTermSP components."
::= { mscAtmIfPnniAddrTermSP 1 }

mscAtmIfPnniAddrTermSPRowStatusEntry OBJECT-TYPE
   SYNTAX     MscAtmIfPnniAddrTermSPRowStatusEntry
   ACCESS     not-accessible
   STATUS     mandatory
   DESCRIPTION
     "A single entry in the table represents a single 
      mscAtmIfPnniAddrTermSP component."
   INDEX {
      mscAtmIfIndex,
      mscAtmIfPnniIndex,
      mscAtmIfPnniAddrAddressIndex,
      mscAtmIfPnniAddrAddressTypeIndex,
      mscAtmIfPnniAddrTermSPIndex }
::= { mscAtmIfPnniAddrTermSPRowStatusTable 1 }

MscAtmIfPnniAddrTermSPRowStatusEntry ::= SEQUENCE {
   mscAtmIfPnniAddrTermSPRowStatus
      RowStatus,
   mscAtmIfPnniAddrTermSPComponentName
      DisplayString,
   mscAtmIfPnniAddrTermSPStorageType
      StorageType,
   mscAtmIfPnniAddrTermSPIndex
      NonReplicated }

mscAtmIfPnniAddrTermSPRowStatus OBJECT-TYPE
   SYNTAX     RowStatus 
   ACCESS     read-write
   STATUS     mandatory
   DESCRIPTION
     "This variable is used as the basis for SNMP naming of
      mscAtmIfPnniAddrTermSP components.
      These components can be added and deleted."
::= { mscAtmIfPnniAddrTermSPRowStatusEntry 1 }

mscAtmIfPnniAddrTermSPComponentName OBJECT-TYPE
   SYNTAX     DisplayString 
   ACCESS     read-only
   STATUS     mandatory
   DESCRIPTION
     "This variable provides the component's string name for
      use with the ASCII Console Interface"
::= { mscAtmIfPnniAddrTermSPRowStatusEntry 2 }

mscAtmIfPnniAddrTermSPStorageType OBJECT-TYPE
   SYNTAX     StorageType 
   ACCESS     read-only
   STATUS     mandatory
   DESCRIPTION
     "This variable represents the storage type value for the
      mscAtmIfPnniAddrTermSP tables."
::= { mscAtmIfPnniAddrTermSPRowStatusEntry 4 }

mscAtmIfPnniAddrTermSPIndex OBJECT-TYPE
   SYNTAX     NonReplicated 
   ACCESS     not-accessible
   STATUS     mandatory
   DESCRIPTION
     "This variable represents the index for the mscAtmIfPnniAddrTermSP tables."
::= { mscAtmIfPnniAddrTermSPRowStatusEntry 10 }


-- AtmIf/n Iisp Addr/address,type PnniInfo
-- AtmIf/n Uni Addr/address,type PnniInfo
-- AtmIf/n Pnni Addr/address,type PnniInfo
-- AtmIf/n Vpt/m Iisp Addr/address,type PnniInfo
-- AtmIf/n Vpt/m Uni Addr/address,type PnniInfo
-- AtmIf/n Vpt/m Pnni Addr/address,type PnniInfo
-- 
-- This component contains provisioned information associated with 
-- the ATM address related to PNNI. This component appears only 
-- under provisioned Address components.

mscAtmIfPnniAddrPnniInfo OBJECT IDENTIFIER ::= { mscAtmIfPnniAddr 3 }



mscAtmIfPnniAddrPnniInfoRowStatusTable OBJECT-TYPE
   SYNTAX     SEQUENCE OF MscAtmIfPnniAddrPnniInfoRowStatusEntry
   ACCESS     not-accessible
   STATUS     mandatory
   DESCRIPTION
     "This entry controls the addition and deletion of 
      mscAtmIfPnniAddrPnniInfo components."
::= { mscAtmIfPnniAddrPnniInfo 1 }

mscAtmIfPnniAddrPnniInfoRowStatusEntry OBJECT-TYPE
   SYNTAX     MscAtmIfPnniAddrPnniInfoRowStatusEntry
   ACCESS     not-accessible
   STATUS     mandatory
   DESCRIPTION
     "A single entry in the table represents a single 
      mscAtmIfPnniAddrPnniInfo component."
   INDEX {
      mscAtmIfIndex,
      mscAtmIfPnniIndex,
      mscAtmIfPnniAddrAddressIndex,
      mscAtmIfPnniAddrAddressTypeIndex,
      mscAtmIfPnniAddrPnniInfoIndex }
::= { mscAtmIfPnniAddrPnniInfoRowStatusTable 1 }

MscAtmIfPnniAddrPnniInfoRowStatusEntry ::= SEQUENCE {
   mscAtmIfPnniAddrPnniInfoRowStatus
      RowStatus,
   mscAtmIfPnniAddrPnniInfoComponentName
      DisplayString,
   mscAtmIfPnniAddrPnniInfoStorageType
      StorageType,
   mscAtmIfPnniAddrPnniInfoIndex
      NonReplicated }

mscAtmIfPnniAddrPnniInfoRowStatus OBJECT-TYPE
   SYNTAX     RowStatus 
   ACCESS     read-write
   STATUS     mandatory
   DESCRIPTION
     "This variable is used as the basis for SNMP naming of
      mscAtmIfPnniAddrPnniInfo components.
      These components can be added and deleted."
::= { mscAtmIfPnniAddrPnniInfoRowStatusEntry 1 }

mscAtmIfPnniAddrPnniInfoComponentName OBJECT-TYPE
   SYNTAX     DisplayString 
   ACCESS     read-only
   STATUS     mandatory
   DESCRIPTION
     "This variable provides the component's string name for
      use with the ASCII Console Interface"
::= { mscAtmIfPnniAddrPnniInfoRowStatusEntry 2 }

mscAtmIfPnniAddrPnniInfoStorageType OBJECT-TYPE
   SYNTAX     StorageType 
   ACCESS     read-only
   STATUS     mandatory
   DESCRIPTION
     "This variable represents the storage type value for the
      mscAtmIfPnniAddrPnniInfo tables."
::= { mscAtmIfPnniAddrPnniInfoRowStatusEntry 4 }

mscAtmIfPnniAddrPnniInfoIndex OBJECT-TYPE
   SYNTAX     NonReplicated 
   ACCESS     not-accessible
   STATUS     mandatory
   DESCRIPTION
     "This variable represents the index for the mscAtmIfPnniAddrPnniInfo tables."
::= { mscAtmIfPnniAddrPnniInfoRowStatusEntry 10 }

mscAtmIfPnniAddrPnniInfoProvTable OBJECT-TYPE
   SYNTAX     SEQUENCE OF MscAtmIfPnniAddrPnniInfoProvEntry
   ACCESS     not-accessible
   STATUS     mandatory
   DESCRIPTION
     "This attribute group contains the provisioned attributes relating to 
      PNNI for a PnniInfo component."
::= { mscAtmIfPnniAddrPnniInfo 10 }

mscAtmIfPnniAddrPnniInfoProvEntry OBJECT-TYPE
   SYNTAX     MscAtmIfPnniAddrPnniInfoProvEntry
   ACCESS     not-accessible
   STATUS     mandatory
   DESCRIPTION
     "An entry in the mscAtmIfPnniAddrPnniInfoProvTable."
   INDEX {
      mscAtmIfIndex,
      mscAtmIfPnniIndex,
      mscAtmIfPnniAddrAddressIndex,
      mscAtmIfPnniAddrAddressTypeIndex,
      mscAtmIfPnniAddrPnniInfoIndex }
::= { mscAtmIfPnniAddrPnniInfoProvTable 1 }

MscAtmIfPnniAddrPnniInfoProvEntry ::= SEQUENCE {
   mscAtmIfPnniAddrPnniInfoScope
      INTEGER,
   mscAtmIfPnniAddrPnniInfoReachability
      INTEGER }

mscAtmIfPnniAddrPnniInfoScope OBJECT-TYPE
   SYNTAX     INTEGER (-1..104)
   ACCESS     read-write
   STATUS     mandatory
   DESCRIPTION
     "This attribute specifies the scope of the ATM address, which is the 
      highest level up to which this address will be advertised in the 
      PNNI hierarchy. The scope must be set to a value numerically less 
      than or equal to the level of the lowest level peer group containing 
      this node. Setting the scope to 0 will cause the address to be 
      advertised globally within this PNNI routing domain."
   DEFVAL     { -1 }
::= { mscAtmIfPnniAddrPnniInfoProvEntry 1 }

mscAtmIfPnniAddrPnniInfoReachability OBJECT-TYPE
   SYNTAX     INTEGER  {
                 internal(0),
                 exterior(1) }
   ACCESS     read-write
   STATUS     mandatory
   DESCRIPTION
     "This attribute indicates whether the address is internal or exterior. 
      An internal reachable address is an address of a destination that is 
      directly attached to the logical node advertising the address. An 
      exterior reachable address is an address that can be reached 
      through a PNNI routing domain, but which is not located in that 
      PNNI routing domain."
   DEFVAL     { internal }
::= { mscAtmIfPnniAddrPnniInfoProvEntry 2 }




-- 
-- Version and Compliance statements
-- 



-- Object-Group Statement:
-- A list of all current accessible leaf objects.

-- OBJECTS { mscAtmIfVptPnniRccVcdWeight,
--           mscAtmIfVptPnniSoftPvpAndPvcRetryPeriod,
--           mscAtmIfPnniSigSuccessfulConnections,
--           mscAtmIfVptPnniSigVcdAtmServiceCategory,
--           mscAtmIfVptPnniAddrPnniInfoScope,
--           mscAtmIfPnniSigCurrentPmpConnections,
--           mscAtmIfPnniCbrWeight,
--           mscAtmIfPnniRccVcdTdpValue,
--           mscAtmIfVptPnniServiceExchange,
--           mscAtmIfPnniSigNewCurrentConnections,
--           mscAtmIfVptPnniRccVcdQosClass,
--           mscAtmIfVptPnniAddrPnniInfoRowStatus,
--           mscAtmIfPnniRccNegotiatedVersion,
--           mscAtmIfVptPnniRccHelloState,
--           mscAtmIfPnniRccComponentName,
--           mscAtmIfVptPnniRccOperationalState,
--           mscAtmIfPnniRccRemotePortId,
--           mscAtmIfPnniSigVcdTdpValue,
--           mscAtmIfPnniAddrPnniInfoScope,
--           mscAtmIfPnniSigAddressConversion,
--           mscAtmIfPnniComponentName,
--           mscAtmIfVptPnniSigRowStatus,
--           mscAtmIfVptPnniRccVcdComponentName,
--           mscAtmIfPnniRccVcdTrafficShaping,
--           mscAtmIfPnniSigLastRxCauseCode,
--           mscAtmIfPnniRccRemoteNodeId,
--           mscAtmIfVptPnniSigStorageType,
--           mscAtmIfPnniAddrPnniInfoComponentName,
--           mscAtmIfVptPnniRccHelloInterval,
--           mscAtmIfPnniAccountConnectionType,
--           mscAtmIfPnniUbrWeight,
--           mscAtmIfVptPnniRccHelloInactivityFactor,
--           mscAtmIfPnniSigVcdUnshapedTransmitQueueing,
--           mscAtmIfVptPnniSigUsageState,
--           mscAtmIfVptPnniRccVcdTrafficShaping,
--           mscAtmIfPnniRccBadHelloPacketsRx,
--           mscAtmIfVptPnniSigVcdWeight,
--           mscAtmIfPnniSigPeakPmpConnections,
--           mscAtmIfPnniSigRowStatus,
--           mscAtmIfVptPnniRccHelloPacketsRx,
--           mscAtmIfPnniRccMismatchedHelloPacketsRx,
--           mscAtmIfVptPnniUbrWeight,
--           mscAtmIfPnniSigPeakConnections,
--           mscAtmIfVptPnniAddrScope,
--           mscAtmIfPnniAddrScope,
--           mscAtmIfVptPnniSigVcdQosClass,
--           mscAtmIfVptPnniAddrComponentName,
--           mscAtmIfVptPnniSigLastTxDiagCode,
--           mscAtmIfPnniPortId,
--           mscAtmIfPnniSigComponentName,
--           mscAtmIfVptPnniSigOperationalState,
--           mscAtmIfVptPnniSigCurrentPmpConnections,
--           mscAtmIfPnniRccVcdTrafficDescType,
--           mscAtmIfVptPnniAddrTermSPComponentName,
--           mscAtmIfPnniRccHelloInactivityFactor,
--           mscAtmIfVptPnniSigVcdComponentName,
--           mscAtmIfPnniSigVcdTrafficShaping,
--           mscAtmIfPnniRtVbrWeight,
--           mscAtmIfPnniSigOperatingMode,
--           mscAtmIfPnniRccVcdUsageParameterControl,
--           mscAtmIfPnniSoftPvpAndPvcHoldOffTime,
--           mscAtmIfPnniRccHelloState,
--           mscAtmIfVptPnniRccType,
--           mscAtmIfVptPnniAddrPnniInfoComponentName,
--           mscAtmIfPnniRccStorageType,
--           mscAtmIfVptPnniRccVcdTdpValue,
--           mscAtmIfPnniAccountCollection,
--           mscAtmIfPnniSigVcdAtmServiceCategory,
--           mscAtmIfVptPnniSigVcdTrafficShaping,
--           mscAtmIfVptPnniAddrTermSPStorageType,
--           mscAtmIfPnniAddrStorageType,
--           mscAtmIfPnniStorageType,
--           mscAtmIfVptPnniRccVcdStorageType,
--           mscAtmIfVptPnniSigLastRxDiagCode,
--           mscAtmIfPnniAddrTermSPRowStatus,
--           mscAtmIfPnniSigVcdStorageType,
--           mscAtmIfVptPnniStorageType,
--           mscAtmIfPnniRccType,
--           mscAtmIfVptPnniSigLastTxCauseCode,
--           mscAtmIfVptPnniSigPeakPmpConnections,
--           mscAtmIfPnniSigSuccessfulPmpConnections,
--           mscAtmIfPnniSigLastTxDiagCode,
--           mscAtmIfVptPnniRccBadHelloPacketsRx,
--           mscAtmIfPnniSigFailedPmpConnections,
--           mscAtmIfPnniAddrReachability,
--           mscAtmIfVptPnniSigRxPdus,
--           mscAtmIfPnniRowStatus,
--           mscAtmIfVptPnniSigSuccessfulConnections,
--           mscAtmIfPnniSigLastRxDiagCode,
--           mscAtmIfPnniSigVcdRowStatus,
--           mscAtmIfVptPnniRccHelloPacketsTx,
--           mscAtmIfVptPnniRccVci,
--           mscAtmIfVptPnniCbrWeight,
--           mscAtmIfPnniAddrPnniInfoStorageType,
--           mscAtmIfVptPnniSigNewCurrentConnections,
--           mscAtmIfVptPnniRccVcdUnshapedTransmitQueueing,
--           mscAtmIfPnniSigVcdUsageParameterControl,
--           mscAtmIfVptPnniRccNegotiatedVersion,
--           mscAtmIfPnniRccRowStatus,
--           mscAtmIfVptPnniRccComponentName,
--           mscAtmIfVptPnniRccVcdRowStatus,
--           mscAtmIfVptPnniRccRemotePortId,
--           mscAtmIfPnniSigStorageType,
--           mscAtmIfVptPnniSigVcdTdpValue,
--           mscAtmIfVptPnniAddrPnniInfoReachability,
--           mscAtmIfVptPnniSigAddressConversion,
--           mscAtmIfVptPnniComponentName,
--           mscAtmIfPnniNrtVbrWeight,
--           mscAtmIfVptPnniAccountClass,
--           mscAtmIfVptPnniSigLastRxCauseCode,
--           mscAtmIfVptPnniVpci,
--           mscAtmIfVptPnniSigVcdStorageType,
--           mscAtmIfVptPnniAddrRowStatus,
--           mscAtmIfPnniAddrTermSPStorageType,
--           mscAtmIfVptPnniRccHelloHoldDown,
--           mscAtmIfPnniRccVcdWeight,
--           mscAtmIfPnniServiceExchange,
--           mscAtmIfVptPnniAccountConnectionType,
--           mscAtmIfPnniSigVci,
--           mscAtmIfPnniRccHelloPacketsTx,
--           mscAtmIfVptPnniAddrPnniInfoStorageType,
--           mscAtmIfVptPnniSigFailedPmpConnections,
--           mscAtmIfPnniRccOperationalState,
--           mscAtmIfPnniAccountClass,
--           mscAtmIfPnniRccAdminState,
--           mscAtmIfVptPnniRccMismatchedHelloPacketsRx,
--           mscAtmIfVptPnniSigVci,
--           mscAtmIfPnniRccVcdComponentName,
--           mscAtmIfPnniRccVcdRowStatus,
--           mscAtmIfPnniSigVcdTrafficDescType,
--           mscAtmIfVptPnniSigAdminState,
--           mscAtmIfVptPnniSigVcdUnshapedTransmitQueueing,
--           mscAtmIfVptPnniPortId,
--           mscAtmIfVptPnniSigComponentName,
--           mscAtmIfVptPnniSigVcdRowStatus,
--           mscAtmIfPnniSigAdminState,
--           mscAtmIfPnniSigTxPdus,
--           mscAtmIfPnniRccUsageState,
--           mscAtmIfVptPnniRccVcdTrafficDescType,
--           mscAtmIfPnniAddrComponentName,
--           mscAtmIfPnniSigUsageState,
--           mscAtmIfVptPnniSigPeakConnections,
--           mscAtmIfPnniAddrRowStatus,
--           mscAtmIfPnniSigVcdWeight,
--           mscAtmIfVptPnniRtVbrWeight,
--           mscAtmIfVptPnniSigTxPdus,
--           mscAtmIfPnniRccHelloPacketsRx,
--           mscAtmIfVptPnniRccVcdUsageParameterControl,
--           mscAtmIfPnniSigFailedConnections,
--           mscAtmIfPnniRccHelloHoldDown,
--           mscAtmIfVptPnniRccStorageType,
--           mscAtmIfVptPnniAccountCollection,
--           mscAtmIfPnniRccVci,
--           mscAtmIfPnniRccVcdQosClass,
--           mscAtmIfPnniSigOperationalState,
--           mscAtmIfPnniRccVcdAtmServiceCategory,
--           mscAtmIfVptPnniAddrStorageType,
--           mscAtmIfVptPnniRccRemoteNodeId,
--           mscAtmIfVptPnniSigOperatingMode,
--           mscAtmIfVptPnniRccVcdAtmServiceCategory,
--           mscAtmIfPnniAddrTermSPComponentName,
--           mscAtmIfPnniSigVcdComponentName,
--           mscAtmIfVptPnniSigSuccessfulPmpConnections,
--           mscAtmIfVptPnniRccAdminState,
--           mscAtmIfVptPnniAddrReachability,
--           mscAtmIfPnniRccVcdUnshapedTransmitQueueing,
--           mscAtmIfVptPnniSigVcdTrafficDescType,
--           mscAtmIfPnniAddrPnniInfoReachability,
--           mscAtmIfPnniSigRxPdus,
--           mscAtmIfVptPnniRccRowStatus,
--           mscAtmIfPnniRccHelloInterval,
--           mscAtmIfPnniSigVcdQosClass,
--           mscAtmIfPnniRccVcdStorageType,
--           mscAtmIfVptPnniSigVcdUsageParameterControl,
--           mscAtmIfVptPnniRowStatus,
--           mscAtmIfVptPnniNrtVbrWeight,
--           mscAtmIfVptPnniAddrTermSPRowStatus,
--           mscAtmIfPnniSoftPvpAndPvcRetryPeriod,
--           mscAtmIfPnniSigLastTxCauseCode,
--           mscAtmIfVptPnniSigFailedConnections,
--           mscAtmIfVptPnniSoftPvpAndPvcHoldOffTime,
--           mscAtmIfVptPnniRccUsageState,
--           mscAtmIfPnniAddrPnniInfoRowStatus }
-- STATUS  mandatory
-- DESCRIPTION
--   "A list of all current accessible leaf objects."

atmPnniGroup OBJECT IDENTIFIER ::= { atmPnniMIB 1 }
atmPnniGroupCA OBJECT IDENTIFIER ::= { atmPnniGroup 1 }
atmPnniGroupCA02 OBJECT IDENTIFIER ::= { atmPnniGroupCA 3 }
atmPnniGroupCA02A OBJECT IDENTIFIER ::= { atmPnniGroupCA02 2 }



-- Agent-Capabilities Statement:

-- PRODUCT-RELEASE "MscPassport Release 1.2 AtmPnni."
-- STATUS          mandatory
-- DESCRIPTION     "Carrier Passport AtmPnni MIB: MIB Version CA02A,
--                  Software Version CA02S9C."
-- SUPPORTS        Nortel-MsCarrier-MscPassport-AtmPnniMIB
--    INCLUDES     { atmPnniGroupCA02A }

atmPnniCapabilities OBJECT IDENTIFIER ::= { atmPnniMIB 3 }
atmPnniCapabilitiesCA OBJECT IDENTIFIER ::= { atmPnniCapabilities 1 }
atmPnniCapabilitiesCA02 OBJECT IDENTIFIER ::= { atmPnniCapabilitiesCA 3 }
atmPnniCapabilitiesCA02A OBJECT IDENTIFIER ::= { atmPnniCapabilitiesCA02 2 }





END
