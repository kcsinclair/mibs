Nortel-MsCarrier-MscPassport-AtmBearerServiceMIB
DEFINITIONS ::= BEGIN



IMPORTS

      OBJECT-TYPE
   FROM RFC-1212

      mscPassportMIBs
   FROM Nortel-MsCarrier-MscPassport-UsefulDefinitionsMIB

      DisplayString,
      StorageType,
      RowStatus
   FROM Nortel-MsCarrier-MscPassport-StandardTextualConventionsMIB

      NonReplicated,
      Link
   FROM Nortel-MsCarrier-MscPassport-TextualConventionsMIB

      mscAtmIfVptVcc,
      mscAtmIfVccIndex,
      mscAtmIfVptIndex,
      mscAtmIfVcc,
      mscAtmIfVpcIndex,
      mscAtmIfVpc,
      mscAtmIfVptVccIndex,
      mscAtmIfIndex
   FROM Nortel-MsCarrier-MscPassport-AtmCoreMIB;




-- LAST-UPDATED   "9909010000Z"
-- ORGANIZATION   "Nortel Networks"
-- CONTACT-INFO   "
--         Nortel Carrier Data Network Management
--         
--         Postal:       P.O. Box 3511, Station C 
--                       Ottawa, Ontario 
--                       Canada  K1Y 4H7
--         
--         via the WEB:  http://www.nortelnetworks.com  
--                       select 'Contact Us' from the menu
--          
--         via phone:    1-800-4NORTEL"
-- DESCRIPTION
--    "The module describing the Nortel MsCarrier MscPassport
--     AtmBearerService Enterprise MIB."

atmBearerServiceMIB OBJECT IDENTIFIER ::= { mscPassportMIBs 64 }










-- AtmIf/n Vcc/vpi.vci Nrp
-- This component is used to establish a single hop of a nailed-up 
-- ATM Bearer Service (ABS) connection. By linking together two 
-- Nrps within a module, the associated connections are configured to 
-- relay ATM cells to one another. The Nrp component requires 
-- exclusive use of its parent Vcc or Vpc and cannot co-exist with other 
-- ATM service components (such as Nep, Test, and Loop).

mscAtmIfVpcNrp OBJECT IDENTIFIER ::= { mscAtmIfVpc 4 }



mscAtmIfVpcNrpRowStatusTable OBJECT-TYPE
   SYNTAX     SEQUENCE OF MscAtmIfVpcNrpRowStatusEntry
   ACCESS     not-accessible
   STATUS     mandatory
   DESCRIPTION
     "This entry controls the addition and deletion of 
      mscAtmIfVpcNrp components."
::= { mscAtmIfVpcNrp 1 }

mscAtmIfVpcNrpRowStatusEntry OBJECT-TYPE
   SYNTAX     MscAtmIfVpcNrpRowStatusEntry
   ACCESS     not-accessible
   STATUS     mandatory
   DESCRIPTION
     "A single entry in the table represents a single 
      mscAtmIfVpcNrp component."
   INDEX {
      mscAtmIfIndex,
      mscAtmIfVpcIndex,
      mscAtmIfVpcNrpIndex }
::= { mscAtmIfVpcNrpRowStatusTable 1 }

MscAtmIfVpcNrpRowStatusEntry ::= SEQUENCE {
   mscAtmIfVpcNrpRowStatus
      RowStatus,
   mscAtmIfVpcNrpComponentName
      DisplayString,
   mscAtmIfVpcNrpStorageType
      StorageType,
   mscAtmIfVpcNrpIndex
      NonReplicated }

mscAtmIfVpcNrpRowStatus OBJECT-TYPE
   SYNTAX     RowStatus 
   ACCESS     read-write
   STATUS     mandatory
   DESCRIPTION
     "This variable is used as the basis for SNMP naming of
      mscAtmIfVpcNrp components.
      These components can be added and deleted."
::= { mscAtmIfVpcNrpRowStatusEntry 1 }

mscAtmIfVpcNrpComponentName OBJECT-TYPE
   SYNTAX     DisplayString 
   ACCESS     read-only
   STATUS     mandatory
   DESCRIPTION
     "This variable provides the component's string name for
      use with the ASCII Console Interface"
::= { mscAtmIfVpcNrpRowStatusEntry 2 }

mscAtmIfVpcNrpStorageType OBJECT-TYPE
   SYNTAX     StorageType 
   ACCESS     read-only
   STATUS     mandatory
   DESCRIPTION
     "This variable represents the storage type value for the
      mscAtmIfVpcNrp tables."
::= { mscAtmIfVpcNrpRowStatusEntry 4 }

mscAtmIfVpcNrpIndex OBJECT-TYPE
   SYNTAX     NonReplicated 
   ACCESS     not-accessible
   STATUS     mandatory
   DESCRIPTION
     "This variable represents the index for the mscAtmIfVpcNrp tables."
::= { mscAtmIfVpcNrpRowStatusEntry 10 }

mscAtmIfVpcNrpProvTable OBJECT-TYPE
   SYNTAX     SEQUENCE OF MscAtmIfVpcNrpProvEntry
   ACCESS     not-accessible
   STATUS     mandatory
   DESCRIPTION
     "This group contains the provisionable attributes for the Nrp 
      component."
::= { mscAtmIfVpcNrp 100 }

mscAtmIfVpcNrpProvEntry OBJECT-TYPE
   SYNTAX     MscAtmIfVpcNrpProvEntry
   ACCESS     not-accessible
   STATUS     mandatory
   DESCRIPTION
     "An entry in the mscAtmIfVpcNrpProvTable."
   INDEX {
      mscAtmIfIndex,
      mscAtmIfVpcIndex,
      mscAtmIfVpcNrpIndex }
::= { mscAtmIfVpcNrpProvTable 1 }

MscAtmIfVpcNrpProvEntry ::= SEQUENCE {
   mscAtmIfVpcNrpNextHop
      Link,
   mscAtmIfVpcNrpConnectionPointType
      INTEGER,
   mscAtmIfVpcNrpOamSegmentBoundary
      INTEGER,
   mscAtmIfVpcNrpTxAal5PartialPacketDiscard
      INTEGER,
   mscAtmIfVpcNrpRxAal5PartialPacketDiscard
      INTEGER,
   mscAtmIfVpcNrpBandwidthElastic
      INTEGER,
   mscAtmIfVpcNrpOverrideHoldingPriority
      INTEGER }

mscAtmIfVpcNrpNextHop OBJECT-TYPE
   SYNTAX     Link 
   ACCESS     read-write
   STATUS     mandatory
   DESCRIPTION
     "This attribute specifies the Nrp component with which this Nrp is 
      associated. A sample value is AtmIf/31 Vcc/0.32 Nrp."
::= { mscAtmIfVpcNrpProvEntry 10 }

mscAtmIfVpcNrpConnectionPointType OBJECT-TYPE
   SYNTAX     INTEGER  {
                 segmentEndPoint(1),
                 connectingPoint(2),
                 autoConfigure(4) }
   ACCESS     read-write
   STATUS     obsolete
   DESCRIPTION
     "This attribute specifies the connection point type desired for a Nrp 
      component. The actual connection point type value is visible in the 
      parent component's connectionPointType attribute. 
      
      The desired connection point type can be specified directly as a 
      segmentEndPoint or connectingPoint. If autoConfigure is 
      specified, the switch will select the connection point type based on 
      the type attribute of the associated AtmIf, choosing 
      segmentEndPoint for a UNI-type ATM interface and 
      connectingPoint for a PPI-type ATM interface.
      
      It is obsoleted. The value is mapped into oamSegmentBoundary 
      attribute. segmentEndPoint is mapped into yes. connectingPoint is 
      mapped into no. autoConfigure is mapped into sameAsInterface."
   DEFVAL     { autoConfigure }
::= { mscAtmIfVpcNrpProvEntry 20 }

mscAtmIfVpcNrpOamSegmentBoundary OBJECT-TYPE
   SYNTAX     INTEGER  {
                 no(0),
                 yes(1),
                 sameAsInterface(2) }
   ACCESS     read-write
   STATUS     mandatory
   DESCRIPTION
     "This attribute specifies the OAM segment boundary desired for a 
      Nrp component. It affects the connection point type value visible in 
      the parent component's connectionPointType attribute. 
      
      The desired OAM segment boundary can be specified directly as 
      yes, no or sameAsInterface. If sameAsInterface is specified, the 
      OAM segment boundary is same as the oamSegmentBoundary 
      attribute of the associated AtmIf and the switch will set the 
      connectionPointType, choosing segmentEndPoint for a segment-
      boundary ATM interface and connectingPoint for a non-segment-
      boundary ATM interface."
   DEFVAL     { sameAsInterface }
::= { mscAtmIfVpcNrpProvEntry 30 }

mscAtmIfVpcNrpTxAal5PartialPacketDiscard OBJECT-TYPE
   SYNTAX     INTEGER  {
                 disabled(0),
                 enabled(1) }
   ACCESS     read-write
   STATUS     obsolete
   DESCRIPTION
     "This attribute is obsolete in P4.2 and has been migrated under Vcd 
      (Vpd) component. 
      
      This attribute specifies whether the AAL5 Partial Packet Discard 
      (PPD) feature has been enabled or disabled on the Nrp in the 
      transmit direction. This feature allows the NRP to discard the 
      remainder of a cell-forwarded AAL5 frame if a cell of this frame 
      has been discarded due to congestion. This increases the 'goodput' 
      of the link, since cells which are only going to be discarded by the 
      AAL5 reassembly are not transmitted.
      
      When this attribute is set to enabled, the PPD feature is applied in 
      the transmit direction. It should only be enabled for connections 
      whose end points are performing AAL5 segmentation and 
      reassembly. When this attribute is set to disabled, the PPD feature is 
      not applied to traffic for this connection in the transmit direction. 
      Note that specifying enabled for a non-AAL5 connection will cause 
      all traffic to be discarded once congestion is encountered."
   DEFVAL     { disabled }
::= { mscAtmIfVpcNrpProvEntry 31 }

mscAtmIfVpcNrpRxAal5PartialPacketDiscard OBJECT-TYPE
   SYNTAX     INTEGER  {
                 disabled(0),
                 enabled(1),
                 sameAsTx(2) }
   ACCESS     read-write
   STATUS     obsolete
   DESCRIPTION
     "This attribute is obsolete in P4.2 and has been migrated under Vcd 
      (Vpd) component.
      
      This attribute specifies whether the AAL5 Partial Packet Discard 
      (PPD) feature has been enabled or disabled on the Nrp in the 
      receive direction. This feature allows the NRP to discard the 
      remainder of a cell-forwarded AAL5 frame if a cell of this frame 
      has been discarded due to congestion or usage parameter control 
      (UPC). This increases the 'goodput' of the link, since cells which 
      are only going to be discarded by the AAL5 reassembly are not 
      transmitted.
      
      When this attribute is set to enabled, the PPD feature is applied in 
      the receive direction. It should only be enabled for connections 
      whose end points are performing AAL5 segmentation and 
      reassembly. When this attribute is set to disabled, the PPD feature is 
      not applied to traffic for this connection in the receive direction. 
      When this attribute is set to sameAsTx, the PPD feature for traffic 
      in the receive direction will be configured the same way as it is in 
      the transmit direction. 
      Note that specifying enabled for a non-AAL5 connection will cause 
      all traffic to be discarded once congestion is encountered."
   DEFVAL     { sameAsTx }
::= { mscAtmIfVpcNrpProvEntry 32 }

mscAtmIfVpcNrpBandwidthElastic OBJECT-TYPE
   SYNTAX     INTEGER  {
                 no(0),
                 yes(1) }
   ACCESS     read-write
   STATUS     mandatory
   DESCRIPTION
     "This attribute is only of importance for connections which are 
      carried on a link with a variable bandwidth. For example, the 
      bandwidth may be reduced in the event that one or more physical 
      links in the IMA group fail, such that the originally requested 
      bandwidth cannot be maintained. This attribute shows whether the 
      application running on this connection can continue to operate if the 
      bandwidth is reduced. If the bandwidth is reduced, the amount by 
      which it is reduced will be displayed in the bandwidthReduction 
      attribute. 
      
      A value of yes, indicates that this connection is elastic, and the 
      bandwidth may be reduced but the connection will not be released. 
      Currently, this attribute should only be set to yes for situations 
      where this Nrp is functioning as a loopback on one side of an IMA 
      link. There are no other situations where this setting is valid.
      
      A value of no indicates that the bandwidth for this connection will 
      not be reduced in the event of link bandwidth reduction. However, 
      this connection may be released based on its holdingPriority."
   DEFVAL     { no }
::= { mscAtmIfVpcNrpProvEntry 33 }

mscAtmIfVpcNrpOverrideHoldingPriority OBJECT-TYPE
   SYNTAX     INTEGER  {
                 n0(0),
                 n1(1),
                 n2(2),
                 n3(3),
                 n4(4),
                 noOverride(6) }
   ACCESS     read-write
   STATUS     mandatory
   DESCRIPTION
     "This attribute specifies the holding priority of this connection. 
      Holding priority is used when there is an IMA group where some 
      physical links have failed. Holding priority determines the order in 
      which connections are released. 4 is the lowest holding priority and 
      is released first. 0 is a higher priority and is released last. The value 
      specified in this attribute will override whatever holdingPriority that 
      has been provisioned at the Vcd (or Vpd). If the value is left at the 
      default of noOverride, the holdingPriority provisioned at the Vcd 
      (or Vpd) will be used."
   DEFVAL     { noOverride }
::= { mscAtmIfVpcNrpProvEntry 34 }


-- AtmIf/n Vcc/vpi.vci Mnrp
-- This component is used to establish a root of a multicast nailed-up 
-- ATM Bearer Service (ABS) connection. By linking a Mnrp to a 
-- Nrp, the associated connections are configured to relay ATM cells 
-- from Mnrp to Nrp. The Mnrp component requires exclusive use of 
-- its parent Vcc or Vpc and cannot co-exist with other ATM service 
-- components (such as Nep, Test, Nrp and Loop). This component is 
-- supported only on 4pOC3SmIrAtm and 4pOC3MmAtm cards.This 
-- component is not supported under Vpt Vcc and Vpt Vpc.

mscAtmIfVpcMnrp OBJECT IDENTIFIER ::= { mscAtmIfVpc 12 }



mscAtmIfVpcMnrpRowStatusTable OBJECT-TYPE
   SYNTAX     SEQUENCE OF MscAtmIfVpcMnrpRowStatusEntry
   ACCESS     not-accessible
   STATUS     mandatory
   DESCRIPTION
     "This entry controls the addition and deletion of 
      mscAtmIfVpcMnrp components."
::= { mscAtmIfVpcMnrp 1 }

mscAtmIfVpcMnrpRowStatusEntry OBJECT-TYPE
   SYNTAX     MscAtmIfVpcMnrpRowStatusEntry
   ACCESS     not-accessible
   STATUS     mandatory
   DESCRIPTION
     "A single entry in the table represents a single 
      mscAtmIfVpcMnrp component."
   INDEX {
      mscAtmIfIndex,
      mscAtmIfVpcIndex,
      mscAtmIfVpcMnrpIndex }
::= { mscAtmIfVpcMnrpRowStatusTable 1 }

MscAtmIfVpcMnrpRowStatusEntry ::= SEQUENCE {
   mscAtmIfVpcMnrpRowStatus
      RowStatus,
   mscAtmIfVpcMnrpComponentName
      DisplayString,
   mscAtmIfVpcMnrpStorageType
      StorageType,
   mscAtmIfVpcMnrpIndex
      NonReplicated }

mscAtmIfVpcMnrpRowStatus OBJECT-TYPE
   SYNTAX     RowStatus 
   ACCESS     read-write
   STATUS     mandatory
   DESCRIPTION
     "This variable is used as the basis for SNMP naming of
      mscAtmIfVpcMnrp components.
      These components can be added and deleted."
::= { mscAtmIfVpcMnrpRowStatusEntry 1 }

mscAtmIfVpcMnrpComponentName OBJECT-TYPE
   SYNTAX     DisplayString 
   ACCESS     read-only
   STATUS     mandatory
   DESCRIPTION
     "This variable provides the component's string name for
      use with the ASCII Console Interface"
::= { mscAtmIfVpcMnrpRowStatusEntry 2 }

mscAtmIfVpcMnrpStorageType OBJECT-TYPE
   SYNTAX     StorageType 
   ACCESS     read-only
   STATUS     mandatory
   DESCRIPTION
     "This variable represents the storage type value for the
      mscAtmIfVpcMnrp tables."
::= { mscAtmIfVpcMnrpRowStatusEntry 4 }

mscAtmIfVpcMnrpIndex OBJECT-TYPE
   SYNTAX     NonReplicated 
   ACCESS     not-accessible
   STATUS     mandatory
   DESCRIPTION
     "This variable represents the index for the mscAtmIfVpcMnrp tables."
::= { mscAtmIfVpcMnrpRowStatusEntry 10 }

mscAtmIfVpcMnrpProvTable OBJECT-TYPE
   SYNTAX     SEQUENCE OF MscAtmIfVpcMnrpProvEntry
   ACCESS     not-accessible
   STATUS     mandatory
   DESCRIPTION
     "This group contains the provisionable attributes for the Mnrp 
      component."
::= { mscAtmIfVpcMnrp 101 }

mscAtmIfVpcMnrpProvEntry OBJECT-TYPE
   SYNTAX     MscAtmIfVpcMnrpProvEntry
   ACCESS     not-accessible
   STATUS     mandatory
   DESCRIPTION
     "An entry in the mscAtmIfVpcMnrpProvTable."
   INDEX {
      mscAtmIfIndex,
      mscAtmIfVpcIndex,
      mscAtmIfVpcMnrpIndex }
::= { mscAtmIfVpcMnrpProvTable 1 }

MscAtmIfVpcMnrpProvEntry ::= SEQUENCE {
   mscAtmIfVpcMnrpOamSegmentBoundary
      INTEGER,
   mscAtmIfVpcMnrpBandwidthElastic
      INTEGER,
   mscAtmIfVpcMnrpOverrideHoldingPriority
      INTEGER }

mscAtmIfVpcMnrpOamSegmentBoundary OBJECT-TYPE
   SYNTAX     INTEGER  {
                 no(0),
                 yes(1),
                 sameAsInterface(2) }
   ACCESS     read-write
   STATUS     mandatory
   DESCRIPTION
     "This attribute specifies the OAM segment boundary desired for a 
      Mnrp component. It affects the connection point type value visible 
      in the parent component's connectionPointType attribute. 
      The desired OAM segment boundary can be specified directly as 
      yes, no or sameAsInterface. If sameAsInterface is specified, the 
      OAM segment boundary is same as the oamSegmentBoundary 
      attribute of the associated AtmIf and the switch will set the 
      connectionPointType, choosing segmentEndPoint for a segment-
      boundary ATM interface and connectingPoint for a non-segment-
      boundary ATM interface."
   DEFVAL     { sameAsInterface }
::= { mscAtmIfVpcMnrpProvEntry 30 }

mscAtmIfVpcMnrpBandwidthElastic OBJECT-TYPE
   SYNTAX     INTEGER  {
                 no(0),
                 yes(1) }
   ACCESS     read-write
   STATUS     mandatory
   DESCRIPTION
     "This attribute is only of importance for connections which are 
      carried on a link with a variable bandwidth. For example, the 
      bandwidth may be reduced in the event that one or more physical 
      links in the IMA group fail, such that the originally requested 
      bandwidth cannot be maintained. This attribute shows whether the 
      application running on this connection can continue to operate if the 
      bandwidth is reduced. If the bandwidth is reduced, the amount by 
      which it is reduced will be displayed in the bandwidthReduction 
      attribute. 
      A value of yes, indicates that this connection is elastic, and the 
      bandwidth may be reduced but the connection will not be released. 
      Currently, this attribute should only be set to yes for situations 
      where this Mnrp is functioning as a loopback on one side of an IMA 
      link. There are no other situations where this setting is valid.
      A value of no indicates that the bandwidth for this connection will 
      not be reduced in the event of link bandwidth reduction. However, 
      this connection may be released based on its holdingPriority."
   DEFVAL     { no }
::= { mscAtmIfVpcMnrpProvEntry 33 }

mscAtmIfVpcMnrpOverrideHoldingPriority OBJECT-TYPE
   SYNTAX     INTEGER  {
                 n0(0),
                 n1(1),
                 n2(2),
                 n3(3),
                 n4(4),
                 noOverride(6) }
   ACCESS     read-write
   STATUS     mandatory
   DESCRIPTION
     "This attribute specifies the holding priority of this connection. 
      Holding priority is used when there is an IMA group where some 
      physical links have failed. Holding priority determines the order in 
      which connections are released. 4 is the lowest holding priority and 
      is released first. 0 is a higher priority and is released last. The value 
      specified in this attribute will override whatever holdingPriority that 
      has been provisioned at the Vcd (or Vpd). If the value is left at the 
      default of noOverride, the holdingPriority provisioned at the Vcd 
      (or Vpd) will be used."
   DEFVAL     { noOverride }
::= { mscAtmIfVpcMnrpProvEntry 34 }

mscAtmIfVpcMnrpNextHopsTable OBJECT-TYPE
   SYNTAX     SEQUENCE OF MscAtmIfVpcMnrpNextHopsEntry
   ACCESS     not-accessible
   STATUS     mandatory
   DESCRIPTION
     "This attribute specifies the list of Nrp components with which this 
      Mnrp is associated. A sample value is AtmIf/31 Vcc/0.32 Nrp. This 
      attribute must be provisioned with at least one Nrp component 
      under a compatible connection type."
::= { mscAtmIfVpcMnrp 658 }

mscAtmIfVpcMnrpNextHopsEntry OBJECT-TYPE
   SYNTAX     MscAtmIfVpcMnrpNextHopsEntry
   ACCESS     not-accessible
   STATUS     mandatory
   DESCRIPTION
     "An entry in the mscAtmIfVpcMnrpNextHopsTable."
   INDEX {
      mscAtmIfIndex,
      mscAtmIfVpcIndex,
      mscAtmIfVpcMnrpIndex,
      mscAtmIfVpcMnrpNextHopsValue }
::= { mscAtmIfVpcMnrpNextHopsTable 1 }

MscAtmIfVpcMnrpNextHopsEntry ::= SEQUENCE {
   mscAtmIfVpcMnrpNextHopsValue
      Link,
   mscAtmIfVpcMnrpNextHopsRowStatus
      RowStatus }

mscAtmIfVpcMnrpNextHopsValue OBJECT-TYPE
   SYNTAX     Link 
   ACCESS     read-write
   STATUS     mandatory
   DESCRIPTION
     "This variable represents both the value and the index for the
      mscAtmIfVpcMnrpNextHopsTable."
::= { mscAtmIfVpcMnrpNextHopsEntry 1 }

mscAtmIfVpcMnrpNextHopsRowStatus OBJECT-TYPE
   SYNTAX     RowStatus 
   ACCESS     write-only
   STATUS     mandatory
   DESCRIPTION
     "This variable is used to control the addition and deletion 
      of individual values of the mscAtmIfVpcMnrpNextHopsTable."
::= { mscAtmIfVpcMnrpNextHopsEntry 2 }


-- AtmIf/n Vcc/vpi.vci Nrp
-- This component is used to establish a single hop of a nailed-up 
-- ATM Bearer Service (ABS) connection. By linking together two 
-- Nrps within a module, the associated connections are configured to 
-- relay ATM cells to one another. The Nrp component requires 
-- exclusive use of its parent Vcc or Vpc and cannot co-exist with other 
-- ATM service components (such as Nep, Test, and Loop).

mscAtmIfVccNrp OBJECT IDENTIFIER ::= { mscAtmIfVcc 4 }



mscAtmIfVccNrpRowStatusTable OBJECT-TYPE
   SYNTAX     SEQUENCE OF MscAtmIfVccNrpRowStatusEntry
   ACCESS     not-accessible
   STATUS     mandatory
   DESCRIPTION
     "This entry controls the addition and deletion of 
      mscAtmIfVccNrp components."
::= { mscAtmIfVccNrp 1 }

mscAtmIfVccNrpRowStatusEntry OBJECT-TYPE
   SYNTAX     MscAtmIfVccNrpRowStatusEntry
   ACCESS     not-accessible
   STATUS     mandatory
   DESCRIPTION
     "A single entry in the table represents a single 
      mscAtmIfVccNrp component."
   INDEX {
      mscAtmIfIndex,
      mscAtmIfVccIndex,
      mscAtmIfVccNrpIndex }
::= { mscAtmIfVccNrpRowStatusTable 1 }

MscAtmIfVccNrpRowStatusEntry ::= SEQUENCE {
   mscAtmIfVccNrpRowStatus
      RowStatus,
   mscAtmIfVccNrpComponentName
      DisplayString,
   mscAtmIfVccNrpStorageType
      StorageType,
   mscAtmIfVccNrpIndex
      NonReplicated }

mscAtmIfVccNrpRowStatus OBJECT-TYPE
   SYNTAX     RowStatus 
   ACCESS     read-write
   STATUS     mandatory
   DESCRIPTION
     "This variable is used as the basis for SNMP naming of
      mscAtmIfVccNrp components.
      These components can be added and deleted."
::= { mscAtmIfVccNrpRowStatusEntry 1 }

mscAtmIfVccNrpComponentName OBJECT-TYPE
   SYNTAX     DisplayString 
   ACCESS     read-only
   STATUS     mandatory
   DESCRIPTION
     "This variable provides the component's string name for
      use with the ASCII Console Interface"
::= { mscAtmIfVccNrpRowStatusEntry 2 }

mscAtmIfVccNrpStorageType OBJECT-TYPE
   SYNTAX     StorageType 
   ACCESS     read-only
   STATUS     mandatory
   DESCRIPTION
     "This variable represents the storage type value for the
      mscAtmIfVccNrp tables."
::= { mscAtmIfVccNrpRowStatusEntry 4 }

mscAtmIfVccNrpIndex OBJECT-TYPE
   SYNTAX     NonReplicated 
   ACCESS     not-accessible
   STATUS     mandatory
   DESCRIPTION
     "This variable represents the index for the mscAtmIfVccNrp tables."
::= { mscAtmIfVccNrpRowStatusEntry 10 }

mscAtmIfVccNrpProvTable OBJECT-TYPE
   SYNTAX     SEQUENCE OF MscAtmIfVccNrpProvEntry
   ACCESS     not-accessible
   STATUS     mandatory
   DESCRIPTION
     "This group contains the provisionable attributes for the Nrp 
      component."
::= { mscAtmIfVccNrp 100 }

mscAtmIfVccNrpProvEntry OBJECT-TYPE
   SYNTAX     MscAtmIfVccNrpProvEntry
   ACCESS     not-accessible
   STATUS     mandatory
   DESCRIPTION
     "An entry in the mscAtmIfVccNrpProvTable."
   INDEX {
      mscAtmIfIndex,
      mscAtmIfVccIndex,
      mscAtmIfVccNrpIndex }
::= { mscAtmIfVccNrpProvTable 1 }

MscAtmIfVccNrpProvEntry ::= SEQUENCE {
   mscAtmIfVccNrpNextHop
      Link,
   mscAtmIfVccNrpConnectionPointType
      INTEGER,
   mscAtmIfVccNrpOamSegmentBoundary
      INTEGER,
   mscAtmIfVccNrpTxAal5PartialPacketDiscard
      INTEGER,
   mscAtmIfVccNrpRxAal5PartialPacketDiscard
      INTEGER,
   mscAtmIfVccNrpBandwidthElastic
      INTEGER,
   mscAtmIfVccNrpOverrideHoldingPriority
      INTEGER }

mscAtmIfVccNrpNextHop OBJECT-TYPE
   SYNTAX     Link 
   ACCESS     read-write
   STATUS     mandatory
   DESCRIPTION
     "This attribute specifies the Nrp component with which this Nrp is 
      associated. A sample value is AtmIf/31 Vcc/0.32 Nrp."
::= { mscAtmIfVccNrpProvEntry 10 }

mscAtmIfVccNrpConnectionPointType OBJECT-TYPE
   SYNTAX     INTEGER  {
                 segmentEndPoint(1),
                 connectingPoint(2),
                 autoConfigure(4) }
   ACCESS     read-write
   STATUS     obsolete
   DESCRIPTION
     "This attribute specifies the connection point type desired for a Nrp 
      component. The actual connection point type value is visible in the 
      parent component's connectionPointType attribute. 
      
      The desired connection point type can be specified directly as a 
      segmentEndPoint or connectingPoint. If autoConfigure is 
      specified, the switch will select the connection point type based on 
      the type attribute of the associated AtmIf, choosing 
      segmentEndPoint for a UNI-type ATM interface and 
      connectingPoint for a PPI-type ATM interface.
      
      It is obsoleted. The value is mapped into oamSegmentBoundary 
      attribute. segmentEndPoint is mapped into yes. connectingPoint is 
      mapped into no. autoConfigure is mapped into sameAsInterface."
   DEFVAL     { autoConfigure }
::= { mscAtmIfVccNrpProvEntry 20 }

mscAtmIfVccNrpOamSegmentBoundary OBJECT-TYPE
   SYNTAX     INTEGER  {
                 no(0),
                 yes(1),
                 sameAsInterface(2) }
   ACCESS     read-write
   STATUS     mandatory
   DESCRIPTION
     "This attribute specifies the OAM segment boundary desired for a 
      Nrp component. It affects the connection point type value visible in 
      the parent component's connectionPointType attribute. 
      
      The desired OAM segment boundary can be specified directly as 
      yes, no or sameAsInterface. If sameAsInterface is specified, the 
      OAM segment boundary is same as the oamSegmentBoundary 
      attribute of the associated AtmIf and the switch will set the 
      connectionPointType, choosing segmentEndPoint for a segment-
      boundary ATM interface and connectingPoint for a non-segment-
      boundary ATM interface."
   DEFVAL     { sameAsInterface }
::= { mscAtmIfVccNrpProvEntry 30 }

mscAtmIfVccNrpTxAal5PartialPacketDiscard OBJECT-TYPE
   SYNTAX     INTEGER  {
                 disabled(0),
                 enabled(1) }
   ACCESS     read-write
   STATUS     obsolete
   DESCRIPTION
     "This attribute is obsolete in P4.2 and has been migrated under Vcd 
      (Vpd) component. 
      
      This attribute specifies whether the AAL5 Partial Packet Discard 
      (PPD) feature has been enabled or disabled on the Nrp in the 
      transmit direction. This feature allows the NRP to discard the 
      remainder of a cell-forwarded AAL5 frame if a cell of this frame 
      has been discarded due to congestion. This increases the 'goodput' 
      of the link, since cells which are only going to be discarded by the 
      AAL5 reassembly are not transmitted.
      
      When this attribute is set to enabled, the PPD feature is applied in 
      the transmit direction. It should only be enabled for connections 
      whose end points are performing AAL5 segmentation and 
      reassembly. When this attribute is set to disabled, the PPD feature is 
      not applied to traffic for this connection in the transmit direction. 
      Note that specifying enabled for a non-AAL5 connection will cause 
      all traffic to be discarded once congestion is encountered."
   DEFVAL     { disabled }
::= { mscAtmIfVccNrpProvEntry 31 }

mscAtmIfVccNrpRxAal5PartialPacketDiscard OBJECT-TYPE
   SYNTAX     INTEGER  {
                 disabled(0),
                 enabled(1),
                 sameAsTx(2) }
   ACCESS     read-write
   STATUS     obsolete
   DESCRIPTION
     "This attribute is obsolete in P4.2 and has been migrated under Vcd 
      (Vpd) component.
      
      This attribute specifies whether the AAL5 Partial Packet Discard 
      (PPD) feature has been enabled or disabled on the Nrp in the 
      receive direction. This feature allows the NRP to discard the 
      remainder of a cell-forwarded AAL5 frame if a cell of this frame 
      has been discarded due to congestion or usage parameter control 
      (UPC). This increases the 'goodput' of the link, since cells which 
      are only going to be discarded by the AAL5 reassembly are not 
      transmitted.
      
      When this attribute is set to enabled, the PPD feature is applied in 
      the receive direction. It should only be enabled for connections 
      whose end points are performing AAL5 segmentation and 
      reassembly. When this attribute is set to disabled, the PPD feature is 
      not applied to traffic for this connection in the receive direction. 
      When this attribute is set to sameAsTx, the PPD feature for traffic 
      in the receive direction will be configured the same way as it is in 
      the transmit direction. 
      Note that specifying enabled for a non-AAL5 connection will cause 
      all traffic to be discarded once congestion is encountered."
   DEFVAL     { sameAsTx }
::= { mscAtmIfVccNrpProvEntry 32 }

mscAtmIfVccNrpBandwidthElastic OBJECT-TYPE
   SYNTAX     INTEGER  {
                 no(0),
                 yes(1) }
   ACCESS     read-write
   STATUS     mandatory
   DESCRIPTION
     "This attribute is only of importance for connections which are 
      carried on a link with a variable bandwidth. For example, the 
      bandwidth may be reduced in the event that one or more physical 
      links in the IMA group fail, such that the originally requested 
      bandwidth cannot be maintained. This attribute shows whether the 
      application running on this connection can continue to operate if the 
      bandwidth is reduced. If the bandwidth is reduced, the amount by 
      which it is reduced will be displayed in the bandwidthReduction 
      attribute. 
      
      A value of yes, indicates that this connection is elastic, and the 
      bandwidth may be reduced but the connection will not be released. 
      Currently, this attribute should only be set to yes for situations 
      where this Nrp is functioning as a loopback on one side of an IMA 
      link. There are no other situations where this setting is valid.
      
      A value of no indicates that the bandwidth for this connection will 
      not be reduced in the event of link bandwidth reduction. However, 
      this connection may be released based on its holdingPriority."
   DEFVAL     { no }
::= { mscAtmIfVccNrpProvEntry 33 }

mscAtmIfVccNrpOverrideHoldingPriority OBJECT-TYPE
   SYNTAX     INTEGER  {
                 n0(0),
                 n1(1),
                 n2(2),
                 n3(3),
                 n4(4),
                 noOverride(6) }
   ACCESS     read-write
   STATUS     mandatory
   DESCRIPTION
     "This attribute specifies the holding priority of this connection. 
      Holding priority is used when there is an IMA group where some 
      physical links have failed. Holding priority determines the order in 
      which connections are released. 4 is the lowest holding priority and 
      is released first. 0 is a higher priority and is released last. The value 
      specified in this attribute will override whatever holdingPriority that 
      has been provisioned at the Vcd (or Vpd). If the value is left at the 
      default of noOverride, the holdingPriority provisioned at the Vcd 
      (or Vpd) will be used."
   DEFVAL     { noOverride }
::= { mscAtmIfVccNrpProvEntry 34 }


-- AtmIf/n Vcc/vpi.vci Mnrp
-- This component is used to establish a root of a multicast nailed-up 
-- ATM Bearer Service (ABS) connection. By linking a Mnrp to a 
-- Nrp, the associated connections are configured to relay ATM cells 
-- from Mnrp to Nrp. The Mnrp component requires exclusive use of 
-- its parent Vcc or Vpc and cannot co-exist with other ATM service 
-- components (such as Nep, Test, Nrp and Loop). This component is 
-- supported only on 4pOC3SmIrAtm and 4pOC3MmAtm cards.This 
-- component is not supported under Vpt Vcc and Vpt Vpc.

mscAtmIfVccMnrp OBJECT IDENTIFIER ::= { mscAtmIfVcc 13 }



mscAtmIfVccMnrpRowStatusTable OBJECT-TYPE
   SYNTAX     SEQUENCE OF MscAtmIfVccMnrpRowStatusEntry
   ACCESS     not-accessible
   STATUS     mandatory
   DESCRIPTION
     "This entry controls the addition and deletion of 
      mscAtmIfVccMnrp components."
::= { mscAtmIfVccMnrp 1 }

mscAtmIfVccMnrpRowStatusEntry OBJECT-TYPE
   SYNTAX     MscAtmIfVccMnrpRowStatusEntry
   ACCESS     not-accessible
   STATUS     mandatory
   DESCRIPTION
     "A single entry in the table represents a single 
      mscAtmIfVccMnrp component."
   INDEX {
      mscAtmIfIndex,
      mscAtmIfVccIndex,
      mscAtmIfVccMnrpIndex }
::= { mscAtmIfVccMnrpRowStatusTable 1 }

MscAtmIfVccMnrpRowStatusEntry ::= SEQUENCE {
   mscAtmIfVccMnrpRowStatus
      RowStatus,
   mscAtmIfVccMnrpComponentName
      DisplayString,
   mscAtmIfVccMnrpStorageType
      StorageType,
   mscAtmIfVccMnrpIndex
      NonReplicated }

mscAtmIfVccMnrpRowStatus OBJECT-TYPE
   SYNTAX     RowStatus 
   ACCESS     read-write
   STATUS     mandatory
   DESCRIPTION
     "This variable is used as the basis for SNMP naming of
      mscAtmIfVccMnrp components.
      These components can be added and deleted."
::= { mscAtmIfVccMnrpRowStatusEntry 1 }

mscAtmIfVccMnrpComponentName OBJECT-TYPE
   SYNTAX     DisplayString 
   ACCESS     read-only
   STATUS     mandatory
   DESCRIPTION
     "This variable provides the component's string name for
      use with the ASCII Console Interface"
::= { mscAtmIfVccMnrpRowStatusEntry 2 }

mscAtmIfVccMnrpStorageType OBJECT-TYPE
   SYNTAX     StorageType 
   ACCESS     read-only
   STATUS     mandatory
   DESCRIPTION
     "This variable represents the storage type value for the
      mscAtmIfVccMnrp tables."
::= { mscAtmIfVccMnrpRowStatusEntry 4 }

mscAtmIfVccMnrpIndex OBJECT-TYPE
   SYNTAX     NonReplicated 
   ACCESS     not-accessible
   STATUS     mandatory
   DESCRIPTION
     "This variable represents the index for the mscAtmIfVccMnrp tables."
::= { mscAtmIfVccMnrpRowStatusEntry 10 }

mscAtmIfVccMnrpProvTable OBJECT-TYPE
   SYNTAX     SEQUENCE OF MscAtmIfVccMnrpProvEntry
   ACCESS     not-accessible
   STATUS     mandatory
   DESCRIPTION
     "This group contains the provisionable attributes for the Mnrp 
      component."
::= { mscAtmIfVccMnrp 101 }

mscAtmIfVccMnrpProvEntry OBJECT-TYPE
   SYNTAX     MscAtmIfVccMnrpProvEntry
   ACCESS     not-accessible
   STATUS     mandatory
   DESCRIPTION
     "An entry in the mscAtmIfVccMnrpProvTable."
   INDEX {
      mscAtmIfIndex,
      mscAtmIfVccIndex,
      mscAtmIfVccMnrpIndex }
::= { mscAtmIfVccMnrpProvTable 1 }

MscAtmIfVccMnrpProvEntry ::= SEQUENCE {
   mscAtmIfVccMnrpOamSegmentBoundary
      INTEGER,
   mscAtmIfVccMnrpBandwidthElastic
      INTEGER,
   mscAtmIfVccMnrpOverrideHoldingPriority
      INTEGER }

mscAtmIfVccMnrpOamSegmentBoundary OBJECT-TYPE
   SYNTAX     INTEGER  {
                 no(0),
                 yes(1),
                 sameAsInterface(2) }
   ACCESS     read-write
   STATUS     mandatory
   DESCRIPTION
     "This attribute specifies the OAM segment boundary desired for a 
      Mnrp component. It affects the connection point type value visible 
      in the parent component's connectionPointType attribute. 
      The desired OAM segment boundary can be specified directly as 
      yes, no or sameAsInterface. If sameAsInterface is specified, the 
      OAM segment boundary is same as the oamSegmentBoundary 
      attribute of the associated AtmIf and the switch will set the 
      connectionPointType, choosing segmentEndPoint for a segment-
      boundary ATM interface and connectingPoint for a non-segment-
      boundary ATM interface."
   DEFVAL     { sameAsInterface }
::= { mscAtmIfVccMnrpProvEntry 30 }

mscAtmIfVccMnrpBandwidthElastic OBJECT-TYPE
   SYNTAX     INTEGER  {
                 no(0),
                 yes(1) }
   ACCESS     read-write
   STATUS     mandatory
   DESCRIPTION
     "This attribute is only of importance for connections which are 
      carried on a link with a variable bandwidth. For example, the 
      bandwidth may be reduced in the event that one or more physical 
      links in the IMA group fail, such that the originally requested 
      bandwidth cannot be maintained. This attribute shows whether the 
      application running on this connection can continue to operate if the 
      bandwidth is reduced. If the bandwidth is reduced, the amount by 
      which it is reduced will be displayed in the bandwidthReduction 
      attribute. 
      A value of yes, indicates that this connection is elastic, and the 
      bandwidth may be reduced but the connection will not be released. 
      Currently, this attribute should only be set to yes for situations 
      where this Mnrp is functioning as a loopback on one side of an IMA 
      link. There are no other situations where this setting is valid.
      A value of no indicates that the bandwidth for this connection will 
      not be reduced in the event of link bandwidth reduction. However, 
      this connection may be released based on its holdingPriority."
   DEFVAL     { no }
::= { mscAtmIfVccMnrpProvEntry 33 }

mscAtmIfVccMnrpOverrideHoldingPriority OBJECT-TYPE
   SYNTAX     INTEGER  {
                 n0(0),
                 n1(1),
                 n2(2),
                 n3(3),
                 n4(4),
                 noOverride(6) }
   ACCESS     read-write
   STATUS     mandatory
   DESCRIPTION
     "This attribute specifies the holding priority of this connection. 
      Holding priority is used when there is an IMA group where some 
      physical links have failed. Holding priority determines the order in 
      which connections are released. 4 is the lowest holding priority and 
      is released first. 0 is a higher priority and is released last. The value 
      specified in this attribute will override whatever holdingPriority that 
      has been provisioned at the Vcd (or Vpd). If the value is left at the 
      default of noOverride, the holdingPriority provisioned at the Vcd 
      (or Vpd) will be used."
   DEFVAL     { noOverride }
::= { mscAtmIfVccMnrpProvEntry 34 }

mscAtmIfVccMnrpNextHopsTable OBJECT-TYPE
   SYNTAX     SEQUENCE OF MscAtmIfVccMnrpNextHopsEntry
   ACCESS     not-accessible
   STATUS     mandatory
   DESCRIPTION
     "This attribute specifies the list of Nrp components with which this 
      Mnrp is associated. A sample value is AtmIf/31 Vcc/0.32 Nrp. This 
      attribute must be provisioned with at least one Nrp component 
      under a compatible connection type."
::= { mscAtmIfVccMnrp 658 }

mscAtmIfVccMnrpNextHopsEntry OBJECT-TYPE
   SYNTAX     MscAtmIfVccMnrpNextHopsEntry
   ACCESS     not-accessible
   STATUS     mandatory
   DESCRIPTION
     "An entry in the mscAtmIfVccMnrpNextHopsTable."
   INDEX {
      mscAtmIfIndex,
      mscAtmIfVccIndex,
      mscAtmIfVccMnrpIndex,
      mscAtmIfVccMnrpNextHopsValue }
::= { mscAtmIfVccMnrpNextHopsTable 1 }

MscAtmIfVccMnrpNextHopsEntry ::= SEQUENCE {
   mscAtmIfVccMnrpNextHopsValue
      Link,
   mscAtmIfVccMnrpNextHopsRowStatus
      RowStatus }

mscAtmIfVccMnrpNextHopsValue OBJECT-TYPE
   SYNTAX     Link 
   ACCESS     read-write
   STATUS     mandatory
   DESCRIPTION
     "This variable represents both the value and the index for the
      mscAtmIfVccMnrpNextHopsTable."
::= { mscAtmIfVccMnrpNextHopsEntry 1 }

mscAtmIfVccMnrpNextHopsRowStatus OBJECT-TYPE
   SYNTAX     RowStatus 
   ACCESS     write-only
   STATUS     mandatory
   DESCRIPTION
     "This variable is used to control the addition and deletion 
      of individual values of the mscAtmIfVccMnrpNextHopsTable."
::= { mscAtmIfVccMnrpNextHopsEntry 2 }


-- AtmIf/n Vcc/vpi.vci Nrp
-- This component is used to establish a single hop of a nailed-up 
-- ATM Bearer Service (ABS) connection. By linking together two 
-- Nrps within a module, the associated connections are configured to 
-- relay ATM cells to one another. The Nrp component requires 
-- exclusive use of its parent Vcc or Vpc and cannot co-exist with other 
-- ATM service components (such as Nep, Test, and Loop).

mscAtmIfVptVccNrp OBJECT IDENTIFIER ::= { mscAtmIfVptVcc 4 }



mscAtmIfVptVccNrpRowStatusTable OBJECT-TYPE
   SYNTAX     SEQUENCE OF MscAtmIfVptVccNrpRowStatusEntry
   ACCESS     not-accessible
   STATUS     mandatory
   DESCRIPTION
     "This entry controls the addition and deletion of 
      mscAtmIfVptVccNrp components."
::= { mscAtmIfVptVccNrp 1 }

mscAtmIfVptVccNrpRowStatusEntry OBJECT-TYPE
   SYNTAX     MscAtmIfVptVccNrpRowStatusEntry
   ACCESS     not-accessible
   STATUS     mandatory
   DESCRIPTION
     "A single entry in the table represents a single 
      mscAtmIfVptVccNrp component."
   INDEX {
      mscAtmIfIndex,
      mscAtmIfVptIndex,
      mscAtmIfVptVccIndex,
      mscAtmIfVptVccNrpIndex }
::= { mscAtmIfVptVccNrpRowStatusTable 1 }

MscAtmIfVptVccNrpRowStatusEntry ::= SEQUENCE {
   mscAtmIfVptVccNrpRowStatus
      RowStatus,
   mscAtmIfVptVccNrpComponentName
      DisplayString,
   mscAtmIfVptVccNrpStorageType
      StorageType,
   mscAtmIfVptVccNrpIndex
      NonReplicated }

mscAtmIfVptVccNrpRowStatus OBJECT-TYPE
   SYNTAX     RowStatus 
   ACCESS     read-write
   STATUS     mandatory
   DESCRIPTION
     "This variable is used as the basis for SNMP naming of
      mscAtmIfVptVccNrp components.
      These components can be added and deleted."
::= { mscAtmIfVptVccNrpRowStatusEntry 1 }

mscAtmIfVptVccNrpComponentName OBJECT-TYPE
   SYNTAX     DisplayString 
   ACCESS     read-only
   STATUS     mandatory
   DESCRIPTION
     "This variable provides the component's string name for
      use with the ASCII Console Interface"
::= { mscAtmIfVptVccNrpRowStatusEntry 2 }

mscAtmIfVptVccNrpStorageType OBJECT-TYPE
   SYNTAX     StorageType 
   ACCESS     read-only
   STATUS     mandatory
   DESCRIPTION
     "This variable represents the storage type value for the
      mscAtmIfVptVccNrp tables."
::= { mscAtmIfVptVccNrpRowStatusEntry 4 }

mscAtmIfVptVccNrpIndex OBJECT-TYPE
   SYNTAX     NonReplicated 
   ACCESS     not-accessible
   STATUS     mandatory
   DESCRIPTION
     "This variable represents the index for the mscAtmIfVptVccNrp tables."
::= { mscAtmIfVptVccNrpRowStatusEntry 10 }

mscAtmIfVptVccNrpProvTable OBJECT-TYPE
   SYNTAX     SEQUENCE OF MscAtmIfVptVccNrpProvEntry
   ACCESS     not-accessible
   STATUS     mandatory
   DESCRIPTION
     "This group contains the provisionable attributes for the Nrp 
      component."
::= { mscAtmIfVptVccNrp 100 }

mscAtmIfVptVccNrpProvEntry OBJECT-TYPE
   SYNTAX     MscAtmIfVptVccNrpProvEntry
   ACCESS     not-accessible
   STATUS     mandatory
   DESCRIPTION
     "An entry in the mscAtmIfVptVccNrpProvTable."
   INDEX {
      mscAtmIfIndex,
      mscAtmIfVptIndex,
      mscAtmIfVptVccIndex,
      mscAtmIfVptVccNrpIndex }
::= { mscAtmIfVptVccNrpProvTable 1 }

MscAtmIfVptVccNrpProvEntry ::= SEQUENCE {
   mscAtmIfVptVccNrpNextHop
      Link,
   mscAtmIfVptVccNrpConnectionPointType
      INTEGER,
   mscAtmIfVptVccNrpOamSegmentBoundary
      INTEGER,
   mscAtmIfVptVccNrpTxAal5PartialPacketDiscard
      INTEGER,
   mscAtmIfVptVccNrpRxAal5PartialPacketDiscard
      INTEGER,
   mscAtmIfVptVccNrpBandwidthElastic
      INTEGER,
   mscAtmIfVptVccNrpOverrideHoldingPriority
      INTEGER }

mscAtmIfVptVccNrpNextHop OBJECT-TYPE
   SYNTAX     Link 
   ACCESS     read-write
   STATUS     mandatory
   DESCRIPTION
     "This attribute specifies the Nrp component with which this Nrp is 
      associated. A sample value is AtmIf/31 Vcc/0.32 Nrp."
::= { mscAtmIfVptVccNrpProvEntry 10 }

mscAtmIfVptVccNrpConnectionPointType OBJECT-TYPE
   SYNTAX     INTEGER  {
                 segmentEndPoint(1),
                 connectingPoint(2),
                 autoConfigure(4) }
   ACCESS     read-write
   STATUS     obsolete
   DESCRIPTION
     "This attribute specifies the connection point type desired for a Nrp 
      component. The actual connection point type value is visible in the 
      parent component's connectionPointType attribute. 
      
      The desired connection point type can be specified directly as a 
      segmentEndPoint or connectingPoint. If autoConfigure is 
      specified, the switch will select the connection point type based on 
      the type attribute of the associated AtmIf, choosing 
      segmentEndPoint for a UNI-type ATM interface and 
      connectingPoint for a PPI-type ATM interface.
      
      It is obsoleted. The value is mapped into oamSegmentBoundary 
      attribute. segmentEndPoint is mapped into yes. connectingPoint is 
      mapped into no. autoConfigure is mapped into sameAsInterface."
   DEFVAL     { autoConfigure }
::= { mscAtmIfVptVccNrpProvEntry 20 }

mscAtmIfVptVccNrpOamSegmentBoundary OBJECT-TYPE
   SYNTAX     INTEGER  {
                 no(0),
                 yes(1),
                 sameAsInterface(2) }
   ACCESS     read-write
   STATUS     mandatory
   DESCRIPTION
     "This attribute specifies the OAM segment boundary desired for a 
      Nrp component. It affects the connection point type value visible in 
      the parent component's connectionPointType attribute. 
      
      The desired OAM segment boundary can be specified directly as 
      yes, no or sameAsInterface. If sameAsInterface is specified, the 
      OAM segment boundary is same as the oamSegmentBoundary 
      attribute of the associated AtmIf and the switch will set the 
      connectionPointType, choosing segmentEndPoint for a segment-
      boundary ATM interface and connectingPoint for a non-segment-
      boundary ATM interface."
   DEFVAL     { sameAsInterface }
::= { mscAtmIfVptVccNrpProvEntry 30 }

mscAtmIfVptVccNrpTxAal5PartialPacketDiscard OBJECT-TYPE
   SYNTAX     INTEGER  {
                 disabled(0),
                 enabled(1) }
   ACCESS     read-write
   STATUS     obsolete
   DESCRIPTION
     "This attribute is obsolete in P4.2 and has been migrated under Vcd 
      (Vpd) component. 
      
      This attribute specifies whether the AAL5 Partial Packet Discard 
      (PPD) feature has been enabled or disabled on the Nrp in the 
      transmit direction. This feature allows the NRP to discard the 
      remainder of a cell-forwarded AAL5 frame if a cell of this frame 
      has been discarded due to congestion. This increases the 'goodput' 
      of the link, since cells which are only going to be discarded by the 
      AAL5 reassembly are not transmitted.
      
      When this attribute is set to enabled, the PPD feature is applied in 
      the transmit direction. It should only be enabled for connections 
      whose end points are performing AAL5 segmentation and 
      reassembly. When this attribute is set to disabled, the PPD feature is 
      not applied to traffic for this connection in the transmit direction. 
      Note that specifying enabled for a non-AAL5 connection will cause 
      all traffic to be discarded once congestion is encountered."
   DEFVAL     { disabled }
::= { mscAtmIfVptVccNrpProvEntry 31 }

mscAtmIfVptVccNrpRxAal5PartialPacketDiscard OBJECT-TYPE
   SYNTAX     INTEGER  {
                 disabled(0),
                 enabled(1),
                 sameAsTx(2) }
   ACCESS     read-write
   STATUS     obsolete
   DESCRIPTION
     "This attribute is obsolete in P4.2 and has been migrated under Vcd 
      (Vpd) component.
      
      This attribute specifies whether the AAL5 Partial Packet Discard 
      (PPD) feature has been enabled or disabled on the Nrp in the 
      receive direction. This feature allows the NRP to discard the 
      remainder of a cell-forwarded AAL5 frame if a cell of this frame 
      has been discarded due to congestion or usage parameter control 
      (UPC). This increases the 'goodput' of the link, since cells which 
      are only going to be discarded by the AAL5 reassembly are not 
      transmitted.
      
      When this attribute is set to enabled, the PPD feature is applied in 
      the receive direction. It should only be enabled for connections 
      whose end points are performing AAL5 segmentation and 
      reassembly. When this attribute is set to disabled, the PPD feature is 
      not applied to traffic for this connection in the receive direction. 
      When this attribute is set to sameAsTx, the PPD feature for traffic 
      in the receive direction will be configured the same way as it is in 
      the transmit direction. 
      Note that specifying enabled for a non-AAL5 connection will cause 
      all traffic to be discarded once congestion is encountered."
   DEFVAL     { sameAsTx }
::= { mscAtmIfVptVccNrpProvEntry 32 }

mscAtmIfVptVccNrpBandwidthElastic OBJECT-TYPE
   SYNTAX     INTEGER  {
                 no(0),
                 yes(1) }
   ACCESS     read-write
   STATUS     mandatory
   DESCRIPTION
     "This attribute is only of importance for connections which are 
      carried on a link with a variable bandwidth. For example, the 
      bandwidth may be reduced in the event that one or more physical 
      links in the IMA group fail, such that the originally requested 
      bandwidth cannot be maintained. This attribute shows whether the 
      application running on this connection can continue to operate if the 
      bandwidth is reduced. If the bandwidth is reduced, the amount by 
      which it is reduced will be displayed in the bandwidthReduction 
      attribute. 
      
      A value of yes, indicates that this connection is elastic, and the 
      bandwidth may be reduced but the connection will not be released. 
      Currently, this attribute should only be set to yes for situations 
      where this Nrp is functioning as a loopback on one side of an IMA 
      link. There are no other situations where this setting is valid.
      
      A value of no indicates that the bandwidth for this connection will 
      not be reduced in the event of link bandwidth reduction. However, 
      this connection may be released based on its holdingPriority."
   DEFVAL     { no }
::= { mscAtmIfVptVccNrpProvEntry 33 }

mscAtmIfVptVccNrpOverrideHoldingPriority OBJECT-TYPE
   SYNTAX     INTEGER  {
                 n0(0),
                 n1(1),
                 n2(2),
                 n3(3),
                 n4(4),
                 noOverride(6) }
   ACCESS     read-write
   STATUS     mandatory
   DESCRIPTION
     "This attribute specifies the holding priority of this connection. 
      Holding priority is used when there is an IMA group where some 
      physical links have failed. Holding priority determines the order in 
      which connections are released. 4 is the lowest holding priority and 
      is released first. 0 is a higher priority and is released last. The value 
      specified in this attribute will override whatever holdingPriority that 
      has been provisioned at the Vcd (or Vpd). If the value is left at the 
      default of noOverride, the holdingPriority provisioned at the Vcd 
      (or Vpd) will be used."
   DEFVAL     { noOverride }
::= { mscAtmIfVptVccNrpProvEntry 34 }


-- AtmIf/n Vcc/vpi.vci Mnrp
-- This component is used to establish a root of a multicast nailed-up 
-- ATM Bearer Service (ABS) connection. By linking a Mnrp to a 
-- Nrp, the associated connections are configured to relay ATM cells 
-- from Mnrp to Nrp. The Mnrp component requires exclusive use of 
-- its parent Vcc or Vpc and cannot co-exist with other ATM service 
-- components (such as Nep, Test, Nrp and Loop). This component is 
-- supported only on 4pOC3SmIrAtm and 4pOC3MmAtm cards.This 
-- component is not supported under Vpt Vcc and Vpt Vpc.

mscAtmIfVptVccMnrp OBJECT IDENTIFIER ::= { mscAtmIfVptVcc 13 }



mscAtmIfVptVccMnrpRowStatusTable OBJECT-TYPE
   SYNTAX     SEQUENCE OF MscAtmIfVptVccMnrpRowStatusEntry
   ACCESS     not-accessible
   STATUS     mandatory
   DESCRIPTION
     "This entry controls the addition and deletion of 
      mscAtmIfVptVccMnrp components."
::= { mscAtmIfVptVccMnrp 1 }

mscAtmIfVptVccMnrpRowStatusEntry OBJECT-TYPE
   SYNTAX     MscAtmIfVptVccMnrpRowStatusEntry
   ACCESS     not-accessible
   STATUS     mandatory
   DESCRIPTION
     "A single entry in the table represents a single 
      mscAtmIfVptVccMnrp component."
   INDEX {
      mscAtmIfIndex,
      mscAtmIfVptIndex,
      mscAtmIfVptVccIndex,
      mscAtmIfVptVccMnrpIndex }
::= { mscAtmIfVptVccMnrpRowStatusTable 1 }

MscAtmIfVptVccMnrpRowStatusEntry ::= SEQUENCE {
   mscAtmIfVptVccMnrpRowStatus
      RowStatus,
   mscAtmIfVptVccMnrpComponentName
      DisplayString,
   mscAtmIfVptVccMnrpStorageType
      StorageType,
   mscAtmIfVptVccMnrpIndex
      NonReplicated }

mscAtmIfVptVccMnrpRowStatus OBJECT-TYPE
   SYNTAX     RowStatus 
   ACCESS     read-write
   STATUS     mandatory
   DESCRIPTION
     "This variable is used as the basis for SNMP naming of
      mscAtmIfVptVccMnrp components.
      These components can be added and deleted."
::= { mscAtmIfVptVccMnrpRowStatusEntry 1 }

mscAtmIfVptVccMnrpComponentName OBJECT-TYPE
   SYNTAX     DisplayString 
   ACCESS     read-only
   STATUS     mandatory
   DESCRIPTION
     "This variable provides the component's string name for
      use with the ASCII Console Interface"
::= { mscAtmIfVptVccMnrpRowStatusEntry 2 }

mscAtmIfVptVccMnrpStorageType OBJECT-TYPE
   SYNTAX     StorageType 
   ACCESS     read-only
   STATUS     mandatory
   DESCRIPTION
     "This variable represents the storage type value for the
      mscAtmIfVptVccMnrp tables."
::= { mscAtmIfVptVccMnrpRowStatusEntry 4 }

mscAtmIfVptVccMnrpIndex OBJECT-TYPE
   SYNTAX     NonReplicated 
   ACCESS     not-accessible
   STATUS     mandatory
   DESCRIPTION
     "This variable represents the index for the mscAtmIfVptVccMnrp tables."
::= { mscAtmIfVptVccMnrpRowStatusEntry 10 }

mscAtmIfVptVccMnrpProvTable OBJECT-TYPE
   SYNTAX     SEQUENCE OF MscAtmIfVptVccMnrpProvEntry
   ACCESS     not-accessible
   STATUS     mandatory
   DESCRIPTION
     "This group contains the provisionable attributes for the Mnrp 
      component."
::= { mscAtmIfVptVccMnrp 101 }

mscAtmIfVptVccMnrpProvEntry OBJECT-TYPE
   SYNTAX     MscAtmIfVptVccMnrpProvEntry
   ACCESS     not-accessible
   STATUS     mandatory
   DESCRIPTION
     "An entry in the mscAtmIfVptVccMnrpProvTable."
   INDEX {
      mscAtmIfIndex,
      mscAtmIfVptIndex,
      mscAtmIfVptVccIndex,
      mscAtmIfVptVccMnrpIndex }
::= { mscAtmIfVptVccMnrpProvTable 1 }

MscAtmIfVptVccMnrpProvEntry ::= SEQUENCE {
   mscAtmIfVptVccMnrpOamSegmentBoundary
      INTEGER,
   mscAtmIfVptVccMnrpBandwidthElastic
      INTEGER,
   mscAtmIfVptVccMnrpOverrideHoldingPriority
      INTEGER }

mscAtmIfVptVccMnrpOamSegmentBoundary OBJECT-TYPE
   SYNTAX     INTEGER  {
                 no(0),
                 yes(1),
                 sameAsInterface(2) }
   ACCESS     read-write
   STATUS     mandatory
   DESCRIPTION
     "This attribute specifies the OAM segment boundary desired for a 
      Mnrp component. It affects the connection point type value visible 
      in the parent component's connectionPointType attribute. 
      The desired OAM segment boundary can be specified directly as 
      yes, no or sameAsInterface. If sameAsInterface is specified, the 
      OAM segment boundary is same as the oamSegmentBoundary 
      attribute of the associated AtmIf and the switch will set the 
      connectionPointType, choosing segmentEndPoint for a segment-
      boundary ATM interface and connectingPoint for a non-segment-
      boundary ATM interface."
   DEFVAL     { sameAsInterface }
::= { mscAtmIfVptVccMnrpProvEntry 30 }

mscAtmIfVptVccMnrpBandwidthElastic OBJECT-TYPE
   SYNTAX     INTEGER  {
                 no(0),
                 yes(1) }
   ACCESS     read-write
   STATUS     mandatory
   DESCRIPTION
     "This attribute is only of importance for connections which are 
      carried on a link with a variable bandwidth. For example, the 
      bandwidth may be reduced in the event that one or more physical 
      links in the IMA group fail, such that the originally requested 
      bandwidth cannot be maintained. This attribute shows whether the 
      application running on this connection can continue to operate if the 
      bandwidth is reduced. If the bandwidth is reduced, the amount by 
      which it is reduced will be displayed in the bandwidthReduction 
      attribute. 
      A value of yes, indicates that this connection is elastic, and the 
      bandwidth may be reduced but the connection will not be released. 
      Currently, this attribute should only be set to yes for situations 
      where this Mnrp is functioning as a loopback on one side of an IMA 
      link. There are no other situations where this setting is valid.
      A value of no indicates that the bandwidth for this connection will 
      not be reduced in the event of link bandwidth reduction. However, 
      this connection may be released based on its holdingPriority."
   DEFVAL     { no }
::= { mscAtmIfVptVccMnrpProvEntry 33 }

mscAtmIfVptVccMnrpOverrideHoldingPriority OBJECT-TYPE
   SYNTAX     INTEGER  {
                 n0(0),
                 n1(1),
                 n2(2),
                 n3(3),
                 n4(4),
                 noOverride(6) }
   ACCESS     read-write
   STATUS     mandatory
   DESCRIPTION
     "This attribute specifies the holding priority of this connection. 
      Holding priority is used when there is an IMA group where some 
      physical links have failed. Holding priority determines the order in 
      which connections are released. 4 is the lowest holding priority and 
      is released first. 0 is a higher priority and is released last. The value 
      specified in this attribute will override whatever holdingPriority that 
      has been provisioned at the Vcd (or Vpd). If the value is left at the 
      default of noOverride, the holdingPriority provisioned at the Vcd 
      (or Vpd) will be used."
   DEFVAL     { noOverride }
::= { mscAtmIfVptVccMnrpProvEntry 34 }

mscAtmIfVptVccMnrpNextHopsTable OBJECT-TYPE
   SYNTAX     SEQUENCE OF MscAtmIfVptVccMnrpNextHopsEntry
   ACCESS     not-accessible
   STATUS     mandatory
   DESCRIPTION
     "This attribute specifies the list of Nrp components with which this 
      Mnrp is associated. A sample value is AtmIf/31 Vcc/0.32 Nrp. This 
      attribute must be provisioned with at least one Nrp component 
      under a compatible connection type."
::= { mscAtmIfVptVccMnrp 658 }

mscAtmIfVptVccMnrpNextHopsEntry OBJECT-TYPE
   SYNTAX     MscAtmIfVptVccMnrpNextHopsEntry
   ACCESS     not-accessible
   STATUS     mandatory
   DESCRIPTION
     "An entry in the mscAtmIfVptVccMnrpNextHopsTable."
   INDEX {
      mscAtmIfIndex,
      mscAtmIfVptIndex,
      mscAtmIfVptVccIndex,
      mscAtmIfVptVccMnrpIndex,
      mscAtmIfVptVccMnrpNextHopsValue }
::= { mscAtmIfVptVccMnrpNextHopsTable 1 }

MscAtmIfVptVccMnrpNextHopsEntry ::= SEQUENCE {
   mscAtmIfVptVccMnrpNextHopsValue
      Link,
   mscAtmIfVptVccMnrpNextHopsRowStatus
      RowStatus }

mscAtmIfVptVccMnrpNextHopsValue OBJECT-TYPE
   SYNTAX     Link 
   ACCESS     read-write
   STATUS     mandatory
   DESCRIPTION
     "This variable represents both the value and the index for the
      mscAtmIfVptVccMnrpNextHopsTable."
::= { mscAtmIfVptVccMnrpNextHopsEntry 1 }

mscAtmIfVptVccMnrpNextHopsRowStatus OBJECT-TYPE
   SYNTAX     RowStatus 
   ACCESS     write-only
   STATUS     mandatory
   DESCRIPTION
     "This variable is used to control the addition and deletion 
      of individual values of the mscAtmIfVptVccMnrpNextHopsTable."
::= { mscAtmIfVptVccMnrpNextHopsEntry 2 }




-- 
-- Version and Compliance statements
-- 



-- Object-Group Statement:
-- A list of all current accessible leaf objects.

-- OBJECTS { mscAtmIfVpcNrpOamSegmentBoundary,
--           mscAtmIfVccNrpComponentName,
--           mscAtmIfVpcNrpOverrideHoldingPriority,
--           mscAtmIfVptVccNrpBandwidthElastic,
--           mscAtmIfVptVccMnrpRowStatus,
--           mscAtmIfVptVccNrpOamSegmentBoundary,
--           mscAtmIfVptVccNrpComponentName,
--           mscAtmIfVccNrpRowStatus,
--           mscAtmIfVpcMnrpOverrideHoldingPriority,
--           mscAtmIfVccNrpNextHop,
--           mscAtmIfVptVccNrpOverrideHoldingPriority,
--           mscAtmIfVccMnrpOamSegmentBoundary,
--           mscAtmIfVpcNrpRowStatus,
--           mscAtmIfVpcNrpBandwidthElastic,
--           mscAtmIfVpcNrpNextHop,
--           mscAtmIfVptVccMnrpBandwidthElastic,
--           mscAtmIfVccMnrpBandwidthElastic,
--           mscAtmIfVccMnrpNextHopsRowStatus,
--           mscAtmIfVpcMnrpComponentName,
--           mscAtmIfVptVccNrpNextHop,
--           mscAtmIfVptVccNrpStorageType,
--           mscAtmIfVpcMnrpRowStatus,
--           mscAtmIfVptVccMnrpComponentName,
--           mscAtmIfVptVccMnrpNextHopsValue,
--           mscAtmIfVccMnrpOverrideHoldingPriority,
--           mscAtmIfVpcMnrpNextHopsRowStatus,
--           mscAtmIfVccNrpOamSegmentBoundary,
--           mscAtmIfVptVccMnrpStorageType,
--           mscAtmIfVccMnrpNextHopsValue,
--           mscAtmIfVpcNrpStorageType,
--           mscAtmIfVccNrpStorageType,
--           mscAtmIfVptVccMnrpOamSegmentBoundary,
--           mscAtmIfVccMnrpComponentName,
--           mscAtmIfVpcNrpComponentName,
--           mscAtmIfVpcMnrpNextHopsValue,
--           mscAtmIfVccNrpBandwidthElastic,
--           mscAtmIfVccMnrpStorageType,
--           mscAtmIfVpcMnrpBandwidthElastic,
--           mscAtmIfVpcMnrpOamSegmentBoundary,
--           mscAtmIfVptVccMnrpNextHopsRowStatus,
--           mscAtmIfVptVccNrpRowStatus,
--           mscAtmIfVptVccMnrpOverrideHoldingPriority,
--           mscAtmIfVccNrpOverrideHoldingPriority,
--           mscAtmIfVpcMnrpStorageType,
--           mscAtmIfVccMnrpRowStatus }
-- STATUS  mandatory
-- DESCRIPTION
--   "A list of all current accessible leaf objects."

atmBearerServiceGroup OBJECT IDENTIFIER ::= { atmBearerServiceMIB 1 }
atmBearerServiceGroupCA OBJECT IDENTIFIER ::= { atmBearerServiceGroup 1 }
atmBearerServiceGroupCA02 OBJECT IDENTIFIER ::= { atmBearerServiceGroupCA 3 }
atmBearerServiceGroupCA02A OBJECT IDENTIFIER ::= { atmBearerServiceGroupCA02 2 }



-- Agent-Capabilities Statement:

-- PRODUCT-RELEASE "MscPassport Release 1.2 AtmBearerService."
-- STATUS          mandatory
-- DESCRIPTION     "Carrier Passport AtmBearerService MIB: MIB Version CA02A,
--                  Software Version CA02S9C."
-- SUPPORTS        Nortel-MsCarrier-MscPassport-AtmBearerServiceMIB
--    INCLUDES     { atmBearerServiceGroupCA02A }

atmBearerServiceCapabilities OBJECT IDENTIFIER ::= { atmBearerServiceMIB 3 }
atmBearerServiceCapabilitiesCA OBJECT IDENTIFIER ::= { atmBearerServiceCapabilities 1 }
atmBearerServiceCapabilitiesCA02 OBJECT IDENTIFIER ::= { atmBearerServiceCapabilitiesCA 3 }
atmBearerServiceCapabilitiesCA02A OBJECT IDENTIFIER ::= { atmBearerServiceCapabilitiesCA02 2 }





END
