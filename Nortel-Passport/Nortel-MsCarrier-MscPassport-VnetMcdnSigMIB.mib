Nortel-MsCarrier-MscPassport-VnetMcdnSigMIB
DEFINITIONS ::= BEGIN



IMPORTS

      OBJECT-TYPE
   FROM RFC-1212

      mscPassportMIBs
   FROM Nortel-MsCarrier-MscPassport-UsefulDefinitionsMIB

      Counter32,
      DisplayString,
      StorageType,
      RowStatus,
      Unsigned32
   FROM Nortel-MsCarrier-MscPassport-StandardTextualConventionsMIB

      NonReplicated,
      Link
   FROM Nortel-MsCarrier-MscPassport-TextualConventionsMIB

      mscSigChan,
      mscSigChanIndex
   FROM Nortel-MsCarrier-MscPassport-VoiceNetworkingMIB;




-- LAST-UPDATED   "9909010000Z"
-- ORGANIZATION   "Nortel Networks"
-- CONTACT-INFO   "
--         Nortel Carrier Data Network Management
--         
--         Postal:       P.O. Box 3511, Station C 
--                       Ottawa, Ontario 
--                       Canada  K1Y 4H7
--         
--         via the WEB:  http://www.nortelnetworks.com  
--                       select 'Contact Us' from the menu
--          
--         via phone:    1-800-4NORTEL"
-- DESCRIPTION
--    "The module describing the Nortel MsCarrier MscPassport
--     VnetMcdnSig Enterprise MIB."

vnetMcdnSigMIB OBJECT IDENTIFIER ::= { mscPassportMIBs 142 }










-- SigChan/n McdnSig
-- The McdnSig component defines the operational characteristics of 
-- the signalling channel's connection to the external equipment. This 
-- is the proprietary MCDN protocol as based on Nortel specification 
-- TR-88-5003.

mscSigChanMcdn OBJECT IDENTIFIER ::= { mscSigChan 17 }



mscSigChanMcdnRowStatusTable OBJECT-TYPE
   SYNTAX     SEQUENCE OF MscSigChanMcdnRowStatusEntry
   ACCESS     not-accessible
   STATUS     mandatory
   DESCRIPTION
     "This entry controls the addition and deletion of 
      mscSigChanMcdn components."
::= { mscSigChanMcdn 1 }

mscSigChanMcdnRowStatusEntry OBJECT-TYPE
   SYNTAX     MscSigChanMcdnRowStatusEntry
   ACCESS     not-accessible
   STATUS     mandatory
   DESCRIPTION
     "A single entry in the table represents a single 
      mscSigChanMcdn component."
   INDEX {
      mscSigChanIndex,
      mscSigChanMcdnIndex }
::= { mscSigChanMcdnRowStatusTable 1 }

MscSigChanMcdnRowStatusEntry ::= SEQUENCE {
   mscSigChanMcdnRowStatus
      RowStatus,
   mscSigChanMcdnComponentName
      DisplayString,
   mscSigChanMcdnStorageType
      StorageType,
   mscSigChanMcdnIndex
      NonReplicated }

mscSigChanMcdnRowStatus OBJECT-TYPE
   SYNTAX     RowStatus 
   ACCESS     read-write
   STATUS     mandatory
   DESCRIPTION
     "This variable is used as the basis for SNMP naming of
      mscSigChanMcdn components.
      These components can be added and deleted."
::= { mscSigChanMcdnRowStatusEntry 1 }

mscSigChanMcdnComponentName OBJECT-TYPE
   SYNTAX     DisplayString 
   ACCESS     read-only
   STATUS     mandatory
   DESCRIPTION
     "This variable provides the component's string name for
      use with the ASCII Console Interface"
::= { mscSigChanMcdnRowStatusEntry 2 }

mscSigChanMcdnStorageType OBJECT-TYPE
   SYNTAX     StorageType 
   ACCESS     read-only
   STATUS     mandatory
   DESCRIPTION
     "This variable represents the storage type value for the
      mscSigChanMcdn tables."
::= { mscSigChanMcdnRowStatusEntry 4 }

mscSigChanMcdnIndex OBJECT-TYPE
   SYNTAX     NonReplicated 
   ACCESS     not-accessible
   STATUS     mandatory
   DESCRIPTION
     "This variable represents the index for the mscSigChanMcdn tables."
::= { mscSigChanMcdnRowStatusEntry 10 }

mscSigChanMcdnL2Table OBJECT-TYPE
   SYNTAX     SEQUENCE OF MscSigChanMcdnL2Entry
   ACCESS     not-accessible
   STATUS     mandatory
   DESCRIPTION
     "This group specifies the provisionable layer 2 attributes of the 
      Q.931 ITU-T protocol."
::= { mscSigChanMcdn 11 }

mscSigChanMcdnL2Entry OBJECT-TYPE
   SYNTAX     MscSigChanMcdnL2Entry
   ACCESS     not-accessible
   STATUS     mandatory
   DESCRIPTION
     "An entry in the mscSigChanMcdnL2Table."
   INDEX {
      mscSigChanIndex,
      mscSigChanMcdnIndex }
::= { mscSigChanMcdnL2Table 1 }

MscSigChanMcdnL2Entry ::= SEQUENCE {
   mscSigChanMcdnT23
      Unsigned32,
   mscSigChanMcdnT200
      Unsigned32,
   mscSigChanMcdnN200
      Unsigned32,
   mscSigChanMcdnT203
      Unsigned32,
   mscSigChanMcdnCircuitSwitchedK
      Unsigned32 }

mscSigChanMcdnT23 OBJECT-TYPE
   SYNTAX     Unsigned32 (1..15)
   ACCESS     read-write
   STATUS     mandatory
   DESCRIPTION
     "This attribute specifies the layer 2 enable request timer."
   DEFVAL     { 10 }
::= { mscSigChanMcdnL2Entry 1 }

mscSigChanMcdnT200 OBJECT-TYPE
   SYNTAX     Unsigned32 (1..20)
   ACCESS     read-write
   STATUS     mandatory
   DESCRIPTION
     "This attribute specifies the maximum time between a layer 2 frame 
      and its acknowledgment."
   DEFVAL     { 1 }
::= { mscSigChanMcdnL2Entry 2 }

mscSigChanMcdnN200 OBJECT-TYPE
   SYNTAX     Unsigned32 (1..8)
   ACCESS     read-write
   STATUS     mandatory
   DESCRIPTION
     "This attribute specifies the maximum number of re-transmissions of 
      a layer 2 frame."
   DEFVAL     { 3 }
::= { mscSigChanMcdnL2Entry 3 }

mscSigChanMcdnT203 OBJECT-TYPE
   SYNTAX     Unsigned32 (2..40)
   ACCESS     read-write
   STATUS     mandatory
   DESCRIPTION
     "This attribute specifies the maximum time for which layer 2 frames 
      may be absent. Expiry triggers a check on whether the far end is 
      alive."
   DEFVAL     { 10 }
::= { mscSigChanMcdnL2Entry 4 }

mscSigChanMcdnCircuitSwitchedK OBJECT-TYPE
   SYNTAX     Unsigned32 (1..127)
   ACCESS     read-write
   STATUS     mandatory
   DESCRIPTION
     "This attribute specifies the maximum number of sequentially 
      numbered I frames (that is, window size (k)) that may be 
      unacknowledged at any given time for a SAP supporting primary 
      rate (64kbit/sec) signalling."
   DEFVAL     { 7 }
::= { mscSigChanMcdnL2Entry 6 }

mscSigChanMcdnL3Table OBJECT-TYPE
   SYNTAX     SEQUENCE OF MscSigChanMcdnL3Entry
   ACCESS     not-accessible
   STATUS     mandatory
   DESCRIPTION
     "This group represents the provisionable Layer 3 timer attributes of 
      the MCDN signalling protocol."
::= { mscSigChanMcdn 12 }

mscSigChanMcdnL3Entry OBJECT-TYPE
   SYNTAX     MscSigChanMcdnL3Entry
   ACCESS     not-accessible
   STATUS     mandatory
   DESCRIPTION
     "An entry in the mscSigChanMcdnL3Table."
   INDEX {
      mscSigChanIndex,
      mscSigChanMcdnIndex }
::= { mscSigChanMcdnL3Table 1 }

MscSigChanMcdnL3Entry ::= SEQUENCE {
   mscSigChanMcdnT302
      Unsigned32,
   mscSigChanMcdnT304
      Unsigned32,
   mscSigChanMcdnT309
      Unsigned32,
   mscSigChanMcdnT310
      Unsigned32,
   mscSigChanMcdnT316
      Unsigned32,
   mscSigChanMcdnT317
      Unsigned32 }

mscSigChanMcdnT302 OBJECT-TYPE
   SYNTAX     Unsigned32 (10..30)
   ACCESS     read-write
   STATUS     mandatory
   DESCRIPTION
     "This attribute specifies the overlap receiving timer; in a UNI, this is 
      network to user, but for Peer to Peer it is all incoming calls. This 
      attribute is ignored if overlap signalling is disabled."
   DEFVAL     { 15 }
::= { mscSigChanMcdnL3Entry 1 }

mscSigChanMcdnT304 OBJECT-TYPE
   SYNTAX     Unsigned32 (10..30)
   ACCESS     read-write
   STATUS     mandatory
   DESCRIPTION
     "This attribute specifies the overlap sending timer; in a UNI, this is 
      user to network, but for Peer to Peer it is all outgoing calls. This 
      attribute is ignored if overlap signalling is disabled."
   DEFVAL     { 10 }
::= { mscSigChanMcdnL3Entry 2 }

mscSigChanMcdnT309 OBJECT-TYPE
   SYNTAX     Unsigned32 (15..120)
   ACCESS     read-write
   STATUS     mandatory
   DESCRIPTION
     "This attribute specifies the data link disconnect timer; used to ride 
      out temporary failures."
   DEFVAL     { 90 }
::= { mscSigChanMcdnL3Entry 3 }

mscSigChanMcdnT310 OBJECT-TYPE
   SYNTAX     Unsigned32 (10..120)
   ACCESS     read-write
   STATUS     mandatory
   DESCRIPTION
     "This attribute specifies the call proceeding state timer."
   DEFVAL     { 10 }
::= { mscSigChanMcdnL3Entry 4 }

mscSigChanMcdnT316 OBJECT-TYPE
   SYNTAX     Unsigned32 (31..180)
   ACCESS     read-write
   STATUS     mandatory
   DESCRIPTION
     "This attribute specifies the restart request response timer.
      It must be set greater than t317."
   DEFVAL     { 120 }
::= { mscSigChanMcdnL3Entry 5 }

mscSigChanMcdnT317 OBJECT-TYPE
   SYNTAX     Unsigned32 (30..179)
   ACCESS     read-only
   STATUS     mandatory
   DESCRIPTION
     "This attribute specifies the restart operation timer, used when a 
      RESTART was received."
   DEFVAL     { 30 }
::= { mscSigChanMcdnL3Entry 6 }

mscSigChanMcdnProvTable OBJECT-TYPE
   SYNTAX     SEQUENCE OF MscSigChanMcdnProvEntry
   ACCESS     not-accessible
   STATUS     mandatory
   DESCRIPTION
     "This group defines the general options of the D-channel signalling 
      link."
::= { mscSigChanMcdn 13 }

mscSigChanMcdnProvEntry OBJECT-TYPE
   SYNTAX     MscSigChanMcdnProvEntry
   ACCESS     not-accessible
   STATUS     mandatory
   DESCRIPTION
     "An entry in the mscSigChanMcdnProvTable."
   INDEX {
      mscSigChanIndex,
      mscSigChanMcdnIndex }
::= { mscSigChanMcdnProvTable 1 }

MscSigChanMcdnProvEntry ::= SEQUENCE {
   mscSigChanMcdnSide
      INTEGER,
   mscSigChanMcdnMaxNonCallConcurrent
      Unsigned32,
   mscSigChanMcdnOverlapSending
      INTEGER,
   mscSigChanMcdnOverlapReceiving
      INTEGER,
   mscSigChanMcdnChanMaintenanceHandling
      INTEGER }

mscSigChanMcdnSide OBJECT-TYPE
   SYNTAX     INTEGER  {
                 network(1),
                 user(2) }
   ACCESS     read-write
   STATUS     mandatory
   DESCRIPTION
     "This attribute specifies whether the interface provides layer 2 and 3 
      services equivalent to the ITU-T network or user side of the 
      connection. If this attribute is set to network, then the interface is 
      master during channel negotiation, and uses network side layer 2 
      command/response bits. If this attribute is set to user, then the 
      interface is slave during channel negotiation, and uses user side 
      layer 2 command/response bits.
      Note that although a peer to peer protocol has no true network or 
      user side, for channel negotiation and layer 2 handling the peer to 
      peer and UNI protocols have identical function. A true UNI may 
      also have uni-directional messages and/or message elements; the 
      peer to peer has all elements bidirectional."
   DEFVAL     { network }
::= { mscSigChanMcdnProvEntry 1 }

mscSigChanMcdnMaxNonCallConcurrent OBJECT-TYPE
   SYNTAX     Unsigned32 (1..30)
   ACCESS     read-write
   STATUS     mandatory
   DESCRIPTION
     "This attribute specifies the maximum number of simultaneous active 
      non-call transactions that are allowed."
   DEFVAL     { 30 }
::= { mscSigChanMcdnProvEntry 2 }

mscSigChanMcdnOverlapSending OBJECT-TYPE
   SYNTAX     INTEGER  {
                 enabled(0),
                 disabled(1) }
   ACCESS     read-write
   STATUS     mandatory
   DESCRIPTION
     "This attribute specifies whether overlap sending to the PBX is 
      enabled."
   DEFVAL     { enabled }
::= { mscSigChanMcdnProvEntry 3 }

mscSigChanMcdnOverlapReceiving OBJECT-TYPE
   SYNTAX     INTEGER  {
                 enabled(0),
                 disabled(1) }
   ACCESS     read-write
   STATUS     mandatory
   DESCRIPTION
     "This attribute specifies whether overlap receiving from the PBX is 
      enabled."
   DEFVAL     { enabled }
::= { mscSigChanMcdnProvEntry 4 }

mscSigChanMcdnChanMaintenanceHandling OBJECT-TYPE
   SYNTAX     INTEGER  {
                 globalOnStartup(0),
                 serviceMessage(1),
                 restartMessage(2) }
   ACCESS     read-write
   STATUS     mandatory
   DESCRIPTION
     "This attribute specifies handling of channel maintenance events 
      such as locking and unlocking a channel or channel registration on 
      start-up. The decision here is whether to send individual channel 
      RESTART messages, SERVICE messages, or nothing. Note that 
      channel registration only occurs after the global interface restart at 
      startup.
      
      The attribute controls start-up handling absolutely, and channel lock 
      and unlock conditionally. That is, setting this to enable SERVICE 
      messages ensures SERVICE messages at start-up and whenever a 
      channel goes into or out of service. However, if this is not set to 
      enable SERVICE messaging, a RESTART is always sent on 
      unlocking a channel. 
      
      globalOnStartup provides the minimum required function at start-
      up, without any individual channel confirmation. Note that when 
      this is set, channel RESTART is still used for channel unlock. 
      globalOnStartup applies to SigChan start-up only.
      
      serviceMessage enables sending and receiving SERVICE messages. 
      If enabled, SERVICE messages are always used for channel 
      maintenance on channel lock, channel unlock and start-up.
      
      restartMessage provides individual channel RESTARTs when a 
      SigChan starts up. If enabled, the RESTART is used at start-up and 
      channel unlock. However, if both SERVICE and RESTART 
      messages are disabled, the RESTART will still be used when a 
      channel unlocks."
   DEFVAL     { restartMessage }
::= { mscSigChanMcdnProvEntry 5 }

mscSigChanMcdnStateTable OBJECT-TYPE
   SYNTAX     SEQUENCE OF MscSigChanMcdnStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscSigChanMcdn 14 }

mscSigChanMcdnStateEntry OBJECT-TYPE
   SYNTAX     MscSigChanMcdnStateEntry
   ACCESS     not-accessible
   STATUS     mandatory
   DESCRIPTION
     "An entry in the mscSigChanMcdnStateTable."
   INDEX {
      mscSigChanIndex,
      mscSigChanMcdnIndex }
::= { mscSigChanMcdnStateTable 1 }

MscSigChanMcdnStateEntry ::= SEQUENCE {
   mscSigChanMcdnAdminState
      INTEGER,
   mscSigChanMcdnOperationalState
      INTEGER,
   mscSigChanMcdnUsageState
      INTEGER }

mscSigChanMcdnAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscSigChanMcdnStateEntry 1 }

mscSigChanMcdnOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscSigChanMcdnStateEntry 2 }

mscSigChanMcdnUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscSigChanMcdnStateEntry 3 }

mscSigChanMcdnStatsTable OBJECT-TYPE
   SYNTAX     SEQUENCE OF MscSigChanMcdnStatsEntry
   ACCESS     not-accessible
   STATUS     mandatory
   DESCRIPTION
     "This group provides the operational components for the McdnSig 
      component."
::= { mscSigChanMcdn 15 }

mscSigChanMcdnStatsEntry OBJECT-TYPE
   SYNTAX     MscSigChanMcdnStatsEntry
   ACCESS     not-accessible
   STATUS     mandatory
   DESCRIPTION
     "An entry in the mscSigChanMcdnStatsTable."
   INDEX {
      mscSigChanIndex,
      mscSigChanMcdnIndex }
::= { mscSigChanMcdnStatsTable 1 }

MscSigChanMcdnStatsEntry ::= SEQUENCE {
   mscSigChanMcdnTotalCallsToIf
      Counter32,
   mscSigChanMcdnTotalCallsFromIf
      Counter32,
   mscSigChanMcdnNonCallAssocSessionsToIf
      Counter32,
   mscSigChanMcdnNonCallAssocSessionsFromIf
      Counter32 }

mscSigChanMcdnTotalCallsToIf OBJECT-TYPE
   SYNTAX     Counter32 
   ACCESS     read-only
   STATUS     mandatory
   DESCRIPTION
     "This attribute counts the total number of calls that have been made 
      to the interface. The value wraps when it reaches its maximum."
::= { mscSigChanMcdnStatsEntry 2 }

mscSigChanMcdnTotalCallsFromIf OBJECT-TYPE
   SYNTAX     Counter32 
   ACCESS     read-only
   STATUS     mandatory
   DESCRIPTION
     "This attribute counts the total number of calls from the interface. 
      The value wraps when it reaches its maximum."
::= { mscSigChanMcdnStatsEntry 3 }

mscSigChanMcdnNonCallAssocSessionsToIf OBJECT-TYPE
   SYNTAX     Counter32 
   ACCESS     read-only
   STATUS     mandatory
   DESCRIPTION
     "This attribute counts the total number of non-call associated 
      sessions to the interface. The value wraps when it reaches its 
      maximum."
::= { mscSigChanMcdnStatsEntry 4 }

mscSigChanMcdnNonCallAssocSessionsFromIf OBJECT-TYPE
   SYNTAX     Counter32 
   ACCESS     read-only
   STATUS     mandatory
   DESCRIPTION
     "This attribute counts the total number of non-call associated 
      sessions from the interface. The value wraps when it reaches its 
      maximum."
::= { mscSigChanMcdnStatsEntry 5 }

mscSigChanMcdnOperTable OBJECT-TYPE
   SYNTAX     SEQUENCE OF MscSigChanMcdnOperEntry
   ACCESS     not-accessible
   STATUS     mandatory
   DESCRIPTION
     "This group provides the operational attributes for the MCDN 
      signalling."
::= { mscSigChanMcdn 16 }

mscSigChanMcdnOperEntry OBJECT-TYPE
   SYNTAX     MscSigChanMcdnOperEntry
   ACCESS     not-accessible
   STATUS     mandatory
   DESCRIPTION
     "An entry in the mscSigChanMcdnOperTable."
   INDEX {
      mscSigChanIndex,
      mscSigChanMcdnIndex }
::= { mscSigChanMcdnOperTable 1 }

MscSigChanMcdnOperEntry ::= SEQUENCE {
   mscSigChanMcdnActiveChannels
      Unsigned32,
   mscSigChanMcdnActiveVoiceChannels
      Unsigned32,
   mscSigChanMcdnActiveDataChannels
      Unsigned32,
   mscSigChanMcdnPeakActiveChannels
      Unsigned32,
   mscSigChanMcdnPeakActiveVoiceChannels
      Unsigned32,
   mscSigChanMcdnPeakActiveDataChannels
      Unsigned32,
   mscSigChanMcdnDChanStatus
      INTEGER }

mscSigChanMcdnActiveChannels OBJECT-TYPE
   SYNTAX     Unsigned32 (0..128)
   ACCESS     read-only
   STATUS     mandatory
   DESCRIPTION
     "This attribute indicates the number of currently active channels. 
      This includes data and voice channels."
   DEFVAL     { 0 }
::= { mscSigChanMcdnOperEntry 1 }

mscSigChanMcdnActiveVoiceChannels OBJECT-TYPE
   SYNTAX     Unsigned32 (0..128)
   ACCESS     read-only
   STATUS     mandatory
   DESCRIPTION
     "This attribute indicates the number of channels that are currently 
      carrying voice."
   DEFVAL     { 0 }
::= { mscSigChanMcdnOperEntry 2 }

mscSigChanMcdnActiveDataChannels OBJECT-TYPE
   SYNTAX     Unsigned32 (0..128)
   ACCESS     read-only
   STATUS     mandatory
   DESCRIPTION
     "This attribute indicates the number of channels that are currently 
      carrying data. This does not include modem data."
   DEFVAL     { 0 }
::= { mscSigChanMcdnOperEntry 3 }

mscSigChanMcdnPeakActiveChannels OBJECT-TYPE
   SYNTAX     Unsigned32 (0..128)
   ACCESS     read-only
   STATUS     mandatory
   DESCRIPTION
     "This attribute indicates the maximum number of channels that have 
      been active on this signalling channel during the last polling period."
   DEFVAL     { 0 }
::= { mscSigChanMcdnOperEntry 4 }

mscSigChanMcdnPeakActiveVoiceChannels OBJECT-TYPE
   SYNTAX     Unsigned32 (0..128)
   ACCESS     read-only
   STATUS     mandatory
   DESCRIPTION
     "This attribute indicates the maximum number of voice channels that 
      have been active on this signalling channel during the last polling 
      period."
   DEFVAL     { 0 }
::= { mscSigChanMcdnOperEntry 5 }

mscSigChanMcdnPeakActiveDataChannels OBJECT-TYPE
   SYNTAX     Unsigned32 (0..128)
   ACCESS     read-only
   STATUS     mandatory
   DESCRIPTION
     "This attribute indicates the maximum number of data channels that 
      have been active on this signalling channel during the last polling 
      period."
   DEFVAL     { 0 }
::= { mscSigChanMcdnOperEntry 6 }

mscSigChanMcdnDChanStatus OBJECT-TYPE
   SYNTAX     INTEGER  {
                 outOfService(0),
                 establishing(1),
                 established(2),
                 enabling(3),
                 inService(4),
                 restarting(5) }
   ACCESS     read-only
   STATUS     mandatory
   DESCRIPTION
     "This attribute indicates the state of the D-channel. 
      outOfService means that there is no layer 2 or layer 3 connectivity 
      to the PBX.
      establishing means that the signalling channel is attempting to stage 
      the layer 2.
      established means that the layer 2 is enabled. If the signalling 
      channel stays in the established state, then it is waiting for a restart 
      from the PBX.
      enabling means that the resources for processing calls are being 
      initialized. If the signalling channel stays in the enabling state then 
      it is waiting for a restart acknowledgement from the PBX. 
      inService means that the resources for processing calls are 
      available. 
      restarting means that the resources for call processing are being rei-
      initialized."
::= { mscSigChanMcdnOperEntry 7 }

mscSigChanMcdnToolsTable OBJECT-TYPE
   SYNTAX     SEQUENCE OF MscSigChanMcdnToolsEntry
   ACCESS     not-accessible
   STATUS     mandatory
   DESCRIPTION
     "This contains a series of operational attributes which turn on and off 
      several kinds of tracing."
::= { mscSigChanMcdn 17 }

mscSigChanMcdnToolsEntry OBJECT-TYPE
   SYNTAX     MscSigChanMcdnToolsEntry
   ACCESS     not-accessible
   STATUS     mandatory
   DESCRIPTION
     "An entry in the mscSigChanMcdnToolsTable."
   INDEX {
      mscSigChanIndex,
      mscSigChanMcdnIndex }
::= { mscSigChanMcdnToolsTable 1 }

MscSigChanMcdnToolsEntry ::= SEQUENCE {
   mscSigChanMcdnTracing
      OCTET STRING,
   mscSigChanMcdnMessageTraced
      OCTET STRING,
   mscSigChanMcdnDirectionTraced
      OCTET STRING }

mscSigChanMcdnTracing OBJECT-TYPE
   SYNTAX     OCTET STRING (SIZE (1))
   ACCESS     read-write
   STATUS     mandatory
   DESCRIPTION
     "This attribute defines which types of tracing are active for this 
      signalling channel.  The tracing messages are sent to the debug 
      stream. To see the messages the agentQueue attribute in Col/debug 
      must be greater than 0 and a Telnet NMIS session must list the 
      debug stream in in its data streams (ex. set nmis telnet session/1 
      dataStreams debug). Different types of tracing can be enabled 
      simultaneously.  
      Note that tracing consumes additional CPU resources and will slow 
      down call processing on a heavily loaded card.  If there is message 
      block exhaustion tracing will be suspended for a period and then 
      automatically reenabled.  An alarm is generated on tracing 
      suspension and resumption.  This mechanism protects the function 
      processor against excessive numbers of tracing messages.
      
      Types of tracing include: 
      protocolErrors - get details of any protocol errors which are 
      occuring. Protocol errors are also reported in summary form as 
      alarms. 
      q931Summary - Summary of the Q.931 messages on the signalling 
      link, including certain call details (calling number, called number, 
      release codes). 
      q931Hex - Q.931 messages displayed in hex format.  Useful to 
      determine protocol compliance in case of errors reported on local or 
      remote ends.
      q931Symbolic - Q.931 messages parsed to give maximum detail.  
      Useful for understanding content of messages flowing on the link.
      portHex - Messages in hex format being sent and received on the 
      link.

      Description of bits:
      protocolErrors(0)
      q931Summary(1)
      q931Hex(2)
      q931Symbolic(3)
      portHex(4)"
::= { mscSigChanMcdnToolsEntry 1 }

mscSigChanMcdnMessageTraced OBJECT-TYPE
   SYNTAX     OCTET STRING (SIZE (4))
   ACCESS     read-write
   STATUS     mandatory
   DESCRIPTION
     "This attribute specifies the type of ISDN messages that are to be 
      traced.

      Description of bits:
      alerting(0)
      callProceeding(1)
      connectionlessFacility(2)
      congestionControl(3)
      connect(4)
      connectAcknowledge(5)
      disconnect(6)
      facility(7)
      facilityAcknowledge(8)
      facilityReject(9)
      information(10)
      notify(11)
      progress(12)
      register(13)
      releaseComp(14)
      release(15)
      restart(16)
      restartAcknowledge(17)
      service(18)
      serviceAcknowledge(19)
      setup(20)
      setupAcknowledge(21)
      status(22)
      statusEnquiry(23)
      userInformation(24)
      all(25)"
   DEFVAL     { 'ffffff80'H }
::= { mscSigChanMcdnToolsEntry 2 }

mscSigChanMcdnDirectionTraced OBJECT-TYPE
   SYNTAX     OCTET STRING (SIZE (1))
   ACCESS     read-write
   STATUS     mandatory
   DESCRIPTION
     "This attribute indicates whether the incoming (from PBX), outgoing 
      (to PBX), or both incoming and outgoing messages are traced.

      Description of bits:
      incoming(0)
      outgoing(1)"
   DEFVAL     { 'c0'H }
::= { mscSigChanMcdnToolsEntry 3 }

mscSigChanMcdnClsTable OBJECT-TYPE
   SYNTAX     SEQUENCE OF MscSigChanMcdnClsEntry
   ACCESS     not-accessible
   STATUS     mandatory
   DESCRIPTION
     "This group enables and disables the support of the MCDN 
      proprietary signalling for connectionless features on the local 
      signalling channel."
::= { mscSigChanMcdn 18 }

mscSigChanMcdnClsEntry OBJECT-TYPE
   SYNTAX     MscSigChanMcdnClsEntry
   ACCESS     not-accessible
   STATUS     mandatory
   DESCRIPTION
     "An entry in the mscSigChanMcdnClsTable."
   INDEX {
      mscSigChanIndex,
      mscSigChanMcdnIndex }
::= { mscSigChanMcdnClsTable 1 }

MscSigChanMcdnClsEntry ::= SEQUENCE {
   mscSigChanMcdnClsFeaturesSupported
      OCTET STRING }

mscSigChanMcdnClsFeaturesSupported OBJECT-TYPE
   SYNTAX     OCTET STRING (SIZE (2))
   ACCESS     read-write
   STATUS     mandatory
   DESCRIPTION
     "This attribute specifies the features to be supported by MCDN 
      'TCAP' connectionless messaging. Note that some features such as 
      Network ACD combine connectionless and connection oriented. In 
      the NACD case, the connectionless messaging enables the source 
      and target PBXs to establish the networked relationship, and calls 
      sent across the network (connection oriented) will contain basic 
      information relating the call to the feature.
      
      Feature Definitions:
      networkAcd: transfer of a call from a pool of agents to a second 
      pool of agents across the network.
      networkMessageService: message waiting capability (for example, 
      lamps on sets). Also includes signalling for voice mail, but is not 
      limited to voice mail.
      networkVoiceMail: a specific subset of Network Message Service, 
      separated functionally as it always terminates on an interactive 
      voice response mailbox application.
      networkRingAgain: ring again to remote sets.
      electronicLock: change of set capabilities by a remote user dialling 
      the applicable code and password.
      remoteCallForward: call forwarding a phone via applicable code 
      and password.
      callPickupNetworkWide (call pickup world wide): scan for a 
      ringing call on another node, to enable the scanning set to pick up 
      the call.
      networkPackage1: a collection of other features including but not 
      limited to network clock synchronization. Note that on the Meridian 
      1, this is a general purpose group used for very small features not 
      requiring a new ISDN Facility feature type.
      isdnApplicationInterface: network wide support of a number of 
      Meridian 1 Application Module Link features.
      mobilityMultisiteNetworking: the capability to use a wireless phone 
      in multiple sites, by having the phone register on arrival at the new 
      site, and having the PBX at the new site negotiate the set 
      'relocation' with the base PBX.
      miscellaneous: Any feature that is not listed above.

      Description of bits:
      networkAcd(0)
      networkMessageService(1)
      networkRingAgain(2)
      networkVoiceMail(3)
      electronicLock(4)
      remoteCallForward(5)
      callPickupWorldWide(6)
      networkPackage1(7)
      isdnApplicationInterface(8)
      mobilityMultisiteNetworking(9)
      notused10(10)
      notused11(11)
      notused12(12)
      notused13(13)
      notused14(14)
      miscellaneous(15)"
   DEFVAL     { 'ffc1'H }
::= { mscSigChanMcdnClsEntry 2 }

mscSigChanMcdnCoTable OBJECT-TYPE
   SYNTAX     SEQUENCE OF MscSigChanMcdnCoEntry
   ACCESS     not-accessible
   STATUS     mandatory
   DESCRIPTION
     "This group enables and disables the support of the MCDN 
      proprietary signalling for the listed features on the local signalling 
      channel."
::= { mscSigChanMcdn 19 }

mscSigChanMcdnCoEntry OBJECT-TYPE
   SYNTAX     MscSigChanMcdnCoEntry
   ACCESS     not-accessible
   STATUS     mandatory
   DESCRIPTION
     "An entry in the mscSigChanMcdnCoTable."
   INDEX {
      mscSigChanIndex,
      mscSigChanMcdnIndex }
::= { mscSigChanMcdnCoTable 1 }

MscSigChanMcdnCoEntry ::= SEQUENCE {
   mscSigChanMcdnDropBackCongestion
      INTEGER,
   mscSigChanMcdnNetworkNameDisplay
      OCTET STRING,
   mscSigChanMcdnMultisiteBusinessGroup
      INTEGER,
   mscSigChanMcdnConOrFeaturesSupported
      OCTET STRING }

mscSigChanMcdnDropBackCongestion OBJECT-TYPE
   SYNTAX     INTEGER  {
                 noDropBackAllowed(0),
                 dropBackToOriginator(1),
                 dropBackToPriorNode(2) }
   ACCESS     read-write
   STATUS     mandatory
   DESCRIPTION
     "This attribute specifies if the Meridian 1 Drop Back Congestion 
      Handling for trunks is enabled, and what type is being supported."
   DEFVAL     { dropBackToOriginator }
::= { mscSigChanMcdnCoEntry 1 }

mscSigChanMcdnNetworkNameDisplay OBJECT-TYPE
   SYNTAX     OCTET STRING (SIZE (1))
   ACCESS     read-write
   STATUS     mandatory
   DESCRIPTION
     "This attribute specifies what Name Display is supported.
      
      nd1 corresponds to the Meridian 1 RCAP (Remote CAPability) 
      nd1. This translates as caller provides name info in SETUP, ringing 
      party name in ALERTING, redirection name in NOTIFY, and 
      answering party name in CONNECT (as applicable, and if the name 
      changes).
      
      nd2 corresponds to the Meridian 1 RCAP (Remote CAPability) 
      nd2. This translates as caller provides name info in SETUP, 
      answering party provides name in NOTIFY on answer.
      
      nd3 corresponds to the Meridian 1 RCAP (Remote CAPability) 
      nd3, which is nd1 plus name information in call clearing messages 
      (busy user, etc.) where a specific user was found but either could not 
      answer or cleared the call. This corresponds to the QSIG name 
      display.

      Description of bits:
      nameDisplay1(0)
      nameDisplay2(1)
      nameDisplay3(2)"
::= { mscSigChanMcdnCoEntry 4 }

mscSigChanMcdnMultisiteBusinessGroup OBJECT-TYPE
   SYNTAX     INTEGER  {
                 transport(0),
                 discard(1) }
   ACCESS     read-write
   STATUS     mandatory
   DESCRIPTION
     "This attribute specifies whether to enable transport for the 
      Meridian 1 Multisite Business Group IE. The Meridian 1 allows 
      multiple 'Tenants' to exist on a single PBX. These Tenants have 
      limited access to each other and to system resources.   That is, users 
      associated with 'Tenant group one' cannot use trunks, attendants, 
      and features from another group, and so forth. The Multi-Site 
      Business Group is a single Tenant existing on more than one PBX.   
      As an example, 'tenant one' on a PBX may 'own' resources 
      belonging to 'tenant one' on another PBX.   The Multi-Site 
      Business Group IE as used in the Meridian 1 Network Tenant 
      Services feature enables linking the two tenants together."
   DEFVAL     { transport }
::= { mscSigChanMcdnCoEntry 7 }

mscSigChanMcdnConOrFeaturesSupported OBJECT-TYPE
   SYNTAX     OCTET STRING (SIZE (2))
   ACCESS     read-write
   STATUS     mandatory
   DESCRIPTION
     "This attribute indicates the features to be supported by MCDN 
      'ROSE' connection oriented messaging. 
      
      Feature Definitions:
      networkAttendantService: network wide support of Attendant 
      ('operator') services.
      classOfServiceTransport: this is not a ROSE feature. Class of 
      Service transport takes place in the called party number when 
      provisioned on the Meridian 1 to use an ESN signalling type.
      trunkRouteOptimization: dropping of redundant links in a call, 
      when a set call forwards a call prior to answer.
      remoteVirtualQueuing: queuing at a remote node without requiring 
      a B channel to be kept up.
      offHookQueuing: Queuing by maintaining the speech path to the 
      queuing node.
      networkCallTrace: call progress tracing across a network (that is, 
      call reached node a, node b, terminated at c,...).
      networkIntercom: network wide access to an intercom system onm 
      a Meridian 1.
      callPickupNetworkWide: connection oriented messages associated 
      with the TCAP call pickup scan operation. The messages that 
      actually pick up the ringing call.
      radioPaging: access to a radio paging system network wide, 
      allowing single radio paging facilities in a relatively dense local 
      PBX network.
      networkAccess: information to enable access to PBX features from 
      outside the network. Additional data is provided to identify access 
      capabilities for a spoecific call. (Similar to transmittiong 
      authorization code capabilities network wide.)
      antiTromboning: actually includes two capabilities - NAS 
      (Network Attendant Setvice) and Trunk Anti-Tromboning. Calls 
      that exit the subnet to a PBX and are transferred back to a network 
      number via the same D channel can be optimized. If PBX A 
      (Passport A) calls across the subnet to Passport B, D channel Z, to 
      PBX B, and PBX B transfers across D channel Z to Passport B and 
      therefore to PBX C/Passport C, this allows tha call to simplify to 
      PBX/Passport A to PBX/Passport C.
      miscellaneous: Any feature that is not listed above.

      Description of bits:
      networkAttendantService(0)
      classOfServiceTransport(1)
      trunkRouteOptimization(2)
      remoteVirtualQueuing(3)
      networkCallId(4)
      offHookQueuing(5)
      networkCallTrace(6)
      networkIntercom(7)
      callPickupNetworkWide(8)
      radioPaging(9)
      networkAccess(10)
      antiTromboning(11)
      miscellaneous(12)"
   DEFVAL     { 'fff8'H }
::= { mscSigChanMcdnCoEntry 8 }


-- SigChan/n Mcdn Framer
-- 
-- The Framer component controls link layer framing for application 
-- components sending and receiving data on a link interface. It is also 
-- through Framer, that an application component is associated with a 
-- specific hardware link interface.
-- 
-- The Framer component provides provisionable attributes related to 
-- data path aspects of the hardware interface (such as crc and frame 
-- length). The Framer component also provides a provisionable 
-- attribute which binds the application component to a specific 
-- hardware component.
-- 
-- The Framer component contains operational attributes for link 
-- interface data path statistics (such as frame counts and aborts).
-- 

mscSigChanMcdnFramer OBJECT IDENTIFIER ::= { mscSigChanMcdn 2 }



mscSigChanMcdnFramerRowStatusTable OBJECT-TYPE
   SYNTAX     SEQUENCE OF MscSigChanMcdnFramerRowStatusEntry
   ACCESS     not-accessible
   STATUS     mandatory
   DESCRIPTION
     "This entry controls the addition and deletion of 
      mscSigChanMcdnFramer components."
::= { mscSigChanMcdnFramer 1 }

mscSigChanMcdnFramerRowStatusEntry OBJECT-TYPE
   SYNTAX     MscSigChanMcdnFramerRowStatusEntry
   ACCESS     not-accessible
   STATUS     mandatory
   DESCRIPTION
     "A single entry in the table represents a single 
      mscSigChanMcdnFramer component."
   INDEX {
      mscSigChanIndex,
      mscSigChanMcdnIndex,
      mscSigChanMcdnFramerIndex }
::= { mscSigChanMcdnFramerRowStatusTable 1 }

MscSigChanMcdnFramerRowStatusEntry ::= SEQUENCE {
   mscSigChanMcdnFramerRowStatus
      RowStatus,
   mscSigChanMcdnFramerComponentName
      DisplayString,
   mscSigChanMcdnFramerStorageType
      StorageType,
   mscSigChanMcdnFramerIndex
      NonReplicated }

mscSigChanMcdnFramerRowStatus OBJECT-TYPE
   SYNTAX     RowStatus 
   ACCESS     read-only
   STATUS     mandatory
   DESCRIPTION
     "This variable is used as the basis for SNMP naming of
      mscSigChanMcdnFramer components.
      These components cannot be added nor deleted."
::= { mscSigChanMcdnFramerRowStatusEntry 1 }

mscSigChanMcdnFramerComponentName OBJECT-TYPE
   SYNTAX     DisplayString 
   ACCESS     read-only
   STATUS     mandatory
   DESCRIPTION
     "This variable provides the component's string name for
      use with the ASCII Console Interface"
::= { mscSigChanMcdnFramerRowStatusEntry 2 }

mscSigChanMcdnFramerStorageType OBJECT-TYPE
   SYNTAX     StorageType 
   ACCESS     read-only
   STATUS     mandatory
   DESCRIPTION
     "This variable represents the storage type value for the
      mscSigChanMcdnFramer tables."
::= { mscSigChanMcdnFramerRowStatusEntry 4 }

mscSigChanMcdnFramerIndex OBJECT-TYPE
   SYNTAX     NonReplicated 
   ACCESS     not-accessible
   STATUS     mandatory
   DESCRIPTION
     "This variable represents the index for the mscSigChanMcdnFramer tables."
::= { mscSigChanMcdnFramerRowStatusEntry 10 }

mscSigChanMcdnFramerProvTable OBJECT-TYPE
   SYNTAX     SEQUENCE OF MscSigChanMcdnFramerProvEntry
   ACCESS     not-accessible
   STATUS     mandatory
   DESCRIPTION
     "This group contains the base provisioning data for the Framer 
      component. Application or hardware interface specific provisioning 
      data is contained in other provisionable Framer groups."
::= { mscSigChanMcdnFramer 10 }

mscSigChanMcdnFramerProvEntry OBJECT-TYPE
   SYNTAX     MscSigChanMcdnFramerProvEntry
   ACCESS     not-accessible
   STATUS     mandatory
   DESCRIPTION
     "An entry in the mscSigChanMcdnFramerProvTable."
   INDEX {
      mscSigChanIndex,
      mscSigChanMcdnIndex,
      mscSigChanMcdnFramerIndex }
::= { mscSigChanMcdnFramerProvTable 1 }

MscSigChanMcdnFramerProvEntry ::= SEQUENCE {
   mscSigChanMcdnFramerInterfaceName
      Link }

mscSigChanMcdnFramerInterfaceName OBJECT-TYPE
   SYNTAX     Link 
   ACCESS     read-write
   STATUS     mandatory
   DESCRIPTION
     "This attribute contains a hardware component name.
      
      The attribute associates the application with a specific link. This 
      defines the module processor on which Framer's parent component 
      (as well as Framer itself) will run."
::= { mscSigChanMcdnFramerProvEntry 1 }

mscSigChanMcdnFramerStateTable OBJECT-TYPE
   SYNTAX     SEQUENCE OF MscSigChanMcdnFramerStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscSigChanMcdnFramer 12 }

mscSigChanMcdnFramerStateEntry OBJECT-TYPE
   SYNTAX     MscSigChanMcdnFramerStateEntry
   ACCESS     not-accessible
   STATUS     mandatory
   DESCRIPTION
     "An entry in the mscSigChanMcdnFramerStateTable."
   INDEX {
      mscSigChanIndex,
      mscSigChanMcdnIndex,
      mscSigChanMcdnFramerIndex }
::= { mscSigChanMcdnFramerStateTable 1 }

MscSigChanMcdnFramerStateEntry ::= SEQUENCE {
   mscSigChanMcdnFramerAdminState
      INTEGER,
   mscSigChanMcdnFramerOperationalState
      INTEGER,
   mscSigChanMcdnFramerUsageState
      INTEGER }

mscSigChanMcdnFramerAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscSigChanMcdnFramerStateEntry 1 }

mscSigChanMcdnFramerOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscSigChanMcdnFramerStateEntry 2 }

mscSigChanMcdnFramerUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscSigChanMcdnFramerStateEntry 3 }

mscSigChanMcdnFramerStatsTable OBJECT-TYPE
   SYNTAX     SEQUENCE OF MscSigChanMcdnFramerStatsEntry
   ACCESS     not-accessible
   STATUS     mandatory
   DESCRIPTION
     "This group contains the operational statistics data for a Framer 
      component."
::= { mscSigChanMcdnFramer 13 }

mscSigChanMcdnFramerStatsEntry OBJECT-TYPE
   SYNTAX     MscSigChanMcdnFramerStatsEntry
   ACCESS     not-accessible
   STATUS     mandatory
   DESCRIPTION
     "An entry in the mscSigChanMcdnFramerStatsTable."
   INDEX {
      mscSigChanIndex,
      mscSigChanMcdnIndex,
      mscSigChanMcdnFramerIndex }
::= { mscSigChanMcdnFramerStatsTable 1 }

MscSigChanMcdnFramerStatsEntry ::= SEQUENCE {
   mscSigChanMcdnFramerFrmToIf
      Counter32,
   mscSigChanMcdnFramerFrmFromIf
      Counter32,
   mscSigChanMcdnFramerOctetFromIf
      Counter32,
   mscSigChanMcdnFramerAborts
      Counter32,
   mscSigChanMcdnFramerCrcErrors
      Counter32,
   mscSigChanMcdnFramerLrcErrors
      Counter32,
   mscSigChanMcdnFramerNonOctetErrors
      Counter32,
   mscSigChanMcdnFramerOverruns
      Counter32,
   mscSigChanMcdnFramerUnderruns
      Counter32,
   mscSigChanMcdnFramerLargeFrmErrors
      Counter32 }

mscSigChanMcdnFramerFrmToIf OBJECT-TYPE
   SYNTAX     Counter32 
   ACCESS     read-only
   STATUS     mandatory
   DESCRIPTION
     "This attribute counts the number of frames transmitted to the link 
      interface by Framer.
      This count wraps to zero after reaching its maximum value."
::= { mscSigChanMcdnFramerStatsEntry 1 }

mscSigChanMcdnFramerFrmFromIf OBJECT-TYPE
   SYNTAX     Counter32 
   ACCESS     read-only
   STATUS     mandatory
   DESCRIPTION
     "This attribute counts the number of frames received from the link 
      interface by Framer.
      This count wraps to zero after reaching its maximum value."
::= { mscSigChanMcdnFramerStatsEntry 2 }

mscSigChanMcdnFramerOctetFromIf OBJECT-TYPE
   SYNTAX     Counter32 
   ACCESS     read-only
   STATUS     mandatory
   DESCRIPTION
     "This attribute counts the number of bytes received from the link 
      interface by Framer. This count wraps to zero when it exceeds its 
      maximum value."
::= { mscSigChanMcdnFramerStatsEntry 3 }

mscSigChanMcdnFramerAborts OBJECT-TYPE
   SYNTAX     Counter32 
   ACCESS     read-only
   STATUS     mandatory
   DESCRIPTION
     "This attribute counts the total number of aborts received.
      This count wraps to zero after reaching its maximum value."
::= { mscSigChanMcdnFramerStatsEntry 4 }

mscSigChanMcdnFramerCrcErrors OBJECT-TYPE
   SYNTAX     Counter32 
   ACCESS     read-only
   STATUS     mandatory
   DESCRIPTION
     "This attribute counts the total number of frames with CRC errors.
      This count wraps to zero after reaching its maximum value."
::= { mscSigChanMcdnFramerStatsEntry 5 }

mscSigChanMcdnFramerLrcErrors OBJECT-TYPE
   SYNTAX     Counter32 
   ACCESS     read-only
   STATUS     mandatory
   DESCRIPTION
     "This attribute counts the total number of frames with LRC errors.
      This count wraps to zero after reaching its maximum value."
::= { mscSigChanMcdnFramerStatsEntry 6 }

mscSigChanMcdnFramerNonOctetErrors OBJECT-TYPE
   SYNTAX     Counter32 
   ACCESS     read-only
   STATUS     mandatory
   DESCRIPTION
     "This attribute counts the total number of frames that were non octet 
      aligned.
      This count wraps to zero after reaching its maximum value."
::= { mscSigChanMcdnFramerStatsEntry 7 }

mscSigChanMcdnFramerOverruns OBJECT-TYPE
   SYNTAX     Counter32 
   ACCESS     read-only
   STATUS     mandatory
   DESCRIPTION
     "This attribute counts the total number of frames received from the 
      link for which overruns occurred.
      This count wraps to zero after reaching its maximum value."
::= { mscSigChanMcdnFramerStatsEntry 8 }

mscSigChanMcdnFramerUnderruns OBJECT-TYPE
   SYNTAX     Counter32 
   ACCESS     read-only
   STATUS     mandatory
   DESCRIPTION
     "This attribute counts the total number of frames transmitted to the 
      link for which underruns occurred.
      This count wraps to zero after reaching its maximum value."
::= { mscSigChanMcdnFramerStatsEntry 9 }

mscSigChanMcdnFramerLargeFrmErrors OBJECT-TYPE
   SYNTAX     Counter32 
   ACCESS     read-only
   STATUS     mandatory
   DESCRIPTION
     "This attribute counts the total number of frames received which 
      were too large (longer than 500 bytes).
      This count wraps to zero after reaching its maximum value."
::= { mscSigChanMcdnFramerStatsEntry 10 }




-- 
-- Version and Compliance statements
-- 



-- Object-Group Statement:
-- A list of all current accessible leaf objects.

-- OBJECTS { mscSigChanMcdnActiveVoiceChannels,
--           mscSigChanMcdnRowStatus,
--           mscSigChanMcdnFramerOverruns,
--           mscSigChanMcdnConOrFeaturesSupported,
--           mscSigChanMcdnT304,
--           mscSigChanMcdnMaxNonCallConcurrent,
--           mscSigChanMcdnNonCallAssocSessionsFromIf,
--           mscSigChanMcdnPeakActiveVoiceChannels,
--           mscSigChanMcdnFramerNonOctetErrors,
--           mscSigChanMcdnFramerUsageState,
--           mscSigChanMcdnFramerComponentName,
--           mscSigChanMcdnUsageState,
--           mscSigChanMcdnFramerFrmFromIf,
--           mscSigChanMcdnTotalCallsToIf,
--           mscSigChanMcdnFramerInterfaceName,
--           mscSigChanMcdnFramerFrmToIf,
--           mscSigChanMcdnCircuitSwitchedK,
--           mscSigChanMcdnSide,
--           mscSigChanMcdnFramerOperationalState,
--           mscSigChanMcdnTracing,
--           mscSigChanMcdnT309,
--           mscSigChanMcdnDropBackCongestion,
--           mscSigChanMcdnT203,
--           mscSigChanMcdnMessageTraced,
--           mscSigChanMcdnChanMaintenanceHandling,
--           mscSigChanMcdnMultisiteBusinessGroup,
--           mscSigChanMcdnFramerLrcErrors,
--           mscSigChanMcdnT317,
--           mscSigChanMcdnFramerAborts,
--           mscSigChanMcdnT310,
--           mscSigChanMcdnComponentName,
--           mscSigChanMcdnPeakActiveChannels,
--           mscSigChanMcdnT316,
--           mscSigChanMcdnActiveDataChannels,
--           mscSigChanMcdnClsFeaturesSupported,
--           mscSigChanMcdnTotalCallsFromIf,
--           mscSigChanMcdnN200,
--           mscSigChanMcdnDirectionTraced,
--           mscSigChanMcdnT302,
--           mscSigChanMcdnFramerStorageType,
--           mscSigChanMcdnT23,
--           mscSigChanMcdnPeakActiveDataChannels,
--           mscSigChanMcdnFramerCrcErrors,
--           mscSigChanMcdnStorageType,
--           mscSigChanMcdnOverlapSending,
--           mscSigChanMcdnT200,
--           mscSigChanMcdnFramerUnderruns,
--           mscSigChanMcdnOverlapReceiving,
--           mscSigChanMcdnFramerOctetFromIf,
--           mscSigChanMcdnFramerLargeFrmErrors,
--           mscSigChanMcdnNetworkNameDisplay,
--           mscSigChanMcdnActiveChannels,
--           mscSigChanMcdnDChanStatus,
--           mscSigChanMcdnFramerAdminState,
--           mscSigChanMcdnNonCallAssocSessionsToIf,
--           mscSigChanMcdnOperationalState,
--           mscSigChanMcdnAdminState,
--           mscSigChanMcdnFramerRowStatus }
-- STATUS  mandatory
-- DESCRIPTION
--   "A list of all current accessible leaf objects."

vnetMcdnSigGroup OBJECT IDENTIFIER ::= { vnetMcdnSigMIB 1 }
vnetMcdnSigGroupCA OBJECT IDENTIFIER ::= { vnetMcdnSigGroup 1 }
vnetMcdnSigGroupCA02 OBJECT IDENTIFIER ::= { vnetMcdnSigGroupCA 3 }
vnetMcdnSigGroupCA02A OBJECT IDENTIFIER ::= { vnetMcdnSigGroupCA02 2 }



-- Agent-Capabilities Statement:

-- PRODUCT-RELEASE "MscPassport Release 1.2 VnetMcdnSig."
-- STATUS          mandatory
-- DESCRIPTION     "Carrier Passport VnetMcdnSig MIB: MIB Version CA02A,
--                  Software Version CA02S9C."
-- SUPPORTS        Nortel-MsCarrier-MscPassport-VnetMcdnSigMIB
--    INCLUDES     { vnetMcdnSigGroupCA02A }

vnetMcdnSigCapabilities OBJECT IDENTIFIER ::= { vnetMcdnSigMIB 3 }
vnetMcdnSigCapabilitiesCA OBJECT IDENTIFIER ::= { vnetMcdnSigCapabilities 1 }
vnetMcdnSigCapabilitiesCA02 OBJECT IDENTIFIER ::= { vnetMcdnSigCapabilitiesCA 3 }
vnetMcdnSigCapabilitiesCA02A OBJECT IDENTIFIER ::= { vnetMcdnSigCapabilitiesCA02 2 }





END
