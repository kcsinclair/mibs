--
-- an.mib
-- MIB generated by MG-SOFT Visual MIB Builder Version 6.0  Build 88
-- Monday, February 23, 2009 at 11:08:32
--

-- Start of ClearCase branch-information of current release:
-- an-mib.mib   /main/she_main_grf/3
-- End of ClearCase branch-information.

	AN-MIB DEFINITIONS ::= BEGIN
 
		IMPORTS
			enterprises			
				FROM RFC1155-SMI			
			OBJECT-GROUP, MODULE-COMPLIANCE			
				FROM SNMPv2-CONF			
			OBJECT-TYPE, MODULE-IDENTITY			
				FROM SNMPv2-SMI;
	
	
-- ***************************************************************
--  *************************************************************
--   *********************************************************** 
--           Nokia Siemens Networks GmbH & Co. KG
-- 
--          This mib is the entry point for
--              hiX SNMP based products
--   *********************************************************** 
--  *************************************************************
-- ***************************************************************
-- 
		an MODULE-IDENTITY 
			LAST-UPDATED "200902231054Z"		-- February 23, 2009 at 10:54 GMT
			ORGANIZATION 
				"Nokia Siemens Networks"
			CONTACT-INFO 
				"Gerd Barchmann
				COO BCS RD SDE HW1
				
				gerd.barchmann@nsn.com
				+49 3834 555654"
			DESCRIPTION 
				"  This is the OEN AN entry point."
			::= { oenProductMibs 2 }

		
	
--
-- Type definitions
--
	
-- The textual convention like SNMPv2-TC. See rfc1903.
-- 
		DisplayString ::= OCTET STRING (SIZE (0..255))

	
--
-- Node definitions
--
	
--  Node definitions
-- 
-- Definition of main groups of the XLD an.mib
-- 
-- 
-- 
-- 1.3.6.1.4.1.231
		sni OBJECT IDENTIFIER ::= { enterprises 231 }

		
--  1.3.6.1.4.1.231.7
		siemensUnits OBJECT IDENTIFIER ::= { sni 7 }

		
--  1.3.6.1.4.1.231.7.1
		oenProductMibs OBJECT IDENTIFIER ::= { siemensUnits 1 }

		
--   These are the nodes for current OEN AN products
-- 
-- 1. XPressLink D
--    A node to hold management information about fiber optic
--    based ATM multiplexer systems with ADSL technology.
-- 
-- 1.3.6.1.4.1.231.7.1.2.1
		xld OBJECT IDENTIFIER ::= { an 1 }

		
--  1.3.6.1.4.1.231.7.1.2.1.1
		onu OBJECT IDENTIFIER ::= { xld 1 }

		
--  1.3.6.1.4.1.231.7.1.2.1.1.100
		xldOnuSnmVersion OBJECT IDENTIFIER ::= { onu 100 }

		
--  DEFAULT next-function-async     fsnOnuSnmVersionNext
-- DEFAULT get-function-async      fsnOnuSnmVersionGet
-- 1.3.6.1.4.1.231.7.1.2.1.1.100.1
		xldSnmMibVersion OBJECT-TYPE
			SYNTAX DisplayString (SIZE (0..10))
			MAX-ACCESS read-only
			STATUS current
			DESCRIPTION
				" Version of ONU SNMP MIB. The string is 'V1.0'. "
			::= { xldOnuSnmVersion 1 }

		
--  DEFAULT next-function-async     fsnOnuSnmVersionNext
-- DEFAULT get-function-async      fsnOnuSnmVersionGet
-- 1.3.6.1.4.1.231.7.1.2.1.1.100.2
		xldSnmAgentVersion OBJECT-TYPE
			SYNTAX DisplayString (SIZE (0..10))
			MAX-ACCESS read-only
			STATUS current
			DESCRIPTION
				" Version of ONU SNMP agent. The string is 'V1.0'. "
			::= { xldOnuSnmVersion 2 }

		
--  1.3.6.1.4.1.231.7.1.2.1.2
		olt OBJECT IDENTIFIER ::= { xld 2 }

		
--  1.3.6.1.4.1.231.7.1.2.2
		ppe OBJECT IDENTIFIER ::= { an 2 }

		
--  1.3.6.1.4.1.231.7.1.2.2.1
		she OBJECT IDENTIFIER ::= { ppe 1 }

		
--  1.3.6.1.4.1.231.7.1.2.2.1.100
		sheSnmVersion OBJECT IDENTIFIER ::= { she 100 }

		
--  1.3.6.1.4.1.231.7.1.2.2.1.100.1
		sheSnmMibVersion OBJECT-TYPE
			SYNTAX DisplayString (SIZE (0..10))
			MAX-ACCESS read-only
			STATUS current
			DESCRIPTION
				" Version of SHE SNMP MIB. The string is 'V1.000'. "
			::= { sheSnmVersion 1 }

		
--  1.3.6.1.4.1.231.7.1.2.2.1.100.2
		sheSnmAgentVersion OBJECT-TYPE
			SYNTAX DisplayString (SIZE (0..10))
			MAX-ACCESS read-only
			STATUS current
			DESCRIPTION
				" Version of SHE SNMP agent. The string is 'R1.01'. "
			::= { sheSnmVersion 2 }

		
--  1.3.6.1.4.1.231.7.1.2.2.2
		gpon OBJECT IDENTIFIER ::= { ppe 2 }

		
--  1.3.6.1.4.1.231.7.1.2.2.2.100
		gponSnmVersion OBJECT IDENTIFIER ::= { gpon 100 }

		
--  1.3.6.1.4.1.231.7.1.2.2.2.100.1
		gponSnmMibVersion OBJECT-TYPE
			SYNTAX DisplayString (SIZE (0..10))
			MAX-ACCESS read-only
			STATUS current
			DESCRIPTION
				" Version of GPON SNMP MIB. The string is 'V1.000'. "
			::= { gponSnmVersion 1 }

		
--  1.3.6.1.4.1.231.7.1.2.2.2.100.2
		gponSnmAgentVersion OBJECT-TYPE
			SYNTAX DisplayString (SIZE (0..10))
			MAX-ACCESS read-only
			STATUS current
			DESCRIPTION
				" Version of GPON SNMP agent. The string is 'R1.0'. "
			::= { gponSnmVersion 2 }

		
--  1.3.6.1.4.1.231.7.1.2.2.3
		vshe OBJECT IDENTIFIER ::= { ppe 3 }

		
--  1.3.6.1.4.1.231.7.1.2.2.3.100
		vsheSnmVersion OBJECT IDENTIFIER ::= { vshe 100 }

		
--  1.3.6.1.4.1.231.7.1.2.2.3.100.1
		vsheSnmMibVersion OBJECT-TYPE
			SYNTAX DisplayString (SIZE (0..10))
			MAX-ACCESS read-only
			STATUS current
			DESCRIPTION
				"Version of VSHE SNMP MIB. The string is 'V1.000'. "
			::= { vsheSnmVersion 1 }

		
--  1.3.6.1.4.1.231.7.1.2.2.3.100.2
		vsheSnmAgentVersion OBJECT-TYPE
			SYNTAX DisplayString (SIZE (0..10))
			MAX-ACCESS read-only
			STATUS current
			DESCRIPTION
				"Version of VSHE SNMP agent. The string is 'R1.01'. "
			::= { vsheSnmVersion 2 }

		
--  1.3.6.1.4.1.231.7.1.2.2.4
		hIX OBJECT IDENTIFIER ::= { ppe 4 }

		
--  1.3.6.1.4.1.231.7.1.2.2.4.100
		hixSnmVersion OBJECT IDENTIFIER ::= { hIX 100 }

		
--  1.3.6.1.4.1.231.7.1.2.2.4.100.1
		hixSnmMibVersion OBJECT-TYPE
			SYNTAX DisplayString (SIZE (0..10))
			MAX-ACCESS read-only
			STATUS current
			DESCRIPTION
				"Version of SNMP MIB. The string is for example 'V1.000'."
			::= { hixSnmVersion 1 }

		
--  1.3.6.1.4.1.231.7.1.2.2.4.100.2
		hixSnmAgentVersion OBJECT-TYPE
			SYNTAX DisplayString (SIZE (0..10))
			MAX-ACCESS read-only
			STATUS current
			DESCRIPTION
				"Version of SNMP agent. The string is for example 'R1.01'."
			::= { hixSnmVersion 2 }

		
--  1.3.6.1.4.1.231.7.1.2.2.5
		hiXSeries1 OBJECT IDENTIFIER ::= { ppe 5 }

		
--  1.3.6.1.4.1.231.7.1.2.2.5.100
		hiXSeries1SnmVersion OBJECT IDENTIFIER ::= { hiXSeries1 100 }

		
--  1.3.6.1.4.1.231.7.1.2.2.5.100.1
		hiXSeries1SnmMibVersion OBJECT-TYPE
			SYNTAX DisplayString (SIZE (0..10))
			MAX-ACCESS read-only
			STATUS current
			DESCRIPTION
				"Version of SNMP MIB. The string is for example 'V1.000'."
			::= { hiXSeries1SnmVersion 1 }

		
--  1.3.6.1.4.1.231.7.1.2.2.5.100.2
		hiXSeries1SnmAgentVersion OBJECT-TYPE
			SYNTAX DisplayString (SIZE (0..10))
			MAX-ACCESS read-only
			STATUS current
			DESCRIPTION
				"Version of SNMP agent. The string is for example 'R1.01'."
			::= { hiXSeries1SnmVersion 2 }

		
		anConformance OBJECT IDENTIFIER ::= { an 100 }

		
		anCompliances OBJECT IDENTIFIER ::= { anConformance 1 }

		
--  this module
		anCompliance MODULE-COMPLIANCE
			STATUS current
			DESCRIPTION 
				"The compliance statement for SNMP entities."
			MODULE -- this module
				MANDATORY-GROUPS { anGroup }
			::= { anCompliances 1 }

		
		anGroups OBJECT IDENTIFIER ::= { anConformance 2 }

		
		anGroup OBJECT-GROUP
			OBJECTS { xldSnmMibVersion, xldSnmAgentVersion, sheSnmMibVersion, sheSnmAgentVersion, gponSnmMibVersion, 
				gponSnmAgentVersion, vsheSnmMibVersion, vsheSnmAgentVersion, hixSnmMibVersion, hixSnmAgentVersion, 
				hiXSeries1SnmMibVersion, hiXSeries1SnmAgentVersion }
			STATUS current
			DESCRIPTION 
				"A collection of objects providing information about a AN product group."
			::= { anGroups 1 }

		
	
	END

--
-- an.mib
--
