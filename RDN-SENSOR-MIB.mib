-- *****************************************************************
-- RDN-SENSOR-MIB.mib:
-- Motorola BSR's Sensor MIB
--
-- Copyright (c) 2001, 2008 by Motorola, Inc. 
-- All rights reserved.
-- *****************************************************************
RDN-SENSOR-MIB DEFINITIONS ::= BEGIN

    IMPORTS
        MODULE-IDENTITY, OBJECT-TYPE, NOTIFICATION-TYPE, Integer32
            FROM SNMPv2-SMI
        DisplayString
            FROM SNMPv2-TC
        riverdelta
            FROM RDN-MIB;

    --
    -- riverdelta sensor mib module
    --

    rdnSensor MODULE-IDENTITY
        LAST-UPDATED "200808080000Z"  -- August 8, 2008
        ORGANIZATION "Motorola"
        CONTACT-INFO "Motorola
                      Customer Service
                      101 Tournament Drive
                      Horsham, PA 19044
                      US Tel: +1 888 944 4357
                      Int Tel: +1 215 323 0044
	              Fax: +1 215 323 1502
                      Email: CPSSupport@Motorola.com"
        DESCRIPTION
                "MIB module for Motorola hardware sensors.

		Copyright (C) 2001, 2008 by Motorola, Inc.
	     	All rights reserved."

	REVISION     "200808080000Z"  -- August 8, 2008
	DESCRIPTION
	    "Added Copyright Statement into MIB modules's
	    description."	
	REVISION     "200311050000Z"
        DESCRIPTION
            "+  Updated the CONTACT-INFO.
	     +  Reorder REVISION/DESCRIPTION in required 
                reverse chronological order."
	REVISION     "200304290000Z"
        DESCRIPTION
                "This `corrects past mistakes' where ASN.1 allowed hyphens
	     	 but SMIv2 states that hyphens are not allowed in 
	         identifiers for objects or for labels on enumerated 
                 integer values. 

		 Hyphens where removed from the lables on enumerated integer
	         values from the 'rdnSensorStatus' object.
		
	         Also cleans up the CONTACT-INFO."
	REVISION     "200108070000Z"
        DESCRIPTION
                "Initial creation."
        ::= { riverdelta 5 }


    rdnSensorTable OBJECT-TYPE
        SYNTAX  SEQUENCE OF RdnSensorEntry
        MAX-ACCESS  not-accessible
        STATUS  current
        DESCRIPTION
                 "Hardware Sensor table."
        ::= { rdnSensor 1 }

    rdnSensorEntry OBJECT-TYPE
        SYNTAX RdnSensorEntry
        MAX-ACCESS  not-accessible
        STATUS  current
        DESCRIPTION
                 "Hardware Sensor table entry."
        INDEX { rdnSensorIndex }
       ::= { rdnSensorTable 1 }

    RdnSensorEntry ::=
        SEQUENCE {
            rdnSensorIndex
                Integer32,
            rdnSensorDescr
                DisplayString,
            rdnSensorObjectID
                OBJECT IDENTIFIER,
            rdnSensorValue
                Integer32,
            rdnSensorThresholdHigh
                Integer32,
            rdnSensorThresholdLow
                Integer32,
            rdnSensorStatus
                INTEGER,
            rdnSensorNotificationEnable
                INTEGER
        }

    --
    -- start of sensor table
    --

    rdnSensorIndex OBJECT-TYPE
        SYNTAX  Integer32
        MAX-ACCESS  read-only
        STATUS  current
        DESCRIPTION
                "An index uniquely identifying an entry
                in the rdnSensorTable."
        ::= { rdnSensorEntry 1 }

    rdnSensorDescr OBJECT-TYPE
        SYNTAX  DisplayString
        MAX-ACCESS  read-only
        STATUS  current
        DESCRIPTION
                "A text description of the sensor described
                by this table entry."
        ::= { rdnSensorEntry 2 }

    rdnSensorObjectID OBJECT-TYPE
        SYNTAX  OBJECT IDENTIFIER
        MAX-ACCESS  read-only
        STATUS  current
        DESCRIPTION
                "The object identifier (OID) describing the
                type of sensor described by this entry."
        ::= { rdnSensorEntry 3 }

    rdnSensorValue OBJECT-TYPE
        SYNTAX  Integer32
        MAX-ACCESS  read-only
        STATUS  current
        DESCRIPTION
                "The temperature value in degrees Celsius of
                the sensor described by this entry."
        ::= { rdnSensorEntry 4 }

    rdnSensorThresholdHigh OBJECT-TYPE
        SYNTAX  Integer32
        MAX-ACCESS  read-write
        STATUS  current
        DESCRIPTION
                "The high temperature threshold value of normal
                operating conditions described by this entry."
        ::= { rdnSensorEntry 5 }

    rdnSensorThresholdLow OBJECT-TYPE
        SYNTAX  Integer32
        MAX-ACCESS  read-write
        STATUS  current
        DESCRIPTION
                "The low temperature threshold value of normal
                operating conditions described by this entry."
        ::= { rdnSensorEntry 6 }

    rdnSensorStatus OBJECT-TYPE
        SYNTAX  INTEGER {
             unknown(1),
             ok(2),
             belowMin(3),
             aboveMax(4),
             defective(5),
             notPresent(6)
             }
        MAX-ACCESS  read-only
        STATUS  current
        DESCRIPTION
                "The operational status of the sensor described
                by this entry."
        ::= { rdnSensorEntry 7 }

    rdnSensorNotificationEnable OBJECT-TYPE
        SYNTAX  INTEGER { enabled(1), disabled(2) }
        MAX-ACCESS  read-write
        STATUS  current
        DESCRIPTION
                "The notification enable of the sensor
                described by this entry."
        ::= { rdnSensorEntry 8 }


    --
    -- sensor notifications
    --

    rdnSensorNotifications       OBJECT IDENTIFIER ::= { rdnSensor 2 }
    rdnSensorNotificationsPrefix OBJECT IDENTIFIER ::= { rdnSensorNotifications 0 }

    rdnSensorThresholdExceeded NOTIFICATION-TYPE
        OBJECTS {
             rdnSensorIndex,
		     rdnSensorDescr,
             rdnSensorObjectID,
             rdnSensorValue,
             rdnSensorThresholdHigh,
             rdnSensorThresholdLow,
             rdnSensorStatus
             }
        STATUS  current
        DESCRIPTION
                "The notification sent for the alarm condition
                triggered when the temperature of a sensor exceeds
                its low or high threshold level."
        ::= { rdnSensorNotificationsPrefix 1 }

END
