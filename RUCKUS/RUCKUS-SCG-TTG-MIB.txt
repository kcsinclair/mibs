--
-- Copyright 2010-2014 Ruckus Wireless, Inc. All rights reserved.
--
-- RUCKUS WIRELESS, INC. CONFIDENTIAL - 
-- This is an unpublished, proprietary work of Ruckus Wireless, Inc., and is 
-- fully protected under copyright and trade secret laws. You may not view, 
-- use, disclose, copy, or distribute this file or any information contained 
-- herein except pursuant to a valid license from Ruckus. 
--

RUCKUS-SCG-TTG-MIB DEFINITIONS ::= BEGIN

IMPORTS
	ruckusSCGTTGModule FROM RUCKUS-ROOT-MIB
	MODULE-IDENTITY,
	OBJECT-TYPE,
	Counter32,
	Integer32,
	Unsigned32,
	IpAddress FROM SNMPv2-SMI
	DisplayString FROM SNMPv2-TC;

ruckusTTGMIB MODULE-IDENTITY
    LAST-UPDATED "201405191100Z"
    ORGANIZATION "Ruckus Wireless, Inc."
    CONTACT-INFO
        "Ruckus Wireless, Inc.

        350 West Java Dr.
        Sunnyvale, CA 94089
        USA

        T: +1 (650) 265-4200
        F: +1 (408) 738-2065
        EMail: info@ruckuswireless.com
        Web: www.ruckuswireless.com"
    DESCRIPTION
        "Ruckus TTG MIB"
    ::= { ruckusSCGTTGModule 1 }

ruckusTTGObjects OBJECT IDENTIFIER     ::= { ruckusTTGMIB 1 }



ruckusAAAInfo OBJECT IDENTIFIER    ::= { ruckusTTGObjects 1 }
ruckusAAATable OBJECT-TYPE
	SYNTAX  SEQUENCE OF RuckusAAAEntry
	MAX-ACCESS not-accessible
	STATUS current
	DESCRIPTION
		"ruckusAAATable"
	::= { ruckusAAAInfo 1 }

ruckusAAAEntry OBJECT-TYPE
	SYNTAX RuckusAAAEntry
	MAX-ACCESS not-accessible
	STATUS current
	DESCRIPTION
		"ruckusAAAEntry"
	INDEX {
		ruckusAAAIndex }
	::= { ruckusAAATable 1 }

RuckusAAAEntry ::= SEQUENCE {
	 ruckusAAAAaaIp	DisplayString,
	 ruckusAAANumSuccAuthPerm	Counter64,
	 ruckusAAANumFailAuthPerm	Counter64,
	 ruckusAAANumSuccAuthPsd	Counter64,
	 ruckusAAANumFailAuthPsd	Counter64,
	 ruckusAAANumSuccFastAuth	Counter64,
	 ruckusAAANumFailFastAuth	Counter64,
	 ruckusAAANumAuthUnknPsd	Counter64,
	 ruckusAAANumAuthUnknFR	Counter64,
	 ruckusAAANumIncompleteAuth	Counter64,
	 ruckusAAANumSuccAcc	Counter64,
	 ruckusAAANumFailAcc	Counter64,
	 ruckusAAANumRadAcsRq	Counter64,
	 ruckusAAANumRadAcsAcpt	Counter64,
	 ruckusAAANumRadAcsChlg	Counter64,
	 ruckusAAANumRadAcsRej	Counter64,
	 ruckusAAANumRadAccRq	Counter64,
	 ruckusAAANumRadAccAcpt	Counter64,
	 ruckusAAANumRadCoaRq	Counter64,
	 ruckusAAANumSuccCoaAcpt	Counter64,
	 ruckusAAANumFailCoaAcpt	Counter64,
	 ruckusAAANumRadDmRq	Counter64,
	 ruckusAAANumSuccDmAcpt	Counter64,
	 ruckusAAANumFailDmAcpt	Counter64,
	 ruckusAAAIndex	Integer32
}

ruckusAAAAaaIp OBJECT-TYPE
	SYNTAX DisplayString
	MAX-ACCESS read-only
	STATUS current
	DESCRIPTION
		"ruckusAAAAaaIp"
	::= { ruckusAAAEntry 1 }

ruckusAAANumSuccAuthPerm OBJECT-TYPE
	SYNTAX Counter64
	MAX-ACCESS read-only
	STATUS current
	DESCRIPTION
		"ruckusAAANumSuccAuthPerm"
	::= { ruckusAAAEntry 2 }

ruckusAAANumFailAuthPerm OBJECT-TYPE
	SYNTAX Counter64
	MAX-ACCESS read-only
	STATUS current
	DESCRIPTION
		"ruckusAAANumFailAuthPerm"
	::= { ruckusAAAEntry 3 }

ruckusAAANumSuccAuthPsd OBJECT-TYPE
	SYNTAX Counter64
	MAX-ACCESS read-only
	STATUS current
	DESCRIPTION
		"ruckusAAANumSuccAuthPsd"
	::= { ruckusAAAEntry 4 }

ruckusAAANumFailAuthPsd OBJECT-TYPE
	SYNTAX Counter64
	MAX-ACCESS read-only
	STATUS current
	DESCRIPTION
		"ruckusAAANumFailAuthPsd"
	::= { ruckusAAAEntry 5 }

ruckusAAANumSuccFastAuth OBJECT-TYPE
	SYNTAX Counter64
	MAX-ACCESS read-only
	STATUS current
	DESCRIPTION
		"ruckusAAANumSuccFastAuth"
	::= { ruckusAAAEntry 6 }

ruckusAAANumFailFastAuth OBJECT-TYPE
	SYNTAX Counter64
	MAX-ACCESS read-only
	STATUS current
	DESCRIPTION
		"ruckusAAANumFailFastAuth"
	::= { ruckusAAAEntry 7 }

ruckusAAANumAuthUnknPsd OBJECT-TYPE
	SYNTAX Counter64
	MAX-ACCESS read-only
	STATUS current
	DESCRIPTION
		"ruckusAAANumAuthUnknPsd"
	::= { ruckusAAAEntry 8 }

ruckusAAANumAuthUnknFR OBJECT-TYPE
	SYNTAX Counter64
	MAX-ACCESS read-only
	STATUS current
	DESCRIPTION
		"ruckusAAANumAuthUnknFR"
	::= { ruckusAAAEntry 9 }

ruckusAAANumIncompleteAuth OBJECT-TYPE
	SYNTAX Counter64
	MAX-ACCESS read-only
	STATUS current
	DESCRIPTION
		"ruckusAAANumIncompleteAuth"
	::= { ruckusAAAEntry 10 }

ruckusAAANumSuccAcc OBJECT-TYPE
	SYNTAX Counter64
	MAX-ACCESS read-only
	STATUS current
	DESCRIPTION
		"ruckusAAANumSuccAcc"
	::= { ruckusAAAEntry 11 }

ruckusAAANumFailAcc OBJECT-TYPE
	SYNTAX Counter64
	MAX-ACCESS read-only
	STATUS current
	DESCRIPTION
		"ruckusAAANumFailAcc"
	::= { ruckusAAAEntry 12 }

ruckusAAANumRadAcsRq OBJECT-TYPE
	SYNTAX Counter64
	MAX-ACCESS read-only
	STATUS current
	DESCRIPTION
		"ruckusAAANumRadAcsRq"
	::= { ruckusAAAEntry 13 }

ruckusAAANumRadAcsAcpt OBJECT-TYPE
	SYNTAX Counter64
	MAX-ACCESS read-only
	STATUS current
	DESCRIPTION
		"ruckusAAANumRadAcsAcpt"
	::= { ruckusAAAEntry 14 }

ruckusAAANumRadAcsChlg OBJECT-TYPE
	SYNTAX Counter64
	MAX-ACCESS read-only
	STATUS current
	DESCRIPTION
		"ruckusAAANumRadAcsChlg"
	::= { ruckusAAAEntry 15 }

ruckusAAANumRadAcsRej OBJECT-TYPE
	SYNTAX Counter64
	MAX-ACCESS read-only
	STATUS current
	DESCRIPTION
		"ruckusAAANumRadAcsRej"
	::= { ruckusAAAEntry 16 }

ruckusAAANumRadAccRq OBJECT-TYPE
	SYNTAX Counter64
	MAX-ACCESS read-only
	STATUS current
	DESCRIPTION
		"ruckusAAANumRadAccRq"
	::= { ruckusAAAEntry 17 }

ruckusAAANumRadAccAcpt OBJECT-TYPE
	SYNTAX Counter64
	MAX-ACCESS read-only
	STATUS current
	DESCRIPTION
		"ruckusAAANumRadAccAcpt"
	::= { ruckusAAAEntry 18 }

ruckusAAANumRadCoaRq OBJECT-TYPE
	SYNTAX Counter64
	MAX-ACCESS read-only
	STATUS current
	DESCRIPTION
		"ruckusAAANumRadCoaRq"
	::= { ruckusAAAEntry 19 }

ruckusAAANumSuccCoaAcpt OBJECT-TYPE
	SYNTAX Counter64
	MAX-ACCESS read-only
	STATUS current
	DESCRIPTION
		"ruckusAAANumSuccCoaAcpt"
	::= { ruckusAAAEntry 20 }

ruckusAAANumFailCoaAcpt OBJECT-TYPE
	SYNTAX Counter64
	MAX-ACCESS read-only
	STATUS current
	DESCRIPTION
		"ruckusAAANumFailCoaAcpt"
	::= { ruckusAAAEntry 21 }

ruckusAAANumRadDmRq OBJECT-TYPE
	SYNTAX Counter64
	MAX-ACCESS read-only
	STATUS current
	DESCRIPTION
		"ruckusAAANumRadDmRq"
	::= { ruckusAAAEntry 22 }

ruckusAAANumSuccDmAcpt OBJECT-TYPE
	SYNTAX Counter64
	MAX-ACCESS read-only
	STATUS current
	DESCRIPTION
		"ruckusAAANumSuccDmAcpt"
	::= { ruckusAAAEntry 23 }

ruckusAAANumFailDmAcpt OBJECT-TYPE
	SYNTAX Counter64
	MAX-ACCESS read-only
	STATUS current
	DESCRIPTION
		"ruckusAAANumFailDmAcpt"
	::= { ruckusAAAEntry 24 }

ruckusAAAIndex OBJECT-TYPE
	SYNTAX Integer32
	MAX-ACCESS read-only
	STATUS current
	DESCRIPTION
		"ruckusAAAIndex"
	::= { ruckusAAAEntry 99 }


	
ruckusAAAProxyInfo OBJECT IDENTIFIER ::= { ruckusTTGObjects 2 }
ruckusAAAProxyTable OBJECT-TYPE
	SYNTAX  SEQUENCE OF RuckusAAAProxyEntry
	MAX-ACCESS not-accessible
	STATUS current
	DESCRIPTION
		"ruckusAAAProxyTable"
	::= { ruckusAAAProxyInfo 1 }

ruckusAAAProxyEntry OBJECT-TYPE
	SYNTAX RuckusAAAProxyEntry
	MAX-ACCESS not-accessible
	STATUS current
	DESCRIPTION
		"ruckusAAAProxyEntry"
	INDEX {
		ruckusAAAProxyIndex }
	::= { ruckusAAAProxyTable 1 }

RuckusAAAProxyEntry ::= SEQUENCE {
	ruckusAAAProxyAaaIp	DisplayString,
	ruckusAAAProxyNumSuccAuth	Counter64,
	ruckusAAAProxyNumFailAuth	Counter64,
	ruckusAAAProxyNumIncmpltAuth	Counter64,
	ruckusAAAProxyNumSuccAcc	Counter64,
	ruckusAAAProxyNumFailAcc	Counter64,
	ruckusAAAProxyNumAcsRqRcvdNas	Counter64,
	ruckusAAAProxyNumAcsRqSntAaa	Counter64,
	ruckusAAAProxyNumAcsChRcvdAaa	Counter64,
	ruckusAAAProxyNumAcsChSntNas	Counter64,
	ruckusAAAProxyNumAcsAcpRcvdAaa	Counter64,
	ruckusAAAProxyNumAcsAcpSntNas	Counter64,
	ruckusAAAProxyNumAcsRejRcvdAaa	Counter64,
	ruckusAAAProxyNumAcsRejSntNas	Counter64,
	ruckusAAAProxyNumAccRqRcvdNas	Counter64,
	ruckusAAAProxyNumAccRqSntAaa	Counter64,
	ruckusAAAProxyNumAccRspRcdAaa	Counter64,
	ruckusAAAProxyNumAccRspSntNas	Counter64,
	ruckusAAAProxyNumCoaRcvdAaa	Counter64,
	ruckusAAAProxyNumCoaSucSntAaa	Counter64,
	ruckusAAAProxyNumCoaFailSntAaa	Counter64,
	ruckusAAAProxyNumDmRcvdAaa	Counter64,
	ruckusAAAProxyNumDmSntNas	Counter64,
	ruckusAAAProxyNumDmSucRcdNas	Counter64,
	ruckusAAAProxyNumDmSucSntAaa	Counter64,
	ruckusAAAProxyNumDmFailRcdNas	Counter64,
	ruckusAAAProxyNumDmFailSntAaa	Counter64,
	 ruckusAAAProxyIndex	Integer32
}

ruckusAAAProxyAaaIp OBJECT-TYPE
	SYNTAX DisplayString
	MAX-ACCESS read-only
	STATUS current
	DESCRIPTION
		"ruckusAAAProxyAaaIp"
	::= { ruckusAAAProxyEntry 1 }

ruckusAAAProxyNumSuccAuth OBJECT-TYPE
	SYNTAX Counter64
	MAX-ACCESS read-only
	STATUS current
	DESCRIPTION
		"ruckusAAAProxyNumSuccAuth"
	::= { ruckusAAAProxyEntry 2 }

ruckusAAAProxyNumFailAuth OBJECT-TYPE
	SYNTAX Counter64
	MAX-ACCESS read-only
	STATUS current
	DESCRIPTION
		"ruckusAAAProxyNumFailAuth"
	::= { ruckusAAAProxyEntry 3 }

ruckusAAAProxyNumIncmpltAuth OBJECT-TYPE
	SYNTAX Counter64
	MAX-ACCESS read-only
	STATUS current
	DESCRIPTION
		"ruckusAAAProxyNumIncmpltAuth"
	::= { ruckusAAAProxyEntry 4 }

ruckusAAAProxyNumSuccAcc OBJECT-TYPE
	SYNTAX Counter64
	MAX-ACCESS read-only
	STATUS current
	DESCRIPTION
		"ruckusAAAProxyNumSuccAcc"
	::= { ruckusAAAProxyEntry 5 }

ruckusAAAProxyNumFailAcc OBJECT-TYPE
	SYNTAX Counter64
	MAX-ACCESS read-only
	STATUS current
	DESCRIPTION
		"ruckusAAAProxyNumFailAcc"
	::= { ruckusAAAProxyEntry 6 }

ruckusAAAProxyNumAcsRqRcvdNas OBJECT-TYPE
	SYNTAX Counter64
	MAX-ACCESS read-only
	STATUS current
	DESCRIPTION
		"ruckusAAAProxyNumAcsRqRcvdNas"
	::= { ruckusAAAProxyEntry 7 }

ruckusAAAProxyNumAcsRqSntAaa OBJECT-TYPE
	SYNTAX Counter64
	MAX-ACCESS read-only
	STATUS current
	DESCRIPTION
		"ruckusAAAProxyNumAcsRqSntAaa"
	::= { ruckusAAAProxyEntry 8 }

ruckusAAAProxyNumAcsChRcvdAaa OBJECT-TYPE
	SYNTAX Counter64
	MAX-ACCESS read-only
	STATUS current
	DESCRIPTION
		"ruckusAAAProxyNumAcsChRcvdAaa"
	::= { ruckusAAAProxyEntry 9 }

ruckusAAAProxyNumAcsChSntNas OBJECT-TYPE
	SYNTAX Counter64
	MAX-ACCESS read-only
	STATUS current
	DESCRIPTION
		"ruckusAAAProxyNumAcsChSntNas"
	::= { ruckusAAAProxyEntry 10 }

ruckusAAAProxyNumAcsAcpRcvdAaa OBJECT-TYPE
	SYNTAX Counter64
	MAX-ACCESS read-only
	STATUS current
	DESCRIPTION
		"ruckusAAAProxyNumAcsAcpRcvdAaa"
	::= { ruckusAAAProxyEntry 11 }

ruckusAAAProxyNumAcsAcpSntNas OBJECT-TYPE
	SYNTAX Counter64
	MAX-ACCESS read-only
	STATUS current
	DESCRIPTION
		"ruckusAAAProxyNumAcsAcpSntNas"
	::= { ruckusAAAProxyEntry 12 }

ruckusAAAProxyNumAcsRejRcvdAaa OBJECT-TYPE
	SYNTAX Counter64
	MAX-ACCESS read-only
	STATUS current
	DESCRIPTION
		"ruckusAAAProxyNumAcsRejRcvdAaa"
	::= { ruckusAAAProxyEntry 13 }

ruckusAAAProxyNumAcsRejSntNas OBJECT-TYPE
	SYNTAX Counter64
	MAX-ACCESS read-only
	STATUS current
	DESCRIPTION
		"ruckusAAAProxyNumAcsRejSntNas"
	::= { ruckusAAAProxyEntry 14 }

ruckusAAAProxyNumAccRqRcvdNas OBJECT-TYPE
	SYNTAX Counter64
	MAX-ACCESS read-only
	STATUS current
	DESCRIPTION
		"ruckusAAAProxyNumAccRqRcvdNas"
	::= { ruckusAAAProxyEntry 15 }

ruckusAAAProxyNumAccRqSntAaa OBJECT-TYPE
	SYNTAX Counter64
	MAX-ACCESS read-only
	STATUS current
	DESCRIPTION
		"ruckusAAAProxyNumAccRqSntAaa"
	::= { ruckusAAAProxyEntry 16 }

ruckusAAAProxyNumAccRspRcdAaa OBJECT-TYPE
	SYNTAX Counter64
	MAX-ACCESS read-only
	STATUS current
	DESCRIPTION
		"ruckusAAAProxyNumAccRspRcdAaa"
	::= { ruckusAAAProxyEntry 17 }

ruckusAAAProxyNumAccRspSntNas OBJECT-TYPE
	SYNTAX Counter64
	MAX-ACCESS read-only
	STATUS current
	DESCRIPTION
		"ruckusAAAProxyNumAccRspSntNas"
	::= { ruckusAAAProxyEntry 18 }

ruckusAAAProxyNumCoaRcvdAaa OBJECT-TYPE
	SYNTAX Counter64
	MAX-ACCESS read-only
	STATUS current
	DESCRIPTION
		"ruckusAAAProxyNumCoaRcvdAaa"
	::= { ruckusAAAProxyEntry 19 }

ruckusAAAProxyNumCoaSucSntAaa OBJECT-TYPE
	SYNTAX Counter64
	MAX-ACCESS read-only
	STATUS current
	DESCRIPTION
		"ruckusAAAProxyNumCoaSucSntAaa"
	::= { ruckusAAAProxyEntry 20 }

ruckusAAAProxyNumCoaFailSntAaa OBJECT-TYPE
	SYNTAX Counter64
	MAX-ACCESS read-only
	STATUS current
	DESCRIPTION
		"ruckusAAAProxyNumCoaFailSntAaa"
	::= { ruckusAAAProxyEntry 21 }

ruckusAAAProxyNumDmRcvdAaa OBJECT-TYPE
	SYNTAX Counter64
	MAX-ACCESS read-only
	STATUS current
	DESCRIPTION
		"ruckusAAAProxyNumDmRcvdAaa"
	::= { ruckusAAAProxyEntry 22 }

ruckusAAAProxyNumDmSntNas OBJECT-TYPE
	SYNTAX Counter64
	MAX-ACCESS read-only
	STATUS current
	DESCRIPTION
		"ruckusAAAProxyNumDmSntNas"
	::= { ruckusAAAProxyEntry 23 }

ruckusAAAProxyNumDmSucRcdNas OBJECT-TYPE
	SYNTAX Counter64
	MAX-ACCESS read-only
	STATUS current
	DESCRIPTION
		"ruckusAAAProxyNumDmSucRcdNas"
	::= { ruckusAAAProxyEntry 24 }

ruckusAAAProxyNumDmSucSntAaa OBJECT-TYPE
	SYNTAX Counter64
	MAX-ACCESS read-only
	STATUS current
	DESCRIPTION
		"ruckusAAAProxyNumDmSucSntAaa"
	::= { ruckusAAAProxyEntry 25 }

ruckusAAAProxyNumDmFailRcdNas OBJECT-TYPE
	SYNTAX Counter64
	MAX-ACCESS read-only
	STATUS current
	DESCRIPTION
		"ruckusAAAProxyNumDmFailRcdNas"
	::= { ruckusAAAProxyEntry 26 }

ruckusAAAProxyNumDmFailSntAaa OBJECT-TYPE
	SYNTAX Counter64
	MAX-ACCESS read-only
	STATUS current
	DESCRIPTION
		"ruckusAAAProxyNumDmFailSntAaa"
	::= { ruckusAAAProxyEntry 27 }

ruckusAAAProxyIndex OBJECT-TYPE
	SYNTAX Integer32
	MAX-ACCESS read-only
	STATUS current
	DESCRIPTION
		"ruckusAAAProxyIndex"
	::= { ruckusAAAProxyEntry 99 }



ruckusCGFInfo OBJECT IDENTIFIER    ::= { ruckusTTGObjects 3 }
ruckusCGFTable OBJECT-TYPE
	SYNTAX  SEQUENCE OF RuckusCGFEntry
	MAX-ACCESS not-accessible
	STATUS current
	DESCRIPTION
		"ruckusCGFTable"
	::= { ruckusCGFInfo 1 }

ruckusCGFEntry OBJECT-TYPE
	SYNTAX RuckusCGFEntry
	MAX-ACCESS not-accessible
	STATUS current
	DESCRIPTION
		"ruckusCGFEntry"
	INDEX {
		ruckusCGFIndex }
	::= { ruckusCGFTable 1 }

RuckusCGFEntry ::= SEQUENCE {
	 ruckusCGFCgfSrvcName	DisplayString,
	 ruckusCGFCgfIp	DisplayString,
	 ruckusCGFNumSuccCdrTxfd	Counter64,
	 ruckusCGFNumCdrTxfrFail	Counter64,
	 ruckusCGFNumCdrPossDup	Counter64,
	 ruckusCGFNumCdrRlsReq	Counter64,
	 ruckusCGFNumCdrCnclReq	Counter64,
	 ruckusCGFNumDrtrReqSnt	Counter64,
	 ruckusCGFNumDrtrSucRspRcvd	Counter64,
	 ruckusCGFNumDrtrFailRspRcvd	Counter64,
	 ruckusCGFIndex	Integer32
}

ruckusCGFCgfSrvcName OBJECT-TYPE
	SYNTAX DisplayString
	MAX-ACCESS read-only
	STATUS current
	DESCRIPTION
		"ruckusCGFCgfSrvcName"
	::= { ruckusCGFEntry 1 }

ruckusCGFCgfIp OBJECT-TYPE
	SYNTAX DisplayString
	MAX-ACCESS read-only
	STATUS current
	DESCRIPTION
		"ruckusCGFCgfIp"
	::= { ruckusCGFEntry 2 }

ruckusCGFNumSuccCdrTxfd OBJECT-TYPE
	SYNTAX Counter64
	MAX-ACCESS read-only
	STATUS current
	DESCRIPTION
		"ruckusCGFNumSuccCdrTxfd"
	::= { ruckusCGFEntry 3 }

ruckusCGFNumCdrTxfrFail OBJECT-TYPE
	SYNTAX Counter64
	MAX-ACCESS read-only
	STATUS current
	DESCRIPTION
		"ruckusCGFNumCdrTxfrFail"
	::= { ruckusCGFEntry 4 }

ruckusCGFNumCdrPossDup OBJECT-TYPE
	SYNTAX Counter64
	MAX-ACCESS read-only
	STATUS current
	DESCRIPTION
		"ruckusCGFNumCdrPossDup"
	::= { ruckusCGFEntry 5 }

ruckusCGFNumCdrRlsReq OBJECT-TYPE
	SYNTAX Counter64
	MAX-ACCESS read-only
	STATUS current
	DESCRIPTION
		"ruckusCGFNumCdrRlsReq"
	::= { ruckusCGFEntry 6 }

ruckusCGFNumCdrCnclReq OBJECT-TYPE
	SYNTAX Counter64
	MAX-ACCESS read-only
	STATUS current
	DESCRIPTION
		"ruckusCGFNumCdrCnclReq"
	::= { ruckusCGFEntry 7 }

ruckusCGFNumDrtrReqSnt OBJECT-TYPE
	SYNTAX Counter64
	MAX-ACCESS read-only
	STATUS current
	DESCRIPTION
		"ruckusCGFNumDrtrReqSnt"
	::= { ruckusCGFEntry 8 }

ruckusCGFNumDrtrSucRspRcvd OBJECT-TYPE
	SYNTAX Counter64
	MAX-ACCESS read-only
	STATUS current
	DESCRIPTION
		"ruckusCGFNumDrtrSucRspRcvd"
	::= { ruckusCGFEntry 9 }

ruckusCGFNumDrtrFailRspRcvd OBJECT-TYPE
	SYNTAX Counter64
	MAX-ACCESS read-only
	STATUS current
	DESCRIPTION
		"ruckusCGFNumDrtrFailRspRcvd"
	::= { ruckusCGFEntry 10 }

ruckusCGFIndex OBJECT-TYPE
	SYNTAX Integer32
	MAX-ACCESS read-only
	STATUS current
	DESCRIPTION
		"ruckusCGFIndex"
	::= { ruckusCGFEntry 99 }

ruckusGTPUInfo OBJECT IDENTIFIER ::= { ruckusTTGObjects 4 }
ruckusGTPUTable OBJECT-TYPE
	SYNTAX  SEQUENCE OF RuckusGTPUEntry
	MAX-ACCESS not-accessible
	STATUS current
	DESCRIPTION
		"ruckusGTPUTable"
	::= { ruckusGTPUInfo 1 }

ruckusGTPUEntry OBJECT-TYPE
	SYNTAX RuckusGTPUEntry
	MAX-ACCESS not-accessible
	STATUS current
	DESCRIPTION
		"ruckusGTPUEntry"
	INDEX {
		ruckusGTPUIndex }
	::= { ruckusGTPUTable 1 }

RuckusGTPUEntry ::= SEQUENCE {
	 ruckusGTPUGgsnIPAddr	DisplayString,
	 ruckusGTPUTxPkts	Counter64,
	 ruckusGTPUTxBytes	Counter64,
	 ruckusGTPURxPkts	Counter64,
	 ruckusGTPURxBytes	Counter64,
	 ruckusGTPUTxDrops	Counter64,
	 ruckusGTPURxDrops	Counter64,
	 ruckusGTPUNumBadGTPU	Counter64,
	 ruckusGTPUNumRXTeidInvalid	Counter64,
	 ruckusGTPUNumTXTeidInvalid	Counter64,
	 ruckusGTPUNumOfEchoRX	Counter64,
	 ruckusGTPUIndex	Integer32
}

ruckusGTPUGgsnIPAddr OBJECT-TYPE
	SYNTAX DisplayString
	MAX-ACCESS read-only
	STATUS current
	DESCRIPTION
		"ruckusGTPUGgsnIPAddr"
	::= { ruckusGTPUEntry 1 }

ruckusGTPUTxPkts OBJECT-TYPE
	SYNTAX Counter64
	MAX-ACCESS read-only
	STATUS current
	DESCRIPTION
		"ruckusGTPUTxPkts"
	::= { ruckusGTPUEntry 2 }

ruckusGTPUTxBytes OBJECT-TYPE
	SYNTAX Counter64
	MAX-ACCESS read-only
	STATUS current
	DESCRIPTION
		"ruckusGTPUTxBytes"
	::= { ruckusGTPUEntry 3 }

ruckusGTPURxPkts OBJECT-TYPE
	SYNTAX Counter64
	MAX-ACCESS read-only
	STATUS current
	DESCRIPTION
		"ruckusGTPURxPkts"
	::= { ruckusGTPUEntry 4 }

ruckusGTPURxBytes OBJECT-TYPE
	SYNTAX Counter64
	MAX-ACCESS read-only
	STATUS current
	DESCRIPTION
		"ruckusGTPURxBytes"
	::= { ruckusGTPUEntry 5 }

ruckusGTPUTxDrops OBJECT-TYPE
	SYNTAX Counter64
	MAX-ACCESS read-only
	STATUS current
	DESCRIPTION
		"ruckusGTPUTxDrops"
	::= { ruckusGTPUEntry 6 }

ruckusGTPURxDrops OBJECT-TYPE
	SYNTAX Counter64
	MAX-ACCESS read-only
	STATUS current
	DESCRIPTION
		"ruckusGTPURxDrops"
	::= { ruckusGTPUEntry 7 }

ruckusGTPUNumBadGTPU OBJECT-TYPE
	SYNTAX Counter64
	MAX-ACCESS read-only
	STATUS current
	DESCRIPTION
		"ruckusGTPUNumBadGTPU"
	::= { ruckusGTPUEntry 8 }

ruckusGTPUNumRXTeidInvalid OBJECT-TYPE
	SYNTAX Counter64
	MAX-ACCESS read-only
	STATUS current
	DESCRIPTION
		"ruckusGTPUNumRXTeidInvalid"
	::= { ruckusGTPUEntry 9 }

ruckusGTPUNumTXTeidInvalid OBJECT-TYPE
	SYNTAX Counter64
	MAX-ACCESS read-only
	STATUS current
	DESCRIPTION
		"ruckusGTPUNumTXTeidInvalid"
	::= { ruckusGTPUEntry 10 }

ruckusGTPUNumOfEchoRX OBJECT-TYPE
	SYNTAX Counter64
	MAX-ACCESS read-only
	STATUS current
	DESCRIPTION
		"ruckusGTPUNumOfEchoRX"
	::= { ruckusGTPUEntry 11 }

ruckusGTPUIndex OBJECT-TYPE
	SYNTAX Integer32
	MAX-ACCESS read-only
	STATUS current
	DESCRIPTION
		"ruckusGTPUIndex"
	::= { ruckusGTPUEntry 99 }


ruckusGGSNGTPCInfo OBJECT IDENTIFIER ::= { ruckusTTGObjects 5 }
ruckusGGSNGTPCTable OBJECT-TYPE
	SYNTAX  SEQUENCE OF RuckusGGSNGTPCEntry
	MAX-ACCESS not-accessible
	STATUS current
	DESCRIPTION
		"ruckusGGSNGTPCTable"
	::= { ruckusGGSNGTPCInfo 1 }

ruckusGGSNGTPCEntry OBJECT-TYPE
	SYNTAX RuckusGGSNGTPCEntry
	MAX-ACCESS not-accessible
	STATUS current
	DESCRIPTION
		"ruckusGGSNGTPCEntry"
	INDEX {
		ruckusGGSNGTPCIndex }
	::= { ruckusGGSNGTPCTable 1 }

RuckusGGSNGTPCEntry ::= SEQUENCE {
	 ruckusGGSNGTPCGgsnIp	DisplayString,
	 ruckusGGSNGTPCNumActPdp	Counter64,
	 ruckusGGSNGTPCSuccPdpCrt	Counter64,
	 ruckusGGSNGTPCFailPdpCrt	Counter64,
	 ruckusGGSNGTPCSuccPdpUpdRcvd	Counter64,
	 ruckusGGSNGTPCFailPdpUpdRcvd	Counter64,
	 ruckusGGSNGTPCSuccPdpUpdInitRM	Counter64,
	 ruckusGGSNGTPCFailPdpUpdInitRM	Counter64,
	 ruckusGGSNGTPCSuccPdpUpdInitAAA	Counter64,
	 ruckusGGSNGTPCFailPdpUpdInitAAA	Counter64,
	 ruckusGGSNGTPCSuccPdpUpdInitHLR	Counter64,
	 ruckusGGSNGTPCFailPdpUpdInitHLR	Counter64,
	 ruckusGGSNGTPCSuccDelPdpRcvd	Counter64,
	 ruckusGGSNGTPCFailDelPdpRcvd	Counter64,
	 ruckusGGSNGTPCSuccDelPdpInitErr	Counter64,
	 ruckusGGSNGTPCFailDelPdpInitErr	Counter64,
	 ruckusGGSNGTPCSuccDelPdpInitDM	Counter64,
	 ruckusGGSNGTPCFailDelPdpInitDM	Counter64,
	 ruckusGGSNGTPCSuccDelPdpInitHLR	Counter64,
	 ruckusGGSNGTPCFailDelPdpInitHLR	Counter64,
	 ruckusGGSNGTPCSuccDelPdpInitSCG	Counter64,
	 ruckusGGSNGTPCFailDelPdpInitSCG	Counter64,
	 ruckusGGSNGTPCSuccDelPdpInitAP	Counter64,
	 ruckusGGSNGTPCFailDelPdpInitAP	Counter64,
	 ruckusGGSNGTPCSuccDelPdpInitD	Counter64,
	 ruckusGGSNGTPCFailDelPdpInitD	Counter64,
	 ruckusGGSNGTPCSuccDelPdpInitClnt	Counter64,
	 ruckusGGSNGTPCFailDelPdpInitClnt	Counter64,
	 ruckusGGSNGTPCIndex	Integer32
}

ruckusGGSNGTPCGgsnIp OBJECT-TYPE
	SYNTAX DisplayString
	MAX-ACCESS read-only
	STATUS current
	DESCRIPTION
		"ruckusGGSNGTPCGgsnIp"
	::= { ruckusGGSNGTPCEntry 1 }

ruckusGGSNGTPCNumActPdp OBJECT-TYPE
	SYNTAX Counter64
	MAX-ACCESS read-only
	STATUS current
	DESCRIPTION
		"ruckusGGSNGTPCNumActPdp"
	::= { ruckusGGSNGTPCEntry 2 }

ruckusGGSNGTPCSuccPdpCrt OBJECT-TYPE
	SYNTAX Counter64
	MAX-ACCESS read-only
	STATUS current
	DESCRIPTION
		"ruckusGGSNGTPCSuccPdpCrt"
	::= { ruckusGGSNGTPCEntry 3 }

ruckusGGSNGTPCFailPdpCrt OBJECT-TYPE
	SYNTAX Counter64
	MAX-ACCESS read-only
	STATUS current
	DESCRIPTION
		"ruckusGGSNGTPCFailPdpCrt"
	::= { ruckusGGSNGTPCEntry 4 }

ruckusGGSNGTPCSuccPdpUpdRcvd OBJECT-TYPE
	SYNTAX Counter64
	MAX-ACCESS read-only
	STATUS current
	DESCRIPTION
		"ruckusGGSNGTPCSuccPdpUpdRcvd"
	::= { ruckusGGSNGTPCEntry 5 }

ruckusGGSNGTPCFailPdpUpdRcvd OBJECT-TYPE
	SYNTAX Counter64
	MAX-ACCESS read-only
	STATUS current
	DESCRIPTION
		"ruckusGGSNGTPCFailPdpUpdRcvd"
	::= { ruckusGGSNGTPCEntry 6 }

ruckusGGSNGTPCSuccPdpUpdInitRM OBJECT-TYPE
	SYNTAX Counter64
	MAX-ACCESS read-only
	STATUS current
	DESCRIPTION
		"ruckusGGSNGTPCSuccPdpUpdInitRM"
	::= { ruckusGGSNGTPCEntry 7 }

ruckusGGSNGTPCFailPdpUpdInitRM OBJECT-TYPE
	SYNTAX Counter64
	MAX-ACCESS read-only
	STATUS current
	DESCRIPTION
		"ruckusGGSNGTPCFailPdpUpdInitRM"
	::= { ruckusGGSNGTPCEntry 8 }

ruckusGGSNGTPCSuccPdpUpdInitAAA OBJECT-TYPE
	SYNTAX Counter64
	MAX-ACCESS read-only
	STATUS current
	DESCRIPTION
		"ruckusGGSNGTPCSuccPdpUpdInitAAA"
	::= { ruckusGGSNGTPCEntry 9 }

ruckusGGSNGTPCFailPdpUpdInitAAA OBJECT-TYPE
	SYNTAX Counter64
	MAX-ACCESS read-only
	STATUS current
	DESCRIPTION
		"ruckusGGSNGTPCFailPdpUpdInitAAA"
	::= { ruckusGGSNGTPCEntry 10 }

ruckusGGSNGTPCSuccPdpUpdInitHLR OBJECT-TYPE
	SYNTAX Counter64
	MAX-ACCESS read-only
	STATUS current
	DESCRIPTION
		"ruckusGGSNGTPCSuccPdpUpdInitHLR"
	::= { ruckusGGSNGTPCEntry 11 }

ruckusGGSNGTPCFailPdpUpdInitHLR OBJECT-TYPE
	SYNTAX Counter64
	MAX-ACCESS read-only
	STATUS current
	DESCRIPTION
		"ruckusGGSNGTPCFailPdpUpdInitHLR"
	::= { ruckusGGSNGTPCEntry 12 }

ruckusGGSNGTPCSuccDelPdpRcvd OBJECT-TYPE
	SYNTAX Counter64
	MAX-ACCESS read-only
	STATUS current
	DESCRIPTION
		"ruckusGGSNGTPCSuccDelPdpRcvd"
	::= { ruckusGGSNGTPCEntry 13 }

ruckusGGSNGTPCFailDelPdpRcvd OBJECT-TYPE
	SYNTAX Counter64
	MAX-ACCESS read-only
	STATUS current
	DESCRIPTION
		"ruckusGGSNGTPCFailDelPdpRcvd"
	::= { ruckusGGSNGTPCEntry 14 }

ruckusGGSNGTPCSuccDelPdpInitErr OBJECT-TYPE
	SYNTAX Counter64
	MAX-ACCESS read-only
	STATUS current
	DESCRIPTION
		"ruckusGGSNGTPCSuccDelPdpInitErr"
	::= { ruckusGGSNGTPCEntry 15 }

ruckusGGSNGTPCFailDelPdpInitErr OBJECT-TYPE
	SYNTAX Counter64
	MAX-ACCESS read-only
	STATUS current
	DESCRIPTION
		"ruckusGGSNGTPCFailDelPdpInitErr"
	::= { ruckusGGSNGTPCEntry 16 }

ruckusGGSNGTPCSuccDelPdpInitDM OBJECT-TYPE
	SYNTAX Counter64
	MAX-ACCESS read-only
	STATUS current
	DESCRIPTION
		"ruckusGGSNGTPCSuccDelPdpInitDM"
	::= { ruckusGGSNGTPCEntry 17 }

ruckusGGSNGTPCFailDelPdpInitDM OBJECT-TYPE
	SYNTAX Counter64
	MAX-ACCESS read-only
	STATUS current
	DESCRIPTION
		"ruckusGGSNGTPCFailDelPdpInitDM"
	::= { ruckusGGSNGTPCEntry 18 }

ruckusGGSNGTPCSuccDelPdpInitHLR OBJECT-TYPE
	SYNTAX Counter64
	MAX-ACCESS read-only
	STATUS current
	DESCRIPTION
		"ruckusGGSNGTPCSuccDelPdpInitHLR"
	::= { ruckusGGSNGTPCEntry 19 }

ruckusGGSNGTPCFailDelPdpInitHLR OBJECT-TYPE
	SYNTAX Counter64
	MAX-ACCESS read-only
	STATUS current
	DESCRIPTION
		"ruckusGGSNGTPCFailDelPdpInitHLR"
	::= { ruckusGGSNGTPCEntry 20 }

ruckusGGSNGTPCSuccDelPdpInitSCG OBJECT-TYPE
	SYNTAX Counter64
	MAX-ACCESS read-only
	STATUS current
	DESCRIPTION
		"ruckusGGSNGTPCSuccDelPdpInitSCG"
	::= { ruckusGGSNGTPCEntry 21 }

ruckusGGSNGTPCFailDelPdpInitSCG OBJECT-TYPE
	SYNTAX Counter64
	MAX-ACCESS read-only
	STATUS current
	DESCRIPTION
		"ruckusGGSNGTPCFailDelPdpInitSCG"
	::= { ruckusGGSNGTPCEntry 22 }

ruckusGGSNGTPCSuccDelPdpInitAP OBJECT-TYPE
	SYNTAX Counter64
	MAX-ACCESS read-only
	STATUS current
	DESCRIPTION
		"ruckusGGSNGTPCSuccDelPdpInitAP"
	::= { ruckusGGSNGTPCEntry 23 }

ruckusGGSNGTPCFailDelPdpInitAP OBJECT-TYPE
	SYNTAX Counter64
	MAX-ACCESS read-only
	STATUS current
	DESCRIPTION
		"ruckusGGSNGTPCFailDelPdpInitAP"
	::= { ruckusGGSNGTPCEntry 24 }

ruckusGGSNGTPCSuccDelPdpInitD OBJECT-TYPE
	SYNTAX Counter64
	MAX-ACCESS read-only
	STATUS current
	DESCRIPTION
		"ruckusGGSNGTPCSuccDelPdpInitD"
	::= { ruckusGGSNGTPCEntry 25 }

ruckusGGSNGTPCFailDelPdpInitD OBJECT-TYPE
	SYNTAX Counter64
	MAX-ACCESS read-only
	STATUS current
	DESCRIPTION
		"ruckusGGSNGTPCFailDelPdpInitD"
	::= { ruckusGGSNGTPCEntry 26 }

ruckusGGSNGTPCSuccDelPdpInitClnt OBJECT-TYPE
	SYNTAX Counter64
	MAX-ACCESS read-only
	STATUS current
	DESCRIPTION
		"ruckusGGSNGTPCSuccDelPdpInitClnt"
	::= { ruckusGGSNGTPCEntry 27 }

ruckusGGSNGTPCFailDelPdpInitClnt OBJECT-TYPE
	SYNTAX Counter64
	MAX-ACCESS read-only
	STATUS current
	DESCRIPTION
		"ruckusGGSNGTPCFailDelPdpInitClnt"
	::= { ruckusGGSNGTPCEntry 28 }

ruckusGGSNGTPCIndex OBJECT-TYPE
	SYNTAX Integer32
	MAX-ACCESS read-only
	STATUS current
	DESCRIPTION
		"ruckusGGSNGTPCIndex"
	::= { ruckusGGSNGTPCEntry 99 }


ruckusHLRInfo OBJECT IDENTIFIER    ::= { ruckusTTGObjects 7 }
ruckusHLRTable OBJECT-TYPE
	SYNTAX  SEQUENCE OF RuckusHLREntry
	MAX-ACCESS not-accessible
	STATUS current
	DESCRIPTION
		"ruckusHLRTable"
	::= { ruckusHLRInfo 1 }

ruckusHLREntry OBJECT-TYPE
	SYNTAX RuckusHLREntry
	MAX-ACCESS not-accessible
	STATUS current
	DESCRIPTION
		"ruckusHLREntry"
	INDEX {
		ruckusHLRIndex }
	::= { ruckusHLRTable 1 }

RuckusHLREntry ::= SEQUENCE {
	 ruckusHLRHlrSrvcName	DisplayString,
	 ruckusHLRNumSucAuthInfoReqSim	Counter64,
	 ruckusHLRNumAuthInfoRqErrHlrSim	Counter64,
	 ruckusHLRNumAuthInfoRqTmotSim	Counter64,
	 ruckusHLRNumSucAuthInfoReqAka	Counter64,
	 ruckusHLRNumAuthInfoRqErrHlrAka	Counter64,
	 ruckusHLRNumAuthInfoRqTmotAka	Counter64,
	 ruckusHLRNumUpdGprsSuccSim	Counter64,
	 ruckusHLRNumUpdGprsFailErrSim	Counter64,
	 ruckusHLRNumUpdGprsFailTmoSim	Counter64,
	 ruckusHLRNumUpdGprsSuccAka	Counter64,
	 ruckusHLRNumUpdGprsFailErrAka	Counter64,
	 ruckusHLRNumUpdGprsFailTmoAka	Counter64,
	 ruckusHLRNumRstDtaSuccSim	Counter64,
	 ruckusHLRNumRstDtaFailErrHlrSim	Counter64,
	 ruckusHLRNumRstDtaFailTmoSim	Counter64,
	 ruckusHLRNumRstDtaSuccAka	Counter64,
	 ruckusHLRNumRstDtaFailErrHlrAka	Counter64,
	 ruckusHLRNumRstDtaFailTmoAka	Counter64,
	 ruckusHLRNumInsrtDtaSuccSim	Counter64,
	 ruckusHLRNumInsrtDtaFailSim	Counter64,
	 ruckusHLRNumInsrtDtaSuccAka	Counter64,
	 ruckusHLRNumInsrtDtaFailAka	Counter64,
	 ruckusHLRNumSaInsrtDtaSucc	Counter64,
	 ruckusHLRNumSaInsrtDtaFailUnkS	Counter64,
	 ruckusHLRNumSaInsrtDtaFailErr	Counter64,
	 ruckusHLRNumCfgAssoc	Counter64,
	 ruckusHLRNumActAssoc	Counter64,
	 ruckusHLRNumRtgFail	Counter64,
	 ruckusHLRIndex	Integer32
}

ruckusHLRHlrSrvcName OBJECT-TYPE
	SYNTAX DisplayString
	MAX-ACCESS read-only
	STATUS current
	DESCRIPTION
		"ruckusHLRHlrSrvcName"
	::= { ruckusHLREntry 1 }

ruckusHLRNumSucAuthInfoReqSim OBJECT-TYPE
	SYNTAX Counter64
	MAX-ACCESS read-only
	STATUS current
	DESCRIPTION
		"ruckusHLRNumSucAuthInfoReqSim"
	::= { ruckusHLREntry 2 }

ruckusHLRNumAuthInfoRqErrHlrSim OBJECT-TYPE
	SYNTAX Counter64
	MAX-ACCESS read-only
	STATUS current
	DESCRIPTION
		"ruckusHLRNumAuthInfoRqErrHlrSim"
	::= { ruckusHLREntry 3 }

ruckusHLRNumAuthInfoRqTmotSim OBJECT-TYPE
	SYNTAX Counter64
	MAX-ACCESS read-only
	STATUS current
	DESCRIPTION
		"ruckusHLRNumAuthInfoRqTmotSim"
	::= { ruckusHLREntry 4 }

ruckusHLRNumSucAuthInfoReqAka OBJECT-TYPE
	SYNTAX Counter64
	MAX-ACCESS read-only
	STATUS current
	DESCRIPTION
		"ruckusHLRNumSucAuthInfoReqAka"
	::= { ruckusHLREntry 5 }

ruckusHLRNumAuthInfoRqErrHlrAka OBJECT-TYPE
	SYNTAX Counter64
	MAX-ACCESS read-only
	STATUS current
	DESCRIPTION
		"ruckusHLRNumAuthInfoRqErrHlrAka"
	::= { ruckusHLREntry 6 }

ruckusHLRNumAuthInfoRqTmotAka OBJECT-TYPE
	SYNTAX Counter64
	MAX-ACCESS read-only
	STATUS current
	DESCRIPTION
		"ruckusHLRNumAuthInfoRqTmotAka"
	::= { ruckusHLREntry 7 }

ruckusHLRNumUpdGprsSuccSim OBJECT-TYPE
	SYNTAX Counter64
	MAX-ACCESS read-only
	STATUS current
	DESCRIPTION
		"ruckusHLRNumUpdGprsSuccSim"
	::= { ruckusHLREntry 8 }

ruckusHLRNumUpdGprsFailErrSim OBJECT-TYPE
	SYNTAX Counter64
	MAX-ACCESS read-only
	STATUS current
	DESCRIPTION
		"ruckusHLRNumUpdGprsFailErrSim"
	::= { ruckusHLREntry 9 }

ruckusHLRNumUpdGprsFailTmoSim OBJECT-TYPE
	SYNTAX Counter64
	MAX-ACCESS read-only
	STATUS current
	DESCRIPTION
		"ruckusHLRNumUpdGprsFailTmoSim"
	::= { ruckusHLREntry 10 }

ruckusHLRNumUpdGprsSuccAka OBJECT-TYPE
	SYNTAX Counter64
	MAX-ACCESS read-only
	STATUS current
	DESCRIPTION
		"ruckusHLRNumUpdGprsSuccAka"
	::= { ruckusHLREntry 11 }

ruckusHLRNumUpdGprsFailErrAka OBJECT-TYPE
	SYNTAX Counter64
	MAX-ACCESS read-only
	STATUS current
	DESCRIPTION
		"ruckusHLRNumUpdGprsFailErrAka"
	::= { ruckusHLREntry 12 }

ruckusHLRNumUpdGprsFailTmoAka OBJECT-TYPE
	SYNTAX Counter64
	MAX-ACCESS read-only
	STATUS current
	DESCRIPTION
		"ruckusHLRNumUpdGprsFailTmoAka"
	::= { ruckusHLREntry 13 }

ruckusHLRNumRstDtaSuccSim OBJECT-TYPE
	SYNTAX Counter64
	MAX-ACCESS read-only
	STATUS current
	DESCRIPTION
		"ruckusHLRNumRstDtaSuccSim"
	::= { ruckusHLREntry 14 }

ruckusHLRNumRstDtaFailErrHlrSim OBJECT-TYPE
	SYNTAX Counter64
	MAX-ACCESS read-only
	STATUS current
	DESCRIPTION
		"ruckusHLRNumRstDtaFailErrHlrSim"
	::= { ruckusHLREntry 15 }

ruckusHLRNumRstDtaFailTmoSim OBJECT-TYPE
	SYNTAX Counter64
	MAX-ACCESS read-only
	STATUS current
	DESCRIPTION
		"ruckusHLRNumRstDtaFailTmoSim"
	::= { ruckusHLREntry 16 }

ruckusHLRNumRstDtaSuccAka OBJECT-TYPE
	SYNTAX Counter64
	MAX-ACCESS read-only
	STATUS current
	DESCRIPTION
		"ruckusHLRNumRstDtaSuccAka"
	::= { ruckusHLREntry 17 }

ruckusHLRNumRstDtaFailErrHlrAka OBJECT-TYPE
	SYNTAX Counter64
	MAX-ACCESS read-only
	STATUS current
	DESCRIPTION
		"ruckusHLRNumRstDtaFailErrHlrAka"
	::= { ruckusHLREntry 18 }

ruckusHLRNumRstDtaFailTmoAka OBJECT-TYPE
	SYNTAX Counter64
	MAX-ACCESS read-only
	STATUS current
	DESCRIPTION
		"ruckusHLRNumRstDtaFailTmoAka"
	::= { ruckusHLREntry 19 }

ruckusHLRNumInsrtDtaSuccSim OBJECT-TYPE
	SYNTAX Counter64
	MAX-ACCESS read-only
	STATUS current
	DESCRIPTION
		"ruckusHLRNumInsrtDtaSuccSim"
	::= { ruckusHLREntry 20 }

ruckusHLRNumInsrtDtaFailSim OBJECT-TYPE
	SYNTAX Counter64
	MAX-ACCESS read-only
	STATUS current
	DESCRIPTION
		"ruckusHLRNumInsrtDtaFailSim"
	::= { ruckusHLREntry 21 }

ruckusHLRNumInsrtDtaSuccAka OBJECT-TYPE
	SYNTAX Counter64
	MAX-ACCESS read-only
	STATUS current
	DESCRIPTION
		"ruckusHLRNumInsrtDtaSuccAka"
	::= { ruckusHLREntry 22 }

ruckusHLRNumInsrtDtaFailAka OBJECT-TYPE
	SYNTAX Counter64
	MAX-ACCESS read-only
	STATUS current
	DESCRIPTION
		"ruckusHLRNumInsrtDtaFailAka"
	::= { ruckusHLREntry 23 }

ruckusHLRNumSaInsrtDtaSucc OBJECT-TYPE
	SYNTAX Counter64
	MAX-ACCESS read-only
	STATUS current
	DESCRIPTION
		"ruckusHLRNumSaInsrtDtaSucc"
	::= { ruckusHLREntry 24 }

ruckusHLRNumSaInsrtDtaFailUnkS OBJECT-TYPE
	SYNTAX Counter64
	MAX-ACCESS read-only
	STATUS current
	DESCRIPTION
		"ruckusHLRNumSaInsrtDtaFailUnkS"
	::= { ruckusHLREntry 25 }

ruckusHLRNumSaInsrtDtaFailErr OBJECT-TYPE
	SYNTAX Counter64
	MAX-ACCESS read-only
	STATUS current
	DESCRIPTION
		"ruckusHLRNumSaInsrtDtaFailErr"
	::= { ruckusHLREntry 26 }

ruckusHLRNumCfgAssoc OBJECT-TYPE
	SYNTAX Counter64
	MAX-ACCESS read-only
	STATUS current
	DESCRIPTION
		"ruckusHLRNumCfgAssoc"
	::= { ruckusHLREntry 27 }

ruckusHLRNumActAssoc OBJECT-TYPE
	SYNTAX Counter64
	MAX-ACCESS read-only
	STATUS current
	DESCRIPTION
		"ruckusHLRNumActAssoc"
	::= { ruckusHLREntry 28 }

ruckusHLRNumRtgFail OBJECT-TYPE
	SYNTAX Counter64
	MAX-ACCESS read-only
	STATUS current
	DESCRIPTION
		"ruckusHLRNumRtgFail"
	::= { ruckusHLREntry 29 }

ruckusHLRIndex OBJECT-TYPE
	SYNTAX Integer32
	MAX-ACCESS read-only
	STATUS current
	DESCRIPTION
		"ruckusHLRIndex"
	::= { ruckusHLREntry 99 }
END
