-- %DNP% $Id: RBN-IETF-IP-CAP.my,v 1.1.2.5.382.5 2011/06/15 18:19:45 danielhe Exp $
-- %DNP% $Source: /cvsroot/pkt/sw/se/xc/bsd/config/snmp/mibs/RBN-IETF-IP-CAP.my,v $
-- *****************************************************************
-- RBN-IETF-IP-CAP.my:	IETF IP-MIB Agent Capabilities
--
-- Copyright (c) 1998, 2002, 2010-2011 Ericsson AB.
-- All rights reserved.
-- 
-- *****************************************************************

RBN-IETF-IP-CAP DEFINITIONS ::= BEGIN

IMPORTS
        MODULE-IDENTITY
                FROM SNMPv2-SMI
        AGENT-CAPABILITIES
                FROM SNMPv2-CONF
        RowStatus
                FROM SNMPv2-TC
        rbnCapabilities
                FROM RBN-SMI;

rbnIetfIpCap MODULE-IDENTITY
    LAST-UPDATED    "201106150000Z" -- Jun 15, 2011
    ORGANIZATION    "Ericsson AB"
    CONTACT-INFO
                "       Ericsson, Inc.

                 Postal: 100 Headquarters Dr
                         San Jose, CA  95134
                         USA

                 Phone: +1 408 750 5000
                 Fax: +1 408 750 5599"

    DESCRIPTION
        "The Agent Capabilities of IETF IP-MIB (RFC 4293).

        If this MIB implementation is platform-dependent,
        the PRODUCT-RELEASE clause contains Ericsson SEOS version and
        at least one of the following Ericsson product families:
            [SE]  SmartEdge Multi-service Edge Router (MSER) family
            [SM]  SM family of Metro Ethernet Service Transport platforms
            [SSR] Smart Service Router (SSR) family"

        REVISION        "201106150000Z" -- Jun 15, 2011
        DESCRIPTION
            "Update DESCRIPTION clause of MODULE-IDENTITY
            and PRODUCT-RELEASE clause of AGENT-CAPABILITIES."
    REVISION        "201003220000Z" -- March 22, 2010
    DESCRIPTION
        "Update ORGANIZATION/CONTACT-INFO. 
         Add rbnIetfTcpCap3 per RFC 4293 implementation"

    REVISION        "200109050000Z" -- September 5, 2001
    DESCRIPTION
        "Added rbnIetfIpCap2 for SmartEdge 2.1.3; 
         updated CONTACT-INFO."

    REVISION        "9803242300Z" -- March 24, 1998
    DESCRIPTION
        "Initial version"
    ::= { rbnCapabilities 3 }

rbnIetfIpCap1 AGENT-CAPABILITIES
	PRODUCT-RELEASE	"AOS 1.0.X.X"
	STATUS		current
	DESCRIPTION	"IP-MIB capabilities"
	SUPPORTS	IP-MIB
	INCLUDES {
		ipGroup,
		icmpGroup
		}

	VARIATION	ipForwarding
	ACCESS		read-only
	DESCRIPTION
		"Write access is not allowed"

	VARIATION	ipDefaultTTL
	ACCESS		read-only
	DESCRIPTION
		"Write access is not allowed"

	VARIATION	ipNetToMediaIfIndex
	ACCESS		read-only
	DESCRIPTION
		"Row creation or modification is not allowed"

	VARIATION	ipNetToMediaPhysAddress
	ACCESS		read-only
	DESCRIPTION
		"Row creation or modification is not allowed"

	VARIATION	ipNetToMediaNetAddress
	ACCESS		read-only
	DESCRIPTION
		"Row creation or modification is not allowed"

	VARIATION	ipNetToMediaType
	ACCESS		read-only
	DESCRIPTION
		"Row creation, modification, or deletion is not allowed"

	::= { rbnIetfIpCap 1 }

rbnIetfIpCap2 AGENT-CAPABILITIES
        PRODUCT-RELEASE     "SEOS 2.1.X.X"
        STATUS              current
        DESCRIPTION         "IP-MIB capabilities"
        SUPPORTS            IP-MIB
        INCLUDES {
                ipGroup,
                icmpGroup
                }

        VARIATION           ipForwarding
        ACCESS              read-only
        DESCRIPTION
                "Write access is not allowed"

        VARIATION           ipDefaultTTL
        ACCESS              read-only
        DESCRIPTION
                "Write access is not allowed"

        VARIATION           ipNetToMediaIfIndex
        ACCESS              read-only
        DESCRIPTION
                "Row creation or modification is not allowed"

        VARIATION           ipNetToMediaPhysAddress
        ACCESS              read-only
        DESCRIPTION
                "Row creation or modification is not allowed"

        VARIATION           ipNetToMediaNetAddress
        ACCESS              read-only
        DESCRIPTION
                "Row creation or modification is not allowed"

        VARIATION           ipNetToMediaType
        ACCESS              read-only
        DESCRIPTION
                "Row creation, modification, or deletion is not allowed"

        ::= { rbnIetfIpCap 2 }
		
rbnIetfIpCap3 AGENT-CAPABILITIES
        PRODUCT-RELEASE     "SEOS 6.4.x [SE, SM]; SEOS 11.1.x [SSR]"
        STATUS              current
        DESCRIPTION         "IP-MIB capabilities"
        SUPPORTS            IP-MIB
        INCLUDES {
                ipGroup,
                icmpGroup,
                ipSystemStatsGroup,   
                ipSystemStatsHCOctetGroup,
                ipSystemStatsHCPacketGroup,
                ipAddressGroup,
                icmpStatsGroup 
                }

        VARIATION           ipForwarding
        ACCESS              read-only
        DESCRIPTION
                "Write access is not allowed"

        VARIATION           ipDefaultTTL
        ACCESS              read-only
        DESCRIPTION
                "Write access is not allowed"

        VARIATION           ipNetToMediaIfIndex
        ACCESS              read-only
        DESCRIPTION
                "Row creation or modification is not allowed"

        VARIATION           ipNetToMediaPhysAddress
        ACCESS              read-only
        DESCRIPTION
                "Row creation or modification is not allowed"

        VARIATION           ipNetToMediaNetAddress
        ACCESS              read-only
        DESCRIPTION
                "Row creation or modification is not allowed"

        VARIATION           ipNetToMediaType
        ACCESS              read-only
        DESCRIPTION
                "Row creation, modification, or deletion is not allowed"
                
        VARIATION           ipAddressSpinLock
        ACCESS              not-implemented
        DESCRIPTION
               "An agent is not required to provide write ACCESS to this
                VARIATION. "

        VARIATION           ipAddressIfIndex
        ACCESS              read-only
        DESCRIPTION
               "An agent is not required to provide write or create access
                to this VARIATION."

        VARIATION           ipAddressType
        ACCESS              read-only
        DESCRIPTION
               "An agent is not required to provide write or create access
                to this VARIATION."

        VARIATION           ipAddressStatus
        ACCESS              read-only
        DESCRIPTION
               "An agent is not required to provide write or create access
                to this VARIATION."

        VARIATION           ipAddressRowStatus
        SYNTAX              RowStatus { active(1) }
        ACCESS              read-only
        DESCRIPTION
               "An agent is not required to provide write or create access
                to this VARIATION."

        VARIATION           ipAddressStorageType
        ACCESS              read-only
        DESCRIPTION
               "An agent is not required to provide write or create access
                to this VARIATION."
                
        ::= { rbnIetfIpCap 3 }

END
