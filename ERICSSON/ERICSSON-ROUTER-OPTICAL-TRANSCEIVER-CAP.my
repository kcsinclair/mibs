-- *****************************************************************
-- ERICSSON-ROUTER-OPTICAL-TRANSCEIVER-CAP
--
-- %DNP% Copyright (c) 2015 Ericsson AB.
-- %DNP% All rights reserved.
--
-- *****************************************************************

ERICSSON-ROUTER-OPTICAL-TRANSCEIVER-CAP DEFINITIONS ::= BEGIN

IMPORTS
    MODULE-IDENTITY
          FROM SNMPv2-SMI
    AGENT-CAPABILITIES
          FROM SNMPv2-CONF
    eriRouterCapabilities
          FROM RBN-SMI;


eriRouterOpticalTransceiverCap MODULE-IDENTITY
        LAST-UPDATED    "201506250000Z" -- June 25, 2015
        ORGANIZATION    "Ericsson AB"
        CONTACT-INFO
                "       Ericsson AB.

                Postal: 200 Headquarters Dr
                        San Jose, CA  95134
                        USA

                 Phone: +1 408 750 5000
                   Fax: +1 408 750 5599

                "

        DESCRIPTION
                "The Agent Capabilities of the MIB used to manage the SFP (Small Form Factor Pluggable)
                 /SFP+/XFP/CFP devices."
        REVISION        "201506250000Z" -- June 25, 2015
        DESCRIPTION
                "Initial version."
        ::= { eriRouterCapabilities 108 }

eriRouterOpticalTransceiverCap1 AGENT-CAPABILITIES
        PRODUCT-RELEASE "IPOS 16.1"
        STATUS          current
        DESCRIPTION     "ERICSSON-ROUTER-OPTICAL-TRANSCEIVER-MIB capabilities"
        SUPPORTS        ERICSSON-ROUTER-OPTICAL-TRANSCEIVER-MIB
        INCLUDES {
           eriRouterOpticalTransceiverMonMIBNotificationGroup
        }

        ::= { eriRouterOpticalTransceiverCap 1 }

END
