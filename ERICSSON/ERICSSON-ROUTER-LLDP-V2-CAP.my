-- *****************************************************************
-- ERICSSON-ROUTER-LAG-MIB
--
-- Copyright (c) 2018 Ericsson AB.
-- All rights reserved.
--
-- *****************************************************************



ERICSSON-ROUTER-LLDP-V2-MIB DEFINITIONS ::= BEGIN

IMPORTS
	MODULE-IDENTITY
		FROM SNMPv2-SMI
	AGENT-CAPABILITIES
		FROM SNMPv2-CONF
	SnmpAdminString
		FROM SNMP-FRAMEWORK-MIB
	eriRouterCapabilities
		FROM ERICSSON-ROUTER-SMI;

eriRouterLLDPV2MibCap MODULE-IDENTITY
     LAST-UPDATED    "201801151800Z" -- Jan 15, 2018
     ORGANIZATION    "Ericsson AB."
     CONTACT-INFO
             "       Ericsson AB.

                     100 Headquarters Dr
                     San Jose, CA  95134
                     USA

             Phone:  +1 408 750-5000
             Fax:    +1 408 750-5599

             "
     DESCRIPTION
             " LLDPV2 MIB"

-- Revision history
     REVISION        "201801151800Z" -- Jan 15, 2018
     DESCRIPTION
             "Initial version of Linkgroup MIB defenition."

        ::= { eriRouterCapabilities 124 }

 eriRouterLLDPV2MibCap1  AGENT-CAPABILITIES
    PRODUCT-RELEASE "SEOS 14.1.x [SSR]"
    STATUS          current
    DESCRIPTION     "LLDP-V2-MIB capabilities"
    SUPPORTS        LLDP-V2-MIB
    INCLUDES {
            lldpV2ConfigGroup,
            lldpV2ConfigTxGroup,
            lldpV2StatsTxGroup,
            lldpV2LocSysGroup,
            lldpV2ConfigRxGroup,
            lldpV2StatsRxGroup,
            lldpV2RemSysGroup,
            lldpV2NotificationsGroup
            }
    VARIATION lldpV2PortConfigAdminStatusV2
    ACCESS       read-only
    DESCRIPTION
        "Write access is not supported."

    VARIATION lldpV2NotificationInterval
    ACCESS       read-only
    DESCRIPTION
        "Write access is not supported."

    VARIATION lldpV2PortConfigNotificationEnableV2
    ACCESS       read-only
    DESCRIPTION
        "Write access is not supported."

    VARIATION lldpV2MessageTxInterval
    ACCESS       read-only
    DESCRIPTION
        "Write access is not supported."

     VARIATION lldpV2MessageTxHoldMultiplier
    ACCESS       read-only
    DESCRIPTION
        "Write access is not supported."

    VARIATION lldpV2ReinitDelay
    ACCESS       read-only
    DESCRIPTION
        "Write access is not supported."

    VARIATION lldpV2PortConfigTLVsTxEnableV2
    ACCESS       read-only
    DESCRIPTION
        "Write access is not supported."

    VARIATION lldpV2ManAddrConfigTxEnable
    ACCESS    not-implemented
    DESCRIPTION
        "Object not supported."

    VARIATION lldpV2ManAddrConfigRowStatus
    ACCESS    not-implemented
    DESCRIPTION
        "Object not supported."

    VARIATION lldpV2TxCreditMax
    ACCESS    not-implemented
    DESCRIPTION
        "Object not supported."

    VARIATION lldpV2MessageFastTx
    ACCESS    not-implemented
    DESCRIPTION
        "Object not supported."

    VARIATION lldpV2TxFastInit
    ACCESS    not-implemented
    DESCRIPTION
        "Object not supported."

    VARIATION lldpV2PortMessageTxInterval
    ACCESS    not-implemented
    DESCRIPTION
        "Object not supported."

    VARIATION lldpV2PortMessageTxHoldMultiplier
    ACCESS    not-implemented
    DESCRIPTION
        "Object not supported."

    VARIATION lldpV2PortReinitDelay
    ACCESS    not-implemented
    DESCRIPTION
        "Object not supported."

    VARIATION lldpV2PortNotificationInterval
    ACCESS       read-only
    DESCRIPTION
        "Write access is not supported."

    VARIATION lldpV2PortTxCreditMax
    ACCESS    not-implemented
    DESCRIPTION
        "Object not supported."

    VARIATION lldpV2PortMessageFastTx
    ACCESS    not-implemented
    DESCRIPTION
        "Object not supported."

    VARIATION lldpV2PortTxFastInit
    ACCESS    not-implemented
    DESCRIPTION
        "Object not supported."

    VARIATION lldpV2LocManAddrIfSubtype
    ACCESS    not-implemented
    DESCRIPTION
        "Object not supported."

    VARIATION lldpV2LocManAddrIfId
    ACCESS    not-implemented
    DESCRIPTION
        "Object not supported."

    VARIATION lldpV2LocManAddrOID
    ACCESS    not-implemented
    DESCRIPTION
        "Object not supported."

    VARIATION lldpV2RemRemoteChanges
    ACCESS    not-implemented
    DESCRIPTION
        "Object not supported."

    VARIATION lldpV2RemTooManyNeighbors
    ACCESS    not-implemented
    DESCRIPTION
        "Object not supported."

    VARIATION lldpV2RemUnknownTLVInfo
    ACCESS    not-implemented
    DESCRIPTION
        "Object not supported."
   
    VARIATION lldpV2RemOrgDefInfo
    ACCESS    not-implemented
    DESCRIPTION
        "Object not supported."

    ::= { eriRouterLLDPV2MibCap  1 }
END
