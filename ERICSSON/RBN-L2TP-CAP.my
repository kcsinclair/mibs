-- %DNP% $Id: RBN-L2TP-CAP.my,v 1.1.2.5.322.3 2011/06/15 18:19:46 danielhe Exp $
-- %DNP% $Source: /cvsroot/pkt/sw/se/xc/bsd/config/snmp/mibs/Attic/RBN-L2TP-CAP.my,v $
-- *****************************************************************
-- RBN-L2TP-CAP.my   L2TP MIB agent capabilities
--
-- Copyright (c) 2000-2005, 2010-2011 Ericsson AB
-- All rights reserved.
-- 
-- *****************************************************************

RBN-L2TP-CAP DEFINITIONS ::= BEGIN

IMPORTS
	MODULE-IDENTITY
		FROM SNMPv2-SMI
	AGENT-CAPABILITIES
		FROM SNMPv2-CONF
	SnmpAdminString
		FROM SNMP-FRAMEWORK-MIB
	rbnCapabilities
		FROM RBN-SMI;

rbnL2tpCap MODULE-IDENTITY
        LAST-UPDATED    "201106150000Z" -- Jun 15, 2011
        ORGANIZATION    "Ericsson Inc."
        CONTACT-INFO
                "       Ericsson, Inc.

                Postal: 100 Headquarters Dr.
                        San Jose, CA  95134
                        USA

                 Phone: +1 408 750 5000
                   Fax: +1 408 750 5599
                "
	DESCRIPTION
		"The Agent Capabilities of the RBN-L2TP-MIB.

                If this MIB implementation is platform-dependent,
                the PRODUCT-RELEASE clause contains Ericsson SEOS version and
                at least one of the following Ericsson product families:
                    [SE]  SmartEdge Multi-service Edge Router (MSER) family
                    [SM]  SM family of Metro Ethernet Service Transport platforms
                    [SSR] Smart Service Router (SSR) family"

        REVISION        "201106150000Z" -- Jun 15, 2011
        DESCRIPTION
            "Update DESCRIPTION clause of MODULE-IDENTITY
            and PRODUCT-RELEASE clause of AGENT-CAPABILITIES."
        REVISION    "201011010000Z" -- Nov 1, 2010
        DESCRIPTION
            "Modified PRODUCT-RELEASE clause for consistent naming.
             Updated CONTACT-INFO."

	REVISION	"200505020000Z" -- May 2, 2005
	DESCRIPTION
		"Added new AGENT-CAPABILITIES for the SE 4.0.5 release
		and updated the contact info."

	REVISION	"200410180000Z" -- Oct 18, 2004
	DESCRIPTION
		"Added new AGENT-CAPABILITIES for the SE 4.0.3 release
		and updated the contact info."

	REVISION	"200402110000Z" -- Feb 11, 2004
	DESCRIPTION
		"Added new AGENT-CAPABILITIES for the SE 2.6.3 release
		and updated the contact info."

	REVISION	"200210150000Z" -- Oct 15, 2002
	DESCRIPTION
		"Added AGENT-CAPABILITIES for providing peer name
		support and changed the contact info."

	REVISION        "200206100000Z" -- Jun 10, 2002
	DESCRIPTION
		"Initial version."

	::= { rbnCapabilities 56 }


rbnL2tpInfoCap1 AGENT-CAPABILITIES
	PRODUCT-RELEASE	"AOS 6.X.X.X"
	STATUS		current
	DESCRIPTION	"RBN-L2TP-MIB capabilities"
	SUPPORTS	RBN-L2TP-MIB
	INCLUDES {
                   rbnL2tpMibPeerCfgGroup,
                   rbnL2tpMibTunnelCfgGroup,
                   rbnL2tpMibPeerCntGroup,
                   rbnL2tpMibTunnelCntGroup,
                   rbnL2tpMibSessionCntGroup,
		   rbnL2tpMibNotificationGroup
		 }

        VARIATION rbnL2tpPCfgMedia
            ACCESS    read-only
            DESCRIPTION
                "Write access is not allowed."

        VARIATION rbnL2tpPCfgRadius
            ACCESS    read-only
            DESCRIPTION
                "Write access is not allowed."

        VARIATION rbnL2tpPCfgRemIPAdd
            ACCESS    read-only
            DESCRIPTION
                "Write access is not allowed."

        VARIATION rbnL2tpPCfgStatic
            ACCESS    read-only
            DESCRIPTION
                "Write access is not allowed."

        VARIATION rbnL2tpPCfgLocalIPAdd
            ACCESS    read-only
            DESCRIPTION
                "Write access is not allowed."

        VARIATION rbnL2tpPCfgMode
            ACCESS    read-only
            DESCRIPTION
                "Write access is not allowed."

        VARIATION rbnL2tpPCfgMaxTunnels
            ACCESS    read-only
            DESCRIPTION
                "Write access is not allowed."

        VARIATION rbnL2tpPCfgMaxSesPerTun
            ACCESS    read-only
            DESCRIPTION
                "Write access is not allowed."

        VARIATION rbnL2tpPCfgCtlRetranTO
            ACCESS    read-only
            DESCRIPTION
                "Write access is not allowed."

        VARIATION rbnL2tpPCfgSessAuth
            ACCESS    read-only
            DESCRIPTION
                "Write access is not allowed."

        VARIATION rbnL2tpPCfgCtlWin
            ACCESS    read-only
            DESCRIPTION
                "Write access is not allowed."

        VARIATION rbnL2tpPCfgDNIS
            ACCESS    read-only
            DESCRIPTION
                "Write access is not allowed."

        VARIATION rbnL2tpPCfgPoliceRate
            ACCESS    read-only
            DESCRIPTION
                "Write access is not allowed."

        VARIATION rbnL2tpPCfgLimitRate
            ACCESS    read-only
            DESCRIPTION
                "Write access is not allowed."

        VARIATION rbnL2tpPCfgLimitBurst
            ACCESS    read-only
            DESCRIPTION
                "Write access is not allowed."

        VARIATION rbnL2tpPCfgGroup
            ACCESS    read-only
            DESCRIPTION
                "Write access is not allowed."

        VARIATION rbnL2tpPCfgPref
            ACCESS    read-only
            DESCRIPTION
                "Write access is not allowed."

        VARIATION rbnL2tpPCfgPasswd
            ACCESS    read-only
            DESCRIPTION
                "Write access is not allowed."

        VARIATION rbnL2tpPCfgHelloTimer
            ACCESS    read-only
            DESCRIPTION
                "Write access is not allowed."

        VARIATION rbnL2tpPCfgSessContext
            ACCESS    read-only
            DESCRIPTION
                "Write access is not allowed."

        VARIATION rbnL2tpPCfgSessService
            ACCESS    read-only
            DESCRIPTION
                "Write access is not allowed."

        VARIATION rbnL2tpPCfgEthEncap
            ACCESS    read-only
            DESCRIPTION
                "Write access is not allowed."

        VARIATION rbnL2tpPCfgEthSession
            ACCESS    read-only
            DESCRIPTION
                "Write access is not allowed."

        ::= { rbnL2tpCap 1  }	

rbnL2tpInfoCap2 AGENT-CAPABILITIES
	PRODUCT-RELEASE	"SEOS 2.6.3"
	STATUS		current
	DESCRIPTION	"RBN-L2TP-MIB capabilities"
	SUPPORTS	RBN-L2TP-MIB
	INCLUDES {
		   rbnL2tpMibNotificationGroup2
		 }

	::= { rbnL2tpCap 2  }	

rbnL2tpInfoCap3 AGENT-CAPABILITIES
	PRODUCT-RELEASE	"SEOS 4.0.3"
	STATUS		current
	DESCRIPTION	"RBN-L2TP-MIB capabilities"
	SUPPORTS	RBN-L2TP-MIB
	INCLUDES {
		   rbnL2tpMibPeerTunCfgGroup,
		   rbnL2tpMibNotificationGroup2
		 }

	VARIATION rbnL2tpMibPeerName
	    SYNTAX          SnmpAdminString (SIZE (1..64))
	    DESCRIPTION
		"Each character must be printable (the posix funtion isprint()
		returns true for each character) and the string may not contain
		any of the characters double quote, single quote ('), bar (|),
		or exclamation point (!).

		Limit this peer name string to a maximum of 64 octets in
		length which is the same as the implementation in CLI."

	VARIATION rbnL2tpPTCfgTunnelLocalNm
	    SYNTAX          SnmpAdminString (SIZE (0..64))
	    DESCRIPTION
		"Limit this tunnel name string to a maximum of 64 octets in
		length which is the same as the implementation in CLI."

	VARIATION rbnL2tpPTCfgTunnelRemoteNm
	    SYNTAX          SnmpAdminString (SIZE (0..64))
	    DESCRIPTION
		"Limit this tunnel name string to a maximum of 64 octets in
		length which is the same as the implementation in CLI."

	VARIATION rbnL2tpPTCfgPeerLocalNm
	    SYNTAX          SnmpAdminString (SIZE (0..64))
	    DESCRIPTION
		"Limit this peer name string to a maximum of 64 octets in
		length which is the same as the implementation in CLI."

	::= { rbnL2tpCap 3  }

rbnL2tpInfoCap4 AGENT-CAPABILITIES
	PRODUCT-RELEASE	"SEOS 4.0.5 [SE]; SEOS 6.3.X [SM]"
	STATUS		current
	DESCRIPTION	"RBN-L2TP-MIB capabilities"
	SUPPORTS	RBN-L2TP-MIB
	INCLUDES {
		   rbnL2tpMibTunnelCfgGroup,
		   rbnL2tpMibPeerTunCfgGroup,
		   rbnL2tpMibNotificationGroup2
		 }

	VARIATION rbnL2tpMibPeerName
	    SYNTAX          SnmpAdminString (SIZE (1..64))
	    DESCRIPTION
		"Each character must be printable (the posix funtion isprint()
		returns true for each character) and the string may not contain
		any of the characters double quote, single quote ('), bar (|),
		or exclamation point (!).

		Limit this peer name string to a maximum of 64 octets in
		length which is the same as the implementation in CLI."

	VARIATION       rbnL2tpTCfgTunCtlErrs
	    ACCESS          not-implemented
	    DESCRIPTION
		"Object not supported"

	VARIATION       rbnL2tpTCfgLastCtlErr
	    ACCESS          not-implemented
	    DESCRIPTION
		"Object not supported"

	VARIATION       rbnL2tpTCfgLastCErrTime
	    ACCESS          not-implemented
	    DESCRIPTION
		"Object not supported"
  
	VARIATION       rbnL2tpTCfgTunDataErrs
	    ACCESS          not-implemented
	    DESCRIPTION
		"Object not supported"

	VARIATION       rbnL2tpTCfgLastDataErr
	    ACCESS          not-implemented
	    DESCRIPTION
		"Object not supported"

	VARIATION       rbnL2tpTCfgLastDErrTime
	    ACCESS          not-implemented
	    DESCRIPTION
		"Object not supported"

	VARIATION rbnL2tpPTCfgTunnelLocalNm
	    SYNTAX          SnmpAdminString (SIZE (0..64))
	    DESCRIPTION
		"Limit this tunnel name string to a maximum of 64 octets in
		length which is the same as the implementation in CLI."

	VARIATION rbnL2tpPTCfgTunnelRemoteNm
	    SYNTAX          SnmpAdminString (SIZE (0..64))
	    DESCRIPTION
		"Limit this tunnel name string to a maximum of 64 octets in
		length which is the same as the implementation in CLI."

	VARIATION rbnL2tpPTCfgPeerLocalNm
	    SYNTAX          SnmpAdminString (SIZE (0..64))
	    DESCRIPTION
		"Limit this peer name string to a maximum of 64 octets in
		length which is the same as the implementation in CLI."

	::= { rbnL2tpCap 4  }
END
