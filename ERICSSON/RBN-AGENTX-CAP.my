-- *****************************************************************
-- AGENTX-MIB-CAP    Ericsson AGENTX Master Capabilities
--
-- Copyright (c) 2013 Ericsson AB.
-- All rights reserved.
--
-- *****************************************************************

RBN-AGENTX-CAP DEFINITIONS ::= BEGIN

IMPORTS
        MODULE-IDENTITY
                FROM SNMPv2-SMI
        AGENT-CAPABILITIES
                FROM SNMPv2-CONF
        rbnCapabilities
                FROM RBN-SMI;

rbnAgentXCap MODULE-IDENTITY
    LAST-UPDATED    "2013032800Z" -- March 28, 2013
    ORGANIZATION    "Ericsson AB."
    CONTACT-INFO    "postal:   Kovacs Zsolt
                            Budapest
                            1117 Irinyi ut
		  email:    kovacs.zsolt@ericssson.com
                 "
    DESCRIPTION
        "
	MIB module for the SNMP Agent Extensibility Protocol (AgentX).
	This MIB module will be implemented by the master agent.
	"
    REVISION    "2013032700Z" -- March 27, 2013
    DESCRIPTION
           "Initial version"
        ::= { rbnCapabilities 104 }

rbnAgentXCap1 AGENT-CAPABILITIES
    PRODUCT-RELEASE "IPOS 13.2.x [SSR]"
    STATUS          current
    DESCRIPTION     "AGENTX-MIB capabilities"
    SUPPORTS        AGENTX-MIB
    INCLUDES {
       agentxConnectionTable,
       agentxSessionTable,
       agentxRegistrationTable
    }

    ::= { rbnAgentXCap 1 }

END
