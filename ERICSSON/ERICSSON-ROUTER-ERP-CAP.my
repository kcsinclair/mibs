-- %DNP% $Id: $
-- %DNP% $Source: /cvsroot/pkt/sw/se/xc/bsd/config/snmp/mibs/Attic/ERICSSON-ROUTER-ERP-CAP.my,v $
-- *****************************************************************
-- ERICSSON-ROUTER-ERP-CAP        ERP Mib Capabilities
--
-- Copyright (c) 2017 Ericsson AB.
-- All rights reserved.
--
-- *****************************************************************

ERICSSON-ROUTER-ERP-CAP DEFINITIONS ::= BEGIN

IMPORTS

    MODULE-IDENTITY
            FROM SNMPv2-SMI
    AGENT-CAPABILITIES
            FROM SNMPv2-CONF
    eriRouterCapabilities
            FROM ERICSSON-ROUTER-SMI;

eriRouterERPMibCap MODULE-IDENTITY
    LAST-UPDATED    "201701161800Z" -- Jan 16, 2017
    ORGANIZATION    "Ericsson AB"
    CONTACT-INFO
        "    Ericsson, AB.

        Postal:    100 Headquarters Dr
            San Jose, CA  95134
            USA

         Phone:    +1 408 750 5000
           Fax: +1 408 750 5599"
    DESCRIPTION
        "The Agent Capabilities of the ERP MIB."

    ::= { eriRouterCapabilities 115 }

eriRouterERPMibCap1 AGENT-CAPABILITIES
    PRODUCT-RELEASE    "IPOS 16.5.x [SSR]"
    STATUS        current
    DESCRIPTION    "ERICSSON-ROUTER-ERP-MIB capabilities"
    SUPPORTS    ERICSSON-ROUTER-ERP-MIB
    INCLUDES {
        eriRouterERPObjectsGroup,
        eriRouterERPNotifyGroup
    }

    ::= { eriRouterERPMibCap 1 }

END
