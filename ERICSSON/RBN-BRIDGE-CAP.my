-- %DNP% $Id: RBN-BRIDGE-CAP.my,v 1.1.2.5.18.4 2011/06/15 18:19:45 danielhe Exp $
-- %DNP% $Source: /cvsroot/pkt/sw/se/xc/bsd/config/snmp/mibs/Attic/RBN-BRIDGE-CAP.my,v $
-- *****************************************************************
-- RBN-BRIDGE-CAP: RBN-BRIDGE-MIB Agent Capabilities
--
-- Copyright (c) 2007, 2008, 2010-2011 Ericsson AB
-- All rights reserved.
--
-- *****************************************************************

RBN-BRIDGE-CAP DEFINITIONS ::= BEGIN

IMPORTS
        MODULE-IDENTITY
                FROM SNMPv2-SMI
        AGENT-CAPABILITIES
                FROM SNMPv2-CONF
        rbnCapabilities
                FROM RBN-SMI;
 
rbnBridgeCap MODULE-IDENTITY
        LAST-UPDATED    "201106150000Z" -- Jun 15, 2011
        ORGANIZATION    "Ericsson Inc."
        CONTACT-INFO
                "       Ericsson, Inc.

                Postal: 100 Headquarters Dr.
                        San Jose, CA  95134
                        USA

                 Phone: +1 408 750 5000
                   Fax: +1 408 750 5599
                "
        DESCRIPTION
                "The Agent Capabilities of the BRIDGE MIB (RBN-BRIDGE-MIB).

                If this MIB implementation is platform-dependent,
                the PRODUCT-RELEASE clause contains Ericsson SEOS version and
                at least one of the following Ericsson product families:
                    [SE]  SmartEdge Multi-service Edge Router (MSER) family
                    [SM]  SM family of Metro Ethernet Service Transport platforms
                    [SSR] Smart Service Router (SSR) family"

        REVISION        "201106150000Z" -- Jun 15, 2011
        DESCRIPTION
            "Update DESCRIPTION clause of MODULE-IDENTITY
            and PRODUCT-RELEASE clause of AGENT-CAPABILITIES."
        
        REVISION    "201011010000Z" -- Nov 1, 2010
        DESCRIPTION
            "Modified PRODUCT-RELEASE clause for consistent naming.
             Updated CONTACT-INFO."

        REVISION        "200802250000Z" -- Feb 25, 2008
        DESCRIPTION
                "Added new OID rbnBridgeCap2. Added new groups
                  rbnBridgeStateNotifyObjectGroup,
                  rbnBridgeBaseObjectGroup, 
                
                 new notification group rbnBridgeStateNotifyGroup."

        REVISION        "200706260000Z" -- June 26, 2007
        DESCRIPTION
                "Initial version"
        ::= { rbnCapabilities 73 }

rbnBridgeCap1 AGENT-CAPABILITIES
        PRODUCT-RELEASE "SEOS 6.1"
        STATUS          obsolete
        DESCRIPTION     "RBN-BRIDGE-MIB capabilities"
        SUPPORTS        RBN-BRIDGE-MIB
        INCLUDES {
                    rbnBridgeNotifyObjectGroup,
                    rbnBridgeNotifyGroup
                 }
        ::= { rbnBridgeCap 1 }

rbnBridgeCap2 AGENT-CAPABILITIES
        PRODUCT-RELEASE "SEOS 6.1.4 [SE]; SEOS 6.3.X [SM]"
        STATUS          current
        DESCRIPTION     "RBN-BRIDGE-MIB capabilities"
        SUPPORTS        RBN-BRIDGE-MIB
        INCLUDES {
                    rbnBridgeNotifyObjectGroup,
                    rbnBridgeStateNotifyObjectGroup,
                    rbnBridgeNotifyGroup,
                    rbnBridgeStateNotifyGroup,
                    rbnBridgeBaseObjectGroup
                 }
        ::= { rbnBridgeCap 2 }

END
