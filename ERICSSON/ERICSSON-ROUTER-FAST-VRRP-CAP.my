-- %DNP% $Id: ERICSSON-ROUTER-FAST-VRRP-CAP.my,v 1.1.18.3 2011/06/15 18:19:45 danielhe Exp $
-- %DNP% $Source: /cvsroot/pkt/sw/se/xc/bsd/config/snmp/mibs/Attic/ERICSSON-ROUTER-FAST-VRRP-CAP.my,v $
-- *****************************************************************
-- ERICSSON-ROUTER-FAST-VRRP-CAP: ERICSSON-ROUTER-FAST-VRRP-MIB Agent Capabilities
--
-- Copyright (c) 2008, 2011, 2015 Ericsson AB.
-- All rights reserved.
--
-- *****************************************************************

ERICSSON-ROUTER-FAST-VRRP-CAP DEFINITIONS ::= BEGIN

IMPORTS
        MODULE-IDENTITY
                FROM SNMPv2-SMI
        AGENT-CAPABILITIES
                FROM SNMPv2-CONF
        eriRouterCapabilities
                FROM ERICSSON-ROUTER-SMI;

eriRouterFastVrrpCap MODULE-IDENTITY
        LAST-UPDATED    "201501141800Z" -- Jan 14, 2015
        ORGANIZATION    "Ericsson AB."
        CONTACT-INFO
                "       Ericsson AB.

                Postal: 100 Headquarters Dr
                        San Jose, CA  95134
                        USA

                 Phone: +1 408 750 5000
                   Fax: +1 408 750 5599
                "
        DESCRIPTION
                "The Agent Capabilities of the Fast VRRP MIB 
                 (ERICSSON-ROUTER-FAST-VRRP-MIB).

                If this MIB implementation is platform-dependent,
                the PRODUCT-RELEASE clause contains Ericsson SEOS version and
                at least one of the following Ericsson product families:
                    [SE]  SmartEdge Multi-service Edge Router (MSER) family
                    [SM]  SM family of Metro Ethernet Service Transport platforms
                    [SSR] Smart Service Router (SSR) family"

        REVISION        "201501141800Z" -- Jan 14, 2015
        DESCRIPTION
            "Updated RBN/rbn/Rbn as ERICSSON-ROUTER/eriRouter/EriRouter
             to migrate RBN MIB to ERICSSON MIB."

        REVISION        "201106150000Z" -- Jun 15, 2011
        DESCRIPTION
            "Update DESCRIPTION clause of MODULE-IDENTITY
            and PRODUCT-RELEASE clause of AGENT-CAPABILITIES."

        REVISION        "201101191800Z" -- Jan 19, 2011
        DESCRIPTION
                "Update CONTACT-INFO & ORGANIZATION. "

        REVISION        "200806240000Z" -- June 24, 2008
        DESCRIPTION
                "Initial version"
        ::= { eriRouterCapabilities 81 }

eriRouterFastVrrpCap1 AGENT-CAPABILITIES
        PRODUCT-RELEASE "SEOS 6.1.4.3"
        STATUS          current
        DESCRIPTION     "ERICSSON-ROUTER-FAST-VRRP-MIB capabilities"
        SUPPORTS        ERICSSON-ROUTER-FAST-VRRP-MIB
        INCLUDES {
                    eriRouterFastVrrpObjectGroup 
                 }

        ::= { eriRouterFastVrrpCap 1 }

END
