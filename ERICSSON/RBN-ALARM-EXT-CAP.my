-- %DNP% $Id: RBN-ALARM-EXT-CAP.my,v 1.1.6.3 2011/06/15 18:19:45 danielhe Exp $
-- %DNP% $Source: /cvsroot/pkt/sw/se/xc/bsd/config/snmp/mibs/Attic/RBN-ALARM-EXT-CAP.my,v $
-- *****************************************************************
-- RBN-ALARM-EXT-CAP.my  
--
-- Copyright (c) 2009, 2011 Ericsson AB.
-- All rights reserved.
-- 
-- *****************************************************************

RBN-ALARM-EXT-CAP DEFINITIONS ::= BEGIN

IMPORTS
	MODULE-IDENTITY
		FROM SNMPv2-SMI
	AGENT-CAPABILITIES
		FROM SNMPv2-CONF
	rbnCapabilities
		FROM RBN-SMI;

rbnAlarmExtCap MODULE-IDENTITY
	LAST-UPDATED    "201106150000Z" -- Jun 15, 2011
	ORGANIZATION	"Ericsson, Inc."
	CONTACT-INFO
		"	Ericsson, Inc.

                Postal: 100 Headquarters Dr
                        San Jose, CA  95134
                        USA

                 Phone: +1 408 570 5000
                   Fax: +1 408 570 5599

                "
	DESCRIPTION
		"The Agent Capabilities of the 
		implementation of the RBN-ALARM-EXT-MIB

                If this MIB implementation is platform-dependent,
                the PRODUCT-RELEASE clause contains Ericsson SEOS version and
                at least one of the following Ericsson product families:
                    [SE]  SmartEdge Multi-service Edge Router (MSER) family
                    [SM]  SM family of Metro Ethernet Service Transport platforms
                    [SSR] Smart Service Router (SSR) family"

        REVISION        "201106150000Z" -- Jun 15, 2011
        DESCRIPTION
            "Update DESCRIPTION clause of MODULE-IDENTITY
            and PRODUCT-RELEASE clause of AGENT-CAPABILITIES."
        
	REVISION	"200910231800Z" -- Oct 23, 2009
	DESCRIPTION
		"Initial version"
	::= { rbnCapabilities 94 }

rbnAlarmExtCap1 AGENT-CAPABILITIES
	PRODUCT-RELEASE	"SEOS 6.3"
	STATUS		current
	DESCRIPTION	"RBN-ALARM-EXT-MIB capabilities"
	SUPPORTS	RBN-ALARM-EXT-MIB
	INCLUDES {
            rbnAlarmModelGroup,
            rbnAlarmClearGroup
	}

	::= { rbnAlarmExtCap 1 }

END
