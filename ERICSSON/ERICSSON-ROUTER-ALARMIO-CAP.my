-- *****************************************************************
-- ERICSSON-ROUTER-ALARMIO-CAP
--
-- Copyright (c) 2015 Ericsson AB.
-- All rights reserved.
-- 
-- *****************************************************************

 ERICSSON-ROUTER-ALARMIO-CAP DEFINITIONS ::= BEGIN

     IMPORTS
         MODULE-IDENTITY, OBJECT-TYPE, OBJECT-IDENTITY,
         NOTIFICATION-TYPE, mib-2, Counter32,
         Integer32, TimeTicks                   FROM SNMPv2-SMI

         TEXTUAL-CONVENTION, DisplayString      FROM SNMPv2-TC

         MODULE-COMPLIANCE, OBJECT-GROUP,
         NOTIFICATION-GROUP                     FROM SNMPv2-CONF;

 eriRouterAlarmioMibCap MODULE-IDENTITY
     LAST-UPDATED "201508180000Z"  -- 18 Aug, 2015
     ORGANIZATION "Ericsson AB"
     CONTACT-INFO
         "David Xia
         Email: david.xia@ericsson.com"
     DESCRIPTION
         "Alarmio is physical connector held external IOs. This module is product specific.
                  It's only used in Spitfire series products.
                  It holds some input pins(ports) and output pins(ports).
                  The input ports are connected with other devices and used to accept signal from them.
                  Alarms are trapped when signal detected.
                  The output ports are connected with other devices and used to send out signal to them.
                  When critical or major alarms are detected, signal will be sent out by these ports.
                  Detailed usage is product specific."

     ::= { eriRouterCapabilities 108 }

 eriRouterAlarmioMibCap1 AGENT-CAPABILITIES
     PRODUCT-RELEASE "Spitfire 1.1.x [SP]"
     STATUS          current
     DESCRIPTION     "ALARMIO-MIB capabilities"
     SUPPORTS        ERICSSON-ROUTER-ALARMIO-MIB
     INCLUDES {
        eriRouterAlarmioMib
     }

     ::= { eriRouterAlarmioMibCap 1 }

 END
