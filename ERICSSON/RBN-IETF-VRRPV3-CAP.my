-- %DNP% $Id: RBN-IETF-VRRPv3-CAP.my,v 1.1.2.1.6.5 2011/06/15 18:19:45 danielhe Exp $
-- %DNP% $Source: /cvsroot/pkt/sw/se/xc/bsd/config/snmp/mibs/Attic/RBN-IETF-VRRP-CAP.my,v $
-- *****************************************************************
-- RBN-IETF-VRRPv3-CAP.my: VRRPv3-MIB Agent Capabilities
--
-- Copyright (c) 2014 Ericsson AB.
-- All rights reserved.
-- 
-- *****************************************************************

RBN-IETF-VRRPV3-CAP DEFINITIONS ::= BEGIN

IMPORTS
    MODULE-IDENTITY
        FROM SNMPv2-SMI
    AGENT-CAPABILITIES
        FROM SNMPv2-CONF
    rbnCapabilities
        FROM RBN-SMI;

rbnIetfVrrpv3Cap MODULE-IDENTITY
    LAST-UPDATED    "201403050000Z" -- MAR 5, 2014
    ORGANIZATION    "Ericsson AB."
    CONTACT-INFO
            "       Ericsson AB.

            Postal: 100 Headquarters Dr
                    San Jose, CA  95134
                    USA

             Phone: +1 408 750 5000
               Fax: +1 408 750 5599
            "
    DESCRIPTION
           "The Agent Capabilities of the VRRPV3-MIB (RFC 6527).

           If this MIB implementation is platform-dependent,
           the PRODUCT-RELEASE clause contains Ericsson SEOS version and
           at least one of the following Ericsson product families:
               [SSR] Smart Service Router (SSR) family"

    REVISION    "201403050000Z" -- MAR 05, 2014
    DESCRIPTION
           "Initial version"
        ::= { rbnCapabilities 107 }

rbnIetfVrrpv3Cap1 AGENT-CAPABILITIES
    PRODUCT-RELEASE "SEOS 14.1.x [SSR]"
    STATUS          current
    DESCRIPTION     "VRRPV3-MIB capabilities"
    SUPPORTS        VRRPV3-MIB
    INCLUDES {
            vrrpv3OperationsGroup,
            vrrpv3StatisticsGroup,
            vrrpv3StatisticsDiscontinuityGroup,
            vrrpv3InfoGroup,
            vrrpv3NotificationsGroup
            }

    VARIATION    vrrpNotificationCntl 
    DESCRIPTION
        "VRRP notification control is disabled by default."

    VARIATION    vrrpv3OperationsMasterIpAddr 
    ACCESS       read-only
    DESCRIPTION
        "Write access is not supported."

    VARIATION    vrrpv3OperationsPrimaryIpAddr 
    ACCESS       read-only
    DESCRIPTION
        "Write access is not supported."

    VARIATION    vrrpv3OperationsVirtualMacAddr 
    ACCESS       read-only
    DESCRIPTION
        "Write access is not supported."

    VARIATION    vrrpv3OperationsStatus
    ACCESS       read-only
    DESCRIPTION
        "Write access is not supported."

    VARIATION    vrrpv3OperationsPriority 
    ACCESS       read-only
    DESCRIPTION
        "Write access is not supported."

    VARIATION    vrrpv3OperationsAddrCount 
    ACCESS       read-only
    DESCRIPTION
        "Write access is not supported."

    VARIATION    vrrpv3OperationsAdvInterval
    ACCESS       read-only
    DESCRIPTION
        "Write access is not supported."

    VARIATION    vrrpv3OperationsPreemptMode 
    ACCESS       read-only
    DESCRIPTION
        "Write access is not supported."

    VARIATION    vrrpv3OperationsAcceptMode
    ACCESS       read-only
    DESCRIPTION
        "Write access is not supported."

    VARIATION    vrrpv3OperationsUpTime
    ACCESS       read-only
    DESCRIPTION
        "Write access is not supported."

    VARIATION    vrrpv3OperationsRowStatus
    ACCESS       read-only
    DESCRIPTION
        "Write access is not supported."

    VARIATION    vrrpv3StatisticsIpTtlErrors
    ACCESS       read-only
    DESCRIPTION
        "This counter is not session based, it is system wide"

    VARIATION    vrrpv3StatisticsAdvIntervalErrors  
    ACCESS       read-only
    DESCRIPTION
        "This counter is not supported"

    VARIATION    vrrpv3StatisticsAddressListErrors 
    ACCESS       read-only
    DESCRIPTION
        "This counter is not supported"

    VARIATION    vrrpv3RouterChecksumErrors 
    ACCESS       read-only
    DESCRIPTION
        "This counter is not supported"

    VARIATION    vrrpv3StatisticsProtoErrReason 
    ACCESS       read-only
    DESCRIPTION
        "This counter is not session based, it is system wide"

    ::= { rbnIetfVrrpv3Cap 1 }
END
