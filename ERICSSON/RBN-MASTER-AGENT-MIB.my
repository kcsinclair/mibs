-- *****************************************************************
-- RBN-MASTER-AGENT-MIB   MasterAgent Mib
--
-- %DNP% Copyright (c) 2013 Ericsson AB
-- %DNP% All rights reserved.
--
-- *****************************************************************
RBN-MASTER-AGENT-MIB DEFINITIONS ::= BEGIN

IMPORTS
    MODULE-IDENTITY, OBJECT-TYPE, NOTIFICATION-TYPE, Integer32
        FROM SNMPv2-SMI

    MODULE-COMPLIANCE, OBJECT-GROUP
        FROM SNMPv2-CONF

    RowStatus
        FROM SNMPv2-TC

    agentxSessionDescr
	FROM AGENTX-MIB

    rbnMgmt
        FROM RBN-SMI;

	rbnMasterAgentMIB MODULE-IDENTITY
	    LAST-UPDATED "201303080000Z"            -- 08 March 2013
	    ORGANIZATION "Ericsson"
	    CONTACT-INFO "postal:   Kovacs Zsolt
		                    Budapest
		                    1117 Irinyi ut

			  email:    kovacs.zsolt@ericssson.com
		         "
	    DESCRIPTION  "An AgentX master mib for
		         "

	    ::= { rbnMgmt 109 }
rbnMasterAgent   OBJECT IDENTIFIER ::= {rbnMasterAgentMIB 1}

rbnAgentxSessionCloseReason OBJECT-TYPE
  SYNTAX    INTEGER {
                reasonOther(1),
                reasonParseError(2),
                reasonProtocolError(3),
                reasonTimeouts(4),
                reasonShutdown(5),
                reasonByManager(6) }
  MAX-ACCESS  not-accessible
  STATUS      current
  DESCRIPTION
     "Contains the reason from AgentX-Close-PDU 'reason' field.
            reasonOther(1)
                 None of the following reasons
            reasonParseError(2)
                 Too many AgentX parse errors from peer
            reasonProtocolError(3)
                 Too many AgentX protocol errors from peer
            reasonTimeouts(4)
                 Too many timeouts waiting for peer
            reasonShutdown(5)
                 Sending entity is shutting down
            reasonByManager(6)
                 Due to Set operation; this reason code can be used only
                 by the master agent, in response to an SNMP management
                 request.
     "
  DEFVAL      { 1 }
  ::= { rbnMasterAgentMIB 2 }

rbnSubAgentLost NOTIFICATION-TYPE
OBJECTS {
	agentxSessionDescr,
	rbnAgentxSessionCloseReason
     }
STATUS   current
DESCRIPTION
  "The notification is sent in case of AgentX sub-agent session is lost or closed."
::= { rbnMasterAgent 2 }

END
