-- *****************************************************************
-- RBN-SUBAGENT-CAP    Ericsson AGENTX SUBAGENT Capabilities
--
-- Copyright (c) 2013-2014 Ericsson AB.
-- All rights reserved.
--
-- *****************************************************************

RBN-SUBAGENT-CAP DEFINITIONS ::= BEGIN

IMPORTS
        MODULE-IDENTITY
                FROM SNMPv2-SMI
        AGENT-CAPABILITIES
                FROM SNMPv2-CONF
        rbnCapabilities
                FROM RBN-SMI;

rbnSubAgentCap MODULE-IDENTITY
    LAST-UPDATED    "201406110000Z" -- June 11, 2014
    ORGANIZATION    "Ericsson AB."
    CONTACT-INFO    "postal:   Kovacs Zsolt
                            Budapest
                            1117 Irinyi ut
		  email:    zsolt.kovacs@ericsson.com
                 "
    DESCRIPTION
        "
	MIB module for the SNMP Agent Extensibility Protocol (AgentX).
	This MIB module will be implemented by the master agent.
	"
    REVISION    "2013032700Z" -- March 27, 2013
    DESCRIPTION
           "Initial version"
        ::= { rbnCapabilities 103 }

rbnSubAgentCap1 AGENT-CAPABILITIES
    PRODUCT-RELEASE "IPOS 13.2.x [SSR]"
    STATUS          current
    DESCRIPTION     "SUB-AGENT-MIB capabilities"
    SUPPORTS        SUB-AGENT-MIB
    INCLUDES {
       subagentManufacturer,
       subagentModelNumber,
       subagentControl,
       subagentDoneness,
       subagentMaterialType
    }

    ::= { rbnSubAgentCap 1 }

END
