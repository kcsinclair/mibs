-- ********************************************************************
-- *  Copyright (c) 2015 Ericsson AB.
-- *  All rights reserved.
-- ********************************************************************

BGP4V2-TC-MIB DEFINITIONS ::= BEGIN

    IMPORTS
        mib-2, MODULE-IDENTITY FROM SNMPv2-SMI
        TEXTUAL-CONVENTION FROM SNMPv2-TC;

        bgp4V2TC MODULE-IDENTITY
            LAST-UPDATED "201002010000Z"
            ORGANIZATION "IETF IDR Working Group"
            CONTACT-INFO "E-mail:  idr@ietf.org"

            DESCRIPTION
                    "Textual conventions for BGP-4.

                     Copyright (C) The IETF Trust (2010).  This
                     version of this MIB module is part of RFC XXX;
                     see the RFC itself for full legal notices."

            REVISION "201002010000Z"
            DESCRIPTION
                   "Initial version."
            ::= { mib-2 141 }

    --
    -- Textual Conventions
    --

    Bgp4V2IdentifierTC ::= TEXTUAL-CONVENTION
        DISPLAY-HINT "1d."
        STATUS       current
        DESCRIPTION
            "The representation of a BGP Identifier.  BGP Identifiers
             are presented in the received network byte order.

             The BGP Identifier is displayed as if it is an IP address,
             even if it would be an illegal one."
        REFERENCE
            "RFC 4273, Section 4.2"
        SYNTAX OCTET STRING(SIZE (4))

    Bgp4V2AddressFamilyIdentifierTC ::= TEXTUAL-CONVENTION
        STATUS       current
        DESCRIPTION
            "The representation of a BGP AFI.  The value of this object
             should be restricted to be between the values of 0 and 65535."
        REFERENCE
            "RFC 4760, Section 3"
        SYNTAX INTEGER {
                ipv4(1),
                ipv6(2)
            }

    Bgp4V2SubsequentAddressFamilyIdentifierTC ::= TEXTUAL-CONVENTION
        STATUS       current
        DESCRIPTION
            "The representation of a BGP SAFI"
        REFERENCE
            "RFC 4760, Section 3.  The value of this object should be
             restricted to be between the values of 0 and 255."
        SYNTAX INTEGER {
                unicast(1),
                multicast(2),
                mpls(4)
            }

END
