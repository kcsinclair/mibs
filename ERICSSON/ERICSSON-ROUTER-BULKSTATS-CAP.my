-- %DNP%
-- %DNP% $Source: /cvsroot/pkt/sw/se/xc/bsd/config/snmp/mibs/Attic/ERICSSON-ROUTER-BULKSTATS-CAP.my,v $
-- *****************************************************************
-- ERICSSON-ROUTER-BULKSTATS-CAP	Bulk Statistics MIB Capabilities
--
-- Copyright (c) 2002-2003, 2010-2011, 2015 Ericsson AB
-- All rights reserved.
-- 
-- *****************************************************************

ERICSSON-ROUTER-BULKSTATS-CAP DEFINITIONS ::= BEGIN

IMPORTS
	MODULE-IDENTITY
		FROM SNMPv2-SMI
	AGENT-CAPABILITIES
		FROM SNMPv2-CONF
	eriRouterCapabilities
		FROM ERICSSON-ROUTER-SMI;

eriRouterBulkStatsCap MODULE-IDENTITY
        LAST-UPDATED    "201501141800Z" -- Jan 14, 2015
        ORGANIZATION    "Ericsson Inc."
        CONTACT-INFO
                "       Ericsson, Inc.

                Postal: 100 Headquarters Dr.
                        San Jose, CA  95134
                        USA

                 Phone: +1 408 750 5000
                   Fax: +1 408 750 5599
                "
 	DESCRIPTION
		"The Agent Capabilities of the 
		Bulk Statistics MIB (ERICSSON-ROUTER-BULKSTATS-MIB).

                If this MIB implementation is platform-dependent,
                the PRODUCT-RELEASE clause contains Ericsson SEOS version and
                at least one of the following Ericsson product families:
                    [SE]  SmartEdge Multi-service Edge Router (MSER) family
                    [SM]  SM family of Metro Ethernet Service Transport platforms
                    [SSR] Smart Service Router (SSR) family"

        REVISION        "201501141800Z" -- Jan 14, 2015
        DESCRIPTION
                "Updated RBN/rbn/Rbn as ERICSSON-ROUTER/eriRouter/EriRouter
                 to migrate RBN MIB to ERICSSON MIB."

        REVISION        "201106150000Z" -- Jun 15, 2011
        DESCRIPTION
                "Update DESCRIPTION clause of MODULE-IDENTITY
                 and PRODUCT-RELEASE clause of AGENT-CAPABILITIES."

        REVISION        "201011010000Z" -- Nov 1, 2010
        DESCRIPTION
                "Modified PRODUCT-RELEASE clause for consistent naming.
                 Updated CONTACT-INFO."

	REVISION	"200305010000Z" -- May 1, 2003
	DESCRIPTION
		"Added new OID: eriRouterBulkStatsCap2."

	REVISION	"200207020000Z" -- July 2, 2002
	DESCRIPTION
		"Initial version."
	::= { eriRouterCapabilities 46 }

eriRouterBulkStatsCap1 AGENT-CAPABILITIES
	PRODUCT-RELEASE	"SEOS 2.3.X"
	STATUS		current
	DESCRIPTION	"ERICSSON-ROUTER-BULKSTATS-MIB capabilities"
	SUPPORTS	ERICSSON-ROUTER-BULKSTATS-MIB
	INCLUDES {
		eriRouterBulkStatsMIBObjectGroup,
		eriRouterBulkStatsMIBNotificationGroup
		}

	::= { eriRouterBulkStatsCap 1 }

eriRouterBulkStatsCap2 AGENT-CAPABILITIES
	PRODUCT-RELEASE	"SEOS 2.5.X [SE]; SEOS 6.3.X [SM]; SEOS 11.1.X [SSR]"
	STATUS		current
	DESCRIPTION	"ERICSSON-ROUTER-BULKSTATS-MIB capabilities"
	SUPPORTS	ERICSSON-ROUTER-BULKSTATS-MIB
	INCLUDES {
		eriRouterBulkStatsMIBObjectGroup2,
		eriRouterBulkStatsMIBNotificationGroup2
		}

	::= { eriRouterBulkStatsCap 2 }

END
