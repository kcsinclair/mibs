-- %DNP% $Id: ERICSSON-ROUTER-CONFIG-FILE-CAP.my,v 1.1.2.5.336.4 2011/06/15 18:19:45 danielhe Exp $
-- %DNP% $Source: /cvsroot/pkt/sw/se/xc/bsd/config/snmp/mibs/Attic/ERICSSON-ROUTER-CONFIG-FILE-CAP.my,v $
-- *****************************************************************
-- ERICSSON-ROUTER-CONFIG-FILE-CAP	    Config File Mib Capabilities
--
-- Copyright (c) 2001-2002, 2004, 2010-2011, 2015-2016 Ericsson AB
-- All rights reserved.
--
-- *****************************************************************

ERICSSON-ROUTER-CONFIG-FILE-CAP DEFINITIONS ::= BEGIN

IMPORTS

    MODULE-IDENTITY
            FROM SNMPv2-SMI
    AGENT-CAPABILITIES
            FROM SNMPv2-CONF

    eriRouterCapabilities
            FROM ERICSSON-ROUTER-SMI;

eriRouterConfigFileMibCap MODULE-IDENTITY
    LAST-UPDATED    "201501141800Z" -- Jan 14, 2015
    ORGANIZATION    "Ericsson Inc."
    CONTACT-INFO
            "       Ericsson, Inc.

            Postal: 100 Headquarters Dr.
                    San Jose, CA  95134
                    USA

             Phone: +1 408 750 5000
               Fax: +1 408 750 5599
            "
    DESCRIPTION
	    "The Agent Capabilities of the Config File MIB.

            If this MIB implementation is platform-dependent,
            the PRODUCT-RELEASE clause contains Ericsson SEOS version and
            at least one of the following Ericsson product families:
                [SE]  SmartEdge Multi-service Edge Router (MSER) family
                [SM]  SM family of Metro Ethernet Service Transport platforms
                [SSR] Smart Service Router (SSR) family"

    REVISION    "201501141800Z" -- Jan 14, 2015
    DESCRIPTION
            "Updated RBN/rbn/Rbn as ERICSSON-ROUTER/eriRouter/EriRouter
             to migrate RBN MIB to ERICSSON MIB."

    REVISION    "201106150000Z" -- Jun 15, 2011
    DESCRIPTION
            "Update DESCRIPTION clause of MODULE-IDENTITY
            and PRODUCT-RELEASE clause of AGENT-CAPABILITIES."

    REVISION    "201011010000Z" -- Nov 1, 2010
    DESCRIPTION
            "Modified PRODUCT-RELEASE clause for consistent naming.
            Updated CONTACT-INFO."

    REVISION    "200408120000Z" -- August 12, 2004
    DESCRIPTION
	    "Added new OID:
	        eriRouterConfigFileMibCap3."

    REVISION	"200210280000Z" -- October 28, 2002
    DESCRIPTION
	    "Updated CONTACT-INFO.
	     Added new OID:
		eriRouterConfigFileMibCap2."

    REVISION	"200110100000Z" -- October 10, 2001
    DESCRIPTION
	    "Initial version."
    ::= { eriRouterCapabilities 36 }

eriRouterConfigFileMibCap1 AGENT-CAPABILITIES
    PRODUCT-RELEASE	"AOS 5.1.X.X"
    STATUS		current
    DESCRIPTION	"ERICSSON-ROUTER-CONFIG-FILE-MIB capabilities"
    SUPPORTS	ERICSSON-ROUTER-CONFIG-FILE-MIB
    INCLUDES {
        eriRouterCfJobGroup,
	    eriRouterCfJobNotifyGroup
    }

    VARIATION eriRouterCfJobIpAddressType
	WRITE-SYNTAX INTEGER { ipv4(1) }
	DESCRIPTION
	"Restrict InetAddressType to ipv4(1)."

    VARIATION eriRouterCfJobUsername
        DESCRIPTION
        "Each character must be printable (the posix function isprint()
        returns true for each character)."

    VARIATION eriRouterCfJobPassword
        DESCRIPTION
        "Each character must be printable (the posix function isprint()
        returns true for each character)."

    VARIATION eriRouterCfJobFilename
        DESCRIPTION
        "Each character must be printable (the posix function isprint()
        returns true for each character)."

    VARIATION eriRouterCfJobErrorMsgs
        DESCRIPTION
        "Each character must be printable (the posix function isprint()
        returns true for each character) or the newline character."

    VARIATION eriRouterCfJobOwner
        DESCRIPTION
        "Each character must be printable (the posix function isprint()
        returns true for each character)."

    ::= { eriRouterConfigFileMibCap 1 }

eriRouterConfigFileMibCap2 AGENT-CAPABILITIES
    PRODUCT-RELEASE	"SEOS 2.3.4"
    STATUS		current
    DESCRIPTION	"ERICSSON-ROUTER-CONFIG-FILE-MIB capabilities"
    SUPPORTS	ERICSSON-ROUTER-CONFIG-FILE-MIB
    INCLUDES {
        eriRouterCfJobGroup
    }

    VARIATION eriRouterCfJobOp
	WRITE-SYNTAX INTEGER { save(1) }
	DESCRIPTION
	"Restrict to save(1)."

    VARIATION eriRouterCfJobProtocol
	WRITE-SYNTAX INTEGER { tftp(1), ftp(2) }
	DEFVAL { tftp }
	DESCRIPTION
	"Restrict to tftp(1), ftp(2). local(0) not supported."

    VARIATION eriRouterCfJobIpAddressType
	WRITE-SYNTAX INTEGER { ipv4(1) }
	DESCRIPTION
	"Restrict InetAddressType to ipv4(1)."

    VARIATION eriRouterCfJobUsername
        DESCRIPTION
        "Each character must be printable (the posix function isprint()
        returns true for each character)."

    VARIATION eriRouterCfJobPassword
        DESCRIPTION
        "Each character must be printable (the posix function isprint()
        returns true for each character)."

    VARIATION eriRouterCfJobFilename
        DESCRIPTION
        "Each character must be printable (the posix function isprint()
        returns true for each character)."

    VARIATION eriRouterCfJobPassiveMode
	ACCESS	not-implemented
	DESCRIPTION
	"Object not supported."

    VARIATION eriRouterCfJobStopAtLine
	ACCESS	not-implemented
	DESCRIPTION
	"Object not supported."

    VARIATION eriRouterCfJobErrorMsgs
        DESCRIPTION
        "Each character must be printable (the posix function isprint()
        returns true for each character) or the newline character."

    VARIATION eriRouterCfJobNotifyOnCompletion
	ACCESS	not-implemented
	DESCRIPTION
	"Object not supported."

    VARIATION eriRouterCfJobOwner
        DESCRIPTION
        "Each character must be printable (the posix function isprint()
        returns true for each character)."

    ::= { eriRouterConfigFileMibCap 2 }

eriRouterConfigFileMibCap3 AGENT-CAPABILITIES
    PRODUCT-RELEASE     "SEOS 2.6.5.X [SE]; SEOS 6.3.X [SM]; SEOS 11.1.X [SSR]"
    STATUS              current
    DESCRIPTION "ERICSSON-ROUTER-CONFIG-FILE-MIB capabilities"
    SUPPORTS    ERICSSON-ROUTER-CONFIG-FILE-MIB
    INCLUDES {
        eriRouterCfJobGroup,
        eriRouterCfJobNotifyGroup
    }

    VARIATION eriRouterCfJobIpAddressType
        WRITE-SYNTAX INTEGER { ipv4(1) }
        DESCRIPTION
        "Restrict InetAddressType to ipv4(1)."

    VARIATION eriRouterCfJobUsername
        DESCRIPTION
        "Each character must be printable (the posix function isprint()
        returns true for each character)."

    VARIATION eriRouterCfJobPassword
        DESCRIPTION
        "Each character must be printable (the posix function isprint()
        returns true for each character)."

    VARIATION eriRouterCfJobFilename
        DESCRIPTION
        "Each character must be printable (the posix function isprint()
        returns true for each character)."

    VARIATION eriRouterCfJobPassiveMode
        ACCESS  not-implemented
        DESCRIPTION
        "Object not supported."

    VARIATION eriRouterCfJobErrorMsgs
        DESCRIPTION
        "Each character must be printable (the posix function isprint()
        returns true for each character) or the newline character."

    VARIATION eriRouterCfJobOwner
        DESCRIPTION
        "Each character must be printable (the posix function isprint()
        returns true for each character)."

    ::= { eriRouterConfigFileMibCap 3 }

END
