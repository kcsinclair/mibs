-- %DNP% $Id: RBN-BGP-ACCOUNTING-CAP.my,v 1.1.4.3.270.4 2011/06/15 18:19:45 danielhe Exp $
-- %DNP% $Source: /cvsroot/pkt/sw/se/xc/bsd/config/snmp/mibs/Attic/RBN-BGP-ACCOUNTING-CAP.my,v $
-- *****************************************************************
-- RBN-BGP-ACCOUNTING-CAP
--
-- Copyright (c) 2002, 2004-2005, 2010-2011 Ericsson AB
-- All rights reserved.
-- 
-- *****************************************************************

RBN-BGP-ACCOUNTING-CAP DEFINITIONS ::= BEGIN

IMPORTS
	MODULE-IDENTITY
		FROM SNMPv2-SMI
	AGENT-CAPABILITIES
		FROM SNMPv2-CONF
	rbnCapabilities
		FROM RBN-SMI;

rbnBgpPolAcctCap MODULE-IDENTITY
        LAST-UPDATED    "201106150000Z" -- Jun 15, 2011
        ORGANIZATION    "Ericsson Inc."
        CONTACT-INFO
                "       Ericsson, Inc.

                Postal: 100 Headquarters Dr.
                        San Jose, CA  95134
                        USA

                 Phone: +1 408 750 5000
                   Fax: +1 408 750 5599
                "
	DESCRIPTION
		"The Agent Capabilities of the BGP policy 
		 based accounting MIB (RBN-BGP-ACCOUNTING-MIB).

                If this MIB implementation is platform-dependent,
                the PRODUCT-RELEASE clause contains Ericsson SEOS version and
                at least one of the following Ericsson product families:
                    [SE]  SmartEdge Multi-service Edge Router (MSER) family
                    [SM]  SM family of Metro Ethernet Service Transport platforms
                    [SSR] Smart Service Router (SSR) family"

        REVISION        "201106150000Z" -- Jun 15, 2011
        DESCRIPTION
            "Update DESCRIPTION clause of MODULE-IDENTITY
            and PRODUCT-RELEASE clause of AGENT-CAPABILITIES."
        REVISION    "201011010000Z" -- Nov 1, 2010
        DESCRIPTION
            "Modified PRODUCT-RELEASE clause for consistent naming.
             Updated CONTACT-INFO."

        REVISION        "200509200000Z" -- September 20, 2005
        DESCRIPTION
                " Added table group capability "

	REVISION        "200212260000Z" -- December 26, 2002
	DESCRIPTION
		"Initial version."
	::= { rbnCapabilities 54 }

rbnBgpPolAcctCap1 AGENT-CAPABILITIES
	PRODUCT-RELEASE "SEOS 2.4.4"
	STATUS		current
	DESCRIPTION	"RBN-BGP-ACCOUNTING-MIB capabilities"
	SUPPORTS	RBN-BGP-ACCOUNTING-MIB
	INCLUDES {
		rbnBpaTableGroup
		}
	::= { rbnBgpPolAcctCap 1 }

rbnBgpPolAcctCap2 AGENT-CAPABILITIES
        PRODUCT-RELEASE "SEOS 5.0.3 [SE]; SEOS 6.3.X [SM]; SEOS 11.1.X [SSR]"
        STATUS          current
        DESCRIPTION     "RBN-BGP-ACCOUNTING-MIB capabilities"
        SUPPORTS        RBN-BGP-ACCOUNTING-MIB
        INCLUDES {
                rbnBpaTableGroup1
                }
        ::= { rbnBgpPolAcctCap 2 }           
END
