-- %DNP% $Id: RBN-IETF-BFD-STD.my,v 1.1.6.3.250.4 2015/03/01 18:19:45 xshaprt xsailes Exp $
-- *****************************************************************
-- RBN-IETF-BFD-STD-CAP
--
-- Copyright (c) 2015-2016 Ericsson AB
-- All rights reserved.
--
-- *****************************************************************

RBN-IETF-BFD-STD-CAP DEFINITIONS ::= BEGIN

IMPORTS
        MODULE-IDENTITY
                FROM SNMPv2-SMI
        AGENT-CAPABILITIES
                FROM SNMPv2-CONF
        rbnCapabilities
                FROM RBN-SMI;

rbnIetfBfdStdCap MODULE-IDENTITY
        LAST-UPDATED    "201503010000Z" -- Mar 01, 2015
	ORGANIZATION	"Ericsson Inc."
	CONTACT-INFO
		"	Ericsson, Inc.

		Postal:	100 Headquarters Dr.
			San Jose, CA  95134
			USA

		 Phone:	+1 408 750 5000
		   Fax: +1 408 750 5599

		"
        DESCRIPTION
                "The Agent Capabilities of the
		implementation of the BFD-STD.

                If this MIB implementation is platform-dependent,
                the PRODUCT-RELEASE clause contains Ericsson SEOS version and
                at least one of the following Ericsson product families:
                    [SE]  SmartEdge Multi-service Edge Router (MSER) family
                    [SM]  SM family of Metro Ethernet Service Transport platforms
                    [SSR] Smart Service Router (SSR) family"

        REVISION        "200003050000Z" -- March 1, 2015
        DESCRIPTION
                "Initial version ."

        ::= { rbnCapabilities 26 }

rbnIetfBfdStdCap1 AGENT-CAPABILITIES
        PRODUCT-RELEASE "IPOS 4.0.X.X"
        STATUS          current
        DESCRIPTION     "BFD-STD capabilities for SMS"
        SUPPORTS         BFD-STD-MIB
        INCLUDES { bfdNotificationGroup}


        VARIATION       bfdSessDiag
        ACCESS           accessible-for-notify
        DESCRIPTION
                "This object is available only in notifications."

        ::= { rbnIetfBfdStdCap 1  }


END
