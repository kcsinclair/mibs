-- %DNP% $Id: ERICSSON-ROUTER-BRIDGE-CAP.my,v 1.1.2.5.18.4 2011/06/15 18:19:45 danielhe Exp $
-- %DNP% $Source: /cvsroot/pkt/sw/se/xc/bsd/config/snmp/mibs/Attic/ERICSSON-ROUTER-BRIDGE-CAP.my,v $
-- *****************************************************************
-- ERICSSON-ROUTER-BRIDGE-CAP: ERICSSON-ROUTER-BRIDGE-MIB Agent Capabilities
--
-- Copyright (c) 2007, 2008, 2010-2011, 2015 Ericsson AB
-- All rights reserved.
--
-- *****************************************************************

ERICSSON-ROUTER-BRIDGE-CAP DEFINITIONS ::= BEGIN

IMPORTS
        MODULE-IDENTITY
                FROM SNMPv2-SMI
        AGENT-CAPABILITIES
                FROM SNMPv2-CONF
        eriRouterCapabilities
                FROM ERICSSON-ROUTER-SMI;
 
eriRouterBridgeCap MODULE-IDENTITY
        LAST-UPDATED    "201501141800Z" -- Jan 14, 2015
        ORGANIZATION    "Ericsson Inc."
        CONTACT-INFO
                "       Ericsson, Inc.

                Postal: 100 Headquarters Dr.
                        San Jose, CA  95134
                        USA

                 Phone: +1 408 750 5000
                   Fax: +1 408 750 5599
                "
        DESCRIPTION
                "The Agent Capabilities of the BRIDGE MIB (ERICSSON-ROUTER-BRIDGE-MIB).

                If this MIB implementation is platform-dependent,
                the PRODUCT-RELEASE clause contains Ericsson SEOS version and
                at least one of the following Ericsson product families:
                    [SE]  SmartEdge Multi-service Edge Router (MSER) family
                    [SM]  SM family of Metro Ethernet Service Transport platforms
                    [SSR] Smart Service Router (SSR) family"

        REVISION        "201501141800Z" -- Jan 14, 2015
        DESCRIPTION
                "Updated RBN/rbn/Rbn as ERICSSON-ROUTER/eriRouter/EriRouter
                 to migrate RBN MIB to ERICSSON MIB."

        REVISION        "201106150000Z" -- Jun 15, 2011
        DESCRIPTION
                "Update DESCRIPTION clause of MODULE-IDENTITY
                 and PRODUCT-RELEASE clause of AGENT-CAPABILITIES."
        
        REVISION        "201011010000Z" -- Nov 1, 2010
        DESCRIPTION
                "Modified PRODUCT-RELEASE clause for consistent naming.
                 Updated CONTACT-INFO."

        REVISION        "200802250000Z" -- Feb 25, 2008
        DESCRIPTION
                "Added new OID eriRouterBridgeCap2. Added new groups
                  eriRouterBridgeStateNotifyObjectGroup,
                  eriRouterBridgeBaseObjectGroup, 
                
                 new notification group eriRouterBridgeStateNotifyGroup."

        REVISION        "200706260000Z" -- June 26, 2007
        DESCRIPTION
                "Initial version"
        ::= { eriRouterCapabilities 73 }

eriRouterBridgeCap1 AGENT-CAPABILITIES
        PRODUCT-RELEASE "SEOS 6.1"
        STATUS          obsolete
        DESCRIPTION     "ERICSSON-ROUTER-BRIDGE-MIB capabilities"
        SUPPORTS        ERICSSON-ROUTER-BRIDGE-MIB
        INCLUDES {
                    eriRouterBridgeNotifyObjectGroup,
                    eriRouterBridgeNotifyGroup
                 }
        ::= { eriRouterBridgeCap 1 }

eriRouterBridgeCap2 AGENT-CAPABILITIES
        PRODUCT-RELEASE "SEOS 6.1.4 [SE]; SEOS 6.3.X [SM]"
        STATUS          current
        DESCRIPTION     "ERICSSON-ROUTER-BRIDGE-MIB capabilities"
        SUPPORTS        ERICSSON-ROUTER-BRIDGE-MIB
        INCLUDES {
                    eriRouterBridgeNotifyObjectGroup,
                    eriRouterBridgeStateNotifyObjectGroup,
                    eriRouterBridgeNotifyGroup,
                    eriRouterBridgeStateNotifyGroup,
                    eriRouterBridgeBaseObjectGroup
                 }
        ::= { eriRouterBridgeCap 2 }

END
