-- %DNP% $Id: RBN-IETF-ENTITY-CAP.my,v 1.1.6.4.250.5 2011/06/15 18:19:45 danielhe Exp $
-- %DNP% $Source: /cvsroot/pkt/sw/se/xc/bsd/config/snmp/mibs/RBN-IETF-ENTITY-CAP.my,v $
-- *****************************************************************
-- RBN-IETF-ENTITY-CAP.my      ENTITY MIB RBN agent capabilities
--
-- Copyright (c) 2001-2006, 2010-2011 Ericsson AB
-- All rights reserved.
-- 
-- *****************************************************************

RBN-IETF-ENTITY-CAP DEFINITIONS ::= BEGIN

IMPORTS
        MODULE-IDENTITY
                FROM SNMPv2-SMI
        AGENT-CAPABILITIES
                FROM SNMPv2-CONF
        rbnCapabilities
                FROM RBN-SMI;

rbnIetfEntityCap MODULE-IDENTITY
        LAST-UPDATED    "201106150000Z" -- Jun 15, 2011
	ORGANIZATION	"Ericsson AB."
	CONTACT-INFO
		"	Ericsson AB.

		Postal:	100 Headquarters Dr.
			San Jose, CA  95134
			USA

		 Phone:	+1 408 750 5000
		   Fax: +1 408 750 5599
		"
        DESCRIPTION
                "The Agent Capabilities of the 
                implementation of the ENTITY-MIB.

                If this MIB implementation is platform-dependent,
                the PRODUCT-RELEASE clause contains Ericsson SEOS version and
                at least one of the following Ericsson product families:
                    [SE]  SmartEdge Multi-service Edge Router (MSER) family
                    [SM]  SM family of Metro Ethernet Service Transport platforms
                    [SSR] Smart Service Router (SSR) family"

        REVISION        "201106150000Z" -- Jun 15, 2011
        DESCRIPTION
            "Update DESCRIPTION clause of MODULE-IDENTITY
            and PRODUCT-RELEASE clause of AGENT-CAPABILITIES."
	REVISION	"201011010000Z" -- Nov 1, 2010
	DESCRIPTION
		"Modified PRODUCT-RELEASE clause for consistent naming.
                 Updated CONTACT-INFO."
                
        REVISION        "200905070000Z" -- May 07, 2009
        DESCRIPTION
                 "Added new OID:
                        rbnIetfEntityCap5.
                 "       
        REVISION        "200503220000Z" -- Mar. 22, 2005
        DESCRIPTION
                "Modified rbnIetfEntityCap4 to include entityMappingGroup.
                 Added new OID:
                        rbnIetfEntityCap4.
                 "

        REVISION        "200310010000Z" -- Oct 1, 2003
        DESCRIPTION
                "Modified rbnIetfEntityCap1 to include entityGeneralGroup.
                 Added new OID:
                        rbnIetfEntityCap3.
                 "

	REVISION	"200105181100Z" -- May 18, 2001
	DESCRIPTION
		"Added new OID:
			rbnIetfEntityCap2"

        REVISION        "200102201000Z" -- February 20, 2001
        DESCRIPTION
                "Initial version."
        ::= { rbnCapabilities 33 }

rbnIetfEntityCap1 AGENT-CAPABILITIES
        PRODUCT-RELEASE "AOS 5.0.X.X"
        STATUS          current
        DESCRIPTION     "ENTITY-MIB capabilities"
        SUPPORTS        ENTITY-MIB  
        INCLUDES { 
                   entityPhysicalGroup,
                   entityGeneralGroup,
                   entityNotificationsGroup
                 }      

        ::= { rbnIetfEntityCap 1  }

rbnIetfEntityCap2 AGENT-CAPABILITIES
        PRODUCT-RELEASE "SEOS 2.0"
        STATUS          current
        DESCRIPTION     "ENTITY-MIB capabilities"
        SUPPORTS        ENTITY-MIB  
        INCLUDES { 
                   entityPhysicalGroup,
                   entityNotificationsGroup
                 }      

        ::= { rbnIetfEntityCap 2  }

rbnIetfEntityCap3 AGENT-CAPABILITIES
        PRODUCT-RELEASE "SEOS 2.5.7"
        STATUS          current
        DESCRIPTION     "ENTITY-MIB capabilities"
        SUPPORTS        ENTITY-MIB
        INCLUDES {
                   entityPhysicalGroup,
                   entityGeneralGroup,
                   entityNotificationsGroup
                 }
        ::= { rbnIetfEntityCap 3  }

rbnIetfEntityCap4 AGENT-CAPABILITIES
        PRODUCT-RELEASE "AOS 6.0.5.X"
        STATUS          current
        DESCRIPTION     "ENTITY-MIB capabilities"
        SUPPORTS        ENTITY-MIB
        INCLUDES {
                   entityPhysicalGroup,
                   entityGeneralGroup,
                   entityNotificationsGroup,
                   entityMappingGroup
                 }
        ::= { rbnIetfEntityCap 4  }

rbnIetfEntityCap5 AGENT-CAPABILITIES
        PRODUCT-RELEASE "SEOS 6.2.X [SE]; SEOS 6.3.X [SM]; SEOS 11.1.x [SSR]"
        STATUS          current
        DESCRIPTION     "ENTITY-MIB capabilities"
        SUPPORTS        ENTITY-MIB
        INCLUDES {
                   entityPhysicalGroup,
                   entityGeneralGroup,
                   entityNotificationsGroup,
                   entityMappingGroup
                 }

        VARIATION      entLPPhysicalIndex
        ACCESS          not-implemented
        DESCRIPTION    "This object is not supported"

        VARIATION      entPhysicalChildIndex
        ACCESS          not-implemented
        DESCRIPTION    "This object is not supported"
        ::= { rbnIetfEntityCap 5  }
END
