-- %DNP% $Id: RBN-ENVMON-CAP.my,v 1.2.4.3.146.8 2011/09/07 19:09:29 sraj Exp $
-- %DNP% $Source: /cvsroot/pkt/sw/se/xc/bsd/config/snmp/mibs/RBN-ENVMON-CAP.my,v $
-- *****************************************************************
-- RBN-ENVMON-CAP	Environmental Monitor MIB Capabilities
--
-- Copyright (c) 1999-2002, 2006-2007, 2010-2011 Ericsson AB.
-- All rights reserved.
-- 
-- *****************************************************************

RBN-ENVMON-CAP DEFINITIONS ::= BEGIN

IMPORTS
	MODULE-IDENTITY
		FROM SNMPv2-SMI
	AGENT-CAPABILITIES
		FROM SNMPv2-CONF
	rbnCapabilities
		FROM RBN-SMI;

rbnEnvMonCap MODULE-IDENTITY
        LAST-UPDATED    "201109020000Z" -- September 02, 2011
        ORGANIZATION    "Ericsson Inc."
        CONTACT-INFO
                "       Ericsson, Inc.

                Postal: 100 Headquarters Dr.
                        San Jose, CA  95134
                        USA

                 Phone: +1 408 750 5000
                   Fax: +1 408 750 5599
                "
	DESCRIPTION
		"The Agent Capabilities of the Environmental 
                 Monitor MIB (RBN-ENVMON-MIB).

                If this MIB implementation is platform-dependent,
                the PRODUCT-RELEASE clause contains Ericsson SEOS version and
                at least one of the following Ericsson product families:
                    [SE]  SmartEdge Multi-service Edge Router (MSER) family
                    [SM]  SM family of Metro Ethernet Service Transport platforms
                    [SSR] Smart Service Router (SSR) family"

        REVISION        "201109020000Z" -- September 02, 2011
        DESCRIPTION
                "Added new OID:
                        rbnEnvMonCap6."

        REVISION        "201106150000Z" -- Jun 15, 2011
        DESCRIPTION
            "Update DESCRIPTION clause of MODULE-IDENTITY
            and PRODUCT-RELEASE clause of AGENT-CAPABILITIES."
        
        REVISION    "201011110000Z" -- Nov 11, 2010
        DESCRIPTION
            "Modified PRODUCT-RELEASE clause for consistent naming.
             Updated CONTACT-INFO."

        REVISION        "200811110000Z" -- November 11, 2008
        DESCRIPTION
                "Added new OID:
                        rbnEnvMonCap5."

	REVISION	"200601160000Z" -- January 16, 2006
	DESCRIPTION
		"Added new OID:
			rbnEnvMonCap4"
	REVISION	"200206050000Z" -- June 5, 2002
	DESCRIPTION
		"Updated/corrected CONTACT-INFO."
	REVISION	"200107250000Z" -- July 25, 2001
	DESCRIPTION
		"Added new OID:
			rbnEnvMonCap3"
	REVISION	"200004240000Z" -- May 24, 2000
	DESCRIPTION
		"Added voltage and temperature sensor tables."
	REVISION        "199903092300Z" -- Mar 9, 1999
	DESCRIPTION
		"Initial version."
	::= { rbnCapabilities 17 }

rbnEnvMonCap1 AGENT-CAPABILITIES
	PRODUCT-RELEASE	"2.3.X.X"
	STATUS		obsolete
	DESCRIPTION	"RBN-ENVMON-MIB capabilities"
	SUPPORTS	RBN-ENVMON-MIB
	INCLUDES {
		rbnEnvMonMIBObjectGroup,
		rbnEnvMonMIBNotificationGroup
		}

	::= { rbnEnvMonCap 1 }

rbnEnvMonCap2 AGENT-CAPABILITIES
	PRODUCT-RELEASE	"4.0.X.X"
	STATUS		current
	DESCRIPTION	"RBN-ENVMON-MIB capabilities"
	SUPPORTS	RBN-ENVMON-MIB
	INCLUDES {
		rbnEnvMonMIBObjectGroup,
		rbnEnvMonMIBNotificationGroup,
		rbnEnvMonVoltageObjectGroup,
		rbnEnvMonTempObjectGroup
		}

	::= { rbnEnvMonCap 2 }

rbnEnvMonCap3 AGENT-CAPABILITIES
	PRODUCT-RELEASE "SmartEdge 2.0.4"
	STATUS		current
	DESCRIPTION	"RBN-ENVMON-MIB capabilities"
	SUPPORTS	RBN-ENVMON-MIB
	INCLUDES {
		rbnEnvMonMIBObjectGroupV2,
		rbnEnvMonMIBNotificationGroupV2,
		rbnEnvMonVoltageObjectGroup
		}

	::= { rbnEnvMonCap 3 }

rbnEnvMonCap4 AGENT-CAPABILITIES
	PRODUCT-RELEASE "SmartEdge 5.0.5"
	STATUS		current
	DESCRIPTION	"RBN-ENVMON-MIB capabilities"
	SUPPORTS	RBN-ENVMON-MIB
	INCLUDES {
		rbnEnvMonMIBObjectGroupV2,
		rbnEnvMonMIBNotificationGroupV2,
		rbnEnvMonVoltageObjectGroup,
		rbnEnvMonFanSpeedObjectGroup
		}

	VARIATION rbnFanUnitDescr
	DESCRIPTION
	"This object is only supported in SE100."

	VARIATION rbnFanSpeedCurrent
	DESCRIPTION
	"This object is only supported in SE100."

	::= { rbnEnvMonCap 4 }

rbnEnvMonCap5 AGENT-CAPABILITIES
        PRODUCT-RELEASE "SEOS 6.2.1 [SE]; SEOS 6.3.X [SM]; SEOS 11.1.X [SSR]"
        STATUS          current
        DESCRIPTION     "RBN-ENVMON-MIB capabilities"
        SUPPORTS        RBN-ENVMON-MIB
        INCLUDES {
                rbnEnvMonMIBObjectGroupV2,
                rbnEnvMonMIBNotificationGroupV2,
                rbnEnvMonVoltageObjectGroup,
                rbnEnvMonFanSpeedObjectGroup,
                rbnEnvMonEntityObjectGroup
                }

        VARIATION rbnFanUnitDescr
        DESCRIPTION
        "This object is only supported in SE100."

        VARIATION rbnFanSpeedCurrent
        DESCRIPTION
        "This object is only supported in SE100."

        ::= { rbnEnvMonCap 5 }

rbnEnvMonCap6 AGENT-CAPABILITIES
        PRODUCT-RELEASE "IPOS 11.1.X"
        STATUS          current
        DESCRIPTION     "RBN-ENVMON-MIB capabilities"
        SUPPORTS        RBN-ENVMON-MIB
        INCLUDES {
                rbnEnvMonMIBObjectGroupV2,
                rbnEnvMonMIBNotificationGroupV2,
                rbnEnvMonVoltageObjectGroup,
                rbnEnvMonFanSpeedObjectGroup,
                rbnEnvMonEntityObjectGroup
                }

        VARIATION rbnFanUnitDescr
        DESCRIPTION
        "This object is only supported in SE100 and SSR."

        VARIATION rbnFanSpeedCurrent
        DESCRIPTION
        "This object is only supported in SE100 and SSR."

        ::= { rbnEnvMonCap 6 }

END
