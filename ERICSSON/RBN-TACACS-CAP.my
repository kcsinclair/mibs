-- %DNP% $Id: RBN-TACACS-CAP.my,v 1.1.4.1.370.3 2011/06/15 18:19:46 danielhe Exp $
-- %RBN% $Source: /cvsroot/pkt/sw/se/xc/bsd/config/snmp/mibs/Attic/RBN-TACACS-CAP.my,v $
-- *****************************************************************
-- RBN-TACACS-CAP     RBN-TACACS-MIB Capabilities
--
-- Copyright (c) 2004, 2011 Ericsson AB
-- All rights reserved.
-- 
-- *****************************************************************

RBN-TACACS-CAP DEFINITIONS ::= BEGIN

IMPORTS
    MODULE-IDENTITY     FROM SNMPv2-SMI
    AGENT-CAPABILITIES  FROM SNMPv2-CONF
    rbnCapabilities     FROM RBN-SMI;

rbnTacacsCap MODULE-IDENTITY
    LAST-UPDATED    "201106150000Z" -- Jun 15, 2011
    ORGANIZATION    "Ericsson AB."
    CONTACT-INFO
            "       Ericsson AB.

            Postal: 100 Headquarters Dr
                    San Jose, CA  95134
                    USA

             Phone: +1 408 750 5000
               Fax: +1 408 750 5599
            "
    DESCRIPTION
        "The Agent Capabilities of the TACACS MIB module (RBN-TACACS-MIB).

        If this MIB implementation is platform-dependent,
        the PRODUCT-RELEASE clause contains Ericsson SEOS version and
        at least one of the following Ericsson product families:
            [SE]  SmartEdge Multi-service Edge Router (MSER) family
            [SM]  SM family of Metro Ethernet Service Transport platforms
            [SSR] Smart Service Router (SSR) family"

        REVISION        "201106150000Z" -- Jun 15, 2011
        DESCRIPTION
            "Update DESCRIPTION clause of MODULE-IDENTITY
            and PRODUCT-RELEASE clause of AGENT-CAPABILITIES."
    REVISION        "201101191800Z" -- Jan 19, 2011
    DESCRIPTION
            "Update CONTACT-INFO & ORGANIZATION. "

    REVISION	"200406291800Z" -- June 29, 2004
    DESCRIPTION
        "add rbnTacacsCap2."

    REVISION	"200403021800Z" -- March 2, 2004
    DESCRIPTION
        "Initial version."
    ::= { rbnCapabilities 61 }
    
rbnTacacsCap1 AGENT-CAPABILITIES
    PRODUCT-RELEASE "AOS 6.0.10.x"
    STATUS	    current
    DESCRIPTION	    "RBN-TACACS-MIB capabilities"
    SUPPORTS	    RBN-TACACS-MIB
    INCLUDES {
        rbnTacacsNotifyGroup
    }
    ::= { rbnTacacsCap 1 }

rbnTacacsCap2 AGENT-CAPABILITIES
    PRODUCT-RELEASE "SEOS 2.6.5 [SE]; SEOS 6.3.X [SM]; SEOS 11.1.x [SSR]"
    STATUS	    current
    DESCRIPTION	    "RBN-TACACS-MIB capabilities"
    SUPPORTS	    RBN-TACACS-MIB
    INCLUDES {
        rbnTacacsNotifyGroup
    }
    ::= { rbnTacacsCap 2 }

END
