-- $Id: ERICSSON-ROUTER-MEDIA-GATEWAY-CAP.my,v 1.1.6.2 2011/06/15 18:19:46 danielhe Exp $ 
-- $Source: /cvsroot/pkt/sw/se/xc/bsd/config/snmp/mibs/Attic/ERICSSON-ROUTER-MEDIA-GATEWAY-CAP.my,v $
-- *****************************************************************
-- ERICSSON-ROUTER-MEDIA_GATEWAY-CAP: ERICSSON-ROUTER-MEDIA_GATEWAY-MIB Agent Capabilities
--
-- Copyright (c) 2009-2010, 2015 Ericsson AB
-- All rights reserved.
--
-- *****************************************************************

ERICSSON-ROUTER-MEDIA-GATEWAY-CAP DEFINITIONS ::= BEGIN

IMPORTS
        MODULE-IDENTITY
                FROM SNMPv2-SMI
        AGENT-CAPABILITIES
                FROM SNMPv2-CONF
        eriRouterCapabilities
                FROM ERICSSON-ROUTER-SMI;
 
eriRouterMediaGatewayCap MODULE-IDENTITY
        LAST-UPDATED   "201501141800Z" -- Jan 14, 2015
        ORGANIZATION   "Ericsson Inc."
        CONTACT-INFO
            "       Ericsson Inc.
                    100 Headquarters Drive
                    San Jose, CA 95134
                    USA

             Phone: +1 408 750 5000
               Fax: +1 408 750 5599
            "

        DESCRIPTION
                "The Agent Capabilities of the MEDIA GATEWAY MIB
                 (ERICSSON-ROUTER-MEDIA-GATEWAY-MIB).

                If this MIB implementation is platform-dependent,
                the PRODUCT-RELEASE clause contains Ericsson SEOS version and
                at least one of the following Ericsson product families:
                    [SE]  SmartEdge Multi-service Edge Router (MSER) family
                    [SM]  SM family of Metro Ethernet Service Transport platforms
                    [SSR] Smart Service Router (SSR) family"

        REVISION       "201501141800Z" -- Jan 14, 2015
        DESCRIPTION
                "Updated RBN/rbn/Rbn as ERICSSON-ROUTER/eriRouter/EriRouter
                 to migrate RBN MIB to ERICSSON MIB."

        REVISION       "201106150000Z" -- Jun 15, 2011
        DESCRIPTION
                "Update DESCRIPTION clause of MODULE-IDENTITY
                 and PRODUCT-RELEASE clause of AGENT-CAPABILITIES."
        
        REVISION       "200910150000Z" -- Oct 15, 2009
        DESCRIPTION
                "Initial version"
        ::= { eriRouterCapabilities 93}

eriRouterMediaGatewayCap1 AGENT-CAPABILITIES
        PRODUCT-RELEASE "SEOS 6.3 [SE]"
        STATUS          current
        DESCRIPTION     "ERICSSON-ROUTER-MEDIA-GATEWAY-MIB capabilities"
        SUPPORTS        ERICSSON-ROUTER-MEDIA-GATEWAY-MIB
        INCLUDES {
                    eriRouterMGNotifyObjectGroup,
                    eriRouterMGLinkNotifyGroup
                 }
        ::= { eriRouterMediaGatewayCap 1 }

END
