-- %DNP% $Id: RBN-IEEE8021-CFM-CAP.my,v 1.1.8.1.2.4 2011/06/15 18:19:45 danielhe Exp $
-- %DNP% $Source: /cvsroot/pkt/sw/se/xc/bsd/config/snmp/mibs/Attic/RBN-IEEE8021-CFM-CAP.my,v $
-- *****************************************************************
-- RBN-IEEE8021-CFM-CAP: IEEE8021-CFM-MIB agent Capabilities
--
-- Copyright (c) 2008, 2011 Ericsson AB.
-- All rights reserved.
--
-- *****************************************************************

RBN-IEEE8021-CFM-CAP DEFINITIONS ::= BEGIN

IMPORTS
        MODULE-IDENTITY
                FROM SNMPv2-SMI
        AGENT-CAPABILITIES
                FROM SNMPv2-CONF
        rbnCapabilities
                FROM RBN-SMI;
 
rbnIeee8021CfmCap MODULE-IDENTITY
        LAST-UPDATED    "201106150000Z" -- Jun 15, 2011
        ORGANIZATION    "Ericsson AB."
        CONTACT-INFO
                "       Ericsson AB.

                Postal: 100 Headquarters Dr
                        San Jose, CA  95134
                        USA

                 Phone: +1 408 750 5000
                   Fax: +1 408 750 5599
                "
        DESCRIPTION
                "The Agent Capabilities of the IEEE8021-CFM-MIB.

                If this MIB implementation is platform-dependent,
                the PRODUCT-RELEASE clause contains Ericsson SEOS version and
                at least one of the following Ericsson product families:
                    [SE]  SmartEdge Multi-service Edge Router (MSER) family
                    [SM]  SM family of Metro Ethernet Service Transport platforms
                    [SSR] Smart Service Router (SSR) family"

        REVISION        "201106150000Z" -- Jun 15, 2011
        DESCRIPTION
            "Update DESCRIPTION clause of MODULE-IDENTITY
            and PRODUCT-RELEASE clause of AGENT-CAPABILITIES."
        
        REVISION        "201101191800Z" -- Jan 19, 2011
        DESCRIPTION
                "Update CONTACT-INFO & ORGANIZATION. "

        REVISION        "200812010000Z" -- Dec 1, 2008
        DESCRIPTION
                "Initial version"
        ::= { rbnCapabilities 79 }

rbnIeee8021CfmCap1 AGENT-CAPABILITIES
    PRODUCT-RELEASE "SEOS 6.1.4.X [SE]; SEOS 6.3.X [SM]"
    STATUS          current
    DESCRIPTION     "IEEE8021-CFM-MIB capabilities"
    SUPPORTS        IEEE8021-CFM-MIB
    INCLUDES {
        dot1agCfmMdGroup,
        dot1agCfmMaGroup,
        dot1agCfmMepGroup,
        dot1agCfmMepDbGroup,
        dot1agCfmNotificationsGroup
    }
    -- *** dot1agCfmMdGroup ***
    -- dot1agCfmMd(5)
    VARIATION   dot1agCfmMdTableNextIndex
    ACCESS      not-implemented
    DESCRIPTION
        "Object is not supported."

    -- dot1agCfmMd::dot1agCfmMdTable(2)
    VARIATION   dot1agCfmMdFormat
    ACCESS      read-only
    DESCRIPTION
        "Create access is not allowed."

    VARIATION   dot1agCfmMdName
    ACCESS      read-only
    DESCRIPTION
        "Create access is not allowed."

    VARIATION   dot1agCfmMdMdLevel
    ACCESS      read-only
    DESCRIPTION
        "Create access is not allowed."

    VARIATION   dot1agCfmMdMhfCreation
    ACCESS      read-only
    DESCRIPTION
        "Create access is not allowed."

    VARIATION   dot1agCfmMdMhfIdPermission
    ACCESS      read-only
    DESCRIPTION
        "Create access is not allowed."
    
    VARIATION   dot1agCfmMdMaNextIndex
    ACCESS      not-implemented
    DESCRIPTION
        "Object is not supported."

    VARIATION   dot1agCfmMdRowStatus
    SYNTAX      INTEGER { active(1) }
    ACCESS      read-only
    DESCRIPTION
        "Create access is not allowed. Only 'active' status is supported."

    -- *** dot1agCfmMaGroup ***
    -- dot1agCfmMa(6)
    -- dot1agCfmMa::dot1agCfmMaNetTable(1)
    VARIATION   dot1agCfmMaNetFormat
    ACCESS      read-only
    DESCRIPTION
        "Create access is not allowed."
   
    VARIATION   dot1agCfmMaNetName
    ACCESS      read-only
    DESCRIPTION
        "Create access is not allowed."
   
    VARIATION   dot1agCfmMaNetCcmInterval
    ACCESS      read-only
    DESCRIPTION
        "Create access is not allowed."
   
    VARIATION   dot1agCfmMaNetRowStatus
    SYNTAX      INTEGER { active(1) }
    ACCESS      read-only
    DESCRIPTION
        "Create access is not allowed. Only 'active' status is supported"

    -- dot1agCfmMa::dot1agCfmMaCompTable(2)
    VARIATION   dot1agCfmMaCompPrimaryVlanId
    ACCESS      not-implemented
    DESCRIPTION
        "Object is not supported."
        
    VARIATION   dot1agCfmMaCompMhfCreation
    ACCESS      not-implemented
    DESCRIPTION
        "Object is not supported."
       
    VARIATION   dot1agCfmMaCompIdPermission
    ACCESS      not-implemented
    DESCRIPTION
        "Object is not supported."
       
    VARIATION   dot1agCfmMaCompNumberOfVids
    ACCESS      not-implemented
    DESCRIPTION
        "Object is not supported."
       
    VARIATION   dot1agCfmMaCompRowStatus
    ACCESS      not-implemented
    DESCRIPTION
        "Object is not supported."
   
    -- dot1agCfmMa::dot1agCfmMaMepListTable(3)     
    VARIATION   dot1agCfmMaMepListRowStatus
    ACCESS      not-implemented
    DESCRIPTION
        "Object is not supported."
  
    -- *** dot1agCfmMepGroup ***
    --dot1agCfmMepTable(1)
    VARIATION   dot1agCfmMepIfIndex
    ACCESS      read-only
    DESCRIPTION
        "Create access is not allowed."
  
    VARIATION   dot1agCfmMepDirection
    ACCESS      read-only
    DESCRIPTION
        "Create access is not allowed."
  
    VARIATION   dot1agCfmMepPrimaryVid
    ACCESS      read-only
    DESCRIPTION
        "Create access is not allowed."
  
    VARIATION   dot1agCfmMepActive
    ACCESS      read-only
    DESCRIPTION
        "Create access is not allowed."
  
    VARIATION   dot1agCfmMepCciEnabled
    ACCESS      read-only
    DESCRIPTION
        "Create access is not allowed."
  
    VARIATION   dot1agCfmMepCcmLtmPriority
    ACCESS      read-only
    DESCRIPTION
        "Create access is not allowed."
  
    VARIATION   dot1agCfmMepLowPrDef
    ACCESS      read-only
    DESCRIPTION
        "Create access is not allowed."
  
    VARIATION   dot1agCfmMepFngAlarmTime
    ACCESS      read-only
    DESCRIPTION
        "Create access is not allowed."
  
    VARIATION   dot1agCfmMepFngResetTime
    ACCESS      read-only
    DESCRIPTION
        "Create access is not allowed."
  
    VARIATION   dot1agCfmMepTransmitLbmStatus
    ACCESS      read-only
    DESCRIPTION
        "Create access is not allowed."
  
    VARIATION   dot1agCfmMepTransmitLbmDestMacAddress
    ACCESS     not-implemented 
    DESCRIPTION
        "This object is not supported."
  
    VARIATION   dot1agCfmMepTransmitLbmDestMepId
    ACCESS      not-implemented
    DESCRIPTION
        "This object is not supported."
  
    VARIATION   dot1agCfmMepTransmitLbmDestIsMepId
    ACCESS      read-only
    DESCRIPTION
        "Create access is not allowed."
  
    VARIATION   dot1agCfmMepTransmitLbmMessages
    ACCESS      read-only
    DESCRIPTION
        "Create access is not allowed."
  
    VARIATION   dot1agCfmMepTransmitLbmDataTlv
    ACCESS      read-only
    DESCRIPTION
        "Create access is not allowed."
  
    VARIATION   dot1agCfmMepTransmitLbmVlanPriority
    ACCESS      read-only
    DESCRIPTION
        "Create access is not allowed."
  
    VARIATION   dot1agCfmMepTransmitLbmVlanDropEnable
    ACCESS      read-only
    DESCRIPTION
        "Create access is not allowed."

    VARIATION   dot1agCfmMepTransmitLbmResultOK
    ACCESS      not-implemented
    DESCRIPTION
        "This object is not supported. "
  
    VARIATION   dot1agCfmMepTransmitLtmFlags
    ACCESS      read-only
    DESCRIPTION
        "Create access is not allowed."
  
    VARIATION   dot1agCfmMepTransmitLtmTargetMacAddress
    ACCESS      not-implemented
    DESCRIPTION
        "This object is not supported."
  
    VARIATION   dot1agCfmMepTransmitLtmTargetMepId
    ACCESS      not-implemented
    DESCRIPTION
        "This object is not supported."
  
    VARIATION   dot1agCfmMepTransmitLtmTargetIsMepId
    ACCESS      read-only
    DESCRIPTION
        "Create access is not allowed."
  
    VARIATION   dot1agCfmMepTransmitLtmTtl
    ACCESS      read-only
    DESCRIPTION
        "Create access is not allowed."

    VARIATION   dot1agCfmMepTransmitLtmResult
    ACCESS      not-implemented
    DESCRIPTION
        "This object is not supported."
  
    VARIATION   dot1agCfmMepTransmitLtmEgressIdentifier
    ACCESS      read-only
    DESCRIPTION
        "Create access is not allowed."
  
    VARIATION   dot1agCfmMepRowStatus
    SYNTAX      INTEGER { active(1) }
    ACCESS      read-only
    DESCRIPTION
        "Create access is not allowed. Only 'active' status is supported."

    ::= { rbnIeee8021CfmCap 1 }
END
