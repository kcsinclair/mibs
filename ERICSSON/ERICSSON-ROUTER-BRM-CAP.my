-- *****************************************************************
-- ERICSSON-ROUTER-TWAMP-CAP
--
-- Copyright (c) 2016 Ericsson AB.
-- All rights reserved.
--
-- *****************************************************************

 ERICSSON-ROUTER-BRM-CAP DEFINITIONS ::= BEGIN

     IMPORTS
         MODULE-IDENTITY, OBJECT-TYPE, OBJECT-IDENTITY,
         NOTIFICATION-TYPE, mib-2, Counter32,
         Integer32, TimeTicks                   FROM SNMPv2-SMI

         TEXTUAL-CONVENTION, DisplayString      FROM SNMPv2-TC

         MODULE-COMPLIANCE, OBJECT-GROUP,
         NOTIFICATION-GROUP                     FROM SNMPv2-CONF;

 eriRouterBRMMibCap MODULE-IDENTITY
     LAST-UPDATED "201609090000Z"  -- 9 September, 2016
     ORGANIZATION "Ericsson AB"
     CONTACT-INFO
         "
          Leopold Yang
          Email: leopold.yang@ericsson.com

         "
     DESCRIPTION
        "The Agent Capabilities of the BRM MIB
         (ERICSSON-ROUTER-BRM-MIB)."

     ::= { eriRouterCapabilities 116 }

 eriRouterBRMMibCap1 AGENT-CAPABILITIES
     PRODUCT-RELEASE "Spitfire 1.1.x [SP]"
     STATUS          current
     DESCRIPTION     "ERICSSON-ROUTER-BRM-MIB capabilities"
     SUPPORTS        ERICSSON-ROUTER-BRM-MIB
     INCLUDES {
        eriRouterBRMMib
     }

     ::= { eriRouterBRMMibCap 1 }

 END
