-- *****************************************************************
-- ERICSSON-ROUTER-TWAMP-CAP
--
-- Copyright (c) 2016 Ericsson AB.
-- All rights reserved.
--
-- *****************************************************************

 ERICSSON-ROUTER-TWAMP-CAP DEFINITIONS ::= BEGIN

     IMPORTS
         MODULE-IDENTITY, OBJECT-TYPE, OBJECT-IDENTITY,
         NOTIFICATION-TYPE, mib-2, Counter32,
         Integer32, TimeTicks                   FROM SNMPv2-SMI

         TEXTUAL-CONVENTION, DisplayString      FROM SNMPv2-TC

         MODULE-COMPLIANCE, OBJECT-GROUP,
         NOTIFICATION-GROUP                     FROM SNMPv2-CONF;

 eriRouterTwampMibCap MODULE-IDENTITY
     LAST-UPDATED "201606060000Z"  -- 6 June, 2016
     ORGANIZATION "Ericsson AB"
     CONTACT-INFO
         "
          Yan Wang J
          Email: yan.j.wang@ericsson.com

          Guangpeng Li
          Email: guangpeng.li@ericsson.com

          Chengxing Zhou
          Email: chengxing.zhou@ericsson.com
         "
     DESCRIPTION
        "The Agent Capabilities of the twamp MIB
         (ERICSSON-ROUTER-TWAMP-MIB)."

     ::= { eriRouterCapabilities 113 }

 eriRouterTwampMibCap1 AGENT-CAPABILITIES
     PRODUCT-RELEASE "Spitfire 1.1.x [SP]"
     STATUS          current
     DESCRIPTION     "ERICSSON-ROUTER-TWAMP-MIB capabilities"
     SUPPORTS        ERICSSON-ROUTER-TWAMP-MIB
     INCLUDES {
        eriRouterTwampMib
     }

     ::= { eriRouterTwampMibCap 1 }

 END
