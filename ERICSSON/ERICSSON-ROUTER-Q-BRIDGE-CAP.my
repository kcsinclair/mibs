-- %DNP% $Id: ERICSSON-ROUTER-Q-BRIDGE-CAP.my,v 1.1.2.1.60.3 2011/06/15 18:19:46 danielhe Exp $
-- %DNP% $Source: /cvsroot/pkt/sw/se/xc/bsd/config/snmp/mibs/Attic/ERICSSON-ROUTER-Q-BRIDGE-CAP.my,v $
-- *****************************************************************
-- ERICSSON-ROUTER-Q-BRIDGE-CAP.my:	Q-BRIDGE-MIB Agent Capabilities
--
-- Copyright (c) 2007, 2008, 2011, 2015 Ericsson AB.
-- All rights reserved.
-- 
-- *****************************************************************

ERICSSON-ROUTER-Q-BRIDGE-CAP DEFINITIONS ::= BEGIN

IMPORTS
	MODULE-IDENTITY
		FROM SNMPv2-SMI
	AGENT-CAPABILITIES
		FROM SNMPv2-CONF
	eriRouterCapabilities
		FROM ERICSSON-ROUTER-SMI;

eriRouterQBridgeCap MODULE-IDENTITY
        LAST-UPDATED    "201501141800Z" -- Jan 14, 2015
        ORGANIZATION    "Ericsson AB."
        CONTACT-INFO
                "       Ericsson AB.

                Postal: 100 Headquarters Dr
                        San Jose, CA  95134
                        USA

                 Phone: +1 408 750 5000
                   Fax: +1 408 750 5599
                "
	DESCRIPTION
		"The Agent Capabilities of the Q-BRIDGE-MIB (RFC 4188).

                If this MIB implementation is platform-dependent,
                the PRODUCT-RELEASE clause contains Ericsson SEOS version and
                at least one of the following Ericsson product families:
                    [SE]  SmartEdge Multi-service Edge Router (MSER) family
                    [SM]  SM family of Metro Ethernet Service Transport platforms
                    [SSR] Smart Service Router (SSR) family"

        REVISION        "201501141800Z" -- Jan 14, 2015
        DESCRIPTION
                "Updated RBN/rbn/Rbn as ERICSSON-ROUTER/eriRouter/EriRouter
                 to migrate RBN MIB to ERICSSON MIB."

        REVISION        "201106150000Z" -- Jun 15, 2011
        DESCRIPTION
                "Update DESCRIPTION clause of MODULE-IDENTITY
                 and PRODUCT-RELEASE clause of AGENT-CAPABILITIES."

        REVISION        "201101191800Z" -- Jan 19, 2011
        DESCRIPTION
                "Update CONTACT-INFO & ORGANIZATION. "

	REVISION	"200802011200Z" -- Feb 1, 2008
	DESCRIPTION
		"Initial version"
	::= { eriRouterCapabilities 78 }

eriRouterQBridgeCap1 AGENT-CAPABILITIES
	PRODUCT-RELEASE	"SEOS 6.1.4 [SE]; SEOS 6.3.X [SM]"
	STATUS		current
	DESCRIPTION	"Q-BRIDGE-MIB capabilities"
	SUPPORTS	Q-BRIDGE-MIB
	INCLUDES {
                  qBridgeBaseGroup
		 }

	::= { eriRouterQBridgeCap 1 }

END
