-- $Id:$
-- $Source:$
-- *****************************************************************
-- ERICSSON-ROUTER-ISSU-TC-MIB.my
--
-- Copyright (c) 2016 Ericsson AB.
-- All rights reserved.
--
-- *****************************************************************

ERICSSON-ROUTER-ISSU-TC-MIB DEFINITIONS ::= BEGIN

IMPORTS
   MODULE-IDENTITY,
    Integer32, Unsigned32
            FROM SNMPv2-SMI
   TEXTUAL-CONVENTION
       FROM SNMPv2-TC;          -- [RFC2579]


eriRouterIssuTC MODULE-IDENTITY
    LAST-UPDATED    "201512090000Z" -- Dec 9, 2015
    ORGANIZATION    "Ericsson AB."
    CONTACT-INFO
            "       Ericsson AB.

            Postal: 100 Headquarters Dr
                    San Jose, CA  95134
                    USA

             Phone: +1 408 750 5000
               Fax: +1 408 750 5599
            "
    DESCRIPTION
        "Defines common textual conventions used in ERICSSON-ROUTER-ISSU mib
        modules."

    REVISION      "201512090000Z" -- Dec 9, 2015
    DESCRIPTION
        "Initial version."
    ::= { eriRouterModules 55 }

EriRouterIssuReason ::= TEXTUAL-CONVENTION
    STATUS current
    DESCRIPTION
        "Reason for the current action."
    SYNTAX      INTEGER {
                     unknown(0),
                     retryAction(1),
                     extendTime(2),
                     timeout(3),
                     completed(4),
                     error(5),
                     systemError(6),
                     internalInfo(7),
                     issuAbort(8),
                     userValidate(9),
                     userPrepare(10),
                     userRpswUpg(11),
                     forwardingUpg(12),
                     userCommit(13),
                     isolate(14),
                     ignore(15),
                     timeoutWarning(16)
             }

EriRouterIssuAction ::= TEXTUAL-CONVENTION
    STATUS current
    DESCRIPTION
        "Action in order to perform the ISSU."
    SYNTAX      INTEGER {
                     unknown(0),
                     idle(1),
                     configLock(2),
                     upgradeFailure(3),
                     manualIntervention(4),
                     validation(5),
                     fixConfigLock(6),
                     preparationWait(7),
                     fixValidation(8),
                     preparationStart(9),
                     fixPrepStart(10),
                     setupProcesses(11),
                     fixSetupProcess(12),
                     reloadStandby(13),
                     fixReloadStandby(14),
                     preparationEnd(15),
                     fixPreparationEnd(16),
                     rpswUpgWait(17),
                     prepareRpso(18),
                     fixPrepareRpso(19),
                     rpsoStart(20),
                     fixRpsoStart(21),
                     rpsoEnd(22),
                     fixRpsoEnd(23),
                     fwdUpgWait(24),
                     prepareFwdUp(25),
                     fixPrepareFwdUpg(26),
                     syncWait(27),
                     fixSyncWait(28),
                     synStart(29),
                     fixSyncStart(30),
                     pfeUpgStart(31),
                     fixPfeUpgStart(32),
                     pfeSwitch(33),
                     fixPfeSwitch(34),
                     syncEnd(35),
                     fixSyncEnd(36),
                     fwdUpgEnd(37),
                     fixFwdUpgEnd(38),
                     commitWait(39),
                     commitChanges(40),
                     fixCommitChanges(41),
                     unlockConfig(42),
                     fixUnlockConfig(43)

             }

EriRouterIssuStage ::= TEXTUAL-CONVENTION
    STATUS current
    DESCRIPTION
        "Stage of the system when performing ISSU."
    SYNTAX      INTEGER {
                     unknown(0),
                     idle(1),
                     failed(2),
                     validate(3),
                     prepare(4),
                     v2Control(5),
                     v2Forward(6),
                     commit(7)
             }
END
