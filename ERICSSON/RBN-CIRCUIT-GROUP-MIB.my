-- %DNP% $Id: RBN-CIRCUIT-GROUP-MIB.my,v 1.1.6.2.4.2 2011/02/22 17:26:16 thatcher Exp $
-- %DNP% $Source: /cvsroot/pkt/sw/se/xc/bsd/config/snmp/mibs/Attic/RBN-CIRCUIT-GROUP-MIB.my,v $
-- *****************************************************************
-- RBN-CIRCUIT-GROUP-MIB
--
-- Copyright (c) 2007-2008, 2011 Ericsson AB
-- All rights reserved.
--
-- *****************************************************************

RBN-CIRCUIT-GROUP-MIB DEFINITIONS ::= BEGIN

IMPORTS

    Counter64,
    MODULE-IDENTITY,
    OBJECT-TYPE,
    Unsigned32
            FROM SNMPv2-SMI

    MODULE-COMPLIANCE,
    OBJECT-GROUP
            FROM SNMPv2-CONF

    SnmpAdminString
            FROM SNMP-FRAMEWORK-MIB

    RbnQosClassId, RbnQosPolicyType
            FROM RBN-QOS-MIB

    rbnMgmt
            FROM RBN-SMI;


rbnCircuitGroupMib MODULE-IDENTITY
    LAST-UPDATED    "201101191800Z" -- Jan 19, 2011
    ORGANIZATION    "Ericsson AB."
    CONTACT-INFO
            "       Ericsson AB.

            Postal: 100 Headquarters Dr
                    San Jose, CA  95134
                    USA

             Phone: +1 408 750 5000
               Fax: +1 408 750 5599
            "
    DESCRIPTION
        "Defines objects which may be used to monitor circuit groups
        policies"

    REVISION        "201101191800Z" -- Jan 19, 2011
    DESCRIPTION
        "Update CONTACT-INFO & ORGANIZATION. "

    REVISION        "200807300000Z" -- July, 30, 2008
    DESCRIPTION
        "rbnCctGrpName object's maximum length has been increased from 39 to 80"
    
    REVISION      "200707250000Z" -- July 25, 2007
    DESCRIPTION
        "Initial version."
    ::= { rbnMgmt 43 }

rbnCircuitGroupObjects
        OBJECT IDENTIFIER ::= { rbnCircuitGroupMib 1 }

rbnCircuitGroupConformance
        OBJECT IDENTIFIER ::= { rbnCircuitGroupMib 2 }

--
-- Circuit Groups
--
rbnCircuitGroupStatsTable OBJECT-TYPE
    SYNTAX      SEQUENCE OF RbnCircuitGroupStatsEntry
    MAX-ACCESS  not-accessible
    STATUS      current
    DESCRIPTION
        "A table containing various Tx, Rx, and drop counters
        for each circuit group."
    ::= { rbnCircuitGroupObjects 1 }
    
rbnCircuitGroupStatsEntry OBJECT-TYPE
    SYNTAX      RbnCircuitGroupStatsEntry
    MAX-ACCESS  not-accessible
    STATUS      current
    DESCRIPTION
        "A conceptual row in the rbnCircuitGroupStatsTable. Each row
        contains a set of packet and octet counters for a circuit group."
    INDEX       { rbnCctGrpName }
    ::= { rbnCircuitGroupStatsTable 1 }
    
RbnCircuitGroupStatsEntry    ::= SEQUENCE {
    rbnCctGrpName                       SnmpAdminString,
    rbnCctGrpTxOctets                   Counter64,
    rbnCctGrpTxPackets                  Counter64,
    rbnCctGrpTxMulticastOctets          Counter64,
    rbnCctGrpTxMulticastPackets         Counter64,
    rbnCctGrpRxOctets                   Counter64,
    rbnCctGrpRxPackets                  Counter64,
    rbnCctGrpRxMulticastOctets          Counter64,
    rbnCctGrpRxMulticastPackets         Counter64,
    rbnCctGrpAdjDroppedOctets           Counter64,
    rbnCctGrpAdjDroppedPackets          Counter64,
    rbnCctGrpDownDroppedOctets          Counter64,
    rbnCctGrpDownDroppedPackets         Counter64,
    rbnCctGrpUnreachDroppedOctets       Counter64,
    rbnCctGrpUnreachDroppedPackets      Counter64,
    rbnCctGrpUnknownEncapsOctets        Counter64,
    rbnCctGrpUnknownEncapsPackets       Counter64
}
 
rbnCctGrpName   OBJECT-TYPE
    SYNTAX      SnmpAdminString (SIZE(1..113))
    MAX-ACCESS  not-accessible
    STATUS      current
    DESCRIPTION
        "The name of the hierarchical group."
    ::= { rbnCircuitGroupStatsEntry  1 }

rbnCctGrpTxOctets   OBJECT-TYPE
    SYNTAX      Counter64
    MAX-ACCESS  read-only
    STATUS      current
    DESCRIPTION
        "The number of octets transmitted by the group including
         its children."
    ::= { rbnCircuitGroupStatsEntry  2 }
   
rbnCctGrpTxPackets   OBJECT-TYPE
    SYNTAX      Counter64
    MAX-ACCESS  read-only
    STATUS      current
    DESCRIPTION
        "The number of packets transmitted by the group including
         its children."
    ::= { rbnCircuitGroupStatsEntry  3 }
   
rbnCctGrpTxMulticastOctets   OBJECT-TYPE
    SYNTAX      Counter64
    MAX-ACCESS  read-only
    STATUS      current
    DESCRIPTION
        "The number of multicast octets transmitted by the group including
         its children."
    ::= { rbnCircuitGroupStatsEntry  4 }
   
rbnCctGrpTxMulticastPackets   OBJECT-TYPE
    SYNTAX      Counter64
    MAX-ACCESS  read-only
    STATUS      current
    DESCRIPTION
        "The number of multicast packets transmitted by the group including
         its children."
    ::= { rbnCircuitGroupStatsEntry  5 }
   

rbnCctGrpRxOctets   OBJECT-TYPE
    SYNTAX      Counter64
    MAX-ACCESS  read-only
    STATUS      current
    DESCRIPTION
        "The number of octets received by the group including
         its children."
    ::= { rbnCircuitGroupStatsEntry  6 }
   
rbnCctGrpRxPackets   OBJECT-TYPE
    SYNTAX      Counter64
    MAX-ACCESS  read-only
    STATUS      current
    DESCRIPTION
        "The number of packets received by the group including
         its children."
    ::= { rbnCircuitGroupStatsEntry  7 }
   
rbnCctGrpRxMulticastOctets   OBJECT-TYPE
    SYNTAX      Counter64
    MAX-ACCESS  read-only
    STATUS      current
    DESCRIPTION
        "The number of multicast octets received by the group including
         its children."
    ::= { rbnCircuitGroupStatsEntry  8 }
   
rbnCctGrpRxMulticastPackets   OBJECT-TYPE
    SYNTAX      Counter64
    MAX-ACCESS  read-only
    STATUS      current
    DESCRIPTION
        "The number of multicast packets received by the group including
         its children."
    ::= { rbnCircuitGroupStatsEntry  9 }

rbnCctGrpAdjDroppedOctets   OBJECT-TYPE
    SYNTAX      Counter64
    MAX-ACCESS  read-only
    STATUS      current
    DESCRIPTION
        "The number of adjacency octets dropped."
    ::= { rbnCircuitGroupStatsEntry 10 }
   
rbnCctGrpAdjDroppedPackets   OBJECT-TYPE
    SYNTAX      Counter64
    MAX-ACCESS  read-only
    STATUS      current
    DESCRIPTION
        "The number of adjacency packets dropped."
    ::= { rbnCircuitGroupStatsEntry 11 }
   
rbnCctGrpDownDroppedOctets   OBJECT-TYPE
    SYNTAX      Counter64
    MAX-ACCESS  read-only
    STATUS      current
    DESCRIPTION
        "The number of down octets dropped."
    ::= { rbnCircuitGroupStatsEntry 12 }
   
rbnCctGrpDownDroppedPackets   OBJECT-TYPE
    SYNTAX      Counter64
    MAX-ACCESS  read-only
    STATUS      current
    DESCRIPTION
        "The number of down packets dropped."
    ::= { rbnCircuitGroupStatsEntry 13 }
   
rbnCctGrpUnreachDroppedOctets   OBJECT-TYPE
    SYNTAX      Counter64
    MAX-ACCESS  read-only
    STATUS      current
    DESCRIPTION
        "The number of unreachable octets dropped."
    ::= { rbnCircuitGroupStatsEntry 14 }
   
rbnCctGrpUnreachDroppedPackets   OBJECT-TYPE
    SYNTAX      Counter64
    MAX-ACCESS  read-only
    STATUS      current
    DESCRIPTION
        "The number of unreachable packets dropped."
    ::= { rbnCircuitGroupStatsEntry 15 }
   
rbnCctGrpUnknownEncapsOctets   OBJECT-TYPE
    SYNTAX      Counter64
    MAX-ACCESS  read-only
    STATUS      current
    DESCRIPTION
        "The number octets dropped due to unknown encapsulation."
    ::= { rbnCircuitGroupStatsEntry 16 }
   
rbnCctGrpUnknownEncapsPackets   OBJECT-TYPE
    SYNTAX      Counter64
    MAX-ACCESS  read-only
    STATUS      current
    DESCRIPTION
        "The number of packets dropped due to unknown encapsulation."
    ::= { rbnCircuitGroupStatsEntry 17 }
   
--
--
--
rbnCircuitGroupQTable OBJECT-TYPE
    SYNTAX      SEQUENCE OF RbnCircuitGroupQEntry
    MAX-ACCESS  not-accessible
    STATUS      current
    DESCRIPTION
        "A table containing various counters for each transmit queue
        assigned to a circuit group."
    ::= { rbnCircuitGroupObjects 2 }
    
rbnCircuitGroupQEntry OBJECT-TYPE
    SYNTAX      RbnCircuitGroupQEntry
    MAX-ACCESS  not-accessible
    STATUS      current
    DESCRIPTION
        "A conceptual row in the rbnCircuitGroupQueueTable. Each row
        contains tx and drop counters for each transmit queue assigned
        to a circuit group."
    INDEX   { rbnCctGrpName, rbnCctGrpQueueId }
    ::= { rbnCircuitGroupQTable 1 }
    
RbnCircuitGroupQEntry ::= SEQUENCE
{
    rbnCctGrpQueueId                Unsigned32,
    rbnCctGrpQTxOctets              Counter64,
    rbnCctGrpQTxPackets             Counter64,
    rbnCctGrpQWredDroppedOctets     Counter64,
    rbnCctGrpQWredDroppedPkts       Counter64,
    rbnCctGrpQTailDroppedOctets     Counter64,
    rbnCctGrpQTailDroppedPkts       Counter64
}

rbnCctGrpQueueId OBJECT-TYPE
    SYNTAX      Unsigned32 (0..7)
    MAX-ACCESS  not-accessible
    STATUS      current
    DESCRIPTION
        "A unique identifier for a transmit queue used by the circuit."
    ::= { rbnCircuitGroupQEntry 1 }

rbnCctGrpQTxOctets OBJECT-TYPE
    SYNTAX      Counter64
    MAX-ACCESS  read-only
    STATUS      current
    DESCRIPTION
           "The number of octets transmitted out of this queue.

            Discontinuities in the value of this counter can occur at
            re-initialization of the management system."
    ::= { rbnCircuitGroupQEntry 2 }

rbnCctGrpQTxPackets OBJECT-TYPE
    SYNTAX      Counter64
    MAX-ACCESS  read-only
    STATUS      current
    DESCRIPTION
           "The number of packets transmitted out of this queue.

            Discontinuities in the value of this counter can occur at
            re-initialization of the management system."
    ::= { rbnCircuitGroupQEntry 3 }

rbnCctGrpQWredDroppedOctets OBJECT-TYPE
    SYNTAX      Counter64
    MAX-ACCESS  read-only
    STATUS      current
    DESCRIPTION
           "The number of octets dropped due to the application of a
            weighted random early detection algorithm.

            Discontinuities in the value of this counter can occur at
            re-initialization of the management system."
    ::= { rbnCircuitGroupQEntry 4 }

rbnCctGrpQWredDroppedPkts OBJECT-TYPE
    SYNTAX      Counter64
    MAX-ACCESS  read-only
    STATUS      current
    DESCRIPTION
           "The number of packets dropped due to the application of a
            weighted random early detection algorithm.

            Discontinuities in the value of this counter can occur at
            re-initialization of the management system."
    ::= { rbnCircuitGroupQEntry 5 }

rbnCctGrpQTailDroppedOctets OBJECT-TYPE
    SYNTAX      Counter64
    MAX-ACCESS  read-only
    STATUS      current
    DESCRIPTION
           "The number of octets dropped when the total number of packets
            in this queue was greater than the maximum threshold.

            Discontinuities in the value of this counter can occur at
            re-initialization of the management system."
    ::= { rbnCircuitGroupQEntry 6 }

rbnCctGrpQTailDroppedPkts OBJECT-TYPE
    SYNTAX      Counter64
    MAX-ACCESS  read-only
    STATUS      current
    DESCRIPTION
           "The number of packets dropped when the total number of
            packets in this queue was greater than the maximum threshold.

            Discontinuities in the value of this counter can occur at
            re-initialization of the management system."
    ::= { rbnCircuitGroupQEntry 7 }

--
--
--
rbnCctGrpRLPolicyStatsTable OBJECT-TYPE
    SYNTAX      SEQUENCE OF RbnCctGrpRLPolicyStatsEntry
    MAX-ACCESS  not-accessible
    STATUS      current
    DESCRIPTION
           "A table of counters for rate limit policies applied to 
           circuit groups."
    ::= { rbnCircuitGroupObjects 3 }

rbnCctGrpRLPolicyStatsEntry    OBJECT-TYPE
    SYNTAX      RbnCctGrpRLPolicyStatsEntry
    MAX-ACCESS  not-accessible
    STATUS      current
    DESCRIPTION
           "A conceptial row in the rbnCircuitGroupPolicyStatsTable. Each
           row contains counters for a rate limit policy applied to the 
           circuit group.  Note that each counter includes the sum of
           all the child circuits. "
    INDEX { rbnCctGrpName, rbnCctGrpRLPolicyType }
    ::=  { rbnCctGrpRLPolicyStatsTable 1 }
    
RbnCctGrpRLPolicyStatsEntry ::= SEQUENCE {
    rbnCctGrpRLPolicyType                   RbnQosPolicyType,
    rbnCctGrpRLPolicyName                   SnmpAdminString,
    rbnCctGrpRLPolicyConformOctets          Counter64,
    rbnCctGrpRLPolicyConformPkts            Counter64,
    rbnCctGrpRLPolicyExceedOctets           Counter64,
    rbnCctGrpRLPolicyExceedPkts             Counter64,
    rbnCctGrpRLPolicyExceedDroppedOctets    Counter64,
    rbnCctGrpRLPolicyExceedDroppedPkts      Counter64,
    rbnCctGrpRLPolicyViolateOctets          Counter64,
    rbnCctGrpRLPolicyViolatePkts            Counter64,
    rbnCctGrpRLPolicyViolateDroppedOctets   Counter64,
    rbnCctGrpRLPolicyViolateDroppedPkts     Counter64
}

rbnCctGrpRLPolicyType OBJECT-TYPE
    SYNTAX      RbnQosPolicyType
    MAX-ACCESS  not-accessible
    STATUS      current
    DESCRIPTION
       "The type of the rate-limit policy which is applied to the
        circuit group."
    ::= { rbnCctGrpRLPolicyStatsEntry 1 }

rbnCctGrpRLPolicyName OBJECT-TYPE
    SYNTAX      SnmpAdminString (SIZE(1..39))
    MAX-ACCESS  read-only
    STATUS      current
    DESCRIPTION
        "Name of the rate-limit policy."
    ::= { rbnCctGrpRLPolicyStatsEntry 2 }


rbnCctGrpRLPolicyConformOctets OBJECT-TYPE
    SYNTAX      Counter64
    MAX-ACCESS  read-only
    STATUS      current
    DESCRIPTION
           "The number of octets that conform to the rate limit set on
            the circuit group for which counters are enabled."
    ::= { rbnCctGrpRLPolicyStatsEntry 3 }

rbnCctGrpRLPolicyConformPkts OBJECT-TYPE
    SYNTAX      Counter64
    MAX-ACCESS  read-only
    STATUS      current
    DESCRIPTION
           "The number of packets that conform to the rate limit set on
            the circuit group for which counters are enabled."
    ::= { rbnCctGrpRLPolicyStatsEntry 4 }

rbnCctGrpRLPolicyExceedOctets OBJECT-TYPE
    SYNTAX      Counter64
    MAX-ACCESS  read-only
    STATUS      current
    DESCRIPTION
           "The number of octets that exceed the rate limit set on the
            interface for which class counters are enabled."
    ::= { rbnCctGrpRLPolicyStatsEntry 5 }

rbnCctGrpRLPolicyExceedPkts OBJECT-TYPE
    SYNTAX      Counter64
    MAX-ACCESS  read-only
    STATUS      current
    DESCRIPTION
           "The number of packets that exceed the rate limit set on the
            interface."
    ::= { rbnCctGrpRLPolicyStatsEntry 6 }

rbnCctGrpRLPolicyExceedDroppedOctets OBJECT-TYPE
    SYNTAX      Counter64
    MAX-ACCESS  read-only
    STATUS      current
    DESCRIPTION
           "The number of octets that were dropped due to the application
            of an exceed action on packets that exceed the rate limit set
            on the circuit group for which counters are enabled."
    ::= { rbnCctGrpRLPolicyStatsEntry 7 }

rbnCctGrpRLPolicyExceedDroppedPkts OBJECT-TYPE
    SYNTAX      Counter64
    MAX-ACCESS  read-only
    STATUS      current
    DESCRIPTION
           "The number of packets that were dropped due to the application
            of an exceed action on packets that exceed the rate limit set
            on the circuit group for which counters are enabled."
    ::= { rbnCctGrpRLPolicyStatsEntry 8 }

rbnCctGrpRLPolicyViolateOctets OBJECT-TYPE
    SYNTAX      Counter64
    MAX-ACCESS  read-only
    STATUS      current
    DESCRIPTION
           "The number of octets that violate the normal and maximum burst
            sizes on the circuit group for which counters are enabled."
    ::= { rbnCctGrpRLPolicyStatsEntry 9 }

rbnCctGrpRLPolicyViolatePkts OBJECT-TYPE
    SYNTAX      Counter64
    MAX-ACCESS  read-only
    STATUS      current
    DESCRIPTION
           "The number of packets that violate the normal and maximum burst
            sizes on the circuit group for which counters are enabled."
    ::= { rbnCctGrpRLPolicyStatsEntry 10 }

rbnCctGrpRLPolicyViolateDroppedOctets OBJECT-TYPE
    SYNTAX      Counter64
    MAX-ACCESS  read-only
    STATUS      current
    DESCRIPTION
           "The number of octets that were dropped due to the application
            of a violate action on packets that violate the normal and
            maximum burst sizes on the circuit group for which counters
            are enabled."
    ::= { rbnCctGrpRLPolicyStatsEntry 11 }

rbnCctGrpRLPolicyViolateDroppedPkts OBJECT-TYPE
    SYNTAX      Counter64
    MAX-ACCESS  read-only
    STATUS      current
    DESCRIPTION
           "The number of packets that were dropped due to the application
            of a violate action on packets that violate the normal and
            maximum burst sizes on the circuit group for which counters
            are enabled."
    ::= { rbnCctGrpRLPolicyStatsEntry 12 }

--
--
--
rbnCctGrpRLClassStatsTable OBJECT-TYPE
    SYNTAX      SEQUENCE OF RbnCctGrpRLClassStatsEntry
    MAX-ACCESS  not-accessible
    STATUS      current
    DESCRIPTION
           "A table of counters for rate limit policy classes applied to 
           circuit groups."
    ::= { rbnCircuitGroupObjects 4 }

rbnCctGrpRLClassStatsEntry    OBJECT-TYPE
    SYNTAX      RbnCctGrpRLClassStatsEntry
    MAX-ACCESS  not-accessible
    STATUS      current
    DESCRIPTION
           "A conceptial row in the rbnCctGrpRLClassStatsTable. Each
           row contains counters for a rate limit policy class applied 
           to the circuit group."
    INDEX { rbnCctGrpName, rbnCctGrpRLPolicyType, rbnCctGrpRLClassId }
    ::=  { rbnCctGrpRLClassStatsTable 1 }
    
RbnCctGrpRLClassStatsEntry ::= SEQUENCE {
    rbnCctGrpRLClassId                    RbnQosClassId,
    rbnCctGrpRLClassName                  SnmpAdminString,
    rbnCctGrpRLClassConformOctets         Counter64,
    rbnCctGrpRLClassConformPkts           Counter64,
    rbnCctGrpRLClassConformDroppedOctets  Counter64,
    rbnCctGrpRLClassConformDroppedPkts    Counter64,
    rbnCctGrpRLClassExceedOctets          Counter64,
    rbnCctGrpRLClassExceedPkts            Counter64,
    rbnCctGrpRLClassExceedDroppedOctets   Counter64,
    rbnCctGrpRLClassExceedDroppedPkts     Counter64,
    rbnCctGrpRLClassViolateOctets         Counter64,
    rbnCctGrpRLClassViolatePkts           Counter64,
    rbnCctGrpRLClassViolateDroppedOctets  Counter64,
    rbnCctGrpRLClassViolateDroppedPkts    Counter64
}

rbnCctGrpRLClassId OBJECT-TYPE
    SYNTAX      RbnQosClassId
    MAX-ACCESS  not-accessible
    STATUS      current
    DESCRIPTION
           "A value that uniquely identifies a class defined in the
            rate-limit policy access list."
    ::= { rbnCctGrpRLClassStatsEntry 1 }

rbnCctGrpRLClassName OBJECT-TYPE
    SYNTAX      SnmpAdminString (SIZE(1..39))
    MAX-ACCESS  read-only
    STATUS      current
    DESCRIPTION
           "Name of the class in the rate-limit policy access list."
    ::= { rbnCctGrpRLClassStatsEntry 2 }

rbnCctGrpRLClassConformOctets OBJECT-TYPE
    SYNTAX      Counter64
    MAX-ACCESS  read-only
    STATUS      current
    DESCRIPTION
           "The number of octets that conform to the policy class rate
            limit set on the circuit group."
    ::= { rbnCctGrpRLClassStatsEntry 3 }

rbnCctGrpRLClassConformPkts OBJECT-TYPE
    SYNTAX      Counter64
    MAX-ACCESS  read-only
    STATUS      current
    DESCRIPTION
           "The number of packets that conform to the policy class rate
            limit set on the circuit group."
    ::= { rbnCctGrpRLClassStatsEntry 4 }

rbnCctGrpRLClassConformDroppedOctets OBJECT-TYPE
    SYNTAX      Counter64
    MAX-ACCESS  read-only
    STATUS      current
    DESCRIPTION
           "The number of octets that were dropped due to the application
            of a conform action on packets that conform to the policy class
            rate limit set on the circuit group."
    ::= { rbnCctGrpRLClassStatsEntry 5 }

rbnCctGrpRLClassConformDroppedPkts OBJECT-TYPE
    SYNTAX      Counter64
    MAX-ACCESS  read-only
    STATUS      current
    DESCRIPTION
           "The number of packets that were dropped due to the application
            of a conform action on packets that conform to the policy class
            rate limit set on the circuit group."
    ::= { rbnCctGrpRLClassStatsEntry 6 }

rbnCctGrpRLClassExceedOctets OBJECT-TYPE
    SYNTAX      Counter64
    MAX-ACCESS  read-only
    STATUS      current
    DESCRIPTION
           "The number of octets that exceed the policy class rate limit
            set on the circuit group."
    ::= { rbnCctGrpRLClassStatsEntry 7 }

rbnCctGrpRLClassExceedPkts OBJECT-TYPE
    SYNTAX      Counter64
    MAX-ACCESS  read-only
    STATUS      current
    DESCRIPTION
           "The number of packets that exceed the policy class rate
            limit set on the circuit group."
    ::= { rbnCctGrpRLClassStatsEntry 8 }

rbnCctGrpRLClassExceedDroppedOctets OBJECT-TYPE
    SYNTAX      Counter64
    MAX-ACCESS  read-only
    STATUS      current
    DESCRIPTION
           "The number of octets that were dropped due to the application
            of an exceed action on packets that exceed the policy class
            rate limit set on the circuit group."
    ::= { rbnCctGrpRLClassStatsEntry 9 }

rbnCctGrpRLClassExceedDroppedPkts OBJECT-TYPE
    SYNTAX      Counter64
    MAX-ACCESS  read-only
    STATUS      current
    DESCRIPTION
           "The number of packets that were dropped due to the application
            of an exceed action on packets that exceed the policy class
            rate limit set on the circuit group."
    ::= { rbnCctGrpRLClassStatsEntry 10 }

rbnCctGrpRLClassViolateOctets OBJECT-TYPE
    SYNTAX      Counter64
    MAX-ACCESS  read-only
    STATUS      current
    DESCRIPTION
           "The number of octets that violate the normal and maximum burst
            sizes on the circuit group."
    ::= { rbnCctGrpRLClassStatsEntry 11 }

rbnCctGrpRLClassViolatePkts OBJECT-TYPE
    SYNTAX      Counter64
    MAX-ACCESS  read-only
    STATUS      current
    DESCRIPTION
           "The number of packets that violate the normal and maximum burst
            sizes on the circuit group."
    ::= { rbnCctGrpRLClassStatsEntry 12 }

rbnCctGrpRLClassViolateDroppedOctets OBJECT-TYPE
    SYNTAX      Counter64
    MAX-ACCESS  read-only
    STATUS      current
    DESCRIPTION
           "The number of octets that were dropped due to the application
            of a violate action on packets that violate the normal and
            maximum burst sizes on the circuit group."
    ::= { rbnCctGrpRLClassStatsEntry 13 }

rbnCctGrpRLClassViolateDroppedPkts OBJECT-TYPE
    SYNTAX      Counter64
    MAX-ACCESS  read-only
    STATUS      current
    DESCRIPTION
           "The number of packets that were dropped due to the application
            of a violate action on packets that violate the normal and
            maximum burst sizes on the circuit group."
    ::= { rbnCctGrpRLClassStatsEntry 14 }


--
-- Compliance statements
--
rbnCircuitGroupCompliances
        OBJECT IDENTIFIER ::= { rbnCircuitGroupConformance 1 }
rbnCircuitGroupConformGroups
        OBJECT IDENTIFIER ::= { rbnCircuitGroupConformance 2 }

rbnCCircuitGroupCompliance MODULE-COMPLIANCE
    STATUS  current
    DESCRIPTION
        "The compliance statement for SNMP entities which implement
         the CircuitGroup MIB."
    MODULE  -- this module
        MANDATORY-GROUPS {
            rbnCctGrpStatsGroup,
            rbnCctGrpQStatsGroup,
            rbnCctGrpPolicyStatsGroup
        }
    ::= { rbnCircuitGroupCompliances 1 }
    
--
-- Groups
--
rbnCctGrpStatsGroup OBJECT-GROUP
    OBJECTS {
        rbnCctGrpTxOctets,
        rbnCctGrpTxPackets,
        rbnCctGrpTxMulticastOctets,
        rbnCctGrpTxMulticastPackets,
        rbnCctGrpRxOctets,
        rbnCctGrpRxPackets,
        rbnCctGrpRxMulticastOctets,
        rbnCctGrpRxMulticastPackets,
        rbnCctGrpAdjDroppedOctets,
        rbnCctGrpAdjDroppedPackets,
        rbnCctGrpDownDroppedOctets,
        rbnCctGrpDownDroppedPackets,
        rbnCctGrpUnreachDroppedOctets,
        rbnCctGrpUnreachDroppedPackets,
        rbnCctGrpUnknownEncapsOctets,
        rbnCctGrpUnknownEncapsPackets
    }
    STATUS    current
    DESCRIPTION
        "The collection of objects which allow monitoring of circuit groups."
    ::= { rbnCircuitGroupConformGroups 1 }
    
rbnCctGrpQStatsGroup OBJECT-GROUP
    OBJECTS {
        rbnCctGrpQTxOctets,
        rbnCctGrpQTxPackets,
        rbnCctGrpQWredDroppedOctets,
        rbnCctGrpQWredDroppedPkts,
        rbnCctGrpQTailDroppedOctets,
        rbnCctGrpQTailDroppedPkts
    }
    STATUS    current
    DESCRIPTION
        "The collection of objects which allow monitoring of circuit group
        queues."
    ::= { rbnCircuitGroupConformGroups 2 }

rbnCctGrpPolicyStatsGroup OBJECT-GROUP
    OBJECTS { 
        rbnCctGrpRLPolicyName,
        rbnCctGrpRLPolicyConformOctets,
        rbnCctGrpRLPolicyConformPkts,
        rbnCctGrpRLPolicyExceedOctets,
        rbnCctGrpRLPolicyExceedPkts,
        rbnCctGrpRLPolicyExceedDroppedOctets,
        rbnCctGrpRLPolicyExceedDroppedPkts,
        rbnCctGrpRLPolicyViolateOctets,
        rbnCctGrpRLPolicyViolatePkts,
        rbnCctGrpRLPolicyViolateDroppedOctets,
        rbnCctGrpRLPolicyViolateDroppedPkts,
        rbnCctGrpRLClassName,
        rbnCctGrpRLClassConformOctets,
        rbnCctGrpRLClassConformPkts,
        rbnCctGrpRLClassConformDroppedOctets,
        rbnCctGrpRLClassConformDroppedPkts,
        rbnCctGrpRLClassExceedOctets,
        rbnCctGrpRLClassExceedPkts,
        rbnCctGrpRLClassExceedDroppedOctets,
        rbnCctGrpRLClassExceedDroppedPkts,
        rbnCctGrpRLClassViolateOctets,
        rbnCctGrpRLClassViolatePkts,
        rbnCctGrpRLClassViolateDroppedOctets,
        rbnCctGrpRLClassViolateDroppedPkts
     }
    STATUS    current
    DESCRIPTION
        "The collection of objects which allow monitoring rate limit
        policy and class counters for circuit groups."
    ::= { rbnCircuitGroupConformGroups 3 }
    
END
