-- %DNP% $Id: RBN-PRODUCT-MIB.my,v 1.2.2.27.2.23 2012/04/18 12:02:19 ethasas Exp $
-- %DNP% $Source: /cvsroot/pkt/sw/se/xc/bsd/config/snmp/mibs/RBN-PRODUCT-MIB.my,v $
-- *****************************************************************
-- RBN-PRODUCT-MIB	Enterprise Product and Entity Assignments
--
-- Copyright (c) 1999-2014 Ericsson AB.
-- All rights reserved.
--
-- *****************************************************************

RBN-PRODUCT-MIB DEFINITIONS ::= BEGIN

IMPORTS
	MODULE-IDENTITY,
	OBJECT-IDENTITY
		FROM SNMPv2-SMI
	rbnModules,
	rbnProducts,
	rbnEntities
		FROM RBN-SMI;

rbnProductMIB MODULE-IDENTITY
	LAST-UPDATED    "201409221800Z" -- Sept 22, 2014
	ORGANIZATION	"Ericsson AB"
	CONTACT-INFO
                "       Ericsson AB

                        100 Headquarters Dr
                        San Jose, CA  95134
                        USA

                 Phone: +1 408 750 5000
                   Fax: +1 408 750 5599
                "
	DESCRIPTION
		"This management information module contains the
		administrative assignments which are used to
		uniquely identify physical components"         

       REVISION        "201409221800Z" -- Sept 22, 2014
       DESCRIPTION
                "Added new OIDs:
                        rbnEntModuleSSR20PortOC3orOC12orOC48orOC192
                        rbnEntPortSSR20POSOCorOC12orOC48orOC192
                "

       REVISION        "201310171800Z" -- Oct 17, 2013
       DESCRIPTION
                "Added new OIDs:
                        rbnEntFanTrayAlarmIOSPSC1
                        rbnEntPortSPSC1AlarmIn
                        rbnEntPortSPSC1AlarmOut
                "

       REVISION        "201309161800Z" -- Sept 3, 2013
       DESCRIPTION
                "Removed OIDs:
                        rbnSSR8006
                        rbnEntChassisSSR8006
                        rbnEntBackplaneSSR8006Data
                        rbnEntContainerSSR8006FanTray
                        rbnEntContainerSSR8006PowerModule
                        rbnEntContainerSSR8006Data
                 Added new OIDs: 
                        rbnSSR8004
                        rbnEntChassisSSR8004
                        rbnEntBackplaneSSR8004Data
                        rbnEntContainerSSR8004FanTray
                        rbnEntContainerSSR8004PowerModule
                        rbnEntContainerSSR8004Data
                "
       REVISION        "201306191800Z" -- June 19, 2013
       DESCRIPTION
                "Added new OIDs:
                        rbnEntBackplaneSP415Data
                        rbnEntBackplaneSP420Data
                        rbnEntBackplaneSFFUMData
                        rbnEntBackplaneSFP1SData
                "

       REVISION        "201304181800Z" -- April 18, 2013
       DESCRIPTION
                "Added new OIDs:
                        rbnSP415
                        rbnSP420
                        rbnSFFUM
                        rbnSFP1S
                        rbnEntChassisSP415
                        rbnEntChassisSP420
                        rbnEntChassisSFFUM
                        rbnEntChassisSFP1S
                        rbnEntContainerSPSC1FanTray
                        rbnEntContainerSPSC1PowerModule
                        rbnEntContainerSPSC1Data
                        rbnEntFanTraySPSC1
                        rbnEntPowerModuleSPSC1AC
                        rbnEntPowerModuleSPSC1DC
                        rbnEntModuleSPSC1SC
                        rbnEntModuleSPSC11Port10GE
                        rbnEntModuleSPSC18PortCES
                        rbnEntModuleSPSC116Port1GE
                        rbnEntModuleSPSC120and2Port1and10GE
                        rbnEntPortSPSC11GE
                        rbnEntPortSPSC110GE
                        rbnEntPortSPSC1SCMgmt
                "

       REVISION        "201301141800Z" -- Jan 14, 2013
       DESCRIPTION
                "Added new OIDs:
                        rbnEntModuleSSC2
                        rbnEntModuleSSR20Port1GEor10GE
                "

       REVISION        "201206251800Z" -- June 25, 2012
       DESCRIPTION
                "Added new OIDs:
                       rbnEntModuleSSR20Port1GEor4Port10GE
                "

       REVISION        "201203191800Z" -- Mar 19, 2012
       DESCRIPTION
                "Added new OIDs:
                        rbnEntModuleSSR2Port40GEor100GE
                        rbnEntPortSSR40GEor100GE
                "

       REVISION        "201202101800Z" -- Feb 10, 2012
       DESCRIPTION
                "Added new OID:
                        rbnEntModuleSSC1
                "

       REVISION        "201106021800Z" -- June 02, 2011
       DESCRIPTION
                "Added new OID:
                        rbnEntPortSSRRPSWMgmt
                "

       REVISION        "201101191800Z" -- Jan 19, 2011
       DESCRIPTION
                "Update CONTACT-INFO & ORGANIZATION. Remove previous
                company name from descriptions."


       REVISION        "201010010000Z" -- Oct 01, 2010
       DESCRIPTION
                "Added new OIDs:
                        rbnEntCpuUnknown
                        rbnEntCpuOcteon
                        rbnEntModuleSEASE2
                        rbnSSR8020
                        rbnSSR8010
                        rbnSSR8006
                        rbnEntChassisSSR8020
                        rbnEntChassisSSR8010
                        rbnEntChassisSSR8006
                        rbnEntBackplaneSSR8020Data
                        rbnEntBackplaneSSR8010Data
                        rbnEntBackplaneSSR8006Data
                        rbnEntContainerSSR8020FanTray
                        rbnEntContainerSSR8020PowerModule
                        rbnEntContainerSSR8020Data
                        rbnEntContainerSSR8010FanTray
                        rbnEntContainerSSR8010PowerModule
                        rbnEntContainerSSR8010Data
                        rbnEntContainerSSR8006FanTray
                        rbnEntContainerSSR8006PowerModule
                        rbnEntContainerSSR8006Data
                        rbnEntFanTraySSR
                        rbnEntPowerModuleSSR
                        rbnEntModuleSSRALSW
                        rbnEntModuleSSRRPSW
                        rbnEntModuleSSRSW
                        rbnEntModuleSSR40Port1GE
                        rbnEntModuleSSR10Port10GE
                        rbnEntModuleSSR1Port100GE
                        rbnEntModuleSSR2Port40GE
                        rbnEntModuleSSR2or1Port40or100GE
                        rbnEntPortSSR1GE
                        rbnEntPortSSR10GE
                        rbnEntPortSSR100GE
                        rbnEntPortSSR40GE
                        rbnEntPortSSR40or100GE
                "

        REVISION        "201008270000Z" -- August 27, 2010
        DESCRIPTION
                "Added new OIDs:	
                        rbnEntModuleSM8OR2PORTCHOC3OC12
                        rbnEntPortSMCHOC3OC12
                        rbnEntPortSMCHOC3
                "

        REVISION        "201004010000Z" -- April 01, 2010
        DESCRIPTION
                "Added new OIDs:
                        rbnEntModuleSEPos8xOC3
                        rbnEntModuleSEPos4xOC12
                        rbnEntModuleSEAtm2xOC12
                "

        REVISION        "201001270000Z" -- January 27, 2010
        DESCRIPTION
                "Added new OIDs:
                        rbnEntModuleSE1Port10GEOC192
                        rbnEntModuleSM1Port10GEOC192
                "
        REVISION        "200910050000Z" -- October 05, 2009
        DESCRIPTION
                "Added new OIDs:
                        rbnEntChassisSE1200H
                        rbnEntBackplaneSE1200HData
                        rbnEntContainerSE1200HData
                        rbnEntFanSE1200H
                "

        REVISION        "200909240000Z" -- September 24, 2009
        DESCRIPTION
                "Added new OIDs:	
                        rbnEntModuleSE8OR2PORTCHOC3OC12
                        rbnEntPortSECHOC3OC12
                        rbnEntPortSECHOC3
                "

        REVISION        "200909130000Z" -- September 13, 2009
        DESCRIPTION
                "Added new OID:
                        rbnEntModuleSE10PortGIGEDDR2
                        rbnEntModuleSM10PortGIGEDDR2
                "

        REVISION        "200909100000Z" -- September 10, 2009
        DESCRIPTION
                "Added new OIDs:
                        rbnEntModuleSE4PortOC48
                        rbnEntModuleSE8PortOC3
                "

        REVISION        "200907160000Z" -- July 16, 2009
        DESCRIPTION
                "Added new OIDs:
                        rbnEntityTypeStack
                        rbnEntityTypeCPU
                        rbnEntityTypeMemory
                        rbnEntModuleSESSE
                        rbnEntityTypeDisk
                        rbnEntDiskSSE
                "

        REVISION        "200902040000Z" -- February 04, 2009
        DESCRIPTION
                "
                        rbnSmartEdge600
                        rbnSM240
                        rbnEntChassisSE600
                        rbnEntChassisSM240
                        rbnEntBackplaneSE600Data
                        rbnEntBackplaneSM240Data
                        rbnEntContainerSE600Data
                        rbnEntContainerSM240Data
                        rbnEntFanSE600
                        rbnEntFanSM240
                        rbnEntSensorAlarmSE600
                        rbnEntSensorAlarmSM240
                "

	REVISION        "200901200000Z" -- January 20, 2009
	DESCRIPTION
		"Added new OIDs:	
			rbnEntModuleSMFE60GE2
                        rbnEntModuleSM20PortGIGE
                        rbnEntModuleSM4Port10GIGE
                        rbnEntPortSMEIM
                 Removed OID
                        rbnEntModuleSMRP1"

        REVISION        "200809230000Z" -- Sep, 23, 2008
        DESCRIPTION
                "Added new OIDs:
                	rbnEntPortSM10GIGEIM
			rbnEntPortSMRPMGMT
			rbnEntPortSMGIGEIM
			rbnEntPortSMGIGETM
			rbnEntPortSM10GIGETM"

        REVISION        "200807020000Z" -- July 02, 2008
        DESCRIPTION
                "Added new OIDs:
              		rbnEntModuleSE20PortGIGE
			rbnEntModuleSE4Port10GIGE
			rbnEntModuleSE10GIGETM
			rbnEntPortSE10GIGETM "

        REVISION        "200805200000Z" -- May 20, 2008
        DESCRIPTION
                "Added new OIDs:
			rbnSM480
			rbnEntChassisSM480
                        rbnEntBackplaneSM480Data
                        rbnEntContainerSM480Data
                        rbnEntFanSM480
			rbnEntModuleSM10GIGEIM
			rbnEntModuleSMRP2
			rbnEntModuleSMGIGEIM
			rbnEntModuleSMRP1
			rbnEntModuleSMGIGETM
			rbnEntModuleSM10GIGETM
                "
        REVISION        "200805080000Z" -- May 08, 2008
        DESCRIPTION
                "Added new OIDs:
                        rbnEntModuleSE5PortGIG
                "

        REVISION        "200709200000Z" -- September 20, 2007
        DESCRIPTION
                "Added new OIDs:
                        rbnEntModuleSEPOSOC192
                        rbnEntPortSEPOSOC192
                "

        REVISION        "200708080000Z" -- August 08, 2007
        DESCRIPTION
                "Added new OIDs:
                        rbnEntModuleSEFE60GE2
                "

	REVISION	"200705090000Z" -- May 09, 2007
	DESCRIPTION
		"Added new OIDs:
			rbnEntModuleSEASE
		"

        REVISION        "200702280000Z" -- February 28, 2007
        DESCRIPTION
                "Added new OIDs:
                        rbnEntModuleSEXC4
                        rbnEntPortSEXC4MGMT
                "

        REVISION        "200702140000Z" -- February 14, 2007
        DESCRIPTION
        	"Added new OIDs:
        		rbnSmartEdge1200
			rbnEntChassisSE1200
			rbnEntBackplaneSE1200Data
			rbnEntContainerSE1200Data
			rbnEntFanSE1200
                "

	REVISION	"200702050000Z" -- February 05, 2007
	DESCRIPTION
		"Added new OIDs:
			rbnEntModuleSE100AIMOC3MIC
			rbnEntPortSE100AIMOC3
		"
	REVISION        "200512270000Z" -- December 27, 2005
	DESCRIPTION
		"Added new OIDs:
			rbnSmartEdge100
			rbnEntChassisSE100
			rbnEntBackplaneSE100Data
			rbnEntContainerSE100Data
			rbnEntContainerSE100Carrier
			rbnEntModuleSE100XC
			rbnEntModuleSE100EMIC
			rbnEntModuleSE100FXMIC
			rbnEntModuleSE100GERJMIC
			rbnEntModuleSE100GEFXMIC
			rbnEntPortSE100XCMGMT
			rbnEntPortSE100EIM
			rbnEntPortSE100FXIM
			rbnEntPortSE100GERJIM
			rbnEntPortSE100GEFXIM
		"
	REVISION	"200503010000Z" -- March 1, 2005
	DESCRIPTION
		"Added new OIDs:
			rbnEntModuleSE10GIGEIM
			rbnEntPortSE10GIGEIM
		"
	REVISION	"200411050000Z" -- November 5, 2004
	DESCRIPTION
		"Added new OIDs:
			rbnEntModuleSEGIGETM
			rbnEntPortSEGIGETM
		"
	REVISION	"200405110000Z" -- May 11, 2004
	DESCRIPTION
		"Added new OIDs:
			rbnEntModuleSEAIMOC12E
			rbnEntPortSEAIMOC12E
		"
	REVISION	"200309250000Z" -- September 25, 2003
	DESCRIPTION
		"Added new OIDs:
			rbnEntModuleSEE3
			rbnEntPortSEE3
		"
	REVISION	"200307240000Z" -- July 24, 2003
	DESCRIPTION
		"Added new OIDs:
			rbnEntSensorAlarmSE400
		"
	REVISION	"200305191700Z" -- May 19, 2003
	DESCRIPTION
		"Added new OIDs:
			rbnEntModuleSMSXFE
		"
	REVISION	"200305050000Z" -- May 5,2003
	DESCRIPTION
		"Added new OID:
			rbnEntPortSEXC3MGMT
		"
	REVISION	"200303250000Z" -- March 25,2003
	DESCRIPTION
		"Added new OIDs:
			rbnSmartEdge400
			rbnEntChassisSE400
			rbnEntBackplaneSE400Data
			rbnEntContainerSE400Data
			rbnEntFanSE400
			rbnEntModuleSEXC3
		"
	REVISION	"200206130000Z" -- June 13, 2002
	DESCRIPTION
		"Added new OIDs:
			rbnEntModuleSECHSTM1E1
			rbnEntModuleSEE1
			rbnEntPortSECHSTM1E1
			rbnEntPortSEE1
		"
	REVISION	"200206060000Z" -- June 6, 2002
	DESCRIPTION
		"Updated the Contact Phone and Fax numbers.
		Added new OIDs:
			rbnEntModuleSEDS3
			rbnEntPortSEDS3
			rbnEntModuleSEAIMDS3
			rbnEntPortSEAIMDS3
		"
	REVISION	"200112120000Z" -- December 12, 2001
	DESCRIPTION
		"Changed the CONTACT-INFO postal address.
		Added new OIDs:
			rbnEntModuleSECHDS3
			rbnEntPortSECHDS3
		"
	REVISION	"200109261700Z" -- September 25, 2001
	DESCRIPTION
		"Added new OIDs:
			rbnEntModuleSEAIMOC3
			rbnEntModuleSEAIMOC12
			rbnEntPortSEAIMOC3
			rbnEntPortSEAIMOC12
		"
	REVISION	"200107251000Z" -- July 25, 2001
	DESCRIPTION
		"Added new OIDs:
			rbnEntModuleSECHOC12DS1
			rbnEntModuleSECHOC12DS3
			rbnEntPortSECHOC12DS1
			rbnEntPortSECHOC12DS3
		"
	REVISION	"200105151507Z" -- May 15, 2001
	DESCRIPTION
		"Updated name for new SMS platform.
		"
	REVISION	"200105041642Z" -- May 04, 2001
	DESCRIPTION
		"Added new OIDs:
			rbnEntChassisSE800
			rbnEntBackplaneSE800Data
			rbnEntContainerSE800Data
			rbnEntFanSE800
			rbnEntModuleSEXC
			rbnEntModuleSEEIM
			rbnEntModuleSEGIGEIM
			rbnEntModuleSEPOSOC12
			rbnEntModuleSEPOSOC48
			rbnEntModuleSEPOSOC3
			rbnEntPortSEXCMGMT
			rbnEntPortSEEIM
			rbnEntPortSEGIGEIM
			rbnEntPortSEPOSOC12
			rbnEntPortSEPOSOC48
			rbnEntPortSEPOSOC3
		"
	REVISION	"200102131857Z" -- February 13, 2001
	DESCRIPTION
		"Added new OID:
			rbnSmartEdge800
		"
	REVISION	"200102131007Z" -- February 13, 2001
	DESCRIPTION
		"Added support for new SMS platform.
		"
	REVISION	"200102011707Z" -- February 1, 2001
	DESCRIPTION
		"Added new OID:
-- %DNP% --			rbnSMS2800
		"
	REVISION	"200101051834Z" -- January 5, 2001
	DESCRIPTION
		"Added new OIDs:
-- %DNP% --			rbnEntModuleSMSCSM
-- %DNP% --			rbnEntPortSMSCSMMGMT
		"
	REVISION	"200012281704Z" -- December 28, 2000
	DESCRIPTION
		"Added new OIDs:
-- %DNP% --			rbnEntChassisSMS2800
-- %DNP% --			rbnEntBackplaneSMS2800Data
-- %DNP% --			rbnEntBackplaneSMS2800Power
-- %DNP% --			rbnEntContainerSMS2800IO
-- %DNP% --			rbnEntContainerSMS2800Power
-- %DNP% --			rbnEntContainerSMS2800CSM
-- %DNP% --			rbnEntPowerSupplySMS2800AC
-- %DNP% --			rbnEntPowerSupplySMS2800DC
		"
	REVISION	"200011151704Z" -- November 15, 2000
	DESCRIPTION
		"Added new OID:
			rbnEntBackplaneSMS10000Midplane
		"
	REVISION	"200011021454Z" -- November 2, 2000
	DESCRIPTION
		"Added new OID:
			rbnEntModuleSMSFE3
		"
	REVISION	"200010251523Z" -- October 25, 2000
	DESCRIPTION
		"Added new OIDs:
			rbnEntModuleSMSPIMCDS3
			rbnEntPortSMSPIMCDS3
		"
	REVISION	"200010201730Z" -- October 20, 2000
	DESCRIPTION
		"Added new OIDs:
			rbnEntModuleSMSFABRIC
			rbnEntModuleSMSTIMING
			rbnEntModuleSMSCM
			rbnEntModuleSMSSM
		"
	REVISION	"200009261330Z"	-- September 26, 2000
	DESCRIPTION
		"Added new OIDs:
-- %DNP% --			rbnEsp200
-- %DNP% --			rbnEsp5000
-- %DNP% --			rbnEsp6000
		"
	REVISION	"200009251120Z"	-- Sep 25, 2000
	DESCRIPTION
		"Added new OID:
			rbnEntPortSMSAIME1
		"
	REVISION	"200007191544Z"	-- Jul 19, 2000
	DESCRIPTION
		"Added new OID:
			rbnEntModuleSMSAIME1
		"
	REVISION	"200007062150Z"	-- July 6, 2000
	DESCRIPTION
		"Added new OID:
-- %DNP% --			rbnSmartEdgeIDT
		"
	REVISION	"200006161700Z"	-- Jun 16, 2000
	DESCRIPTION
		"In MODULE-IDENTITY, updated CONTACT-INFO and added
		new REVISION info.

		Added new OIDs:
		    rbnEntModuleSMSAIMOC12
		    rbnEntPortSMSAIMOC12"

	REVISION	"200006131700Z"	-- Jun 13, 2000
	DESCRIPTION
		"In MODULE-IDENTITY, updated CONTACT-INFO and added
		new REVISION info.

		Added new OIDs:
			rbnEntModuleSMSAIMT1
			rbnEntPortSMSAIMT1
			rbnEntModuleSMSAIME3
			rbnEntPortSMSAIME3"

	REVISION	"200005180000Z"	-- May 18, 2000
	DESCRIPTION
		"Addition of rbnSMS10000"

	REVISION	"9907081712Z"	-- Jul 8, 1999
	DESCRIPTION
		"Addition of rbnSMS1800"

	REVISION	"9808051900Z"	-- Aug 5, 1998
	DESCRIPTION
		"Initial version"
	::= { rbnModules 1 }


--
-- Product Assignments
--

rbnSMS1000 OBJECT-IDENTITY
	STATUS  current
	DESCRIPTION
		"The definitive identifier of the SMS 1000"
	::= { rbnProducts 1 }

rbnSMS500 OBJECT-IDENTITY
	STATUS  current
	DESCRIPTION
		"The definitive identifier of the SMS 500"
	::= { rbnProducts 2 }

rbnSMS1800 OBJECT-IDENTITY
        STATUS  current
        DESCRIPTION
                "The definitive identifier of the SMS 1800"
        ::= { rbnProducts 3 }

rbnSMS10000 OBJECT-IDENTITY
        STATUS  current
        DESCRIPTION
                "The definitive identifier of the SMS 10000"
        ::= { rbnProducts 4 }


-- %DNP% --rbnSmartEdgeIDT OBJECT-IDENTITY
-- %DNP% --        STATUS  obsolete
-- %DNP% --        DESCRIPTION
-- %DNP% --                "The definitive identifier of the SmartEdge IDT"
-- %DNP% --        ::= { rbnProducts 5 }

-- %DNP% --rbnEsp200 OBJECT-IDENTITY
-- %DNP% --        STATUS  obsolete
-- %DNP% --        DESCRIPTION
-- %DNP% --                "The definitive identifier of the ESP 200"
-- %DNP% --        ::= { rbnProducts 6 }

-- %DNP% --rbnEsp5000 OBJECT-IDENTITY
-- %DNP% --        STATUS  obsolete
-- %DNP% --        DESCRIPTION
-- %DNP% --                "The definitive identifier of the ESP 5000"
-- %DNP% --        ::= { rbnProducts 7 }

-- %DNP% --rbnEsp6000 OBJECT-IDENTITY
-- %DNP% --        STATUS  obsolete
-- %DNP% --        DESCRIPTION
-- %DNP% --                "The definitive identifier of the ESP 6000"
-- %DNP% --        ::= { rbnProducts 8 }

-- %DNP% --rbnSMS2800 OBJECT-IDENTITY
-- %DNP% --        STATUS  obsolete
-- %DNP% --        DESCRIPTION
-- %DNP% --                "The definitive identifier of the SMS 2800"
-- %DNP% --        ::= { rbnProducts 9 }

rbnSmartEdge800 OBJECT-IDENTITY
        STATUS  current
        DESCRIPTION
                "The definitive identifier of the SmartEdge 800"
        ::= { rbnProducts 10 }

rbnSmartEdge400 OBJECT-IDENTITY
        STATUS  current
        DESCRIPTION
                "The definitive identifier of the SmartEdge 400"
        ::= { rbnProducts 11 }

rbnSmartEdge100 OBJECT-IDENTITY
        STATUS  current
        DESCRIPTION
                "The definitive identifier of the SmartEdge 100"
        ::= { rbnProducts 12 }

rbnSmartEdge1200 OBJECT-IDENTITY
        STATUS  current
        DESCRIPTION
                "The definitive identifier of the SmartEdge 1200"
        ::= { rbnProducts 13 }

rbnSM480 OBJECT-IDENTITY
        STATUS  current
        DESCRIPTION
                "The definitive identifier of the SM 480"
        ::= { rbnProducts 14 }

rbnSmartEdge600 OBJECT-IDENTITY
        STATUS  current
        DESCRIPTION
                "The definitive identifier of the SmartEdge 600"
        ::= { rbnProducts 15 }

rbnSM240 OBJECT-IDENTITY
        STATUS  current
        DESCRIPTION
                "The definitive identifier of the SM240"
        ::= { rbnProducts 16 }

rbnSSR8020 OBJECT-IDENTITY
        STATUS  current
        DESCRIPTION
                "The definitive identifier for the Smart Services
                Router(SSR) 8020"
        ::= { rbnProducts 17 }

rbnSSR8010 OBJECT-IDENTITY
        STATUS  current
        DESCRIPTION
                "The definitive identifier for the Smart Services
                Router(SSR) 8010"
        ::= { rbnProducts 18 }

rbnSSR8004 OBJECT-IDENTITY
        STATUS  current
        DESCRIPTION
                "The definitive identifier for the Smart Services
                Router(SSR) 8004"
        ::= { rbnProducts 19 }

rbnSP415 OBJECT-IDENTITY
        STATUS  current
        DESCRIPTION
                "The definitive identifier for the Smart Packet
                (SP) 415"
        ::= { rbnProducts 20 }

rbnSP420 OBJECT-IDENTITY
        STATUS  current
        DESCRIPTION
                "The definitive identifier for the Smart Packet
                (SP) 420"
        ::= { rbnProducts 21 }

rbnSFFUM OBJECT-IDENTITY
        STATUS  current
        DESCRIPTION
                "The definitive identifier for the Smart Packet
                (SF) FUM"
        ::= { rbnProducts 22 }

rbnSFP1S OBJECT-IDENTITY
        STATUS  current
        DESCRIPTION
                "The definitive identifier for the Smart Packet
                (SF) P1S"
        ::= { rbnProducts 23 }

--
-- Entity Assignments
--
-- { rbnEntities 1 } and { rbnEntities 2 } are unassigned

rbnEntityTypeOther OBJECT-IDENTITY
      STATUS  current
      DESCRIPTION
              "The top-level category identifier for entities which
              reside in the ENTITY-MIB PhysicalClass *other*"
      ::= { rbnEntities 1 }

rbnEntityTypeUnknown OBJECT-IDENTITY
      STATUS  current
      DESCRIPTION
              "The top-level category identifier for entities which
              reside in the ENTITY-MIB PhysicalClass *unknown*"
      ::= { rbnEntities 2 }

rbnEntityTypeChassis OBJECT-IDENTITY
      STATUS  current
      DESCRIPTION
              "The top-level category identifier for entities which
              reside in the ENTITY-MIB PhysicalClass *chassis*"
      ::= { rbnEntities 3 }

rbnEntChassisSMS1000 OBJECT-IDENTITY
      STATUS  current
      DESCRIPTION
              "The definitive identifier for the SMS 1000 chassis entity."
      ::= { rbnEntityTypeChassis 1 }

rbnEntChassisSMS500 OBJECT-IDENTITY
      STATUS  current
      DESCRIPTION
              "The definitive identifier for the SMS 500 chassis entity."
      ::= { rbnEntityTypeChassis 2 }

rbnEntChassisSMS1800 OBJECT-IDENTITY
      STATUS  current
      DESCRIPTION
              "The definitive identifier for the SMS 1800 chassis entity."
      ::= { rbnEntityTypeChassis 3 }

rbnEntChassisSMS10000 OBJECT-IDENTITY
      STATUS  current
      DESCRIPTION
              "The definitive identifier for the SMS 10000 chassis entity."
      ::= { rbnEntityTypeChassis 4 }

-- %DNP% --rbnEntChassisSMS2800 OBJECT-IDENTITY
-- %DNP% --      STATUS  obsolete
-- %DNP% --      DESCRIPTION
-- %DNP% --              "The definitive identifier for the
-- %DNP% --              SMS 2800 chassis entity."
-- %DNP% --      ::= { rbnEntityTypeChassis 5 }

rbnEntChassisSE800 OBJECT-IDENTITY
      STATUS current
      DESCRIPTION
              "The definitive identifier for the
              SE 800 chassis entity."
      ::= { rbnEntityTypeChassis 6 }

rbnEntChassisSE400 OBJECT-IDENTITY
      STATUS current
      DESCRIPTION
              "The definitive identifier for the
              SE 400 chassis entity."
      ::= { rbnEntityTypeChassis 7 }

rbnEntChassisSE100 OBJECT-IDENTITY
      STATUS current
      DESCRIPTION
              "The definitive identifier for the
              SE 100 chassis entity."
      ::= { rbnEntityTypeChassis 8 }

rbnEntChassisSE1200 OBJECT-IDENTITY
      STATUS current
      DESCRIPTION
              "The definitive identifier for the
              SE 1200 chassis entity."
      ::= { rbnEntityTypeChassis 9 }

rbnEntChassisSM480 OBJECT-IDENTITY
      STATUS current
      DESCRIPTION
              "The definitive identifier for the
              SM 480 chassis entity."
      ::= { rbnEntityTypeChassis 10 }

rbnEntChassisSE600 OBJECT-IDENTITY
      STATUS current
      DESCRIPTION
              "The definitive identifier for the
              SmartEdge 600 chassis entity."
      ::= { rbnEntityTypeChassis 11 }

rbnEntChassisSM240 OBJECT-IDENTITY
      STATUS current
      DESCRIPTION
              "The definitive identifier for the
              SM240 chassis entity."
      ::= { rbnEntityTypeChassis 12 }

rbnEntChassisSE1200H OBJECT-IDENTITY
      STATUS current
      DESCRIPTION
              "The definitive identifier for the SE1200H chassis entity."
      ::= { rbnEntityTypeChassis 13 }

rbnEntChassisSSR8020 OBJECT-IDENTITY
      STATUS current
      DESCRIPTION
              "The definitive identifier for the Smart Services Router 8020
              chassis entity."
      ::= { rbnEntityTypeChassis 14 }

rbnEntChassisSSR8010 OBJECT-IDENTITY
      STATUS current
      DESCRIPTION
              "The definitive identifier for the Smart Services Router 8010
              chassis entity."
      ::= { rbnEntityTypeChassis 15 }

rbnEntChassisSSR8004 OBJECT-IDENTITY
      STATUS current
      DESCRIPTION
              "The definitive identifier for the Smart Services Router 8004
              chassis entity."
      ::= { rbnEntityTypeChassis 16 }

rbnEntChassisSP415 OBJECT-IDENTITY
      STATUS current
      DESCRIPTION
              "The definitive identifier for the Smart Packet 415
              chassis entity."
      ::= { rbnEntityTypeChassis 17 }

rbnEntChassisSP420 OBJECT-IDENTITY
      STATUS current
      DESCRIPTION
              "The definitive identifier for the Smart Packet 420
              chassis entity."
      ::= { rbnEntityTypeChassis 18 }

rbnEntChassisSFFUM OBJECT-IDENTITY
      STATUS current
      DESCRIPTION
              "The definitive identifier for the Smart Packet FUM
              chassis entity."
      ::= { rbnEntityTypeChassis 19 }

rbnEntChassisSFP1S OBJECT-IDENTITY
      STATUS current
      DESCRIPTION
              "The definitive identifier for the Smart Packet P1S
              chassis entity."
      ::= { rbnEntityTypeChassis 20 }

rbnEntityTypeBackplane OBJECT-IDENTITY
      STATUS  current
      DESCRIPTION
              "The top-level category identifier for entities which
              reside in the ENTITY-MIB PhysicalClass *backplane*"
      ::= { rbnEntities 4 }

rbnEntBackplaneSMS1000Data OBJECT-IDENTITY
      STATUS  current
      DESCRIPTION
              "The definitive identifier for the
              SMS 1000 data backplane entity."
      ::= { rbnEntityTypeBackplane 1 }

rbnEntBackplaneSMS1000Power OBJECT-IDENTITY
      STATUS  current
      DESCRIPTION
              "The definitive identifier for the
              SMS 1000 power backplane entity."
      ::= { rbnEntityTypeBackplane 2 }

rbnEntBackplaneSMS500Data OBJECT-IDENTITY
      STATUS  current
      DESCRIPTION
              "The definitive identifier for the
              SMS 500 data backplane entity."
      ::= { rbnEntityTypeBackplane 3 }

rbnEntBackplaneSMS500Power OBJECT-IDENTITY
      STATUS  current
      DESCRIPTION
              "The definitive identifier for the
              SMS 500 power backplane entity."
      ::= { rbnEntityTypeBackplane 4 }

rbnEntBackplaneSMS1800Data OBJECT-IDENTITY
      STATUS  current
      DESCRIPTION
              "The definitive identifier for the
              SMS 1800 data backplane entity."
      ::= { rbnEntityTypeBackplane 5 }

rbnEntBackplaneSMS1800Power OBJECT-IDENTITY
      STATUS  current
      DESCRIPTION
              "The definitive identifier for the
              SMS 1800 power backplane entity."
      ::= { rbnEntityTypeBackplane 6 }

rbnEntBackplaneSMS10000Midplane OBJECT-IDENTITY
      STATUS  current
      DESCRIPTION
              "The definitive identifier for the
              SMS 10000 midplane entity."
      ::= { rbnEntityTypeBackplane 7 }

-- %DNP% --rbnEntBackplaneSMS2800Data OBJECT-IDENTITY
-- %DNP% --      STATUS  obsolete
-- %DNP% --      DESCRIPTION
-- %DNP% --              "The definitive identifier for the
-- %DNP% --              SMS 2800 data backplane entity."
-- %DNP% --      ::= { rbnEntityTypeBackplane 8 }

-- %DNP% --rbnEntBackplaneSMS2800Power OBJECT-IDENTITY
-- %DNP% --      STATUS  obsolete
-- %DNP% --      DESCRIPTION
-- %DNP% --              "The definitive identifier for the
-- %DNP% --              SMS 2800 power backplane entity."
-- %DNP% --      ::= { rbnEntityTypeBackplane 9 }

rbnEntBackplaneSE800Data OBJECT-IDENTITY
      STATUS current
      DESCRIPTION
              "The definitive identifier for the
              SE 800 data backplane entity."
      ::= { rbnEntityTypeBackplane 10 }

rbnEntBackplaneSE400Data OBJECT-IDENTITY
      STATUS current
      DESCRIPTION
              "The definitive identifier for the
              SE 400 data backplane entity."
      ::= { rbnEntityTypeBackplane 11 }

rbnEntBackplaneSE100Data OBJECT-IDENTITY
      STATUS current
      DESCRIPTION
              "The definitive identifier for the
              SE 100 data backplane entity."
      ::= { rbnEntityTypeBackplane 12 }

rbnEntBackplaneSE1200Data OBJECT-IDENTITY
      STATUS current
      DESCRIPTION
              "The definitive identifier for the
              SE 1200 data backplane entity."
      ::= { rbnEntityTypeBackplane 13 }

rbnEntBackplaneSM480Data OBJECT-IDENTITY
      STATUS current
      DESCRIPTION
              "The definitive identifier for the
              SM 480 data backplane entity."
      ::= { rbnEntityTypeBackplane 14 }

rbnEntBackplaneSE600Data OBJECT-IDENTITY
      STATUS current
      DESCRIPTION
              "The definitive identifier for the
              SmartEdge 600 data backplane entity."
      ::= { rbnEntityTypeBackplane 15 }

rbnEntBackplaneSM240Data OBJECT-IDENTITY
      STATUS current
      DESCRIPTION
              "The definitive identifier for the
              SM240 data backplane entity."
      ::= { rbnEntityTypeBackplane 16 }

rbnEntBackplaneSE1200HData OBJECT-IDENTITY
      STATUS current
      DESCRIPTION
              "The definitive identifier for the SE1200H data backplane entity."
      ::= { rbnEntityTypeBackplane 17 }

rbnEntBackplaneSSR8020Data OBJECT-IDENTITY
      STATUS  current
      DESCRIPTION
              "The definitive identifier for the Smart Services Router 8020
              data backplane entity."
      ::= { rbnEntityTypeBackplane 18 }

rbnEntBackplaneSSR8010Data OBJECT-IDENTITY
      STATUS  current
      DESCRIPTION
              "The definitive identifier for the Smart Services Router 8010
              data backplane entity."
      ::= { rbnEntityTypeBackplane 19 }

rbnEntBackplaneSSR8004Data OBJECT-IDENTITY
      STATUS  current
      DESCRIPTION
              "The definitive identifier for the Smart Services Router 8004
              data backplane entity."
      ::= { rbnEntityTypeBackplane 20 }

rbnEntBackplaneSP415Data OBJECT-IDENTITY
      STATUS  current
      DESCRIPTION
              "The definitive identifier for the Smart Packet 415
              data backplane entity."
      ::= { rbnEntityTypeBackplane 21 }

rbnEntBackplaneSP420Data OBJECT-IDENTITY
      STATUS  current
      DESCRIPTION
              "The definitive identifier for the Smart Packet 420
              data backplane entity."
      ::= { rbnEntityTypeBackplane 22 }

rbnEntBackplaneSFFUMData OBJECT-IDENTITY
      STATUS  current
      DESCRIPTION
              "The definitive identifier for the Smart Packet FUM
              data backplane entity."
      ::= { rbnEntityTypeBackplane 23 }

rbnEntBackplaneSFP1SData OBJECT-IDENTITY
      STATUS  current
      DESCRIPTION
              "The definitive identifier for the Smart Packet P1S
              data backplane entity."
      ::= { rbnEntityTypeBackplane 24 }

rbnEntityTypeContainer OBJECT-IDENTITY
      STATUS  current
      DESCRIPTION
              "The top-level category identifier for entities which
              reside in the ENTITY-MIB PhysicalClass *container*"
      ::= { rbnEntities 5 }

rbnEntContainerSMS1000Data OBJECT-IDENTITY
      STATUS  current
      DESCRIPTION
              "The definitive identifier for the
              SMS 1000 data container (slot) entity."
      ::= { rbnEntityTypeContainer 1 }

rbnEntContainerSMS1000Power OBJECT-IDENTITY
      STATUS  current
      DESCRIPTION
              "The definitive identifier for the
              SMS 1000 power container (slot) entity."
      ::= { rbnEntityTypeContainer 2 }

rbnEntContainerSMS500Data OBJECT-IDENTITY
      STATUS  current
      DESCRIPTION
              "The definitive identifier for the
              SMS 500 data container (slot) entity."
      ::= { rbnEntityTypeContainer 3 }

rbnEntContainerSMS500Power OBJECT-IDENTITY
      STATUS  current
      DESCRIPTION
              "The definitive identifier for the
              SMS 500 power container (slot) entity."
      ::= { rbnEntityTypeContainer 4 }

rbnEntContainerSMS1800Data OBJECT-IDENTITY
      STATUS  current
      DESCRIPTION
              "The definitive identifier for the
              SMS 1800 data container (slot) entity."
      ::= { rbnEntityTypeContainer 5 }

rbnEntContainerSMS1800Power OBJECT-IDENTITY
      STATUS  current
      DESCRIPTION
              "The definitive identifier for the
              SMS 1800 power container (slot) entity."
      ::= { rbnEntityTypeContainer 6 }

rbnEntContainerSMS10000Fabric OBJECT-IDENTITY
      STATUS  current
      DESCRIPTION
              "The definitive identifier for the
              SMS 10000 fabric container (slot) entity."
      ::= { rbnEntityTypeContainer 7 }

rbnEntContainerSMS10000Timing OBJECT-IDENTITY
      STATUS  current
      DESCRIPTION
              "The definitive identifier for the
              SMS 10000 timing container (slot) entity."
      ::= { rbnEntityTypeContainer 8 }

rbnEntContainerSMS10000SMCM OBJECT-IDENTITY
      STATUS  current
      DESCRIPTION
              "The definitive identifier for the
              SMS 10000 SM/CM container (slot) entity."
      ::= { rbnEntityTypeContainer 9 }

rbnEntContainerSMS10000IO OBJECT-IDENTITY
      STATUS  current
      DESCRIPTION
              "The definitive identifier for the
              SMS 10000 IO container (slot) entity."
      ::= { rbnEntityTypeContainer 10 }

-- %DNP% --rbnEntContainerSMS2800Power OBJECT-IDENTITY
-- %DNP% --      STATUS  obsolete
-- %DNP% --      DESCRIPTION
-- %DNP% --              "The definitive identifier for the
-- %DNP% --              SMS 2800 Power container (slot) entity."
-- %DNP% --      ::= { rbnEntityTypeContainer 11 }

-- %DNP% --rbnEntContainerSMS2800CSM OBJECT-IDENTITY
-- %DNP% --      STATUS  obsolete
-- %DNP% --      DESCRIPTION
-- %DNP% --              "The definitive identifier for the
-- %DNP% --              SMS 2800 CSM container (slot) entity."
-- %DNP% --      ::= { rbnEntityTypeContainer 12 }

-- %DNP% --rbnEntContainerSMS2800IO OBJECT-IDENTITY
-- %DNP% --      STATUS  obsolete
-- %DNP% --      DESCRIPTION
-- %DNP% --              "The definitive identifier for the
-- %DNP% --              SMS 2800 IO container (slot) entity."
-- %DNP% --      ::= { rbnEntityTypeContainer 13 }

rbnEntContainerSE800Data OBJECT-IDENTITY
      STATUS current
      DESCRIPTION
              "The definitive identifier for the
              SE 800 data container (slot) entity."
      ::= { rbnEntityTypeContainer 14 }

rbnEntContainerSE400Data OBJECT-IDENTITY
      STATUS current
      DESCRIPTION
              "The definitive identifier for the
              SE 400 data container (slot) entity."
      ::= { rbnEntityTypeContainer 15 }

rbnEntContainerSE100Data OBJECT-IDENTITY
      STATUS current
      DESCRIPTION
              "The definitive identifier for the
              SE 100 data container (slot) entity."
      ::= { rbnEntityTypeContainer 16 }

rbnEntContainerSE100Carrier OBJECT-IDENTITY
      STATUS  current
      DESCRIPTION
              "The definitive identifier for the
              SE 100 carrier container (MIC-card holder) entity"
      ::= { rbnEntityTypeContainer 17 }

rbnEntContainerSE1200Data OBJECT-IDENTITY
      STATUS current
      DESCRIPTION
              "The definitive identifier for the
              SE 1200 data container (slot) entity."
      ::= { rbnEntityTypeContainer 18 }

rbnEntContainerSM480Data OBJECT-IDENTITY
      STATUS current
      DESCRIPTION
              "The definitive identifier for the
              SM480 data container (slot) entity."
      ::= { rbnEntityTypeContainer 19 }

rbnEntContainerSE600Data OBJECT-IDENTITY
      STATUS current
      DESCRIPTION
              "The definitive identifier for the
              SE 600 data container (slot) entity."
      ::= { rbnEntityTypeContainer 20 }

rbnEntContainerSM240Data OBJECT-IDENTITY
      STATUS current
      DESCRIPTION
              "The definitive identifier for the
              SM240 data container (slot) entity."
      ::= { rbnEntityTypeContainer 21 }

rbnEntContainerSE1200HData OBJECT-IDENTITY
      STATUS current
      DESCRIPTION
              "The definitive identifier for the SE1200H data
               container (slot) entity."
      ::= { rbnEntityTypeContainer 22 }

rbnEntContainerSSR8020FanTray OBJECT-IDENTITY
      STATUS current
      DESCRIPTION
              "The definitive identifier for the Smart Services Router 8020
              fan tray container (slot) entity."
      ::= { rbnEntityTypeContainer 23 }

rbnEntContainerSSR8020PowerModule OBJECT-IDENTITY
      STATUS current
      DESCRIPTION
              "The definitive identifier for the Smart Services Router 8020
              power module container (slot) entity."
      ::= { rbnEntityTypeContainer 24 }

rbnEntContainerSSR8020Data OBJECT-IDENTITY
      STATUS current
      DESCRIPTION
              "The definitive identifier for the Smart Services Router 8020
              data container (slot) entity."
      ::= { rbnEntityTypeContainer 25 }

rbnEntContainerSSR8010FanTray OBJECT-IDENTITY
      STATUS current
      DESCRIPTION
              "The definitive identifier for the Smart Services Router 8010
              fan tray container (slot) entity."
      ::= { rbnEntityTypeContainer 26 }

rbnEntContainerSSR8010PowerModule OBJECT-IDENTITY
      STATUS current
      DESCRIPTION
              "The definitive identifier for the Smart Services Router 8010
              power module container (slot) entity."
      ::= { rbnEntityTypeContainer 27 }

rbnEntContainerSSR8010Data OBJECT-IDENTITY
      STATUS current
      DESCRIPTION
              "The definitive identifier for the Smart Services Router 8010
              data container (slot) entity."
      ::= { rbnEntityTypeContainer 28 }

rbnEntContainerSSR8004FanTray OBJECT-IDENTITY
      STATUS current
      DESCRIPTION
              "The definitive identifier for the Smart Services Router 8004
              fan tray container (slot) entity."
      ::= { rbnEntityTypeContainer 29 }

rbnEntContainerSSR8004PowerModule OBJECT-IDENTITY
      STATUS current
      DESCRIPTION
              "The definitive identifier for the Smart Services Router 8004
              power module container (slot) entity."
      ::= { rbnEntityTypeContainer 30 }

rbnEntContainerSSR8004Data OBJECT-IDENTITY
      STATUS current
      DESCRIPTION
              "The definitive identifier for the Smart Services Router 8004
              data container (slot) entity."
      ::= { rbnEntityTypeContainer 31 }

rbnEntContainerSPSC1FanTray OBJECT-IDENTITY
      STATUS current
      DESCRIPTION
              "The definitive identifier for the Smart Packet SP-SC1
              fan tray container (slot) entity."
      ::= { rbnEntityTypeContainer 32 }

rbnEntContainerSPSC1PowerModule OBJECT-IDENTITY
      STATUS current
      DESCRIPTION
              "The definitive identifier for the Smart Packet SP-SC1
              power module container (slot) entity."
      ::= { rbnEntityTypeContainer 33 }

rbnEntContainerSPSC1Data OBJECT-IDENTITY
      STATUS current
      DESCRIPTION
              "The definitive identifier for the Smart Packet SP-SC1
              data container (slot) entity."
      ::= { rbnEntityTypeContainer 34 }

rbnEntityTypePowerSupply OBJECT-IDENTITY
      STATUS  current
      DESCRIPTION
              "The top-level category identifier for entities which
              reside in the ENTITY-MIB PhysicalClass *powerSupply*"
      ::= { rbnEntities 6 }

rbnEntPowerSupplyUnknown OBJECT-IDENTITY
      STATUS  current
      DESCRIPTION
              "The identifier use to represent any power supply which
              cannot be definitively identified, probably due to the
              fact that its configuration EEPROM is not valid"
      ::= { rbnEntityTypePowerSupply 1 }

rbnEntPowerSupplySMS1000AC OBJECT-IDENTITY
      STATUS  current
      DESCRIPTION
              "The definitive identifier for the
              SMS 1000 AC Power Supply, model PS-1K-AC"
      ::= { rbnEntityTypePowerSupply 2 }

rbnEntPowerSupplySMS1000DC OBJECT-IDENTITY
      STATUS  current
      DESCRIPTION
              "The definitive identifier for the
              SMS 1000 DC Power Supply, model PS-1K-DC"
      ::= { rbnEntityTypePowerSupply 3 }

rbnEntPowerSupplySMS500AC OBJECT-IDENTITY
      STATUS  current
      DESCRIPTION
              "The definitive identifier for the
              SMS 500 AC Power Supply"
      ::= { rbnEntityTypePowerSupply 4 }

rbnEntPowerSupplySMS500DC OBJECT-IDENTITY
      STATUS  current
      DESCRIPTION
              "The definitive identifier for the
              SMS 500 DC Power Supply"
      ::= { rbnEntityTypePowerSupply 5 }

rbnEntPowerSupplySMS1800AC OBJECT-IDENTITY
      STATUS  current
      DESCRIPTION
              "The definitive identifier for the
              SMS 1800 AC Power Supply"
      ::= { rbnEntityTypePowerSupply 6 }

rbnEntPowerSupplySMS1800DC OBJECT-IDENTITY
      STATUS  current
      DESCRIPTION
              "The definitive identifier for the
              SMS 1800 DC Power Supply"
      ::= { rbnEntityTypePowerSupply 7 }

-- %DNP% --rbnEntPowerSupplySMS2800AC OBJECT-IDENTITY
-- %DNP% --      STATUS  obsolete
-- %DNP% --      DESCRIPTION
-- %DNP% --              "The definitive identifier for the
-- %DNP% --              SMS 2800 AC Power Supply"
-- %DNP% --      ::= { rbnEntityTypePowerSupply 8 }

-- %DNP% --rbnEntPowerSupplySMS2800DC OBJECT-IDENTITY
-- %DNP% --      STATUS  obsolete
-- %DNP% --      DESCRIPTION
-- %DNP% --              "The definitive identifier for the
-- %DNP% --              SMS 2800 DC Power Supply"
-- %DNP% --      ::= { rbnEntityTypePowerSupply 9 }

rbnEntPowerModuleSSR OBJECT-IDENTITY
      STATUS  current
      DESCRIPTION
              "The definitive identifier for the Smart Services Router
              Power Supply Module"
      ::= { rbnEntityTypePowerSupply 10 }

rbnEntPowerModuleSPSC1AC OBJECT-IDENTITY
      STATUS  current
      DESCRIPTION
              "The definitive identifier for the Smart Packet SP-SC1
              AC Power Supply Module"
      ::= { rbnEntityTypePowerSupply 11 }

rbnEntPowerModuleSPSC1DC OBJECT-IDENTITY
      STATUS  current
      DESCRIPTION
              "The definitive identifier for the Smart Packet SP-SC1
              DC Power Supply Module"
      ::= { rbnEntityTypePowerSupply 12 }

rbnEntityTypeFan OBJECT-IDENTITY
      STATUS  current
      DESCRIPTION
              "The top-level category identifier for entities which
              reside in the ENTITY-MIB PhysicalClass *fan*"
      ::= { rbnEntities 7 }

rbnEntFanSE800 OBJECT-IDENTITY
      STATUS  current
      DESCRIPTION
              "The definitive identifier for the
              SE 800 Fan Tray"
      ::= { rbnEntityTypeFan 1 }

rbnEntFanSE400 OBJECT-IDENTITY
      STATUS  current
      DESCRIPTION
              "The definitive identifier for the
              SE 400 Fan Tray"
      ::= { rbnEntityTypeFan 2 }

rbnEntFanSE1200 OBJECT-IDENTITY
      STATUS  current
      DESCRIPTION
              "The definitive identifier for the
              SE 1200 Fan Tray"
      ::= { rbnEntityTypeFan 3 }

rbnEntFanSM480 OBJECT-IDENTITY
      STATUS  current
      DESCRIPTION
              "The definitive identifier for the
              SM 480 Fan Tray"
      ::= { rbnEntityTypeFan 4 }

rbnEntFanSE600 OBJECT-IDENTITY
      STATUS  current
      DESCRIPTION
              "The definitive identifier for the
              SE 600 Fan Tray"
      ::= { rbnEntityTypeFan 5 }

rbnEntFanSM240 OBJECT-IDENTITY
      STATUS  current
      DESCRIPTION
              "The definitive identifier for the
              SM240 Fan Tray"
      ::= { rbnEntityTypeFan 6 }

rbnEntFanSE1200H OBJECT-IDENTITY
      STATUS  current
      DESCRIPTION
              "The definitive identifier for the SE1200H Fan Tray"
      ::= { rbnEntityTypeFan 7 }

rbnEntFanTraySSR OBJECT-IDENTITY
      STATUS  current
      DESCRIPTION
              "The definitive identifier for the Smart Services Router
              Fan Tray"
      ::= { rbnEntityTypeFan 8 }

rbnEntFanTraySPSC1 OBJECT-IDENTITY
      STATUS  current
      DESCRIPTION
              "The definitive identifier for the Smart Packet Fan Tray"
      ::= { rbnEntityTypeFan 9 }

rbnEntFanTrayAlarmIOSPSC1 OBJECT-IDENTITY
      STATUS  current
      DESCRIPTION
              "The definitive identifier for the Smart Packet Fan Tray
              with DB-15 Alarm IO"
      ::= { rbnEntityTypeFan 10 }
            
rbnEntityTypeSensor OBJECT-IDENTITY
      STATUS  current
      DESCRIPTION
              "The top-level category identifier for entities which
              reside in the ENTITY-MIB PhysicalClass *sensor*"
      ::= { rbnEntities 8 }

rbnEntSensorAlarmSE400 OBJECT-IDENTITY
      STATUS  current
      DESCRIPTION
              "The definitive identifier for the
              SE 400 Alarm Card"
      ::= { rbnEntityTypeSensor 1 }

rbnEntSensorAlarmSE600 OBJECT-IDENTITY
      STATUS  current
      DESCRIPTION
              "The definitive identifier for the
              SE 600 Alarm Card"
      ::= { rbnEntityTypeSensor 2 }

rbnEntSensorAlarmSM240 OBJECT-IDENTITY
      STATUS  current
      DESCRIPTION
              "The definitive identifier for the
              SM 240 Alarm Card"
      ::= { rbnEntityTypeSensor 3 }

rbnEntityTypeModule OBJECT-IDENTITY
      STATUS  current
      DESCRIPTION
              "The top-level category identifier for entities which
              reside in the ENTITY-MIB PhysicalClass *module*"
      ::= { rbnEntities 9 }

rbnEntModuleUnknown OBJECT-IDENTITY
      STATUS  current
      DESCRIPTION
              "The identifier use to represent any module which
              cannot be definitively identified, probably due
              to the fact that its configuration EEPROM is not
              valid"
      ::= { rbnEntityTypeModule 1 }

rbnEntModuleSMSCE1 OBJECT-IDENTITY
      STATUS  current
      DESCRIPTION
              "The definitive identifier for the
              SMS Control Engine 1"
      ::= { rbnEntityTypeModule 16 }

rbnEntModuleSMSCE2 OBJECT-IDENTITY
      STATUS  current
      DESCRIPTION
              "The definitive identifier for the
              SMS Control Engine 2"
      ::= { rbnEntityTypeModule 17 }

rbnEntModuleSMSCE3 OBJECT-IDENTITY
      STATUS  current
      DESCRIPTION
              "The definitive identifier for the
              SMS Control Engine 3"
      ::= { rbnEntityTypeModule 18 }

rbnEntModuleSMSFE1 OBJECT-IDENTITY
      STATUS  current
      DESCRIPTION
              "The definitive identifier for the
              SMS Forwarding Engine 1"
      ::= { rbnEntityTypeModule 10 }

rbnEntModuleSMSFE2 OBJECT-IDENTITY
      STATUS  current
      DESCRIPTION
              "The definitive identifier for the
              SMS Forwarding Engine 2"
      ::= { rbnEntityTypeModule 12 }

rbnEntModuleSMSFE3 OBJECT-IDENTITY
      STATUS  current
      DESCRIPTION
              "The definitive identifier for the
              SMS Forwarding Engine 3"
      ::= { rbnEntityTypeModule 35 }

rbnEntModuleSMSXFE OBJECT-IDENTITY
      STATUS  current
      DESCRIPTION
              "The definitive identifier for the
              SMS Extended Forwarding Engine"
      ::= { rbnEntityTypeModule 40 }

rbnEntModuleSMSFABRIC OBJECT-IDENTITY
      STATUS  current
      DESCRIPTION
              "The definitive identifier for the
              SMS Switch Fabric module"
      ::= { rbnEntityTypeModule 29 }

rbnEntModuleSMSTIMING OBJECT-IDENTITY
      STATUS  current
      DESCRIPTION
              "The definitive identifier for the
              SMS Timing module"
      ::= { rbnEntityTypeModule 31 }

rbnEntModuleSMSCM OBJECT-IDENTITY
      STATUS  current
      DESCRIPTION
              "The definitive identifier for the
              SMS Connection Manager module"
      ::= { rbnEntityTypeModule 30 }

rbnEntModuleSMSSM OBJECT-IDENTITY
      STATUS  current
      DESCRIPTION
              "The definitive identifier for the
              SMS System Manager module"
      ::= { rbnEntityTypeModule 32 }

-- %DNP% --rbnEntModuleSMSCSM OBJECT-IDENTITY
-- %DNP% --      STATUS  obsolete
-- %DNP% --      DESCRIPTION
-- %DNP% --              "The definitive identifier for the
-- %DNP% --              Connection System Manager (CSM) module"
-- %DNP% --      ::= { rbnEntityTypeModule 36 }

rbnEntModuleSMSEIM OBJECT-IDENTITY
      STATUS  current
      DESCRIPTION
              "The definitive identifier for the
              SMS 10/100BaseT Ethernet Interface Module"
      ::= { rbnEntityTypeModule 6 }

rbnEntModuleSMSGIGEIM OBJECT-IDENTITY
      STATUS  current
      DESCRIPTION
              "The definitive identifier for the
              SMS Gigabit Ethernet Interface Module"
      ::= { rbnEntityTypeModule 26 }

rbnEntModuleSMSAIMDS3 OBJECT-IDENTITY
      STATUS  current
      DESCRIPTION
              "The definitive identifier for the
              SMS ATM DS3 Interface Module"
      ::= { rbnEntityTypeModule 4 }

rbnEntModuleSMSPIME3 OBJECT-IDENTITY
      STATUS  current
      DESCRIPTION
              "The definitive identifier for the
              SMS Packet E3 Interface Module"
      ::= { rbnEntityTypeModule 8 }

rbnEntModuleSMSPIME1 OBJECT-IDENTITY
      STATUS  current
      DESCRIPTION
              "The definitive identifier for the
              SMS Packet E1 Interface Module"
      ::= { rbnEntityTypeModule 22 }

rbnEntModuleSMSAIME3 OBJECT-IDENTITY
      STATUS  current
      DESCRIPTION
              "The definitive identifier for the
              SMS ATM E3 Interface Module"
      ::= { rbnEntityTypeModule 5 }

rbnEntModuleSMSAIME1 OBJECT-IDENTITY
      STATUS  current
      DESCRIPTION
              "The definitive identifier for the
              SMS ATM E1 Interface Module"
      ::= { rbnEntityTypeModule 23 }

rbnEntModuleSMSAIMT1 OBJECT-IDENTITY
      STATUS  current
      DESCRIPTION
              "The definitive identifier for the
              SMS ATM T1 Interface Module"
      ::= { rbnEntityTypeModule 20 }

rbnEntModuleSMSAIMOC3 OBJECT-IDENTITY
      STATUS  current
      DESCRIPTION
              "The definitive identifier for the
              SMS ATM OC3 Interface Module"
      ::= { rbnEntityTypeModule 3 }

rbnEntModuleSMSAIMOC12 OBJECT-IDENTITY
      STATUS  current
      DESCRIPTION
              "The definitive identifier for the
              SMS ATM OC12 Interface Module"
      ::= { rbnEntityTypeModule 27 }

rbnEntModuleSMSPOSOC3 OBJECT-IDENTITY
      STATUS  current
      DESCRIPTION
              "The definitive identifier for the
              SMS POS OC3 Interface Module"
      ::= { rbnEntityTypeModule 24 }

rbnEntModuleSMSPOSOC12 OBJECT-IDENTITY
      STATUS  current
      DESCRIPTION
              "The definitive identifier for the
              SMS POS OC12 Interface Module"
      ::= { rbnEntityTypeModule 25 }

rbnEntModuleSMSIPSEC OBJECT-IDENTITY
      STATUS  current
      DESCRIPTION
              "The definitive identifier for the
              SMS IPSEC Interface Module"
      ::= { rbnEntityTypeModule 28 }

rbnEntModuleSMSPIMDS1 OBJECT-IDENTITY
      STATUS  current
      DESCRIPTION
              "The definitive identifier for the
              SMS Packet DS1 Interface Module"
      ::= { rbnEntityTypeModule 14 }

rbnEntModuleSMSPIMDS3 OBJECT-IDENTITY
      STATUS  current
      DESCRIPTION
              "The definitive identifier for the
              SMS Packet DS3 Interface Module"
      ::= { rbnEntityTypeModule 7 }

rbnEntModuleSMSPIMCDS3 OBJECT-IDENTITY
      STATUS  current
      DESCRIPTION
              "The definitive identifier for the
              SMS Channelized DS3 Interface Module"
      ::= { rbnEntityTypeModule 15 }

rbnEntModuleSMSPIMHSSI OBJECT-IDENTITY
      STATUS  current
      DESCRIPTION
              "The definitive identifier for the
              SMS Packet HSSI Interface Module"
      ::= { rbnEntityTypeModule 9 }

rbnEntModuleSEXC OBJECT-IDENTITY
      STATUS  current
      DESCRIPTION
              "The definitive identifier for the
              SE Cross Connect Module"
      ::= { rbnEntityTypeModule 41 }

rbnEntModuleSEEIM OBJECT-IDENTITY
      STATUS  current
      DESCRIPTION
              "The definitive identifier for the
              SE 10/100BaseT Ethernet Interface Module"
      ::= { rbnEntityTypeModule 42}

rbnEntModuleSEGIGEIM OBJECT-IDENTITY
      STATUS  current
      DESCRIPTION
              "The definitive identifier for the
              SE Gigabit Ethernet Interface Module"
      ::= { rbnEntityTypeModule 43 }

rbnEntModuleSEPOSOC12 OBJECT-IDENTITY
      STATUS  current
      DESCRIPTION
              "The definitive identifier for the
              SE POS OC12 Interface Module"
      ::= { rbnEntityTypeModule 44 }

rbnEntModuleSEPOSOC48 OBJECT-IDENTITY
      STATUS  current
      DESCRIPTION
              "The definitive identifier for the
              SE POS OC48 Interface Module"
      ::= { rbnEntityTypeModule 45 }

rbnEntModuleSEPOSOC3 OBJECT-IDENTITY
      STATUS  current
      DESCRIPTION
              "The definitive identifier for the
              SE POS OC3 Interface Module"
      ::= { rbnEntityTypeModule 46 }

rbnEntModuleSECHOC12DS1 OBJECT-IDENTITY
      STATUS  current
      DESCRIPTION
              "The definitive identifier for the
              SE Channelized OC12 DS1 Interface Module"
      ::= { rbnEntityTypeModule 47 }

rbnEntModuleSECHOC12DS3 OBJECT-IDENTITY
      STATUS  current
      DESCRIPTION
              "The definitive identifier for the
              SE Channelized OC12 DS3 Interface Module"
      ::= { rbnEntityTypeModule 48 }

rbnEntModuleSEAIMOC3 OBJECT-IDENTITY
      STATUS  current
      DESCRIPTION
              "The definitive identifier for the
              SE ATM OC3 Interface Module"
      ::= { rbnEntityTypeModule 49 }

rbnEntModuleSEAIMOC12 OBJECT-IDENTITY
      STATUS  current
      DESCRIPTION
              "The definitive identifier for the
              SE ATM OC12 Interface Module"
      ::= { rbnEntityTypeModule 50 }

rbnEntModuleSECHDS3 OBJECT-IDENTITY
      STATUS  current
      DESCRIPTION
              "The definitive identifier for the
              SE Channelized DS3 Interface Module"
      ::= { rbnEntityTypeModule 51 }

rbnEntModuleSEDS3 OBJECT-IDENTITY
      STATUS  current
      DESCRIPTION
              "The definitive identifier for the
              SE DS3 Interface Module"
      ::= { rbnEntityTypeModule 52 }

rbnEntModuleSEAIMDS3 OBJECT-IDENTITY
      STATUS  current
      DESCRIPTION
              "The definitive identifier for the
              SE ATM DS3 Interface Module"
      ::= { rbnEntityTypeModule 53 }

rbnEntModuleSECHSTM1E1 OBJECT-IDENTITY
      STATUS  current
      DESCRIPTION
              "The definitive identifier for the
              SE Channelized STM-1 to E1 Interface Module"
      ::= { rbnEntityTypeModule 54 }

rbnEntModuleSEE1 OBJECT-IDENTITY
      STATUS  current
      DESCRIPTION
              "The definitive identifier for the
              SE E1 Interface Module"
      ::= { rbnEntityTypeModule 55 }

rbnEntModuleSEXC3 OBJECT-IDENTITY
      STATUS  current
      DESCRIPTION
              "The definitive identifier for the
              SE Cross Connect Module Version 3"
      ::= { rbnEntityTypeModule 56 }

rbnEntModuleSEE3 OBJECT-IDENTITY
      STATUS  current
      DESCRIPTION
              "The definitive identifier for the
              SE E3 Interface Module"
      ::= { rbnEntityTypeModule 57 }

rbnEntModuleSEAIMOC12E OBJECT-IDENTITY
      STATUS  current
      DESCRIPTION
              "The definitive identifier for the
              SE ATM OC12 Enhanced Interface Module"
      ::= { rbnEntityTypeModule 58 }

rbnEntModuleSEGIGETM OBJECT-IDENTITY
      STATUS  current
      DESCRIPTION
              "The definitive identifier for the
              SE Gigabit Ethernet with Traffic Management Module"
      ::= { rbnEntityTypeModule 59 }

rbnEntModuleSE10GIGEIM OBJECT-IDENTITY
      STATUS  current
      DESCRIPTION
              "The definitive identifier for the
              SE 10 Gigabit Ethernet Interface Module"
      ::= { rbnEntityTypeModule 60 }

rbnEntModuleSE100XC OBJECT-IDENTITY
      STATUS  current
      DESCRIPTION
              "The definitive identifier for the
              SE 100 Cross Connect Module"
      ::= { rbnEntityTypeModule 61 }

rbnEntModuleSE100EMIC OBJECT-IDENTITY
      STATUS  current
      DESCRIPTION
              "The definitive identifier for the
              SE 100 10/100BaseT Ethernet Media Interface Connect
              Module"
      ::= { rbnEntityTypeModule 62 }

rbnEntModuleSE100FXMIC OBJECT-IDENTITY
      STATUS  current
      DESCRIPTION
              "The definitive identifier for the
              SE 100 FX-100 Ethernet Media Interface Connect Module"
      ::= { rbnEntityTypeModule 63 }

rbnEntModuleSE100GERJMIC OBJECT-IDENTITY
      STATUS  current
      DESCRIPTION
              "The definitive identifier for the
              SE 100 Gigabit Ethernet Media Interface Connect Module"
      ::= { rbnEntityTypeModule 64 }

rbnEntModuleSE100GEFXMIC OBJECT-IDENTITY
      STATUS  current
      DESCRIPTION
              "The definitive identifier for the
              SE 100 FX-1000 Ethernet Media Interface Connect Module"
      ::= { rbnEntityTypeModule 65 }

rbnEntModuleSEXC4 OBJECT-IDENTITY
      STATUS  current
      DESCRIPTION
              "The definitive identifier for the
              SE Cross Connect Module Version 4"
      ::= { rbnEntityTypeModule 66 }

rbnEntModuleSE100AIMOC3MIC OBJECT-IDENTITY
      STATUS  current
      DESCRIPTION
              "The definitive identifier for the
              SE 100 2-port ATM OC3 Media Interface Connect Module"
      ::= { rbnEntityTypeModule 67 }

rbnEntModuleSEASE OBJECT-IDENTITY
      STATUS  current
      DESCRIPTION
              "The definitive identifier for the
              SE Advanced Services Engine Module"
      ::= { rbnEntityTypeModule 68 }

rbnEntModuleSEFE60GE2 OBJECT-IDENTITY
      STATUS  current
      DESCRIPTION
              "The definitive identifier for the
              FE60GE2 Ethernet Interface Module"
      ::= { rbnEntityTypeModule 69 }

rbnEntModuleSEPOSOC192 OBJECT-IDENTITY
      STATUS  current
      DESCRIPTION
              "The definitive identifier for the
              SE POS OC192 Media Interface Module"
      ::= { rbnEntityTypeModule 70 }

rbnEntModuleSE5PortGIGE OBJECT-IDENTITY
      STATUS  current
      DESCRIPTION
              "The definitive identifier for the 5 port PPA2
             based Gigabit Ethernet Media Interface Connect Module"
      ::= { rbnEntityTypeModule 71 }

rbnEntModuleSE20PortGIGE OBJECT-IDENTITY
      STATUS  current
      DESCRIPTION
              "The definitive identifier for the 20 port PPA3/PMA3
              based Gigabit Ethernet Media Interface Connect Module"
      ::= { rbnEntityTypeModule 72 }

rbnEntModuleSE4Port10GIGE OBJECT-IDENTITY
      STATUS  current
      DESCRIPTION
              "The definitive identifier for the 4 port PPA3/PMA3
              based 10 Gigabit Ethernet Media Interface Connect Module"
      ::= { rbnEntityTypeModule 73 }

rbnEntModuleSE10GIGETM OBJECT-IDENTITY
      STATUS  current
      DESCRIPTION
              "The definitive identifier for the SE 10 Gigabit
              Ethernet with Traffic Management Interface Module"
      ::= { rbnEntityTypeModule 74 }

rbnEntModuleSESSE OBJECT-IDENTITY
      STATUS  current
      DESCRIPTION
              "The definitive identifier for the
              SmartEdge Server Engine(Winchester)"
      ::= { rbnEntityTypeModule 75 }

rbnEntModuleSE10PortGIGEDDR2 OBJECT-IDENTITY
      STATUS  current
      DESCRIPTION
               "The definitive identifier for the
               SE 10 Gigabit Ethernet with DDR Upgrade"
      ::= { rbnEntityTypeModule 76 }

rbnEntModuleSE4PortOC48 OBJECT-IDENTITY
      STATUS current
      DESCRIPTION
              "The definitive identifier for the
              SE 4 port OC-48 POS  Media Interface Module"
      ::= { rbnEntityTypeModule 77 }

rbnEntModuleSE8PortOC3 OBJECT-IDENTITY
      STATUS current
      DESCRIPTION
              "The definitive identifier for the
              SE 8 port OC-3 ATM Media Interface Module"
      ::= { rbnEntityTypeModule 78 }

rbnEntModuleSE8OR2PORTCHOC3OC12 OBJECT-IDENTITY
      STATUS current
      DESCRIPTION
              "The definitive identifier for the SE Channelized
              OC3/STM1 or OC12/STM4 8 or 2 Port Interface Module"
      ::= { rbnEntityTypeModule 79 }

rbnEntModuleSEASE2 OBJECT-IDENTITY
      STATUS  current
      DESCRIPTION
              "The definitive identifier for the SE Advanced Services
              Engine 2 Module"
      ::= { rbnEntityTypeModule 80 }

rbnEntModuleSE1Port10GEOC192 OBJECT-IDENTITY
      STATUS  current
      DESCRIPTION
              "The definitive identifier for the SE version of
              a line card supporting  either 10GE (gigabit ethernet)
              or OC192 but not both."
      ::= { rbnEntityTypeModule 81 }

rbnEntModuleSEPos8xOC3 OBJECT-IDENTITY
      STATUS current
      DESCRIPTION
              "The definitive identifier for the
              SE 8 port OC-3 POS PPA2 Media Interface Module"
      ::= { rbnEntityTypeModule 82 }

rbnEntModuleSEPos4xOC12 OBJECT-IDENTITY
      STATUS current
      DESCRIPTION
              "The definitive identifier for the
              SE 4 port OC-12 POS PPA2 Media Interface Module"
      ::= { rbnEntityTypeModule 83 }

rbnEntModuleSEAtm2xOC12 OBJECT-IDENTITY
      STATUS current
      DESCRIPTION
              "The definitive identifier for the
              SE 2 port OC-12 ATM PPA2  Media Interface Module"
      ::= { rbnEntityTypeModule 84 }

rbnEntModuleSM10GIGEIM OBJECT-IDENTITY
      STATUS  current
      DESCRIPTION
              "The definitive identifier for the
              SM 10 Gigabit Ethernet Interface Module"
      ::= { rbnEntityTypeModule 101 }

rbnEntModuleSMRP2 OBJECT-IDENTITY
      STATUS  current
      DESCRIPTION
              "The definitive identifier for the
              SM Routing Processor Module version 2 "
      ::= { rbnEntityTypeModule 102 }

rbnEntModuleSMGIGEIM OBJECT-IDENTITY
      STATUS  current
      DESCRIPTION
              "The definitive identifier for the
              SM Gigabit Ethernet Interface Module"
      ::= { rbnEntityTypeModule 104 }

rbnEntModuleSMGIGETM OBJECT-IDENTITY
      STATUS  current
      DESCRIPTION
              "The definitive identifier for the
              SM Gigabit Ethernet with Traffic Management Module"
      ::= { rbnEntityTypeModule 105 }

rbnEntModuleSM10GIGETM OBJECT-IDENTITY
      STATUS  current
      DESCRIPTION
              "The definitive identifier for the
              SM 10 Gigabit Ethernet with Traffic Management
              Module"
      ::= { rbnEntityTypeModule 106 }

rbnEntModuleSMFE60GE2 OBJECT-IDENTITY
      STATUS  current
      DESCRIPTION
              "The definitive identifier for the
              SM FE60GE2 Ethernet Interface Module"
      ::= { rbnEntityTypeModule 107 }

rbnEntModuleSM20PortGIGE OBJECT-IDENTITY
      STATUS  current
      DESCRIPTION
              "The definitive identifier for the
              SM 20 port PPA3/PMA3 based Gigabit Ethernet
              Media Interface Connect Module"
      ::= { rbnEntityTypeModule 108 }

rbnEntModuleSM4Port10GIGE OBJECT-IDENTITY
      STATUS  current
      DESCRIPTION
              "The definitive identifier for the
              SM 4 port PPA3/PMA3 based 10 Gigabit Ethernet
              Media Interface Connect Module"
      ::= { rbnEntityTypeModule 109 }

rbnEntModuleSM10PortGIGEDDR2 OBJECT-IDENTITY
      STATUS  current
      DESCRIPTION
               "The definitive identifier for the SM version of
               the 10 Gigabit Ethernet with DDR Upgrade"
      ::= { rbnEntityTypeModule 110 }

rbnEntModuleSM1Port10GEOC192 OBJECT-IDENTITY
      STATUS  current
      DESCRIPTION
               "The definitive identifier for the SM version of
               a line card supporting either 10GE (gigabit ethernet)
               or OC192 but not both."
      ::= { rbnEntityTypeModule 111 }

rbnEntModuleSM8OR2PORTCHOC3OC12 OBJECT-IDENTITY
      STATUS current
      DESCRIPTION
              "The definitive identifier for the SM Channelized
              OC3/STM1 or OC12/STM4 8 or 2 Port Interface Module"
      ::= { rbnEntityTypeModule 112 }

rbnEntModuleSSRALSW OBJECT-IDENTITY
      STATUS  current
      DESCRIPTION
              "The definitive identifier for the Smart Services Router
              Alarm with Switch Fabric module."
      ::= { rbnEntityTypeModule 201 }

rbnEntModuleSSRRPSW OBJECT-IDENTITY
      STATUS  current
      DESCRIPTION
              "The definitive identifier for the Smart Services Router
              Route Processor with Switch Fabric module."
      ::= { rbnEntityTypeModule 202 }

rbnEntModuleSSRSW OBJECT-IDENTITY
      STATUS  current
      DESCRIPTION
              "The definitive identifier for the Smart Services Router
              Switch module."
      ::= { rbnEntityTypeModule 203 }

rbnEntModuleSSR40Port1GE OBJECT-IDENTITY
      STATUS  current
      DESCRIPTION
              "The definitive identifier for the Smart Services Router
              40 port 1 Gigabit Ethernet Interface Module."
      ::= { rbnEntityTypeModule 204 }

rbnEntModuleSSR10Port10GE OBJECT-IDENTITY
      STATUS  current
      DESCRIPTION
              "The definitive identifier for the Smart Services Router
              10 port 10 Gigabit Ethernet Interface Module."
      ::= { rbnEntityTypeModule 205 }

rbnEntModuleSSC1 OBJECT-IDENTITY
      STATUS current
      DESCRIPTION
              "The definitive identifier for the Smart Services Card
              with Storage (SSC1)."
      ::= { rbnEntityTypeModule 207 }

rbnEntModuleSSC2 OBJECT-IDENTITY
      STATUS  current
      DESCRIPTION
              "The definitive identifier for the Smart Services Card
              with Pluggable Daughter Cards (SSC2)."
      ::= { rbnEntityTypeModule 208 }

rbnEntModuleSSR20Port1GEor10GE OBJECT-IDENTITY
      STATUS  current
      DESCRIPTION
              "The definitive identifier for the Smart Services Router
              20 port 1 Gigabit or 10 Gigabit Ethernet Interface Module."
      ::= { rbnEntityTypeModule 209 }

rbnEntModuleSSR2Port40GEor100GE OBJECT-IDENTITY
      STATUS  current
      DESCRIPTION
              "The definitive identifier for the Smart Services Router
              1 port 100 Gigabit or 2 port 40 Gigabit Ethernet Interface Module."
      ::= { rbnEntityTypeModule 210 }

rbnEntModuleSSR20Port1GEor4Port10GE OBJECT-IDENTITY
      STATUS  current
      DESCRIPTION
              "The definitive identifier for the Smart Services Router
              4 port 10 Gigabit or
              20 port 1 Gigabit + 2 port 10 Gigabit or
              24 port 1 gigabit Ethernet Interface Module."
      ::= { rbnEntityTypeModule 211 }

rbnEntModuleSPSC1SC OBJECT-IDENTITY
      STATUS  current
      DESCRIPTION
              "The definitive identifier for the Smart Packet SP-SC1
              System Controller module."
      ::= { rbnEntityTypeModule 212 }

rbnEntModuleSPSC11Port10GE OBJECT-IDENTITY
      STATUS  current
      DESCRIPTION
              "The definitive identifier for the Smart Packet SP-SC1
              1 port 10 Gigabit Ethernet Interface Service Module."
      ::= { rbnEntityTypeModule 213 }

rbnEntModuleSPSC18PortCES OBJECT-IDENTITY
      STATUS  current
      DESCRIPTION
              "The definitive identifier for the Smart Packet SP-SC1
              8 port T1 or E1 CES Service Module."
      ::= { rbnEntityTypeModule 214 }

rbnEntModuleSPSC116Port1GE OBJECT-IDENTITY
      STATUS  current
      DESCRIPTION
              "The definitive identifier for the Smart Packet SP-SC1
              16 port 1 Gigabit Ethernet Interface Service Module
              (physically located in SC card)."
      ::= { rbnEntityTypeModule 215 }

rbnEntModuleSPSC120and2Port1and10GE OBJECT-IDENTITY
      STATUS  current
      DESCRIPTION
              "The definitive identifier for the Smart Packet SP-SC1
              20 port 1 Gigabit  + 2 port 10 Gigabit
              Ethernet Interface Service Module (physically
              located in SC card)."
      ::= { rbnEntityTypeModule 216 }

rbnEntModuleSSR20PortOC3orOC12orOC48orOC192 OBJECT-IDENTITY
      STATUS  current
      DESCRIPTION
              "The definitive identifier for the Smart Services Router
              4 port OC192 and 16 port OC3 or OC12 or OC48 
              POS Interface Module."
      ::= { rbnEntityTypeModule 217 }

rbnEntityTypePort OBJECT-IDENTITY
      STATUS  current
      DESCRIPTION
              "The top-level category identifier for entities which
              reside in the ENTITY-MIB PhysicalClass *port*"
      ::= { rbnEntities 10 }

rbnEntPortUnknown OBJECT-IDENTITY
      STATUS  current
      DESCRIPTION
              "The identifier use to represent any module which
              cannot be definitively identified, probably due
              to the fact that its configuration EEPROM is not
              valid"
      ::= { rbnEntityTypePort 1 }

rbnEntPortSMSCE1MGMT OBJECT-IDENTITY
      STATUS  current
      DESCRIPTION
              "The definitive identifier for the
              SMS Control Engine 1, Local Management Port"
      ::= { rbnEntityTypePort 16 }

rbnEntPortSMSCE2MGMT OBJECT-IDENTITY
      STATUS  current
      DESCRIPTION
              "The definitive identifier for the
              SMS Control Engine 2, Local Management Port"
      ::= { rbnEntityTypePort 17 }

rbnEntPortSMSCE3MGMT OBJECT-IDENTITY
      STATUS  current
      DESCRIPTION
              "The definitive identifier for the
              SMS Control Engine 3, Local Management Port"
      ::= { rbnEntityTypePort 18 }

-- %DNP% --rbnEntPortSMSCSMMGMT OBJECT-IDENTITY
-- %DNP% --      STATUS  obsolete
-- %DNP% --      DESCRIPTION
-- %DNP% --              "The definitive identifier for the
-- %DNP% --              Connection System Manager (CSM), Local Management Port"
-- %DNP% --      ::= { rbnEntityTypePort 36 }

rbnEntPortSMSEIM OBJECT-IDENTITY
      STATUS  current
      DESCRIPTION
              "The definitive identifier for the
              SMS 10/100BaseT Ethernet Interface Port"
      ::= { rbnEntityTypePort 6 }

rbnEntPortSMSGIGEIM OBJECT-IDENTITY
      STATUS  current
      DESCRIPTION
              "The definitive identifier for the
              SMS Gigabit Ethernet Interface Port"
      ::= { rbnEntityTypePort 26 }

rbnEntPortSMSAIMDS3 OBJECT-IDENTITY
      STATUS  current
      DESCRIPTION
              "The definitive identifier for the
              SMS ATM DS3 Interface Port"
      ::= { rbnEntityTypePort 4 }

rbnEntPortSMSPIME3 OBJECT-IDENTITY
      STATUS  current
      DESCRIPTION
              "The definitive identifier for the
              SMS Packet E3 Interface Port"
      ::= { rbnEntityTypePort 8 }

rbnEntPortSMSPIME1 OBJECT-IDENTITY
      STATUS  current
      DESCRIPTION
              "The definitive identifier for the
              SMS Packet E1 Interface Port"
      ::= { rbnEntityTypePort 22 }

rbnEntPortSMSAIME3 OBJECT-IDENTITY
      STATUS  current
      DESCRIPTION
              "The definitive identifier for the
              SMS ATM E3 Interface Port"
      ::= { rbnEntityTypePort 5 }

rbnEntPortSMSAIME1 OBJECT-IDENTITY
      STATUS  current
      DESCRIPTION
              "The definitive identifier for the
              SMS ATM E1 Interface Port"
      ::= { rbnEntityTypePort 23 }

rbnEntPortSMSAIMT1 OBJECT-IDENTITY
      STATUS  current
      DESCRIPTION
              "The definitive identifier for the
              SMS ATM T1 Interface Port"
      ::= { rbnEntityTypePort 20 }

rbnEntPortSMSAIMOC3 OBJECT-IDENTITY
      STATUS  current
      DESCRIPTION
              "The definitive identifier for the
              SMS ATM OC3 Interface Port"
      ::= { rbnEntityTypePort 3 }

rbnEntPortSMSAIMOC12 OBJECT-IDENTITY
      STATUS  current
      DESCRIPTION
              "The definitive identifier for the
              SMS ATM OC12 Interface Port"
      ::= { rbnEntityTypePort 27 }

rbnEntPortSMSPOSOC3 OBJECT-IDENTITY
      STATUS  current
      DESCRIPTION
              "The definitive identifier for the
              SMS POS OC3 Interface Port"
      ::= { rbnEntityTypePort 24 }

rbnEntPortSMSPOSOC12 OBJECT-IDENTITY
      STATUS  current
      DESCRIPTION
              "The definitive identifier for the
              SMS POS OC12 Interface Port"
      ::= { rbnEntityTypePort 25 }

rbnEntPortSMSPIMDS1 OBJECT-IDENTITY
      STATUS  current
      DESCRIPTION
              "The definitive identifier for the
              SMS Packet DS1 Interface Port"
      ::= { rbnEntityTypePort 14 }

rbnEntPortSMSPIMDS3 OBJECT-IDENTITY
      STATUS  current
      DESCRIPTION
              "The definitive identifier for the
              SMS Packet DS3 Interface Port"
      ::= { rbnEntityTypePort 7 }

rbnEntPortSMSPIMCDS3 OBJECT-IDENTITY
      STATUS  current
      DESCRIPTION
              "The definitive identifier for the
              SMS Channelized DS3 Interface Port"
      ::= { rbnEntityTypePort 15 }

rbnEntPortSMSPIMHSSI OBJECT-IDENTITY
      STATUS  current
      DESCRIPTION
              "The definitive identifier for the
              SMS Packet HSSI Interface Port"
      ::= { rbnEntityTypePort 9 }

rbnEntPortSEXCMGMT OBJECT-IDENTITY
      STATUS  current
      DESCRIPTION
              "The definitive identifier for the
              SE Cross Connect, Local Management Port"
      ::= { rbnEntityTypePort 41 }

rbnEntPortSEEIM OBJECT-IDENTITY
      STATUS  current
      DESCRIPTION
              "The definitive identifier for the
              SE 10/100BaseT Ethernet Interface Port"
      ::= { rbnEntityTypePort 42 }

rbnEntPortSEGIGEIM OBJECT-IDENTITY
      STATUS  current
      DESCRIPTION
              "The definitive identifier for the
              SE Gigabit Ethernet Interface Port"
      ::= { rbnEntityTypePort 43 }

rbnEntPortSEPOSOC12 OBJECT-IDENTITY
      STATUS  current
      DESCRIPTION
              "The definitive identifier for the
              SE POS OC12 Interface Port"
      ::= { rbnEntityTypePort 44 }

rbnEntPortSEPOSOC48 OBJECT-IDENTITY
      STATUS  current
      DESCRIPTION
              "The definitive identifier for the
              SE POS OC48 Interface Port"
      ::= { rbnEntityTypePort 45 }

rbnEntPortSEPOSOC3 OBJECT-IDENTITY
      STATUS  current
      DESCRIPTION
              "The definitive identifier for the
              SE POS OC3 Interface Port"
      ::= { rbnEntityTypePort 46 }

rbnEntPortSECHOC12DS1 OBJECT-IDENTITY
      STATUS  current
      DESCRIPTION
              "The definitive identifier for the
              SE Channelized OC12 DS1 Interface Port"
      ::= { rbnEntityTypePort 47 }

rbnEntPortSECHOC12DS3 OBJECT-IDENTITY
      STATUS  current
      DESCRIPTION
              "The definitive identifier for the
              SE Channelized OC12 DS3 Interface Port"
      ::= { rbnEntityTypePort 48 }

rbnEntPortSEAIMOC3 OBJECT-IDENTITY
      STATUS  current
      DESCRIPTION
              "The definitive identifier for the
              SE ATM OC3 Interface Port"
      ::= { rbnEntityTypePort 49 }

rbnEntPortSEAIMOC12 OBJECT-IDENTITY
      STATUS  current
      DESCRIPTION
              "The definitive identifier for the
              SE ATM OC12 Interface Port"
      ::= { rbnEntityTypePort 50 }

rbnEntPortSECHDS3 OBJECT-IDENTITY
      STATUS  current
      DESCRIPTION
              "The definitive identifier for the
              SE Channelized DS3 Interface Port"
      ::= { rbnEntityTypePort 51 }

rbnEntPortSEDS3 OBJECT-IDENTITY
      STATUS  current
      DESCRIPTION
              "The definitive identifier for the
              SE DS3 Interface Port"
      ::= { rbnEntityTypePort 52 }

rbnEntPortSEAIMDS3 OBJECT-IDENTITY
      STATUS  current
      DESCRIPTION
              "The definitive identifier for the
              SE ATM DS3 Interface Port"
      ::= { rbnEntityTypePort 53 }

rbnEntPortSECHSTM1E1 OBJECT-IDENTITY
      STATUS  current
      DESCRIPTION
              "The definitive identifier for the
              SE Channelized STM-1 to E1 Interface Port"
      ::= { rbnEntityTypePort 54 }

rbnEntPortSEE1 OBJECT-IDENTITY
      STATUS  current
      DESCRIPTION
              "The definitive identifier for the
              SE E1 Interface Port"
      ::= { rbnEntityTypePort 55 }

rbnEntPortSEXC3MGMT OBJECT-IDENTITY
      STATUS  current
      DESCRIPTION
              "The definitive identifier for the
              SE Cross Connect 3, Local Management Port"
      ::= { rbnEntityTypePort 56 }

rbnEntPortSEE3 OBJECT-IDENTITY
      STATUS  current
      DESCRIPTION
              "The definitive identifier for the
              SE E3 Interface Port"
      ::= { rbnEntityTypePort 57 }

rbnEntPortSEAIMOC12E OBJECT-IDENTITY
      STATUS  current
      DESCRIPTION
              "The definitive identifier for the
              SE ATM OC12 Enhanced Interface Port"
      ::= { rbnEntityTypePort 58 }

rbnEntPortSEGIGETM OBJECT-IDENTITY
      STATUS  current
      DESCRIPTION
              "The definitive identifier for the
              SE Gigabit Ethernet with Traffic Management Interface
              Port"
      ::= { rbnEntityTypePort 59 }

rbnEntPortSE10GIGEIM OBJECT-IDENTITY
      STATUS  current
      DESCRIPTION
              "The definitive identifier for the
              SE 10 Gigabit Ethernet Interface Port"
      ::= { rbnEntityTypePort 60 }

rbnEntPortSE100XCMGMT OBJECT-IDENTITY
      STATUS  current
      DESCRIPTION
              "The definitive identifier for the
              SE 100 Cross Connect, Local Management Port"
      ::= { rbnEntityTypePort 61 }

rbnEntPortSE100EIM OBJECT-IDENTITY
      STATUS  current
      DESCRIPTION
              "The definitive identifier for the
              SE 100 10/100BaseT Ethernet Interface Port"
      ::= { rbnEntityTypePort 62 }

rbnEntPortSE100FXIM OBJECT-IDENTITY
      STATUS  current
      DESCRIPTION
              "The definitive identifier for the
              SE 100 FX-100 Ethernet Interface Port"
      ::= { rbnEntityTypePort 63 }

rbnEntPortSE100GERJIM OBJECT-IDENTITY
      STATUS  current
      DESCRIPTION
              "The definitive identifier for the
              SE 100 Gigabit Ethernet Interface Port"
      ::= { rbnEntityTypePort 64 }

rbnEntPortSE100GEFXIM OBJECT-IDENTITY
      STATUS  current
      DESCRIPTION
              "The definitive identifier for the
              SE 100 FX-1000 Ethernet Interface Port"
      ::= { rbnEntityTypePort 65 }

rbnEntPortSEXC4MGMT OBJECT-IDENTITY
      STATUS  current
      DESCRIPTION
              "The definitive identifier for the
              SE Cross Connect 4, Local Management Port"
      ::= { rbnEntityTypePort 66 }


rbnEntPortSE100AIMOC3 OBJECT-IDENTITY
      STATUS  current
      DESCRIPTION
              "The definitive identifier for the
              SE 100 ATM OC3 Interface Port"
      ::= { rbnEntityTypePort 67 }

rbnEntPortSEPOSOC192 OBJECT-IDENTITY
      STATUS  current
      DESCRIPTION
              "The definitive identifier for the
              SE POS OC192 Interface Port"
      ::= { rbnEntityTypePort 68 }

rbnEntPortSE10GIGETM OBJECT-IDENTITY
      STATUS  current
      DESCRIPTION
              "The definitive identifier for the SE 10 Gigabit
              Ethernet with Traffic Management Interface Port"
      ::= { rbnEntityTypePort 69 }

rbnEntPortSECHOC3OC12 OBJECT-IDENTITY
      STATUS  current
      DESCRIPTION
              "The definitive identifier for the SE Channelized
              OC3/STM1 or OC12/STM4 Interface Port"
      ::= { rbnEntityTypePort 70 }

rbnEntPortSECHOC3 OBJECT-IDENTITY
      STATUS  current
      DESCRIPTION
              "The definitive identifier for the SE Channelized
              OC3/STM1 Interface Port"
      ::= { rbnEntityTypePort 71 }

rbnEntPortSM10GIGEIM OBJECT-IDENTITY
      STATUS  current
      DESCRIPTION
              "The definitive identifier for the
              SM 10 Gigabit Ethernet Interface Port"
      ::= { rbnEntityTypePort 101 }

rbnEntPortSMRPMGMT OBJECT-IDENTITY
      STATUS  current
      DESCRIPTION
              "The definitive identifier for the
                SM Routing Processor, Local Management Port"
      ::= { rbnEntityTypePort 103 }

rbnEntPortSMGIGEIM OBJECT-IDENTITY
      STATUS  current
      DESCRIPTION
              "The definitive identifier for the
              SM Gigabit Ethernet Interface Port"
      ::= { rbnEntityTypePort 104 }

rbnEntPortSMGIGETM OBJECT-IDENTITY
      STATUS  current
      DESCRIPTION
              "The definitive identifier for the SM Gigabit
              Ethernet with Traffic Management Interface
              Port"
      ::= { rbnEntityTypePort 105 }

rbnEntPortSM10GIGETM OBJECT-IDENTITY
      STATUS  current
      DESCRIPTION
              "The definitive identifier for the SM 10 Gigabit
              Ethernet with Traffic Management port"
      ::= { rbnEntityTypePort 106 }

rbnEntPortSMEIM OBJECT-IDENTITY
      STATUS  current
      DESCRIPTION
              "The definitive identifier for the
              SM 10/100BaseT Ethernet Interface Port"
      ::= { rbnEntityTypePort 107 }

rbnEntPortSMCHOC3OC12 OBJECT-IDENTITY
      STATUS  current
      DESCRIPTION
              "The definitive identifier for the SM Channelized
              OC3/STM1 or OC12/STM4 Interface Port"
      ::= { rbnEntityTypePort 108 }

rbnEntPortSMCHOC3 OBJECT-IDENTITY
      STATUS  current
      DESCRIPTION
              "The definitive identifier for the SM Channelized
              OC3/STM1 Interface Port"
      ::= { rbnEntityTypePort 109 }

rbnEntPortSSR1GE OBJECT-IDENTITY
      STATUS  current
      DESCRIPTION
              "The definitive identifier for the Smart Services Router
              1 Gigabit Ethernet Interface Port"
      ::= { rbnEntityTypePort 201 }

rbnEntPortSSR10GE OBJECT-IDENTITY
      STATUS  current
      DESCRIPTION
              "The definitive identifier for the Smart Services Router
              10 Gigabit Ethernet Interface Port"
      ::= { rbnEntityTypePort 202 }

rbnEntPortSSRRPSWMgmt OBJECT-IDENTITY
      STATUS  current
      DESCRIPTION
              "The definitive identifier for the Smart Services Router
              Route Processor with Switch Fabric card Local Management Port"
      ::= { rbnEntityTypePort 203 }

rbnEntPortSSR100GE OBJECT-IDENTITY
      STATUS  current
      DESCRIPTION
              "The definitive identifier for the Smart Services Router
               100 Gigabit Ethernet Interface Port"
      ::= { rbnEntityTypePort 204 }

rbnEntPortSSR40GE OBJECT-IDENTITY
      STATUS  current
      DESCRIPTION
              "The definitive identifier for the Smart Services Router
               40 Gigabit Ethernet Interface Port"
      ::= { rbnEntityTypePort 205 }

rbnEntPortSSR40GEor100GE OBJECT-IDENTITY
      STATUS  current
      DESCRIPTION
              "The definitive identifier for the Smart Services Router
               40 or 100 Gigabit Ethernet Interface Port"
      ::= { rbnEntityTypePort 206 }

rbnEntPortSPSC11GE OBJECT-IDENTITY
      STATUS  current
      DESCRIPTION
              "The definitive identifier for the Smart Packet SP-SC1
              1 Gigabit Ethernet Interface Port"
      ::= { rbnEntityTypePort 207 }

rbnEntPortSPSC110GE OBJECT-IDENTITY
      STATUS  current
      DESCRIPTION
              "The definitive identifier for the Smart Packet SP-SC1
              10 Gigabit Ethernet Interface Port"
      ::= { rbnEntityTypePort 208 }

rbnEntPortSPSC1SCMgmt OBJECT-IDENTITY
      STATUS  current
      DESCRIPTION
              "The definitive identifier for the Smart Packet SP-SC1
              System Controller Local Management Port"
      ::= { rbnEntityTypePort 209 }

rbnEntPortSPSC1AlarmIn OBJECT-IDENTITY
      STATUS  current
      DESCRIPTION
              "The definitive identifier for the Smart Packet SP-SC1
              Input Alarm Port"
      ::= { rbnEntityTypePort 210 }

rbnEntPortSPSC1AlarmOut OBJECT-IDENTITY
      STATUS  current
      DESCRIPTION
              "The definitive identifier for the Smart Packet SP-SC1
              Output Alarm Port"
      ::= { rbnEntityTypePort 211 }
                
rbnEntPortSSR20POSOCorOC12orOC48orOC192 OBJECT-IDENTITY
      STATUS  current
      DESCRIPTION
              "The definitive identifier for the Smart Services Router
               OC3 or OC12 or OC48 or OC192 POS Interface Port"
      ::= { rbnEntityTypePort 212 }

rbnEntityTypeStack OBJECT-IDENTITY
      STATUS  current
      DESCRIPTION
              "The top-level category identifier for entities which
              reside in the ENTITY-MIB PhysicalClass *module*"
      ::= { rbnEntities 11 }

rbnEntityTypeCPU OBJECT-IDENTITY
      STATUS  current
      DESCRIPTION
              "The top-level category identifier for entities which
              reside in the ENTITY-MIB PhysicalClass *module*"
      ::= { rbnEntities 12 }

rbnEntCpuUnknown OBJECT-IDENTITY
      STATUS  current
      DESCRIPTION
              "The identifier use to represent any cpu which
              cannot be definitively identified."
      ::= { rbnEntityTypeCPU 1 }

rbnEntCpuOcteon OBJECT-IDENTITY
STATUS  current
      DESCRIPTION
              "The definitive identifier for the RedBack Networks
              Octeon Processor."
      ::= { rbnEntityTypeCPU 2 }

rbnEntityTypeDisk OBJECT-IDENTITY
      STATUS  current
      DESCRIPTION
              "The top-level category identifier for entities which
              reside in the ENTITY-MIB PhysicalClass *module*"
      ::= { rbnEntities 13 }

rbnEntDiskUnknown OBJECT-IDENTITY
      STATUS  current
      DESCRIPTION
              "The identifier use to represent any disk which
              cannot be definitively identified."
      ::= { rbnEntityTypeDisk 1 }

rbnEntDiskSSE OBJECT-IDENTITY
      STATUS  current
      DESCRIPTION
              "The definitive identifier for the
              removable disks on SSE card."
      ::= { rbnEntityTypeDisk 2 }

rbnEntityTypeMemory OBJECT-IDENTITY
      STATUS  current
      DESCRIPTION
              "The top-level category identifier for entities which
              reside in the ENTITY-MIB PhysicalClass *module*"
      ::= { rbnEntities 14 }

END
