-- *****************************************************************
-- ERICSSON-ROUTER-LDAP-CAP        LDAP Mib Capabilities
--
-- Copyright (c) 2017 Ericsson AB.
-- All rights reserved.
--
-- *****************************************************************

ERICSSON-ROUTER-LDAP-CAP DEFINITIONS ::= BEGIN

IMPORTS

    MODULE-IDENTITY
            FROM SNMPv2-SMI
    AGENT-CAPABILITIES
            FROM SNMPv2-CONF
    eriRouterCapabilities
            FROM ERICSSON-ROUTER-SMI;

eriRouterLdapMibCap MODULE-IDENTITY
    LAST-UPDATED    "201709261600Z" -- Sept 26, 2017
    ORGANIZATION    "Ericsson AB"
    CONTACT-INFO
        "    Ericsson, AB.

        Postal:    100 Headquarters Dr
            San Jose, CA  95134
            USA

         Phone:    +1 408 750 5000
           Fax: +1 408 750 5599"
    DESCRIPTION
        "The Agent Capabilities of the LDAP MIB."

    REVISION    "201709261600Z" -- Sept 26, 2017
    DESCRIPTION
        "Initial version."

    ::= { eriRouterCapabilities 123 }

eriRouterLdapMibCap1 AGENT-CAPABILITIES
    PRODUCT-RELEASE    "IPOS 17.2 [SSR]"
    STATUS        current
    DESCRIPTION    "ERICSSON-ROUTER-LDAP-MIB capabilities"
    SUPPORTS    ERICSSON-ROUTER-LDAP-MIB
    INCLUDES {
        eriRouterLdapObjectsGroup,
        eriRouterLdapNotifyGroup
    }

    ::= { eriRouterLdapMibCap 1 }

END
