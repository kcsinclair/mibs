-- %DNP%
-- %DNP% $Source: /cvsroot/pkt/sw/se/xc/bsd/config/snmp/mibs/Attic/RBN-ICR-CAP.my,v $
-- *****************************************************************
-- RBN-CPG-MIB    Ericsson Inter Chassis Resilience(ICR) MIB 
--
-- Copyright (c) 2011 Ericsson AB.
-- All rights reserved.
--
-- *****************************************************************

RBN-ICR-CAP DEFINITIONS ::= BEGIN

IMPORTS
        MODULE-IDENTITY
                FROM SNMPv2-SMI
        AGENT-CAPABILITIES
                FROM SNMPv2-CONF
        rbnCapabilities
                FROM RBN-SMI;

rbnIcrCap MODULE-IDENTITY
    LAST-UPDATED    "201508110000Z" -- Aug 11, 2015
    ORGANIZATION    "Ericsson AB."
    CONTACT-INFO
            "       Ericsson, Inc.

            Postal: 100 Headquarters Drive
                    San Jose, CA  95134-1370
                    USA

             Phone: +1 408 750 5000
               Fax: +1 408 750 5599"

    DESCRIPTION
        "The Agent Capabilities of Inter Chassis Resilience(ICR) MIB
        implementation."

    REVISION "201508110000Z" -- Aug 11, 2015
    DESCRIPTION
        "Added a new OID: rbnIcrCap2."

    REVISION    "201101100000Z" -- Jan 10, 2011
    DESCRIPTION
           "Initial version"
        ::= { rbnCapabilities 101 }

rbnIcrCap1 AGENT-CAPABILITIES
    PRODUCT-RELEASE "SEOS 11.1.x"
    STATUS          current
    DESCRIPTION     "RBN-ICR-MIB capabilities"
    SUPPORTS        RBN-ICR-MIB
    INCLUDES {
        rbnIcrGroup,
        rbnIcrNotificationObjectGroup,
        rbnIcrNotificationGroup
    }

    VARIATION   rbnIcrLocalAddressType 
    ACCESS      read-only 
    DESCRIPTION
        "Write access is not supported."

    VARIATION   rbnIcrLocalAddress 
    ACCESS      read-only 
    DESCRIPTION
        "Write access is not supported."

    VARIATION   rbnIcrLocalPort 
    ACCESS      read-only 
    DESCRIPTION
        "Write access is not supported."

    VARIATION   rbnIcrPeerAddressType 
    ACCESS      read-only 
    DESCRIPTION
        "Write access is not supported."

    VARIATION   rbnIcrPeerAddress 
    ACCESS      read-only 
    DESCRIPTION
        "Write access is not supported."

    VARIATION   rbnIcrPeerPort 
    ACCESS      read-only 
    DESCRIPTION
        "Write access is not supported."

    VARIATION   rbnIcrPriority 
    ACCESS      read-only 
    DESCRIPTION
        "Write access is not supported."

    VARIATION   rbnIcrKeepAliveInterval
    ACCESS      read-only 
    DESCRIPTION
        "Write access is not supported."

    VARIATION   rbnIcrHoldTime 
    ACCESS      read-only 
    DESCRIPTION
        "Write access is not supported."

    VARIATION   rbnIcrAdminStatus 
    ACCESS      read-only
    DESCRIPTION
        "Writ access is not supported."

    VARIATION   rbnIcrRowStatus 
    ACCESS      read-only
    DESCRIPTION
        "Write access is not supported."
    ::= { rbnIcrCap 1 }


rbnIcrCap2 AGENT-CAPABILITIES
    PRODUCT-RELEASE "SSR "
    STATUS          current
    DESCRIPTION     "RBN-ICR-MIB capabilities"
    SUPPORTS        RBN-ICR-MIB
    INCLUDES {
        rbnIcrGroup,
        rbnIcrNotificationObjectGroup,
        rbnIcrNotificationGroup
    }

    VARIATION   rbnIcrLocalAddressType
    ACCESS      read-only
    DESCRIPTION
        "Write access is not supported."

    VARIATION   rbnIcrLocalAddress
    ACCESS      read-only
    DESCRIPTION
        "Write access is not supported."

    VARIATION   rbnIcrLocalPort
    ACCESS      read-only
    DESCRIPTION
        "Write access is not supported."

    VARIATION   rbnIcrPeerAddressType
    ACCESS      read-only
    DESCRIPTION
        "Write access is not supported."

    VARIATION   rbnIcrPeerAddress
    ACCESS      read-only
    DESCRIPTION
        "Write access is not supported."

    VARIATION   rbnIcrPeerPort
    ACCESS      read-only
    DESCRIPTION
        "Write access is not supported."

    VARIATION   rbnIcrPriority
    ACCESS      read-only
    DESCRIPTION
        "Write access is not supported."

    VARIATION   rbnIcrKeepAliveInterval
    ACCESS      read-only
    DESCRIPTION
        "Write access is not supported."

    VARIATION   rbnIcrHoldTime
    ACCESS      read-only
    DESCRIPTION
        "Write access is not supported."

    VARIATION   rbnIcrAdminStatus
    ACCESS      read-only
    DESCRIPTION
        "Writ access is not supported."

    VARIATION   rbnIcrRowStatus
    ACCESS      read-only
    DESCRIPTION
        "Write access is not supported."
    ::= { rbnIcrCap 2 }

END
