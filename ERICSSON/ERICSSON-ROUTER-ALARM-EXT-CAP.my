-- %DNP% $Id: ERICSSON-ROUTER-ALARM-EXT-CAP.my,v 1.1.6.3 2011/06/15 18:19:45 danielhe Exp $
-- %DNP% $Source: /cvsroot/pkt/sw/se/xc/bsd/config/snmp/mibs/Attic/ERICSSON-ROUTER-ALARM-EXT-CAP.my,v $
-- *****************************************************************
-- ERICSSON-ROUTER-ALARM-EXT-CAP.my  
--
-- Copyright (c) 2009, 2011, 2015 Ericsson AB.
-- All rights reserved.
-- 
-- *****************************************************************

ERICSSON-ROUTER-ALARM-EXT-CAP DEFINITIONS ::= BEGIN

IMPORTS
	MODULE-IDENTITY
		FROM SNMPv2-SMI
	AGENT-CAPABILITIES
		FROM SNMPv2-CONF
	eriRouterCapabilities
		FROM ERICSSON-ROUTER-SMI;

eriRouterAlarmExtCap MODULE-IDENTITY
	LAST-UPDATED    "201501141800Z" -- Jan 14, 2015
	ORGANIZATION	"Ericsson, Inc."
	CONTACT-INFO
		"	Ericsson, Inc.

                Postal: 100 Headquarters Dr
                        San Jose, CA  95134
                        USA

                 Phone: +1 408 570 5000
                   Fax: +1 408 570 5599

                "
	DESCRIPTION
		"The Agent Capabilities of the 
		implementation of the ERICSSON-ROUTER-ALARM-EXT-MIB

                If this MIB implementation is platform-dependent,
                the PRODUCT-RELEASE clause contains Ericsson SEOS version and
                at least one of the following Ericsson product families:
                    [SE]  SmartEdge Multi-service Edge Router (MSER) family
                    [SM]  SM family of Metro Ethernet Service Transport platforms
                    [SSR] Smart Service Router (SSR) family"

        REVISION        "201501141800Z" -- Jan 14, 2015
        DESCRIPTION
                "Updated RBN/rbn/Rbn as ERICSSON-ROUTER/eriRouter/EriRouter
                to migrate RBN MIB to ERICSSON MIB."

        REVISION        "201106150000Z" -- Jun 15, 2011
        DESCRIPTION
                "Update DESCRIPTION clause of MODULE-IDENTITY
                 and PRODUCT-RELEASE clause of AGENT-CAPABILITIES."
        
	REVISION	"200910231800Z" -- Oct 23, 2009
	DESCRIPTION
		"Initial version"
	::= { eriRouterCapabilities 94 }

eriRouterAlarmExtCap1 AGENT-CAPABILITIES
	PRODUCT-RELEASE	"SEOS 6.3"
	STATUS		current
	DESCRIPTION	"ERICSSON-ROUTER-ALARM-EXT-MIB capabilities"
	SUPPORTS	ERICSSON-ROUTER-ALARM-EXT-MIB
	INCLUDES {
            eriRouterAlarmModelGroup,
            eriRouterAlarmClearGroup
	}

	::= { eriRouterAlarmExtCap 1 }

eriRouterAlarmExtCap2 AGENT-CAPABILITIES
        PRODUCT-RELEASE "IPOS 15.3"
        STATUS          current
        DESCRIPTION     "ERICSSON-ROUTER-ALARM-EXT-MIB capabilities"
        SUPPORTS        ERICSSON-ROUTER-ALARM-EXT-MIB
        INCLUDES {
            eriRouterAlarmModelGroup,
            eriRouterAlarmClearGroup,
            eriRouterAlarmActivesGroup,
            eriRouterAlarmActiveVariableGroup
        }

        ::= { eriRouterAlarmExtCap 2 }

END
