-- %DNP% $Id: RBN-RADIUS-CAP.my,v 1.1.2.4.154.4 2011/06/15 18:19:46 danielhe Exp $
-- %DNP% $Source: /cvsroot/pkt/sw/se/xc/bsd/config/snmp/mibs/Attic/RBN-RADIUS-CAP.my,v $
-- *****************************************************************
-- RBN-RADIUS-CAP              RADIUS MIB Capabilities
--
-- Copyright (c) 2003-2006, 2010-2011 Ericsson AB.
-- All rights reserved.
--
-- *****************************************************************

RBN-RADIUS-CAP DEFINITIONS ::= BEGIN

IMPORTS
    MODULE-IDENTITY     FROM SNMPv2-SMI
    AGENT-CAPABILITIES  FROM SNMPv2-CONF
    rbnCapabilities     FROM RBN-SMI;

rbnRadiusCap MODULE-IDENTITY
        LAST-UPDATED    "201106150000Z" -- Jun 15, 2011
        ORGANIZATION    "Ericsson AB."
        CONTACT-INFO
                "       Ericsson AB.

                Postal: 100 Headquarters Dr
                        San Jose, CA  95134
                        USA

                 Phone: +1 408 750 5000
                   Fax: +1 408 750 5599
                "
    DESCRIPTION
        "The Agent Capabilities of the RADIUS MIB.

        If this MIB implementation is platform-dependent,
        the PRODUCT-RELEASE clause contains Ericsson SEOS version and
        at least one of the following Ericsson product families:
            [SE]  SmartEdge Multi-service Edge Router (MSER) family
            [SM]  SM family of Metro Ethernet Service Transport platforms
            [SSR] Smart Service Router (SSR) family"

        REVISION        "201106150000Z" -- Jun 15, 2011
        DESCRIPTION
            "Update DESCRIPTION clause of MODULE-IDENTITY
            and PRODUCT-RELEASE clause of AGENT-CAPABILITIES."
    REVISION    "201011010000Z" -- Nov 1, 2010
    DESCRIPTION
        "Modified PRODUCT-RELEASE clause for consistent naming.
         Updated CONTACT-INFO."

    REVISION    "200503291700Z" -- March 29, 2005
    DESCRIPTION
        "add rbnRadiusCap3."

    REVISION    "200403021800Z" -- March 2, 2004
    DESCRIPTION
        "add rbnRadiusCap2."

    REVISION    "200312160000Z" -- Dec 16, 2003
    DESCRIPTION
        "Initial version."
    ::= { rbnCapabilities 59 }

rbnRadiusCap1 AGENT-CAPABILITIES
    PRODUCT-RELEASE "SEOS 2.6.x"
    STATUS          current
    DESCRIPTION     "RBN-RADIUS-MIB capabilities"
    SUPPORTS        RBN-RADIUS-MIB
    INCLUDES {
        rbnRadiusAuthGroup,
        rbnRadiusAcctGroup,
        rbnRadiusNotifyGroup,
        rbnRadiusAuthNotifyGroup,
        rbnRadiusAcctNotifyGroup
    }

    VARIATION rbnRadiusAuthPktTimeout
    ACCESS    read-only
    DESCRIPTION
        "Write access is not allowed."

    VARIATION rbnRadiusAuthSrvTimeout
    ACCESS    read-only
    DESCRIPTION
        "Write access is not allowed."

    VARIATION rbnRadiusAuthDeadtime
    ACCESS    read-only
    DESCRIPTION
        "Write access is not allowed."

    VARIATION rbnRadiusAuthTries
    ACCESS    read-only
    DESCRIPTION
        "Write access is not allowed."

    VARIATION rbnRadiusAcctPktTimeout
    ACCESS    read-only
    DESCRIPTION
        "Write access is not allowed."

    VARIATION rbnRadiusAcctSrvTimeout
    ACCESS    read-only
    DESCRIPTION
        "Write access is not allowed."

    VARIATION rbnRadiusAcctDeadtime
    ACCESS    read-only
    DESCRIPTION
        "Write access is not allowed."

    VARIATION rbnRadiusAcctTries
    ACCESS    read-only
    DESCRIPTION
        "Write access is not allowed."

    VARIATION rbnRadiusReason
    SYNTAX    INTEGER { responding(1), serverTimeout(3) }
    DESCRIPTION
        "The only reason a server may change state is when it starts
         responding and when a server-level timeout occurs."

    ::= { rbnRadiusCap 1 }

rbnRadiusCap2 AGENT-CAPABILITIES
    PRODUCT-RELEASE "AOS 6.0.10.x"
    STATUS          current
    DESCRIPTION     "RBN-RADIUS-MIB capabilities"
    SUPPORTS        RBN-RADIUS-MIB
    INCLUDES {
        rbnRadiusNotifyGroup,
        rbnRadiusAuthNotifyGroup,
        rbnRadiusAcctNotifyGroup
    }

    ::= { rbnRadiusCap 2 }

rbnRadiusCap3 AGENT-CAPABILITIES
    PRODUCT-RELEASE "SEOS 4.0.5.x [SE]"
    STATUS          current
    DESCRIPTION     "RBN-RADIUS-MIB capabilities"
    SUPPORTS        RBN-RADIUS-MIB
    INCLUDES {
        rbnRadiusAuthGroup2,
        rbnRadiusAcctGroup2,
        rbnRadiusNotifyGroup,
        rbnRadiusAuthNotifyGroup,
        rbnRadiusAcctNotifyGroup
    }

    VARIATION rbnRadiusAuthPktTimeout
    ACCESS    read-only
    DESCRIPTION
        "Write access is not allowed."

    VARIATION rbnRadiusAuthSrvTimeout
    ACCESS    read-only
    DESCRIPTION
        "Write access is not allowed."

    VARIATION rbnRadiusAuthDeadtime
    ACCESS    read-only
    DESCRIPTION
        "Write access is not allowed."

    VARIATION rbnRadiusAuthTries
    ACCESS    read-only
    DESCRIPTION
        "Write access is not allowed."

    VARIATION rbnRadiusAuthStripDomain
    ACCESS    read-only
    DESCRIPTION
        "Write access is not allowed."

    VARIATION rbnRadiusAcctPktTimeout
    ACCESS    read-only
    DESCRIPTION
        "Write access is not allowed."

    VARIATION rbnRadiusAcctSrvTimeout
    ACCESS    read-only
    DESCRIPTION
        "Write access is not allowed."

    VARIATION rbnRadiusAcctDeadtime
    ACCESS    read-only
    DESCRIPTION
        "Write access is not allowed."

    VARIATION rbnRadiusAcctTries
    ACCESS    read-only
    DESCRIPTION
        "Write access is not allowed."

    VARIATION rbnRadiusAcctStripDomain
    ACCESS    read-only
    DESCRIPTION
        "Write access is not allowed."

    VARIATION rbnRadiusReason
    SYNTAX    INTEGER { responding(1), serverTimeout(3) }
    DESCRIPTION
        "The only reason a server may change state is when it starts
         responding and when a server-level timeout occurs."

    ::= { rbnRadiusCap 3 }

END
