-- %DNP% $Id: RBN-CONFIG-FILE-CAP.my,v 1.1.2.5.336.4 2011/06/15 18:19:45 danielhe Exp $
-- %DNP% $Source: /cvsroot/pkt/sw/se/xc/bsd/config/snmp/mibs/Attic/RBN-CONFIG-FILE-CAP.my,v $
-- *****************************************************************
-- RBN-CONFIG-FILE-CAP	    Config File Mib Capabilities
--
-- Copyright (c) 2001-2002, 2004, 2010-2011 Ericsson AB
-- All rights reserved.
-- 
-- *****************************************************************

RBN-CONFIG-FILE-CAP DEFINITIONS ::= BEGIN

IMPORTS

    MODULE-IDENTITY
            FROM SNMPv2-SMI
    AGENT-CAPABILITIES
            FROM SNMPv2-CONF
    
    rbnCapabilities
            FROM RBN-SMI;

rbnConfigFileMibCap MODULE-IDENTITY
    LAST-UPDATED    "201106150000Z" -- Jun 15, 2011
    ORGANIZATION    "Ericsson Inc."
    CONTACT-INFO
            "       Ericsson, Inc.

            Postal: 100 Headquarters Dr.
                    San Jose, CA  95134
                    USA

             Phone: +1 408 750 5000
               Fax: +1 408 750 5599
            "
    DESCRIPTION
	    "The Agent Capabilities of the Config File MIB.

            If this MIB implementation is platform-dependent,
            the PRODUCT-RELEASE clause contains Ericsson SEOS version and
            at least one of the following Ericsson product families:
                [SE]  SmartEdge Multi-service Edge Router (MSER) family
                [SM]  SM family of Metro Ethernet Service Transport platforms
                [SSR] Smart Service Router (SSR) family"

        REVISION        "201106150000Z" -- Jun 15, 2011
        DESCRIPTION
            "Update DESCRIPTION clause of MODULE-IDENTITY
            and PRODUCT-RELEASE clause of AGENT-CAPABILITIES."
    REVISION    "201011010000Z" -- Nov 1, 2010
    DESCRIPTION
        "Modified PRODUCT-RELEASE clause for consistent naming.
         Updated CONTACT-INFO."

    REVISION    "200408120000Z" -- August 12, 2004
    DESCRIPTION
	    "Added new OID:
	        rbnConfigFileMibCap3."
    REVISION	"200210280000Z" -- October 28, 2002
    DESCRIPTION
	    "Updated CONTACT-INFO.
	     Added new OID:
		rbnConfigFileMibCap2."
    REVISION	"200110100000Z" -- October 10, 2001
    DESCRIPTION
	    "Initial version."
    ::= { rbnCapabilities 36 }

rbnConfigFileMibCap1 AGENT-CAPABILITIES
    PRODUCT-RELEASE	"AOS 5.1.X.X"
    STATUS		current
    DESCRIPTION	"RBN-CONFIG-FILE-MIB capabilities"
    SUPPORTS	RBN-CONFIG-FILE-MIB
    INCLUDES {
        rcfJobGroup,
	rcfJobNotifyGroup
    }

    VARIATION rcfJobIpAddressType
	WRITE-SYNTAX INTEGER { ipv4(1) }
	DESCRIPTION	
	"Restrict InetAddressType to ipv4(1)."

    VARIATION rcfJobUsername
        DESCRIPTION
        "Each character must be printable (the posix function isprint()
        returns true for each character)."

    VARIATION rcfJobPassword
        DESCRIPTION
        "Each character must be printable (the posix function isprint()
        returns true for each character)."

    VARIATION rcfJobFilename
        DESCRIPTION
        "Each character must be printable (the posix function isprint()
        returns true for each character)."

    VARIATION rcfJobErrorMsgs
        DESCRIPTION
        "Each character must be printable (the posix function isprint()
        returns true for each character) or the newline character."

    VARIATION rcfJobOwner
        DESCRIPTION
        "Each character must be printable (the posix function isprint()
        returns true for each character)."

    ::= { rbnConfigFileMibCap 1 }
	
rbnConfigFileMibCap2 AGENT-CAPABILITIES
    PRODUCT-RELEASE	"SEOS 2.3.4"
    STATUS		current
    DESCRIPTION	"RBN-CONFIG-FILE-MIB capabilities"
    SUPPORTS	RBN-CONFIG-FILE-MIB
    INCLUDES {
        rcfJobGroup
    }

    VARIATION rcfJobOp
	WRITE-SYNTAX INTEGER { save(1) }
	DESCRIPTION
	"Restrict to save(1)."

    VARIATION rcfJobProtocol
	WRITE-SYNTAX INTEGER { tftp(1), ftp(2) }
	DEFVAL { tftp }
	DESCRIPTION
	"Restrict to tftp(1), ftp(2). local(0) not supported."

    VARIATION rcfJobIpAddressType
	WRITE-SYNTAX INTEGER { ipv4(1) }
	DESCRIPTION
	"Restrict InetAddressType to ipv4(1)."

    VARIATION rcfJobUsername
        DESCRIPTION
        "Each character must be printable (the posix function isprint()
        returns true for each character)."

    VARIATION rcfJobPassword
        DESCRIPTION
        "Each character must be printable (the posix function isprint()
        returns true for each character)."

    VARIATION rcfJobFilename
        DESCRIPTION
        "Each character must be printable (the posix function isprint()
        returns true for each character)."

    VARIATION rcfJobPassiveMode
	ACCESS	not-implemented
	DESCRIPTION
	"Object not supported."

    VARIATION rcfJobStopAtLine
	ACCESS	not-implemented
	DESCRIPTION
	"Object not supported."

    VARIATION rcfJobErrorMsgs
        DESCRIPTION
        "Each character must be printable (the posix function isprint()
        returns true for each character) or the newline character."

    VARIATION rcfJobNotifyOnCompletion
	ACCESS	not-implemented
	DESCRIPTION
	"Object not supported."

    VARIATION rcfJobOwner
        DESCRIPTION
        "Each character must be printable (the posix function isprint()
        returns true for each character)."

    ::= { rbnConfigFileMibCap 2 }

rbnConfigFileMibCap3 AGENT-CAPABILITIES
    PRODUCT-RELEASE     "SEOS 2.6.5.X [SE]; SEOS 6.3.X [SM]; SEOS 11.1.X [SSR]"
    STATUS              current
    DESCRIPTION "RBN-CONFIG-FILE-MIB capabilities"
    SUPPORTS    RBN-CONFIG-FILE-MIB
    INCLUDES {
        rcfJobGroup,
        rcfJobNotifyGroup
    }

    VARIATION rcfJobIpAddressType
        WRITE-SYNTAX INTEGER { ipv4(1) }
        DESCRIPTION
        "Restrict InetAddressType to ipv4(1)."

    VARIATION rcfJobUsername
        DESCRIPTION
        "Each character must be printable (the posix function isprint()
        returns true for each character)."

    VARIATION rcfJobPassword
        DESCRIPTION
        "Each character must be printable (the posix function isprint()
        returns true for each character)."

    VARIATION rcfJobFilename
        DESCRIPTION
        "Each character must be printable (the posix function isprint()
        returns true for each character)."

    VARIATION rcfJobPassiveMode
        ACCESS  not-implemented
        DESCRIPTION
        "Object not supported."

    VARIATION rcfJobErrorMsgs
        DESCRIPTION
        "Each character must be printable (the posix function isprint()
        returns true for each character) or the newline character."

    VARIATION rcfJobOwner
        DESCRIPTION
        "Each character must be printable (the posix function isprint()
        returns true for each character)."

    ::= { rbnConfigFileMibCap 3 }

END
