-- $Id: RBN-MEDIA-GATEWAY-CAP.my,v 1.1.6.2 2011/06/15 18:19:46 danielhe Exp $ 
-- $Source: /cvsroot/pkt/sw/se/xc/bsd/config/snmp/mibs/Attic/RBN-MEDIA-GATEWAY-CAP.my,v $
-- *****************************************************************
-- RBN-MEDIA_GATEWAY-CAP: RBN-MEDIA_GATEWAY-MIB Agent Capabilities
--
-- Copyright (c) 2009-2010 Ericsson AB
-- All rights reserved.
--
-- *****************************************************************

RBN-MEDIA-GATEWAY-CAP DEFINITIONS ::= BEGIN

IMPORTS
        MODULE-IDENTITY
                FROM SNMPv2-SMI
        AGENT-CAPABILITIES
                FROM SNMPv2-CONF
        rbnCapabilities
                FROM RBN-SMI;
 
rbnMediaGatewayCap MODULE-IDENTITY
        LAST-UPDATED    "201106150000Z" -- Jun 15, 2011
        ORGANIZATION   "Ericsson Inc."
        CONTACT-INFO
            "       Ericsson Inc.
                    100 Headquarters Drive
                    San Jose, CA 95134
                    USA

             Phone: +1 408 750 5000
               Fax: +1 408 750 5599
            "

        DESCRIPTION
                "The Agent Capabilities of the MEDIA GATEWAY MIB
                 (RBN-MEDIA-GATEWAY-MIB).

                If this MIB implementation is platform-dependent,
                the PRODUCT-RELEASE clause contains Ericsson SEOS version and
                at least one of the following Ericsson product families:
                    [SE]  SmartEdge Multi-service Edge Router (MSER) family
                    [SM]  SM family of Metro Ethernet Service Transport platforms
                    [SSR] Smart Service Router (SSR) family"

        REVISION        "201106150000Z" -- Jun 15, 2011
        DESCRIPTION
            "Update DESCRIPTION clause of MODULE-IDENTITY
            and PRODUCT-RELEASE clause of AGENT-CAPABILITIES."
        
        REVISION      "200910150000Z" -- Oct 15, 2009
        DESCRIPTION
                "Initial version"
        ::= { rbnCapabilities 93}

rbnMediaGatewayCap1 AGENT-CAPABILITIES
        PRODUCT-RELEASE "SEOS 6.3 [SE]"
        STATUS          current
        DESCRIPTION     "RBN-MEDIA-GATEWAY-MIB capabilities"
        SUPPORTS        RBN-MEDIA-GATEWAY-MIB
        INCLUDES {
                    rbnMGNotifyObjectGroup,
                    rbnMGLinkNotifyGroup
                 }
        ::= { rbnMediaGatewayCap 1 }

END
