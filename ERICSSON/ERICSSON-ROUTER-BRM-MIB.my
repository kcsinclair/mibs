-- *****************************************************************
-- ERICSSON-ROUTER-BRM-MIB               BRM MIB
--
-- Copyright (c) 2016 Ericsson AB.
-- All rights reserved.
--
-- *****************************************************************

 ERICSSON-ROUTER-BRM-MIB DEFINITIONS ::= BEGIN

     IMPORTS
         MODULE-IDENTITY, OBJECT-TYPE, OBJECT-IDENTITY,
         NOTIFICATION-TYPE, mib-2, Counter32,
         Integer32, Unsigned32, TimeTicks       FROM SNMPv2-SMI

         TEXTUAL-CONVENTION, DisplayString,
         DateAndTime                            FROM SNMPv2-TC

         MODULE-COMPLIANCE, OBJECT-GROUP,
         NOTIFICATION-GROUP                     FROM SNMPv2-CONF

         ItuPerceivedSeverity                   FROM ITU-ALARM-TC-MIB

         eriRouterMgmt                          FROM ERICSSON-ROUTER-SMI

         EriAlarmType                           FROM ERICSSON-ALARM-TC-MIB;


 eriRouterBRMMib MODULE-IDENTITY
     LAST-UPDATED "201609090000Z"  -- 9 September, 2016
     ORGANIZATION "Ericsson AB"
     CONTACT-INFO
         "
          Leopold Yang
          Email: leopold.yang@ericsson.com

         "
     DESCRIPTION
         "Defines the objects necessary support BRM."

     REVISION "201609090000Z"
     DESCRIPTION
         "Initial revision."

     ::= { eriRouterMgmt 116 }

--
-- MIB table
--

 eriRouterBRMAlarmActiveTable OBJECT-TYPE
     SYNTAX     SEQUENCE OF EriRouterBRMAlarmActiveEntry
     MAX-ACCESS not-accessible
     STATUS     current
     DESCRIPTION
         "A list of BRM active alarm entries."
     ::= { eriRouterBRMMib 1 }

 eriRouterBRMAlarmActiveEntry OBJECT-TYPE
     SYNTAX     EriRouterBRMAlarmActiveEntry
     MAX-ACCESS not-accessible
     STATUS     current
     DESCRIPTION
         "A collection of BRM active alarm info."
     INDEX { eriRouterBRMAlarmActiveIndex }
     ::= { eriRouterBRMAlarmActiveTable 1 }

 EriRouterBRMAlarmActiveEntry ::= SEQUENCE {
     eriRouterBRMAlarmActiveIndex            Unsigned32,
     eriRouterBRMAlarmDateAndTime            DateAndTime,
     eriRouterBRMEriAlarmType                EriAlarmType,
     eriRouterBRMAlarmSeverity               ItuPerceivedSeverity,
     eriRouterBRMAlarmDescription            DisplayString
 }

 eriRouterBRMAlarmActiveIndex OBJECT-TYPE
     SYNTAX     Unsigned32 (1..65535)
     MAX-ACCESS read-only
     STATUS     current
     DESCRIPTION
         "The unique identification of BRM alarm."
     ::= { eriRouterBRMAlarmActiveEntry 1 }

 eriRouterBRMAlarmDateAndTime OBJECT-TYPE
     SYNTAX     DateAndTime
     MAX-ACCESS read-only
     STATUS     current
     DESCRIPTION
         "The date and time when the alarm was raised or cleared."
     ::= { eriRouterBRMAlarmActiveEntry 2 }

 eriRouterBRMEriAlarmType OBJECT-TYPE
        SYNTAX              EriAlarmType
        MAX-ACCESS          read-only
        STATUS              current
        DESCRIPTION
            "The Ericsson alarm type id of this alarm."
    ::= { eriRouterBRMAlarmActiveEntry 3 }

 eriRouterBRMAlarmSeverity OBJECT-TYPE
     SYNTAX     ItuPerceivedSeverity
     MAX-ACCESS read-only
     STATUS     current
     DESCRIPTION
         "The Severity of this alarm."
     ::= { eriRouterBRMAlarmActiveEntry 4 }

 eriRouterBRMAlarmDescription OBJECT-TYPE
     SYNTAX     DisplayString
     MAX-ACCESS read-only
     STATUS     current
     DESCRIPTION
         "The description of this alarm."
     ::= { eriRouterBRMAlarmActiveEntry 5 }


--
-- Notifications
--
 eriRouterBRMAlarm NOTIFICATION-TYPE
     OBJECTS  { eriRouterBRMAlarmActiveIndex,
                eriRouterBRMAlarmDateAndTime,
                eriRouterBRMEriAlarmType,
                eriRouterBRMAlarmSeverity,
                eriRouterBRMAlarmDescription}
     STATUS   current
     DESCRIPTION
         "This notification signifies a BRM alarm."
     ::= { eriRouterBRMMib 2 }

 END
