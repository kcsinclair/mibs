-- %DNP% $Id: RBN-IETF-ISIS-CAP.my,v 1.1.4.3 2011/06/15 18:19:45 danielhe Exp $
-- %DNP% $Source: /cvsroot/pkt/sw/se/xc/bsd/config/snmp/mibs/Attic/RBN-IETF-ISIS-CAP.my,v $
-- *****************************************************************
-- RBN-IETF-ISIS-CAP DEFINITIONS
--
-- Copyright (c) 2010 Ericsson AB
-- All rights reserved.
-- 
-- *****************************************************************
RBN-IETF-ISIS-CAP DEFINITIONS ::= BEGIN

IMPORTS
        MODULE-IDENTITY
            FROM SNMPv2-SMI
        AGENT-CAPABILITIES
            FROM SNMPv2-CONF
        rbnCapabilities
            FROM RBN-SMI;

rbnIetfIsisCap MODULE-IDENTITY
        LAST-UPDATED    "201106150000Z" -- Jun 15, 2011
        ORGANIZATION    "Ericsson, Inc."
        CONTACT-INFO
            "       Ericsson, Inc.
                    100 Headquarters Drive
                    San Jose, CA  95134
                    USA

                 Phone: +1 408 571 5000
                   Fax: +1 408 571 5599
            "
        DESCRIPTION
            "The Agent Capabilities of the ISIS mib.

            If this MIB implementation is platform-dependent,
            the PRODUCT-RELEASE clause contains Ericsson SEOS version and
            at least one of the following Ericsson product families:
                [SE]  SmartEdge Multi-service Edge Router (MSER) family
                [SM]  SM family of Metro Ethernet Service Transport platforms
                [SSR] Smart Service Router (SSR) family"

        REVISION        "201106150000Z" -- Jun 15, 2011
        DESCRIPTION
            "Update DESCRIPTION clause of MODULE-IDENTITY
            and PRODUCT-RELEASE clause of AGENT-CAPABILITIES."
        REVISION        "201008161800Z" -- Aug 16, 2010
        DESCRIPTION
                "Initial version. "
        ::= { rbnCapabilities 97 }

rbnIetfIsisCap1 AGENT-CAPABILITIES
        PRODUCT-RELEASE "SEOS 6.5.1.x [SE, SM]; SEOS 11.1.X [SSR]"
        STATUS          current
        DESCRIPTION     "ISIS-MIB capabilities - isisReadOnlyCompliance"
        SUPPORTS        ISIS-MIB
        INCLUDES    {
                isisSystemGroup,
                isisCircuitGroup,
                isisISAdjGroup,
                isisISPDUCounterGroup,
                isisRATableGroup,
                isisISIPRADestGroup,
                isisLSPGroup
        }
        
        VARIATION isisSysLevelType
        ACCESS    read-only
        DESCRIPTION
             "This object is read-only."

        VARIATION isisSysID
        ACCESS    read-only
        DESCRIPTION
             "This object is read-only."

        VARIATION isisSysMaxPathSplits
        ACCESS    read-only
        DESCRIPTION
             "This object is read-only."

        VARIATION isisSysMaxLSPGenInt
        ACCESS    read-only
        DESCRIPTION
             "This object is read-only."

        VARIATION isisSysPollESHelloRate
        ACCESS    read-only
        DESCRIPTION
             "This object is read-only."

        VARIATION isisSysWaitTime
        ACCESS    read-only
        DESCRIPTION
             "This object is read-only."

        VARIATION isisSysAdminState
        ACCESS    read-only
        DESCRIPTION
             "This object is read-only."

        VARIATION isisSysL2toL1Leaking
        ACCESS    read-only
        DESCRIPTION
             "This object is read-only."

        VARIATION isisSysMaxAge
        ACCESS    read-only
        DESCRIPTION
             "This object is read-only."

        VARIATION isisSysReceiveLSPBufferSize
        ACCESS    read-only
        DESCRIPTION
             "This object is read-only."

        VARIATION isisSysNotificationEnable
        ACCESS    read-only
        DESCRIPTION
             "This object is read-only."

        VARIATION isisSysLevelOrigLSPBuffSize
        ACCESS    read-only
        DESCRIPTION
             "This object is read-only."

        VARIATION isisSysLevelMinLSPGenInt
        ACCESS    read-only
        DESCRIPTION
             "This object is read-only."

        VARIATION isisSysLevelSetOverload
        ACCESS    read-only
        DESCRIPTION
             "This object is read-only."

        VARIATION isisSysLevelSetOverloadUntil
        ACCESS    read-only
        DESCRIPTION
             "This object is read-only."

        VARIATION isisSysLevelMetricStyle
        ACCESS    read-only
        DESCRIPTION
             "This object is read-only."

        VARIATION isisSysLevelSPFConsiders
        ACCESS    read-only
        DESCRIPTION
             "This object is read-only."

        VARIATION isisSysLevelTEEnabled
        ACCESS    read-only
        DESCRIPTION
             "This object is read-only."

        VARIATION isisSysReceiveLSPBufferSize
        ACCESS    read-only
        DESCRIPTION
             "This object is read-only."

        VARIATION isisManAreaAddrExistState
        ACCESS    read-only
        DESCRIPTION
             "This object is read-only."

        VARIATION isisSummAddrExistState
        ACCESS    read-only
        DESCRIPTION
             "This object is read-only."

        VARIATION isisSummAddrMetric
        ACCESS    read-only
        DESCRIPTION
             "This object is read-only."

        VARIATION isisSummAddrFullMetric
        ACCESS    read-only
        DESCRIPTION
             "This object is read-only."

        VARIATION isisRedistributeAddrExistState
        ACCESS    read-only
        DESCRIPTION
             "This object is read-only."

        VARIATION isisCircAdminState
        ACCESS    read-only
        DESCRIPTION
             "This object is read-only."

        VARIATION isisCircExistState
        ACCESS    read-only
        DESCRIPTION
             "This object is read-only."

        VARIATION isisCircType
        ACCESS    read-only
        DESCRIPTION
             "This object is read-only."

        VARIATION isisCircExtDomain
        ACCESS    read-only
        DESCRIPTION
             "This object is read-only."

        VARIATION isisCircLevelType
        ACCESS    read-only
        DESCRIPTION
             "This object is read-only."

        VARIATION isisCircPassiveCircuit
        ACCESS    read-only
        DESCRIPTION
             "This object is read-only."

        VARIATION isisCircMeshGroupEnabled
        ACCESS    read-only
        DESCRIPTION
             "This object is read-only."

        VARIATION isisCircMeshGroup
        ACCESS    read-only
        DESCRIPTION
             "This object is read-only."

        VARIATION isisCircSmallHellos
        ACCESS    read-only
        DESCRIPTION
             "This object is read-only."

        VARIATION isisCircExtendedCircID
        ACCESS    read-only
        DESCRIPTION
             "This object is read-only."

        VARIATION isisCircIfIndex
        ACCESS    read-only
        DESCRIPTION
             "This object is read-only."

        VARIATION isisCirc3WayEnabled
        ACCESS    read-only
        DESCRIPTION
             "This object is read-only."

        VARIATION isisCircLevelMetric
        ACCESS    read-only
        DESCRIPTION
             "This object is read-only."

        VARIATION isisCircLevelWideMetric
        ACCESS    read-only
        DESCRIPTION
             "This object is read-only."

        VARIATION isisCircLevelISPriority
        ACCESS    read-only
        DESCRIPTION
             "This object is read-only."

        VARIATION isisCircLevelHelloMultiplier
        ACCESS    read-only
        DESCRIPTION
             "This object is read-only."

        VARIATION isisCircLevelHelloTimer
        ACCESS    read-only
        DESCRIPTION
             "This object is read-only."

        VARIATION isisCircLevelDRHelloTimer
        ACCESS    read-only
        DESCRIPTION
             "This object is read-only."

        VARIATION isisCircLevelLSPThrottle
        ACCESS    read-only
        DESCRIPTION
             "This object is read-only."

        VARIATION isisCircLevelMinLSPRetransInt
        ACCESS    read-only
        DESCRIPTION
             "This object is read-only."

        VARIATION isisCircLevelCSNPInterval
        ACCESS    read-only
        DESCRIPTION
             "This object is read-only."

        VARIATION isisCircLevelPartSNPInterval
        ACCESS    read-only
        DESCRIPTION
            "This object is read-only."

        VARIATION isisRAExistState
        ACCESS    read-only
        DESCRIPTION
            "This object is read-only."

        VARIATION isisRAAdminState
        ACCESS    read-only
        DESCRIPTION
            "This object is read-only."

        VARIATION isisRAAddrPrefix
        ACCESS    read-only
        DESCRIPTION
            "This object is read-only."

        VARIATION isisRAMapType
        ACCESS    read-only
        DESCRIPTION
            "This object is read-only."

        VARIATION isisRAMetric
        ACCESS    read-only
        DESCRIPTION
            "This object is read-only."

        VARIATION isisRAMetricType
        ACCESS    read-only
        DESCRIPTION
            "This object is read-only."

        VARIATION isisRASNPAAddress
        ACCESS    read-only
        DESCRIPTION
            "This object is read-only."

        VARIATION isisRASNPAPrefix
        ACCESS    read-only
        DESCRIPTION
            "This object is read-only."

        VARIATION isisRAType
        ACCESS    read-only
        DESCRIPTION
            "This object is read-only."

        VARIATION isisRASNPAMask
        ACCESS    read-only
        DESCRIPTION
            "This object is read-only."

        VARIATION isisIPRANextHopType
        ACCESS    read-only
        DESCRIPTION
            "This object is read-only."

        VARIATION isisIPRANextHop
        ACCESS    read-only
        DESCRIPTION
            "This object is read-only."

        VARIATION isisIPRAType
        ACCESS    read-only
        DESCRIPTION
            "This object is read-only."

        VARIATION isisIPRAExistState
        ACCESS    read-only
        DESCRIPTION
            "This object is read-only."

        VARIATION isisIPRAAdminState
        ACCESS    read-only
        DESCRIPTION
            "This object is read-only."

        VARIATION isisIPRAAdminState
        ACCESS    read-only
        DESCRIPTION
            "This object is read-only."

        VARIATION isisIPRAMetric
        ACCESS    read-only
        DESCRIPTION
            "This object is read-only."

        VARIATION isisIPRAMetricType
        ACCESS    read-only
        DESCRIPTION
            "This object is read-only."

        VARIATION isisIPRAFullMetric
        ACCESS    read-only
        DESCRIPTION
            "This object is read-only."

        VARIATION isisIPRASNPAAddress
        ACCESS    read-only
        DESCRIPTION
            "This object is read-only."

        VARIATION isisIPRASourceType
        ACCESS    read-only
        DESCRIPTION
            "This object is read-only."

        ::= { rbnIetfIsisCap 1}
        
END
