-- %DNP% $Id: ERICSSON-ROUTER-L2TP-CAP.my,v 1.1.2.5.322.3 2011/06/15 18:19:46 danielhe Exp $
-- %DNP% $Source: /cvsroot/pkt/sw/se/xc/bsd/config/snmp/mibs/Attic/ERICSSON-ROUTER-L2TP-CAP.my,v $
-- *****************************************************************
-- ERICSSON-ROUTER-L2TP-CAP.my   L2TP MIB agent capabilities
--
-- Copyright (c) 2000-2005, 2010-2011, 2015 Ericsson AB
-- All rights reserved.
-- 
-- *****************************************************************

ERICSSON-ROUTER-L2TP-CAP DEFINITIONS ::= BEGIN

IMPORTS
	MODULE-IDENTITY
		FROM SNMPv2-SMI
	AGENT-CAPABILITIES
		FROM SNMPv2-CONF
	SnmpAdminString
		FROM SNMP-FRAMEWORK-MIB
	eriRouterCapabilities
		FROM ERICSSON-ROUTER-SMI;

eriRouterL2tpCap MODULE-IDENTITY
        LAST-UPDATED    "201501141800Z" -- Jan 14, 2015
        ORGANIZATION    "Ericsson Inc."
        CONTACT-INFO
                "       Ericsson, Inc.

                Postal: 100 Headquarters Dr.
                        San Jose, CA  95134
                        USA

                 Phone: +1 408 750 5000
                   Fax: +1 408 750 5599
                "
	DESCRIPTION
		"The Agent Capabilities of the ERICSSON-ROUTER-L2TP-MIB.

                If this MIB implementation is platform-dependent,
                the PRODUCT-RELEASE clause contains Ericsson SEOS version and
                at least one of the following Ericsson product families:
                    [SE]  SmartEdge Multi-service Edge Router (MSER) family
                    [SM]  SM family of Metro Ethernet Service Transport platforms
                    [SSR] Smart Service Router (SSR) family"

        REVISION        "201501141800Z" -- Jan 14, 2015
        DESCRIPTION
                "Updated RBN/rbn/Rbn as ERICSSON-ROUTER/eriRouter/EriRouter
                to migrate RBN MIB to ERICSSON MIB."

        REVISION        "201106150000Z" -- Jun 15, 2011
        DESCRIPTION
                "Update DESCRIPTION clause of MODULE-IDENTITY
                and PRODUCT-RELEASE clause of AGENT-CAPABILITIES."

        REVISION        "201011010000Z" -- Nov 1, 2010
        DESCRIPTION
                "Modified PRODUCT-RELEASE clause for consistent naming.
                Updated CONTACT-INFO."

	REVISION	"200505020000Z" -- May 2, 2005
	DESCRIPTION
		"Added new AGENT-CAPABILITIES for the SE 4.0.5 release
		and updated the contact info."

	REVISION	"200410180000Z" -- Oct 18, 2004
	DESCRIPTION
		"Added new AGENT-CAPABILITIES for the SE 4.0.3 release
		and updated the contact info."

	REVISION	"200402110000Z" -- Feb 11, 2004
	DESCRIPTION
		"Added new AGENT-CAPABILITIES for the SE 2.6.3 release
		and updated the contact info."

	REVISION	"200210150000Z" -- Oct 15, 2002
	DESCRIPTION
		"Added AGENT-CAPABILITIES for providing peer name
		support and changed the contact info."

	REVISION        "200206100000Z" -- Jun 10, 2002
	DESCRIPTION
		"Initial version."

	::= { eriRouterCapabilities 56 }


eriRouterL2tpInfoCap1 AGENT-CAPABILITIES
	PRODUCT-RELEASE	"AOS 6.X.X.X"
	STATUS		current
	DESCRIPTION	"ERICSSON-ROUTER-L2TP-MIB capabilities"
	SUPPORTS	ERICSSON-ROUTER-L2TP-MIB
	INCLUDES {
                   eriRouterL2tpMibPeerCfgGroup,
                   eriRouterL2tpMibTunnelCfgGroup,
                   eriRouterL2tpMibPeerCntGroup,
                   eriRouterL2tpMibTunnelCntGroup,
                   eriRouterL2tpMibSessionCntGroup,
		   eriRouterL2tpMibNotificationGroup
		 }

        VARIATION eriRouterL2tpPCfgMedia
            ACCESS    read-only
            DESCRIPTION
                "Write access is not allowed."

        VARIATION eriRouterL2tpPCfgRadius
            ACCESS    read-only
            DESCRIPTION
                "Write access is not allowed."

        VARIATION eriRouterL2tpPCfgRemIPAdd
            ACCESS    read-only
            DESCRIPTION
                "Write access is not allowed."

        VARIATION eriRouterL2tpPCfgStatic
            ACCESS    read-only
            DESCRIPTION
                "Write access is not allowed."

        VARIATION eriRouterL2tpPCfgLocalIPAdd
            ACCESS    read-only
            DESCRIPTION
                "Write access is not allowed."

        VARIATION eriRouterL2tpPCfgMode
            ACCESS    read-only
            DESCRIPTION
                "Write access is not allowed."

        VARIATION eriRouterL2tpPCfgMaxTunnels
            ACCESS    read-only
            DESCRIPTION
                "Write access is not allowed."

        VARIATION eriRouterL2tpPCfgMaxSesPerTun
            ACCESS    read-only
            DESCRIPTION
                "Write access is not allowed."

        VARIATION eriRouterL2tpPCfgCtlRetranTO
            ACCESS    read-only
            DESCRIPTION
                "Write access is not allowed."

        VARIATION eriRouterL2tpPCfgSessAuth
            ACCESS    read-only
            DESCRIPTION
                "Write access is not allowed."

        VARIATION eriRouterL2tpPCfgCtlWin
            ACCESS    read-only
            DESCRIPTION
                "Write access is not allowed."

        VARIATION eriRouterL2tpPCfgDNIS
            ACCESS    read-only
            DESCRIPTION
                "Write access is not allowed."

        VARIATION eriRouterL2tpPCfgPoliceRate
            ACCESS    read-only
            DESCRIPTION
                "Write access is not allowed."

        VARIATION eriRouterL2tpPCfgLimitRate
            ACCESS    read-only
            DESCRIPTION
                "Write access is not allowed."

        VARIATION eriRouterL2tpPCfgLimitBurst
            ACCESS    read-only
            DESCRIPTION
                "Write access is not allowed."

        VARIATION eriRouterL2tpPCfgGroup
            ACCESS    read-only
            DESCRIPTION
                "Write access is not allowed."

        VARIATION eriRouterL2tpPCfgPref
            ACCESS    read-only
            DESCRIPTION
                "Write access is not allowed."

        VARIATION eriRouterL2tpPCfgPasswd
            ACCESS    read-only
            DESCRIPTION
                "Write access is not allowed."

        VARIATION eriRouterL2tpPCfgHelloTimer
            ACCESS    read-only
            DESCRIPTION
                "Write access is not allowed."

        VARIATION eriRouterL2tpPCfgSessContext
            ACCESS    read-only
            DESCRIPTION
                "Write access is not allowed."

        VARIATION eriRouterL2tpPCfgSessService
            ACCESS    read-only
            DESCRIPTION
                "Write access is not allowed."

        VARIATION eriRouterL2tpPCfgEthEncap
            ACCESS    read-only
            DESCRIPTION
                "Write access is not allowed."

        VARIATION eriRouterL2tpPCfgEthSession
            ACCESS    read-only
            DESCRIPTION
                "Write access is not allowed."

        ::= { eriRouterL2tpCap 1  }	

eriRouterL2tpInfoCap2 AGENT-CAPABILITIES
	PRODUCT-RELEASE	"SEOS 2.6.3"
	STATUS		current
	DESCRIPTION	"ERICSSON-ROUTER-L2TP-MIB capabilities"
	SUPPORTS	ERICSSON-ROUTER-L2TP-MIB
	INCLUDES {
		   eriRouterL2tpMibNotificationGroup2
		 }

	::= { eriRouterL2tpCap 2  }	

eriRouterL2tpInfoCap3 AGENT-CAPABILITIES
	PRODUCT-RELEASE	"SEOS 4.0.3"
	STATUS		current
	DESCRIPTION	"ERICSSON-ROUTER-L2TP-MIB capabilities"
	SUPPORTS	ERICSSON-ROUTER-L2TP-MIB
	INCLUDES {
		   eriRouterL2tpMibPeerTunCfgGroup,
		   eriRouterL2tpMibNotificationGroup2
		 }

	VARIATION eriRouterL2tpMibPeerName
	    SYNTAX          SnmpAdminString (SIZE (1..64))
	    DESCRIPTION
		"Each character must be printable (the posix funtion isprint()
		returns true for each character) and the string may not contain
		any of the characters double quote, single quote ('), bar (|),
		or exclamation point (!).

		Limit this peer name string to a maximum of 64 octets in
		length which is the same as the implementation in CLI."

	VARIATION eriRouterL2tpPTCfgTunnelLocalNm
	    SYNTAX          SnmpAdminString (SIZE (0..64))
	    DESCRIPTION
		"Limit this tunnel name string to a maximum of 64 octets in
		length which is the same as the implementation in CLI."

	VARIATION eriRouterL2tpPTCfgTunnelRemoteNm
	    SYNTAX          SnmpAdminString (SIZE (0..64))
	    DESCRIPTION
		"Limit this tunnel name string to a maximum of 64 octets in
		length which is the same as the implementation in CLI."

	VARIATION eriRouterL2tpPTCfgPeerLocalNm
	    SYNTAX          SnmpAdminString (SIZE (0..64))
	    DESCRIPTION
		"Limit this peer name string to a maximum of 64 octets in
		length which is the same as the implementation in CLI."

	::= { eriRouterL2tpCap 3  }

eriRouterL2tpInfoCap4 AGENT-CAPABILITIES
	PRODUCT-RELEASE	"SEOS 4.0.5 [SE]; SEOS 6.3.X [SM]"
	STATUS		current
	DESCRIPTION	"ERICSSON-ROUTER-L2TP-MIB capabilities"
	SUPPORTS	ERICSSON-ROUTER-L2TP-MIB
	INCLUDES {
		   eriRouterL2tpMibTunnelCfgGroup,
		   eriRouterL2tpMibPeerTunCfgGroup,
		   eriRouterL2tpMibNotificationGroup2
		 }

	VARIATION eriRouterL2tpMibPeerName
	    SYNTAX          SnmpAdminString (SIZE (1..64))
	    DESCRIPTION
		"Each character must be printable (the posix funtion isprint()
		returns true for each character) and the string may not contain
		any of the characters double quote, single quote ('), bar (|),
		or exclamation point (!).

		Limit this peer name string to a maximum of 64 octets in
		length which is the same as the implementation in CLI."

	VARIATION       eriRouterL2tpTCfgTunCtlErrs
	    ACCESS          not-implemented
	    DESCRIPTION
		"Object not supported"

	VARIATION       eriRouterL2tpTCfgLastCtlErr
	    ACCESS          not-implemented
	    DESCRIPTION
		"Object not supported"

	VARIATION       eriRouterL2tpTCfgLastCErrTime
	    ACCESS          not-implemented
	    DESCRIPTION
		"Object not supported"
  
	VARIATION       eriRouterL2tpTCfgTunDataErrs
	    ACCESS          not-implemented
	    DESCRIPTION
		"Object not supported"

	VARIATION       eriRouterL2tpTCfgLastDataErr
	    ACCESS          not-implemented
	    DESCRIPTION
		"Object not supported"

	VARIATION       eriRouterL2tpTCfgLastDErrTime
	    ACCESS          not-implemented
	    DESCRIPTION
		"Object not supported"

	VARIATION eriRouterL2tpPTCfgTunnelLocalNm
	    SYNTAX          SnmpAdminString (SIZE (0..64))
	    DESCRIPTION
		"Limit this tunnel name string to a maximum of 64 octets in
		length which is the same as the implementation in CLI."

	VARIATION eriRouterL2tpPTCfgTunnelRemoteNm
	    SYNTAX          SnmpAdminString (SIZE (0..64))
	    DESCRIPTION
		"Limit this tunnel name string to a maximum of 64 octets in
		length which is the same as the implementation in CLI."

	VARIATION eriRouterL2tpPTCfgPeerLocalNm
	    SYNTAX          SnmpAdminString (SIZE (0..64))
	    DESCRIPTION
		"Limit this peer name string to a maximum of 64 octets in
		length which is the same as the implementation in CLI."

	::= { eriRouterL2tpCap 4  }
END
