-- %DNP% $Id: ERICSSON-ROUTER-IETF-RADIUS-AUTH-CLIENT-CAP.my,v 1.1.4.3.182.4 2011/06/15 18:19:45 danielhe Exp $
-- %DNP% $Source: /cvsroot/pkt/sw/se/xc/bsd/config/snmp/mibs/Attic/ERICSSON-ROUTER-IETF-RADIUS-AUTH-CLIENT-CAP.my,v $
-- *****************************************************************
-- ERICSSON-ROUTER-IETF-RADIUS-AUTH-CLIENT-CAP:    RADIUS-AUTH-CLIENT capabilities
--
-- Copyright (c) 2002-2006, 2010-2011, 2015 Ericsson AB
-- All rights reserved.
-- 
-- *****************************************************************

ERICSSON-ROUTER-IETF-RADIUS-AUTH-CLIENT-CAP DEFINITIONS ::= BEGIN
 
IMPORTS
    MODULE-IDENTITY
        FROM SNMPv2-SMI
    AGENT-CAPABILITIES
        FROM SNMPv2-CONF
    eriRouterCapabilities
        FROM ERICSSON-ROUTER-SMI;

eriRouterIetfRadiusAuthClientCap MODULE-IDENTITY
    LAST-UPDATED    "201501141800Z" -- Jan 14, 2015
    ORGANIZATION    "Ericsson Inc."
    CONTACT-INFO
        "               Ericsson, Inc. 

                        100 Headquarters Drive
                        San Jose, CA  95134
                        USA

                 Phone: +1 408 750 5000
                   Fax: +1 408 750 5599"
    DESCRIPTION
        "The Agent Capabilities of the  
         implementation of the RADIUS Authentication Client
         mib module (RADIUS-AUTH-CLIENT-MIB).

        If this MIB implementation is platform-dependent,
        the PRODUCT-RELEASE clause contains Ericsson SEOS version and
        at least one of the following Ericsson product families:
            [SE]  SmartEdge Multi-service Edge Router (MSER) family
            [SM]  SM family of Metro Ethernet Service Transport platforms
            [SSR] Smart Service Router (SSR) family"

    REVISION        "201501141800Z" -- Jan 14, 2015
    DESCRIPTION
        "Updated RBN/rbn/Rbn as ERICSSON-ROUTER/eriRouter/EriRouter
         to migrate RBN MIB to ERICSSON MIB."

    REVISION        "201106150000Z" -- Jun 15, 2011
    DESCRIPTION
        "Update DESCRIPTION clause of MODULE-IDENTITY
         and PRODUCT-RELEASE clause of AGENT-CAPABILITIES."

    REVISION	    "201011010000Z" -- Nov 1, 2010
    DESCRIPTION
	"Modified PRODUCT-RELEASE clause for consistent naming.
         Updated CONTACT-INFO."

    REVISION        "200608231500Z" -- Aug 23, 2006
    DESCRIPTION
        "Add radiusAuthClientBadAuthenticators and
         radiusAuthClientUnknownTypes for SEOS."

    REVISION        "200309081800Z" -- Sept 8, 2003
    DESCRIPTION
        "Add eriRouterRadiusAuthClientCap2 for SEOS."

    REVISION        "200207190000Z" -- July 25, 2002
    DESCRIPTION
        "Initial version"
    ::= { eriRouterCapabilities 47 }

eriRouterRadiusAuthClientCap1 AGENT-CAPABILITIES
    PRODUCT-RELEASE    "AOS 6.0.x.x"
    STATUS          current
    DESCRIPTION     "RADIUS-AUTH-CLIENT-MIB capabilities"
    SUPPORTS        RADIUS-AUTH-CLIENT-MIB
    INCLUDES        { radiusAuthClientMIBGroup}

    VARIATION       radiusAuthClientIdentifier
    ACCESS          not-implemented
    DESCRIPTION
        "Object not supported"

    VARIATION       radiusAuthClientInvalidServerAddresses
    ACCESS          not-implemented
    DESCRIPTION
        "Object not supported"

    VARIATION       radiusAuthClientRoundTripTime
    ACCESS          not-implemented
    DESCRIPTION
        "Object not supported"

    VARIATION       radiusAuthClientAccessChallenges
    ACCESS          not-implemented
    DESCRIPTION
        "Object not supported"

    VARIATION       radiusAuthClientMalformedAccessResponses
    ACCESS          not-implemented
    DESCRIPTION
        "Object not supported"

    VARIATION       radiusAuthClientPendingRequests
    ACCESS          not-implemented
    DESCRIPTION
        "Object not supported"

    ::= { eriRouterIetfRadiusAuthClientCap 1 }
        
eriRouterRadiusAuthClientCap2 AGENT-CAPABILITIES
    PRODUCT-RELEASE    "SEOS 2.5.6.X [SE]"
    STATUS          current
    DESCRIPTION     "RADIUS-AUTH-CLIENT-MIB capabilities"
    SUPPORTS        RADIUS-AUTH-CLIENT-MIB
    INCLUDES        { radiusAuthClientMIBGroup}

    VARIATION       radiusAuthClientIdentifier
    ACCESS          not-implemented
    DESCRIPTION
        "Object not supported"

    VARIATION       radiusAuthClientInvalidServerAddresses
    ACCESS          not-implemented
    DESCRIPTION
        "Object not supported"

    VARIATION       radiusAuthClientRoundTripTime
    ACCESS          not-implemented
    DESCRIPTION
        "Object not supported"

    VARIATION       radiusAuthClientAccessChallenges
    ACCESS          not-implemented
    DESCRIPTION
        "Object not supported"

    VARIATION       radiusAuthClientMalformedAccessResponses
    ACCESS          not-implemented
    DESCRIPTION
        "Object not supported"

    VARIATION       radiusAuthClientBadAuthenticators
    ACCESS          not-implemented
    DESCRIPTION
        "Object not supported"

    VARIATION       radiusAuthClientPendingRequests
    ACCESS          not-implemented
    DESCRIPTION
        "Object not supported"

    VARIATION       radiusAuthClientUnknownTypes
    ACCESS          not-implemented
    DESCRIPTION
        "Object not supported"

    ::= { eriRouterIetfRadiusAuthClientCap 2 }
        
END
