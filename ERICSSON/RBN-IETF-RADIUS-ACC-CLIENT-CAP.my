-- %DNP% $Id: RBN-IETF-RADIUS-ACC-CLIENT-CAP.my,v 1.1.2.3.154.4 2011/06/15 18:19:45 danielhe Exp $
-- %DNP% $Source: /cvsroot/pkt/sw/se/xc/bsd/config/snmp/mibs/Attic/RBN-IETF-RADIUS-ACC-CLIENT-CAP.my,v $
-- *****************************************************************
-- RBN-IETF-RADIUS-ACC-CLIENT-CAP     RADIUS-ACC-CLIENT MIB Capabilities
--
-- Copyright (c) 2003-2006, 2010-2011 Ericsson AB
-- All rights reserved.
-- 
-- *****************************************************************

RBN-IETF-RADIUS-ACC-CLIENT-CAP DEFINITIONS ::= BEGIN

IMPORTS
    MODULE-IDENTITY     FROM SNMPv2-SMI
    AGENT-CAPABILITIES  FROM SNMPv2-CONF
    rbnCapabilities     FROM RBN-SMI;

rbnIetfRadiusAccClientCap MODULE-IDENTITY
    LAST-UPDATED    "201106150000Z" -- Jun 15, 2011
    ORGANIZATION    "Ericsson Inc."
    CONTACT-INFO
            "       Ericsson, Inc.

            Postal: 100 Headquarters Dr.
                    San Jose, CA  95134
                    USA

             Phone: +1 408 750 5000
               Fax: +1 408 750 5599
            "
    DESCRIPTION
        "The Agent Capabilities of the implementation
         of the RADIUS Accounting Client MIB module (RADIUS-ACC-CLIENT-MIB).

        If this MIB implementation is platform-dependent,
        the PRODUCT-RELEASE clause contains Ericsson SEOS version and
        at least one of the following Ericsson product families:
            [SE]  SmartEdge Multi-service Edge Router (MSER) family
            [SM]  SM family of Metro Ethernet Service Transport platforms
            [SSR] Smart Service Router (SSR) family"

        REVISION        "201106150000Z" -- Jun 15, 2011
        DESCRIPTION
            "Update DESCRIPTION clause of MODULE-IDENTITY
            and PRODUCT-RELEASE clause of AGENT-CAPABILITIES."
    REVISION    "201011010000Z" -- Nov 1, 2010
    DESCRIPTION
        "Modified PRODUCT-RELEASE clause for consistent naming.
         Updated CONTACT-INFO."

    REVISION    "200403021800Z" -- March 2, 2004
    DESCRIPTION
        "Add rbnRadiusAccClientCap2."
    REVISION    "200312160000Z" -- Dec 16, 2003
    DESCRIPTION
        "Initial version."
    ::= { rbnCapabilities 60 }
    
rbnRadiusAccClientCap1 AGENT-CAPABILITIES
    PRODUCT-RELEASE "SEOS 2.6.x [SE]"
    STATUS          current
    DESCRIPTION     "RADIUS-ACC-CLIENT-MIB capabilities"
    SUPPORTS        RADIUS-ACC-CLIENT-MIB
    INCLUDES {
        radiusAccClientMIBGroup
    }

    VARIATION radiusAccClientInvalidServerAddresses
    ACCESS    not-implemented
    DESCRIPTION
        "Object not supported."

    VARIATION radiusAccClientIdentifier
    ACCESS    not-implemented
    DESCRIPTION
        "Object not supported."

    VARIATION radiusAccClientRoundTripTime
    ACCESS    not-implemented
    DESCRIPTION
        "Object not supported."

    VARIATION radiusAccClientMalformedResponses
    ACCESS    not-implemented
    DESCRIPTION
        "Object not supported."

    VARIATION radiusAccClientBadAuthenticators
    ACCESS    not-implemented
    DESCRIPTION
        "Object not supported."

    VARIATION radiusAccClientPendingRequests
    ACCESS    not-implemented
    DESCRIPTION
        "Object not supported."

    VARIATION radiusAccClientUnknownTypes
    ACCESS    not-implemented
    DESCRIPTION
        "Object not supported."

    VARIATION radiusAccClientPacketsDropped
    ACCESS    not-implemented
    DESCRIPTION
        "Object not supported."

    ::= { rbnIetfRadiusAccClientCap 1 }
    
rbnRadiusAccClientCap2 AGENT-CAPABILITIES
    PRODUCT-RELEASE "AOS 6.0.10.x"
    STATUS          current
    DESCRIPTION     "RADIUS-ACC-CLIENT-MIB capabilities"
    SUPPORTS        RADIUS-ACC-CLIENT-MIB
    INCLUDES {
        radiusAccClientMIBGroup
    }

    VARIATION radiusAccClientInvalidServerAddresses
    ACCESS    not-implemented
    DESCRIPTION
        "Object not supported."

    VARIATION radiusAccClientIdentifier
    ACCESS    not-implemented
    DESCRIPTION
        "Object not supported."

    VARIATION radiusAccClientRoundTripTime
    ACCESS    not-implemented
    DESCRIPTION
        "Object not supported."

    VARIATION radiusAccClientMalformedResponses
    ACCESS    not-implemented
    DESCRIPTION
        "Object not supported."

    VARIATION radiusAccClientBadAuthenticators
    ACCESS    not-implemented
    DESCRIPTION
        "Object not supported."

    VARIATION radiusAccClientPendingRequests
    ACCESS    not-implemented
    DESCRIPTION
        "Object not supported."

    VARIATION radiusAccClientUnknownTypes
    ACCESS    not-implemented
    DESCRIPTION
        "Object not supported."

    ::= { rbnIetfRadiusAccClientCap 2 }
END
