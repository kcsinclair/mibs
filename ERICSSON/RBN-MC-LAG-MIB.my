-- %DNP%
-- %DNP% $Source: /cvsroot/pkt/sw/se/xc/bsd/config/snmp/mibs/Attic/RBN-MC-LAG-MIB.my,v $
-- *****************************************************************
-- RBN-MC-LAG-MIB
--
-- Copyright (c) 2012 RedBack Networks, Inc.
-- All rights reserved.
--
-- Copyright (c) 2012, 2016 Ericsson AB.
-- All rights reserved.
--
-- *****************************************************************

RBN-MC-LAG-MIB DEFINITIONS ::= BEGIN

IMPORTS
  MODULE-IDENTITY, OBJECT-TYPE, NOTIFICATION-TYPE, Integer32
      FROM SNMPv2-SMI
  MODULE-COMPLIANCE
         FROM SNMPv2-CONF                                    -- [RFC2580]
  MacAddress,
  TruthValue,
  DateAndTime
      FROM SNMPv2-TC
  SnmpAdminString
      FROM SNMP-FRAMEWORK-MIB
  rbnMgmt
      FROM RBN-SMI
  RbnSlot, RbnPort
      FROM RBN-TC
  InterfaceIndex
      FROM IF-MIB
  OBJECT-GROUP, NOTIFICATION-GROUP
      FROM SNMPv2-CONF;

rbnMcLagMIB MODULE-IDENTITY
     LAST-UPDATED    "201604111400Z" -- Apr 11, 2016
     ORGANIZATION    "Ericsson AB."
     CONTACT-INFO
             "       Ericsson AB.

                     100 Headquarters Dr
                     San Jose, CA  95134
                     USA

             Phone:  +1 408 750-5000
             Fax:    +1 408 750-5599

             "
  DESCRIPTION
      "Creating new file with same renamed contents from
       RBN-LAG-MIB.my. Renaming: Lag to McLag."
       
  REVISION    "201602171800Z" -- February 17th, 2016
  DESCRIPTION
      " Defines the objects necessary to monitor the MC-LAG information
      and the state changes of the MC-LAG and its constituent circuits."
    ::= { rbnMgmt 102 }

-- Top level components of this MIB.
rbnMcLagNotifications OBJECT IDENTIFIER ::= { rbnMcLagMIB 0 }
rbnMcLagObjects OBJECT IDENTIFIER ::= { rbnMcLagMIB 1 }
rbnMcLagConformance   OBJECT IDENTIFIER ::= { rbnMcLagMIB 2 }

--
-- Scalars and Tables
--
rbnMcLagTable OBJECT-TYPE
  SYNTAX  SEQUENCE OF RbnMcLagEntry
  MAX-ACCESS not-accessible
  STATUS  current
  DESCRIPTION
      "This table consists of MC-LAG management objects."
  ::= { rbnMcLagObjects 1 }


rbnMcLagEntry OBJECT-TYPE
  SYNTAX  RbnMcLagEntry
  MAX-ACCESS not-accessible
  STATUS  current
  DESCRIPTION
      "Each entry contains management objects of an MC-LAG node."
  INDEX {
      rbnMcLagName }
  ::= { rbnMcLagTable 1 }


RbnMcLagEntry ::= SEQUENCE {
  rbnMcLagName                 SnmpAdminString,
  rbnMcLagId                   Integer32,
  rbnMcLagSystemPriority       Integer32,
  rbnMcLagSystemMacAddress     MacAddress,
  rbnMcLagRevertiveMode        TruthValue,
  rbnMcLagRevertiveHoldTimer   Integer32,
  rbnMcLagOperState            INTEGER,
  rbnMcLagOperErrorCode        INTEGER,
  rbnMcLagSwitchOverTime       DateAndTime,
  rbnMcLagSwitchOverReason     SnmpAdminString 
  }


rbnMcLagName OBJECT-TYPE
  SYNTAX  SnmpAdminString (SIZE(1..16))
  MAX-ACCESS not-accessible
  STATUS  current
  DESCRIPTION
      "This string name uniquely identifies an MC-LAG within an MC-LAG
      cluster. Within an MC-LAG cluster, there could not be two LAG with
      the same name on the same chassis. The MC-LAGs with the same name on
      different chassis are peer to each other."
  ::= { rbnMcLagEntry 1 }

rbnMcLagId OBJECT-TYPE
  SYNTAX  Integer32
  MAX-ACCESS read-only 
  STATUS  current
  DESCRIPTION
      "The identifier is assigned to a LAG on individual chassis at the
      time of LAG configuration. This identifier could be different
      between LAG in the same MC-LAG. There is no coordination between the
      two id manager on the two chassis in assigning the LAG ID on
      different chassis."
  ::= { rbnMcLagEntry 2 }

rbnMcLagSystemPriority OBJECT-TYPE
  SYNTAX  Integer32
  MAX-ACCESS read-only
  STATUS  current
  DESCRIPTION
      "This is a configurable value. The system priority will form part of
      the link-group system id. System priority priority will occupy the
      last 32 bit of the system-id."
  ::= { rbnMcLagEntry 3 }


rbnMcLagSystemMacAddress OBJECT-TYPE
  SYNTAX  MacAddress
  MAX-ACCESS read-only
  STATUS  current
  DESCRIPTION
      "The ."
  ::= { rbnMcLagEntry 4 }


rbnMcLagRevertiveMode OBJECT-TYPE
  SYNTAX  TruthValue 
  MAX-ACCESS read-only
  STATUS  current
  DESCRIPTION
      "This boolean value indicates whether revertive mode is set for an
      MC-LAG. If revertive mode is set, the LAG with higher priority starts the
      revertive process once it recovers from some failures to a state
      where it has regained capacity to take over as the active LAG of an MC-LAG."
  ::= { rbnMcLagEntry 5 }


rbnMcLagRevertiveHoldTimer OBJECT-TYPE
  SYNTAX  Integer32
  UNITS
      "seconds"
  MAX-ACCESS read-only
  STATUS  current
  DESCRIPTION
      "This is a configurable value in revertive mode. If this value is
      configured, the LAG with higher priority will hold off for the
      seconds configured by the value before starting the revertive
      procedure."
  ::= { rbnMcLagEntry 6 }

rbnMcLagOperState OBJECT-TYPE
  SYNTAX  INTEGER {
          up(1),
          down(2),
          standby(3) }
  MAX-ACCESS read-only
  STATUS  current
  DESCRIPTION
      "The current MC-LAG state:
      Up      -  When the MC-LAG is active on one of the two chassis.
                 In this state, the traffic are flowing through the active
                 LAG.
      Down    -  When the MC-LAG is down, the LAG is not in a position to 
                 take over as active LAG of an MC-LAG.
      Standby -  When the MC-LAG is standby, the LAG is ready to take over
                 as the active LAG fails."
  ::= { rbnMcLagEntry 7 }

rbnMcLagOperErrorCode OBJECT-TYPE
  SYNTAX  INTEGER {
          noError(0),
          configMismatch(1),
          priorityError(2),
          downMinLink(3)
          }
  MAX-ACCESS read-only
  STATUS  current
  DESCRIPTION
      " The reason that MC-LAG is Down.
        configMismatch - MC-LAG is down because LAG related configuration
                         is not the same between the two LAGs in an MC-LAG.
        priorityError - MC-LAG is down because the configured port priority 
                        values between the two LAGs of an MC-LAG are
                        ambiguous as to which LAG is higher in priority.
        downMinLink - MC-LAG is down because the LAG doesn't have enough
                      links that are up to satisfy the configured minimum link
                      requirement."
  ::= { rbnMcLagEntry 8 }

rbnMcLagSwitchOverTime OBJECT-TYPE
  SYNTAX DateAndTime
  MAX-ACCESS read-only
  STATUS  current
  DESCRIPTION "This indicated the last time MC-LAG was switched-over."
  ::= { rbnMcLagEntry 9 }

rbnMcLagSwitchOverReason OBJECT-TYPE
  SYNTAX  SnmpAdminString
  MAX-ACCESS read-only
  STATUS  current
  DESCRIPTION " This indicate in text the reason for MC-LAG switchover. "
  ::= { rbnMcLagEntry 10 }

-- Multi-chassis Link-group constituent Table

rbnMcLagConstituentTable OBJECT-TYPE
  SYNTAX  SEQUENCE OF RbnMcLagConstituentEntry
  MAX-ACCESS not-accessible
  STATUS  current
  DESCRIPTION " This is a table of constituent links for a LAG"
  ::= { rbnMcLagObjects 2 }

rbnMcLagConstituentEntry OBJECT-TYPE
  SYNTAX  RbnMcLagConstituentEntry
  MAX-ACCESS not-accessible
  STATUS  current
  DESCRIPTION "A constituent link of an MCLAG. A constituent link is
               uniquely identified by a slot, port, and port priority."
  INDEX {
      rbnMcLagConstituentName, rbnMcLagConstituentSlot, rbnMcLagConstituentPort
  }
  ::= { rbnMcLagConstituentTable 1 }

RbnMcLagConstituentEntry ::= SEQUENCE {
  rbnMcLagConstituentName           SnmpAdminString,
  rbnMcLagConstituentSlot           RbnSlot,
  rbnMcLagConstituentPort           RbnPort,
  rbnMcLagConstituentPortPriority   INTEGER,
  rbnMcLagConstituentPortIfIndex    InterfaceIndex,
  rbnMcLagConstituentLACPErrorCode  INTEGER
}

rbnMcLagConstituentName OBJECT-TYPE
  SYNTAX  SnmpAdminString (SIZE(1..16))
  MAX-ACCESS not-accessible
  STATUS  current
  DESCRIPTION
      "This string name uniquely identifies an MC-LAG within an MC-LAG
      cluster. Within an MC-LAG cluster, there could not be two LAG with
      the same name on the same chassis. The MC-LAGs with the same name on
      different chassis are peer to each other."
  ::= { rbnMcLagConstituentEntry 1 }
 
rbnMcLagConstituentSlot  OBJECT-TYPE
  SYNTAX  RbnSlot
  MAX-ACCESS not-accessible
  STATUS  current
  DESCRIPTION
      " This indicates the slot number of the constituent link."
  ::= { rbnMcLagConstituentEntry 2 }

rbnMcLagConstituentPort OBJECT-TYPE
  SYNTAX  RbnPort
  MAX-ACCESS not-accessible
  STATUS  current
  DESCRIPTION
      " This indicates the port number of the constituent link."
  ::= { rbnMcLagConstituentEntry 3 }

rbnMcLagConstituentPortPriority OBJECT-TYPE
  SYNTAX  Integer32
  MAX-ACCESS read-only
  STATUS  current
  DESCRIPTION " This indicates the configured priority of the constituent
                link."
  ::= { rbnMcLagConstituentEntry 4 }

rbnMcLagConstituentPortIfIndex OBJECT-TYPE
  SYNTAX  InterfaceIndex
  MAX-ACCESS read-only
  STATUS  current
  DESCRIPTION " The hardware interface index associated with the constituent link."
  ::= { rbnMcLagConstituentEntry 5 }

rbnMcLagConstituentLACPErrorCode OBJECT-TYPE
  SYNTAX  INTEGER {
          noError(0),
          portFailure(1),
          ccmFailure(2),
          bfdFailure(3)
          }
  MAX-ACCESS read-only 
  STATUS  current
  DESCRIPTION
      " The reason LACP on a constituent is down.
        portFailure   - LACP is down because the consitutent port is down.
        ccmFailure    - LACP is down because the ccm is down.
        bfdFailure    - LACP is down because bfd is down."
  ::= { rbnMcLagConstituentEntry 6 }

--
-- Notification Types
--

-- MC-LAG level 

rbnMcLagSwitchOverEvent NOTIFICATION-TYPE
  OBJECTS {
      rbnMcLagOperState,
      rbnMcLagSwitchOverReason
      }
  STATUS  current
  DESCRIPTION
      "An MC-LAG switch-over trap indicates that a switch-over has happened
      and also it identifies which LAG will become active LAG."
  ::= { rbnMcLagNotifications 1 }

rbnMcLagOperFailed NOTIFICATION-TYPE
  OBJECTS {
      rbnMcLagOperState,
      rbnMcLagOperErrorCode
      }
  STATUS  current
  DESCRIPTION
      "This trap indicates an MC-LAG has failed and why."
  ::= { rbnMcLagNotifications 2 }

rbnMcLagOperFailureCleared NOTIFICATION-TYPE
  OBJECTS {
      rbnMcLagOperState
      }
  STATUS  current
  DESCRIPTION
      "This trap indicates an MC-LAG has recovered from a failure."
  ::= { rbnMcLagNotifications 3 }

-- MC-LAG constituent port level

rbnMcLagConstituentPortUp NOTIFICATION-TYPE
  OBJECTS {
          rbnMcLagConstituentPortPriority,
          rbnMcLagConstituentPortIfIndex
       }
  STATUS  current
  DESCRIPTION
      "This trap indicates whether LACP on a constituent link is active in a LAG of
       an MC-LAG."
  ::= { rbnMcLagNotifications 4 }

rbnMcLagConstituentPortDown NOTIFICATION-TYPE
  OBJECTS {
          rbnMcLagConstituentPortPriority,
          rbnMcLagConstituentPortIfIndex,
          rbnMcLagConstituentLACPErrorCode
       }
  STATUS  current
  DESCRIPTION
      "This trap indicates whether LACP on a constituent link has failed
       in a LAG of an  MC-LAG."
  ::= { rbnMcLagNotifications 5 }


-- Conformance Statement
rbnMcLagGroups
      OBJECT IDENTIFIER ::= { rbnMcLagConformance 1 }

rbnMcLagCompliances
      OBJECT IDENTIFIER ::= { rbnMcLagConformance 2 }

-- Module Compliance

rbnMcLagModuleCompliance MODULE-COMPLIANCE
      STATUS current
      DESCRIPTION
          "Compliance statement for agents that provide support
           for the RBN-MC-LAG-MIB"
      MODULE -- this module
         MANDATORY-GROUPS    { 
                               rbnMcLagObjectGroup,
                               rbnMcLagNotificationGroup
                             }
   ::= { rbnMcLagCompliances 1 }

-- Units of conformance.

rbnMcLagObjectGroup OBJECT-GROUP
      OBJECTS {
         rbnMcLagId,
         rbnMcLagSystemPriority,
         rbnMcLagSystemMacAddress,
         rbnMcLagRevertiveMode, 
         rbnMcLagRevertiveHoldTimer,
         rbnMcLagOperState,
         rbnMcLagOperErrorCode,
         rbnMcLagSwitchOverTime,
         rbnMcLagSwitchOverReason,
         rbnMcLagConstituentPortPriority,
         rbnMcLagConstituentPortIfIndex,
         rbnMcLagConstituentLACPErrorCode
        }
      STATUS  current
      DESCRIPTION
             "Collection of scalar objects required for Multi-chassis
             Link-group management."
      ::= { rbnMcLagGroups 1 }

rbnMcLagNotificationGroup NOTIFICATION-GROUP
       NOTIFICATIONS {
       rbnMcLagSwitchOverEvent,
       rbnMcLagOperFailed,
       rbnMcLagOperFailureCleared,
       rbnMcLagConstituentPortUp,
       rbnMcLagConstituentPortDown
                     }
      STATUS  current
      DESCRIPTION
             "Objects required for Multi-chassis Link-group notifications."
   ::= { rbnMcLagGroups 2 }
END
