-- %DNP% $Id: RBN-IETF-BGP4-CAP.my,v 1.1.6.3.250.4 2011/06/15 18:19:45 danielhe Exp $
-- %DNP% $Source: /cvsroot/pkt/sw/se/xc/bsd/config/snmp/mibs/Attic/RBN-IETF-BGP4V2-CAP.my,v $
-- *****************************************************************
-- RBN-IETF-BGP4V2-CAP
--
-- Copyright (c) 2000, 2003-2006, 2010-2011 Ericsson AB
-- All rights reserved.
--
-- *****************************************************************

RBN-IETF-BGP4V2-CAP DEFINITIONS ::= BEGIN

IMPORTS
        MODULE-IDENTITY
                FROM SNMPv2-SMI
        AGENT-CAPABILITIES
                FROM SNMPv2-CONF
        rbnCapabilities
                FROM RBN-SMI;

rbnIetfBgp4V2Cap MODULE-IDENTITY
        LAST-UPDATED    "201503190000Z" -- Mar 19, 2015
	ORGANIZATION	"Ericsson Inc."
	CONTACT-INFO
		"	Ericsson, Inc.

		Postal:	100 Headquarters Dr.
			San Jose, CA  95134
			USA

		 Phone:	+1 408 750 5000
		   Fax: +1 408 750 5599

		"
        DESCRIPTION
                "The Agent Capabilities of the 
                implementation of the BGP4-MIB.

                If this MIB implementation is platform-dependent,
                the PRODUCT-RELEASE clause contains Ericsson SEOS version and
                at least one of the following Ericsson product families:
                    [SE]  SmartEdge Multi-service Edge Router (MSER) family
                    [SM]  SM family of Metro Ethernet Service Transport platforms
                    [SSR] Smart Service Router (SSR) family"
        REVISION        "201503190000Z" -- March 19, 2015
        DESCRIPTION
                "Initial version ."

        ::= { rbnCapabilities 29 }

rbnIetfBgp4V2Cap1 AGENT-CAPABILITIES
        PRODUCT-RELEASE "AOS 4.0.X.X"
        STATUS         current 
        DESCRIPTION    "BGP4V2-MIB capabilities for notification"
        SUPPORTS       BGP4V2-MIB
        INCLUDES { 
                 bgp4V2StdMIBNotificationGroup
                 }

        VARIATION        bgp4V2BackwardTransitionNotification
        ACCESS           accessible-for-notify
        DESCRIPTION
                "This object is available only in notifications."

        VARIATION        bgp4V2EstablishedNotification
        ACCESS           accessible-for-notify
        DESCRIPTION
                "This object is available only in notifications."

        VARIATION        bgp4V2PeerRemotePort
        ACCESS           accessible-for-notify
        DESCRIPTION
                "This object is available only in notifications."

        VARIATION        bgp4V2PeerLocalPort
        ACCESS           accessible-for-notify
        DESCRIPTION
                "This object is available only in notifications."

        VARIATION        bgp4V2PeerState
        ACCESS           accessible-for-notify
        DESCRIPTION
                "This object is available only in notifications."
        VARIATION        bgp4V2PeerLastErrorCodeReceived
        ACCESS           accessible-for-notify
        DESCRIPTION
                "This object is available only in notifications."

        VARIATION        bgp4V2PeerLastErrorSubCodeReceived
        ACCESS           accessible-for-notify
        DESCRIPTION
                "This object is available only in notifications."

        VARIATION        bgp4V2PeerLastErrorReceivedText
        ACCESS           accessible-for-notify
        DESCRIPTION
                "This object is available only in notifications."


        ::= {rbnIetfBgp4V2Cap 1  }       
END
