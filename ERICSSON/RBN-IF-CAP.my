-- *****************************************************************
-- RBN-IF-MIB     Extension of IF-MIB.my
--
-- %DNP% Copyright (c) 2011 Ericsson AB.
-- %DNP% All rights reserved.
-- 
-- *****************************************************************
RBN-IF-CAP DEFINITIONS ::= BEGIN

IMPORTS
        MODULE-IDENTITY
                FROM SNMPv2-SMI
        AGENT-CAPABILITIES
                FROM SNMPv2-CONF
        rbnCapabilities
                FROM RBN-SMI;

rbnIfCap MODULE-IDENTITY
    LAST-UPDATED    "201208280000Z" --  Aug 28, 2012
    ORGANIZATION    "Ericsson AB."
    CONTACT-INFO
            "       Ericsson, Inc.

            Postal: 100 Headquarters Drive
                    San Jose, CA  95134-1370
                    USA
    
             Phone: +1 408 750 5000
               Fax: +1 408 750 5599"

    DESCRIPTION 
        "The Agent Capabilities of RBN-IF-MIB implementation."

    REVISION    "201208280000Z" --  Aug 28, 2012
    DESCRIPTION 
           "Initial version"
        ::= { rbnCapabilities 102 }

rbnIfCap1 AGENT-CAPABILITIES
    PRODUCT-RELEASE "SEOS 11.1.x"
    STATUS          current
    DESCRIPTION     "RBN-IF-MIB capabilities"
    SUPPORTS        RBN-IF-MIB
    INCLUDES {
        rbnIfMIBGroup
    }
    ::= { rbnIfCap 1 }   

END
