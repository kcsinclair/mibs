-- *****************************************************************
-- ERICSSON-ROUTER-TWAMP-CAP
--
-- Copyright (c) 2018 Ericsson AB.
-- All rights reserved.
--
-- *****************************************************************

 ERICSSON-ROUTER-PTP-CAP DEFINITIONS ::= BEGIN

     IMPORTS
         MODULE-IDENTITY, OBJECT-TYPE, OBJECT-IDENTITY,
         NOTIFICATION-TYPE, mib-2, Counter32,
         Integer32, TimeTicks                   FROM SNMPv2-SMI

         TEXTUAL-CONVENTION, DisplayString      FROM SNMPv2-TC

         MODULE-COMPLIANCE, OBJECT-GROUP,
         NOTIFICATION-GROUP                     FROM SNMPv2-CONF;

 eriRouterPTPMibCap MODULE-IDENTITY
     LAST-UPDATED "201801110000Z"  -- 11 Jan, 2018
     ORGANIZATION "Ericsson AB"
     CONTACT-INFO
         "
          Tonghe Liu
          Email: tonghe.liu@ericsson.com

         "
     DESCRIPTION
        "The Agent Capabilities of the PTP MIB
         (ERICSSON-ROUTER-PTP-MIB)."

     ::= { eriRouterCapabilities 118 }

 eriRouterPTPMibCap1 AGENT-CAPABILITIES
     PRODUCT-RELEASE "Spitfire 1.1.x [SP]"
     STATUS          current
     DESCRIPTION     "ERICSSON-ROUTER-PTP-MIB capabilities"
     SUPPORTS        ERICSSON-ROUTER-PTP-MIB
     INCLUDES {
        eriRouterPTPMib
     }

     ::= { eriRouterPTPMibCap 1 }

 END
