-- %DNP%
-- %DNP% $Source: /cvsroot/pkt/sw/se/xc/bsd/config/snmp/mibs/Attic/RBN-MC-LAG-CAP.my,v $
-- *****************************************************************
-- RBN-MC-LAG-MIB    Ericsson MC-LAG MIB
--
-- Copyright (c) 2012, 2016 Ericsson AB.
-- All rights reserved.
--
-- *****************************************************************

RBN-MC-LAG-CAP DEFINITIONS ::= BEGIN

IMPORTS
        MODULE-IDENTITY
                FROM SNMPv2-SMI
        AGENT-CAPABILITIES
                FROM SNMPv2-CONF
        rbnCapabilities
                FROM RBN-SMI;

rbnMcLagCap MODULE-IDENTITY
    LAST-UPDATED    "201604111400Z" -- Apr 11, 2016
    ORGANIZATION    "Ericsson AB."
    CONTACT-INFO
            "       Ericsson, Inc.

            Postal: 300 Headquarters Drive
                    San Jose, CA  95134-1370
                    USA

             Phone: +1 408 750 5000
               Fax: +1 408 750 5599"

    DESCRIPTION
        "Creating new file with same renamed contents from
         RBN-LAG-CAP.my. Renaming: Lag to McLag."

    REVISION    "201602171800Z" -- February 17th, 2016
    DESCRIPTION
        "The Agent Capabilities of Circuit Emulation Service(MC-LAG) MIB
        implementation."

        REVISION        "201602171800Z" -- February 17th, 2016
        DESCRIPTION
            "Update DESCRIPTION clause of MODULE-IDENTITY
            and PRODUCT-RELEASE clause of AGENT-CAPABILITIES."
    REVISION    "201602171800Z" -- February 17th, 2016
    DESCRIPTION
           "Initial version"
        ::= { rbnCapabilities 105 }

rbnMcLagCap1 AGENT-CAPABILITIES
    PRODUCT-RELEASE "IPOS 12.2.x [SSR]"
    STATUS          current
    DESCRIPTION     "RBN-MC-LAG-MIB capabilities"
    SUPPORTS        RBN-MC-LAG-MIB
    INCLUDES {
       rbnMcLagObjectGroup,
       rbnMcLagNotificationGroup
    }

    ::= { rbnMcLagCap 1 }

END
