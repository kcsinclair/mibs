-- ************************************************************************************
-- ERICSSON-ROUTER-LICENSE-MGR-CAP: ERICSSON-ROUTER-LICENSE-MGR-MIB Agent Capabilities
--
-- Copyright (c) 2015-2016 Ericsson AB
-- All rights reserved.
--
-- ************************************************************************************

ERICSSON-ROUTER-LICENSE-MGR-CAP DEFINITIONS ::= BEGIN

IMPORTS
        MODULE-IDENTITY
                FROM SNMPv2-SMI
        AGENT-CAPABILITIES
                FROM SNMPv2-CONF
        eriRouterCapabilities
                FROM ERICSSON-ROUTER-SMI;

eriRouterLicenseMgrCap MODULE-IDENTITY
        LAST-UPDATED   "201604180000Z" -- Apr 18, 2016
        ORGANIZATION   "Ericsson AB"
        CONTACT-INFO
                "       Ericsson AB
                        200 Headquarters Dr
                        San Jose, CA 95134
                        USA

                 Phone: +1 408 750 5000
                   Fax: +1 408 750 5599
                "
        DESCRIPTION
                "The Agent Capabilities of the LICENSE MANAGER MIB
                 (ERICSSON-ROUTER-IP-LICENSE-MGR-MIB)."

        REVISION       "201604180000Z" -- Apr 18, 2016
        DESCRIPTION
                "Added new OID:
                       eriRouterLicenseMgrCap2."

        REVISION       "201510130000Z" -- Oct 13, 2015
        DESCRIPTION
                "Initial version"
        ::= { eriRouterCapabilities 106}

eriRouterLicenseMgrCap1 AGENT-CAPABILITIES
        PRODUCT-RELEASE "IPOS 15.3"
        STATUS          current
        DESCRIPTION     "ERICSSON-ROUTER-LICENSE-MGR-MIB capabilities"
        SUPPORTS        ERICSSON-ROUTER-LICENSE-MGR-MIB
        INCLUDES {
                    eriRouterLicenseMgrNotifyObjectGroup,
                    eriRouterLicenseMgrNotifyGroup
                 }
        ::= { eriRouterLicenseMgrCap 1 }

eriRouterLicenseMgrCap2 AGENT-CAPABILITIES
        PRODUCT-RELEASE "IPOS 16.1"
        STATUS          current
        DESCRIPTION     "ERICSSON-ROUTER-LICENSE-MGR-MIB capabilities"
        SUPPORTS        ERICSSON-ROUTER-LICENSE-MGR-MIB
        INCLUDES {
                    eriRouterLicenseMgrNotifyObjectGroupV2,
                    eriRouterLicenseMgrNotifyGroupV2
                 }
        ::= { eriRouterLicenseMgrCap 2 }

END
