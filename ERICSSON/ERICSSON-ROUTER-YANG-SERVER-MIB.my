-- ERICSSON-ROUTER-YANG-SERVER-MIB    Ericsson YANG Server MIB
--
-- %DNP% Copyright (c) 2016-2017 Ericsson AB.
-- %DNP% All rights reserved.
--
-- *****************************************************************

ERICSSON-ROUTER-YANG-SERVER-MIB DEFINITIONS ::= BEGIN

IMPORTS
    MODULE-IDENTITY,
    OBJECT-TYPE,
    Integer32,
    NOTIFICATION-TYPE
            FROM SNMPv2-SMI

    MODULE-COMPLIANCE,
    OBJECT-GROUP,
    NOTIFICATION-GROUP
            FROM SNMPv2-CONF

    SnmpAdminString
            FROM SNMP-FRAMEWORK-MIB

    ItuPerceivedSeverity
            FROM ITU-ALARM-TC-MIB
    eriRouterMgmt
            FROM ERICSSON-ROUTER-SMI;

eriRouterYangServerMib MODULE-IDENTITY

    LAST-UPDATED "201611110000Z" -- Nov 11, 2016
    ORGANIZATION "Ericsson AB."
    CONTACT-INFO "Email: snmp.mib.contact@ericsson.com."

    DESCRIPTION
        "The MIB define the YANG server management."

    REVISION "201611110000Z" -- Nov 11, 2016
    DESCRIPTION
        "Initial verison."

    ::= { eriRouterMgmt 116 }

eriRouterYangServerNotifications OBJECT IDENTIFIER ::= { eriRouterYangServerMib 0 }

eriRouterYangServerObjects       OBJECT IDENTIFIER ::= { eriRouterYangServerMib 1 }

eriRouterYangServerConformance   OBJECT IDENTIFIER ::= { eriRouterYangServerMib 2 }

--
-- some structure for the mib objects
--

eriRouterYangServerNotify        OBJECT IDENTIFIER ::= { eriRouterYangServerObjects 1 }

--
-- YangServer Alarm notification objects
--
--
eriRouterYangServerEventDateAndTime OBJECT-TYPE
    SYNTAX      DateAndTime
    MAX-ACCESS  accessible-for-notify
    STATUS      current
    DESCRIPTION
        "The date and time when the event was raised"
    ::= { eriRouterYangServerNotify 2 }

eriRouterYangServerEventAdditionalText OBJECT-TYPE
    SYNTAX      SnmpAdminString  (SIZE(0..256))
    MAX-ACCESS  accessible-for-notify
    STATUS      current
    DESCRIPTION
        "The additional text of the event."
    ::= { eriRouterYangServerNotify 3 }
eriRouterYangServerEventSeverity OBJECT-TYPE
    SYNTAX      ItuPerceivedSeverity
    MAX-ACCESS  accessible-for-notify
    STATUS      current
    DESCRIPTION
       "The current severity of the event."
    ::= { eriRouterYangServerNotify 4 }

--
-- NOTIFICATIONS - node for hanging notification definitions
--

eriRouterYangServerInconsistentAlarm NOTIFICATION-TYPE
OBJECTS {
        eriRouterYangServerEventDateAndTime,
        eriRouterYangServerEventAdditionalText,
        eriRouterYangServerEventSeverity
    }
    STATUS current
    DESCRIPTION
         "This notification signifies that CDB and RDB is inconsistent."
    ::= { eriRouterYangServerNotifications 1 }

eriRouterYangServerInconsistentAlarmCleared NOTIFICATION-TYPE
OBJECTS {
        eriRouterYangServerEventDateAndTime,
        eriRouterYangServerEventAdditionalText,
        eriRouterYangServerEventSeverity
    }
    STATUS current
    DESCRIPTION
         "This notification signifies that CDB and RDB is not inconsistent."
    ::= { eriRouterYangServerNotifications 2 }

eriRouterYangServerBootFail NOTIFICATION-TYPE
OBJECTS {
        eriRouterYangServerEventDateAndTime,
        eriRouterYangServerEventAdditionalText,
        eriRouterYangServerEventSeverity
    }
    STATUS current
    DESCRIPTION
         "This notification signifies that yang server boot failed."
    ::= { eriRouterYangServerNotifications 3 }

eriRouterYangServerFatalError NOTIFICATION-TYPE
OBJECTS {
        eriRouterYangServerEventDateAndTime,
        eriRouterYangServerEventAdditionalText,
        eriRouterYangServerEventSeverity
    }
    STATUS current
    DESCRIPTION
         "This notification signifies that yang server encountered fatal error."
    ::= { eriRouterYangServerNotifications 4 }

eriRouterYangServerCommitFail NOTIFICATION-TYPE
OBJECTS {
        eriRouterYangServerEventDateAndTime,
        eriRouterYangServerEventAdditionalText,
        eriRouterYangServerEventSeverity
    }
    STATUS current
    DESCRIPTION
         "This notification signifies that configuration commit failed."
    ::= { eriRouterYangServerNotifications 5 }

eriRouterYangServerSlaveFailure NOTIFICATION-TYPE
OBJECTS {
        eriRouterYangServerEventDateAndTime,
        eriRouterYangServerEventAdditionalText,
        eriRouterYangServerEventSeverity
    }
    STATUS current
    DESCRIPTION
         "This notification signifies that yangserver set slave failure due to cdb corrupt."
    ::= { eriRouterYangServerNotifications 6 }

--
-- compliance statements
--
eriRouterYangServerCompliances OBJECT IDENTIFIER ::= { eriRouterYangServerConformance 1 }
eriRouterYangServerGroups      OBJECT IDENTIFIER ::= { eriRouterYangServerConformance 2 }

eriRouterYangServerCompliance MODULE-COMPLIANCE
    STATUS  current
    DESCRIPTION
        "The compliance statement for SNMP entities which implement
         the YangServer Alarm MIB."

    MODULE  -- this module
        MANDATORY-GROUPS {
            eriRouterYangServerNotifyObjectGroup,
            eriRouterYangServerNotifyGroup
        }
    ::= { eriRouterYangServerCompliances 1 }

--
-- groupings
--
eriRouterYangServerNotifyObjectGroup OBJECT-GROUP
    OBJECTS {
        eriRouterYangServerEventDateAndTime,
        eriRouterYangServerEventAdditionalText,
        eriRouterYangServerEventSeverity
    }
    STATUS current
    DESCRIPTION
        "The collection of objects related to YangServer
        notifications."
    ::= { eriRouterYangServerGroups 1 }

eriRouterYangServerNotifyGroup NOTIFICATION-GROUP
    NOTIFICATIONS {
        eriRouterYangServerInconsistentAlarm,
        eriRouterYangServerInconsistentAlarmCleared,
        eriRouterYangServerBootFail,
        eriRouterYangServerFatalError,
        eriRouterYangServerCommitFail,
        eriRouterYangServerSlaveFailure
    }
    STATUS current
    DESCRIPTION
        "Notification for tracking YangServer events."
    ::= { eriRouterYangServerGroups 2 }

END
