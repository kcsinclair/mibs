-- %DNP% $Id: RBN-SFP-CAP.my,v 1.1.12.3 2011/06/15 18:19:46 danielhe Exp $
-- %DNP% $Source: /cvsroot/pkt/sw/se/xc/bsd/config/snmp/mibs/Attic/RBN-SFP-CAP.my,v $
-- *****************************************************************
-- RBN-SFP-CAP        SFP Monitor MIB Capabilities
--
-- Copyright (c) 2008, 2011 Ericsson AB.
-- All rights reserved.
--
-- *****************************************************************

RBN-SFP-CAP DEFINITIONS ::= BEGIN

IMPORTS
        MODULE-IDENTITY
                FROM SNMPv2-SMI
        AGENT-CAPABILITIES
                FROM SNMPv2-CONF
        rbnCapabilities
                FROM RBN-SMI;

rbnSfpMonCap MODULE-IDENTITY
        LAST-UPDATED    "201106150000Z" -- Jun 15, 2011
        ORGANIZATION    "Ericsson AB."
        CONTACT-INFO
                "       Ericsson AB.

                Postal: 100 Headquarters Dr
                        San Jose, CA  95134
                        USA

                 Phone: +1 408 750 5000
                   Fax: +1 408 750 5599
                "
        DESCRIPTION
                "The Agent Capabilities of the (RBN-SFP-MIB).

                If this MIB implementation is platform-dependent,
                the PRODUCT-RELEASE clause contains Ericsson SEOS version and
                at least one of the following Ericsson product families:
                    [SE]  SmartEdge Multi-service Edge Router (MSER) family
                    [SM]  SM family of Metro Ethernet Service Transport platforms
                    [SSR] Smart Service Router (SSR) family"

        REVISION        "201106150000Z" -- Jun 15, 2011
        DESCRIPTION
            "Update DESCRIPTION clause of MODULE-IDENTITY
            and PRODUCT-RELEASE clause of AGENT-CAPABILITIES."
        REVISION        "200809240000Z" -- September 24, 2008
        DESCRIPTION
                "Initial version."
        ::= { rbnCapabilities 87 }

rbnSfpMonCap1 AGENT-CAPABILITIES
        PRODUCT-RELEASE "SEOS 6.1.4.2"
        STATUS          current
        DESCRIPTION     "RBN-SFP-MIB capabilities"
        SUPPORTS        RBN-SFP-MIB
        INCLUDES {
                rbnSfpMonMIBObjectGroup,
                rbnSfpMonMIBNotificationGroup
                }
 
        ::= { rbnSfpMonCap 1 }


END
