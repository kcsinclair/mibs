-- %DNP% $Id: RBN-SYS-SECURITY-CAP.my,v 1.1.6.3 2011/06/15 18:19:46 danielhe Exp $
-- %DNP% $Source: /cvsroot/pkt/sw/se/xc/bsd/config/snmp/mibs/Attic/RBN-SYS-SECURITY-CAP.my,v $
-- *****************************************************************
-- RBN-SYS-SECURITY-CAP.my  
--
-- Copyright (c) 2009 Ericsson AB
-- All rights reserved.
-- 
-- *****************************************************************

RBN-SYS-SECURITY-CAP DEFINITIONS ::= BEGIN

IMPORTS
	MODULE-IDENTITY
		FROM SNMPv2-SMI
	AGENT-CAPABILITIES
		FROM SNMPv2-CONF
	rbnCapabilities
		FROM RBN-SMI;

rbnSysSecCap MODULE-IDENTITY
	LAST-UPDATED    "201106150000Z" -- Jun 15, 2011
	ORGANIZATION	"Ericsson Inc."
	CONTACT-INFO
		"	Ericsson Inc.

                Postal: 100 Headquarters Dr
                        San Jose, CA  95134
                        USA

                 Phone: +1 408 570 5000
                   Fax: +1 408 570 5599

                "
	DESCRIPTION
		"The Agent Capabilities of the implementation
		 of the RBN-SYS-SECURITY-MIB

                If this MIB implementation is platform-dependent,
                the PRODUCT-RELEASE clause contains Ericsson SEOS version and
                at least one of the following Ericsson product families:
                    [SE]  SmartEdge Multi-service Edge Router (MSER) family
                    [SM]  SM family of Metro Ethernet Service Transport platforms
                    [SSR] Smart Service Router (SSR) family"

        REVISION        "201106150000Z" -- Jun 15, 2011
        DESCRIPTION
            "Update DESCRIPTION clause of MODULE-IDENTITY
            and PRODUCT-RELEASE clause of AGENT-CAPABILITIES."
        
	REVISION	"200911051800Z"  -- Nov 5, 2009
	DESCRIPTION
		"Initial version"
	::= { rbnCapabilities 95 }

rbnSysSecCap1 AGENT-CAPABILITIES
	PRODUCT-RELEASE	"SEOS 6.3 [SE]"
	STATUS		current
	DESCRIPTION	"RBN-SYS-SECURITY-MIB capabilities"
	SUPPORTS	RBN-SYS-SECURITY-MIB
	INCLUDES {
            rbnMaliciousPktGroup,
            rbnSysSecNotifyObjectsGroup,
            rbnSysSecNotificationGroup
	}
        
        VARIATION   rbnMeasurementInterval
        ACCESS      read-only
        DESCRIPTION
            "Object is read-only."
        
        VARIATION   rbnMaliciousPktsThresholdHi
        ACCESS      read-only
        DESCRIPTION
            "Object is read-only."
        
        VARIATION   rbnMaliciousPktsThresholdLow
        ACCESS      read-only
        DESCRIPTION
            "Object is read-only."
        
        VARIATION   rbnMaliciousPktsDelta
        ACCESS      accessible-for-notify
        DESCRIPTION
            "Object is available only in notification."
        
        VARIATION   rbnSysSecNotifyEnable
        ACCESS      read-only
        DESCRIPTION
            "Object is read-only."
            
	::= { rbnSysSecCap 1 }

END
