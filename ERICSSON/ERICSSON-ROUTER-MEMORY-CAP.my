-- %DNP% $Id: ERICSSON-ROUTER-MEMORY-CAP.my,v 1.1.2.3.380.5 2011/06/29 21:28:38 chiachun Exp $
-- %DNP% $Source: /cvsroot/pkt/sw/se/xc/bsd/config/snmp/mibs/Attic/ERICSSON-ROUTER-MEMORY-CAP.my,v $
-- *****************************************************************
-- ERICSSON-ROUTER-MEMORY-CAP       Memory Usage MIB Capabilities
--
-- Copyright (c) 2002,2004, 2010-2011, 2015 Ericsson AB
-- All rights reserved.
-- 
-- *****************************************************************

ERICSSON-ROUTER-MEMORY-CAP DEFINITIONS ::= BEGIN

IMPORTS

        MODULE-IDENTITY
                        FROM SNMPv2-SMI
        AGENT-CAPABILITIES
                        FROM SNMPv2-CONF
        eriRouterCapabilities
                        FROM ERICSSON-ROUTER-SMI;

eriRouterMemoryMibCap MODULE-IDENTITY
        LAST-UPDATED    "201501141800Z" -- Jan 14, 2015
        ORGANIZATION    "Ericsson AB."
        CONTACT-INFO
                "       Ericsson AB.

                Postal: 100 Headquarters Dr.
                        San Jose, CA  95134
                        USA

                 Phone: +1 408 750 5000
                   Fax: +1 408 750 5599
                "
        DESCRIPTION
                "The Agent Capabilities of the 
                 Memory Usage MIB (ERICSSON-ROUTER-MEMORY-MIB).

                If this MIB implementation is platform-dependent,
                the PRODUCT-RELEASE clause contains Ericsson SEOS version and
                at least one of the following Ericsson product families:
                    [SE]  SmartEdge Multi-service Edge Router (MSER) family
                    [SM]  SM family of Metro Ethernet Service Transport platforms
                    [SSR] Smart Service Router (SSR) family"

        REVISION        "201501141800Z" -- Jan 14, 2015
        DESCRIPTION
                "Updated RBN/rbn/Rbn as ERICSSON-ROUTER/eriRouter/EriRouter
                 to migrate RBN MIB to ERICSSON MIB."

        REVISION        "201106150000Z" -- Jun 15, 2011
        DESCRIPTION
                "Update DESCRIPTION clause of MODULE-IDENTITY
                 and PRODUCT-RELEASE clause of AGENT-CAPABILITIES."

        REVISION        "201101191800Z" -- Jan 19, 2011
        DESCRIPTION
                "Update CONTACT-INFO & ORGANIZATION. "

        REVISION        "201011010000Z" -- Nov 1, 2010
        DESCRIPTION
                "Modified PRODUCT-RELEASE clause for consistent naming.
                 Updated CONTACT-INFO."

        REVISION        "200403051700Z" -- Mar 5, 2004
        DESCRIPTION
                "Changed STATUS of eriRouterMemoryMibCap1 to obsolete.
                Added new OID: eriRouterMemoryMibCap3."

        REVISION        "200206260000Z" -- Jun 26, 2002
        DESCRIPTION
                "Updated CONTACT-INFO.  Added new OID: eriRouterMemoryMibCap2."

        REVISION        "200201031700Z" -- Jan 3, 2002
        DESCRIPTION
                "Initial version."

        ::= { eriRouterCapabilities 39 }

eriRouterMemoryMibCap1 AGENT-CAPABILITIES
        PRODUCT-RELEASE "AOS 5.1.X.X"
        STATUS          obsolete
        DESCRIPTION     "ERICSSON-ROUTER-MEMORY-MIB capabilities"
        SUPPORTS        ERICSSON-ROUTER-MEMORY-MIB
        INCLUDES {
                eriRouterSmsMemoryGroup
        }

        ::= { eriRouterMemoryMibCap 1 }
        
eriRouterMemoryMibCap2 AGENT-CAPABILITIES
        PRODUCT-RELEASE "SEOS 2.3.3"
        STATUS          current
        DESCRIPTION     "ERICSSON-ROUTER-MEMORY-MIB capabilities"
        SUPPORTS        ERICSSON-ROUTER-MEMORY-MIB
        INCLUDES {
                eriRouterMemoryGroup
        }
                
        VARIATION       eriRouterMemoryCumulBlocks
        ACCESS          not-implemented
        DESCRIPTION
                "This object is not supported."

        ::= { eriRouterMemoryMibCap 2 }

eriRouterMemoryMibCap3 AGENT-CAPABILITIES
        PRODUCT-RELEASE "SEOS 6.1.X.X [SE]; SEOS 6.3.X [SM]; SEOS 11.1.x [SSR]"
        STATUS          current
        DESCRIPTION     "ERICSSON-ROUTER-MEMORY-MIB capabilities"
        SUPPORTS        ERICSSON-ROUTER-MEMORY-MIB
        INCLUDES {
                eriRouterMemoryGroup
        }

        VARIATION       eriRouterMemoryCumulBlocks
        ACCESS          not-implemented
        DESCRIPTION
                "This object is not supported."

        ::= { eriRouterMemoryMibCap 3 }
        
END
