-- %DNP% $Id: RBN-IPPOOL-CAP.my,v 1.1.2.4.272.5 2011/06/15 18:19:46 danielhe Exp $
-- %DNP% $Source: /cvsroot/pkt/sw/se/xc/bsd/config/snmp/mibs/Attic/RBN-IPPOOL-CAP.my,v $
-- *****************************************************************
-- RBN-IPPOOL-CAP	IP Pool Mib Capabilities
--
-- Copyright (c) 2001-2002, 2004-2005, 2010-2011 Ericsson AB.
-- All rights reserved.
-- 
-- *****************************************************************

RBN-IPPOOL-CAP DEFINITIONS ::= BEGIN

IMPORTS

	MODULE-IDENTITY
			FROM SNMPv2-SMI
	AGENT-CAPABILITIES
			FROM SNMPv2-CONF
	rbnCapabilities
			FROM RBN-SMI;

rbnIpPoolMibCap MODULE-IDENTITY
    LAST-UPDATED    "201106150000Z" -- Jun 15, 2011
    ORGANIZATION    "Ericsson AB"
    CONTACT-INFO
                "       Ericsson, AB.

                 Postal: 100 Headquarters Dr
                         San Jose, CA  95134
                         USA

                 Phone: +1 408 750 5000
                 Fax: +1 408 750 5599"
    DESCRIPTION
        "The Agent Capabilities of RBN-IPPOOL-MIB.

        If this MIB implementation is platform-dependent,
        the PRODUCT-RELEASE clause contains Ericsson SEOS version and
        at least one of the following Ericsson product families:
            [SE]  SmartEdge Multi-service Edge Router (MSER) family
            [SM]  SM family of Metro Ethernet Service Transport platforms
            [SSR] Smart Service Router (SSR) family"

        REVISION        "201106150000Z" -- Jun 15, 2011
        DESCRIPTION
            "Update DESCRIPTION clause of MODULE-IDENTITY
            and PRODUCT-RELEASE clause of AGENT-CAPABILITIES."
    REVISION    "201011010000Z" -- Nov 1, 2010
    DESCRIPTION
        "Modified PRODUCT-RELEASE clause for consistent naming.
        "

    REVISION    "201003220000Z" -- March 22, 2010
    DESCRIPTION
        "Added rbnIpPoolMibCap5 for SEOS 6.4, supporting IPv6 Pool."

    REVISION    "200506170000Z" -- June 17, 2005
    DESCRIPTION
        "Added rbnIpPoolMibCap4 for SEOS 4.0.5.1, supporting context
        percentage threshold."

    REVISION    "200503300000Z" -- March 30, 2005
    DESCRIPTION
        "Added range IP pool capability."

    REVISION        "200409280000Z" -- September 28, 2004
    DESCRIPTION
        "Add named IP pool capability."

    REVISION    "200111071700Z" -- Nov 7, 2001
    DESCRIPTION
        "Initial version."

    ::= { rbnCapabilities 38 }

rbnIpPoolMibCap1 AGENT-CAPABILITIES
	PRODUCT-RELEASE	"AOS 6.0.X.X"
	STATUS		current
	DESCRIPTION	"RBN-IPPOOL-MIB capabilities"
	SUPPORTS	RBN-IPPOOL-MIB
	INCLUDES {
		rbnIpPoolGroup,
		rbnIpPoolNotifyGroup
	}

	::= { rbnIpPoolMibCap 1 }

rbnIpPoolMibCap2 AGENT-CAPABILITIES
	PRODUCT-RELEASE	"SEOS 4.0.3"
	STATUS		current
	DESCRIPTION	"RBN-IPPOOL-MIB capabilities"
	SUPPORTS	RBN-IPPOOL-MIB
	INCLUDES {
		rbnIpPoolGroup,
		rbnIpPoolNotifyGroup,
		rbnIpPoolNameGroup
	}

	::= { rbnIpPoolMibCap 2 }

rbnIpPoolMibCap3 AGENT-CAPABILITIES
	PRODUCT-RELEASE	"SEOS 4.0.5"
	STATUS		current
	DESCRIPTION	"RBN-IPPOOL-MIB capabilities"
	SUPPORTS	RBN-IPPOOL-MIB
	INCLUDES {
		rbnIpPoolGroupV2,
		rbnIpPoolNotifyGroup,
		rbnIpPoolNameGroup,
		rbnIpPoolRangeGroup
	}

	::= {rbnIpPoolMibCap 3 }

rbnIpPoolMibCap4 AGENT-CAPABILITIES
	PRODUCT-RELEASE	"SEOS 4.0.5.1"
	STATUS		current
	DESCRIPTION	"RBN-IPPOOL-MIB capabilities"
	SUPPORTS	RBN-IPPOOL-MIB
	INCLUDES {
		rbnIpPoolInterfaceGroup,
		rbnIpPoolContextGroup,
		rbnIpPoolNotifyGroupV2
	}

	::= {rbnIpPoolMibCap 4 }

rbnIpPoolMibCap5 AGENT-CAPABILITIES
    PRODUCT-RELEASE    "SEOS 6.4.x [SE]"
    STATUS        current
    DESCRIPTION    "RBN-IPPOOL-MIB capabilities"
    SUPPORTS    RBN-IPPOOL-MIB
    INCLUDES {
        rbnIpPoolInterfaceGroup,
        rbnIpPoolContextGroup,
        rbnIpPoolNotifyGroupV2,
        rbnInetIpPoolGroup,
        rbnInetIpPoolNotifyGroup
    }

    ::= {rbnIpPoolMibCap 5 }
END
