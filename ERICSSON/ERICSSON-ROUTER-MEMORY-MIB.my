-- %DNP% $Id: ERICSSON-ROUTER-MEMORY-MIB.my,v 1.1.2.2.380.2 2011/02/22 17:26:17 thatcher Exp $
-- %DNP% $Source: /cvsroot/pkt/sw/se/xc/bsd/config/snmp/mibs/Attic/ERICSSON-ROUTER-MEMORY-MIB.my,v $
-- *****************************************************************
-- ERICSSON-ROUTER-MEMORY-MIB	Memory Mib
--
-- Copyright (c) 2002, 2004, 2011, 2015 Ericsson AB.
-- All rights reserved.
-- 
-- *****************************************************************

ERICSSON-ROUTER-MEMORY-MIB DEFINITIONS ::= BEGIN

IMPORTS
	MODULE-IDENTITY, OBJECT-TYPE,
	Unsigned32
		FROM SNMPv2-SMI

	MODULE-COMPLIANCE, OBJECT-GROUP
		FROM SNMPv2-CONF

	SnmpAdminString
		FROM SNMP-FRAMEWORK-MIB

	eriRouterMgmt
		FROM ERICSSON-ROUTER-SMI

	EriRouterKBytes
		FROM ERICSSON-ROUTER-TC;

eriRouterMemoryMib MODULE-IDENTITY
        LAST-UPDATED    "201501141800Z" -- Jan 14, 2015
        ORGANIZATION    "Ericsson AB."
        CONTACT-INFO
                "       Ericsson AB.

                Postal: 100 Headquarters Dr
                        San Jose, CA  95134
                        USA

                 Phone: +1 408 750 5000
                   Fax: +1 408 750 5599
                "
	DESCRIPTION
		"Defines the objects necessary to obtain information allowing
		monitoring of system memory usage in a network device."

        REVISION        "201501141800Z" -- Jan 14, 2015
        DESCRIPTION
                "Updated RBN/rbn/Rbn as ERICSSON-ROUTER/eriRouter/EriRouter
                 to migrate RBN MIB to ERICSSON MIB."

	REVISION	"201101191800Z" -- Jan 19, 2011
	DESCRIPTION
		"Update CONTACT-INFO & ORGANIZATION."

	REVISION	"200403051700Z" -- Mar 5, 2004
	DESCRIPTION
		"Obsoleted eriRouterSmsMemoryTable and corresponding conformance
		information."

	REVISION	"200206260000Z" -- Jun 26, 2002
	DESCRIPTION
		"Updated CONTACT-INFO.  Added eriRouterMemoryTable, eriRouterMemoryGroup
		conformance group, and compliance statements.  Deprecated 
		eriRouterSmsMemoryTable and conformance information relevant to the 
		table."

	REVISION	"200201031700Z" -- Jan 3, 2002
	DESCRIPTION
		"Initial version."

	::= { eriRouterMgmt 16 }


eriRouterMemoryMIBNotifications OBJECT IDENTIFIER ::= { eriRouterMemoryMib 0 }

eriRouterMemoryMIBObjects       OBJECT IDENTIFIER ::= { eriRouterMemoryMib 1 }

eriRouterMemoryMIBConformance   OBJECT IDENTIFIER ::= { eriRouterMemoryMib 2 }


--
-- SMS Memory Usage Table
--

eriRouterSmsMemoryTable OBJECT-TYPE
	SYNTAX       SEQUENCE OF EriRouterSmsMemoryEntry
	MAX-ACCESS   not-accessible
	STATUS       obsolete
	DESCRIPTION
		"This table contains the objects which identify information
		about SMS memory usage.  This table has been obsoleted.  The
		new eriRouterMemoryTable must be used instead."
	::= { eriRouterMemoryMIBObjects 1 }

eriRouterSmsMemoryEntry OBJECT-TYPE
	SYNTAX       EriRouterSmsMemoryEntry
	MAX-ACCESS   not-accessible
	STATUS       obsolete
	DESCRIPTION
		"A conceptual row in the eriRouterSmsMemoryTable.  This Entry has
		been obsoleted.  The new eriRouterMemoryEntry must be used
		instead."
	INDEX        { eriRouterSmsMemoryIndex }
	::= { eriRouterSmsMemoryTable 1 }

EriRouterSmsMemoryEntry ::=
	SEQUENCE {
		eriRouterSmsMemoryIndex		Unsigned32,
		eriRouterSmsMemoryModule		SnmpAdminString,
		eriRouterSmsMemoryFreeBytes		Unsigned32,
		eriRouterSmsMemoryBytesInUse		Unsigned32,
		eriRouterSmsMemoryBlocksInUse		Unsigned32,
		eriRouterSmsMemoryCumulBlocks		Unsigned32
	}

eriRouterSmsMemoryIndex OBJECT-TYPE
	SYNTAX       Unsigned32 (1..4294967295)
	MAX-ACCESS   not-accessible
	STATUS       obsolete
	DESCRIPTION
		"A unique identifier for an entry in this table."
	::= { eriRouterSmsMemoryEntry 1 }

eriRouterSmsMemoryModule OBJECT-TYPE
	SYNTAX       SnmpAdminString (SIZE (0..32))
	MAX-ACCESS   read-only
	STATUS       obsolete
	DESCRIPTION
		"The name of the module.  This name is the same as that
		 which would be displayed via the `show memory' CLI command.
		 Examples would be CE, FE, SM 2, CM 3."
	::= { eriRouterSmsMemoryEntry 2 }

eriRouterSmsMemoryFreeBytes OBJECT-TYPE
	SYNTAX       Unsigned32 (0..4294967295)
	MAX-ACCESS   read-only
	STATUS       obsolete
	DESCRIPTION
		"The number of unused bytes of memory in this entry."
	::= { eriRouterSmsMemoryEntry 3 }

eriRouterSmsMemoryBytesInUse OBJECT-TYPE
	SYNTAX       Unsigned32 (0..4294967295)
	MAX-ACCESS   read-only
	STATUS       obsolete
	DESCRIPTION
		"The number of bytes of memory in use in this entry."
	::= { eriRouterSmsMemoryEntry 4 }

eriRouterSmsMemoryBlocksInUse OBJECT-TYPE
	SYNTAX       Unsigned32 (0..4294967295)
	MAX-ACCESS   read-only
	STATUS       obsolete
	DESCRIPTION
		"The number of blocks of memory in use in this entry.
		 A block of memory is the amount of memory returned by a
		 single call to the memory allocation routine in AOS.
		 Hence the size of a block of memory is variable.

		 This statistic can be used to check for memory leaks.
		 One possible strategy is to note the value, do some
		 operations, undo the operations, then check the value
		 again - the start and end values should match.  If they
		 do not, there may be a memory leak."
	::= { eriRouterSmsMemoryEntry 5 }

eriRouterSmsMemoryCumulBlocks OBJECT-TYPE
	SYNTAX       Unsigned32 (0..4294967295)
	MAX-ACCESS   read-only
	STATUS       obsolete
	DESCRIPTION
		"The cumulative blocks count for this entry.  It is an
		 indication of how many times the memory allocation in
		 AOS has been called since the system booted.

		 It can be used to measure the expense of an operation
		 in terms of calls to allocate memory, which are fairly
		 expensive in terms of CPU time."
	::= { eriRouterSmsMemoryEntry 6 }

--
-- Memory Usage Table
--

eriRouterMemoryTable OBJECT-TYPE
        SYNTAX       SEQUENCE OF EriRouterMemoryEntry
        MAX-ACCESS   not-accessible
        STATUS       current
        DESCRIPTION
                "This table contains the objects which identify information
                 about memory usage."
        ::= { eriRouterMemoryMIBObjects 2 }

eriRouterMemoryEntry OBJECT-TYPE
        SYNTAX       EriRouterMemoryEntry
        MAX-ACCESS   not-accessible
        STATUS       current
        DESCRIPTION
                "A conceptual row in the eriRouterMemoryTable."
        INDEX { eriRouterMemoryIndex }
        ::= { eriRouterMemoryTable 1 }
                    
EriRouterMemoryEntry ::= 
        SEQUENCE {
                eriRouterMemoryIndex              Unsigned32,
                eriRouterMemoryModule             SnmpAdminString,
                eriRouterMemoryFreeKBytes         EriRouterKBytes,
                eriRouterMemoryKBytesInUse        EriRouterKBytes,
                eriRouterMemoryBlocksInUse        Unsigned32,
                eriRouterMemoryCumulBlocks        Unsigned32
        }

eriRouterMemoryIndex OBJECT-TYPE
        SYNTAX       Unsigned32 (1..4294967295)
        MAX-ACCESS   not-accessible
        STATUS       current
        DESCRIPTION
                "A unique identifier for an entry in this table."
        ::= { eriRouterMemoryEntry 1 }

eriRouterMemoryModule OBJECT-TYPE
        SYNTAX       SnmpAdminString (SIZE (0..32))
        MAX-ACCESS   read-only
        STATUS       current
        DESCRIPTION
                "The name of the module on which this memory resides."
        ::= { eriRouterMemoryEntry 2 }

eriRouterMemoryFreeKBytes OBJECT-TYPE
        SYNTAX       EriRouterKBytes
        UNITS        "KBytes"
        MAX-ACCESS   read-only
        STATUS       current
        DESCRIPTION
                "The size of unused memory in this entry."
        ::= { eriRouterMemoryEntry 3 }

eriRouterMemoryKBytesInUse OBJECT-TYPE
        SYNTAX       EriRouterKBytes
        UNITS        "KBytes"
        MAX-ACCESS   read-only
        STATUS       current
        DESCRIPTION
                "The size of memory in use in this entry."
        ::= { eriRouterMemoryEntry 4 }

eriRouterMemoryBlocksInUse OBJECT-TYPE
        SYNTAX       Unsigned32 (0..4294967295)
        MAX-ACCESS   read-only
        STATUS       current
        DESCRIPTION
                "The number of blocks of memory on this module which is in
                 use.  A block of memory is a unit of physical/virtual 
                 memory that can be allocated or freed by the user. This  
                 statistic can be used to check for memory leaks. One 
                 possible strategy is to note the value, do some operations, 
                 undo the operations, then check the value again - the start 
                 and end values should match.  If they do not, there may be 
                 a memory leak."
        ::= { eriRouterMemoryEntry 5 }

eriRouterMemoryCumulBlocks OBJECT-TYPE
        SYNTAX       Unsigned32 (0..4294967295)
        MAX-ACCESS   read-only
        STATUS       current
        DESCRIPTION
                "The cumulative blocks count for this entry.  For example,
                 in some systems, this indicates how many times the memory 
                 allocation routine has been called since the system booted.
                 Then, this can be used to measure the expense of an operation
                 because the calls to allocate memory are often considered to 
		 be cpu-intensive."
        ::= { eriRouterMemoryEntry 6 }

--
-- Compliance statements
--

eriRouterSmsMemoryCompliances OBJECT IDENTIFIER ::= { eriRouterMemoryMIBConformance 1 }
eriRouterSmsMemoryGroups      OBJECT IDENTIFIER ::= { eriRouterMemoryMIBConformance 2 }
eriRouterMemoryCompliances    OBJECT IDENTIFIER ::= { eriRouterMemoryMIBConformance 3 }
eriRouterMemoryGroups         OBJECT IDENTIFIER ::= { eriRouterMemoryMIBConformance 4 }

eriRouterMemoryCompliance MODULE-COMPLIANCE
        STATUS       current
        DESCRIPTION
                "The requirements for conformance to this Memory
                 Usage MIB."
        MODULE      -- this module
        MANDATORY-GROUPS {
            eriRouterMemoryGroup
        }
        ::= { eriRouterMemoryCompliances 1}

-- Units of conformance

eriRouterMemoryGroup OBJECT-GROUP
        OBJECTS {
                eriRouterMemoryModule,
                eriRouterMemoryFreeKBytes,
                eriRouterMemoryKBytesInUse,
                eriRouterMemoryBlocksInUse,
                eriRouterMemoryCumulBlocks
        }
        STATUS       current
        DESCRIPTION
                "The collection of objects providing memory usage
                 information."
        ::= { eriRouterMemoryGroups 1}

-- Obsolete Definitions

eriRouterSmsMemoryGroup	OBJECT-GROUP
	OBJECTS {
		eriRouterSmsMemoryModule,
		eriRouterSmsMemoryFreeBytes,
		eriRouterSmsMemoryBytesInUse,
		eriRouterSmsMemoryBlocksInUse,
		eriRouterSmsMemoryCumulBlocks
	}
	STATUS	obsolete
	DESCRIPTION
		"The collection of objects providing SMS memory usage
                 information."
	::= { eriRouterSmsMemoryGroups 1}

eriRouterSmsMemoryCompliance MODULE-COMPLIANCE
	STATUS       obsolete
	DESCRIPTION
		"The compliance statement for SNMP entities which implement
		 the SMS memory usage MIB."
	MODULE      -- this module
	MANDATORY-GROUPS {
		eriRouterSmsMemoryGroup
	}
	::= { eriRouterSmsMemoryCompliances 1}

END
