-- %DNP% $Id: RBN-STACKEDVLAN-CAP.my,v 1.1.2.1.136.3 2011/06/15 18:19:46 danielhe Exp $
-- %DNP% $Source: /cvsroot/pkt/sw/se/xc/bsd/config/snmp/mibs/Attic/RBN-STACKEDVLAN-CAP.my,v $
-- *****************************************************************
-- RBN-STACKEDVLAN-CAP: RBN-STACKEDVLAN-MIB Agent Capabilities
--
-- Copyright (c) 2007, 2010-2011 Ericsson AB
-- All rights reserved.
--
-- *****************************************************************

RBN-STACKEDVLAN-CAP DEFINITIONS ::= BEGIN

IMPORTS
        MODULE-IDENTITY
                FROM SNMPv2-SMI
        AGENT-CAPABILITIES
                FROM SNMPv2-CONF
        rbnCapabilities
                FROM RBN-SMI;
 
rbnStackedVlanCap MODULE-IDENTITY
        LAST-UPDATED    "201106150000Z" -- Jun 15, 2011
        ORGANIZATION    "Ericsson AB."
        CONTACT-INFO
                "       Ericsson AB.

            Postal:     100 Headquarters Dr.
			San Jose, CA  95134
			USA

		 Phone:	+1 408 750 5000
		   Fax: +1 408 750 5599
		"
        DESCRIPTION
                "The Agent Capabilities of the STACKED
                 VLAN MIB (RBN-STACKEDVLAN-MIB).

                If this MIB implementation is platform-dependent,
                the PRODUCT-RELEASE clause contains Ericsson SEOS version and
                at least one of the following Ericsson product families:
                    [SE]  SmartEdge Multi-service Edge Router (MSER) family
                    [SM]  SM family of Metro Ethernet Service Transport platforms
                    [SSR] Smart Service Router (SSR) family"

        REVISION        "201106150000Z" -- Jun 15, 2011
        DESCRIPTION
            "Update DESCRIPTION clause of MODULE-IDENTITY
            and PRODUCT-RELEASE clause of AGENT-CAPABILITIES."
        REVISION    "201011010000Z" -- Nov 1, 2010
        DESCRIPTION
            "Modified PRODUCT-RELEASE clause for consistent naming.
             Updated CONTACT-INFO."

        REVISION        "200702270000Z" -- Feb 27, 2007
        DESCRIPTION
                "Initial version"
        ::= { rbnCapabilities 71 }

rbnStackedVlanCap1 AGENT-CAPABILITIES
        PRODUCT-RELEASE "SEOS 6.0.5.1 [SE]; SEOS 6.3.X [SM]; SEOS 11.1.x [SSR]"
        STATUS          current
        DESCRIPTION     "RBN-STACKEDVLAN-MIB capabilities"
        SUPPORTS        RBN-STACKEDVLAN-MIB
        INCLUDES {
                    rbnStackedVlanMIBGroup
                 }

        ::= { rbnStackedVlanCap 1 }

END
