-- %DNP% $Id: RBN-BIND-CAP.my,v 1.1.4.6.386.3 2011/06/15 18:19:45 danielhe Exp $
-- %DNP% $Source: /cvsroot/pkt/sw/se/xc/bsd/config/snmp/mibs/Attic/RBN-BIND-CAP.my,v $
-- *****************************************************************
-- RBN-BIND-CAP	    Bind Mib Capabilities
--
-- Copyright (c) 2002-2003, 2010-2011 Ericsson AB
-- All rights reserved.
--
-- *****************************************************************

RBN-BIND-CAP DEFINITIONS ::= BEGIN

IMPORTS

	MODULE-IDENTITY
			FROM SNMPv2-SMI
	AGENT-CAPABILITIES
			FROM SNMPv2-CONF
	SnmpAdminString
			FROM SNMP-FRAMEWORK-MIB
	rbnCapabilities
			FROM RBN-SMI;

rbnBindMibCap MODULE-IDENTITY
        LAST-UPDATED    "201106150000Z" -- Jun 15, 2011
        ORGANIZATION    "Ericsson Inc."
        CONTACT-INFO
                "       Ericsson, Inc.

                Postal: 100 Headquarters Dr.
                        San Jose, CA  95134
                        USA

                 Phone: +1 408 750 5000
                   Fax: +1 408 750 5599
                "
	DESCRIPTION
		"The Agent Capabilities of the Bind MIB.

                If this MIB implementation is platform-dependent,
                the PRODUCT-RELEASE clause contains Ericsson SEOS version and
                at least one of the following Ericsson product families:
                    [SE]  SmartEdge Multi-service Edge Router (MSER) family
                    [SM]  SM family of Metro Ethernet Service Transport platforms
                    [SSR] Smart Service Router (SSR) family"

        REVISION        "201106150000Z" -- Jun 15, 2011
        DESCRIPTION
            "Update DESCRIPTION clause of MODULE-IDENTITY
            and PRODUCT-RELEASE clause of AGENT-CAPABILITIES."
        REVISION    "201011010000Z" -- Nov 1, 2010
        DESCRIPTION
            "Modified PRODUCT-RELEASE clause for consistent naming.
             Updated CONTACT-INFO."

        REVISION        "200310131700Z" -- October 13, 2003
        DESCRIPTION
                "Added rbnBindMibCap4 for AOS release 7.0.X.X"

        REVISION        "200307070000Z" -- Jul 7, 2003
        DESCRIPTION
                "Added rbnBindMibCap3 for SmartEdge release 2.5.4."

        REVISION        "200301100000Z" -- Jan 10, 2003
        DESCRIPTION
                "Added rbnBindMibCap2 for SmartEdge release 2.4.4."

	REVISION	"200201071700Z" -- Jan 7, 2001
	DESCRIPTION
		"Initial version ."

	::= { rbnCapabilities 40 }

rbnBindMibCap1 AGENT-CAPABILITIES
	PRODUCT-RELEASE	"AOS 6.0.X.X"
	STATUS		current
	DESCRIPTION	"RBN-BIND-MIB capabilities"
	SUPPORTS	RBN-BIND-MIB
	INCLUDES {
		rbnBindConfigGroup
	}

	VARIATION rbnBindName
	WRITE-SYNTAX SnmpAdminString (SIZE (1..64))
	DESCRIPTION
		"The length of a line allowed in the CLI is 128 characters.
		Thus, in order to manipulate objects created with SNMP via
		the CLI, the length must be limited."

	::= { rbnBindMibCap 1 }

rbnBindMibCap2 AGENT-CAPABILITIES
        PRODUCT-RELEASE "SEOS 2.4.4"
        STATUS          current
        DESCRIPTION     "RBN-BIND-MIB capabilities"
        SUPPORTS        RBN-BIND-MIB
        INCLUDES {
                rbnBindConfigGroup
        }

        VARIATION       rbnBindType
        ACCESS          read-only
        DESCRIPTION
                 "The following types are supported in Release 2.4
                      unbound,
                      authBind,
                      interfaceBind,
                      subscriberBind,
                 Write access is not allowed.

                 REFERENCE SmartEdge 800 Router Configuration Guide Release 2.4"

        VARIATION       rbnBindName
        WRITE-SYNTAX    SnmpAdminString (SIZE (1..64))
        ACCESS          read-only
        DESCRIPTION
                "The length of a line allowed in the CLI is 128 characters.
                Thus, in order to manipulate objects created with SNMP via
                the CLI, the length must be limited. Write access is not
                allowed"

        VARIATION       rbnBindPassword
        ACCESS          read-only
        DESCRIPTION     "Write access is not allowed."

        VARIATION       rbnBindContext
        ACCESS          read-only
        DESCRIPTION
                 "The object is only applicable to the following type[s]
                      interfaceBind,
                      subscriberBind
                  Write access is not allowed."

        VARIATION       rbnBindAuthContext
        ACCESS          read-only
        DESCRIPTION
                 "The object is only applicable to the following type[s]
                      authBind
                  Write access is not allowed."

        VARIATION       rbnBindServiceGrp
        ACCESS          not-implemented
        DESCRIPTION    "Object not supported."

        VARIATION       rbnBindAcl
        ACCESS          not-implemented
        DESCRIPTION    "Object not supported."

        VARIATION       rbnBindAuthChap
        ACCESS          read-only
        DESCRIPTION
                 "The object is only applicable to the following type[s]
                      authBind
                  Write access is not allowed."

        VARIATION       rbnBindAuthPap
        ACCESS          read-only
        DESCRIPTION
                 "The object is only applicable to the following type[s]
                      authBind
                  Write access is not allowed."

        VARIATION       rbnBindAuthWait
        ACCESS          read-only
        DESCRIPTION
                 "The object is only applicable to the following type[s]
                      authBind
                  Write access is not allowed."

        VARIATION       rbnBindMaxSessions
        ACCESS          read-only
        DESCRIPTION
                 "The object is only applicable to the following type[s]
                      authBind
                  Write access is not allowed."

        VARIATION      rbnBindPvcSlot
        ACCESS         not-implemented
        DESCRIPTION    "Object not supported."

        VARIATION      rbnBindPvcPort
        ACCESS         not-implemented
        DESCRIPTION    "Object not supported."

        VARIATION      rbnBindVpn
        ACCESS         not-implemented
        DESCRIPTION    "Object not supported."

        ::= { rbnBindMibCap 2 }

rbnBindMibCap3 AGENT-CAPABILITIES
        PRODUCT-RELEASE "SEOS 2.5.4 [SE]; SEOS 6.3.X [SM]; SEOS 11.1.X [SSR]"
        STATUS          current
        DESCRIPTION     "RBN-BIND-MIB capabilities"
        SUPPORTS        RBN-BIND-MIB
        INCLUDES {
                rbnBindConfigGroup
        }

        VARIATION       rbnBindType
        SYNTAX          INTEGER {
                        unbound(1),            -- state on initial creation
                        authBind(2),           -- "bind authentication"
                        interfaceBind(4),      -- "bind interface"
                        subscriberBind(5)      -- "bind subscriber"
                        }
        ACCESS          read-only
        DESCRIPTION
                "Write access is not allowed.  The values bypassBind(3),
                l2tptunnelBind(6), sessionBind(7), dot1qBind(8),
                multiIntfBind(9), multiSubBind(10), and multiClipsBind(11)
                are not supported."

        VARIATION       rbnBindName
        SYNTAX          SnmpAdminString (SIZE (1..127))
        ACCESS          read-only
        DESCRIPTION
                "Write access is not allowed."

        VARIATION       rbnBindPassword
        ACCESS          read-only
        DESCRIPTION
                "Write access is not allowed."

        VARIATION       rbnBindContext
        ACCESS          read-only
        DESCRIPTION
                "Write access is not allowed."

        VARIATION       rbnBindAuthContext
        ACCESS          read-only
        DESCRIPTION
                "Write access is not allowed."

        VARIATION       rbnBindServiceGrp
        ACCESS          not-implemented
        DESCRIPTION
                "Object not supported."

        VARIATION       rbnBindAcl
        ACCESS          not-implemented
        DESCRIPTION
                "Object not supported."

        VARIATION       rbnBindAuthChap
        ACCESS          read-only
        DESCRIPTION
                "Write access is not allowed."

        VARIATION       rbnBindAuthPap
        ACCESS          read-only
        DESCRIPTION
                "Write access is not allowed."

        VARIATION       rbnBindAuthWait
        ACCESS          read-only
        DESCRIPTION
                "Write access is not allowed."

        VARIATION       rbnBindAuthPapFirst
        ACCESS          read-only
        DESCRIPTION
                "Write access is not allowed."

        VARIATION       rbnBindMaxSessions
        ACCESS          read-only
        DESCRIPTION
                "The maximum number of concurrent PPPoE sessions allowed
                on the circuit on the SE800/400 platform is 8000.

                Write access is not allowed."

        VARIATION      rbnBindPvcSlot
        ACCESS         not-implemented
        DESCRIPTION
                "Object not supported."

        VARIATION      rbnBindPvcPort
        ACCESS         not-implemented
        DESCRIPTION
                "Object not supported."

        VARIATION      rbnBindVpn
        ACCESS         not-implemented
        DESCRIPTION
                "Object not supported."

        ::= { rbnBindMibCap 3 }

rbnBindMibCap4 AGENT-CAPABILITIES
	PRODUCT-RELEASE	"AOS 7.0.X.X"
	STATUS		current
	DESCRIPTION	"RBN-BIND-MIB capabilities"
	SUPPORTS	RBN-BIND-MIB
	INCLUDES {
		rbnBindConfigGroup2
	}

	VARIATION rbnBindName
	WRITE-SYNTAX SnmpAdminString (SIZE (1..64))
	DESCRIPTION
		"The length of a line allowed in the CLI is 128 characters.
		Thus, in order to manipulate objects created with SNMP via
		the CLI, the length must be limited."

	::= { rbnBindMibCap 4 }

END
