-- %DNP% $Id: ERICSSON-ROUTER-IETF-ETHER-WIS-CAP.my,v 1.1.4.5 2011/06/15 18:19:45 danielhe Exp $
-- %DNP% $Source: /cvsroot/pkt/sw/se/xc/bsd/config/snmp/mibs/Attic/ERICSSON-ROUTER-IETF-ETHER-WIS-CAP.my,v $
-- *****************************************************************
-- ERICSSON-ROUTER-IETF-ETHER-WIS-CAP.my    IETF ETHER-WIS 
--
-- Copyright (c) 2010, 2015 Ericsson AB.
-- All rights reserved.
-- 
-- *****************************************************************

ERICSSON-ROUTER-IETF-ETHER-WIS-CAP DEFINITIONS ::= BEGIN

IMPORTS
	MODULE-IDENTITY
		FROM SNMPv2-SMI
	AGENT-CAPABILITIES
		FROM SNMPv2-CONF
	eriRouterCapabilities
		FROM ERICSSON-ROUTER-SMI;

eriRouterIetfEtherWisCap MODULE-IDENTITY
	LAST-UPDATED    "201501141800Z" -- Jan 14, 2015
	ORGANIZATION	"Ericsson AB."
	CONTACT-INFO
		"	Ericsson AB.

                Postal: 100 Headquarters Dr.
                        San Jose, CA  95134
                        USA

                 Phone: +1 408 570 5000
                   Fax: +1 408 570 5599"

	DESCRIPTION
		"The Agent Capabilities of the IETF ETHER-WIS-MIB.

                If this MIB implementation is platform-dependent,
                the PRODUCT-RELEASE clause contains Ericsson SEOS version and
                at least one of the following Ericsson product families:
                    [SE]  SmartEdge Multi-service Edge Router (MSER) family
                    [SM]  SM family of Metro Ethernet Service Transport platforms
                    [SSR] Smart Service Router (SSR) family"

        REVISION        "201501141800Z" -- Jan 14, 2015
        DESCRIPTION
                "Updated RBN/rbn/Rbn as ERICSSON-ROUTER/eriRouter/EriRouter
                 to migrate RBN MIB to ERICSSON MIB."

        REVISION        "201106150000Z" -- Jun 15, 2011
        DESCRIPTION
                "Update DESCRIPTION clause of MODULE-IDENTITY
                and PRODUCT-RELEASE clause of AGENT-CAPABILITIES."
        
	REVISION        "200903031700Z" -- March 3, 2009
	DESCRIPTION
		"Initial version"
        ::= { eriRouterCapabilities 96 }

eriRouterIetfEtherWisCap1 AGENT-CAPABILITIES
	PRODUCT-RELEASE	"SEOS 6.3"
	STATUS		current
	DESCRIPTION	"ETHER-WIS capabilities"
	SUPPORTS	ETHER-WIS
	INCLUDES {
            etherWisPathGroup
	}
	::= { eriRouterIetfEtherWisCap 1 }

END
