-- *****************************************************************
-- ERICSSON-ROUTER-HW-RES-MGMT-CAP
--
-- Copyright (c) 2016 Ericsson AB.
-- All rights reserved.
--
-- *****************************************************************

 ERICSSON-ROUTER-HW-RES-MGMT-CAP DEFINITIONS ::= BEGIN

     IMPORTS
         MODULE-IDENTITY, OBJECT-TYPE, OBJECT-IDENTITY,
         NOTIFICATION-TYPE, mib-2, Counter32,
         Integer32, TimeTicks                   FROM SNMPv2-SMI

         TEXTUAL-CONVENTION, DisplayString      FROM SNMPv2-TC

         MODULE-COMPLIANCE, OBJECT-GROUP,
         NOTIFICATION-GROUP                     FROM SNMPv2-CONF;

 eriRouterHWResMgmtMibCap MODULE-IDENTITY
     LAST-UPDATED "201604250000Z"  -- 25 April, 2016
     ORGANIZATION "Ericsson AB"
     CONTACT-INFO
         "
          Rong Fu R
          Email: rong.r.fu@ericsson.com

          Zephyr Nie
          Email: zephyr.nie@ericsson.com

          Jiang He
          Email: jiang.he@ericsson.com
         "
     DESCRIPTION
        "The Agent Capabilities of the HW Resource Management MIB
         (ERICSSON-ROUTER-HW-RES-MGMT-MIB)."

     ::= { eriRouterCapabilities 112 }

 eriRouterHWResMgmtMibCap1 AGENT-CAPABILITIES
     PRODUCT-RELEASE "Spitfire 1.1.x [SP]"
     STATUS          current
     DESCRIPTION     "ERICSSON-ROUTER-HW-RES-MGMT-MIB capabilities"
     SUPPORTS        ERICSSON-ROUTER-HW-RES-MGMT-MIB
     INCLUDES {
        eriRouterHWResMgmtMib
     }

     ::= { eriRouterHWResMgmtMibCap 1 }

 END
