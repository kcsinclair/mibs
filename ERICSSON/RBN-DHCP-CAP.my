-- %DNP% $Id: RBN-DHCP-CAP.my,v 1.1.8.1.252.5 2011/06/15 18:19:45 danielhe Exp $
-- %DNP% $Source: /cvsroot/pkt/sw/se/xc/bsd/config/snmp/mibs/Attic/RBN-DHCP-CAP.my,v $
-- *****************************************************************
-- RBN-DHCP-CAP		DHCP Mib Capabilities
--
-- Copyright (c) 2004-2009, 2010 Ericsson AB.
-- All rights reserved.
--
-- *****************************************************************

RBN-DHCP-CAP DEFINITIONS ::= BEGIN

IMPORTS

	MODULE-IDENTITY
			FROM SNMPv2-SMI
	AGENT-CAPABILITIES
			FROM SNMPv2-CONF
	rbnCapabilities
			FROM RBN-SMI;

rbnDhcpMibCap MODULE-IDENTITY
	LAST-UPDATED    "201106150000Z" -- Jun 15, 2011
	ORGANIZATION	"Ericsson AB"
	CONTACT-INFO
		"	Ericsson, AB.

		Postal:	100 Headquarters Dr 
			San Jose, CA  95134
			USA

		 Phone:	+1 408 750 5000
		   Fax: +1 408 750 5599"
	DESCRIPTION
		"The Agent Capabilities of the DHCP MIB.

                If this MIB implementation is platform-dependent,
                the PRODUCT-RELEASE clause contains Ericsson SEOS version and
                at least one of the following Ericsson product families:
                    [SE]  SmartEdge Multi-service Edge Router (MSER) family
                    [SM]  SM family of Metro Ethernet Service Transport platforms
                    [SSR] Smart Service Router (SSR) family"

        REVISION        "201106150000Z" -- Jun 15, 2011
        DESCRIPTION
            "Update DESCRIPTION clause of MODULE-IDENTITY
            and PRODUCT-RELEASE clause of AGENT-CAPABILITIES."
	REVISION	"201003101700Z" -- Mar 10, 2010
	DESCRIPTION
		"Added rbnDhcpMibCap3 AGENT-CAPABILITIES."

	REVISION	"200510141700Z" -- Oct 14, 2005
	DESCRIPTION
		"Added rbnDhcpMibCap2 AGENT-CAPABILITIES."

	REVISION	"200405031700Z" -- May 3, 2004
	DESCRIPTION
		"Initial version."

	::= { rbnCapabilities 57 }

rbnDhcpMibCap1 AGENT-CAPABILITIES
	PRODUCT-RELEASE	"AOS 6.1.X.X"
	STATUS		current
	DESCRIPTION	"RBN-DHCP-MIB capabilities"
	SUPPORTS	RBN-DHCP-MIB
	INCLUDES {
		rbnDhcpThresholdGroup,
		rbnDhcpThresholdNotifyGroup
	}

	::= { rbnDhcpMibCap 1 }

rbnDhcpMibCap2 AGENT-CAPABILITIES
	PRODUCT-RELEASE	"SEOS 5.0.3"
	STATUS		current
	DESCRIPTION	"RBN-DHCP-MIB capabilities"
	SUPPORTS	RBN-DHCP-MIB
	INCLUDES {
		rbnDhcpCtxThresholdGroup,
		rbnDhcpRangeThresholdGroup,
		rbnDhcpCtxThresholdNotifyGroup,
		rbnDhcpRangeThresholdNotifyGroup
	}

        VARIATION      rbnDhcpIntfThresholdContextName
        ACCESS         not-implemented
        DESCRIPTION
                "Object not supported."

        VARIATION      rbnDhcpIntfThresholdSize
        ACCESS         not-implemented
        DESCRIPTION
                "Object not supported."

        VARIATION      rbnDhcpIntfThresholdAvailable
        ACCESS         not-implemented
        DESCRIPTION
                "Object not supported."

        VARIATION      rbnDhcpIntfThresholdInuse
        ACCESS         not-implemented
        DESCRIPTION
                "Object not supported."

        VARIATION      rbnDhcpIntfThresholdFallingThreshold
        ACCESS         not-implemented
        DESCRIPTION
                "Object not supported."

        VARIATION      rbnDhcpIntfThresholdFallingSendTrap
        ACCESS         not-implemented
        DESCRIPTION
                "Object not supported."

        VARIATION      rbnDhcpIntfThresholdFallingLogMessage
        ACCESS         not-implemented
        DESCRIPTION
                "Object not supported."

        VARIATION      rbnDhcpIntfThresholdRisingThreshold
        ACCESS         not-implemented
        DESCRIPTION
                "Object not supported."

        VARIATION      rbnDhcpIntfThresholdRisingSendTrap
        ACCESS         not-implemented
        DESCRIPTION
                "Object not supported."

        VARIATION      rbnDhcpIntfThresholdRisingLogMessage
        ACCESS         not-implemented
        DESCRIPTION
                "Object not supported."

	::= { rbnDhcpMibCap 2 }

rbnDhcpMibCap3 AGENT-CAPABILITIES
	PRODUCT-RELEASE	"SEOS 6.1.x [SE]; SEOS 6.3.X [SM]; SEOS 11.1.X [SSR]"
	STATUS		current
	DESCRIPTION	"RBN-DHCP-MIB capabilities"
	SUPPORTS	RBN-DHCP-MIB
	INCLUDES {
                rbnDhcpCtxThresholdGroup,
                rbnDhcpRangeThresholdGroup,
                rbnDhcpCtxThresholdNotifyGroup,
                rbnDhcpRangeThresholdNotifyGroup,
                rbnDhcpLeaseFileFailureTrapGroup,
                rbnDhcpLeaseFileFailureNotifyGroup
	}

        VARIATION      rbnDhcpIntfThresholdContextName
        ACCESS         not-implemented
        DESCRIPTION
                "Object not supported."

        VARIATION      rbnDhcpIntfThresholdSize
        ACCESS         not-implemented
        DESCRIPTION
                "Object not supported."

        VARIATION      rbnDhcpIntfThresholdAvailable
        ACCESS         not-implemented
        DESCRIPTION
                "Object not supported."

        VARIATION      rbnDhcpIntfThresholdInuse
        ACCESS         not-implemented
        DESCRIPTION
                "Object not supported."

        VARIATION      rbnDhcpIntfThresholdFallingThreshold
        ACCESS         not-implemented
        DESCRIPTION
                "Object not supported."

        VARIATION      rbnDhcpIntfThresholdFallingSendTrap
        ACCESS         not-implemented
        DESCRIPTION
                "Object not supported."

        VARIATION      rbnDhcpIntfThresholdFallingLogMessage
        ACCESS         not-implemented
        DESCRIPTION
                "Object not supported."

        VARIATION      rbnDhcpIntfThresholdRisingThreshold
        ACCESS         not-implemented
        DESCRIPTION
                "Object not supported."

        VARIATION      rbnDhcpIntfThresholdRisingSendTrap
        ACCESS         not-implemented
        DESCRIPTION
                "Object not supported."

        VARIATION      rbnDhcpIntfThresholdRisingLogMessage
        ACCESS         not-implemented
        DESCRIPTION
                "Object not supported."

	::= { rbnDhcpMibCap 3 }

END
