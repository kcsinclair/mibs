-- %DNP% $Id: RBN-QOS-CAP.my,v 1.1.2.11.92.6 2011/06/15 18:19:46 danielhe Exp $
-- %DNP% $Source: /cvsroot/pkt/sw/se/xc/bsd/config/snmp/mibs/Attic/RBN-QOS-CAP.my,v $
-- *****************************************************************
-- RBN-QOS-CAP	 QOS MIB Capabilities
--
-- Copyright (c) 2002-2003, 2005-2007, 2010-2011 Ericsson AB.
-- All rights reserved.
-- 
-- *****************************************************************

RBN-QOS-CAP DEFINITIONS ::= BEGIN

IMPORTS
	MODULE-IDENTITY
		FROM SNMPv2-SMI
	AGENT-CAPABILITIES
		FROM SNMPv2-CONF
	rbnCapabilities
		FROM RBN-SMI;

rbnQosCap MODULE-IDENTITY
        LAST-UPDATED    "201106150000Z" -- Jun 15, 2011
        ORGANIZATION    "Ericsson AB."
        CONTACT-INFO
                "       Ericsson AB.

            Postal:     100 Headquarters Dr.
			San Jose, CA  95134
			USA

		 Phone:	+1 408 750 5000
		   Fax: +1 408 750 5599
		"
	DESCRIPTION
		"The Agent Capabilities of the Quality of Service
                 counters MIB (RBN-QOS-MIB).

                If this MIB implementation is platform-dependent,
                the PRODUCT-RELEASE clause contains Ericsson SEOS version and
                at least one of the following Ericsson product families:
                    [SE]  SmartEdge Multi-service Edge Router (MSER) family
                    [SM]  SM family of Metro Ethernet Service Transport platforms
                    [SSR] Smart Service Router (SSR) family"

        REVISION        "201106150000Z" -- Jun 15, 2011
        DESCRIPTION
            "Update DESCRIPTION clause of MODULE-IDENTITY
            and PRODUCT-RELEASE clause of AGENT-CAPABILITIES."
        REVISION    "201011010000Z" -- Nov 1, 2010
        DESCRIPTION
            "Modified PRODUCT-RELEASE clause for consistent naming.
            "

        REVISION        "201003010000Z" -- March 1, 2010
        DESCRIPTION
                "Addes rbnQosCap7. Updated rbnQosSubscriberQueueStatsEntry
                 DESCRIPTION clause in rbnQosCap7 to indicate WFQ support 
                 for ATM subscribers. "

	REVISION        "201001050000Z" -- Jan 5, 2010
	DESCRIPTION
                "Updated rbnQosSubscriberQueueStatsEntry DESCRIPTION clause in 
                 rbnQosCap6 to indicate MDRR support. "

	REVISION        "200708140000Z" -- Aug 14, 2007
	DESCRIPTION
		"Added a new OID: rbnQosCap6."

	REVISION        "200609120000Z" -- Sept 12, 2006
	DESCRIPTION
		"Added a new OID: rbnQosCap5."

	REVISION        "200509260000Z" -- Sept 26, 2005
	DESCRIPTION
		"Added a new OID: rbnQosCap4."

	REVISION        "200503100000Z" -- Mar 10, 2005
	DESCRIPTION
		"Added a new OID: rbnQosCap3."

	REVISION        "200308120000Z" -- Aug 12, 2003
	DESCRIPTION
		"Added a new OID: rbnQosCap2."

	REVISION        "200207010000Z" -- July 1, 2002
	DESCRIPTION
		"Initial version."
	::= { rbnCapabilities 45 }

rbnQosCap1 AGENT-CAPABILITIES
	PRODUCT-RELEASE	"SEOS 2.3.x"
	STATUS		current
	DESCRIPTION	"RBN-QOS-MIB capabilities"
	SUPPORTS	RBN-QOS-MIB
	INCLUDES {
		rbnQosIfGroup
		}

	::= { rbnQosCap 1 }

rbnQosCap2 AGENT-CAPABILITIES
	PRODUCT-RELEASE	"SEOS 2.5.4"
	STATUS		current
	DESCRIPTION	"RBN-QOS-MIB capabilities"
	SUPPORTS	RBN-QOS-MIB
	INCLUDES {
		rbnQosIfGroup,
		rbnQosIfQueueGroup
		}

	VARIATION rbnQosIfInDroppedOctets
	DESCRIPTION
	"This object is not supported for atm-ds3-12-port and atm-oc3-4-port
	cards."

	VARIATION rbnQosIfHCInDroppedOctets
	DESCRIPTION
	"This object is not supported for atm-ds3-12-port and atm-oc3-4-port
	cards."

	VARIATION rbnQosIfOutDroppedOctets
	DESCRIPTION
	"This object is not supported for atm-ds3-12-port and atm-oc3-4-port
	cards."

	VARIATION rbnQosIfHCOutDroppedOctets
	DESCRIPTION
	"This object is not supported for atm-ds3-12-port and atm-oc3-4-port
	cards."

	VARIATION rbnQosIfQueueWredDroppedOctets
	DESCRIPTION
	"This object is not supported for atm-ds3-12-port and atm-oc3-4-port
	cards."

	VARIATION rbnQosIfQueueHCWredDroppedOctets
	DESCRIPTION
	"This object is not supported for atm-ds3-12-port and atm-oc3-4-port
	cards."

	VARIATION rbnQosIfQueueTailDroppedOctets
	DESCRIPTION
	"This object is not supported for atm-ds3-12-port and atm-oc3-4-port
	cards."

	VARIATION rbnQosIfQueueHCTailDroppedOctets
	DESCRIPTION
	"This object is not supported for atm-ds3-12-port and atm-oc3-4-port
	cards."

	::= { rbnQosCap 2 }

rbnQosCap3 AGENT-CAPABILITIES
	PRODUCT-RELEASE "SEOS 2.6.5"
	STATUS          current
	DESCRIPTION     "RBN-QOS-MIB capabilities"
	SUPPORTS        RBN-QOS-MIB
	INCLUDES {
		rbnQosIfGroup,
		rbnQosIfQueueGroup
		}

	VARIATION rbnQosIfInDroppedOctets
	DESCRIPTION
	"This object is not supported for ATM cards using PortMaker II
	(PM2) SAR, e.g. atm-ds3-12-port, atm-oc3-4-port, atm-oc12e-1-port,
	etc."

	VARIATION rbnQosIfHCInDroppedOctets
	DESCRIPTION
	"This object is not supported for ATM cards using PortMaker II
	(PM2) SAR, e.g. atm-ds3-12-port, atm-oc3-4-port, atm-oc12e-1-port,
	etc."

	VARIATION rbnQosIfOutDroppedOctets
	DESCRIPTION
	"This object is not supported for ATM cards using PortMaker II
	(PM2) SAR, e.g. atm-ds3-12-port, atm-oc3-4-port, atm-oc12e-1-port,
	etc."

	VARIATION rbnQosIfHCOutDroppedOctets
	DESCRIPTION
	"This object is not supported for ATM cards using PortMaker II
	(PM2) SAR, e.g. atm-ds3-12-port, atm-oc3-4-port, atm-oc12e-1-port,
	etc."

	VARIATION rbnQosIfQueueWredDroppedOctets
	DESCRIPTION
	"This object is not supported for ATM cards using PortMaker II
	(PM2) SAR, e.g. atm-ds3-12-port, atm-oc3-4-port, atm-oc12e-1-port,
	etc."

	VARIATION rbnQosIfQueueHCWredDroppedOctets
	DESCRIPTION
	"This object is not supported for ATM cards using PortMaker II
	(PM2) SAR, e.g. atm-ds3-12-port, atm-oc3-4-port, atm-oc12e-1-port,
	etc."

	VARIATION rbnQosIfQueueTailDroppedOctets
	DESCRIPTION
	"This object is not supported for ATM cards using PortMaker II
	(PM2) SAR, e.g. atm-ds3-12-port, atm-oc3-4-port, atm-oc12e-1-port,
	etc."

	VARIATION rbnQosIfQueueHCTailDroppedOctets
	DESCRIPTION
	"This object is not supported for ATM cards using PortMaker II
	(PM2) SAR, e.g. atm-ds3-12-port, atm-oc3-4-port, atm-oc12e-1-port,
	etc."

        ::= { rbnQosCap 3 }

rbnQosCap4 AGENT-CAPABILITIES
	PRODUCT-RELEASE "SEOS 5.0.3"
	STATUS          current
	DESCRIPTION     "RBN-QOS-MIB capabilities"
	SUPPORTS        RBN-QOS-MIB
	INCLUDES {
		rbnQosIfGroup,
		rbnQosIfQueueGroup,
		rbnQosSubscriberQueueGroup
		}

	VARIATION rbnQosIfInDroppedOctets
	DESCRIPTION
	"This object is not supported for ATM cards using PortMaker II
	(PM2) SAR, e.g. atm-ds3-12-port, atm-oc3-4-port, atm-oc12e-1-port,
	etc."

	VARIATION rbnQosIfHCInDroppedOctets
	DESCRIPTION
	"This object is not supported for ATM cards using PortMaker II
	(PM2) SAR, e.g. atm-ds3-12-port, atm-oc3-4-port, atm-oc12e-1-port,
	etc."

	VARIATION rbnQosIfOutDroppedOctets
	DESCRIPTION
	"This object is not supported for ATM cards using PortMaker II
	(PM2) SAR, e.g. atm-ds3-12-port, atm-oc3-4-port, atm-oc12e-1-port,
	etc."

	VARIATION rbnQosIfHCOutDroppedOctets
	DESCRIPTION
	"This object is not supported for ATM cards using PortMaker II
	(PM2) SAR, e.g. atm-ds3-12-port, atm-oc3-4-port, atm-oc12e-1-port,
	etc."

	VARIATION rbnQosIfQueueWredDroppedOctets
	DESCRIPTION
	"This object is not supported for ATM cards using PortMaker II
	(PM2) SAR, e.g. atm-ds3-12-port, atm-oc3-4-port, atm-oc12e-1-port,
	etc."

	VARIATION rbnQosIfQueueHCWredDroppedOctets
	DESCRIPTION
	"This object is not supported for ATM cards using PortMaker II
	(PM2) SAR, e.g. atm-ds3-12-port, atm-oc3-4-port, atm-oc12e-1-port,
	etc."

	VARIATION rbnQosIfQueueTailDroppedOctets
	DESCRIPTION
	"This object is not supported for ATM cards using PortMaker II
	(PM2) SAR, e.g. atm-ds3-12-port, atm-oc3-4-port, atm-oc12e-1-port,
	etc."

	VARIATION rbnQosIfQueueHCTailDroppedOctets
	DESCRIPTION
	"This object is not supported for ATM cards using PortMaker II
	(PM2) SAR, e.g. atm-ds3-12-port, atm-oc3-4-port, atm-oc12e-1-port,
	etc."

	VARIATION rbnQosSubscriberQueueStatsEntry
	DESCRIPTION
	"This entry is only supported for the PPP and CLIPS subscriber
	session with PWFQ policy applied."

	::= { rbnQosCap 4 }

rbnQosCap5 AGENT-CAPABILITIES
	PRODUCT-RELEASE "SEOS 6.0.3"
	STATUS          current
	DESCRIPTION     "RBN-QOS-MIB capabilities"
	SUPPORTS        RBN-QOS-MIB
	INCLUDES {
		rbnQosIfGroup,
		rbnQosIfQueueGroup,
		rbnQosSubscriberQueueGroup,
		rbnQosIfRLClassStatsGroup,
		rbnQosSubscriberRLClassStatsGroup
		}

	VARIATION rbnQosIfInDroppedOctets
	DESCRIPTION
	"This object is not supported for ATM cards using PortMaker II
	(PM2) SAR, e.g. atm-ds3-12-port, atm-oc3-4-port, atm-oc12e-1-port,
	etc."

	VARIATION rbnQosIfHCInDroppedOctets
	DESCRIPTION
	"This object is not supported for ATM cards using PortMaker II
	(PM2) SAR, e.g. atm-ds3-12-port, atm-oc3-4-port, atm-oc12e-1-port,
	etc."

	VARIATION rbnQosIfOutDroppedOctets
	DESCRIPTION
	"This object is not supported for ATM cards using PortMaker II
	(PM2) SAR, e.g. atm-ds3-12-port, atm-oc3-4-port, atm-oc12e-1-port,
	etc."

	VARIATION rbnQosIfHCOutDroppedOctets
	DESCRIPTION
	"This object is not supported for ATM cards using PortMaker II
	(PM2) SAR, e.g. atm-ds3-12-port, atm-oc3-4-port, atm-oc12e-1-port,
	etc."

	VARIATION rbnQosIfQueueWredDroppedOctets
	DESCRIPTION
	"This object is not supported for ATM cards using PortMaker II
	(PM2) SAR, e.g. atm-ds3-12-port, atm-oc3-4-port, atm-oc12e-1-port,
	etc."

	VARIATION rbnQosIfQueueHCWredDroppedOctets
	DESCRIPTION
	"This object is not supported for ATM cards using PortMaker II
	(PM2) SAR, e.g. atm-ds3-12-port, atm-oc3-4-port, atm-oc12e-1-port,
	etc."

	VARIATION rbnQosIfQueueTailDroppedOctets
	DESCRIPTION
	"This object is not supported for ATM cards using PortMaker II
	(PM2) SAR, e.g. atm-ds3-12-port, atm-oc3-4-port, atm-oc12e-1-port,
	etc."

	VARIATION rbnQosIfQueueHCTailDroppedOctets
	DESCRIPTION
	"This object is not supported for ATM cards using PortMaker II
	(PM2) SAR, e.g. atm-ds3-12-port, atm-oc3-4-port, atm-oc12e-1-port,
	etc."

	VARIATION rbnQosSubscriberQueueStatsEntry
	DESCRIPTION
	"This entry is only supported for the PPP and CLIPS subscriber
	session with PWFQ policy applied."

	VARIATION rbnQosIfRLPolicyType
        SYNTAX INTEGER {
                policing(1),
                metering(2)
        }
        DESCRIPTION
        "The value edrr(3), mdrr(4), pq(5), atmwfq(6), or pwfq(7) is not
        supported."

	VARIATION rbnQosSubsRLPolicyType
        SYNTAX INTEGER {
                policing(1),
                metering(2)
        }
        DESCRIPTION
        "The value edrr(3), mdrr(4), pq(5), atmwfq(6), or pwfq(7) is not
        supported."

	::= { rbnQosCap 5 }


rbnQosCap6 AGENT-CAPABILITIES
	PRODUCT-RELEASE "SEOS 6.2"
	STATUS          current
	DESCRIPTION     "RBN-QOS-MIB capabilities"
	SUPPORTS        RBN-QOS-MIB
	INCLUDES {
		rbnQosIfGroup,
		rbnQosIfQueueGroup,
		rbnQosSubscriberQueueGroup,
		rbnQosIfRLClassStatsGroup,
		rbnQosSubscriberRLClassStatsGroup,
                rbnQosHierarchicalPolicyStatsGroup
		}

	VARIATION rbnQosIfInDroppedOctets
	DESCRIPTION
	"This object is not supported for ATM cards using PortMaker II
	(PM2) SAR, e.g. atm-ds3-12-port, atm-oc3-4-port, atm-oc12e-1-port,
	etc."

	VARIATION rbnQosIfHCInDroppedOctets
	DESCRIPTION
	"This object is not supported for ATM cards using PortMaker II
	(PM2) SAR, e.g. atm-ds3-12-port, atm-oc3-4-port, atm-oc12e-1-port,
	etc."

	VARIATION rbnQosIfOutDroppedOctets
	DESCRIPTION
	"This object is not supported for ATM cards using PortMaker II
	(PM2) SAR, e.g. atm-ds3-12-port, atm-oc3-4-port, atm-oc12e-1-port,
	etc."

	VARIATION rbnQosIfHCOutDroppedOctets
	DESCRIPTION
	"This object is not supported for ATM cards using PortMaker II
	(PM2) SAR, e.g. atm-ds3-12-port, atm-oc3-4-port, atm-oc12e-1-port,
	etc."

	VARIATION rbnQosIfQueueWredDroppedOctets
	DESCRIPTION
	"This object is not supported for ATM cards using PortMaker II
	(PM2) SAR, e.g. atm-ds3-12-port, atm-oc3-4-port, atm-oc12e-1-port,
	etc."

	VARIATION rbnQosIfQueueHCWredDroppedOctets
	DESCRIPTION
	"This object is not supported for ATM cards using PortMaker II
	(PM2) SAR, e.g. atm-ds3-12-port, atm-oc3-4-port, atm-oc12e-1-port,
	etc."

	VARIATION rbnQosIfQueueTailDroppedOctets
	DESCRIPTION
	"This object is not supported for ATM cards using PortMaker II
	(PM2) SAR, e.g. atm-ds3-12-port, atm-oc3-4-port, atm-oc12e-1-port,
	etc."

	VARIATION rbnQosIfQueueHCTailDroppedOctets
	DESCRIPTION
	"This object is not supported for ATM cards using PortMaker II
	(PM2) SAR, e.g. atm-ds3-12-port, atm-oc3-4-port, atm-oc12e-1-port,
	etc."

	VARIATION rbnQosSubscriberQueueStatsEntry
	DESCRIPTION
	"This entry is only supported for the PPP and CLIPS subscriber
	session with PWFQ / MDRR policy applied."

	VARIATION rbnQosIfRLPolicyType
        SYNTAX INTEGER {
                policing(1),
                metering(2)
        }
        DESCRIPTION
        "The value edrr(3), mdrr(4), pq(5), atmwfq(6), or pwfq(7) is not
        supported."

	VARIATION rbnQosSubsRLPolicyType
        SYNTAX INTEGER {
                policing(1),
                metering(2)
        }
        DESCRIPTION
        "The value edrr(3), mdrr(4), pq(5), atmwfq(6), or pwfq(7) is not
        supported."

	VARIATION rbnQosHierarchicalPolicyType
        SYNTAX INTEGER {
                policing(1),
                metering(2)
        }
        DESCRIPTION
        "The value edrr(3), mdrr(4), pq(5), atmwfq(6), or pwfq(7) is not
        supported."

	::= { rbnQosCap 6 }

rbnQosCap7 AGENT-CAPABILITIES
        PRODUCT-RELEASE "SEOS 6.3.X [SE, SM]; SEOS 11.1.x [SSR]"
        STATUS          current
        DESCRIPTION     "RBN-QOS-MIB capabilities"
        SUPPORTS        RBN-QOS-MIB
        INCLUDES {
                rbnQosIfGroup,
                rbnQosIfQueueGroup,
                rbnQosSubscriberQueueGroup,
                rbnQosIfRLClassStatsGroup,
                rbnQosSubscriberRLClassStatsGroup,
                rbnQosHierarchicalPolicyStatsGroup
                }

        VARIATION rbnQosIfInDroppedOctets
        DESCRIPTION
        "This object is not supported for ATM cards using PortMaker II
        (PM2) SAR, e.g. atm-ds3-12-port, atm-oc3-4-port, atm-oc12e-1-port,
        etc."

        VARIATION rbnQosIfHCInDroppedOctets
        DESCRIPTION
        "This object is not supported for ATM cards using PortMaker II
        (PM2) SAR, e.g. atm-ds3-12-port, atm-oc3-4-port, atm-oc12e-1-port,
        etc."

        VARIATION rbnQosIfOutDroppedOctets
        DESCRIPTION
        "This object is not supported for ATM cards using PortMaker II
        (PM2) SAR, e.g. atm-ds3-12-port, atm-oc3-4-port, atm-oc12e-1-port,
        etc."

        VARIATION rbnQosIfHCOutDroppedOctets
        DESCRIPTION
        "This object is not supported for ATM cards using PortMaker II
        (PM2) SAR, e.g. atm-ds3-12-port, atm-oc3-4-port, atm-oc12e-1-port,
        etc."

        VARIATION rbnQosIfQueueWredDroppedOctets
        DESCRIPTION
        "This object is not supported for ATM cards using PortMaker II
        (PM2) SAR, e.g. atm-ds3-12-port, atm-oc3-4-port, atm-oc12e-1-port,
        etc."

        VARIATION rbnQosIfQueueHCWredDroppedOctets
        DESCRIPTION
        "This object is not supported for ATM cards using PortMaker II
        (PM2) SAR, e.g. atm-ds3-12-port, atm-oc3-4-port, atm-oc12e-1-port,
        etc."

        VARIATION rbnQosIfQueueTailDroppedOctets
        DESCRIPTION
        "This object is not supported for ATM cards using PortMaker II
        (PM2) SAR, e.g. atm-ds3-12-port, atm-oc3-4-port, atm-oc12e-1-port,
        etc."

        VARIATION rbnQosIfQueueHCTailDroppedOctets
        DESCRIPTION
        "This object is not supported for ATM cards using PortMaker II
        (PM2) SAR, e.g. atm-ds3-12-port, atm-oc3-4-port, atm-oc12e-1-port,
        etc."

        VARIATION rbnQosSubscriberQueueStatsEntry
        DESCRIPTION
        "This entry is only supported for the PPP and CLIPS subscriber
        session with PWFQ / MDRR, and ATM subscribers with WFQ policy applied."

        VARIATION rbnQosIfRLPolicyType
        SYNTAX INTEGER {
                policing(1),
                metering(2)
        }
        DESCRIPTION
        "The value edrr(3), mdrr(4), pq(5), atmwfq(6), or pwfq(7) is not
        supported."

        VARIATION rbnQosSubsRLPolicyType
        SYNTAX INTEGER {
                policing(1),
                metering(2)
        }
        DESCRIPTION
        "The value edrr(3), mdrr(4), pq(5), atmwfq(6), or pwfq(7) is not
        supported."

        VARIATION rbnQosHierarchicalPolicyType
        SYNTAX INTEGER {
                policing(1),
                metering(2)
        }
        DESCRIPTION
        "The value edrr(3), mdrr(4), pq(5), atmwfq(6), or pwfq(7) is not
        supported."

        ::= { rbnQosCap 7 }

END
