-- %DNP% $Id: RBN-SYS-RESOURCES-CAP.my,v 1.1.2.8.136.6 2011/07/11 20:00:30 ekimpri Exp $
-- %DNP% $Source: /cvsroot/pkt/sw/se/xc/bsd/config/snmp/mibs/Attic/RBN-SYS-RESOURCES-CAP.my,v $
-- *************************************************************
-- RBN-SYS-RESOURCES-CAP   RBN-SYS-RESOURCES-MIB Capabilities
--
-- Copyright (c) 2010 Ericsson AB
-- Copyright (c) 2002-2003, 2005, 2007 RedBack Networks, Inc.
-- All rights reserved.
--
-- *************************************************************

RBN-SYS-RESOURCES-CAP DEFINITIONS ::= BEGIN

IMPORTS
        MODULE-IDENTITY
                FROM SNMPv2-SMI
        AGENT-CAPABILITIES
                FROM SNMPv2-CONF
        rbnCapabilities
                FROM RBN-SMI;

rbnSysResourcesCap MODULE-IDENTITY
        LAST-UPDATED    "201106150000Z" -- Jun 15, 2011
        ORGANIZATION    "Ericsson AB"
        CONTACT-INFO
                    "       Ericsson, Inc.

                     Postal: 100 Headquarters Drive
                             San Jose, CA  95134-1370
                             USA

                     Phone: +1 408 750 5000
                     Fax: +1 408 750 5599"
        DESCRIPTION
                "The Agent Capabilities of the System Resources MIB.

                If this MIB implementation is platform-dependent,
                the PRODUCT-RELEASE clause contains Ericsson SEOS version and
                at least one of the following Ericsson product families:
                    [SE]  SmartEdge Multi-service Edge Router (MSER) family
                    [SM]  SM family of Metro Ethernet Service Transport platforms
                    [SSR] Smart Service Router (SSR) family"

        REVISION        "201106150000Z" -- Jun 15, 2011
        DESCRIPTION
            "Update DESCRIPTION clause of MODULE-IDENTITY
            and PRODUCT-RELEASE clause of AGENT-CAPABILITIES."
        
        REVISION    "201011010000Z" -- Nov 1, 2010
        DESCRIPTION
            "Modified PRODUCT-RELEASE clause for consistent naming.
             Updated CONTACT-INFO.
             
             Add rbnSysResourcesCap6"

        REVISION        "200907160000Z" -- July 16, 2009
        DESCRIPTION
                        "Add rbnSysResourcesCap5, includes
                        SSE objects."

        REVISION        "200705300000Z" -- May 30, 2007
	DESCRIPTION
	                "Add rbnSysResourcesCap4."

        REVISION        "200504180000Z" -- April 18, 2005
        DESCRIPTION
                "Add rbnSysResourcesCap3 and updated the VARIATION
                clause in rbnSysResourcesCap1 and rbnSysResourcesCap2."
        REVISION      	"200309101800Z" -- Sept 10, 2003
        DESCRIPTION
                "Add rbnSysResourcesCap2."

        REVISION      	"200206140000Z" -- June 6, 2002
        DESCRIPTION
                "Initial version."
        ::= { rbnCapabilities 44 }

rbnSysResourcesCap1 AGENT-CAPABILITIES
	PRODUCT-RELEASE "SEOS 2.3.3"
	STATUS          obsolete 
	DESCRIPTION     "This is superceeded by rbnSysResourcesCap4"
	SUPPORTS        RBN-SYS-RESOURCES-MIB
	INCLUDES {
		rbnSRProcessNotifyGroup,
		rbnSRStorageGroup,
		rbnSRProcessEventNotificationGroup
		}

	VARIATION       rbnSRStorageDescr
	DESCRIPTION
		"Limit this textual information to the human readable
		form as specified in the TEXTUAL-CONVENTION DisplayString."

        VARIATION       rbnSRStorageTable
        DESCRIPTION
                "This table is supported for the internal SEOS storage
                device only."

    ::= { rbnSysResourcesCap 1 }

rbnSysResourcesCap2 AGENT-CAPABILITIES
	PRODUCT-RELEASE "SEOS 2.5.6.X"
	STATUS          obsolete
	DESCRIPTION     "This is superceeded by rbnSysResourcesCap4"
	SUPPORTS        RBN-SYS-RESOURCES-MIB
	INCLUDES {
		rbnSRProcessNotifyGroup,
		rbnSRStorageGroup,
		rbnSRNotificationGroup
		}

	VARIATION       rbnSRStorageDescr
	DESCRIPTION
		"Limit this textual information to the human readable
		form as specified in the TEXTUAL-CONVENTION DisplayString."

        VARIATION       rbnSRStorageTable
        DESCRIPTION
                "This table is supported for the internal SEOS storage
                device only."

    ::= { rbnSysResourcesCap 2 }

rbnSysResourcesCap3 AGENT-CAPABILITIES
        PRODUCT-RELEASE "SEOS 4.0.5.X"
        STATUS          current
        DESCRIPTION     "RBN-SYS-RESOURCES-MIB capabilities"
        SUPPORTS        RBN-SYS-RESOURCES-MIB
        INCLUDES {
                rbnSRProcessNotifyGroup,
                rbnSRStorageGroup2,
                rbnSRNotificationGroup2,
                rbnSRSystemGroup
                }

        VARIATION       rbnSRStorageDescr
        DESCRIPTION
                "Limit this textual information to the human readable
                form as specified in the TEXTUAL-CONVENTION DisplayString."

        VARIATION       rbnSRSystemDate
        ACCESS          read-only
        DESCRIPTION
                "Write access is not allowed."

    ::= { rbnSysResourcesCap 3 }

rbnSysResourcesCap4 AGENT-CAPABILITIES
        PRODUCT-RELEASE "SEOS 6.1.X.X"
        STATUS          current
        DESCRIPTION     "RBN-SYS-RESOURCES-MIB capabilities"
        SUPPORTS        RBN-SYS-RESOURCES-MIB
        INCLUDES {
                rbnSRProcessNotifyGroup,
                rbnSRStorageGroup2,
                rbnSRNotificationGroup2,
                rbnSRSystemGroup,
		rbnSRPowerExceededGroup,
		rbnSRPowerNotifyGroup
        }
        VARIATION       rbnSRStorageDescr
        DESCRIPTION
                "Limit this textual information to the human readable
                form as specified in the TEXTUAL-CONVENTION DisplayString."

        VARIATION       rbnSRSystemDate
        ACCESS          read-only
        DESCRIPTION
                "Write access is not allowed."

     ::= { rbnSysResourcesCap 4  }

rbnSysResourcesCap5 AGENT-CAPABILITIES
        PRODUCT-RELEASE "SEOS 6.2.1 [SE]; SEOS 6.3.X [SM]; SEOS 11.1.x [SSR]"
        STATUS          current
        DESCRIPTION     "RBN-SYS-RESOURCES-MIB capabilities"
        SUPPORTS        RBN-SYS-RESOURCES-MIB
        INCLUDES {
                rbnSRProcessNotifyGroup,
                rbnSRStorageGroup2,
                rbnSRNotificationGroup2,
                rbnSRSystemGroup,
                rbnSRPowerExceededGroup,
                rbnSRPowerNotifyGroup,
                rbnSseDiskGroup,
                rbnSseDiskEventObjectGroup,
                rbnSseDiskNotifyGroup
        }
        VARIATION       rbnSRStorageDescr
        DESCRIPTION
                "Limit this textual information to the human readable
                form as specified in the TEXTUAL-CONVENTION DisplayString."

        VARIATION       rbnSRSystemDate
        ACCESS          read-only
        DESCRIPTION
                "Write access is not allowed."

     ::= { rbnSysResourcesCap 5  }


rbnSysResourcesCap6 AGENT-CAPABILITIES
        PRODUCT-RELEASE "SEOS 11.1"
        STATUS          current
        DESCRIPTION     "RBN-SYS-RESOURCES-MIB capabilities"
        SUPPORTS        RBN-SYS-RESOURCES-MIB
        INCLUDES {
                rbnSRProcessNotifyGroup,
                rbnSRStorageGroup2,
                rbnSRNotificationGroup2,
                rbnSRSystemGroup,
                rbnSRPowerExceededGroup,
                rbnSRPowerNotifyGroup,
                rbnSseDiskGroup,
                rbnSseDiskEventObjectGroup,
                rbnSseDiskNotifyGroup,
                rbnIssuGroup,
                rbnIssuNotifyGroup
        }
        VARIATION       rbnSRStorageDescr
        DESCRIPTION
                "Limit this textual information to the human readable
                form as specified in the TEXTUAL-CONVENTION DisplayString."

        VARIATION       rbnSRSystemDate
        ACCESS          read-only
        DESCRIPTION
                "Write access is not allowed."

     ::= { rbnSysResourcesCap 6 }


END
