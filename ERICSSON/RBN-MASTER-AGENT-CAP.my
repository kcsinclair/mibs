-- *****************************************************************
-- RBN-MASTER-AGENT-CAP   MasterAgent Mib Capabilities
--
-- %DNP% Copyright (c) 2015-2016 Ericsson AB
-- %DNP% All rights reserved.
--
-- *****************************************************************
RBN-MASTER-AGENT-CAP DEFINITIONS ::= BEGIN

IMPORTS
        MODULE-IDENTITY, OBJECT-TYPE, NOTIFICATION-TYPE, Unsigned32
                FROM SNMPv2-SMI
        MODULE-COMPLIANCE, OBJECT-GROUP
                FROM SNMPv2-CONF
        RowStatus
                FROM SNMPv2-TC
        agentxSessionDescr
                FROM AGENTX-MIB
        rbnMgmt, rbnCapabilities
                FROM RBN-SMI;

rbnMasterAgentCap MODULE-IDENTITY
	    LAST-UPDATED "201601060000Z"            -- 06 Janurary 2016
	    ORGANIZATION "Ericsson"
	    CONTACT-INFO "postal:   Kovacs Zsolt
		                    Budapest
		                    1117 Irinyi ut

			  email:    kovacs.zsolt@ericssson.com
		         "
	    DESCRIPTION  "An AgentX master mib capabilities.
		         "

	    ::= { rbnCapabilities 109 }

rbnMasterAgentCap1 AGENT-CAPABILITIES
        PRODUCT-RELEASE "IPOS 13.2.x [SSR]"
        STATUS          current
        DESCRIPTION     "RBN-MASTER-AGENT-MIB capabilities"
        SUPPORTS        RBN-MASTER-AGENT-MIB
        INCLUDES {
                    rbnSubAgentLost
                 }
        ::= { rbnMasterAgentCap 1 }

END
