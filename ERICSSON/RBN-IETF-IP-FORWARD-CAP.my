-- %DNP% $Id: RBN-IETF-IP-FORWARD-CAP.my,v 1.1.6.2.452.5 2011/06/15 18:19:45 danielhe Exp $
-- %DNP% $Source: /cvsroot/pkt/sw/se/xc/bsd/config/snmp/mibs/RBN-IETF-IP-FORWARD-CAP.my,v $
-- *****************************************************************
-- RBN-IETF-IP-FORWARD-CAP.my:	IETF IP-FORWARD-MIB Agent Capabilities
--
-- Copyright (c) 1998-2011 Ericsson AB.
-- All rights reserved.
-- 
-- *****************************************************************

RBN-IETF-IP-FORWARD-CAP DEFINITIONS ::= BEGIN

IMPORTS
	MODULE-IDENTITY
		FROM SNMPv2-SMI
	AGENT-CAPABILITIES
		FROM SNMPv2-CONF
	rbnCapabilities
		FROM RBN-SMI
	RowStatus                          
	    FROM SNMPv2-TC;

rbnIetfIpForwardCap MODULE-IDENTITY
    LAST-UPDATED    "201106150000Z" -- Jun 15, 2011
    ORGANIZATION    "Ericsson AB"
    CONTACT-INFO
                "       Ericsson AB.

                 Postal: 100 Headquarters Dr.
                         San Jose, CA  95134
                         USA

                 Phone: +1 408 750 5000
                 Fax: +1 408 750 5599
                "
	DESCRIPTION
		"The Agent Capabilities of IETF IP-FORWARD-MIB (RFC 4292).

                If this MIB implementation is platform-dependent,
                the PRODUCT-RELEASE clause contains Ericsson SEOS version and
                at least one of the following Ericsson product families:
                    [SE]  SmartEdge Multi-service Edge Router (MSER) family
                    [SM]  SM family of Metro Ethernet Service Transport platforms
                    [SSR] Smart Service Router (SSR) family"

        REVISION        "201106150000Z" -- Jun 15, 2011
        DESCRIPTION
            "Update DESCRIPTION clause of MODULE-IDENTITY
            and PRODUCT-RELEASE clause of AGENT-CAPABILITIES."
	REVISION	"201011010000Z" -- Nov 1, 2010
	DESCRIPTION
		"Modified PRODUCT-RELEASE clause for consistent naming.
                "
                
        REVISION        "201003220000Z" -- March 22, 2010
        DESCRIPTION
            "Updated ORGANIZATION/CONTACT-INFO. 
             Added rbnIetfIpForwardCap2 per RFC 4292 implementation"
		 
	REVISION	"200111210000Z"	-- November 21, 2001
	DESCRIPTION
		"Added new OID:
			rbnIetfIpForwardCap2"

        REVISION	"9803242300Z"
        DESCRIPTION
		"Initial version."
	::= { rbnCapabilities 6 }

rbnIetfIpForwardCap1 AGENT-CAPABILITIES
	PRODUCT-RELEASE	"AOS 1.0.X.X"
	STATUS		current
	DESCRIPTION	"IP-FORWARD-MIB capabilities"
	SUPPORTS	IP-FORWARD-MIB
	INCLUDES {
		ipForwardCidrRouteGroup
		}

	-- the ipCidrRouteTable is read-only

	VARIATION	ipCidrRouteIfIndex
	ACCESS		read-only
	DESCRIPTION
		"Row creation or modification is not allowed"

	VARIATION	ipCidrRouteType
	ACCESS		read-only
	DESCRIPTION
		"Row creation or modification is not allowed"

	VARIATION	ipCidrRouteInfo
	ACCESS		read-only
	DESCRIPTION
		"Row creation or modification is not allowed"

	VARIATION	ipCidrRouteNextHopAS
	ACCESS		read-only
	DESCRIPTION
		"Row creation or modification is not allowed"

	VARIATION	ipCidrRouteMetric1
	ACCESS		read-only
	DESCRIPTION
		"Row creation or modification is not allowed"

	VARIATION	ipCidrRouteMetric2
	ACCESS		read-only
	DESCRIPTION
		"Row creation or modification is not allowed"

	VARIATION	ipCidrRouteMetric3
	ACCESS		read-only
	DESCRIPTION
		"Row creation or modification is not allowed"

	VARIATION	ipCidrRouteMetric4
	ACCESS		read-only
	DESCRIPTION
		"Row creation or modification is not allowed"

	VARIATION	ipCidrRouteMetric5
	ACCESS		read-only
	DESCRIPTION
		"Row creation or modification is not allowed"

	VARIATION	ipCidrRouteStatus
	SYNTAX		INTEGER { active(1) }
	ACCESS		read-only
	DESCRIPTION
		"Row creation or modification is not allowed"

	::= { rbnIetfIpForwardCap 1 }

rbnIetfIpForwardCap2 AGENT-CAPABILITIES
	PRODUCT-RELEASE "SEOS 2.0.3.X"
	STATUS		current
	DESCRIPTION	"IP-FORWARD-MIB capabilities"
	SUPPORTS	IP-FORWARD-MIB
	INCLUDES {
		ipForwardCidrRouteGroup
		}

	-- the ipCidrRouteTable is read-only

	VARIATION	ipCidrRouteIfIndex
	ACCESS		read-only
	DESCRIPTION
		"Row creation or modification is not allowed"

	VARIATION	ipCidrRouteType
	ACCESS		read-only
	DESCRIPTION
		"Row creation or modification is not allowed"

	VARIATION	ipCidrRouteInfo
	ACCESS		read-only
	DESCRIPTION
		"Row creation or modification is not allowed"

	VARIATION	ipCidrRouteNextHopAS
	ACCESS		read-only
	DESCRIPTION
		"Row creation or modification is not allowed"

	VARIATION	ipCidrRouteMetric1
	ACCESS		read-only
	DESCRIPTION
		"Row creation or modification is not allowed"

	VARIATION	ipCidrRouteMetric2
	ACCESS		read-only
	DESCRIPTION
		"Row creation or modification is not allowed"

	VARIATION	ipCidrRouteMetric3
	ACCESS		read-only
	DESCRIPTION
		"Row creation or modification is not allowed"

	VARIATION	ipCidrRouteMetric4
	ACCESS		read-only
	DESCRIPTION
		"Row creation or modification is not allowed"

	VARIATION	ipCidrRouteMetric5
	ACCESS		read-only
	DESCRIPTION
		"Row creation or modification is not allowed"

	VARIATION	ipCidrRouteStatus
	SYNTAX		INTEGER { active(1) }
	ACCESS		read-only
	DESCRIPTION
		"Row creation or modification is not allowed"

	::= { rbnIetfIpForwardCap 2 }
	
rbnIetfIpForwardCap3 AGENT-CAPABILITIES
    PRODUCT-RELEASE    "SEOS 6.4.X [SE, SM]; SEOS 11.1.X [SSR]"
    STATUS        current
    DESCRIPTION    "IP-FORWARD-MIB capabilities"
    SUPPORTS    IP-FORWARD-MIB
    INCLUDES {
        ipForwardCidrRouteGroup,
        inetForwardCidrRouteGroup
        }

    -- the ipCidrRouteTable is read-only

    VARIATION    ipCidrRouteIfIndex
    ACCESS        read-only
    DESCRIPTION
        "Row creation or modification is not allowed"

    VARIATION    ipCidrRouteType
    ACCESS        read-only
    DESCRIPTION
        "Row creation or modification is not allowed"

    VARIATION    ipCidrRouteInfo
    ACCESS        read-only
    DESCRIPTION
        "Row creation or modification is not allowed"

    VARIATION    ipCidrRouteNextHopAS
    ACCESS        read-only
    DESCRIPTION
        "Row creation or modification is not allowed"

    VARIATION    ipCidrRouteMetric1
    ACCESS        read-only
    DESCRIPTION
        "Row creation or modification is not allowed"

    VARIATION    ipCidrRouteMetric2
    ACCESS        read-only
    DESCRIPTION
        "Row creation or modification is not allowed"

    VARIATION    ipCidrRouteMetric3
    ACCESS        read-only
    DESCRIPTION
        "Row creation or modification is not allowed"

    VARIATION    ipCidrRouteMetric4
    ACCESS        read-only
    DESCRIPTION
        "Row creation or modification is not allowed"

    VARIATION    ipCidrRouteMetric5
    ACCESS        read-only
    DESCRIPTION
        "Row creation or modification is not allowed"

    VARIATION    ipCidrRouteStatus
    SYNTAX        INTEGER { active(1) }
    ACCESS        read-only
    DESCRIPTION
        "Row creation or modification is not allowed"
        
    --
    -- inetCidrRouteTable implemented without support for read-
    -- create (i.e., in read-only mode)
    --
    VARIATION      inetCidrRouteIfIndex
    ACCESS         read-only
    DESCRIPTION
          "Write access is not required."

    VARIATION      inetCidrRouteType

    ACCESS         read-only
    DESCRIPTION
          "Write access is not required."

    VARIATION      inetCidrRouteNextHopAS
    ACCESS         read-only
    DESCRIPTION
          "Write access is not required."

    VARIATION      inetCidrRouteMetric1
    ACCESS         read-only
    DESCRIPTION
          "Write access is not required."

    VARIATION      inetCidrRouteMetric2
    ACCESS         read-only
    DESCRIPTION
          "Write access is not required."

    VARIATION      inetCidrRouteMetric3
    ACCESS         read-only
    DESCRIPTION
          "Write access is not required."

    VARIATION      inetCidrRouteMetric4
    ACCESS         read-only
    DESCRIPTION
          "Write access is not required."

    VARIATION      inetCidrRouteMetric5
    ACCESS         read-only
    DESCRIPTION
          "Write access is not required."

    VARIATION      inetCidrRouteStatus
    SYNTAX         RowStatus { active(1) }
    ACCESS         read-only
    DESCRIPTION
          "Write access is not required."
          
    ::= { rbnIetfIpForwardCap 3 }
    
END
