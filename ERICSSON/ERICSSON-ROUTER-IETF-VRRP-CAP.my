-- %DNP% $Id: ERICSSON-ROUTER-IETF-VRRP-CAP.my,v 1.1.2.1.6.5 2011/06/15 18:19:45 danielhe Exp $
-- %DNP% $Source: /cvsroot/pkt/sw/se/xc/bsd/config/snmp/mibs/Attic/ERICSSON-ROUTER-IETF-VRRP-CAP.my,v $
-- *****************************************************************
-- ERICSSON-ROUTER-IETF-VRRP-CAP.my: VRRP-MIB Agent Capabilities
--
-- Copyright (c) 2008, 2011 Ericsson AB.
-- Copyright (c) 2014, 2015 Ericsson AB.
-- All rights reserved.
-- 
-- *****************************************************************

ERICSSON-ROUTER-IETF-VRRP-CAP DEFINITIONS ::= BEGIN

IMPORTS
    MODULE-IDENTITY
        FROM SNMPv2-SMI
    AGENT-CAPABILITIES
        FROM SNMPv2-CONF
    eriRouterCapabilities
        FROM ERICSSON-ROUTER-SMI;

eriRouterIetfVrrpCap MODULE-IDENTITY
    LAST-UPDATED    "201501141800Z" -- Jan 14, 2015
    ORGANIZATION    "Ericsson AB."
    CONTACT-INFO
            "       Ericsson AB.

            Postal: 100 Headquarters Dr
                    San Jose, CA  95134
                    USA

             Phone: +1 408 750 5000
               Fax: +1 408 750 5599
            "
    DESCRIPTION
           "The Agent Capabilities of the VRRP-MIB (RFC 2787).

           If this MIB implementation is platform-dependent,
           the PRODUCT-RELEASE clause contains Ericsson SEOS version and
           at least one of the following Ericsson product families:
               [SE]  SmartEdge Multi-service Edge Router (MSER) family
               [SM]  SM family of Metro Ethernet Service Transport platforms
               [SSR] Smart Service Router (SSR) family"

    REVISION        "201501141800Z" -- Jan 14, 2015
    DESCRIPTION
           "Updated RBN/rbn/Rbn as ERICSSON-ROUTER/eriRouter/EriRouter
            to migrate RBN MIB to ERICSSON MIB."

    REVISION        "201106150000Z" -- Jun 15, 2011
    DESCRIPTION
            "Update DESCRIPTION clause of MODULE-IDENTITY
            and PRODUCT-RELEASE clause of AGENT-CAPABILITIES."

    REVISION        "201101191800Z" -- Jan 19, 2011
    DESCRIPTION
            "Update CONTACT-INFO & ORGANIZATION. "

    REVISION        "200901151800Z" -- Jan 15, 2009
    DESCRIPTION
           "Add vrrpNotificationCntl variation to indicate that 
            VRRP notification control is disabled by default." 

    REVISION        "200806160000Z" -- Jun 16, 2008
    DESCRIPTION
           "Initial version"
        ::= { eriRouterCapabilities 80 }

eriRouterIetfVrrpCap1 AGENT-CAPABILITIES
    PRODUCT-RELEASE "SEOS 6.1.4.3 [SE]; SEOS 6.3.X [SM]; SEOS 11.1.x [SSR]"
    STATUS          current
    DESCRIPTION     "VRRP-MIB capabilities"
    SUPPORTS        VRRP-MIB
    INCLUDES {
            vrrpOperGroup,
            vrrpStatsGroup,
            vrrpTrapGroup,
            vrrpNotificationGroup
            }

    VARIATION    vrrpNotificationCntl 
    DESCRIPTION
        "VRRP notification control is disabled by default."

    VARIATION    vrrpOperAdminState 
    ACCESS       read-only
    DESCRIPTION
        "Write access is not supported."

    VARIATION    vrrpOperPriority 
    ACCESS       read-only
    DESCRIPTION
        "Write access is not supported."

    VARIATION    vrrpOperPrimaryIpAddr 
    ACCESS       read-only
    DESCRIPTION
        "Write access is not supported."

    VARIATION    vrrpOperAuthType 
    ACCESS       read-only
    DESCRIPTION
        "Write access is not supported."

    VARIATION    vrrpOperAuthKey 
    ACCESS       read-only
    DESCRIPTION
        "Write access is not supported."

    VARIATION    vrrpOperAdvertisementInterval 
    ACCESS       read-only
    DESCRIPTION
        "Write access is not supported."

    VARIATION    vrrpOperPreemptMode 
    ACCESS       read-only
    DESCRIPTION
        "Write access is not supported."

    VARIATION    vrrpOperProtocol 
    ACCESS       read-only
    DESCRIPTION
        "Write access is not supported."

    VARIATION    vrrpOperRowStatus 
    ACCESS       read-only
    DESCRIPTION
        "Write access is not supported."

    VARIATION    vrrpAssoIpAddrRowStatus 
    ACCESS       read-only
    DESCRIPTION
        "Write access is not supported."

    VARIATION    vrrpStatsIpTtlErrors 
    ACCESS       read-only
    DESCRIPTION
        "This counter is not session based, it is system wide"

    ::= { eriRouterIetfVrrpCap 1 }
END
