-- %DNP% $Id: RBN-NOTIFY-ENHANCE-CAP.my,v 1.1.2.3.180.5 2011/06/15 18:19:46 danielhe Exp $
-- %DNP% $Source: /cvsroot/pkt/sw/se/xc/bsd/config/snmp/mibs/Attic/RBN-NOTIFY-ENHANCE-CAP.my,v $
-- *****************************************************************
-- RBN-NOTIFY-ENHANCE-CAP: RBN-NOTIFY-ENHANCE-MIB Agent Capabilities
--
-- Copyright (c) 2005-2011 Ericsson AB.
-- All rights reserved.
--
-- *****************************************************************

RBN-NOTIFY-ENHANCE-CAP DEFINITIONS ::= BEGIN

IMPORTS
        MODULE-IDENTITY
                FROM SNMPv2-SMI
        AGENT-CAPABILITIES
                FROM SNMPv2-CONF
        rbnCapabilities
                FROM RBN-SMI;

rbnNotifyEnhanceCap MODULE-IDENTITY
        LAST-UPDATED    "201106150000Z" -- Jun 15, 2011
        ORGANIZATION    "Ericsson Inc."
        CONTACT-INFO
                "       Ericsson, Inc.

                Postal: 100 Headquarters Dr.
                        San Jose, CA  95134
                        USA

                 Phone: +1 408 750 5000
                   Fax: +1 408 750 5599
                "
        DESCRIPTION
                "The Agent Capabilities of the Notify Enhance
                 MIB (RBN-NOTIFY-ENHANCE-MIB).

                If this MIB implementation is platform-dependent,
                the PRODUCT-RELEASE clause contains Ericsson SEOS version and
                at least one of the following Ericsson product families:
                    [SE]  SmartEdge Multi-service Edge Router (MSER) family
                    [SM]  SM family of Metro Ethernet Service Transport platforms
                    [SSR] Smart Service Router (SSR) family"

        REVISION        "201106150000Z" -- Jun 15, 2011
        DESCRIPTION
            "Update DESCRIPTION clause of MODULE-IDENTITY
            and PRODUCT-RELEASE clause of AGENT-CAPABILITIES."
        REVISION    "201011010000Z" -- Nov 1, 2010
        DESCRIPTION
            "Modified PRODUCT-RELEASE clause for consistent naming.
             Updated CONTACT-INFO."

        REVISION        "200903240000Z" -- March 24, 2009
        DESCRIPTION
                "Added rbnNotifyEnhanceCap2 which include
                rbnNotifyEnhanceMIBObjectGroup. SNMP agent may 
                append rbnNEGroupName to rbnNELinkUp and rbnNELinkDown
                notifications. "
        
        REVISION        "200505130000Z" -- May 13, 2005
        DESCRIPTION
                "Initial version"
        ::= { rbnCapabilities 64 }

rbnNotifyEnhanceCap1 AGENT-CAPABILITIES
        PRODUCT-RELEASE "4.0.5"
        STATUS          current
        DESCRIPTION     "RBN-NOTIFY-ENHANCE-MIB capabilities"
        SUPPORTS        RBN-NOTIFY-ENHANCE-MIB
        INCLUDES {
                    rbnNotifyEnhanceMIBNotificationGroup
                 }

        ::= { rbnNotifyEnhanceCap 1 }

rbnNotifyEnhanceCap2 AGENT-CAPABILITIES
        PRODUCT-RELEASE "SEOS 6.1.5 [SE]; SEOS 6.3.X [SM]; SEOS 11.1.x [SSR]"
        STATUS          current
        DESCRIPTION     "RBN-NOTIFY-ENHANCE-MIB capabilities"
        SUPPORTS        RBN-NOTIFY-ENHANCE-MIB
        INCLUDES {
                    rbnNotifyEnhanceMIBNotificationGroup,
                    rbnNotifyEnhanceMIBObjectGroup
                 }
        ::= { rbnNotifyEnhanceCap 2 }
END
