-- %DNP% $Id: RBN-SUBSCRIBER-ACTIVE-CAP.my,v 1.1.2.14.62.7 2012/04/13 03:45:23 pkuncham Exp $
-- %DNP% $Source: /cvsroot/pkt/sw/se/xc/bsd/config/snmp/mibs/Attic/RBN-SUBSCRIBER-ACTIVE-CAP.my,v $
-- *****************************************************************
-- RBN-SUBSCRIBER-ACTIVE-CAP    Subscriber MIB Capabilities
--
-- Copyright (c) 2003-2007, 2010-2011 Ericsson AB
-- All rights reserved.
--
-- *****************************************************************

RBN-SUBSCRIBER-ACTIVE-CAP DEFINITIONS ::= BEGIN

IMPORTS
    MODULE-IDENTITY     FROM SNMPv2-SMI
    AGENT-CAPABILITIES  FROM SNMPv2-CONF
    rbnCapabilities     FROM RBN-SMI;

rbnSubscriberActiveMibCap MODULE-IDENTITY
    LAST-UPDATED    "201204060000Z" -- Apr 6, 2012
    ORGANIZATION    "Ericsson AB"
    CONTACT-INFO
                "       Ericsson AB.

                 Postal: 100 Headquarters Dr
                         San Jose, CA  95134
                         USA

                 Phone: +1 408 750 5000
                 Fax: +1 408 750 5599"
    DESCRIPTION
        "The Agent Capabilities of RBN-SUBSCRIBER-ACTIVE-MIB.

        If this MIB implementation is platform-dependent,
        the PRODUCT-RELEASE clause contains Ericsson SEOS version and
        at least one of the following Ericsson product families:
            [SE]  SmartEdge Multi-service Edge Router (MSER) family
            [SM]  SM family of Metro Ethernet Service Transport platforms
            [SSR] Smart Service Router (SSR) family"

    REVISION    "201204060000Z" -- Apr 6, 2012
    DESCRIPTION
        "Add rbnSubscriberActiveMibCap12 for SEOS 12.1"      

    REVISION    "201106150000Z" -- Jun 15, 2011
    DESCRIPTION
        "Update DESCRIPTION clause of MODULE-IDENTITY
        and PRODUCT-RELEASE clause of AGENT-CAPABILITIES."
        
    REVISION    "201011010000Z" -- Nov 1, 2010
    DESCRIPTION
        "Modified PRODUCT-RELEASE clause for consistent naming."

    REVISION     "201003220000Z" -- March 22, 2010
    DESCRIPTION
        "Added rbnSubsActiveGroup4, rbnSubsStatsGroup3 support for SEOS 6.4+"

    REVISION     "200812031800Z" -- Dec 3, 2008
    DESCRIPTION
        "Added rbnSubsLicenseGroup support for SEOS 6.1.5"

    REVISION    "200711281800Z" -- Nov 28, 2007
    DESCRIPTION
        "Add rbnSubscriberActiveMibCap9 for SEOS 5.0.7.10"

    REVISION    "200703211700Z" -- Mar 21, 2007
    DESCRIPTION
        "Add rbnSubscriberActiveMibCap8 for SEOS 6.1"

    REVISION    "200610241700Z" -- Oct 24, 2006
    DESCRIPTION
        "Add rbnSubscriberActiveMibCap7 for SEOS 5.0.7.x"

    REVISION    "200505041700Z" -- May 4, 2005
    DESCRIPTION
        "Add rbnSubscriberActiveMibCap6 for AOS 6.2.3.x"
    REVISION    "200408111800Z" -- Aug 11, 2004
    DESCRIPTION
        "Add rbnSubscriberActiveMibCap5 for SEOS 2.6.5."
    REVISION    "200404131800Z" -- Apr 13, 2004
    DESCRIPTION
        "Add rbnSubscriberActiveMibCap4 for AOS 6.1.3."
    REVISION    "200311051800Z" -- Nov 5, 2003
    DESCRIPTION
        "Add rbnSubscriberActiveMibCap2 for SEOS 2.5.7, supporting
        rbnSubsEncapsulationType clips(12)."
    REVISION    "200305140000Z" -- May 14, 2003
    DESCRIPTION
        "Initial version."
    ::= { rbnCapabilities 55 }

rbnSubscriberActiveMibCap1 AGENT-CAPABILITIES
    PRODUCT-RELEASE     "SEOS 2.4.4.x"
    STATUS      current
    DESCRIPTION "RBN-SUBSCRIBER-ACTIVE-MIB capabilities"
    SUPPORTS    RBN-SUBSCRIBER-ACTIVE-MIB
    INCLUDES {
        rbnSubsActiveGroup,
        rbnSubsStatsGroup
    }

    VARIATION rbnSubsActiveName
        DESCRIPTION
        "Each character must be printable (the posix funtion isprint()
        returns true for each character) and the string may not contain
        any of the characters double quote, single quote ('), bar (|), or
        exclamation point (!)."

    VARIATION rbnSubsClearSubscriberName
        DESCRIPTION
        "Each character must be printable (the posix funtion isprint()
        returns true for each character) and the string may not contain
        any of the characters double quote, single quote ('), bar (|), or
        exclamation point (!)."

    VARIATION rbnSubsBounceName
        DESCRIPTION
        "Each character must be printable (the posix funtion isprint()
        returns true for each character) and the string may not contain
        any of the characters double quote, single quote ('), bar (|), or
        exclamation point (!)."

    VARIATION rbnSubsEncapsulationType
        SYNTAX  INTEGER {
                    ppp(1),
                    pppoe(2),
                    bridged1483(3),
                    routed1483(4),
                    multi1483(5),
                    dot1q1483(6),
                    dot1qEnet(7),
                    other(255)
                }
        DESCRIPTION
        "SmartEdge does not support any 1490 (Frame Relay) or clips based
        subscribers at this time."
    ::= { rbnSubscriberActiveMibCap 1 }

rbnSubscriberActiveMibCap2 AGENT-CAPABILITIES
    PRODUCT-RELEASE     "SEOS 2.5.7.x"
    STATUS      current
    DESCRIPTION "RBN-SUBSCRIBER-ACTIVE-MIB capabilities"
    SUPPORTS    RBN-SUBSCRIBER-ACTIVE-MIB
    INCLUDES {
        rbnSubsActiveGroup,
        rbnSubsStatsGroup
    }

    VARIATION rbnSubsActiveName
        DESCRIPTION
        "Each character must be printable (the posix funtion isprint()
        returns true for each character) and the string may not contain
        any of the characters double quote, single quote ('), bar (|), or
        exclamation point (!)."

    VARIATION rbnSubsClearSubscriberName
        DESCRIPTION
        "Each character must be printable (the posix funtion isprint()
        returns true for each character) and the string may not contain
        any of the characters double quote, single quote ('), bar (|), or
        exclamation point (!)."

    VARIATION rbnSubsBounceName
        DESCRIPTION
        "Each character must be printable (the posix funtion isprint()
        returns true for each character) and the string may not contain
        any of the characters double quote, single quote ('), bar (|), or
        exclamation point (!)."

    VARIATION rbnSubsEncapsulationType
        SYNTAX  INTEGER {
                    ppp(1),
                    pppoe(2),
                    bridged1483(3),
                    routed1483(4),
                    multi1483(5),
                    dot1q1483(6),
                    dot1qEnet(7),
                    clips(12),
                    other(255)
                }
        DESCRIPTION
        "SmartEdge does not support any 1490 (Frame Relay) at this time."

    ::= { rbnSubscriberActiveMibCap 2 }


rbnSubscriberActiveMibCap3 AGENT-CAPABILITIES
    PRODUCT-RELEASE     "SEOS 2.6.3.x"
    STATUS      obsolete
    DESCRIPTION "RBN-SUBSCRIBER-ACTIVE-MIB capabilities"
    SUPPORTS    RBN-SUBSCRIBER-ACTIVE-MIB
    INCLUDES {
        rbnSubsActiveGroup2,
        rbnSubsStatsGroup2
    }

    VARIATION rbnSubsActiveName
        DESCRIPTION
        "Each character must be printable (the posix funtion isprint()
        returns true for each character) and the string may not contain
        any of the characters double quote, single quote ('), bar (|), or
        exclamation point (!)."

    VARIATION rbnSubsClearSubscriberName
        DESCRIPTION
        "Each character must be printable (the posix funtion isprint()
        returns true for each character) and the string may not contain
        any of the characters double quote, single quote ('), bar (|), or
        exclamation point (!)."

    VARIATION rbnSubsClearSessionId
        DESCRIPTION
        "Each character must be printable (the posix funtion isprint()
        returns true for each character) and the string may not contain
        any of the characters double quote, single quote ('), bar (|), or
        exclamation point (!)."

    VARIATION rbnSubsReauthName
        DESCRIPTION
        "Each character must be printable (the posix funtion isprint()
        returns true for each character) and the string may not contain
        any of the characters double quote, single quote ('), bar (|), or
        exclamation point (!)."

    VARIATION rbnSubsReauthSessionId
        DESCRIPTION
        "Each character must be printable (the posix funtion isprint()
        returns true for each character) and the string may not contain
        any of the characters double quote, single quote ('), bar (|), or
        exclamation point (!)."

    VARIATION rbnSubsBounceName
        DESCRIPTION
        "Each character must be printable (the posix funtion isprint()
        returns true for each character) and the string may not contain
        any of the characters double quote, single quote ('), bar (|), or
        exclamation point (!)."

    VARIATION rbnSubsEncapsulationType
        SYNTAX  INTEGER {
                    ppp(1),
                    pppoe(2),
                    bridged1483(3),
                    routed1483(4),
                    multi1483(5),
                    dot1q1483(6),
                    dot1qEnet(7),
                    clips(12),
                    other(255)
                }
        DESCRIPTION
        "SmartEdge does not support any 1490 (Frame Relay) at this time."

    ::= { rbnSubscriberActiveMibCap 3 }

rbnSubscriberActiveMibCap4 AGENT-CAPABILITIES
    PRODUCT-RELEASE     "AOS 6.1.3.X"
    STATUS      current
    DESCRIPTION "RBN-SUBSCRIBER-ACTIVE-MIB capabilities"
    SUPPORTS    RBN-SUBSCRIBER-ACTIVE-MIB
    INCLUDES {
        rbnSubsActiveGroup2,
        rbnSubsStatsGroup2
    }

    VARIATION rbnSubsActiveName
        DESCRIPTION
        "Each character must be printable (the posix funtion isprint()
        returns true for each character) and the string may not contain
        any of the characters double quote, single quote ('), bar (|), or
        exclamation point (!)."

    VARIATION rbnSubsClearSubscriberName
        DESCRIPTION
        "Each character must be printable (the posix funtion isprint()
        returns true for each character) and the string may not contain
        any of the characters double quote, single quote ('), bar (|), or
        exclamation point (!)."

    VARIATION rbnSubsBounceName
        ACCESS  not-implemented
        DESCRIPTION "Object is not supported."

    VARIATION rbnSubsBounceSessionId
        ACCESS  not-implemented
        DESCRIPTION "Object is not supported."

    VARIATION rbnSubsClearReason
        ACCESS  not-implemented
        DESCRIPTION "Object is not supported."

    VARIATION rbnSubsReauthRadiusID
        ACCESS  not-implemented
        DESCRIPTION "Object is not supported."

    VARIATION rbnSubsReauthRadiusIndex
        ACCESS  not-implemented
        DESCRIPTION "Object is not supported."

    VARIATION rbnSubsProfileCountTable
        ACCESS  not-implemented
        DESCRIPTION "Object is not supported."

    ::= { rbnSubscriberActiveMibCap 4 }

rbnSubscriberActiveMibCap5 AGENT-CAPABILITIES
    PRODUCT-RELEASE     "SEOS 2.6.5.x"
    STATUS      current
    DESCRIPTION "RBN-SUBSCRIBER-ACTIVE-MIB capabilities"
    SUPPORTS    RBN-SUBSCRIBER-ACTIVE-MIB
    INCLUDES {
        rbnSubsActiveGroup3,
        rbnSubsStatsGroup2
    }

    VARIATION rbnSubsActiveName
        DESCRIPTION
        "Each character must be printable (the posix funtion isprint()
        returns true for each character) and the string may not contain
        any of the characters double quote, single quote ('), bar (|), or
        exclamation point (!)."

    VARIATION rbnSubsClearSubscriberName
        DESCRIPTION
        "Each character must be printable (the posix funtion isprint()
        returns true for each character) and the string may not contain
        any of the characters double quote, single quote ('), bar (|), or
        exclamation point (!)."

    VARIATION rbnSubsClearSessionId
        DESCRIPTION
        "Each character must be printable (the posix funtion isprint()
        returns true for each character) and the string may not contain
        any of the characters double quote, single quote ('), bar (|), or
        exclamation point (!)."

    VARIATION rbnSubsReauthName
        DESCRIPTION
        "Each character must be printable (the posix funtion isprint()
        returns true for each character) and the string may not contain
        any of the characters double quote, single quote ('), bar (|), or
        exclamation point (!)."

    VARIATION rbnSubsReauthSessionId
        DESCRIPTION
        "Each character must be printable (the posix funtion isprint()
        returns true for each character) and the string may not contain
        any of the characters double quote, single quote ('), bar (|), or
        exclamation point (!)."

    VARIATION rbnSubsBounceName
        DESCRIPTION
        "Each character must be printable (the posix funtion isprint()
        returns true for each character) and the string may not contain
        any of the characters double quote, single quote ('), bar (|), or
        exclamation point (!)."

    VARIATION rbnSubsEncapsulationType
        SYNTAX  INTEGER {
                    ppp(1),
                    pppoe(2),
                    bridged1483(3),
                    routed1483(4),
                    multi1483(5),
                    dot1q1483(6),
                    dot1qEnet(7),
                    clips(12),
                    other(255)
                }
        DESCRIPTION
        "SmartEdge does not support any 1490 (Frame Relay) at this time."

    ::= { rbnSubscriberActiveMibCap 5 }

rbnSubscriberActiveMibCap6 AGENT-CAPABILITIES
    PRODUCT-RELEASE     "AOS 6.2.3.X"
    STATUS      current
    DESCRIPTION "RBN-SUBSCRIBER-ACTIVE-MIB capabilities"
    SUPPORTS    RBN-SUBSCRIBER-ACTIVE-MIB
    INCLUDES {
        rbnSubsActiveGroup2,
        rbnSubsStatsGroup2
    }

    VARIATION rbnSubsActiveName
        DESCRIPTION
        "Each character must be printable (the posix funtion isprint()
        returns true for each character) and the string may not contain
        any of the characters double quote, single quote ('), bar (|), or
        exclamation point (!)."

    VARIATION rbnSubsClearSubscriberName
        DESCRIPTION
        "Each character must be printable (the posix funtion isprint()
        returns true for each character) and the string may not contain
        any of the characters double quote, single quote ('), bar (|), or
        exclamation point (!)."

    VARIATION rbnSubsClearReason
        DESCRIPTION
        "An unsigned integer value which may be included in the set request
         for rbnSubsClearSubscriberName or rbnSubsClearSessionId."

    VARIATION rbnSubsBounceName
        ACCESS  not-implemented
        DESCRIPTION "Object is not supported."

    VARIATION rbnSubsBounceSessionId
        ACCESS  not-implemented
        DESCRIPTION "Object is not supported."

    VARIATION rbnSubsReauthRadiusID
        ACCESS  not-implemented
        DESCRIPTION "Object is not supported."

    VARIATION rbnSubsReauthRadiusIndex
        ACCESS  not-implemented
        DESCRIPTION "Object is not supported."

    VARIATION rbnSubsProfileCountTable
        ACCESS  not-implemented
        DESCRIPTION "Object is not supported."

    ::= { rbnSubscriberActiveMibCap 6 }

rbnSubscriberActiveMibCap7 AGENT-CAPABILITIES
    PRODUCT-RELEASE     "SEOS 5.0.7.4"
    STATUS      current
    DESCRIPTION "RBN-SUBSCRIBER-ACTIVE-MIB capabilities"
    SUPPORTS    RBN-SUBSCRIBER-ACTIVE-MIB
    INCLUDES {
        rbnSubsActiveGroup3,
        rbnSubsStatsGroup2
    }

    VARIATION rbnSubsActiveName
        DESCRIPTION
        "Each character must be printable (the posix funtion isprint()
        returns true for each character) and the string may not contain
        any of the characters double quote, single quote ('), bar (|), or
        exclamation point (!)."

    VARIATION rbnSubsClearSubscriberName
        DESCRIPTION
        "Each character must be printable (the posix funtion isprint()
        returns true for each character) and the string may not contain
        any of the characters double quote, single quote ('), bar (|), or
        exclamation point (!)."

    VARIATION rbnSubsClearSessionId
        DESCRIPTION
        "Each character must be printable (the posix funtion isprint()
        returns true for each character) and the string may not contain
        any of the characters double quote, single quote ('), bar (|), or
        exclamation point (!)."

    VARIATION rbnSubsReauthName
        DESCRIPTION
        "Each character must be printable (the posix funtion isprint()
        returns true for each character) and the string may not contain
        any of the characters double quote, single quote ('), bar (|), or
        exclamation point (!)."

    VARIATION rbnSubsReauthSessionId
        DESCRIPTION
        "Each character must be printable (the posix funtion isprint()
        returns true for each character) and the string may not contain
        any of the characters double quote, single quote ('), bar (|), or
        exclamation point (!)."

    VARIATION rbnSubsBounceName
        DESCRIPTION
        "Each character must be printable (the posix funtion isprint()
        returns true for each character) and the string may not contain
        any of the characters double quote, single quote ('), bar (|), or
        exclamation point (!)."

    VARIATION rbnSubsEncapsulationType
        SYNTAX  INTEGER {
                    ppp(1),
                    pppoe(2),
                    bridged1483(3),
                    routed1483(4),
                    multi1483(5),
                    dot1q1483(6),
                    dot1qEnet(7),
                    clips(12),
                    other(255)
                }
        DESCRIPTION
        "SmartEdge does not support any 1490 (Frame Relay) at this time."

    VARIATION rbnSubsXmitOctetsDropped
        ACCESS  not-implemented
        DESCRIPTION "Object is not supported."

    VARIATION rbnSubsXmitPktsDropped
        ACCESS  not-implemented
        DESCRIPTION "Object is not supported."

    ::= { rbnSubscriberActiveMibCap 7 }

rbnSubscriberActiveMibCap8 AGENT-CAPABILITIES
    PRODUCT-RELEASE     "SEOS 6.1"
    STATUS      current
    DESCRIPTION "RBN-SUBSCRIBER-ACTIVE-MIB capabilities"
    SUPPORTS    RBN-SUBSCRIBER-ACTIVE-MIB
    INCLUDES {
        rbnSubsActiveGroup3,
        rbnSubsStatsGroup2,
        rbnSubsServicesGroup,
        rbnSubsNotifyObjectGroup,
        rbnSubsNotifyGroup
    }

    VARIATION rbnSubsActiveName
        DESCRIPTION
        "Each character must be printable (the posix funtion isprint()
        returns true for each character) and the string may not contain
        any of the characters double quote, single quote ('), bar (|), or
        exclamation point (!)."

    VARIATION rbnSubsClearSubscriberName
        DESCRIPTION
        "Each character must be printable (the posix funtion isprint()
        returns true for each character) and the string may not contain
        any of the characters double quote, single quote ('), bar (|), or
        exclamation point (!)."

    VARIATION rbnSubsClearSessionId
        DESCRIPTION
        "Each character must be printable (the posix funtion isprint()
        returns true for each character) and the string may not contain
        any of the characters double quote, single quote ('), bar (|), or
        exclamation point (!)."

    VARIATION rbnSubsReauthName
        DESCRIPTION
        "Each character must be printable (the posix funtion isprint()
        returns true for each character) and the string may not contain
        any of the characters double quote, single quote ('), bar (|), or
        exclamation point (!)."

    VARIATION rbnSubsReauthSessionId
        DESCRIPTION
        "Each character must be printable (the posix funtion isprint()
        returns true for each character) and the string may not contain
        any of the characters double quote, single quote ('), bar (|), or
        exclamation point (!)."

    VARIATION rbnSubsBounceName
        DESCRIPTION
        "Each character must be printable (the posix funtion isprint()
        returns true for each character) and the string may not contain
        any of the characters double quote, single quote ('), bar (|), or
        exclamation point (!)."

    VARIATION rbnSubsEncapsulationType
        SYNTAX  INTEGER {
                    ppp(1),
                    pppoe(2),
                    bridged1483(3),
                    routed1483(4),
                    multi1483(5),
                    dot1q1483(6),
                    dot1qEnet(7),
                    clips(12),
                    other(255)
                }
        DESCRIPTION
        "SmartEdge does not support any 1490 (Frame Relay) at this time."

    VARIATION rbnSubsXmitOctetsDropped
        ACCESS  not-implemented
        DESCRIPTION "Object is not supported."

    VARIATION rbnSubsXmitPktsDropped
        ACCESS  not-implemented
        DESCRIPTION "Object is not supported."

    VARIATION rbnSubsServiceName
        ACCESS read-only
        DESCRIPTION "Object is read-only"

    VARIATION rbnSubsServiceTag
        ACCESS read-only
        DESCRIPTION "Object is read-only"

    VARIATION rbnSubsServiceVolumeLimitIn
        ACCESS read-only
        DESCRIPTION "Object is read-only"

    VARIATION rbnSubsServiceVolumeLimitOut
        ACCESS read-only
        DESCRIPTION "Object is read-only"

    ::= { rbnSubscriberActiveMibCap 8 }

rbnSubscriberActiveMibCap9 AGENT-CAPABILITIES
    PRODUCT-RELEASE     "SEOS 5.0.7.10"
    STATUS      current
    DESCRIPTION "RBN-SUBSCRIBER-ACTIVE-MIB capabilities"
    SUPPORTS    RBN-SUBSCRIBER-ACTIVE-MIB
    INCLUDES {
        rbnSubsActiveGroup3,
        rbnSubsStatsGroup2,
        rbnSubsNotifyObjectGroup,
        rbnSubsNotifyGroup
    }

    VARIATION rbnSubsActiveName
        DESCRIPTION
        "Each character must be printable (the posix funtion isprint()
        returns true for each character) and the string may not contain
        any of the characters double quote, single quote ('), bar (|), or
        exclamation point (!)."

    VARIATION rbnSubsClearSubscriberName
        DESCRIPTION
        "Each character must be printable (the posix funtion isprint()
        returns true for each character) and the string may not contain
        any of the characters double quote, single quote ('), bar (|), or
        exclamation point (!)."

    VARIATION rbnSubsClearSessionId
        DESCRIPTION
        "Each character must be printable (the posix funtion isprint()
        returns true for each character) and the string may not contain
        any of the characters double quote, single quote ('), bar (|), or
        exclamation point (!)."

    VARIATION rbnSubsReauthName
        DESCRIPTION
        "Each character must be printable (the posix funtion isprint()
        returns true for each character) and the string may not contain
        any of the characters double quote, single quote ('), bar (|), or
        exclamation point (!)."

    VARIATION rbnSubsReauthSessionId
        DESCRIPTION
        "Each character must be printable (the posix funtion isprint()
        returns true for each character) and the string may not contain
        any of the characters double quote, single quote ('), bar (|), or
        exclamation point (!)."

    VARIATION rbnSubsBounceName
        DESCRIPTION
        "Each character must be printable (the posix funtion isprint()
        returns true for each character) and the string may not contain
        any of the characters double quote, single quote ('), bar (|), or
        exclamation point (!)."

    VARIATION rbnSubsEncapsulationType
        SYNTAX  INTEGER {
                    ppp(1),
                    pppoe(2),
                    bridged1483(3),
                    routed1483(4),
                    multi1483(5),
                    dot1q1483(6),
                    dot1qEnet(7),
                    clips(12),
                    other(255)
                }
        DESCRIPTION
        "SmartEdge does not support any 1490 (Frame Relay) at this time."

    VARIATION rbnSubsXmitOctetsDropped
        ACCESS  not-implemented
        DESCRIPTION "Object is not supported."

    VARIATION rbnSubsXmitPktsDropped
        ACCESS  not-implemented
        DESCRIPTION "Object is not supported."

    ::= { rbnSubscriberActiveMibCap 9 }

rbnSubscriberActiveMibCap10 AGENT-CAPABILITIES
    PRODUCT-RELEASE     "SEOS 6.1.5"
    STATUS      current
    DESCRIPTION "RBN-SUBSCRIBER-ACTIVE-MIB capabilities"
    SUPPORTS    RBN-SUBSCRIBER-ACTIVE-MIB
    INCLUDES {
        rbnSubsActiveGroup3,
        rbnSubsStatsGroup2,
        rbnSubsServicesGroup,
        rbnSubsNotifyObjectGroup,
        rbnSubsNotifyGroup,
        rbnSubsLicenseGroup
    }

    VARIATION rbnSubsActiveName
        DESCRIPTION
        "Each character must be printable (the posix funtion isprint()
        returns true for each character) and the string may not contain
        any of the characters double quote, single quote ('), bar (|), or
        exclamation point (!)."

    VARIATION rbnSubsClearSubscriberName
        DESCRIPTION
        "Each character must be printable (the posix funtion isprint()
        returns true for each character) and the string may not contain
        any of the characters double quote, single quote ('), bar (|), or
        exclamation point (!)."

    VARIATION rbnSubsClearSessionId
        DESCRIPTION
        "Each character must be printable (the posix funtion isprint()
        returns true for each character) and the string may not contain
        any of the characters double quote, single quote ('), bar (|), or
        exclamation point (!)."

    VARIATION rbnSubsReauthName
        DESCRIPTION
        "Each character must be printable (the posix funtion isprint()
        returns true for each character) and the string may not contain
        any of the characters double quote, single quote ('), bar (|), or
        exclamation point (!)."

    VARIATION rbnSubsReauthSessionId
        DESCRIPTION
        "Each character must be printable (the posix funtion isprint()
        returns true for each character) and the string may not contain
        any of the characters double quote, single quote ('), bar (|), or
        exclamation point (!)."

    VARIATION rbnSubsBounceName
        DESCRIPTION
        "Each character must be printable (the posix funtion isprint()
        returns true for each character) and the string may not contain
        any of the characters double quote, single quote ('), bar (|), or
        exclamation point (!)."

    VARIATION rbnSubsEncapsulationType
        SYNTAX  INTEGER {
                    ppp(1),
                    pppoe(2),
                    bridged1483(3),
                    routed1483(4),
                    multi1483(5),
                    dot1q1483(6),
                    dot1qEnet(7),
                    clips(12),
                    other(255)
                }
        DESCRIPTION
        "SmartEdge does not support any 1490 (Frame Relay) at this time."

    VARIATION rbnSubsXmitOctetsDropped
        ACCESS  not-implemented
        DESCRIPTION "Object is not supported."

    VARIATION rbnSubsXmitPktsDropped
        ACCESS  not-implemented
        DESCRIPTION "Object is not supported."

    VARIATION rbnSubsServiceName
        ACCESS read-only
        DESCRIPTION "Object is read-only"

    VARIATION rbnSubsServiceTag
        ACCESS read-only
        DESCRIPTION "Object is read-only"

    VARIATION rbnSubsServiceVolumeLimitIn
        ACCESS read-only
        DESCRIPTION "Object is read-only"

    VARIATION rbnSubsServiceVolumeLimitOut
        ACCESS read-only
        DESCRIPTION "Object is read-only"

    ::= { rbnSubscriberActiveMibCap 10 }


rbnSubscriberActiveMibCap11 AGENT-CAPABILITIES
    PRODUCT-RELEASE     "SEOS 6.4.x [SE, SM]"
    STATUS      current
    DESCRIPTION "RBN-SUBSCRIBER-ACTIVE-MIB capabilities"
    SUPPORTS    RBN-SUBSCRIBER-ACTIVE-MIB
    INCLUDES {
        rbnSubsActiveGroup4,
        rbnSubsStatsGroup3,
        rbnSubsServicesGroup,
        rbnSubsNotifyObjectGroup,
        rbnSubsNotifyGroup,
        rbnSubsLicenseGroup
    }

    VARIATION rbnSubsActiveName
        DESCRIPTION
        "Each character must be printable (the posix funtion isprint()
        returns true for each character) and the string may not contain
        any of the characters double quote, single quote ('), bar (|), or
        exclamation point (!)."

    VARIATION rbnSubsClearSubscriberName
        DESCRIPTION
        "Each character must be printable (the posix funtion isprint()
        returns true for each character) and the string may not contain
        any of the characters double quote, single quote ('), bar (|), or
        exclamation point (!)."

    VARIATION rbnSubsClearSessionId
        DESCRIPTION
        "Each character must be printable (the posix funtion isprint()
        returns true for each character) and the string may not contain
        any of the characters double quote, single quote ('), bar (|), or
        exclamation point (!)."

    VARIATION rbnSubsReauthName
        DESCRIPTION
        "Each character must be printable (the posix funtion isprint()
        returns true for each character) and the string may not contain
        any of the characters double quote, single quote ('), bar (|), or
        exclamation point (!)."

    VARIATION rbnSubsReauthSessionId
        DESCRIPTION
        "Each character must be printable (the posix funtion isprint()
        returns true for each character) and the string may not contain
        any of the characters double quote, single quote ('), bar (|), or
        exclamation point (!)."

    VARIATION rbnSubsBounceName
        DESCRIPTION
        "Each character must be printable (the posix funtion isprint()
        returns true for each character) and the string may not contain
        any of the characters double quote, single quote ('), bar (|), or
        exclamation point (!)."

    VARIATION rbnSubsEncapsulationType
        SYNTAX  INTEGER {
                    ppp(1),
                    pppoe(2),
                    bridged1483(3),
                    routed1483(4),
                    multi1483(5),
                    dot1q1483(6),
                    dot1qEnet(7),
                    clips(12),
                    other(255)
                }
        DESCRIPTION
        "SmartEdge does not support any 1490 (Frame Relay) at this time."

    VARIATION rbnSubsXmitOctetsDropped
        ACCESS  not-implemented
        DESCRIPTION "Object is not supported."

    VARIATION rbnSubsXmitPktsDropped
        ACCESS  not-implemented
        DESCRIPTION "Object is not supported."

    VARIATION rbnSubsServiceName
        ACCESS read-only
        DESCRIPTION "Object is read-only"

    VARIATION rbnSubsServiceTag
        ACCESS read-only
        DESCRIPTION "Object is read-only"

    VARIATION rbnSubsServiceVolumeLimitIn
        ACCESS read-only
        DESCRIPTION "Object is read-only"

    VARIATION rbnSubsServiceVolumeLimitOut
        ACCESS read-only
        DESCRIPTION "Object is read-only"

    ::= { rbnSubscriberActiveMibCap 11 }


rbnSubscriberActiveMibCap12 AGENT-CAPABILITIES
    PRODUCT-RELEASE     "SEOS 12.1[SE, SM]"
    STATUS      current
    DESCRIPTION "RBN-SUBSCRIBER-ACTIVE-MIB capabilities"
    SUPPORTS    RBN-SUBSCRIBER-ACTIVE-MIB
    INCLUDES {
        rbnSubsActiveGroup4,
        rbnSubsStatsGroup3,
        rbnSubsServicesGroup,
        rbnSubsNotifyObjectGroup,
        rbnSubsNotifyGroup,
        rbnSubsLicenseGroup
    }

    VARIATION rbnSubsActiveName
        DESCRIPTION
        "Each character must be printable (the posix funtion isprint()
        returns true for each character) and the string may not contain
        any of the characters double quote, single quote ('), bar (|), or
        exclamation point (!). When the knob :
        radius attribute acct-session-id [format physical]  is turned on, 
        the rbnSubsActiveName is truncated to 74."

    VARIATION rbnSubsClearSubscriberName
        DESCRIPTION
        "Each character must be printable (the posix funtion isprint()
        returns true for each character) and the string may not contain
        any of the characters double quote, single quote ('), bar (|), or
        exclamation point (!)."

    VARIATION rbnSubsClearSessionId
        DESCRIPTION
        "Each character must be printable (the posix funtion isprint()
        returns true for each character) and the string may not contain
        any of the characters double quote, single quote ('), bar (|), or
        exclamation point (!)."

    VARIATION rbnSubsReauthName
        DESCRIPTION
        "Each character must be printable (the posix funtion isprint()
        returns true for each character) and the string may not contain
        any of the characters double quote, single quote ('), bar (|), or
        exclamation point (!)."

    VARIATION rbnSubsReauthSessionId
        DESCRIPTION
        "Each character must be printable (the posix funtion isprint()
        returns true for each character) and the string may not contain
        any of the characters double quote, single quote ('), bar (|), or
        exclamation point (!)."

    VARIATION rbnSubsBounceName
        DESCRIPTION
        "Each character must be printable (the posix funtion isprint()
        returns true for each character) and the string may not contain
        any of the characters double quote, single quote ('), bar (|), or
        exclamation point (!)."

    VARIATION rbnSubsEncapsulationType
        SYNTAX  INTEGER {
                    ppp(1),
                    pppoe(2),
                    bridged1483(3),
                    routed1483(4),
                    multi1483(5),
                    dot1q1483(6),
                    dot1qEnet(7),
                    clips(12),
                    other(255)
                }
        DESCRIPTION
        "SmartEdge does not support any 1490 (Frame Relay) at this time."

    VARIATION rbnSubsXmitOctetsDropped
        ACCESS  not-implemented
        DESCRIPTION "Object is not supported."

    VARIATION rbnSubsXmitPktsDropped
        ACCESS  not-implemented
        DESCRIPTION "Object is not supported."

    VARIATION rbnSubsServiceName
        ACCESS read-only
        DESCRIPTION "Object is read-only"

    VARIATION rbnSubsServiceTag
        ACCESS read-only
        DESCRIPTION "Object is read-only"

    VARIATION rbnSubsServiceVolumeLimitIn
        ACCESS read-only
        DESCRIPTION "Object is read-only"

    VARIATION rbnSubsServiceVolumeLimitOut
        ACCESS read-only
        DESCRIPTION "Object is read-only"

    VARIATION rbnSubsActiveSessionId      
        ACCESS read-only
        DESCRIPTION
            " When the knob :
              radius attribute acct-session-id [format physical]
              is turned on, the length of rbnSubsActiveSessionId is 33."

    ::= { rbnSubscriberActiveMibCap 12 }

END
