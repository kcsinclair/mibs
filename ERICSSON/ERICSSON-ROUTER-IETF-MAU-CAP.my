-- %DNP% $Id: ERICSSON-ROUTER-IETF-MAU-CAP.my,v 1.1.4.2.60.4 2011/06/15 18:19:45 danielhe Exp $
-- %DNP% $Source: /cvsroot/pkt/sw/se/xc/bsd/config/snmp/mibs/Attic/ERICSSON-ROUTER-IETF-MAU-CAP.my,v $
-- *****************************************************************
-- ERICSSON-ROUTER-IETF-MAU-CAP.my: IETF MAU-MIB Agent Capabilities
--
-- Copyright (c) 1998-2008, 2010-2011, 2015 Ericsson AB
-- All rights reserved.
-- 
-- *****************************************************************

ERICSSON-ROUTER-IETF-MAU-CAP DEFINITIONS ::= BEGIN

IMPORTS
        MODULE-IDENTITY
                FROM SNMPv2-SMI
        AGENT-CAPABILITIES
                FROM SNMPv2-CONF
        eriRouterCapabilities
                FROM ERICSSON-ROUTER-SMI;

eriRouterIetfMauCap MODULE-IDENTITY
        LAST-UPDATED    "201501141800Z" -- Jan 14, 2015
        ORGANIZATION    "Ericsson AB"
        CONTACT-INFO
                    "        Ericsson AB.

                     Postal: 100 Headquarters Dr
                             San Jose, CA  95134
                             USA

                     Phone: +1 408 750 5000
                     Fax: +1 408 750 5599"
        DESCRIPTION
            "The Agent Capabilities of the 
             implementation of the IETF MAU-MIB (RFC2668).
             The Agent Capabilities of SmartEdge 6.1.3 IETF MAU-MIB 
             is based on RFC4836

            If this MIB implementation is platform-dependent,
            the PRODUCT-RELEASE clause contains Ericsson SEOS version and
            at least one of the following Ericsson product families:
                [SE]  SmartEdge Multi-service Edge Router (MSER) family
                [SM]  SM family of Metro Ethernet Service Transport platforms
                [SSR] Smart Service Router (SSR) family"

        REVISION        "201501141800Z" -- Jan 14, 2015
        DESCRIPTION
            "Updated RBN/rbn/Rbn as ERICSSON-ROUTER/eriRouter/EriRouter
             to migrate RBN MIB to ERICSSON MIB."

        REVISION        "201106150000Z" -- Jun 15, 2011
        DESCRIPTION
            "Update DESCRIPTION clause of MODULE-IDENTITY
            and PRODUCT-RELEASE clause of AGENT-CAPABILITIES."
             
	REVISION	"201011010000Z" -- Nov 1, 2010
	DESCRIPTION
	    "Modified PRODUCT-RELEASE clause for consistent naming."
                
        REVISION        "200802140000Z" -- February 14, 2008 00:00:00 EST 
        DESCRIPTION
            "(1) Add eriRouterIetfMauCapSE for SmartEdge 6.1.3. 
             (2) Update CONTACT-INFO 
             (3) Update SmartEdge MAU-MIB based on RFC4836
             (4) Update PRODUCT-RELEASE with the prefix AOS for SMS
                 releases"

        REVISION        "199912152300Z"
        DESCRIPTION
            "Updated to reference RFC 2668"
        ::= { eriRouterCapabilities 11 }

eriRouterIetfMauCap1 AGENT-CAPABILITIES
	PRODUCT-RELEASE	"AOS 1.0.X.X"
	STATUS		current
	DESCRIPTION	"MAU-MIB capabilities"
	SUPPORTS	MAU-MIB
	INCLUDES {
		mauIfGrpBasic,
		mauIfGrp100Mbs,
		mauIfGrpJack,
		mauIfGrpAutoNeg
		}

	VARIATION	ifMauStatus
	ACCESS		read-only
	DESCRIPTION
		"Write access is not allowed"

	VARIATION	ifMauDefaultType
	ACCESS		read-only
	DESCRIPTION
		"Write access is not allowed"

	VARIATION	ifMauAutoNegAdminStatus
	ACCESS		read-only
	DESCRIPTION
		"Write access is not allowed"

	VARIATION	ifMauAutoNegCapAdvertised
	ACCESS		read-only
	DESCRIPTION
		"Write access is not allowed"

	VARIATION	ifMauAutoNegRestart
	ACCESS		read-only
	DESCRIPTION
		"Write access is not allowed"


	::= { eriRouterIetfMauCap 1 }

eriRouterIetfMauCapFast AGENT-CAPABILITIES
	PRODUCT-RELEASE	"AOS 4.0.X.X"
	STATUS		current
	DESCRIPTION	"MAU-MIB 10/100 ethernet capabilities"
	SUPPORTS	MAU-MIB
	INCLUDES {
		mauIfGrpBasic,
                mauIfGrpHighCapacity,
                mauIfGrpJack,
                mauIfGrpAutoNeg2
		}

	VARIATION	ifMauStatus
	ACCESS		read-only
	DESCRIPTION
		"Write access is not allowed"

	VARIATION	ifMauDefaultType
	ACCESS		read-only
	DESCRIPTION
		"Write access is not allowed"

	VARIATION	ifMauAutoNegAdminStatus
	ACCESS		read-only
	DESCRIPTION
		"Write access is not allowed"

	VARIATION	ifMauAutoNegCapAdvertisedBits
	ACCESS		read-only
	DESCRIPTION
		"Write access is not allowed"

	VARIATION	ifMauAutoNegRestart
	ACCESS		read-only
	DESCRIPTION
		"Write access is not allowed"

	::= { eriRouterIetfMauCap 2 }

eriRouterIetfMauCapGig AGENT-CAPABILITIES
	PRODUCT-RELEASE	"AOS 4.0.X.X"
	STATUS		current
	DESCRIPTION	"MAU-MIB gigabit ethernet capabilities"
	SUPPORTS	MAU-MIB
	INCLUDES {
		mauIfGrpBasic,
                mauIfGrpHighCapacity,
                mauIfGrpJack
		}

	VARIATION	ifMauStatus
	ACCESS		read-only
	DESCRIPTION
		"Write access is not allowed"

	VARIATION	ifMauDefaultType
	ACCESS		read-only
	DESCRIPTION
		"Write access is not allowed"

	VARIATION	ifMauFalseCarriers
	ACCESS		not-implemented
	DESCRIPTION
		"This information is not available."

	::= { eriRouterIetfMauCap 3 }


eriRouterIetfMauCapSE AGENT-CAPABILITIES
        PRODUCT-RELEASE     "SEOS 6.1.3 [SE]; SEOS 6.3.X [SM]; SEOS 11.1.x [SSR]"
        STATUS              current
        DESCRIPTION         "MAU-MIB capabilities for SmartEdge"
        SUPPORTS            MAU-MIB
        INCLUDES {
                   mauIfGrpBasic,
                   mauIfGrpHighCapacity,
                   mauIfGrpHCStats,
                   mauIfGrpAutoNeg2,
                   mauIfGrpAutoNeg1000Mbps
                 }
                
        VARIATION       ifMauStatus
        ACCESS          read-only
        DESCRIPTION     
            "Write access in not allowed."
            
        VARIATION       ifMauDefaultType
        ACCESS          read-only
        DESCRIPTION     
            "Write access in not allowed."

        VARIATION       ifMauAutoNegAdminStatus
        ACCESS          read-only
        DESCRIPTION     
            "Write access in not allowed."
            
        VARIATION       ifMauAutoNegRestart
        ACCESS          read-only
        DESCRIPTION     
            "Write access in not allowed."

        VARIATION       ifMauAutoNegCapAdvertisedBits
        ACCESS          read-only
        DESCRIPTION     
            "Write access in not allowed."

        VARIATION       ifMauAutoNegRemoteFaultAdvertised
        ACCESS          read-only
        DESCRIPTION     
            "Write access in not allowed."


        ::= { eriRouterIetfMauCap 4 }

END
