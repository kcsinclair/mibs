-- %DNP% $Id: RBN-IETF-ITU-ALARM-CAP.my,v 1.1.4.4 2011/06/15 18:19:45 danielhe Exp $
-- %DNP% $Source: /cvsroot/pkt/sw/se/xc/bsd/config/snmp/mibs/Attic/RBN-IETF-ITU-ALARM-CAP.my,v $
-- *****************************************************************
-- RBN-IETF-ITU-ALARM-CAP.my:	IETF ITU-ALARM-MIB Agent Capabilities
--
-- Copyright (c) 2009, 2011 Ericsson AB.
-- All rights reserved.
-- 
-- *****************************************************************

RBN-IETF-ITU-ALARM-CAP DEFINITIONS ::= BEGIN

IMPORTS
	MODULE-IDENTITY
		FROM SNMPv2-SMI
	AGENT-CAPABILITIES
		FROM SNMPv2-CONF
	rbnCapabilities
		FROM RBN-SMI;

rbnIetfItuAlarmCap MODULE-IDENTITY
        LAST-UPDATED    "201106150000Z" -- Jun 15, 2011
        ORGANIZATION    "Ericsson AB."
        CONTACT-INFO
                "       Ericsson AB.

                Postal: 100 Headquarters Dr
                        San Jose, CA  95134
                        USA

                 Phone: +1 408 750 5000
                   Fax: +1 408 750 5599
                "
	DESCRIPTION
		"The Agent Capabilities of the 
                 IETF ITU-ALARM-MIB (RFC 3877)

                If this MIB implementation is platform-dependent,
                the PRODUCT-RELEASE clause contains Ericsson SEOS version and
                at least one of the following Ericsson product families:
                    [SE]  SmartEdge Multi-service Edge Router (MSER) family
                    [SM]  SM family of Metro Ethernet Service Transport platforms
                    [SSR] Smart Service Router (SSR) family"

        REVISION        "201106150000Z" -- Jun 15, 2011
        DESCRIPTION
            "Update DESCRIPTION clause of MODULE-IDENTITY
            and PRODUCT-RELEASE clause of AGENT-CAPABILITIES."
        
        REVISION        "201101191800Z" -- Jan 19, 2011
        DESCRIPTION
                "Update CONTACT-INFO & ORGANIZATION. "

	REVISION	"200903031700Z" -- March 3, 2009
	DESCRIPTION
		"Initial version"
	::= { rbnCapabilities 92 }

rbnIetfItuAlarmCap1 AGENT-CAPABILITIES
	PRODUCT-RELEASE	"SEOS 6.2.1 [SE]; SEOS 6.3.X [SM]; SEOS 11.1.x [SSR]"
	STATUS		current
	DESCRIPTION	"ITU-ALARM-MIB capabilities"
	SUPPORTS	ITU-ALARM-MIB
	INCLUDES {
            ituAlarmGroup
        }
	::= { rbnIetfItuAlarmCap 1 }


END
