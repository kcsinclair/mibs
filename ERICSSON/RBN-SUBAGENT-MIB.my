-- *****************************************************************
-- RBN-SUBAGENT-MIB   SubAgent test Mib
--
-- %DNP% Copyright (c) 2013 Ericsson AB
-- %DNP% All rights reserved.
--
-- *****************************************************************
SUBAGENT-MIB DEFINITIONS ::= BEGIN

IMPORTS
    MODULE-IDENTITY, OBJECT-TYPE, NOTIFICATION-TYPE, Integer32
        FROM SNMPv2-SMI

    MODULE-COMPLIANCE, OBJECT-GROUP
        FROM SNMPv2-CONF

    RowStatus
        FROM SNMPv2-TC

    rbnMgmt
        FROM RBN-SMI;

subagentxMIB MODULE-IDENTITY
    LAST-UPDATED "201303080000Z"            -- 08 March 2013
    ORGANIZATION "Ericsson"
    CONTACT-INFO "postal:   Kovacs Zsolt
                            Budapest
                            1117 Irinyi ut

		  email:    kovacs.zsolt@ericssson.com
                 "
    DESCRIPTION  "A simple mib for demonstration purposes.
                 "
    ::= { rbnMgmt 103 }
subagent         OBJECT IDENTIFIER ::= {subagentxMIB 1}

subagentManufacturer OBJECT-TYPE
  SYNTAX  DisplayString
  MAX-ACCESS  read-only
  STATUS  current
  DESCRIPTION
          "The name of the subagent's manufacturer. For instance,
          Ericsson subagent."
  ::= {subagent 1}

subagentModelNumber OBJECT-TYPE
  SYNTAX  DisplayString
  MAX-ACCESS  read-only
  STATUS  current
  DESCRIPTION
          "The name of the subagent's model. For instance,
          SSR Automatic."
  ::= {subagent 2}

subagentControl OBJECT-TYPE
  SYNTAX  INTEGER  {up (1), down (2)}
  MAX-ACCESS  read-write
  STATUS  current
  DESCRIPTION
          "This variable controls the current state of the subagent. To
          begin working, set it to down (2). To abort working
          (perhaps in the event of an emergency), set it to up (2)."
  ::= {subagent 3}

subagentDoneness OBJECT-TYPE
  SYNTAX  INTEGER (1..10)
  MAX-ACCESS  read-write
  STATUS  current
  DESCRIPTION
          "This variable controls how well-done is the ensuing processing. It
          should be on a scale of 1 to 10."
  ::= {subagent 4}

subagentMaterialType OBJECT-TYPE
  SYNTAX  INTEGER { gypsum(1),
                    calcite(2),
                    fluorite(3),
                    apatite(4),
                    topaz(5),
                    garnet(6),
                    diamond(7)
                  }
  MAX-ACCESS  read-write
  STATUS  current
  DESCRIPTION
          "This variable informs the subagent of the type of material that
          is being processed. The subagent uses this information, combined
          with subagentToastDoneness, to compute for how long the material
          must be processed to achieve the required doneness."
  ::= {subagent 5}

END
