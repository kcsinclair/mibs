-- %DNP% $Id: RBN-IETF-ETHER-WIS-CAP.my,v 1.1.4.5 2011/06/15 18:19:45 danielhe Exp $
-- %DNP% $Source: /cvsroot/pkt/sw/se/xc/bsd/config/snmp/mibs/Attic/RBN-IETF-ETHER-WIS-CAP.my,v $
-- *****************************************************************
-- RBN-IETF-ETHER-WIS-CAP.my    IETF ETHER-WIS 
--
-- Copyright (c) 2010 Ericsson AB.
-- All rights reserved.
-- 
-- *****************************************************************

RBN-IETF-ETHER-WIS-CAP DEFINITIONS ::= BEGIN

IMPORTS
	MODULE-IDENTITY
		FROM SNMPv2-SMI
	AGENT-CAPABILITIES
		FROM SNMPv2-CONF
	rbnCapabilities
		FROM RBN-SMI;

rbnIetfEtherWisCap MODULE-IDENTITY
	LAST-UPDATED    "201106150000Z" -- Jun 15, 2011
	ORGANIZATION	"Ericsson AB."
	CONTACT-INFO
		"	Ericsson AB.

                Postal: 100 Headquarters Dr.
                        San Jose, CA  95134
                        USA

                 Phone: +1 408 570 5000
                   Fax: +1 408 570 5599"

	DESCRIPTION
		"The Agent Capabilities of the IETF ETHER-WIS-MIB.

                If this MIB implementation is platform-dependent,
                the PRODUCT-RELEASE clause contains Ericsson SEOS version and
                at least one of the following Ericsson product families:
                    [SE]  SmartEdge Multi-service Edge Router (MSER) family
                    [SM]  SM family of Metro Ethernet Service Transport platforms
                    [SSR] Smart Service Router (SSR) family"

        REVISION        "201106150000Z" -- Jun 15, 2011
        DESCRIPTION
            "Update DESCRIPTION clause of MODULE-IDENTITY
            and PRODUCT-RELEASE clause of AGENT-CAPABILITIES."
        
	REVISION    "200903031700Z" -- March 3, 2009
	DESCRIPTION
		"Initial version"
        ::= { rbnCapabilities 96 }

rbnIetfEtherWisCap1 AGENT-CAPABILITIES
	PRODUCT-RELEASE	"SEOS 6.3"
	STATUS		current
	DESCRIPTION	"ETHER-WIS capabilities"
	SUPPORTS	ETHER-WIS
	INCLUDES {
            etherWisPathGroup
	}
	::= { rbnIetfEtherWisCap 1 }

END
