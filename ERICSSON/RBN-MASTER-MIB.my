-- *****************************************************************
-- RBN-MASTER-MIB   MasterAgent Mib
--
-- %DNP% Copyright (c) 2013 Ericsson AB
-- %DNP% All rights reserved.
-- This MIB should not be used anymore, all the product should use
-- RBN-MASTER-AGENT.my instead of this one.
--
-- *****************************************************************
MASTERAGENT-MIB DEFINITIONS ::= BEGIN

IMPORTS
    MODULE-IDENTITY, OBJECT-TYPE, NOTIFICATION-TYPE, Unsigned32
        FROM SNMPv2-SMI

    MODULE-COMPLIANCE, OBJECT-GROUP
        FROM SNMPv2-CONF

    RowStatus
        FROM SNMPv2-TC

    agentxSessionDescr
	FROM AGENTX-MIB

    rbnMgmt
        FROM RBN-SMI;

	masteragentxMIB MODULE-IDENTITY
	    LAST-UPDATED "201303080000Z"            -- 08 March 2013
	    ORGANIZATION "Ericsson"
	    CONTACT-INFO "postal:   Kovacs Zsolt
		                    Budapest
		                    1117 Irinyi ut

			  email:    kovacs.zsolt@ericssson.com
		         "
	    DESCRIPTION  "An AgentX master mib for
		         "

	    ::= { rbnMgmt 104 }
masteragent   OBJECT IDENTIFIER ::= {masteragentxMIB 1}

agentxSessionCloseReason OBJECT-TYPE
  SYNTAX      Unsigned32 (1..6)
  MAX-ACCESS  not-accessible
  STATUS      current
  DESCRIPTION
     "Contains the reason from AgentX-Close-PDU 'reason' field.
     "
  DEFVAL      { 0 }
  ::= { masteragentxMIB 2 }

rbnSubAgentLost NOTIFICATION-TYPE
OBJECTS {
	agentxSessionDescr,
	agentxSessionCloseReason
     }
STATUS   deprecated
DESCRIPTION
  "The notification is sent in case of AgentX sub-agent session is lost or closed."
::= { masteragent 2 }

END
