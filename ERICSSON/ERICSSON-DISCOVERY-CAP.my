-- *****************************************************************
-- ERICSSON-DISCOVERY-CAP
--
-- Copyright (c) 2016 Ericsson AB.
-- All rights reserved.
--
-- *****************************************************************

ERICSSON-DISCOVERY-CAP DEFINITIONS ::= BEGIN

IMPORTS
        MODULE-IDENTITY, OBJECT-TYPE, NOTIFICATION-TYPE,
        Integer32
                FROM SNMPv2-SMI
        TEXTUAL-CONVENTION
                FROM SNMPv2-TC
        InetAddress, InetAddressType
                FROM INET-ADDRESS-MIB
        ericssonModules
                FROM ERICSSON-TOP-MIB
        OBJECT-GROUP, NOTIFICATION-GROUP, MODULE-COMPLIANCE
                FROM SNMPv2-CONF;

ericssonDiscoveryMibCap MODULE-IDENTITY
        LAST-UPDATED    "201601131700Z"  -- 13 Jan, 2016
        ORGANIZATION    "Ericsson Inc."
        CONTACT-INFO
                "       Ericsson, Inc.

                Postal: 100 Headquarters Dr.
                        San Jose, CA 95134
                        USA

                 Phone: +1 408 750 5000
                   Fax: +1 408 750 5599
                "
        DESCRIPTION
                "The Agent Capabilities of the Ericsson Discovery MIB
                (ERICSSON-DISCOVERY-MIB).

                If this MIB implementation is platform-dependent,
                the PRODUCT-RELEASE clause contains Ericsson SEOS version and
                at least one of the following Ericsson product families:
                [SE]  SmartEdge Multi-service Edge Router (MSER) family
                [SM]  SM family of Metro Ethernet Service Transport platforms
                [SSR] Smart Service Router (SSR) family"

        ::= { eriRouterCapabilities 110 }

ericssonDiscoveryMibCap1 AGENT-CAPABILITIES
        PRODUCT-RELEASE "IPOS 6.2.x.x"
        STATUS          current
        DESCRIPTION     "ERICSSON-DISCOVERY-MIB capabilities"
        SUPPORTS        ERICSSON-DISCOVERY-MIB
        INCLUDES {
                eriDiscoveryControlGroup,
                eriDiscoveryEventContentGroup1,
                eriDiscoveryEventGroup,
                eriDiscoveryEventOptionalContentGroup1
        }

        ::= { ericssonDiscoveryMibCap 1 }

END
