-- *****************************************************************
-- ERICSSON-ROUTER-MASTER-MIB   MasterAgent Mib
--
-- %DNP% Copyright (c) 2013, 2015 Ericsson AB
-- %DNP% All rights reserved.
-- This MIB should not be used anymore, all the product should use
-- ERICSSON-ROUTER-MASTER-AGENT.my instead of this one.
--
-- *****************************************************************
ERICSSON-ROUTER-MASTER-MIB DEFINITIONS ::= BEGIN

IMPORTS
    MODULE-IDENTITY, OBJECT-TYPE, NOTIFICATION-TYPE, Unsigned32
        FROM SNMPv2-SMI

    MODULE-COMPLIANCE, OBJECT-GROUP
        FROM SNMPv2-CONF

    RowStatus
        FROM SNMPv2-TC

    agentxSessionDescr
	FROM AGENTX-MIB

    eriRouterMgmt
        FROM ERICSSON-ROUTER-SMI;

	eriRouterMasteragentxMIB MODULE-IDENTITY
	    LAST-UPDATED "201501141800Z" -- Jan 14, 2015
	    ORGANIZATION "Ericsson"
	    CONTACT-INFO "postal:   Kovacs Zsolt
		                    Budapest
		                    1117 Irinyi ut

			  email:    kovacs.zsolt@ericssson.com
		         "
	    DESCRIPTION  "An AgentX master mib for
		         "

            REVISION     "201501141800Z" -- Jan 14, 2015
            DESCRIPTION
                "Updated RBN/rbn/Rbn as ERICSSON-ROUTER/eriRouter/EriRouter
                 to migrate RBN MIB to ERICSSON MIB."

	    ::= { eriRouterMgmt 104 }
eriRouterMasteragent   OBJECT IDENTIFIER ::= {eriRouterMasteragentxMIB 1}

eriRouterAgentxSessionCloseReason OBJECT-TYPE
  SYNTAX      Unsigned32 (1..6)
  MAX-ACCESS  not-accessible
  STATUS      current
  DESCRIPTION
     "Contains the reason from AgentX-Close-PDU 'reason' field.
     "
  DEFVAL      { 0 }
  ::= { eriRouterMasteragentxMIB 2 }

eriRouterSubAgentLost NOTIFICATION-TYPE
OBJECTS {
	eriRouterAgentxSessionDescr,
	eriRouterAgentxSessionCloseReason
     }
STATUS   deprecated
DESCRIPTION
  "The notification is sent in case of AgentX sub-agent session is lost or closed."
::= { eriRouterMasteragent 2 }

END
