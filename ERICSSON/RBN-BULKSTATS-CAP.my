-- %DNP%
-- %DNP% $Source: /cvsroot/pkt/sw/se/xc/bsd/config/snmp/mibs/Attic/RBN-BULKSTATS-CAP.my,v $
-- *****************************************************************
-- RBN-BULKSTATS-CAP	Bulk Statistics MIB Capabilities
--
-- Copyright (c) 2002-2003, 2010-2011 Ericsson AB
-- All rights reserved.
-- 
-- *****************************************************************

RBN-BULKSTATS-CAP DEFINITIONS ::= BEGIN

IMPORTS
	MODULE-IDENTITY
		FROM SNMPv2-SMI
	AGENT-CAPABILITIES
		FROM SNMPv2-CONF
	rbnCapabilities
		FROM RBN-SMI;

rbnBulkStatsCap MODULE-IDENTITY
        LAST-UPDATED    "201106150000Z" -- Jun 15, 2011
        ORGANIZATION    "Ericsson Inc."
        CONTACT-INFO
                "       Ericsson, Inc.

                Postal: 100 Headquarters Dr.
                        San Jose, CA  95134
                        USA

                 Phone: +1 408 750 5000
                   Fax: +1 408 750 5599
                "
 	DESCRIPTION
		"The Agent Capabilities of the 
		Bulk Statistics MIB (RBN-BULKSTATS-MIB).

                If this MIB implementation is platform-dependent,
                the PRODUCT-RELEASE clause contains Ericsson SEOS version and
                at least one of the following Ericsson product families:
                    [SE]  SmartEdge Multi-service Edge Router (MSER) family
                    [SM]  SM family of Metro Ethernet Service Transport platforms
                    [SSR] Smart Service Router (SSR) family"

        REVISION        "201106150000Z" -- Jun 15, 2011
        DESCRIPTION
            "Update DESCRIPTION clause of MODULE-IDENTITY
            and PRODUCT-RELEASE clause of AGENT-CAPABILITIES."
        REVISION    "201011010000Z" -- Nov 1, 2010
        DESCRIPTION
            "Modified PRODUCT-RELEASE clause for consistent naming.
             Updated CONTACT-INFO."

	REVISION	"200305010000Z" -- May 1, 2003
	DESCRIPTION
		"Added new OID: rbnBulkStatsCap2."

	REVISION	"200207020000Z" -- July 2, 2002
	DESCRIPTION
		"Initial version."
	::= { rbnCapabilities 46 }

rbnBulkStatsCap1 AGENT-CAPABILITIES
	PRODUCT-RELEASE	"SEOS 2.3.X"
	STATUS		current
	DESCRIPTION	"RBN-BULKSTATS-MIB capabilities"
	SUPPORTS	RBN-BULKSTATS-MIB
	INCLUDES {
		rbnBulkStatsMIBObjectGroup,
		rbnBulkStatsMIBNotificationGroup
		}

	::= { rbnBulkStatsCap 1 }

rbnBulkStatsCap2 AGENT-CAPABILITIES
	PRODUCT-RELEASE	"SEOS 2.5.X [SE]; SEOS 6.3.X [SM]; SEOS 11.1.X [SSR]"
	STATUS		current
	DESCRIPTION	"RBN-BULKSTATS-MIB capabilities"
	SUPPORTS	RBN-BULKSTATS-MIB
	INCLUDES {
		rbnBulkStatsMIBObjectGroup2,
		rbnBulkStatsMIBNotificationGroup2
		}

	::= { rbnBulkStatsCap 2 }

END
