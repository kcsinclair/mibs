BTI7800-CONDITIONS-MIB DEFINITIONS ::= BEGIN
IMPORTS
    enterprises, MODULE-IDENTITY, OBJECT-TYPE,
    Integer32, Unsigned32, Counter32, Counter64,
    Gauge32, IpAddress
        FROM SNMPv2-SMI
    TEXTUAL-CONVENTION, RowStatus, DateAndTime,
    TruthValue
        FROM SNMPv2-TC
;

bTI7800-CONDITIONS-MIB MODULE-IDENTITY
    LAST-UPDATED "201302190000Z"
    ORGANIZATION "@ORGANIZATION"
    CONTACT-INFO "@CONTACT-INFO"
    DESCRIPTION "The atlas-conditions submodule defines the data modeling that supports
the retrieval of active alarms and conditions on the Atlas system."
    REVISION "201302190000Z"
    DESCRIPTION "@REVISION-DESCRIPTION"
    ::= { enterprises 18070 2 9 1 }

ConfdString ::= TEXTUAL-CONVENTION
    DISPLAY-HINT "1t"
    STATUS      current
    DESCRIPTION "xs: and confd: types mapped to strings"
    SYNTAX      OCTET STRING

String ::= TEXTUAL-CONVENTION
    DISPLAY-HINT "1t"
    STATUS      current
    DESCRIPTION "xs:string"
    SYNTAX      OCTET STRING

Severity ::= TEXTUAL-CONVENTION
    STATUS      current
    DESCRIPTION ""
    SYNTAX      INTEGER {critical(1),major(2),minor(3),not-alarmed(4),not-reported(5)}

ConditionCode ::= TEXTUAL-CONVENTION
    STATUS      current
    DESCRIPTION ""
    SYNTAX      INTEGER {eqptMiss(1),eqptUnkn(2),eqptMism(3),eqptFail(4),eqptDgrd(5),eqptComm(6),upgr(7),lpbk(8),los(9),lof(10),loSync(11),lola(12),lom(13),tim(14),sd(15),bdi(16),pyldMism(17),odtgMism(18),ais-l(19),ms-ais(20),otu-ais(21),odu-ais(22),lck(23),oci(24),highBer(25),lf(26),rf(27),rdi-l(28),ms-rdi(29),oprHighTh(30),oprLowTh(31),optHighTh(32),optLowTh(33),laserTempHighTh(34),laserTempLowTh(35),laserFail(36),cfgUnsupp(37),cfgFail(38),lolightRx(39),lolightTx(40),feim(41),feci(42),contComS(43),contComE(44),loSpecRx(45),tLossRxHt(46),iaocp(47),iaocm(48),iaocb(49),apsd(50),pmi(51),uneqO(52),aisO(53),posRx(54),posTx(55),obros(56),chnDfc(57),replUnitDegrade(58),cnxMea(59),cnxVldTmout(60),posRxHigh(61),posRxLow(62),oprHighFail(63),obrHt(64),apr(65),modTempHighTh(66),modTempLowTh(67),modTempShutdown(68),envTempHighTh(69),envTempLowTh(70),envTempFail(71),envVoltHighTh(72),envVoltLowTh(73),envVoltFail(74),scmNmiDown(75),scmNoNmConn(76),eqptLatchOpen(77),powerAbsent(78),fanSpeedLowTh(79),nonCoLocatedController(80),preFecBerTh(81),firmUpgrdReqd(82),otuBerTh(83),oduBerTh(84),pcsBerTh(85),berTh-s(86),berTh-l(87),rs-berTh(88),ms-berTh(89),oneCableDisconnected(90),envCurrentHighTh(91),envCurrentLowTh(92),prbs(93),forced(94),lockout(95),tLossRxLt(96),omsBdi(97),ochAis(98),ochRdi(99),ochUeq(100),ochOci(101),defRDICCM(102),defMACStatus(103),defRemoteCCM(104),defErrorCCM(105),defXconCCM(106),defBfdDown(107),lf-tx(108),apsData(109),omsAis(110),isisDbOvrld(111),isisXDown(112),isisAdjDown(113),isisAdjRejected(114),rsvpAdjDown(115),diskHighUsage(116),memHighUsage(117),invUnknown(118),airfilterAbsense(119),tx-msais(120),tx-msrdi(121),tx-aisl(122),tx-rdil(123),tx-rf(124),tx-oduAis(125),tx-oduLck(126),tx-oduOci(127),tx-opucsf(128),firmUpgrdInProg(129),firmUpgrdFail(130),partitionFault(131),oom(132),lolck(133),inventoryUnsupp(134),eqptBrownout(135)}

conditionsTable OBJECT-TYPE
    SYNTAX      SEQUENCE OF ConditionsEntry
    MAX-ACCESS  not-accessible
    STATUS      current
    DESCRIPTION "Severity and handling of system condition events"
    ::= { bTI7800-CONDITIONS-MIB 1 }

conditionsEntry OBJECT-TYPE
    SYNTAX      ConditionsEntry
    MAX-ACCESS  not-accessible
    STATUS      current
    DESCRIPTION ""
    INDEX { conditionsEntityName, conditionsCode }
        ::= { conditionsTable 1 }

ConditionsEntry ::=
    SEQUENCE {
        conditionsEntityName String,
        conditionsCode ConditionCode,
        conditionsReportType INTEGER,
        conditionsTimeStamp DateAndTime,
        conditionsSeverity Severity,
        conditionsServiceAffecting TruthValue,
        conditionsDescription String
    }

conditionsEntityName OBJECT-TYPE
    SYNTAX      String
    MAX-ACCESS  not-accessible
    STATUS      current
    DESCRIPTION ""
    ::= { conditionsEntry 1 }

conditionsCode OBJECT-TYPE
    SYNTAX      ConditionCode
    MAX-ACCESS  not-accessible
    STATUS      current
    DESCRIPTION ""
    ::= { conditionsEntry 2 }

conditionsReportType OBJECT-TYPE
    SYNTAX      INTEGER {non-alarmed(1),alarmed(2)}
    MAX-ACCESS  read-only
    STATUS      current
    DESCRIPTION ""
    ::= { conditionsEntry 3 }

conditionsTimeStamp OBJECT-TYPE
    SYNTAX      DateAndTime
    MAX-ACCESS  read-only
    STATUS      current
    DESCRIPTION ""
    ::= { conditionsEntry 4 }

conditionsSeverity OBJECT-TYPE
    SYNTAX      Severity
    MAX-ACCESS  read-only
    STATUS      current
    DESCRIPTION ""
    ::= { conditionsEntry 5 }

conditionsServiceAffecting OBJECT-TYPE
    SYNTAX      TruthValue
    MAX-ACCESS  read-only
    STATUS      current
    DESCRIPTION ""
    ::= { conditionsEntry 6 }

conditionsDescription OBJECT-TYPE
    SYNTAX      String
    MAX-ACCESS  read-only
    STATUS      current
    DESCRIPTION ""
    ::= { conditionsEntry 7 }

END
