-- CVX Policy Manager MIB

CPM-MIB

--FORCE-INCLUDE <envoy/h/asn1.h>
--FORCE-INCLUDE <envoy/h/mib.h>
--FORCE-INCLUDE <envoy/h/snmpdefs.h>
--FORCE-INCLUDE <envoy/h/snmp.h>
--FORCE-INCLUDE <envoy/h/snmpstat.h>
-- FORCE-INCLUDE "snmp_proxy.hxx"
--FORCE-INCLUDE "mib_callbacks.hxx"

DEFINITIONS ::= BEGIN

IMPORTS
    dialaccess        
        FROM CPM-NORTEL-MIB
    MODULE-IDENTITY, OBJECT-IDENTITY, OBJECT-TYPE, IpAddress,
    Integer32  -- NOTIFICATION-TYPE, Counter32
        FROM SNMPv2-SMI
    DisplayString     
        FROM SNMPv2-TC
    TRAP-TYPE         
        FROM RFC-1215;

cpm MODULE-IDENTITY
    LAST-UPDATED "0002170000Z"    -- February 17, 2000
    ORGANIZATION "Nortel Networks"
    CONTACT-INFO
            "       Jim Wimberley

                    Nortel Networks
                    3500 Carling Avenue
                    Nepean, Ontario, Canada
                    K2H 8E9

             phone: 613-765-2582
             email: rrjames@nortelnetworks.com"
    DESCRIPTION
            "CVX Policy Manager MIB"
    ::= { dialaccess 3 }


-- - - - - - - - - - - - - - - - - - - - - - - 
-- 
-- Define the top level branches 
-- 

cpm-conf    OBJECT-IDENTITY   
    STATUS      current 
    DESCRIPTION "Sub-tree for configuration objects" 
    ::= { cpm 1 }

cpm-performance    OBJECT-IDENTITY   
    STATUS      current 
    DESCRIPTION "Sub-tree for performance and operational metrics
             objects" 
    ::= { cpm 2 }

cpm-surv    OBJECT-IDENTITY   
    STATUS      current 
    DESCRIPTION "Sub-tree for surveillance related objects" 
    ::= { cpm 3 }

-- cpm-accounting OBJECT-IDENTITY   ::= { cpm 4 }
-- cpm-security   OBJECT-IDENTITY   ::= { cpm 5 }


-- - - - - - - - - - - - - - - - - - - - - - - 
-- 
-- Configuration subtree is divided into multiple groups:  
-- 

cpm-sysconf OBJECT-IDENTITY 
    STATUS      current 
    DESCRIPTION     "sub-tree for cpm system related objects"
    --DEFAULT     get-function-async  cpmmib_get_%n
    --DEFAULT     next-function-async std_next_async
    ::= { cpm-conf 1 } 

-- How about the following objects:  
--    sysAbsStartTime        - absolute seconds since epoch
--    sysMibRevision         - MIB version string
--    sysSoftwareRevision    - CPM version string
--    sysConfigFile          - "pathname of current config file"
--    sysLogFile             - "pathname of current log file"
--    sysLogFileMaxSize      - "max size (in lines) of log file"
--    sysTraceLevel          - one of DEBUG(7) to EMERGENCY(0) 
--    sysOperationalState    - one of: 
--                           - initializing (read configuration)
--                           - discovering  (auditing network ... )
--                           - ready        (audit complete ...
--                           - receiving-requests
--

sysAbsStartTime OBJECT-TYPE
    SYNTAX       Integer32 
    MAX-ACCESS   read-only
    STATUS       current
    DESCRIPTION  "time of last system startup in seconds since 
                  epoch (Jan 1, 1970 GMT)"
    ::=     { cpm-sysconf 1 } 

sysMibRevision OBJECT-TYPE
    SYNTAX       DisplayString(SIZE(8)) 
    MAX-ACCESS   read-only
    STATUS       current
    DESCRIPTION  "major and minor version number of MIB (vX.X)"
    ::= { cpm-sysconf 2 }  

sysSoftwareRevision OBJECT-TYPE
    SYNTAX       DisplayString(SIZE(8)) 
    MAX-ACCESS   read-only
    STATUS       current
    DESCRIPTION  "major and minor version number of cpm software (vX.X)"
    ::= { cpm-sysconf 3 }  

sysConfigFile OBJECT-TYPE
    SYNTAX       DisplayString(SIZE(255))
    MAX-ACCESS   read-only
    STATUS       current
    DESCRIPTION  "current configuration file name"
    ::= { cpm-sysconf 4 }  

sysLogFile  OBJECT-TYPE
    SYNTAX       DisplayString(SIZE(255))
    MAX-ACCESS   read-only
    STATUS       current
    DESCRIPTION  "current log file"
    ::= { cpm-sysconf 5 }  

sysLogFileMaxSize  OBJECT-TYPE
    SYNTAX       Integer32
    MAX-ACCESS   read-only
    STATUS       current
    DESCRIPTION  "max number of lines in log file"
    ::= { cpm-sysconf 6 }  

sysTraceLevel OBJECT-TYPE
    SYNTAX       Integer32
    MAX-ACCESS   read-only
    STATUS       current
    DESCRIPTION  "current logging/trace level"
    ::= { cpm-sysconf 7 }  

sysOperationalState OBJECT-TYPE
    SYNTAX INTEGER { 
        initializing(0), -- reading configuration
        discovering(1),  -- auditing NAS sessions 
        ready(2)         -- initial audit complete 
    }
    MAX-ACCESS   read-only
    STATUS       current
    DESCRIPTION  "current operating state of CPM"
    ::= { cpm-sysconf 8 }  

-- - - - - - - - - - - - - - - - - - - - - - - 
-- The table containing access to the current CPM OM
-- values (per VPOP)

cpmVpopOMTable OBJECT-TYPE -- cpmVpopMonitoringTable
    SYNTAX       SEQUENCE OF CpmVpopOMEntry
    MAX-ACCESS   not-accessible
    STATUS       current
    DESCRIPTION  "table of current OMs, per VPOP"
    --DEFAULT  get-function-async   cpmVpopOMTable_get_callback
    --DEFAULT  next-function-async  cpmVpopOMTable_next_callback
    ::= { cpm-performance 1 }

cpmVpopOMEntry OBJECT-TYPE -- cpmVpopMonitoringStatsEntry
    SYNTAX       CpmVpopOMEntry
    MAX-ACCESS   not-accessible 
    STATUS       current
    DESCRIPTION  "a VPOP entry in the table of current OMs"
    INDEX       { cpmVpopOMVpopId }
    ::= { cpmVpopOMTable 1 }

CpmVpopOMEntry ::= SEQUENCE {
    cpmVpopOMVpopId                   INTEGER,
    cpmVpopOMPortLimit                INTEGER,
    cpmVpopOMOverflowPortLimit        INTEGER,
    cpmVpopOMActiveCalls              INTEGER,
    cpmVpopOMActivePortLimitCalls     INTEGER,
    cpmVpopOMAcceptedCalls            INTEGER,
    cpmVpopOMAcceptedOverflowCalls    INTEGER,
    cpmVpopOMReleasedCalls            INTEGER,
    cpmVpopOMPortLimitReject          INTEGER,
    cpmVpopOMOverflowPortLimitReject  INTEGER,
    cpmVpopOMClidFilterReject         INTEGER,
    cpmVpopOMProxyReject              INTEGER,
    cpmVpopOMIPAddressReject          INTEGER,
    cpmVpopOMGatewayReject            INTEGER,
    cpmVpopOMGuaranteeReject          INTEGER
}

cpmVpopOMVpopId OBJECT-TYPE -- cpmVpopId
    SYNTAX       INTEGER
    MAX-ACCESS   read-only
    STATUS       current
    DESCRIPTION  "a unique number that identifies the VPOP"
    ::= { cpmVpopOMEntry 1 }

cpmVpopOMPortLimit OBJECT-TYPE -- cpmVpopCurrentLimit
    SYNTAX       INTEGER
    MAX-ACCESS   read-only
    STATUS       current
    DESCRIPTION  "(by VPOP) the current portlimit"
    ::= { cpmVpopOMEntry 2 }

cpmVpopOMOverflowPortLimit OBJECT-TYPE -- cpmVpopOverflow
    SYNTAX       INTEGER
    MAX-ACCESS   read-only
    STATUS       current
    DESCRIPTION  "(by VPOP) the current overflow portlimit"
    ::= { cpmVpopOMEntry 3 }

cpmVpopOMActiveCalls OBJECT-TYPE -- cpmVpopActiveCalls
    SYNTAX       INTEGER
    MAX-ACCESS   read-only
    STATUS       current
    DESCRIPTION  "(by VPOP) the current number of active calls"
    ::= { cpmVpopOMEntry 4 }

cpmVpopOMActivePortLimitCalls OBJECT-TYPE -- cpmVpopPortLimitCalls
    SYNTAX       INTEGER
    MAX-ACCESS   read-only
    STATUS       current
    DESCRIPTION  "(by VPOP) the current number of active port limit calls"
    ::= { cpmVpopOMEntry 5 }

cpmVpopOMAcceptedCalls OBJECT-TYPE -- cpmVpopAcceptedCalls
    SYNTAX       INTEGER
    MAX-ACCESS   read-only
    STATUS       current
    DESCRIPTION  "(by VPOP) the total number of calls accepted during the 
                  uptime of this CPM server"
    ::= { cpmVpopOMEntry 6 }

cpmVpopOMAcceptedOverflowCalls OBJECT-TYPE -- cpmVpopCallsGrantedInOverflowMode
    SYNTAX       INTEGER
    MAX-ACCESS   read-only
    STATUS       current
    DESCRIPTION  "(by VPOP) the total number of calls accepted as overflow calls
                  during the uptime of this CPM server"
    ::= { cpmVpopOMEntry 7 }

cpmVpopOMReleasedCalls OBJECT-TYPE -- cpmVpopReleasedCalls
    SYNTAX       INTEGER
    MAX-ACCESS   read-only
    STATUS       current
    DESCRIPTION  "(by VPOP) the total number of released calls during the uptime 
                  of this CPM server"
    ::= { cpmVpopOMEntry 8 }

cpmVpopOMPortLimitReject  OBJECT-TYPE -- cpmVpopPortLimitReject
    SYNTAX       INTEGER
    MAX-ACCESS   read-only
    STATUS       current
    DESCRIPTION  "(by VPOP) the total number of call attempts that were rejected
                  by the portlimit during the uptime of this server"
    ::= { cpmVpopOMEntry 9 }

cpmVpopOMOverflowPortLimitReject OBJECT-TYPE -- cpmVpopOverflowReject
    SYNTAX       INTEGER
    MAX-ACCESS   read-only
    STATUS       current
    DESCRIPTION  "(by VPOP) the total number of call attempts that were rejected
                  by the overflow portlimit during the uptime of this server"
    ::= { cpmVpopOMEntry 10 }

cpmVpopOMClidFilterReject OBJECT-TYPE -- cpmVpopClidFilterReject
    SYNTAX       INTEGER
    MAX-ACCESS   read-only
    STATUS       current
    DESCRIPTION  "(by VPOP) the total number of call attempts that were rejected 
                  by CLID filters during the uptime of this server"
    ::= { cpmVpopOMEntry 11 }

cpmVpopOMProxyReject OBJECT-TYPE -- cpmVpopCallsProxyReject
    SYNTAX      INTEGER
    MAX-ACCESS      read-only
    STATUS      current
    DESCRIPTION     "N/A" 
    ::= { cpmVpopOMEntry 12 }

cpmVpopOMIPAddressReject OBJECT-TYPE -- cpmVpopIPAddressReject
    SYNTAX       INTEGER
    MAX-ACCESS   read-only
    STATUS       current
    DESCRIPTION  "(by VPOP) the total number of call attempts that were rejected 
                  during the uptime of this server because CPM was unable to 
                  assign an IP Address"
    ::= { cpmVpopOMEntry 13 }

cpmVpopOMGatewayReject OBJECT-TYPE -- cpmVpopGatewayReject
    SYNTAX       INTEGER
    MAX-ACCESS   read-only
    STATUS       current
    DESCRIPTION  "(by VPOP) the total number of call attempts that were rejected 
                  during the uptime of this server because CPM was unable to 
                  assign a call to a gateway (or LNS)"
    ::= { cpmVpopOMEntry 14 }

cpmVpopOMGuaranteeReject OBJECT-TYPE -- cpmVpopGuaranteeReject
    SYNTAX       INTEGER
    MAX-ACCESS   read-only
    STATUS       current
    DESCRIPTION  "(by VPOP) the total number of call attempts that were rejected 
                  by the port guarantees."
    ::= { cpmVpopOMEntry 15 }

-- - - - - - - - - - - - - - - - - - - - - - - 
-- The table containing snapshots of OM values (per VPOP)

cpmVpopOMSnapshotTable OBJECT-TYPE -- cpmVpopActiveMonitoringTable
    SYNTAX       SEQUENCE OF CpmVpopOMSnapshotEntry 
    MAX-ACCESS   not-accessible
    STATUS       current 
    DESCRIPTION  "a table of OM snapshots per VPOP" 
    --DEFAULT   get-function-async   cpmVpopOMSnapshotTable_get_callback
    --DEFAULT   next-function-async  cpmVpopOMSnapshotTable_next_callback
    ::= { cpm-performance 2 } 

cpmVpopOMSnapshotEntry       OBJECT-TYPE -- cpmVpopActiveMonitoringStatsEntry
    SYNTAX       CpmVpopOMSnapshotEntry 
    MAX-ACCESS   not-accessible 
    STATUS       current 
    DESCRIPTION  "an entry in the table of OM snapshots per VPOP"
    INDEX           { cpmVpopOMSnapshotVpopId, cpmVpopOMSnapshotTimeStamp } 
    ::= { cpmVpopOMSnapshotTable 1 } 

CpmVpopOMSnapshotEntry ::= SEQUENCE { 
    cpmVpopOMSnapshotVpopId     INTEGER, 
    cpmVpopOMSnapshotTimeStamp  INTEGER,
    cpmVpopOMSnapshotMinCalls   INTEGER, 
    cpmVpopOMSnapshotMaxCalls   INTEGER 
} 

cpmVpopOMSnapshotVpopId OBJECT-TYPE -- cpmVpopIdP
    SYNTAX       INTEGER 
    MAX-ACCESS   read-only 
    STATUS       current 
    DESCRIPTION  "a unique number that identifies the VPOP"
    ::= { cpmVpopOMSnapshotEntry 1 } 

cpmVpopOMSnapshotTimeStamp  OBJECT-TYPE -- cpmVpopOMTimeStamp
    SYNTAX       INTEGER 
    MAX-ACCESS   read-only 
    STATUS       current 
    DESCRIPTION  "the time of of the snapshot in seconds since epoch
                  (Jan 1, 1970 GMT)"
    ::= { cpmVpopOMSnapshotEntry 2 } 

cpmVpopOMSnapshotMinCalls OBJECT-TYPE -- cpmVpopMinCalls
    SYNTAX       INTEGER 
    MAX-ACCESS   read-only 
    STATUS       current 
    DESCRIPTION  "(by VPOP) the minimum number of active calls during reporting 
                  period"
    ::= { cpmVpopOMSnapshotEntry 3 } 

cpmVpopOMSnapshotMaxCalls OBJECT-TYPE -- cpmVpopMaxCalls
    SYNTAX       INTEGER 
    MAX-ACCESS   read-only 
    STATUS       current 
    DESCRIPTION  "(by VPOP) the maximum number of active calls during reporting 
                  period"
    ::= { cpmVpopOMSnapshotEntry 4 } 

-- - - - - - - - - - - - - - - - - - - - - - - 
-- The table containing current alarms

cpmAlarmTable OBJECT-TYPE -- cpmAlarmTable
    SYNTAX       SEQUENCE OF CpmAlarmTableEntry 
    MAX-ACCESS   not-accessible
    STATUS       current 
    DESCRIPTION  "a table of active traps" 
    --DEFAULT   get-function-async   cpmAlarmTable_get_callback
    --DEFAULT   next-function-async  cpmAlarmTable_next_callback
    ::= { cpm-surv 2 } 

cpmAlarmTableEntry       OBJECT-TYPE
    SYNTAX       CpmAlarmTableEntry 
    MAX-ACCESS   not-accessible 
    STATUS       current 
    DESCRIPTION  "an entry in the table of alarms"
    INDEX           { cpmAlarmTableTrapGenNum } 
    ::= { cpmAlarmTable 1 } 

CpmAlarmTableEntry ::= SEQUENCE { 
    cpmAlarmTableTrapGenNum	    INTEGER,
    cpmAlarmTableTrapType		INTEGER,
    cpmAlarmTableTrapSeverity	INTEGER,
    cpmAlarmTableTrapTimeTicks	INTEGER,
    cpmAlarmTableTrapArg1		DisplayString,
    cpmAlarmTableTrapArg2		DisplayString,
    cpmAlarmTableTrapArg3		DisplayString
} 

cpmAlarmTableTrapGenNum OBJECT-TYPE
    SYNTAX       INTEGER 
    MAX-ACCESS   read-only 
    STATUS       current 
    DESCRIPTION  "a unique number that identifies the trap"
    ::= { cpmAlarmTableEntry 1 } 

cpmAlarmTableTrapType OBJECT-TYPE
    SYNTAX       INTEGER {
                     nasNotResponding(2),
                     gatewayRemovedFromService(4),
                     gatewaysUnavailable(6),
                     mpGatewaysUnavailable(8),
                     ipAddressExhausted(10),
                     portsUnavailable(12),
                     overflowPortsInUse(14)
                     }
    MAX-ACCESS   read-only 
    STATUS       current 
    DESCRIPTION  "type of the trap"
    ::= { cpmAlarmTableEntry 2 } 

cpmAlarmTableTrapSeverity OBJECT-TYPE
    SYNTAX       INTEGER {
	                 warning(1),
					 critical(4)
					 }
    MAX-ACCESS   read-only
    STATUS       current 
    DESCRIPTION  "severity of the trap"
    ::= { cpmAlarmTableEntry 3 } 

cpmAlarmTableTrapTimeTicks OBJECT-TYPE
    SYNTAX       INTEGER 
    MAX-ACCESS   read-only 
    STATUS       current 
    DESCRIPTION  "the time that the trap was raised"
    ::= { cpmAlarmTableEntry 4 } 

cpmAlarmTableTrapArg1 OBJECT-TYPE
    SYNTAX       DisplayString(SIZE(255))
    MAX-ACCESS   read-only
    STATUS       current
    DESCRIPTION  "trap raise arguement"
    ::= { cpmAlarmTableEntry 5 } 

cpmAlarmTableTrapArg2 OBJECT-TYPE
    SYNTAX       DisplayString(SIZE(255))
    MAX-ACCESS   read-only
    STATUS       current
    DESCRIPTION  "trap raise arguement"
    ::= { cpmAlarmTableEntry 6 }

cpmAlarmTableTrapArg3 OBJECT-TYPE
    SYNTAX       DisplayString(SIZE(255))
    MAX-ACCESS   read-only
    STATUS       current
    DESCRIPTION  "trap raise arguement"
    ::= { cpmAlarmTableEntry 7 }  	 

-- - - - - - - - - - - - - - - - - - - - - - - 
--
-- Trap Variables
--

cpm-trapVariables OBJECT-IDENTITY 
    STATUS      current 
    DESCRIPTION     "The subtree of information related to Traps"
    ::= { cpm-surv 1 } 

trap-severity OBJECT-TYPE
    SYNTAX INTEGER { 
          normal(0),
          warning(1),
          minor(2), 
          major(3),
          critical(4)
    }
    MAX-ACCESS  not-accessible
    STATUS          current
    DESCRIPTION     "The trap severity."
    ::= { cpm-trapVariables 1 }  

trap-nasIPAddress  OBJECT-TYPE
    SYNTAX       IpAddress
    MAX-ACCESS   not-accessible
    STATUS       current
    DESCRIPTION  "The ip address of a NAS."
    ::= { cpm-trapVariables 2 }  

trap-gatewayIPAddress  OBJECT-TYPE
    SYNTAX       IpAddress
    MAX-ACCESS   not-accessible
    STATUS       current
    DESCRIPTION  "The ip address of a gateway."
    ::= { cpm-trapVariables 3 }  

trap-vpopId  OBJECT-TYPE
    SYNTAX       Integer32
    MAX-ACCESS   not-accessible
    STATUS       current
    DESCRIPTION  "The VPOP id."
    ::= { cpm-trapVariables 4 }  

trap-gennum OBJECT-TYPE
    SYNTAX       Integer32
    MAX-ACCESS   not-accessible
    STATUS       current
    DESCRIPTION  "Unique identifier for the trap."
    ::= { cpm-trapVariables 5 }

trap-AAAServerIPAddress  OBJECT-TYPE
    SYNTAX       IpAddress
    MAX-ACCESS   not-accessible
    STATUS       current
    DESCRIPTION  "The ip address of a AAA server."
    ::= { cpm-trapVariables 6 }  

-- - - - - - - - - - - - - - - - - - - - - - - 
--
-- Trap Definitions
--

cpmStateChangeTrap TRAP-TYPE
    ENTERPRISE cpm
    VARIABLES  {
	   trap-gennum,
       trap-severity,
       sysOperationalState
    }
    DESCRIPTION
      "The Trap generated when CPM changes states."
    ::= 1

nasNotRespondingTrap TRAP-TYPE
    ENTERPRISE cpm
    VARIABLES  {
	   trap-gennum,
       trap-severity,
       trap-nasIPAddress
    }
    DESCRIPTION
      "The Trap generated when a nas stops responding."
    ::= 2

nasNowRespondingTrap TRAP-TYPE
    ENTERPRISE cpm
    VARIABLES  {
	   trap-gennum,
       trap-severity,
       trap-nasIPAddress
    }
    DESCRIPTION
      "The Trap generated when a nas starts responding."
    ::= 3

gatewayRemovedFromService TRAP-TYPE
    ENTERPRISE cpm
    VARIABLES  {
	   trap-gennum,
       trap-severity,
       trap-gatewayIPAddress
    }
    DESCRIPTION
      "The Trap generated when a gateway is removed from service."
    ::= 4

gatewayReturnedToService TRAP-TYPE
    ENTERPRISE cpm
    VARIABLES  {
	   trap-gennum,
       trap-severity,
       trap-gatewayIPAddress
    }
    DESCRIPTION
      "The Trap generated when a gateway is returned to service."
    ::= 5

gatewaysUnavailable TRAP-TYPE
    ENTERPRISE cpm
    VARIABLES  {
	   trap-gennum,
       trap-severity,
       trap-vpopId
    }
    DESCRIPTION
      "The Trap generated when a call is rejected because all 
       gateways are at capacity or administratively locked."
    ::= 6

gatewaysAvailable TRAP-TYPE
    ENTERPRISE cpm
    VARIABLES  {
	   trap-gennum,
       trap-severity,
       trap-vpopId
    }
    DESCRIPTION
      "The Trap generated when a call is accepted after the above
       trap was generated."
    ::= 7

mpGatewaysUnavailable TRAP-TYPE
    ENTERPRISE cpm
    VARIABLES  {
	   trap-gennum,
       trap-severity,
       trap-vpopId
    }
    DESCRIPTION
      "The Trap generated when a call is rejected because all 
       multilink PPP gateways are at capacity or administratively 
       locked."
    ::= 8

mpGatewaysAvailable TRAP-TYPE
    ENTERPRISE cpm
    VARIABLES  {
	   trap-gennum,
       trap-severity,
       trap-vpopId
    }
    DESCRIPTION
      "The Trap generated when a call is accepted after the above
       trap was generated."
    ::= 9

ipAddressesExhausted TRAP-TYPE
    ENTERPRISE cpm
    VARIABLES  {
	   trap-gennum,
       trap-severity,
       trap-vpopId,
       trap-nasIPAddress
    }
    DESCRIPTION
      "The Trap is generated when a call is rejected because an IP
       address could not be assigned from the available pools."
    ::= 10

ipAddressesAvailable TRAP-TYPE
    ENTERPRISE cpm
    VARIABLES  {
	   trap-gennum,
       trap-severity,
       trap-vpopId,
       trap-nasIPAddress
    }
    DESCRIPTION
      "The Trap generated when a call is accepted after the above
       trap was generated."
    ::= 11

portsUnavailable TRAP-TYPE
    ENTERPRISE cpm
    VARIABLES  {
	   trap-gennum,
       trap-severity,
       trap-vpopId
    }
    DESCRIPTION
      "The Trap generated when a call is rejected because all 
       ports, including overflow, are used up."
    ::= 12

portsAvailable TRAP-TYPE
    ENTERPRISE cpm
    VARIABLES  {
	   trap-gennum,
       trap-severity,
       trap-vpopId
    }
    DESCRIPTION
      "The Trap generated when a call is accepted after the above
       trap was generated."
    ::= 13

overflowPortsInUse TRAP-TYPE
    ENTERPRISE cpm
    VARIABLES  {
	   trap-gennum,
       trap-severity,
       trap-vpopId
    }
    DESCRIPTION
      "The trap generated when a call is accepted as an overflow
       port."
    ::= 14

overflowPortsNotInUse TRAP-TYPE
    ENTERPRISE cpm
    VARIABLES  {
	   trap-gennum,
       trap-severity,
       trap-vpopId
    }
    DESCRIPTION
      "The trap generated when a call is accepted not as an overflow 
       after the above trap was generated."
    ::= 15

disconnectRequestDiscarded TRAP-TYPE
    ENTERPRISE cpm
    VARIABLES  {
	   trap-gennum,
       trap-severity,
       trap-AAAServerIPAddress
    }
    DESCRIPTION
      "The trap generated when a RADIUS disconnect request is discarded."
    ::= 16

END
