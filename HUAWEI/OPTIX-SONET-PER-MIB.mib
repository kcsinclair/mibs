--
-- OPTIX-SONET-PER-MIB.mib
-- MIB generated by MG-SOFT Visual MIB Builder Version 3.0 Build 253
-- Monday, March 06, 2006 at 10:26:16
--

-- =================================================================
--  Copyright (C) 2006 by HUAWEI TECHNOLOGIES. All rights reserved
--  
--  Description:This MIB describes the Performance interface of Huawei SONET transmit
--  Reference:
--  Version: V1.00
--  History:
-- 	<author>,<date>,<contents>
-- =================================================================
-- 

	OPTIX-SONET-PER-MIB DEFINITIONS ::= BEGIN
 
		IMPORTS
			optixCommonSonet			
				FROM OPTIX-OID-MIB			
			MOD2Type, PerformanceEventType, LocationType, DirectionType, ValidflagType			
				FROM OPTIX-SONET-TC-MIB			
			OBJECT-GROUP, MODULE-COMPLIANCE			
				FROM SNMPv2-CONF			
			Integer32, Unsigned32, OBJECT-TYPE, MODULE-IDENTITY			
				FROM SNMPv2-SMI			
			DateAndTime			
				FROM SNMPv2-TC;
	
	
		optixSonetPerformance MODULE-IDENTITY 
			LAST-UPDATED "200602250000Z"
			ORGANIZATION 
				"Huawei Technologies co.,Ltd."
			CONTACT-INFO 
				"R&D Building
				Huawei Technologies Co., Ltd.
				Bantian, Longgang District 
				Shenzhen, P. R. China
				http://www.huawei.com
				Zip:518129
				E-mail:support@huawei.com"
			DESCRIPTION 
				"Description."
			REVISION "200602250000Z"
			DESCRIPTION
				"The initial revision of this MIB module."
			::= { optixCommonSonet 20 }
		
	
	
--
-- Node definitions
--
	
--  Alarm data    
		-- 1.3.6.1.4.1.2011.2.25.3.20.20.10
		pmData OBJECT IDENTIFIER ::= { optixSonetPerformance 10 }
		
--  *************************************************************************
-- Perfomance
-- -------------------------------------------------------------------------
-- Perfomance 15-MIN Current Data Table (RTRV-PM-<MOD2>)
-- ------------------------------------------------------------------------- 
		-- 1.3.6.1.4.1.2011.2.25.3.20.20.10.10
		per15mCurDataTable OBJECT-TYPE
			SYNTAX SEQUENCE OF Per15mCurDataEntry
			MAX-ACCESS not-accessible
			STATUS current
			DESCRIPTION
				"instructs an NE to send its current 
				set of PM data associated with one or 
				more equipment units, facilities, 
				links, or signaling links within the NE."
			::= { pmData 10 }
		
--  EID, Such as CV-L, ES-S...
-- NEND FEND
-- RECV TRAN
		-- 1.3.6.1.4.1.2011.2.25.3.20.20.10.10.1
		per15mCurDataEntry OBJECT-TYPE
			SYNTAX Per15mCurDataEntry
			MAX-ACCESS not-accessible
			STATUS current
			DESCRIPTION
				"instructs an NE to send its current 
				set of PM data associated with one or 
				more equipment units, facilities, 
				links, or signaling links within the NE."
			INDEX { pm15mCurDataMOD2, pm15mCurDataSlot, pm15mCurDataPort, pm15mCurDataPath, pm15mCurDataVT, 
				pm15mCurDataName, pm15mCurDataLocation, pm15mCurDataDirection }
			::= { per15mCurDataTable 1 }
		
		Per15mCurDataEntry ::=
			SEQUENCE { 
				pm15mCurDataMOD2
					MOD2Type,
				pm15mCurDataSlot
					Unsigned32,
				pm15mCurDataPort
					Unsigned32,
				pm15mCurDataPath
					Unsigned32,
				pm15mCurDataVT
					Unsigned32,
				pm15mCurDataName
					PerformanceEventType,
				pm15mCurDataLocation
					LocationType,
				pm15mCurDataDirection
					DirectionType,
				pm15mCurDataMonVal
					Integer32,
				pm15mCurDataVldty
					ValidflagType,
				pm15mCurDataStartTime
					DateAndTime
			 }

		-- 1.3.6.1.4.1.2011.2.25.3.20.20.10.10.1.1
		pm15mCurDataMOD2 OBJECT-TYPE
			SYNTAX MOD2Type
			MAX-ACCESS read-only
			STATUS current
			DESCRIPTION
				"Signal mode."
			::= { per15mCurDataEntry 1 }
		
		-- 1.3.6.1.4.1.2011.2.25.3.20.20.10.10.1.2
		pm15mCurDataSlot OBJECT-TYPE
			SYNTAX Unsigned32
			MAX-ACCESS read-only
			STATUS current
			DESCRIPTION
				"Slot number. 
				
				This will indicate what is the slot 
				of the object which raised this PM data.
				If not relevant to the PM data, will be
				zero."
			::= { per15mCurDataEntry 2 }
		
		-- 1.3.6.1.4.1.2011.2.25.3.20.20.10.10.1.3
		pm15mCurDataPort OBJECT-TYPE
			SYNTAX Unsigned32
			MAX-ACCESS read-only
			STATUS current
			DESCRIPTION
				"Port number.
				
				This will indicate what is the Port
				of the object which raised this PM data.
				If not relevant to the PM data, will be
				zero. "
			::= { per15mCurDataEntry 3 }
		
		-- 1.3.6.1.4.1.2011.2.25.3.20.20.10.10.1.4
		pm15mCurDataPath OBJECT-TYPE
			SYNTAX Unsigned32
			MAX-ACCESS read-only
			STATUS current
			DESCRIPTION
				"Path number.
				
				This will indicate what is the Path
				of the object which raised this PM data.
				If not relevant to the PM data, will be
				zero. "
			::= { per15mCurDataEntry 4 }
		
		-- 1.3.6.1.4.1.2011.2.25.3.20.20.10.10.1.5
		pm15mCurDataVT OBJECT-TYPE
			SYNTAX Unsigned32
			MAX-ACCESS read-only
			STATUS current
			DESCRIPTION
				"VT path number.  
				
				This will indicate what is the VT path
				of the object which raised this PM data.
				If not relevant to the PM data, will be
				zero. "
			::= { per15mCurDataEntry 5 }
		
		-- 1.3.6.1.4.1.2011.2.25.3.20.20.10.10.1.6
		pm15mCurDataName OBJECT-TYPE
			SYNTAX PerformanceEventType
			MAX-ACCESS read-only
			STATUS current
			DESCRIPTION
				"Indicates the type of monitored 
				parameter for which a value is retrieved."
			::= { per15mCurDataEntry 6 }
		
		-- 1.3.6.1.4.1.2011.2.25.3.20.20.10.10.1.7
		pm15mCurDataLocation OBJECT-TYPE
			SYNTAX LocationType
			MAX-ACCESS read-only
			STATUS current
			DESCRIPTION
				"Indicates the location.
				Only NEND(Near end)|FEND(Far end)|ALL will be represented here."
			::= { per15mCurDataEntry 7 }
		
		-- 1.3.6.1.4.1.2011.2.25.3.20.20.10.10.1.8
		pm15mCurDataDirection OBJECT-TYPE
			SYNTAX DirectionType
			MAX-ACCESS read-only
			STATUS current
			DESCRIPTION
				"specifies the direction of monitoring.
				Only RCV(Receive direction)|TRMT(Transmit direction)|ALL will be represented here."
			::= { per15mCurDataEntry 8 }
		
		-- 1.3.6.1.4.1.2011.2.25.3.20.20.10.10.1.9
		pm15mCurDataMonVal OBJECT-TYPE
			SYNTAX Integer32
			MAX-ACCESS read-only
			STATUS current
			DESCRIPTION
				"Measured value."
			::= { per15mCurDataEntry 9 }
		
		-- 1.3.6.1.4.1.2011.2.25.3.20.20.10.10.1.10
		pm15mCurDataVldty OBJECT-TYPE
			SYNTAX ValidflagType
			MAX-ACCESS read-only
			STATUS current
			DESCRIPTION
				"It indicates whether the information 
				for the specified time period was 
				accumulated over the entire time period 
				or some portion of it.
				Only INVALID|VALID will be represented here."
			::= { per15mCurDataEntry 10 }
		
		-- 1.3.6.1.4.1.2011.2.25.3.20.20.10.10.1.11
		pm15mCurDataStartTime OBJECT-TYPE
			SYNTAX DateAndTime
			MAX-ACCESS read-only
			STATUS current
			DESCRIPTION
				"The beginning date and time of the PM period."
			::= { per15mCurDataEntry 11 }
		
--  -------------------------------------------------------------------------
-- Perfomance 15-MIN History Data Table (RTRV-PM-<MOD2>)
-- ------------------------------------------------------------------------- 
		-- 1.3.6.1.4.1.2011.2.25.3.20.20.10.20
		per15mHisDataTable OBJECT-TYPE
			SYNTAX SEQUENCE OF Per15mHisDataEntry
			MAX-ACCESS not-accessible
			STATUS current
			DESCRIPTION
				"instructs an NE to send its history 
				set of PM data associated with one or 
				more equipment units, facilities, 
				links, or signaling links within the NE."
			::= { pmData 20 }
		
--  EID, Such as CV-L, ES-S...
-- NEND FEND
-- RECV TRAN
-- Period number
		-- 1.3.6.1.4.1.2011.2.25.3.20.20.10.20.1
		per15mHisDataEntry OBJECT-TYPE
			SYNTAX Per15mHisDataEntry
			MAX-ACCESS not-accessible
			STATUS current
			DESCRIPTION
				"instructs an NE to send its history 
				set of PM data associated with one or 
				more equipment units, facilities, 
				links, or signaling links within the NE."
			INDEX { pm15mHisDataMOD2, pm15mHisDataSlot, pm15mHisDataPort, pm15mHisDataPath, pm15mHisDataVT, 
				pm15mHisDataName, pm15mHisDataLocation, pm15mHisDataDirection, pm15mHisDataInterval }
			::= { per15mHisDataTable 1 }
		
		Per15mHisDataEntry ::=
			SEQUENCE { 
				pm15mHisDataMOD2
					MOD2Type,
				pm15mHisDataSlot
					Unsigned32,
				pm15mHisDataPort
					Unsigned32,
				pm15mHisDataPath
					Unsigned32,
				pm15mHisDataVT
					Unsigned32,
				pm15mHisDataName
					PerformanceEventType,
				pm15mHisDataLocation
					LocationType,
				pm15mHisDataDirection
					DirectionType,
				pm15mHisDataInterval
					Unsigned32,
				pm15mHisDataMonVal
					Integer32,
				pm15mHisDataVldty
					ValidflagType,
				pm15mHisDataStartTime
					DateAndTime
			 }

		-- 1.3.6.1.4.1.2011.2.25.3.20.20.10.20.1.1
		pm15mHisDataMOD2 OBJECT-TYPE
			SYNTAX MOD2Type
			MAX-ACCESS read-only
			STATUS current
			DESCRIPTION
				"Signal mode."
			::= { per15mHisDataEntry 1 }
		
		-- 1.3.6.1.4.1.2011.2.25.3.20.20.10.20.1.2
		pm15mHisDataSlot OBJECT-TYPE
			SYNTAX Unsigned32
			MAX-ACCESS read-only
			STATUS current
			DESCRIPTION
				"Slot number. 
				
				This will indicate what is the slot 
				of the object which raised this PM data.
				If not relevant to the PM data, will be
				zero."
			::= { per15mHisDataEntry 2 }
		
		-- 1.3.6.1.4.1.2011.2.25.3.20.20.10.20.1.3
		pm15mHisDataPort OBJECT-TYPE
			SYNTAX Unsigned32
			MAX-ACCESS read-only
			STATUS current
			DESCRIPTION
				"Port number.
				
				This will indicate what is the Port
				of the object which raised this PM data.
				If not relevant to the PM data, will be
				zero. "
			::= { per15mHisDataEntry 3 }
		
		-- 1.3.6.1.4.1.2011.2.25.3.20.20.10.20.1.4
		pm15mHisDataPath OBJECT-TYPE
			SYNTAX Unsigned32
			MAX-ACCESS read-only
			STATUS current
			DESCRIPTION
				"Path number.
				
				This will indicate what is the Path
				of the object which raised this PM data.
				If not relevant to the PM data, will be
				zero. "
			::= { per15mHisDataEntry 4 }
		
		-- 1.3.6.1.4.1.2011.2.25.3.20.20.10.20.1.5
		pm15mHisDataVT OBJECT-TYPE
			SYNTAX Unsigned32
			MAX-ACCESS read-only
			STATUS current
			DESCRIPTION
				"VT path number.  
				
				This will indicate what is the VT path
				of the object which raised this PM data.
				If not relevant to the PM data, will be
				zero. "
			::= { per15mHisDataEntry 5 }
		
		-- 1.3.6.1.4.1.2011.2.25.3.20.20.10.20.1.6
		pm15mHisDataName OBJECT-TYPE
			SYNTAX PerformanceEventType
			MAX-ACCESS read-only
			STATUS current
			DESCRIPTION
				"Indicates the type of monitored 
				parameter for which a value is retrieved."
			::= { per15mHisDataEntry 6 }
		
		-- 1.3.6.1.4.1.2011.2.25.3.20.20.10.20.1.7
		pm15mHisDataLocation OBJECT-TYPE
			SYNTAX LocationType
			MAX-ACCESS read-only
			STATUS current
			DESCRIPTION
				"Indicates the location.
				Only NEND(Near end)|FEND(Far end)|ALL will be represented here."
			::= { per15mHisDataEntry 7 }
		
		-- 1.3.6.1.4.1.2011.2.25.3.20.20.10.20.1.8
		pm15mHisDataDirection OBJECT-TYPE
			SYNTAX DirectionType
			MAX-ACCESS read-only
			STATUS current
			DESCRIPTION
				"Specifies the direction of monitoring.
				Only RCV(Receive direction)|TRMT(Transmit direction)|ALL will be represented here."
			::= { per15mHisDataEntry 8 }
		
		-- 1.3.6.1.4.1.2011.2.25.3.20.20.10.20.1.9
		pm15mHisDataInterval OBJECT-TYPE
			SYNTAX Unsigned32
			MAX-ACCESS read-only
			STATUS current
			DESCRIPTION
				"The period number."
			::= { per15mHisDataEntry 9 }
		
		-- 1.3.6.1.4.1.2011.2.25.3.20.20.10.20.1.10
		pm15mHisDataMonVal OBJECT-TYPE
			SYNTAX Integer32
			MAX-ACCESS read-only
			STATUS current
			DESCRIPTION
				"Measured value."
			::= { per15mHisDataEntry 10 }
		
		-- 1.3.6.1.4.1.2011.2.25.3.20.20.10.20.1.11
		pm15mHisDataVldty OBJECT-TYPE
			SYNTAX ValidflagType
			MAX-ACCESS read-only
			STATUS current
			DESCRIPTION
				"It indicates whether the information 
				for the specified time period was 
				accumulated over the entire time period 
				or some portion of it.
				Only INVALID|VALID will be represented here."
			::= { per15mHisDataEntry 11 }
		
		-- 1.3.6.1.4.1.2011.2.25.3.20.20.10.20.1.12
		pm15mHisDataStartTime OBJECT-TYPE
			SYNTAX DateAndTime
			MAX-ACCESS read-only
			STATUS current
			DESCRIPTION
				"The beginning date and time of the PM period."
			::= { per15mHisDataEntry 12 }
		
--  -------------------------------------------------------------------------
-- Perfomance 1-DAY Current Data Table (RTRV-PM-<MOD2>)
-- ------------------------------------------------------------------------- 
		-- 1.3.6.1.4.1.2011.2.25.3.20.20.10.30
		per1dayCurDataTable OBJECT-TYPE
			SYNTAX SEQUENCE OF Per1dayCurDataEntry
			MAX-ACCESS not-accessible
			STATUS current
			DESCRIPTION
				"instructs an NE to send its current 
				set of PM data associated with one or 
				more equipment units, facilities, 
				links, or signaling links within the NE."
			::= { pmData 30 }
		
--  EID, Such as CV-L, ES-S...
-- NEND FEND
-- RECV TRAN
		-- 1.3.6.1.4.1.2011.2.25.3.20.20.10.30.1
		per1dayCurDataEntry OBJECT-TYPE
			SYNTAX Per1dayCurDataEntry
			MAX-ACCESS not-accessible
			STATUS current
			DESCRIPTION
				"instructs an NE to send its current 
				set of PM data associated with one or 
				more equipment units, facilities, 
				links, or signaling links within the NE."
			INDEX { pm1dayCurDataMOD2, pm1dayCurDataSlot, pm1dayCurDataPort, pm1dayCurDataPath, pm1dayCurDataVT, 
				pm1dayCurDataName, pm1dayCurDataLocation, pm1dayCurDataDirection }
			::= { per1dayCurDataTable 1 }
		
		Per1dayCurDataEntry ::=
			SEQUENCE { 
				pm1dayCurDataMOD2
					MOD2Type,
				pm1dayCurDataSlot
					Unsigned32,
				pm1dayCurDataPort
					Unsigned32,
				pm1dayCurDataPath
					Unsigned32,
				pm1dayCurDataVT
					Unsigned32,
				pm1dayCurDataName
					PerformanceEventType,
				pm1dayCurDataLocation
					LocationType,
				pm1dayCurDataDirection
					DirectionType,
				pm1dayCurDataMonVal
					Integer32,
				pm1dayCurDataVldty
					ValidflagType,
				pm1dayCurDataStartTime
					DateAndTime
			 }

		-- 1.3.6.1.4.1.2011.2.25.3.20.20.10.30.1.1
		pm1dayCurDataMOD2 OBJECT-TYPE
			SYNTAX MOD2Type
			MAX-ACCESS read-only
			STATUS current
			DESCRIPTION
				"Signal mode."
			::= { per1dayCurDataEntry 1 }
		
		-- 1.3.6.1.4.1.2011.2.25.3.20.20.10.30.1.2
		pm1dayCurDataSlot OBJECT-TYPE
			SYNTAX Unsigned32
			MAX-ACCESS read-only
			STATUS current
			DESCRIPTION
				"Slot number. 
				
				This will indicate what is the slot 
				of the object which raised this PM data.
				If not relevant to the PM data, will be
				zero."
			::= { per1dayCurDataEntry 2 }
		
		-- 1.3.6.1.4.1.2011.2.25.3.20.20.10.30.1.3
		pm1dayCurDataPort OBJECT-TYPE
			SYNTAX Unsigned32
			MAX-ACCESS read-only
			STATUS current
			DESCRIPTION
				"Port number.
				
				This will indicate what is the Port
				of the object which raised this PM data.
				If not relevant to the PM data, will be
				zero. "
			::= { per1dayCurDataEntry 3 }
		
		-- 1.3.6.1.4.1.2011.2.25.3.20.20.10.30.1.4
		pm1dayCurDataPath OBJECT-TYPE
			SYNTAX Unsigned32
			MAX-ACCESS read-only
			STATUS current
			DESCRIPTION
				"Path number.
				
				This will indicate what is the Path
				of the object which raised this PM data.
				If not relevant to the PM data, will be
				zero. "
			::= { per1dayCurDataEntry 4 }
		
		-- 1.3.6.1.4.1.2011.2.25.3.20.20.10.30.1.5
		pm1dayCurDataVT OBJECT-TYPE
			SYNTAX Unsigned32
			MAX-ACCESS read-only
			STATUS current
			DESCRIPTION
				"VT path number.  
				
				This will indicate what is the VT path
				of the object which raised this PM data.
				If not relevant to the PM data, will be
				zero. "
			::= { per1dayCurDataEntry 5 }
		
		-- 1.3.6.1.4.1.2011.2.25.3.20.20.10.30.1.6
		pm1dayCurDataName OBJECT-TYPE
			SYNTAX PerformanceEventType
			MAX-ACCESS read-only
			STATUS current
			DESCRIPTION
				"Indicates the type of monitored 
				parameter for which a value is retrieved."
			::= { per1dayCurDataEntry 6 }
		
		-- 1.3.6.1.4.1.2011.2.25.3.20.20.10.30.1.7
		pm1dayCurDataLocation OBJECT-TYPE
			SYNTAX LocationType
			MAX-ACCESS read-only
			STATUS current
			DESCRIPTION
				"Indicates the location.
				Only NEND(Near end)|FEND(Far end)|ALL will be represented here."
			::= { per1dayCurDataEntry 7 }
		
		-- 1.3.6.1.4.1.2011.2.25.3.20.20.10.30.1.8
		pm1dayCurDataDirection OBJECT-TYPE
			SYNTAX DirectionType
			MAX-ACCESS read-only
			STATUS current
			DESCRIPTION
				"Specifies the direction of monitoring.
				Only RCV(Receive direction)|TRMT(Transmit direction)|ALL will be represented here."
			::= { per1dayCurDataEntry 8 }
		
		-- 1.3.6.1.4.1.2011.2.25.3.20.20.10.30.1.9
		pm1dayCurDataMonVal OBJECT-TYPE
			SYNTAX Integer32
			MAX-ACCESS read-only
			STATUS current
			DESCRIPTION
				"measured value."
			::= { per1dayCurDataEntry 9 }
		
		-- 1.3.6.1.4.1.2011.2.25.3.20.20.10.30.1.10
		pm1dayCurDataVldty OBJECT-TYPE
			SYNTAX ValidflagType
			MAX-ACCESS read-only
			STATUS current
			DESCRIPTION
				"It indicates whether the information 
				for the specified time period was 
				accumulated over the entire time period 
				or some portion of it.
				Only INVALID|VALID will be represented here."
			::= { per1dayCurDataEntry 10 }
		
		-- 1.3.6.1.4.1.2011.2.25.3.20.20.10.30.1.11
		pm1dayCurDataStartTime OBJECT-TYPE
			SYNTAX DateAndTime
			MAX-ACCESS read-only
			STATUS current
			DESCRIPTION
				"The beginning date and time of the PM period."
			::= { per1dayCurDataEntry 11 }
		
--  -------------------------------------------------------------------------
-- Perfomance 1-DAY History Data Table (RTRV-PM-<MOD2>)
-- ------------------------------------------------------------------------- 
		-- 1.3.6.1.4.1.2011.2.25.3.20.20.10.40
		per1dayHisDataTable OBJECT-TYPE
			SYNTAX SEQUENCE OF Per1dayHisDataEntry
			MAX-ACCESS not-accessible
			STATUS current
			DESCRIPTION
				"instructs an NE to send its history 
				set of PM data associated with one or 
				more equipment units, facilities, 
				links, or signaling links within the NE."
			::= { pmData 40 }
		
--  EID, Such as CV-L, ES-S...
-- NEND FEND
-- RECV TRAN
-- Period number
		-- 1.3.6.1.4.1.2011.2.25.3.20.20.10.40.1
		per1dayHisDataEntry OBJECT-TYPE
			SYNTAX Per1dayHisDataEntry
			MAX-ACCESS not-accessible
			STATUS current
			DESCRIPTION
				"instructs an NE to send its history
				set of PM data associated with one or 
				more equipment units, facilities, 
				links, or signaling links within the NE."
			INDEX { pm1dayHisDataMOD2, pm1dayHisDataSlot, pm1dayHisDataPort, pm1dayHisDataPath, pm1dayHisDataVT, 
				pm1dayHisDataName, pm1dayHisDataLocation, pm1dayHisDataDirection, pm1dayHisDataInterval }
			::= { per1dayHisDataTable 1 }
		
		Per1dayHisDataEntry ::=
			SEQUENCE { 
				pm1dayHisDataMOD2
					MOD2Type,
				pm1dayHisDataSlot
					Unsigned32,
				pm1dayHisDataPort
					Unsigned32,
				pm1dayHisDataPath
					Unsigned32,
				pm1dayHisDataVT
					Unsigned32,
				pm1dayHisDataName
					PerformanceEventType,
				pm1dayHisDataLocation
					LocationType,
				pm1dayHisDataDirection
					DirectionType,
				pm1dayHisDataInterval
					Unsigned32,
				pm1dayHisDataMonVal
					Integer32,
				pm1dayHisDataVldty
					ValidflagType,
				pm1dayHisDataStartTime
					DateAndTime
			 }

		-- 1.3.6.1.4.1.2011.2.25.3.20.20.10.40.1.1
		pm1dayHisDataMOD2 OBJECT-TYPE
			SYNTAX MOD2Type
			MAX-ACCESS read-only
			STATUS current
			DESCRIPTION
				"Signal mode."
			::= { per1dayHisDataEntry 1 }
		
		-- 1.3.6.1.4.1.2011.2.25.3.20.20.10.40.1.2
		pm1dayHisDataSlot OBJECT-TYPE
			SYNTAX Unsigned32
			MAX-ACCESS read-only
			STATUS current
			DESCRIPTION
				"Slot number. 
				
				This will indicate what is the slot 
				of the object which raised this PM data.
				If not relevant to the PM data, will be
				zero."
			::= { per1dayHisDataEntry 2 }
		
		-- 1.3.6.1.4.1.2011.2.25.3.20.20.10.40.1.3
		pm1dayHisDataPort OBJECT-TYPE
			SYNTAX Unsigned32
			MAX-ACCESS read-only
			STATUS current
			DESCRIPTION
				"Port number.
				
				This will indicate what is the Port
				of the object which raised this PM data.
				If not relevant to the PM data, will be
				zero. "
			::= { per1dayHisDataEntry 3 }
		
		-- 1.3.6.1.4.1.2011.2.25.3.20.20.10.40.1.4
		pm1dayHisDataPath OBJECT-TYPE
			SYNTAX Unsigned32
			MAX-ACCESS read-only
			STATUS current
			DESCRIPTION
				"Path number.
				
				This will indicate what is the Path
				of the object which raised this PM data.
				If not relevant to the PM data, will be
				zero. "
			::= { per1dayHisDataEntry 4 }
		
		-- 1.3.6.1.4.1.2011.2.25.3.20.20.10.40.1.5
		pm1dayHisDataVT OBJECT-TYPE
			SYNTAX Unsigned32
			MAX-ACCESS read-only
			STATUS current
			DESCRIPTION
				"VT path number.  
				
				This will indicate what is the VT path
				of the object which raised this PM data.
				If not relevant to the PM data, will be
				zero. "
			::= { per1dayHisDataEntry 5 }
		
		-- 1.3.6.1.4.1.2011.2.25.3.20.20.10.40.1.6
		pm1dayHisDataName OBJECT-TYPE
			SYNTAX PerformanceEventType
			MAX-ACCESS read-only
			STATUS current
			DESCRIPTION
				"Indicates the type of monitored 
				parameter for which a value is retrieved."
			::= { per1dayHisDataEntry 6 }
		
		-- 1.3.6.1.4.1.2011.2.25.3.20.20.10.40.1.7
		pm1dayHisDataLocation OBJECT-TYPE
			SYNTAX LocationType
			MAX-ACCESS read-only
			STATUS current
			DESCRIPTION
				"Indicates the location.
				Only NEND(Near end)|FEND(Far end)|ALL will be represented here."
			::= { per1dayHisDataEntry 7 }
		
		-- 1.3.6.1.4.1.2011.2.25.3.20.20.10.40.1.8
		pm1dayHisDataDirection OBJECT-TYPE
			SYNTAX DirectionType
			MAX-ACCESS read-only
			STATUS current
			DESCRIPTION
				"Specifies the direction of monitoring.
				Only RCV(Receive direction)|TRMT(Transmit direction)|ALL will be represented here."
			::= { per1dayHisDataEntry 8 }
		
		-- 1.3.6.1.4.1.2011.2.25.3.20.20.10.40.1.9
		pm1dayHisDataInterval OBJECT-TYPE
			SYNTAX Unsigned32
			MAX-ACCESS read-only
			STATUS current
			DESCRIPTION
				"The period number."
			::= { per1dayHisDataEntry 9 }
		
		-- 1.3.6.1.4.1.2011.2.25.3.20.20.10.40.1.10
		pm1dayHisDataMonVal OBJECT-TYPE
			SYNTAX Integer32
			MAX-ACCESS read-only
			STATUS current
			DESCRIPTION
				"Measured value."
			::= { per1dayHisDataEntry 10 }
		
		-- 1.3.6.1.4.1.2011.2.25.3.20.20.10.40.1.11
		pm1dayHisDataVldty OBJECT-TYPE
			SYNTAX ValidflagType
			MAX-ACCESS read-only
			STATUS current
			DESCRIPTION
				"It indicates whether the information 
				for the specified time period was 
				accumulated over the entire time period 
				or some portion of it.
				Only INVALID|VALID will be represented here."
			::= { per1dayHisDataEntry 11 }
		
		-- 1.3.6.1.4.1.2011.2.25.3.20.20.10.40.1.12
		pm1dayHisDataStartTime OBJECT-TYPE
			SYNTAX DateAndTime
			MAX-ACCESS read-only
			STATUS current
			DESCRIPTION
				"The beginning date and time of the PM period."
			::= { per1dayHisDataEntry 12 }
		
		-- 1.3.6.1.4.1.2011.2.25.3.20.20.20
		optixSonetPmConformance OBJECT IDENTIFIER ::= { optixSonetPerformance 20 }
		
		-- 1.3.6.1.4.1.2011.2.25.3.20.20.20.1
		optixSonetPmGroups OBJECT IDENTIFIER ::= { optixSonetPmConformance 1 }
		
		-- 1.3.6.1.4.1.2011.2.25.3.20.20.20.1.1
		optixSonetPmObjectGroup OBJECT-GROUP
			OBJECTS { pm15mCurDataMOD2, pm15mCurDataSlot, pm15mCurDataPort, pm15mCurDataPath, pm15mCurDataVT, 
				pm15mCurDataName, pm15mCurDataLocation, pm15mCurDataDirection, pm15mCurDataMonVal, pm15mCurDataVldty, 
				pm15mCurDataStartTime, pm15mHisDataMOD2, pm15mHisDataSlot, pm15mHisDataPort, pm15mHisDataPath, 
				pm15mHisDataVT, pm15mHisDataName, pm15mHisDataLocation, pm15mHisDataDirection, pm15mHisDataInterval, 
				pm15mHisDataMonVal, pm15mHisDataVldty, pm15mHisDataStartTime, pm1dayCurDataMOD2, pm1dayCurDataSlot, 
				pm1dayCurDataPort, pm1dayCurDataPath, pm1dayCurDataVT, pm1dayCurDataName, pm1dayCurDataLocation, 
				pm1dayCurDataDirection, pm1dayCurDataMonVal, pm1dayCurDataVldty, pm1dayCurDataStartTime, pm1dayHisDataMOD2, 
				pm1dayHisDataSlot, pm1dayHisDataPort, pm1dayHisDataPath, pm1dayHisDataVT, pm1dayHisDataName, 
				pm1dayHisDataLocation, pm1dayHisDataDirection, pm1dayHisDataInterval, pm1dayHisDataMonVal, pm1dayHisDataVldty, 
				pm1dayHisDataStartTime }
			STATUS current
			DESCRIPTION 
				"Enter the description of the created OBJECT-GROUP."
			::= { optixSonetPmGroups 1 }
		
		-- 1.3.6.1.4.1.2011.2.25.3.20.20.20.2
		optixSonetPmCompliances OBJECT IDENTIFIER ::= { optixSonetPmConformance 2 }
		
		-- 1.3.6.1.4.1.2011.2.25.3.20.20.20.2.1
		optixSonetPmBasicCompliance MODULE-COMPLIANCE
			STATUS current
			DESCRIPTION 
				"Enter the description of the created MODULE-COMPLIANCE."
			MODULE -- this module
				MANDATORY-GROUPS { optixSonetPmObjectGroup }
			::= { optixSonetPmCompliances 1 }
		
	
	END

--
-- OPTIX-SONET-PER-MIB.mib
--
