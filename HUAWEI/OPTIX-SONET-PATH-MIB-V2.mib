--
-- OPTIX-SONET-PATH-MIB-V2.mib
-- MIB generated by MG-SOFT Visual MIB Builder Version 3.0 Build 253
-- Wednesday, July 26, 2006 at 17:18:08
--

	OPTIX-SONET-PATH-MIB-V2 DEFINITIONS ::= BEGIN
 
		IMPORTS
			optixProvisionSonet			
				FROM OPTIX-OID-MIB			
			OBJECT-GROUP, MODULE-COMPLIANCE			
				FROM SNMPv2-CONF			
			Gauge32, OBJECT-TYPE, MODULE-IDENTITY			
				FROM SNMPv2-SMI			
			TEXTUAL-CONVENTION			
				FROM SNMPv2-TC;
	
	
		optixsonetPathAttrib MODULE-IDENTITY 
			LAST-UPDATED "200605261729Z"		-- May 26, 2006 at 17:29 GMT
			ORGANIZATION 
				"Your organization"
			CONTACT-INFO 
				"Your contact info"
			DESCRIPTION 
				"Enter the description for this MIB module."
			::= { optixProvisionSonet 5 }
		
	
--
-- Textual conventions
--
	
		C2Value ::= TEXTUAL-CONVENTION
			STATUS current
			DESCRIPTION 
				"Enter the description for the C2Value TEXTUAL-CONVENTION converted from type assignment."
			SYNTAX INTEGER
				{
				eqpd(1),
				vt-sts1(2),
				lock-vt(3),
				ds3(4),
				ds4na(18),
				atm(19),
				dqdb(20),
				fddi(21),
				hdlc-over-sonet(22),
				laps(24),
				gfp(27),
				pdi-1(225),
				pdi-2(226),
				pdi-3(227),
				pdi-4(228),
				pdi-5(229),
				pdi-6(230),
				pdi-7(231),
				pdi-8(232),
				pdi-9(233),
				pdi-10(234),
				pdi-11(235),
				pdi-12(236),
				pdi-13(237),
				pdi-14(238),
				pdi-15(239),
				pdi-16(240),
				pdi-17(241),
				pdi-18(242),
				pdi-19(243),
				pdi-20(244),
				pdi-21(245),
				pdi-22(246),
				pdi-23(247),
				pdi-24(248),
				pdi-29(249),
				pdi-26(250),
				pdi-27(251),
				pdi-28(252),
				uneq(253),
				o-181(254),
				invalid(65534)
				}
			
		LpbkType ::= TEXTUAL-CONVENTION
			STATUS current
			DESCRIPTION 
				"Enter the description for the LpbkType TEXTUAL-CONVENTION converted from type assignment."
			SYNTAX INTEGER
				{
				terminal(1),
				facility(2),
				crs(3),
				ds1feac(4),
				ds3feac(5),
				fac2ni(6),
				noloop(255)
				}
			
	
--
-- Node definitions
--
	
		-- 1.3.6.1.4.1.2011.2.25.4.20.5.1
		optixsonetStsPathTable OBJECT-TYPE
			SYNTAX SEQUENCE OF OptixsonetStsPathEntry
			MAX-ACCESS not-accessible
			STATUS current
			DESCRIPTION
				"This table describes the STS path management interface of Huawei SONET transmit platform
				"
			::= { optixsonetPathAttrib 1 }
		
		-- 1.3.6.1.4.1.2011.2.25.4.20.5.1.1
		optixsonetStsPathEntry OBJECT-TYPE
			SYNTAX OptixsonetStsPathEntry
			MAX-ACCESS not-accessible
			STATUS current
			DESCRIPTION
				"The STS path management entry
				"
			INDEX { stsPathLevel, stsPathBid, stsPathPid, stsPathStsId }
			::= { optixsonetStsPathTable 1 }
		
		OptixsonetStsPathEntry ::=
			SEQUENCE { 
				stsPathLevel
					INTEGER,
				stsPathBid
					Gauge32,
				stsPathPid
					Gauge32,
				stsPathStsId
					Gauge32,
				stsPathRevertiveMode
					INTEGER,
				stsPathRevertiveTime
					Gauge32,
				stsPathSwitchConditon
					INTEGER,
				stsPathDelayTime
					Gauge32,
				stsPathSFBER
					INTEGER,
				stsPathSDBER
					INTEGER,
				stsPathJ1TRCMODE
					INTEGER,
				stsPathTRCJ1
					OCTET STRING,
				stsPathEXPTRCJ1
					OCTET STRING,
				stsPathINCTRCJ1
					OCTET STRING,
				stsPathTRCC2
					C2Value,
				stsPathEXPTRCC2
					C2Value,
				stsPathINCTRCC2
					C2Value,
				stsPathSQL
					INTEGER,
				stsPathSwitchState
					INTEGER,
				stsPathPST
					OCTET STRING,
				stsPathSST
					OCTET STRING,
				stsPathLoopbackStatus
					LpbkType
			 }

		-- 1.3.6.1.4.1.2011.2.25.4.20.5.1.1.1
		stsPathLevel OBJECT-TYPE
			SYNTAX INTEGER
				{
				levelSTS1(9),
				levelSTS3c(10),
				levelSTS6c(11),
				levelSTS9c(12),
				levelSTS12c(13),
				levelSTS15c(14),
				levelSTS24c(15),
				levelSTS48c(16),
				levelSTS192c(17)
				}
			MAX-ACCESS read-only
			STATUS current
			DESCRIPTION
				"The path level that identifies the type of STS path."
			::= { optixsonetStsPathEntry 1 }
		
		-- 1.3.6.1.4.1.2011.2.25.4.20.5.1.1.2
		stsPathBid OBJECT-TYPE
			SYNTAX Gauge32
			MAX-ACCESS read-only
			STATUS current
			DESCRIPTION
				"Slot number.
				 	
				 	This will indicate what is the slot 
				 	of the object."
			::= { optixsonetStsPathEntry 2 }
		
		-- 1.3.6.1.4.1.2011.2.25.4.20.5.1.1.3
		stsPathPid OBJECT-TYPE
			SYNTAX Gauge32
			MAX-ACCESS read-only
			STATUS current
			DESCRIPTION
				"Port Number.
				 	
				 	This will indicate what is the Port 
				 	of the object.
				"
			::= { optixsonetStsPathEntry 3 }
		
		-- 1.3.6.1.4.1.2011.2.25.4.20.5.1.1.4
		stsPathStsId OBJECT-TYPE
			SYNTAX Gauge32
			MAX-ACCESS read-only
			STATUS current
			DESCRIPTION
				"Sts Number.
				 	
				 	This will indicate what is the Sts 
				 	of the object."
			::= { optixsonetStsPathEntry 4 }
		
		-- 1.3.6.1.4.1.2011.2.25.4.20.5.1.1.5
		stsPathRevertiveMode OBJECT-TYPE
			SYNTAX INTEGER
				{
				yes(1),
				no(2),
				null(254)
				}
			MAX-ACCESS read-write
			STATUS current
			DESCRIPTION
				"A revertive mode. It only applies to UPSR.Valid values are shown below.
				Value	Description
				Y	Revertive mode.
				N	No-revertive mode.
				"
			::= { optixsonetStsPathEntry 5 }
		
		-- 1.3.6.1.4.1.2011.2.25.4.20.5.1.1.6
		stsPathRevertiveTime OBJECT-TYPE
			SYNTAX Gauge32
			MAX-ACCESS read-write
			STATUS current
			DESCRIPTION
				"Revertive time. It only applies to UPSR.Valid values are shown below.
				Value	Description
				5 to 12	Revertive time of UPSR, ranging from 5 to 12 minutes, default is 5 minutes, in increments of 1 minute.
				
				"
			::= { optixsonetStsPathEntry 6 }
		
		-- 1.3.6.1.4.1.2011.2.25.4.20.5.1.1.7
		stsPathSwitchConditon OBJECT-TYPE
			SYNTAX INTEGER
				{
				no(1),
				yes(2),
				null(255)
				}
			MAX-ACCESS read-write
			STATUS current
			DESCRIPTION
				"Optional switching condition. Valid value is 
				Y (switch when existing PDI-P) or N (do not 
				switch when existing PDI-P).Default value is N."
			::= { optixsonetStsPathEntry 7 }
		
		-- 1.3.6.1.4.1.2011.2.25.4.20.5.1.1.8
		stsPathDelayTime OBJECT-TYPE
			SYNTAX Gauge32
			MAX-ACCESS read-write
			STATUS current
			DESCRIPTION
				"Delay time is hold-off time. It is an integer. 
				Valid value ranges from 0 to 255. Unit is 100 ms. 
				Default value is 0.Delay times are useful for 
				interworking of protection schemes. For example, 
				an optical port is configured for both UPSR and 
				BLSR simultaneously. After the delay time is set, 
				when a defect condition is declared on the port, 
				the UPSR switching is not initiated. When the timer expires, 
				the UPSR switching is initiated if the defect 
				condition is still present at this point. 
				When only one kind of protection UPSR is configured, 
				just use the default value.
				"
			::= { optixsonetStsPathEntry 8 }
		
		-- 1.3.6.1.4.1.2011.2.25.4.20.5.1.1.9
		stsPathSFBER OBJECT-TYPE
			SYNTAX INTEGER
				{
				sf1E-3(3),
				sf1E-4(4),
				sf1E-5(5)
				}
			MAX-ACCESS read-write
			STATUS current
			DESCRIPTION
				"Threshold of path (B3) SFBER on a facility. Valid values are shown
				below.
				Value	Description
				1E-3 to 1E-5	SFBER ranges from 1E-3 to 1E-5, Default threshold is 1E-4.
				1E-5 to 1E-9	SDBER ranges from 1E-5 to 1E-9, Default threshold is 1E-6.
				"
			::= { optixsonetStsPathEntry 9 }
		
		-- 1.3.6.1.4.1.2011.2.25.4.20.5.1.1.10
		stsPathSDBER OBJECT-TYPE
			SYNTAX INTEGER
				{
				sd1E-5(5),
				sd1E-6(6),
				sd1E-7(7),
				sd1E-8(8),
				sd1E-9(9)
				}
			MAX-ACCESS read-write
			STATUS current
			DESCRIPTION
				"Threshold of path (B3) SDBER on a facility. Valid values are shown
				below.
				Value	Description
				1E-3 to 1E-5	SFBER ranges from 1E-3 to 1E-5, Default threshold is 1E-4.
				1E-5 to 1E-9	SDBER ranges from 1E-5 to 1E-9, Default threshold is 1E-6."
			::= { optixsonetStsPathEntry 10 }
		
		-- 1.3.6.1.4.1.2011.2.25.4.20.5.1.1.11
		stsPathJ1TRCMODE OBJECT-TYPE
			SYNTAX INTEGER
				{
				manual(1),
				auto(2),
				off(3),
				invalid(254)
				}
			MAX-ACCESS read-write
			STATUS current
			DESCRIPTION
				"Path trace mode. Valid values are shown below.
				Value	Description
				MANUAL 	Performs the comparison of the received string with the user-entered expected string.
				AUTO 	Performs the comparison of the present received string with an expected string set to a previously received string. If there is a mismatch, TIM-P alarm is raised.
				OFF	Don't perform the comparison. Default value is OFF.
				"
			::= { optixsonetStsPathEntry 11 }
		
		-- 1.3.6.1.4.1.2011.2.25.4.20.5.1.1.12
		stsPathTRCJ1 OBJECT-TYPE
			SYNTAX OCTET STRING (SIZE (0..62))
			MAX-ACCESS read-write
			STATUS current
			DESCRIPTION
				"The path trace message contents (J1) to be transmitted."
			::= { optixsonetStsPathEntry 12 }
		
		-- 1.3.6.1.4.1.2011.2.25.4.20.5.1.1.13
		stsPathEXPTRCJ1 OBJECT-TYPE
			SYNTAX OCTET STRING (SIZE (0..62))
			MAX-ACCESS read-write
			STATUS current
			DESCRIPTION
				"The expected path traces message (J1) contents."
			::= { optixsonetStsPathEntry 13 }
		
		-- 1.3.6.1.4.1.2011.2.25.4.20.5.1.1.14
		stsPathINCTRCJ1 OBJECT-TYPE
			SYNTAX OCTET STRING (SIZE (0..62))
			MAX-ACCESS read-only
			STATUS current
			DESCRIPTION
				"The path trace message received.
				It can not include escape characters except \ and .
				"
			::= { optixsonetStsPathEntry 14 }
		
		-- 1.3.6.1.4.1.2011.2.25.4.20.5.1.1.15
		stsPathTRCC2 OBJECT-TYPE
			SYNTAX C2Value
			MAX-ACCESS read-write
			STATUS current
			DESCRIPTION
				"The C2 byte hex code to be transmitted. Valid values are shown below.
				Value	Description
				UNEQ	0x00 The C2 content to be transmitted is unloaded.
				EQPD (default)	0x01 The C2 content to be transmitted is loaded with normal SPE.
				VT-STS1	0x02 The C2 content to be transmitted: STS-1 SPE of VT structure. Default value for C2 in DS1 unit
				LOCK-VT	0x03 The C2 content to be transmitted: lock VT mode.
				DS3	0x04 The C2 content to be transmitted: DS3 asynchronous mapping.
				Default value for C2 in DS3 port.
				DS4NA	0x12 The C2 content to be transmitted: DS4NA asynchronous mapping.
				ATM	0x13 The C2 content to be transmitted: ATM mapping.
				DQDB	0x14 The C2 content to be transmitted: DQDB mapping.
				FDDI	0x15 The C2 content to be transmitted: FDDI asynchronous mapping.
				HDLC-OVER-SONET	0x16 The C2 content to be transmitted: HDLC-OVER-SONET mapping. 
				LAPS	0x18
				GFP	0x1b
				O.181	0xfe The C2 content to be transmitted: O.181 testing signal.
				Other byte Hex code	Non standard C2.
				"
			::= { optixsonetStsPathEntry 15 }
		
		-- 1.3.6.1.4.1.2011.2.25.4.20.5.1.1.16
		stsPathEXPTRCC2 OBJECT-TYPE
			SYNTAX C2Value
			MAX-ACCESS read-write
			STATUS current
			DESCRIPTION
				"The expected C2 byte hex code. Valid values are shown below.
				Value	Description
				UNEQ	0x00 The C2 content to be transmitted is unloaded.
				EQPD (default)	0x01 The C2 content to be transmitted is loaded with normal SPE.
				VT-STS1	0x02 The C2 content to be transmitted: STS-1 SPE of VT structure. Default value for C2 in DS1 unit
				LOCK-VT	0x03 The C2 content to be transmitted: lock VT mode.
				DS3	0x04 The C2 content to be transmitted: DS3 asynchronous mapping.
				Default value for C2 in DS3 port.
				DS4NA	0x12 The C2 content to be transmitted: DS4NA asynchronous mapping.
				ATM	0x13 The C2 content to be transmitted: ATM mapping.
				DQDB	0x14 The C2 content to be transmitted: DQDB mapping.
				FDDI	0x15 The C2 content to be transmitted: FDDI asynchronous mapping.
				HDLC-OVER-SONET	0x16 The C2 content to be transmitted: HDLC-OVER-SONET mapping. 
				LAPS	0x18
				GFP	0x1b
				O.181	0xfe The C2 content to be transmitted: O.181 testing signal.
				Other byte Hex code	Non standard C2.
				"
			::= { optixsonetStsPathEntry 16 }
		
		-- 1.3.6.1.4.1.2011.2.25.4.20.5.1.1.17
		stsPathINCTRCC2 OBJECT-TYPE
			SYNTAX C2Value
			MAX-ACCESS read-only
			STATUS current
			DESCRIPTION
				"The C2 byte hex code received. Valid values are shown below.
				Value	Description
				UNEQ	0x00 The C2 content to be transmitted is unloaded.
				EQPD (default)	0x01 The C2 content to be transmitted is loaded with normal SPE.
				VT-STS1	0x02 The C2 content to be transmitted: STS-1 SPE of VT structure. Default value for C2 in DS1 unit
				LOCK-VT	0x03 The C2 content to be transmitted: lock VT mode.
				DS3	0x04 The C2 content to be transmitted: DS3 asynchronous mapping.
				Default value for C2 in DS3 port.
				DS4NA	0x12 The C2 content to be transmitted: DS4NA asynchronous mapping.
				ATM	0x13 The C2 content to be transmitted: ATM mapping.
				DQDB	0x14 The C2 content to be transmitted: DQDB mapping.
				FDDI	0x15 The C2 content to be transmitted: FDDI asynchronous mapping.
				HDLC-OVER-SONET	0x16 The C2 content to be transmitted: HDLC-OVER-SONET mapping. 
				LAPS	0x18
				GFP	0x1b
				O.181	0xfe The C2 content to be transmitted: O.181 testing signal.
				Other byte Hex code	Non standard C2.
				"
			::= { optixsonetStsPathEntry 17 }
		
		-- 1.3.6.1.4.1.2011.2.25.4.20.5.1.1.18
		stsPathSQL OBJECT-TYPE
			SYNTAX INTEGER
				{
				yes(1),
				no(2),
				invalid(254)
				}
			MAX-ACCESS read-only
			STATUS current
			DESCRIPTION
				"The flag of squelch. This parameter only supplies for BLSR. Valid value is Y or N."
			::= { optixsonetStsPathEntry 18 }
		
		-- 1.3.6.1.4.1.2011.2.25.4.20.5.1.1.19
		stsPathSwitchState OBJECT-TYPE
			SYNTAX INTEGER
				{
				wtr(1),
				autosw(2),
				manPtoW(3),
				manWtoP(4),
				frcPtoW(5),
				frcWtoP(6),
				lockout(7),
				clear(8),
				idle(253),
				invalid(254)
				}
			MAX-ACCESS read-only
			STATUS current
			DESCRIPTION
				"It is only valid when the port is in the UPSR protection group. Valid values are shown below.
				Value	Description
				IDLE	Idle
				WTR	Wait to restore
				AUTOSW	Automatic switch
				MANPtoW	Manually switch to the working unit
				MANWtoP	Manually switch to the protecting unit
				FRCPtoW	Forced switch to the working unit
				FRCWtoP	Forced switch to the protecting unit
				LOCKOUT	Lock to the working unit
				CLEAR	Clear
				INVALID	Invalid
				"
			::= { optixsonetStsPathEntry 19 }
		
		-- 1.3.6.1.4.1.2011.2.25.4.20.5.1.1.20
		stsPathPST OBJECT-TYPE
			SYNTAX OCTET STRING (SIZE (0..16))
			MAX-ACCESS read-write
			STATUS current
			DESCRIPTION
				"<PST> means the primary state of the entity. Valid values are IS-NR, OOS-AU, OOS-MA and OOS-AUMA."
			::= { optixsonetStsPathEntry 20 }
		
		-- 1.3.6.1.4.1.2011.2.25.4.20.5.1.1.21
		stsPathSST OBJECT-TYPE
			SYNTAX OCTET STRING (SIZE (0..32))
			MAX-ACCESS read-write
			STATUS current
			DESCRIPTION
				"<SST> means the secondary state of the entity. Valid values are MT, LPBK, SGEO and FAF,"
			::= { optixsonetStsPathEntry 21 }
		
		-- 1.3.6.1.4.1.2011.2.25.4.20.5.1.1.22
		stsPathLoopbackStatus OBJECT-TYPE
			SYNTAX LpbkType
			MAX-ACCESS read-write
			STATUS current
			DESCRIPTION
				"This variable represents the current state of the
				loopback on the sts path. "
			::= { optixsonetStsPathEntry 22 }
		
		-- 1.3.6.1.4.1.2011.2.25.4.20.5.2
		optixsonetPathAttribConformance OBJECT IDENTIFIER ::= { optixsonetPathAttrib 2 }
		
		-- 1.3.6.1.4.1.2011.2.25.4.20.5.2.1
		optixsonetPathAttribGroups OBJECT IDENTIFIER ::= { optixsonetPathAttribConformance 1 }
		
		-- 1.3.6.1.4.1.2011.2.25.4.20.5.2.1.1
		currentObjectGroup OBJECT-GROUP
			OBJECTS { stsPathLevel, stsPathBid, stsPathPid, stsPathStsId, stsPathRevertiveMode, 
				stsPathRevertiveTime, stsPathSwitchConditon, stsPathDelayTime, stsPathSFBER, stsPathSDBER, 
				stsPathJ1TRCMODE, stsPathTRCJ1, stsPathEXPTRCJ1, stsPathINCTRCJ1, stsPathTRCC2, 
				stsPathEXPTRCC2, stsPathINCTRCC2, stsPathSQL, stsPathSwitchState, stsPathPST, 
				stsPathSST, stsPathLoopbackStatus }
			STATUS current
			DESCRIPTION 
				"Enter the description of the created OBJECT-GROUP."
			::= { optixsonetPathAttribGroups 1 }
		
		-- 1.3.6.1.4.1.2011.2.25.4.20.5.2.2
		optixsonetPathAttribCompliances OBJECT IDENTIFIER ::= { optixsonetPathAttribConformance 2 }
		
		-- 1.3.6.1.4.1.2011.2.25.4.20.5.2.2.1
		basicCompliance MODULE-COMPLIANCE
			STATUS current
			DESCRIPTION 
				"Enter the description of the created MODULE-COMPLIANCE."
			MODULE -- this module
				MANDATORY-GROUPS { currentObjectGroup }
			::= { optixsonetPathAttribCompliances 1 }
		
	
	END

--
-- OPTIX-SONET-PATH-MIB-V2.mib
--
