--
-- OPTIX-SONET-LPBK-MIB-V2.mib
-- MIB generated by MG-SOFT Visual MIB Builder Version 3.0 Build 253
-- Friday, February 24, 2006 at 14:19:57
--

	OPTIX-SONET-LPBK-MIB-V2 DEFINITIONS ::= BEGIN
 
		IMPORTS
			optixCommonSonet			
				FROM OPTIX-OID-MIB			
			MOD2Type			
				FROM OPTIX-SONET-TC-MIB			
			OBJECT-GROUP, MODULE-COMPLIANCE			
				FROM SNMPv2-CONF			
			Gauge32, OBJECT-TYPE, MODULE-IDENTITY			
				FROM SNMPv2-SMI			
			TEXTUAL-CONVENTION			
				FROM SNMPv2-TC;
	
	
		optixSonetMaintenance MODULE-IDENTITY 
			LAST-UPDATED "200602231756Z"		-- February 23, 2006 at 17:56 GMT
			ORGANIZATION 
				"Huawei Technologies Co.,Ltd."
			CONTACT-INFO 
				"R&D Building
				Huawei Technologies Co., Ltd.
				Bantian, Longgang District 
				Shenzhen, P. R. China
				http://www.huawei.com
				Zip:518129
				E-mail:support@huawei.com
				"
			DESCRIPTION 
				"This module describes the Loopback interface of Huawei SONET transmit platform
				"
			::= { optixCommonSonet 50 }
		
	
--
-- Textual conventions
--
	
		LpbkType ::= TEXTUAL-CONVENTION
			STATUS current
			DESCRIPTION 
				"Enter the description for the LpbkType TEXTUAL-CONVENTION converted from type assignment."
			SYNTAX INTEGER
				{
				noloop(255),
				terminal(1),
				facility(2),
				crs(3),
				ds1feac(4),
				ds3feac(5),
				fac2ni(6)
				}
			
	
--
-- Node definitions
--
	
		-- 1.3.6.1.4.1.2011.2.25.3.20.50.10
		optixSonetLoopback OBJECT IDENTIFIER ::= { optixSonetMaintenance 10 }
		
		-- 1.3.6.1.4.1.2011.2.25.3.20.50.10.10
		lpbkStateTable OBJECT-TYPE
			SYNTAX SEQUENCE OF LpbkStateEntry
			MAX-ACCESS not-accessible
			STATUS current
			DESCRIPTION
				"Loopback state table
				"
			::= { optixSonetLoopback 10 }
		
		-- 1.3.6.1.4.1.2011.2.25.3.20.50.10.10.1
		lpbkStateEntry OBJECT-TYPE
			SYNTAX LpbkStateEntry
			MAX-ACCESS not-accessible
			STATUS current
			DESCRIPTION
				"Loopback state entry
				"
			INDEX { lpbkStateMOD2, lpbkStateSlot, lpbkStatePort, lpbkStatePath, lpbkStateVT
				 }
			::= { lpbkStateTable 1 }
		
		LpbkStateEntry ::=
			SEQUENCE { 
				lpbkStateMOD2
					MOD2Type,
				lpbkStateSlot
					Gauge32,
				lpbkStatePort
					Gauge32,
				lpbkStatePath
					Gauge32,
				lpbkStateVT
					Gauge32,
				lpbkStateLpbkType
					LpbkType,
				lpbkStateTimeout
					Gauge32
			 }

		-- 1.3.6.1.4.1.2011.2.25.3.20.50.10.10.1.1
		lpbkStateMOD2 OBJECT-TYPE
			SYNTAX MOD2Type
			MAX-ACCESS read-only
			STATUS current
			DESCRIPTION
				"The modifier that identifies the type of the facility"
			::= { lpbkStateEntry 1 }
		
		-- 1.3.6.1.4.1.2011.2.25.3.20.50.10.10.1.2
		lpbkStateSlot OBJECT-TYPE
			SYNTAX Gauge32
			MAX-ACCESS read-only
			STATUS current
			DESCRIPTION
				"Slot number.
				            
				            This will indicate what is the slot 
				 			of the object."
			::= { lpbkStateEntry 2 }
		
		-- 1.3.6.1.4.1.2011.2.25.3.20.50.10.10.1.3
		lpbkStatePort OBJECT-TYPE
			SYNTAX Gauge32
			MAX-ACCESS read-only
			STATUS current
			DESCRIPTION
				"Port Number.
				            
				            This will indicate what is the Port 
				 			of the object."
			::= { lpbkStateEntry 3 }
		
		-- 1.3.6.1.4.1.2011.2.25.3.20.50.10.10.1.4
		lpbkStatePath OBJECT-TYPE
			SYNTAX Gauge32
			MAX-ACCESS read-only
			STATUS current
			DESCRIPTION
				"Path number.
				            
				            This will indicate what is the Path 
				 			of the object."
			::= { lpbkStateEntry 4 }
		
		-- 1.3.6.1.4.1.2011.2.25.3.20.50.10.10.1.5
		lpbkStateVT OBJECT-TYPE
			SYNTAX Gauge32
			MAX-ACCESS read-only
			STATUS current
			DESCRIPTION
				"VT path number.
				            
				            This will indicate what is the VT path 
				 			of the object."
			::= { lpbkStateEntry 5 }
		
		-- 1.3.6.1.4.1.2011.2.25.3.20.50.10.10.1.6
		lpbkStateLpbkType OBJECT-TYPE
			SYNTAX LpbkType
			MAX-ACCESS read-only
			STATUS current
			DESCRIPTION
				"The loopback type of the facility
				"
			::= { lpbkStateEntry 6 }
		
		-- 1.3.6.1.4.1.2011.2.25.3.20.50.10.10.1.7
		lpbkStateTimeout OBJECT-TYPE
			SYNTAX Gauge32
			MAX-ACCESS read-only
			STATUS current
			DESCRIPTION
				"The remnant time that loop-back will be released.
				"
			::= { lpbkStateEntry 7 }
		
		-- 1.3.6.1.4.1.2011.2.25.3.20.50.10.20
		lpbkFlagTable OBJECT-TYPE
			SYNTAX SEQUENCE OF LpbkFlagEntry
			MAX-ACCESS not-accessible
			STATUS current
			DESCRIPTION
				"Loopback Enable table"
			::= { optixSonetLoopback 20 }
		
		-- 1.3.6.1.4.1.2011.2.25.3.20.50.10.20.1
		lpbkFlagEntry OBJECT-TYPE
			SYNTAX LpbkFlagEntry
			MAX-ACCESS not-accessible
			STATUS current
			DESCRIPTION
				"Loopback Enable entry"
			INDEX { lpbkFlagMOD2, lpbkFlagSlot, lpbkFlagPort, lpbkFlagPath, lpbkFlagVT
				 }
			::= { lpbkFlagTable 1 }
		
		LpbkFlagEntry ::=
			SEQUENCE { 
				lpbkFlagMOD2
					MOD2Type,
				lpbkFlagSlot
					Gauge32,
				lpbkFlagPort
					Gauge32,
				lpbkFlagPath
					Gauge32,
				lpbkFlagVT
					Gauge32,
				lpbkFlagLpbkType
					LpbkType,
				lpbkFlagEnFlag
					INTEGER,
				lpbkFlagTimeout
					Gauge32
			 }

		-- 1.3.6.1.4.1.2011.2.25.3.20.50.10.20.1.1
		lpbkFlagMOD2 OBJECT-TYPE
			SYNTAX MOD2Type
			MAX-ACCESS read-only
			STATUS current
			DESCRIPTION
				"The modifier that identifies the type of the facility"
			::= { lpbkFlagEntry 1 }
		
		-- 1.3.6.1.4.1.2011.2.25.3.20.50.10.20.1.2
		lpbkFlagSlot OBJECT-TYPE
			SYNTAX Gauge32
			MAX-ACCESS read-only
			STATUS current
			DESCRIPTION
				"Slot number.
				            
				            This will indicate what is the slot 
				 			of the object."
			::= { lpbkFlagEntry 2 }
		
		-- 1.3.6.1.4.1.2011.2.25.3.20.50.10.20.1.3
		lpbkFlagPort OBJECT-TYPE
			SYNTAX Gauge32
			MAX-ACCESS read-only
			STATUS current
			DESCRIPTION
				"Port Number.
				            
				            This will indicate what is the Port 
				 			of the object."
			::= { lpbkFlagEntry 3 }
		
		-- 1.3.6.1.4.1.2011.2.25.3.20.50.10.20.1.4
		lpbkFlagPath OBJECT-TYPE
			SYNTAX Gauge32
			MAX-ACCESS read-only
			STATUS current
			DESCRIPTION
				"Path number.
				            
				            This will indicate what is the Path 
				 			of the object."
			::= { lpbkFlagEntry 4 }
		
		-- 1.3.6.1.4.1.2011.2.25.3.20.50.10.20.1.5
		lpbkFlagVT OBJECT-TYPE
			SYNTAX Gauge32
			MAX-ACCESS read-only
			STATUS current
			DESCRIPTION
				"VT path number.
				            
				            This will indicate what is the VT path 
				 			of the object."
			::= { lpbkFlagEntry 5 }
		
		-- 1.3.6.1.4.1.2011.2.25.3.20.50.10.20.1.6
		lpbkFlagLpbkType OBJECT-TYPE
			SYNTAX LpbkType
			MAX-ACCESS read-only
			STATUS current
			DESCRIPTION
				"The loopback type of the facility
				"
			::= { lpbkFlagEntry 6 }
		
		-- 1.3.6.1.4.1.2011.2.25.3.20.50.10.20.1.7
		lpbkFlagEnFlag OBJECT-TYPE
			SYNTAX INTEGER
				{
				disable(0),
				enable(1)
				}
			MAX-ACCESS read-only
			STATUS current
			DESCRIPTION
				"T1 or T3 remote loop-back enable flag
				"
			::= { lpbkFlagEntry 7 }
		
		-- 1.3.6.1.4.1.2011.2.25.3.20.50.10.20.1.8
		lpbkFlagTimeout OBJECT-TYPE
			SYNTAX Gauge32
			MAX-ACCESS read-only
			STATUS current
			DESCRIPTION
				"The automatic release time of loopback."
			::= { lpbkFlagEntry 8 }
		
		-- 1.3.6.1.4.1.2011.2.25.3.20.50.11
		optixSonetMaintenanceConformance OBJECT IDENTIFIER ::= { optixSonetMaintenance 11 }
		
		-- 1.3.6.1.4.1.2011.2.25.3.20.50.11.1
		optixSonetMaintenanceGroups OBJECT IDENTIFIER ::= { optixSonetMaintenanceConformance 1 }
		
		-- 1.3.6.1.4.1.2011.2.25.3.20.50.11.1.1
		currentObjectGroup OBJECT-GROUP
			OBJECTS { lpbkStateMOD2, lpbkStateSlot, lpbkStatePort, lpbkStatePath, lpbkStateVT, 
				lpbkStateLpbkType, lpbkStateTimeout, lpbkFlagMOD2, lpbkFlagSlot, lpbkFlagPort, 
				lpbkFlagPath, lpbkFlagVT, lpbkFlagLpbkType, lpbkFlagEnFlag, lpbkFlagTimeout
				 }
			STATUS current
			DESCRIPTION 
				"Enter the description of the created OBJECT-GROUP."
			::= { optixSonetMaintenanceGroups 1 }
		
		-- 1.3.6.1.4.1.2011.2.25.3.20.50.11.2
		optixSonetMaintenanceCompliances OBJECT IDENTIFIER ::= { optixSonetMaintenanceConformance 2 }
		
		-- 1.3.6.1.4.1.2011.2.25.3.20.50.11.2.1
		basicCompliance MODULE-COMPLIANCE
			STATUS current
			DESCRIPTION 
				"Enter the description of the created MODULE-COMPLIANCE."
			MODULE -- this module
				MANDATORY-GROUPS { currentObjectGroup }
			::= { optixSonetMaintenanceCompliances 1 }
		
	
	END

--
-- OPTIX-SONET-LPBK-MIB-V2.mib
--
