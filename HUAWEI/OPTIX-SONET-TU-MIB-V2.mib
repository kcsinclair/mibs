--
-- OPTIX-SONET-TU-MIB-V2.mib
-- MIB generated by MG-SOFT Visual MIB Builder Version 3.0 Build 253
-- Wednesday, July 26, 2006 at 17:22:43
--

	OPTIX-SONET-TU-MIB-V2 DEFINITIONS ::= BEGIN
 
		IMPORTS
			optixProvisionSonet			
				FROM OPTIX-OID-MIB			
			OBJECT-GROUP, MODULE-COMPLIANCE			
				FROM SNMPv2-CONF			
			Gauge32, OBJECT-TYPE, MODULE-IDENTITY			
				FROM SNMPv2-SMI			
			TEXTUAL-CONVENTION			
				FROM SNMPv2-TC;
	
	
		optixsonetFacilityMgt MODULE-IDENTITY 
			LAST-UPDATED "200605232008Z"		-- May 23, 2006 at 20:08 GMT
			ORGANIZATION 
				"Your organization"
			CONTACT-INFO 
				"Your contact info"
			DESCRIPTION 
				"Enter the description for this MIB module."
			::= { optixProvisionSonet 2 }
		
	
--
-- Textual conventions
--
	
		LpbkType ::= TEXTUAL-CONVENTION
			STATUS current
			DESCRIPTION 
				"Enter the description for the LpbkType TEXTUAL-CONVENTION converted from type assignment."
			SYNTAX INTEGER
				{
				terminal(1),
				facility(2),
				crs(3),
				ds1feac(4),
				ds3feac(5),
				fac2ni(6),
				noloop(255)
				}
			
		IntfType ::= TEXTUAL-CONVENTION
			STATUS current
			DESCRIPTION 
				"Enter the description for the IntfType TEXTUAL-CONVENTION converted from type assignment."
			SYNTAX INTEGER
				{
				ds1-asyn-vt1(1),
				ds3-asyn-sts1(10),
				ec(12),
				ds3-tmux-ds1(13),
				ds3-srv-ds1(17),
				uas(65),
				mix(100),
				invalid(254)
				}
			
	
--
-- Node definitions
--
	
		-- 1.3.6.1.4.1.2011.2.25.4.20.2.1
		ds3PortAttribTable OBJECT-TYPE
			SYNTAX SEQUENCE OF Ds3PortAttribEntry
			MAX-ACCESS not-accessible
			STATUS current
			DESCRIPTION
				"The DS3 facilities configuration Table"
			::= { optixsonetFacilityMgt 1 }
		
		-- 1.3.6.1.4.1.2011.2.25.4.20.2.1.1
		ds3PortAttribEntry OBJECT-TYPE
			SYNTAX Ds3PortAttribEntry
			MAX-ACCESS not-accessible
			STATUS current
			DESCRIPTION
				"The DS3 facilities configuration entry"
			INDEX { ds3PortIndexSlotId, ds3PortIndexPortId }
			::= { ds3PortAttribTable 1 }
		
		Ds3PortAttribEntry ::=
			SEQUENCE { 
				ds3PortIndexSlotId
					Gauge32,
				ds3PortIndexPortId
					Gauge32,
				ds3PortAttribReq
					INTEGER,
				ds3PortAttribLbo
					INTEGER,
				ds3PortAttribLineCde
					INTEGER,
				ds3PortAttribFmt
					INTEGER,
				ds3PortAttribTACC
					INTEGER,
				ds3PortAttribLof2ais
					INTEGER,
				ds3PortAttribSvtimer
					OCTET STRING,
				ds3PortAttribPST
					OCTET STRING,
				ds3PortAttribSST
					OCTET STRING,
				ds3LoopbackStatus
					LpbkType,
				ds3LoopbackTimeout
					Gauge32,
				ds3RemoteALWFELPBK
					INTEGER
			 }

		-- 1.3.6.1.4.1.2011.2.25.4.20.2.1.1.1
		ds3PortIndexSlotId OBJECT-TYPE
			SYNTAX Gauge32
			MAX-ACCESS read-only
			STATUS current
			DESCRIPTION
				"Slot number.
				 	
				 	This will indicate what is the slot 
				 	of the object.
				"
			::= { ds3PortAttribEntry 1 }
		
		-- 1.3.6.1.4.1.2011.2.25.4.20.2.1.1.2
		ds3PortIndexPortId OBJECT-TYPE
			SYNTAX Gauge32
			MAX-ACCESS read-only
			STATUS current
			DESCRIPTION
				"Port Number.
				 	
				 	This will indicate what is the Port 
				 	of the object.
				"
			::= { ds3PortAttribEntry 2 }
		
		-- 1.3.6.1.4.1.2011.2.25.4.20.2.1.1.3
		ds3PortAttribReq OBJECT-TYPE
			SYNTAX INTEGER
				{
				high(1),
				low(2),
				invalid(254)
				}
			MAX-ACCESS read-write
			STATUS current
			DESCRIPTION
				"High or low receive equalizer."
			::= { ds3PortAttribEntry 3 }
		
		-- 1.3.6.1.4.1.2011.2.25.4.20.2.1.1.4
		ds3PortAttribLbo OBJECT-TYPE
			SYNTAX INTEGER (1..2)
			MAX-ACCESS read-write
			STATUS current
			DESCRIPTION
				"Line build out.
				Line build out (DS3 port) values 
				Value	Description
				1	Cable length range from 0 to 225 feet.
				2	Cable length range from 226 to 450 feet.
				"
			::= { ds3PortAttribEntry 4 }
		
		-- 1.3.6.1.4.1.2011.2.25.4.20.2.1.1.5
		ds3PortAttribLineCde OBJECT-TYPE
			SYNTAX INTEGER
				{
				b3zs(3),
				invalid(254)
				}
			MAX-ACCESS read-only
			STATUS current
			DESCRIPTION
				"DS3 line code. Valid value is B3ZS."
			::= { ds3PortAttribEntry 5 }
		
		-- 1.3.6.1.4.1.2011.2.25.4.20.2.1.1.6
		ds3PortAttribFmt OBJECT-TYPE
			SYNTAX INTEGER
				{
				cbit(3),
				m23(4),
				unframed(255)
				}
			MAX-ACCESS read-write
			STATUS current
			DESCRIPTION
				"Frame format. Valid values are CBIT, M23 or UNFRAMED. 
				For PDM3 unit, if the port type is DS3_ASYN_STS1, 
				then <FMT> can be CBIT, M23 or UNFRAMED. If the port 
				type is DS3_TMUX_DS1 or DS3_SRV_DS1, then the <FMT> only can be CBIT or M23."
			::= { ds3PortAttribEntry 6 }
		
		-- 1.3.6.1.4.1.2011.2.25.4.20.2.1.1.7
		ds3PortAttribTACC OBJECT-TYPE
			SYNTAX INTEGER (0..999)
			MAX-ACCESS read-write
			STATUS current
			DESCRIPTION
				"Defines the DS3 port as a test access port with a selected unique TAP number."
			::= { ds3PortAttribEntry 7 }
		
		-- 1.3.6.1.4.1.2011.2.25.4.20.2.1.1.8
		ds3PortAttribLof2ais OBJECT-TYPE
			SYNTAX INTEGER
				{
				yes(1),
				no(2),
				invalid(254)
				}
			MAX-ACCESS read-write
			STATUS current
			DESCRIPTION
				"The parameter is provisioned to determine whether or 
				not to generate DS3 AIS for the DS3 LOF. The Valid 
				value of this parameter is 'no' and 'yes'.
				PQT3/PQT3A/PQT3P/PQT3B units support this parameter.
				"
			::= { ds3PortAttribEntry 8 }
		
		-- 1.3.6.1.4.1.2011.2.25.4.20.2.1.1.9
		ds3PortAttribSvtimer OBJECT-TYPE
			SYNTAX OCTET STRING (SIZE (0..6))
			MAX-ACCESS read-write
			STATUS current
			DESCRIPTION
				"Signal validation timer in minutes. Valid values are shown below.
				Value	     Description
				From 00-03   Signal validation timer in minutes. Only valid if auto in-service feature is supported. <SVTIMER> is a string, and format is: HH-MM.
				to 48-00     HH - Hour, it is an integer ranging from 0 to 48;
				             MM - Minute, it is an integer ranging from 0 to 59. The longest time is 48 hours. Default is 00-03 (3 minutes).
					
				"
			::= { ds3PortAttribEntry 9 }
		
		-- 1.3.6.1.4.1.2011.2.25.4.20.2.1.1.10
		ds3PortAttribPST OBJECT-TYPE
			SYNTAX OCTET STRING (SIZE (0..16))
			MAX-ACCESS read-write
			STATUS current
			DESCRIPTION
				"The primary state of the entity.
				Administrative State (PST) Definition
				IS  Puts the entity in service.
				OOS Puts the entity out of service.
				"
			::= { ds3PortAttribEntry 10 }
		
		-- 1.3.6.1.4.1.2011.2.25.4.20.2.1.1.11
		ds3PortAttribSST OBJECT-TYPE
			SYNTAX OCTET STRING (SIZE (0..32))
			MAX-ACCESS read-write
			STATUS current
			DESCRIPTION
				"The secondary state of the entity.
				Administrative State (PST) Definition.
				AINS Puts the entity in automatic in-service.
				MT   Removes the entity from service for maintenance."
			::= { ds3PortAttribEntry 11 }
		
		-- 1.3.6.1.4.1.2011.2.25.4.20.2.1.1.12
		ds3LoopbackStatus OBJECT-TYPE
			SYNTAX LpbkType
			MAX-ACCESS read-write
			STATUS current
			DESCRIPTION
				"This variable represents the current state of the
				loopback on the DS3 interface.  It contains
				information about loopbacks established by a
				manager and remotely from the far end.
				"
			::= { ds3PortAttribEntry 12 }
		
		-- 1.3.6.1.4.1.2011.2.25.4.20.2.1.1.13
		ds3LoopbackTimeout OBJECT-TYPE
			SYNTAX Gauge32
			MAX-ACCESS read-only
			STATUS current
			DESCRIPTION
				"The remnant time that loop-back will be released.
				"
			::= { ds3PortAttribEntry 13 }
		
		-- 1.3.6.1.4.1.2011.2.25.4.20.2.1.1.14
		ds3RemoteALWFELPBK OBJECT-TYPE
			SYNTAX INTEGER
				{
				enable(1),
				disable(2),
				invalid(254)
				}
			MAX-ACCESS read-write
			STATUS current
			DESCRIPTION
				"(Optional) Far-end loopback allowance attribute of the port. If it is
				enable, the automatic far-end loopbacks are allowed. It is either enable or
				disable. The system default is enable. The parameter type is ENABLE_DISABLE, 
				which disables or enables an attribute.Automatic application of loopbacks 
				originating from the far end can be initiated on the T3 ports of
				a PDM3 card.
				"
			::= { ds3PortAttribEntry 14 }
		
		-- 1.3.6.1.4.1.2011.2.25.4.20.2.2
		ds1PortAttribTable OBJECT-TYPE
			SYNTAX SEQUENCE OF Ds1PortAttribEntry
			MAX-ACCESS not-accessible
			STATUS current
			DESCRIPTION
				"The DS1 facilities configuration Table"
			::= { optixsonetFacilityMgt 2 }
		
		-- 1.3.6.1.4.1.2011.2.25.4.20.2.2.1
		ds1PortAttribEntry OBJECT-TYPE
			SYNTAX Ds1PortAttribEntry
			MAX-ACCESS not-accessible
			STATUS current
			DESCRIPTION
				"The DS1 facilities configuration entry"
			INDEX { ds1PortIndexSlotId, ds1PortIndexPortId, ds1PortIndexPath }
			::= { ds1PortAttribTable 1 }
		
		Ds1PortAttribEntry ::=
			SEQUENCE { 
				ds1PortIndexSlotId
					Gauge32,
				ds1PortIndexPortId
					Gauge32,
				ds1PortIndexPath
					Gauge32,
				ds1PortAttribLbo
					INTEGER,
				ds1PortAttribLineCde
					INTEGER,
				ds1PortAttribFmt
					INTEGER,
				ds1PortAttribTACC
					INTEGER,
				ds1PortAttribLof2ais
					INTEGER,
				ds1PortAttribSvtimer
					OCTET STRING,
				ds1PortAttribPST
					OCTET STRING,
				ds1PortAttribSST
					OCTET STRING,
				ds1LoopbackStatus
					LpbkType,
				ds1LoopbackTimeout
					Gauge32,
				ds1RemoteALWFELPBK
					INTEGER,
				ds1PortLpbkAutomaticTime
					Gauge32
			 }

		-- 1.3.6.1.4.1.2011.2.25.4.20.2.2.1.1
		ds1PortIndexSlotId OBJECT-TYPE
			SYNTAX Gauge32
			MAX-ACCESS read-only
			STATUS current
			DESCRIPTION
				"Slot number.
				 	
				 	This will indicate what is the slot 
				 	of the object.
				"
			::= { ds1PortAttribEntry 1 }
		
		-- 1.3.6.1.4.1.2011.2.25.4.20.2.2.1.2
		ds1PortIndexPortId OBJECT-TYPE
			SYNTAX Gauge32
			MAX-ACCESS read-only
			STATUS current
			DESCRIPTION
				"Port Number.
				 	
				 	This will indicate what is the Port of the object.For the Transmux unit this is the DS3 port number.And for other Ds1 units, it's the Ds1 port Number. 
				"
			::= { ds1PortAttribEntry 2 }
		
		-- 1.3.6.1.4.1.2011.2.25.4.20.2.2.1.3
		ds1PortIndexPath OBJECT-TYPE
			SYNTAX Gauge32
			MAX-ACCESS read-only
			STATUS current
			DESCRIPTION
				"Ds1 identifier of the Transmux unit .For DS1 in a Transmux unit, it is equivalent to DS1 port number of its Transmux unit.
				For other Ds1 units, It will be zero. 
				"
			::= { ds1PortAttribEntry 3 }
		
		-- 1.3.6.1.4.1.2011.2.25.4.20.2.2.1.4
		ds1PortAttribLbo OBJECT-TYPE
			SYNTAX INTEGER (1..5)
			MAX-ACCESS read-write
			STATUS current
			DESCRIPTION
				"Line build out.
				Line build out (DS1 port) values 
				Value	Description
				1	Cable length range from 0 to 131 feet.
				2	Cable length range from 132 to 262 feet.
				3	Cable length range from 263 to 393 feet.
				4	Cable length range from 394 to 524 feet.
				5	Cable length range from 525 to 655 feet.
				"
			::= { ds1PortAttribEntry 4 }
		
		-- 1.3.6.1.4.1.2011.2.25.4.20.2.2.1.5
		ds1PortAttribLineCde OBJECT-TYPE
			SYNTAX INTEGER
				{
				b8zs(1),
				ami(2),
				invalid(254)
				}
			MAX-ACCESS read-write
			STATUS current
			DESCRIPTION
				"DS1 Line coding. Valid value is AMI or B8ZS. Default is B8ZS."
			::= { ds1PortAttribEntry 5 }
		
		-- 1.3.6.1.4.1.2011.2.25.4.20.2.2.1.6
		ds1PortAttribFmt OBJECT-TYPE
			SYNTAX INTEGER
				{
				sf(1),
				esf(2),
				unframed(255)
				}
			MAX-ACCESS read-write
			STATUS current
			DESCRIPTION
				"Frame format. Valid value is SF, ESF or UNFRAMED."
			::= { ds1PortAttribEntry 6 }
		
		-- 1.3.6.1.4.1.2011.2.25.4.20.2.2.1.7
		ds1PortAttribTACC OBJECT-TYPE
			SYNTAX INTEGER (0..999)
			MAX-ACCESS read-write
			STATUS current
			DESCRIPTION
				"Defines the DS1/T1 port as a test access port with a selected unique TAP number. "
			::= { ds1PortAttribEntry 7 }
		
		-- 1.3.6.1.4.1.2011.2.25.4.20.2.2.1.8
		ds1PortAttribLof2ais OBJECT-TYPE
			SYNTAX INTEGER
				{
				yes(1),
				no(2),
				invalid(254)
				}
			MAX-ACCESS read-write
			STATUS current
			DESCRIPTION
				"The parameter is provisioned to determine whether or not to generate DS1 AIS for the DS1 LOF"
			::= { ds1PortAttribEntry 8 }
		
		-- 1.3.6.1.4.1.2011.2.25.4.20.2.2.1.9
		ds1PortAttribSvtimer OBJECT-TYPE
			SYNTAX OCTET STRING (SIZE (0..6))
			MAX-ACCESS read-write
			STATUS current
			DESCRIPTION
				"Signal validation timer in minutes. Valid values are shown below.
				Value	     Description
				From 00-03   Signal validation timer in minutes. Only valid if auto in-service feature is supported. <SVTIMER> is a string, and format is: HH-MM.
				to 48-00     HH - Hour, it is an integer ranging from 0 to 48;
				             MM - Minute, it is an integer ranging from 0 to 59. The longest time is 48 hours. Default is 00-03 (3 minutes).
					
				"
			::= { ds1PortAttribEntry 9 }
		
		-- 1.3.6.1.4.1.2011.2.25.4.20.2.2.1.10
		ds1PortAttribPST OBJECT-TYPE
			SYNTAX OCTET STRING (SIZE (0..16))
			MAX-ACCESS read-write
			STATUS current
			DESCRIPTION
				"The primary state of the entity.
				Administrative State (PST) Definition
				IS  Puts the entity in service.
				OOS Puts the entity out of service.
				"
			::= { ds1PortAttribEntry 10 }
		
		-- 1.3.6.1.4.1.2011.2.25.4.20.2.2.1.11
		ds1PortAttribSST OBJECT-TYPE
			SYNTAX OCTET STRING (SIZE (0..32))
			MAX-ACCESS read-write
			STATUS current
			DESCRIPTION
				"The secondary state of the entity.
				Administrative State (PST) Definition.
				AINS Puts the entity in automatic in-service.
				MT   Removes the entity from service for maintenance."
			::= { ds1PortAttribEntry 11 }
		
		-- 1.3.6.1.4.1.2011.2.25.4.20.2.2.1.12
		ds1LoopbackStatus OBJECT-TYPE
			SYNTAX LpbkType
			MAX-ACCESS read-write
			STATUS current
			DESCRIPTION
				"This variable represents the current state of the
				loopback on the DS1 interface.  It contains
				information about loopbacks established by a
				manager and remotely from the far end."
			::= { ds1PortAttribEntry 12 }
		
		-- 1.3.6.1.4.1.2011.2.25.4.20.2.2.1.13
		ds1LoopbackTimeout OBJECT-TYPE
			SYNTAX Gauge32
			MAX-ACCESS read-only
			STATUS current
			DESCRIPTION
				"The remnant time that loop-back will be released.
				"
			::= { ds1PortAttribEntry 13 }
		
		-- 1.3.6.1.4.1.2011.2.25.4.20.2.2.1.14
		ds1RemoteALWFELPBK OBJECT-TYPE
			SYNTAX INTEGER
				{
				enable(1),
				disable(2),
				invalid(254)
				}
			MAX-ACCESS read-write
			STATUS current
			DESCRIPTION
				"(Optional) Far-end loopback allowance attribute of the port. If it is
				enable, the automatic far-end loopbacks are allowed. It is either enable or
				disable. The system default is enable. The parameter type is ENABLE_DISABLE, 
				which disables or enables an attribute.Automatic application of loopbacks 
				originating from the far end can be initiated on the T1 ports of
				a PLT1,PDT1,PDT1P card.It indicates that the port not support this parameter 
				when the attribute is invalid.
				"
			::= { ds1PortAttribEntry 14 }
		
		-- 1.3.6.1.4.1.2011.2.25.4.20.2.2.1.15
		ds1PortLpbkAutomaticTime OBJECT-TYPE
			SYNTAX Gauge32
			MAX-ACCESS read-write
			STATUS current
			DESCRIPTION
				"Time-out ticks (1 minute). For the T1 port default value is 120 (2 hours). 0 means time-out function is disabling. Valid values are 0~9999."
			::= { ds1PortAttribEntry 15 }
		
		-- 1.3.6.1.4.1.2011.2.25.4.20.2.3
		portTypeTable OBJECT-TYPE
			SYNTAX SEQUENCE OF PortTypeEntry
			MAX-ACCESS not-accessible
			STATUS current
			DESCRIPTION
				"Port type management table."
			::= { optixsonetFacilityMgt 3 }
		
		-- 1.3.6.1.4.1.2011.2.25.4.20.2.3.1
		portTypeEntry OBJECT-TYPE
			SYNTAX PortTypeEntry
			MAX-ACCESS not-accessible
			STATUS current
			DESCRIPTION
				"Port type management entry."
			INDEX { portIndexSlotId, portIndexPortId }
			::= { portTypeTable 1 }
		
		PortTypeEntry ::=
			SEQUENCE { 
				portIndexSlotId
					Gauge32,
				portIndexPortId
					Gauge32,
				portType
					IntfType
			 }

		-- 1.3.6.1.4.1.2011.2.25.4.20.2.3.1.1
		portIndexSlotId OBJECT-TYPE
			SYNTAX Gauge32
			MAX-ACCESS read-only
			STATUS current
			DESCRIPTION
				"Slot number.
				 	
				 	This will indicate what is the slot 
				 	of the object.
				"
			::= { portTypeEntry 1 }
		
		-- 1.3.6.1.4.1.2011.2.25.4.20.2.3.1.2
		portIndexPortId OBJECT-TYPE
			SYNTAX Gauge32
			MAX-ACCESS read-only
			STATUS current
			DESCRIPTION
				"Port Number.
				 	
				 	This will indicate what is the Port 
				 	of the object.
				"
			::= { portTypeEntry 2 }
		
		-- 1.3.6.1.4.1.2011.2.25.4.20.2.3.1.3
		portType OBJECT-TYPE
			SYNTAX IntfType
			MAX-ACCESS read-write
			STATUS current
			DESCRIPTION
				"The AID unit port type.Valid values are shown below.
				INTFTYPE values 
				Value	        Description
				DS3_ASYN_STS1	DS3 signal asynchronous mapped into STS1. Default for DS3 unit.
				DS3_TMUX_DS1	Multiplexing and de-multiplexing of DS1s to/from DS3. Default for Transmux unit (PDM3).
				DS1_ASYN_VT1	DS1 signal asynchronous mapped into VT1. Default for DS1 unit.
				DS3_SRV_DS1	Multiplexing and de-multiplexing of DS1s to/from DS3 as M13 server. 
				EC1	        EC1 signal mapped into STS1. PQT3A support EC1 service.
				UAS	        It indicates there is no use of the port.
				"
			::= { portTypeEntry 3 }
		
		-- 1.3.6.1.4.1.2011.2.25.4.20.2.4
		optixsonetFacilityMgtConformance OBJECT IDENTIFIER ::= { optixsonetFacilityMgt 4 }
		
		-- 1.3.6.1.4.1.2011.2.25.4.20.2.4.1
		optixsonetFacilityMgtGroups OBJECT IDENTIFIER ::= { optixsonetFacilityMgtConformance 1 }
		
		-- 1.3.6.1.4.1.2011.2.25.4.20.2.4.1.1
		currentObjectGroup OBJECT-GROUP
			OBJECTS { ds3PortIndexSlotId, ds3PortIndexPortId, ds3PortAttribReq, ds3PortAttribLbo, ds3PortAttribLineCde, 
				ds3PortAttribFmt, ds3PortAttribTACC, ds3PortAttribLof2ais, ds3PortAttribSvtimer, ds3PortAttribPST, 
				ds3PortAttribSST, ds3LoopbackStatus, ds3LoopbackTimeout, ds3RemoteALWFELPBK, ds1PortIndexSlotId, 
				ds1PortIndexPortId, ds1PortIndexPath, ds1PortAttribLbo, ds1PortAttribLineCde, ds1PortAttribFmt, 
				ds1PortAttribTACC, ds1PortAttribLof2ais, ds1PortAttribSvtimer, ds1PortAttribPST, ds1PortAttribSST, 
				ds1LoopbackStatus, ds1LoopbackTimeout, ds1RemoteALWFELPBK, ds1PortLpbkAutomaticTime, portIndexSlotId, 
				portIndexPortId, portType }
			STATUS current
			DESCRIPTION 
				"Enter the description of the created OBJECT-GROUP."
			::= { optixsonetFacilityMgtGroups 1 }
		
		-- 1.3.6.1.4.1.2011.2.25.4.20.2.4.2
		optixsonetFacilityMgtCompliances OBJECT IDENTIFIER ::= { optixsonetFacilityMgtConformance 2 }
		
		-- 1.3.6.1.4.1.2011.2.25.4.20.2.4.2.1
		basicCompliance MODULE-COMPLIANCE
			STATUS current
			DESCRIPTION 
				"Enter the description of the created MODULE-COMPLIANCE."
			MODULE -- this module
				MANDATORY-GROUPS { currentObjectGroup }
			::= { optixsonetFacilityMgtCompliances 1 }
		
	
	END

--
-- OPTIX-SONET-TU-MIB-V2.mib
--
