ADTRAN-MEF-PER-COS-PER-UNI-TOTAL-COUNT-MIB DEFINITIONS ::= BEGIN

IMPORTS
   MODULE-IDENTITY,
   OBJECT-TYPE,
   Integer32, Unsigned32
      FROM SNMPv2-SMI
   DisplayString
       FROM SNMPv2-TC
   ifIndex
       FROM IF-MIB
   HCPerfTimeElapsed,
   HCPerfValidIntervals,
   HCPerfInvalidIntervals,
   HCPerfCurrentCount,
   HCPerfIntervalCount,
   HCPerfTotalCount
      FROM HC-PerfHist-TC-MIB
   MODULE-COMPLIANCE,
   OBJECT-GROUP
      FROM SNMPv2-CONF
   adIdentity
      FROM ADTRAN-MIB
   adGenAOSMef,
   adGenAOSConformance
      FROM ADTRAN-AOS;

adGenAosMefPerCosPerUniTotalCountMib MODULE-IDENTITY
   LAST-UPDATED "201710140000Z" -- October 14, 2017
   ORGANIZATION "ADTRAN Inc."
   CONTACT-INFO
     "Info:   www.adtran.com
      Postal: ADTRAN, Inc.
              901 Explorer Blvd.
              Huntsville, AL 35806
      Tel:    +1 888 423-8726
      E-mail: support@adtran.com"

   DESCRIPTION
     "This MIB module defines high capacity performance statistics
      per COS per Uni within an AOS product.

      Copyright (C) ADTRAN, Inc. (2017)."

   REVISION    "201710140000Z" -- October 14, 2017
   DESCRIPTION
     "Initial version"
    ::= { adIdentity 10000 53 9 6 }

adGenAosMefPerCosPerUniTotalCount OBJECT IDENTIFIER ::= { adGenAOSMef 6 }

------------------------------------------------------------
-- Current Table for Total count of Green, yellow and red counters for Per Cos Per Uni. 
--
adMefPerCosPerUniTcTable OBJECT-TYPE
   SYNTAX      SEQUENCE OF AdMefPerCosPerUniTcEntry
   MAX-ACCESS  not-accessible
   STATUS      current
   DESCRIPTION
     "This table contains totla number of count for green, yellow and red 
      counters with Per Cos Per Uni. This table is indexed by ifIndex 
      and the queue number."
   ::= { adGenAosMefPerCosPerUniTotalCount 1 }

adMefPerCosPerUniTcEntry OBJECT-TYPE
   SYNTAX      AdMefPerCosPerUniTcEntry
   MAX-ACCESS  not-accessible
   STATUS      current
   DESCRIPTION
     "This specifies the information contained in one entry of the
      adMefPerCosPerUniTcTable. It is indexed by an interface's ifIndex,
      and the queue number."
   INDEX { ifIndex, adMefPerCosPerUniTcQueueNumber }
   ::= { adMefPerCosPerUniTcTable 1 }

AdMefPerCosPerUniTcEntry ::=
   SEQUENCE
   {
       adMefPerCosPerUniTcQueueNumber                         Unsigned32,
       adMefPerCosPerUniTotalIngressGreenOctets               HCPerfCurrentCount,
       adMefPerCosPerUniTotalIngressGreenFrames               HCPerfCurrentCount,
       adMefPerCosPerUniTotalIngressYellowOctets              HCPerfCurrentCount,
       adMefPerCosPerUniTotalIngressYellowFrames              HCPerfCurrentCount,
       adMefPerCosPerUniTotalIngressRedFrames                 HCPerfCurrentCount
   }

adMefPerCosPerUniTcQueueNumber OBJECT-TYPE
   SYNTAX      Unsigned32 (0..7)
   MAX-ACCESS  not-accessible
   STATUS      current
   DESCRIPTION
     "UNI queue number."
   ::= { adMefPerCosPerUniTcEntry 1 }
   

adMefPerCosPerUniTotalIngressGreenOctets OBJECT-TYPE
   SYNTAX      HCPerfCurrentCount
   MAX-ACCESS  read-only
   STATUS      current
   DESCRIPTION
     "Total number of Green Octets"
   ::= { adMefPerCosPerUniTcEntry 2 }

adMefPerCosPerUniTotalIngressGreenFrames OBJECT-TYPE
   SYNTAX      HCPerfCurrentCount
   MAX-ACCESS  read-only
   STATUS      current
   DESCRIPTION
     "Total number of Green frames."
   ::= { adMefPerCosPerUniTcEntry 3 }

adMefPerCosPerUniTotalIngressYellowOctets OBJECT-TYPE
   SYNTAX      HCPerfCurrentCount
   MAX-ACCESS  read-only
   STATUS      current
   DESCRIPTION
     "Total number of yellow octets."
   ::= { adMefPerCosPerUniTcEntry 4 }

adMefPerCosPerUniTotalIngressYellowFrames OBJECT-TYPE
   SYNTAX      HCPerfCurrentCount
   MAX-ACCESS  read-only
   STATUS      current
   DESCRIPTION
     "The total number of yellow frames."
   ::= { adMefPerCosPerUniTcEntry 5 }

adMefPerCosPerUniTotalIngressRedFrames OBJECT-TYPE
   SYNTAX      HCPerfCurrentCount
   MAX-ACCESS  read-only
   STATUS      current
   DESCRIPTION
     "Total number of red frames."
   ::= { adMefPerCosPerUniTcEntry 6 }

------------------------------------------------------------
-- Conformance information
--
adGenAosMefPerCosPerUniTotalCountConformance OBJECT IDENTIFIER
   ::= { adGenAOSConformance 28 }

adMefPerCosPerUniTotalCountGroups OBJECT IDENTIFIER
   ::= { adGenAosMefPerCosPerUniTotalCountConformance 1 }

adGenAosMefPerCosPerUniTotalCountCompliances OBJECT IDENTIFIER
   ::= { adGenAosMefPerCosPerUniTotalCountConformance 2 }

-- Compliance statements
--

adGenAosMefPerUniTotalCountCompliance MODULE-COMPLIANCE
   STATUS  current
   DESCRIPTION
     "The compliance statement for SNMPv2 entities which
      implement UNI interface for total number of count."
   MODULE
   MANDATORY-GROUPS {
      adMefPerCosPerUniTotalCountGroup
   }
   ::= { adGenAosMefPerCosPerUniTotalCountCompliances 1 }

-- Units of conformance
--
adMefPerCosPerUniTotalCountGroup OBJECT-GROUP
   OBJECTS 
   {
      adMefPerCosPerUniTotalIngressGreenOctets,
      adMefPerCosPerUniTotalIngressGreenFrames,      
      adMefPerCosPerUniTotalIngressYellowOctets,
      adMefPerCosPerUniTotalIngressYellowFrames,	  
      adMefPerCosPerUniTotalIngressRedFrames
   }
   STATUS  current
   DESCRIPTION
     "The Current Group."
   ::= { adMefPerCosPerUniTotalCountGroups 1 }
END
