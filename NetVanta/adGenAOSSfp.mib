ADTRAN-AOS-SFP-MIB   DEFINITIONS  ::= BEGIN
   
IMPORTS    
    MODULE-IDENTITY, OBJECT-TYPE, 
    NOTIFICATION-TYPE, Integer32,
    Unsigned32
       FROM SNMPv2-SMI
    DisplayString, 
    TEXTUAL-CONVENTION,
    TruthValue
       FROM SNMPv2-TC
    adIdentity
       FROM ADTRAN-MIB
    MODULE-COMPLIANCE, OBJECT-GROUP,
    NOTIFICATION-GROUP
       FROM SNMPv2-CONF
    ifDescr, ifIndex	
       FROM   IF-MIB
	adIdentity
       FROM ADTRAN-MIB
    adGenAOSCommon,
    adGenAOSConformance  
       FROM ADTRAN-AOS;
    

adGenAOSSfp MODULE-IDENTITY
        LAST-UPDATED "201710100000Z"
        ORGANIZATION "ADTRAN, Inc."
        CONTACT-INFO
               "Technical Support Dept.
                Postal: ADTRAN, Inc.
                901 Explorer Blvd.
                Huntsville, AL 35806
                Tel: +1 800 923 8726
                Fax: +1 256 963 6217
                E-mail: support@adtran.com"
        DESCRIPTION
            "The MIB module is for AdtranOS SFP Status."
            
     	REVISION "201710100000Z" -- October 10, 2017 / YYYYMMDDHHMMZ
        DESCRIPTION
               "Created the adGenAosSfp MIB. Revision R13.2"
    
        ::= { adIdentity 10000 53 1 12 }

adGenAOSSfp OBJECT IDENTIFIER ::= { adGenAOSCommon 12 }
adSFPTraps OBJECT IDENTIFIER ::= { adGenAOSSfp  0}

---
--- SFP Data
---

AdSFPThresholdTypeTC  ::= TEXTUAL-CONVENTION
    STATUS      current
    DESCRIPTION
        "This field indicates the type of the SFP threshold alarm."
    SYNTAX      INTEGER {
        alarmThresholdHigh(1),
        alarmThresholdLow(2)
    }

adGenAOSSFPAlarmThreshold  OBJECT-TYPE
    SYNTAX       AdSFPThresholdTypeTC 
    MAX-ACCESS  accessible-for-notify
    STATUS      current
    DESCRIPTION
        "This field indicates alarm threshold type high or low."
    ::= { adGenAOSSfp 1 }
     
adGenAOSSFPFailureReason  OBJECT-TYPE
    SYNTAX      OCTET STRING  (SIZE(0..256)) 
    MAX-ACCESS  accessible-for-notify
    STATUS      current
    DESCRIPTION
        "This field indicates the reason for the SFP Detection Failure."
    ::= { adGenAOSSfp 2 }	

adGenAoSSFPHwInfo OBJECT-TYPE
	SYNTAX		OCTET STRING  (SIZE(0..256))
	MAX-ACCESS	accessible-for-notify
	STATUS		current
	DESCRIPTION
		"This field indicates SFP information"
	::={ adGenAOSSfp 3 }
	
--- Conformance Information
---  
 adGenAOSSfpConformance OBJECT IDENTIFIER ::= { adGenAOSConformance 30 }
 adGenAOSSfpGroup       OBJECT IDENTIFIER ::= { adGenAOSSfpConformance 1 }
 adGenAOSSfpCompliances OBJECT IDENTIFIER ::= { adGenAOSSfpConformance 2 }

---
--- Notifications
---

adSfpAlarmRxPowerError NOTIFICATION-TYPE
    OBJECTS {
       ifDescr,
       adGenAOSSFPAlarmThreshold
    }
    STATUS current
    DESCRIPTION
        "This trap indicates that Rx Power exceeded alarm threshold level
         for an SFP. Information about the SFP and alarm threshold type are
         contained with in this trap."          
    ::= { adSFPTraps 1 }

adSfpAlarmRxPowerResume NOTIFICATION-TYPE
    OBJECTS {
       ifDescr
    }
    STATUS current
    DESCRIPTION
        "This trap indicates that Rx Power is with in the alarm thresholds 
         range for an SFP. Information about the SFP is contained with in 
         this trap."          
    ::= { adSFPTraps 2 }

adSfpAlarmSupplyVoltageError NOTIFICATION-TYPE
    OBJECTS {
       ifDescr,
       adGenAOSSFPAlarmThreshold
    }
    STATUS current
    DESCRIPTION
        "This trap indicates that Supply voltage exceeded alarm threshold level
         for an SFP. Information about the SFP and alarm threshold type are
         contained with in this trap."          
    ::= { adSFPTraps 5 }

adSfpAlarmSupplyVoltageResume NOTIFICATION-TYPE
    OBJECTS {
       ifDescr
    }
    STATUS current
    DESCRIPTION
        "This trap indicates that supply voltage is with in the alarm thresholds 
         range for an SFP. Information about the SFP is contained with in 
         this trap."          
    ::= { adSFPTraps 6 }

adSfpAlarmTxPowerError NOTIFICATION-TYPE
    OBJECTS {
       ifDescr,
       adGenAOSSFPAlarmThreshold
    }
    STATUS current
    DESCRIPTION
        "This trap indicates that Tx Power exceeded alarm threshold level
         for an SFP. Information about the SFP and alarm threshold type are
         contained with in this trap."          
    ::= { adSFPTraps 3 }

adSfpAlarmTxPowerResume NOTIFICATION-TYPE
    OBJECTS {
       ifDescr
    }
    STATUS current
    DESCRIPTION
        "This trap indicates that Tx Power is with in the alarm thresholds 
         range for an SFP. Information about the SFP is contained with in 
         this trap."          
    ::= { adSFPTraps 4 }

adSfpAlarmTemperatureError NOTIFICATION-TYPE
    OBJECTS {
       ifDescr,
       adGenAOSSFPAlarmThreshold
    }
    STATUS current
    DESCRIPTION
        "This trap indicates that Temperature exceeded alarm threshold level
         for an SFP. Information about the SFP and alarm threshold type are
         contained with in this trap."          
    ::= { adSFPTraps 7 }

adSfpAlarmTemperatureResume NOTIFICATION-TYPE
    OBJECTS {
       ifDescr
    }
    STATUS current
    DESCRIPTION
        "This trap indicates that Temperature is with in the alarm thresholds 
         range for an SFP. Information about the SFP is contained with in 
         this trap."          
    ::= { adSFPTraps 8 }

adSfpAlarmBiasCurrentError NOTIFICATION-TYPE
    OBJECTS {
       ifDescr,
       adGenAOSSFPAlarmThreshold
    }
    STATUS current
    DESCRIPTION
        "This trap indicates that Bias Current exceeded alarm threshold level
         for an SFP. Information about the SFP and alarm threshold type are
         contained with in this trap."          
    ::= { adSFPTraps 9 }

adSfpAlarmBiasCurrentResume NOTIFICATION-TYPE
    OBJECTS {
       ifDescr
    }
    STATUS current
    DESCRIPTION
        "This trap indicates that Bias Current is with in the alarm thresholds 
         range for an SFP. Information about the SFP is contained with in 
         this trap."          
    ::= { adSFPTraps 10 }

adSfpTypeFailure NOTIFICATION-TYPE
    OBJECTS {
       ifDescr,
	   adGenAOSSFPFailureReason
    }
    STATUS current
    DESCRIPTION
        "This trap indicates that SFP inserted is not supported by AdtranOS. 
         Information about the SFP is contained with in this trap."          
    ::= { adSFPTraps 11 }
	
adSfpEntConfigChangeInsertion NOTIFICATION-TYPE
    OBJECTS {
       ifDescr,
	   adGenAoSSFPHwInfo
    }
    STATUS current
    DESCRIPTION
        "This trap indicates that SFP is inserted into device. 
         Information about the SFP  and the interface is contained in this trap."          
    ::= { adSFPTraps 12 }
	
adSfpEntConfigChangeRemoval NOTIFICATION-TYPE
    OBJECTS {
       ifDescr,
	   adGenAoSSFPHwInfo
    }
    STATUS current
    DESCRIPTION
        "This trap indicates that SFP is removed from device. 
         Information about the SFP  and the interface is contained in this trap."          
    ::= { adSFPTraps 13}
    
--
-- MIB Compliance statements.
--

-- Full compliance statement
adGenAOSSfpFullCompliance MODULE-COMPLIANCE
    STATUS  current
    DESCRIPTION
       "The compliance statement for SNMP entities which implement
        version 2 of the adGenAOSSfp MIB."

    MODULE  -- this module

    MANDATORY-GROUPS { adGenAOSSfpInfoGroup,adGenAOSSfpNotificationGroup }
   ::= { adGenAOSSfpCompliances 1 }

-- units of conformance

adGenAOSSfpInfoGroup    OBJECT-GROUP
    OBJECTS {
       ifDescr,
       adGenAOSSFPAlarmThreshold
    }
    STATUS  current
    DESCRIPTION
       "Objects designed to assist in providing information about SFP
             attribute indicating Threshold failures."
         ::= { adGenAOSSfpGroup 1 }

adGenAOSSfpNotificationGroup    NOTIFICATION-GROUP
    NOTIFICATIONS {
        adSfpAlarmRxPowerError,
        adSfpAlarmRxPowerResume,
        adSfpAlarmTxPowerError,
        adSfpAlarmTxPowerResume,
        adSfpAlarmSupplyVoltageError,
        adSfpAlarmSupplyVoltageResume,
        adSfpAlarmTemperatureError,
        adSfpAlarmTemperatureResume,
        adSfpAlarmBiasCurrentError,
        adSfpAlarmBiasCurrentResume,
        adSfpTypeFailure,
        adSfpEntConfigChangeInsertion,
        adSfpEntConfigChangeRemoval
    }
    STATUS  current
    DESCRIPTION
       "Objects designed to assist in sending SFP
        Threshold Failure Notifications."

    ::= { adGenAOSSfpGroup 2 }


END
