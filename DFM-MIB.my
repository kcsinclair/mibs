-- DFM-MIB.my: CiscoWorks2000 Device Fault Manager
-- Copyright 1999 by System Management ARTS, Inc.
-- All Rights Reserved
--
DFM-MIB DEFINITIONS ::= BEGIN

IMPORTS
            enterprises, Counter32, OBJECT-TYPE,
            MODULE-IDENTITY, NOTIFICATION-TYPE
            FROM SNMPv2-SMI;

dfmMIB MODULE-IDENTITY
    LAST-UPDATED "9909232300Z"
    ORGANIZATION "Cisco Systems"
    CONTACT-INFO
            "Support
            Postal:Cisco Systems, Inc.
                    170 West Tasman Drive
                    San Jose, CA 95134
                    US
            Phone:+1 408 526-4000
            E-mail:tac@cisco.com"
            DESCRIPTION
                    "The CiscoWorks2000 Device Fault Manager MIB
                    module for entities defined by
                    Cisco Systems, Inc."
    ::= { enterprises 733 }


-- top level groups in the DFM-MIB

smNotificationTrap                  OBJECT IDENTIFIER ::= { dfmMIB 0 }
smNotificationData                  OBJECT IDENTIFIER ::= { dfmMIB 2 }
-- The smNotificationData Group
-- The members of this group are the OIDs for VarBinds containing
-- notification data.
-- Group for generic notification data.

smGenericNotify             OBJECT IDENTIFIER ::= { smNotificationData 1 }

smNotifTimestamp OBJECT-TYPE
    SYNTAX Counter32
    MAX-ACCESS not-accessible
    STATUS  current
    DESCRIPTION
    "The timestamp of the notification."
    ::= { smGenericNotify 1 }

smNotifServer OBJECT-TYPE
    SYNTAX OCTET STRING
    MAX-ACCESS not-accessible
    STATUS current
    DESCRIPTION
    "The name of the server that is sending the notification."
    ::= { smGenericNotify 2 }

smNotifClass OBJECT-TYPE
    SYNTAX OCTET STRING
    MAX-ACCESS not-accessible
    STATUS current
    DESCRIPTION
    "The class of the object associated with the notification."
    ::= { smGenericNotify 3 }

smNotifInstance OBJECT-TYPE
    SYNTAX OCTET STRING
    MAX-ACCESS not-accessible
    STATUS current
    DESCRIPTION
    "The instance name of the object associated with the 
notification."
    ::= { smGenericNotify 4 }





smNotifEventName OBJECT-TYPE
    SYNTAX OCTET STRING
    MAX-ACCESS not-accessible
    STATUS current
    DESCRIPTION
    "The name of the event causing the notification."
    ::= { smGenericNotify 5 }

smNotifInstanceID OBJECT-TYPE
    SYNTAX OCTET STRING
    MAX-ACCESS not-accessible
    STATUS current
    DESCRIPTION
    "The unique DFM inventory identification 
      for the object associated with the notification ."
    ::= { smGenericNotify 6 }

smNotifDescription OBJECT-TYPE
    SYNTAX OCTET STRING
    MAX-ACCESS not-accessible
    STATUS current
    DESCRIPTION
    "A complete description of the event."
    ::= { smGenericNotify 7 }

smNotifCertainty OBJECT-TYPE
    SYNTAX OCTET STRING
    MAX-ACCESS not-accessible
    STATUS current
    DESCRIPTION
    "The certainty of the event.  Floating-point number in the
      range 0-100, stored as a string."
    ::= { smGenericNotify 8 }

smNotifSeverity OBJECT-TYPE
    SYNTAX INTEGER {
            notApplicable (1),
            informational (2),
            warning (3),
            minor (4),
            major (5),
            severe (6)
    }
    MAX-ACCESS not-accessible
    STATUS  current
    DESCRIPTION
    "The severity of the event.  Integer number in the range 1-6."
    ::= { smGenericNotify 9 }

-- The DFM enterprise Traps
--
-- These are the enterprise-specific trap codes currently in-use in
-- DFM software.  The final sub-OID of each object is the code sent
-- in the "specific-trap" field of an SNMPv1 Trap-PDU.
--
-- The definition of these objects mimics the SNMPv2 convention for
-- sending traps: Take the enterprise OID, append 0, then append the
-- trap code.
 
    smTrapNotification NOTIFICATION-TYPE
    OBJECTS {               smNotifTimestamp,
                    smNotifServer,
                    smNotifClass,
                    smNotifInstance,
                    smNotifEventName,
                    smNotifInstanceID,
                    smNotifDescription,
                    smNotifCertainty,
                    smNotifSeverity
            }
    STATUS current
    DESCRIPTION
            "A trap describing a DFM root cause notification.
            The text in smNotifDescription indicates the nature of
            the problem."
      ::= { smNotificationTrap 4 }

    smTrapCertaintyChange NOTIFICATION-TYPE
    OBJECTS {               smNotifTimestamp,
                    smNotifServer,
                    smNotifClass,
                    smNotifInstance,
                    smNotifEventName,
                    smNotifInstanceID,
                    smNotifDescription,
                    smNotifCertainty,
                    smNotifSeverity
            }
    STATUS current
    DESCRIPTION
            "A trap indicating a certainty change of a DFM
            notification. The text in smNotifDescription indicates
            the nature of the problem."
      ::=  { smNotificationTrap 2 }



    smTrapSeverityChange NOTIFICATION-TYPE
    OBJECTS {               smNotifTimestamp,
                    smNotifServer,
                    smNotifClass,
                    smNotifInstance,
                    smNotifEventName,
                    smNotifInstanceID,
                    smNotifDescription,
                    smNotifCertainty,
                    smNotifSeverity
            }
    STATUS current
    DESCRIPTION
            "A trap indicating a severity change of a DFM
            notification. The text in smNotifDescription indicates
            the nature of the notification."
       ::= { smNotificationTrap 3 }

    smTrapNotificationClear NOTIFICATION-TYPE
    OBJECTS {               smNotifTimestamp,
                    smNotifServer,
                    smNotifClass,
                    smNotifInstance,
                    smNotifEventName,
                    smNotifInstanceID,
                    smNotifDescription,
                    smNotifCertainty,
                    smNotifSeverity
            }
    STATUS current
    DESCRIPTION
            "A trap indicating the clear of a DFM notification."
    ::= { smNotificationTrap 7 }


END
