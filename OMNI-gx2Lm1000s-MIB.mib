OMNI-gx2Lm1000s-MIB DEFINITIONS ::= BEGIN

    IMPORTS     
    IpAddress, TimeTicks
					      FROM RFC1155-SMI
	OBJECT-TYPE                     
					      FROM RFC-1212
	sysUpTime, DisplayString        
					      FROM RFC1213-MIB
	TRAP-TYPE                       
					      FROM RFC-1215
	gi, motproxies                   
					      FROM NLS-BBNIDENT-MIB
	gx2Lm1000s
					      FROM GX2HFC-MIB

	trapIdentifier,trapNetworkElemModelNumber,
	trapNetworkElemSerialNum, trapPerceivedSeverity,
	trapNetworkElemOperState, trapNetworkElemAlarmStatus,
	trapNetworkElemAdminState, trapNetworkElemAvailStatus,
	trapText, trapNETrapLastTrapTimeStamp, trapChangedObjectId,
	trapChangedValueInteger, trapChangedValueDisplayString
					      FROM NLSBBN-TRAPS-MIB;



	       -- This MIB module uses the extended OBJECT-TYPE macro as
	       -- defined in RFC1212 and the TRAP-TYPE macro as defined
	       -- in RFC 1215.

		   --REVISION	"0" Sept 1, 2003
		   --DESCRIPTION
		   --			Added revision and description comment section


		--    OMNISTAR DM 1550 Laser Module (Return Path Transmetter)  MIB MODULE

	-- This MIB module defines information for management of HFC networks
		-- 
		-- The MIB module assumes that all generic (static) network element
		-- information is defined in a different module such as the HFC module
		-- The MIB consists of two groups:
		-- the device type descriptor subgroup and 
		-- gx2Lm1000s Network Elements subgroup.
		-- The device type descriptor subgroup is used to define 
		-- parameters specific to gx2Lm1000s device type.
		-- These parameters are common across all network elements
		-- from gx2Lm1000s device type.
		--
		-- The gx2Lm1000s Network Elements subgroup is
		-- a list of gx2Lm1000s type elements in the
		-- current network topology with nominal
		-- and current parameter values for the
		-- individual network elements; the individual
		-- network elements are identified by  
		-- index from hfcCommonTable.
		-- That implies what hfcCommonTableIndex and
		-- gx2Lm1000sTableIndex are equal for each individual
		-- network element.
		-- This table is an extension of the hfcCommonTable
		-- for all elements of gx2Lm1000s type.
		--
		-- Both groups are mandatory for management of gx2Lm1000s devices.

-- ****************************************************************************
		--
		-- All floating point numbers will be represented by an IEEE 32 Bit number.
		-- Conversion of this number must be done on the user interface to view the 
		-- actual floating point number. 
		--

		Float ::= Counter  -- UNSIGNED (32 BITS) 

-- ****************************************************************************

		-- gx2Lm1000s Device Descriptor subgroup.

		-- The device type descriptor subgroup is used to define 
		-- parameters specific to gx2Lm1000s device type.
		-- These parameters are common across all network elements
		-- from gx2Lm1000s device type.


		gx2Lm1000sDescriptor OBJECT IDENTIFIER ::= {gx2Lm1000s 1}



--*****************************************************************************
		--              gx2Lm1000s Table
		
		-- The individual network elements indentified by  
		-- index from hfcCommonTable.
		-- That implies what hfcCommonTableIndex and
		-- gx2Lm1000sTableIndex are equal for each individual
		-- nettwork element.
		-- This table should be used as an extension of the hfcCommonTable
		-- for all elements of gx2Lm1000s type.


	       gx2Lm1000sAnalogTable                    OBJECT-TYPE
			 SYNTAX             SEQUENCE OF Gx2Lm1000sAnalogEntry
			 ACCESS             not-accessible
			 STATUS             mandatory
			 DESCRIPTION
			 "This table contains gx2Lm1000s specific parameters with
			  nominal and current values."
			 ::= { gx2Lm1000s 2 }


	       gx2Lm1000sAnalogEntry               OBJECT-TYPE
			 SYNTAX             Gx2Lm1000sAnalogEntry
			 ACCESS             not-accessible
			 STATUS             mandatory
			 DESCRIPTION
			 "This list contains the analog parameters and descriptions."
			 INDEX { gx2Lm1000sAnalogTableIndex }
			 ::= { gx2Lm1000sAnalogTable  1}

--*************************************************************************
	       gx2Lm1000sDigitalTable                    OBJECT-TYPE
			 SYNTAX             SEQUENCE OF Gx2Lm1000sDigitalEntry
			 ACCESS             not-accessible
			 STATUS             mandatory
			 DESCRIPTION
			 "This table contains gx2Lm1000sm specific parameters with
			  nominal and current values."
			 ::= { gx2Lm1000s 3 }

	       gx2Lm1000sDigitalEntry               OBJECT-TYPE
			 SYNTAX             Gx2Lm1000sDigitalEntry
			 ACCESS             not-accessible
			 STATUS             mandatory
			 DESCRIPTION
			 "This list contains digital parameters and descriptions."
			 INDEX { gx2Lm1000sDigitalTableIndex }
			 ::= { gx2Lm1000sDigitalTable  2}

--*************************************************************************
	       gx2Lm1000sStatusTable                    OBJECT-TYPE
			 SYNTAX             SEQUENCE OF Gx2Lm1000sStatusEntry
			 ACCESS             not-accessible
			 STATUS             mandatory
			 DESCRIPTION
			 "This table contains gx2Lm1000s specific parameters with
			  nominal and current values."
			 ::= { gx2Lm1000s 4 }

	       gx2Lm1000sStatusEntry               OBJECT-TYPE
			 SYNTAX             Gx2Lm1000sStatusEntry
			 ACCESS             not-accessible
			 STATUS             mandatory
			 DESCRIPTION
			 "This list contains Status parameters and descriptions."
			 INDEX { gx2Lm1000sStatusTableIndex }
			 ::= { gx2Lm1000sStatusTable  3}

--*************************************************************************
	       gx2Lm1000sFactoryTable                    OBJECT-TYPE
			 SYNTAX             SEQUENCE OF Gx2Lm1000sFactoryEntry
			 ACCESS             not-accessible
			 STATUS             mandatory
			 DESCRIPTION
			 "This table contains gx2Lm1000s specific parameters with
			  nominal and current values."
			 ::= { gx2Lm1000s 5 }

	       gx2Lm1000sFactoryEntry               OBJECT-TYPE
			 SYNTAX             Gx2Lm1000sFactoryEntry
			 ACCESS             not-accessible
			 STATUS             mandatory
			 DESCRIPTION
			 "This list contains Factory parameters and descriptions."
			 INDEX { gx2Lm1000sFactoryTableIndex }
			 ::= { gx2Lm1000sFactoryTable  4}
--*************************************************************************

	      Gx2Lm1000sAnalogEntry    ::= SEQUENCE  
	       {
		gx2Lm1000sAnalogTableIndex         INTEGER,
		
		--           Analog Parameters

		lm1000slabelOffsetNomMonitor			DisplayString (SIZE (0..80)),
		lm1000suomOffsetNomMonitor			DisplayString (SIZE (0..80)),
		lm1000smajorHighOffsetNomMonitor 		Float, 
		lm1000smajorLowOffsetNomMonitor 		Float, 
		lm1000sminorHighOffsetNomMonitor 		Float,
		lm1000sminorLowOffsetNomMonitor 		Float, 
		lm1000scurrentValueOffsetNomMonitor 	Float, 
		lm1000sstateFlagOffsetNomMonitor 		INTEGER,
		lm1000sminValueOffsetNomMonitor 		Float,
		lm1000smaxValueOffsetNomMonitor  		Float,
		lm1000salarmStateOffsetNomMonitor 	INTEGER,

		lm1000slabelLaserPower				DisplayString (SIZE (0..80)),
		lm1000suomLaserPower					DisplayString (SIZE (0..80)),
		lm1000smajorHighLaserPower			Float, 
		lm1000smajorLowLaserPower				Float, 
		lm1000sminorHighLaserPower			Float,
		lm1000sminorLowLaserPower				Float, 
		lm1000scurrentValueLaserPower			Float, 
		lm1000sstateFlagLaserPower			INTEGER,
		lm1000sminValueLaserPower				Float,
		lm1000smaxValueLaserPower 			Float,
		lm1000salarmStateLaserPower			INTEGER,

		lm1000slabelLaserTemp					DisplayString (SIZE (0..80)),
		lm1000suomLaserTemp					DisplayString (SIZE (0..80)),
		lm1000smajorHighLaserTemp				Float, 
		lm1000smajorLowLaserTemp				Float, 
		lm1000sminorHighLaserTemp				Float,
		lm1000sminorLowLaserTemp				Float, 
		lm1000scurrentValueLaserTemp			Float, 
		lm1000sstateFlagLaserTemp				INTEGER,
		lm1000sminValueLaserTemp				Float,
		lm1000smaxValueLaserTemp 				Float,
		lm1000salarmStateLaserTemp			INTEGER,

		lm1000slabelLaserCurrent				DisplayString (SIZE (0..80)),
		lm1000suomLaserCurrent				DisplayString (SIZE (0..80)),
		lm1000smajorHighLaserCurrent			Float, 
		lm1000smajorLowLaserCurrent			Float, 
		lm1000sminorHighLaserCurrent			Float,
		lm1000sminorLowLaserCurrent			Float, 
		lm1000scurrentValueLaserCurrent		Float, 
		lm1000sstateFlagLaserCurrent			INTEGER,
		lm1000sminValueLaserCurrent			Float,
		lm1000smaxValueLaserCurrent 			Float,
		lm1000salarmStateLaserCurrent			INTEGER,

		lm1000slabelTecCurrent				DisplayString (SIZE (0..80)),
		lm1000suomTecCurrent					DisplayString (SIZE (0..80)),
		lm1000smajorHighTecCurrent			Float, 
		lm1000smajorLowTecCurrent				Float, 
		lm1000sminorHighTecCurrent			Float,
		lm1000sminorLowTecCurrent				Float, 
		lm1000scurrentValueTecCurrent			Float, 
		lm1000sstateFlagTecCurrent			INTEGER,
		lm1000sminValueTecCurrent				Float,
		lm1000smaxValueTecCurrent				Float,
		lm1000salarmStateTecCurrent			INTEGER,

		lm1000slabelModTemp					DisplayString (SIZE (0..80)),
		lm1000suomModTemp						DisplayString (SIZE (0..80)),
		lm1000smajorHighModTemp				Float, 
		lm1000smajorLowModTemp				Float, 
		lm1000sminorHighModTemp				Float,
		lm1000sminorLowModTemp				Float, 
		lm1000scurrentValueModTemp			Float, 
		lm1000sstateFlagModTemp				INTEGER,
		lm1000sminValueModTemp				Float,
		lm1000smaxValueModTemp 				Float,
		lm1000salarmStateModTemp				INTEGER,

		lm1000slabelFanCurrent				DisplayString (SIZE (0..80)),
		lm1000suomFanCurrent					DisplayString (SIZE (0..80)),
		lm1000smajorHighFanCurrent			Float, 
		lm1000smajorLowFanCurrent				Float, 
		lm1000sminorHighFanCurrent			Float,
		lm1000sminorLowFanCurrent				Float, 
		lm1000scurrentValueFanCurrent			Float, 
		lm1000sstateFlagFanCurrent			INTEGER,
		lm1000sminValueFanCurrent				Float,
		lm1000smaxValueFanCurrent				Float,
		lm1000salarmStateFanCurrent			INTEGER
		}

		-- ****************  Digital Parameters ***********************

      Gx2Lm1000sDigitalEntry    ::= SEQUENCE  
      {
		gx2Lm1000sDigitalTableIndex         INTEGER,

		lm1000slabelRfInput				DisplayString (SIZE (0..80)),
		lm1000senumRfInput				DisplayString (SIZE (0..80)),
		lm1000svalueRfInput				INTEGER,
		lm1000sstateflagRfInput  			INTEGER,

		lm1000slabelOptOutput				DisplayString (SIZE (0..80)),
		lm1000senumOptOutput				DisplayString (SIZE (0..80)),
		lm1000svalueOptOutput				INTEGER,
		lm1000sstateflagOptOutput         INTEGER,

		lm1000slabelAttnSetting			DisplayString (SIZE (0..80)),
		lm1000senumAttnSetting				DisplayString (SIZE (0..80)),
		lm1000svalueAttnSetting			INTEGER,
		lm1000sstateflagAttnSetting        INTEGER,

		lm1000slabelFactoryDefault		DisplayString (SIZE (0..80)),
		lm1000senumFactoryDefault			DisplayString (SIZE (0..80)),
		lm1000svalueFactoryDefault		INTEGER,
		lm1000sstateflagFactoryDefault   	INTEGER
		}


		-- ****************  Status Parameters ************************************
	    Gx2Lm1000sStatusEntry    ::= SEQUENCE  
	    {
		gx2Lm1000sStatusTableIndex		INTEGER,

		lm1000slabelBoot					DisplayString (SIZE (0..80)),
		lm1000svalueBoot					INTEGER,
		lm1000sstateflagBoot				INTEGER,
		
		lm1000slabelFlash					DisplayString (SIZE (0..80)),
		lm1000svalueFlash					INTEGER,
		lm1000sstateflagFlash				INTEGER,

		lm1000slabelFactoryDataCRC 		DisplayString (SIZE (0..80)),
		lm1000svalueFactoryDataCRC		INTEGER,
		lm1000sstateflagFactoryDataCRC	INTEGER,

		lm1000slabelLaserDataCRC 			DisplayString (SIZE (0..80)),
		lm1000svalueLaserDataCRC 			INTEGER,
		lm1000sstateflagLaserDataCRC 		INTEGER,

		lm1000slabelAlarmDataCrc			DisplayString (SIZE (0..80)),
		lm1000svalueAlarmDataCrc			INTEGER,
		lm1000sstateflagAlarmDataCrc		INTEGER,

		lm1000slabelRFInputStatus			DisplayString (SIZE (0..80)),
		lm1000svalueRFInputStatus			INTEGER,
		lm1000sstateflagRFInputStatus		INTEGER
		}


		-- ****************  Factory Parameters *************************************
	    Gx2Lm1000sFactoryEntry    ::= SEQUENCE  
	    {
		gx2Lm1000sFactoryTableIndex		INTEGER,
		lm1000sbootControlByte  			INTEGER,
		lm1000sbootStatusByte   			INTEGER,
		lm1000sbank1CRC    				INTEGER,
		lm1000sbank2CRC    				INTEGER,
		lm1000sprgEEPROMByte    			INTEGER,
		lm1000sfactoryCRC    				INTEGER,
		lm1000scalculateCRC    			INTEGER,
		lm1000shourMeter    				INTEGER,
		lm1000sflashPrgCntA    			INTEGER,
		lm1000sflashPrgCntB    			INTEGER,
		lm1000sflashBankARev    			DisplayString (SIZE (0..80)),
		lm1000sflashBankBRev    			DisplayString (SIZE (0..80))


		}
            -- ************** Analog Parameters ****************************
		gx2Lm1000sAnalogTableIndex			OBJECT-TYPE
			   SYNTAX				INTEGER (1..2147483647)
			   ACCESS				read-only
			   STATUS				mandatory
			   DESCRIPTION			
			   "The value of this object identifies the network
			    element. This index is equal to the
			    hfcCommonTableIndex for the same element."
			   ::= { gx2Lm1000sAnalogEntry 1}

-- New Parameter

		lm1000slabelOffsetNomMonitor              OBJECT-TYPE
			   SYNTAX           DisplayString (SIZE (0..80))
			   ACCESS           read-only
			   STATUS           optional
			   DESCRIPTION
			   "The value of this object provides the label of the
			    Offset Monitor Analog parameter."
			   ::= { gx2Lm1000sAnalogEntry 2}

		lm1000suomOffsetNomMonitor                OBJECT-TYPE
			   SYNTAX           DisplayString (SIZE (0..80))
			   ACCESS           read-only
			   STATUS           optional
			   DESCRIPTION
			   "The value of this object provides the Unit of Measure of the
			    Offset Monitor Analog parameter. The unit of measure for 
			    this parameter is dB"
			   ::= { gx2Lm1000sAnalogEntry 3}

		lm1000smajorHighOffsetNomMonitor          OBJECT-TYPE
			   SYNTAX           Float 
			   ACCESS           read-only
			   STATUS           obsolete
			   DESCRIPTION
			   "The value of this object provides the Major High alarm value
			   of the Offset Monitor Analog parameter.
			   This object is not used by this module and always returns invalid 
			   float value of 0xFFFFFFFF . This object is kept here for persistence."
			   ::= { gx2Lm1000sAnalogEntry 4}


		lm1000smajorLowOffsetNomMonitor           OBJECT-TYPE
			   SYNTAX           Float 
			   ACCESS           read-only
			   STATUS           obsolete
			   DESCRIPTION
			   "The value of this object provides the Major Low alarm value
			    of the Offset Monitor Power Analog parameter.
			   This object is not used by this module and always returns invalid 
			   float value of 0xFFFFFFFF . This object is kept here for persistence."
			   ::= { gx2Lm1000sAnalogEntry 5}

		lm1000sminorHighOffsetNomMonitor          OBJECT-TYPE
			   SYNTAX           Float
			   ACCESS           read-only
			   STATUS           obsolete
			   DESCRIPTION
			   "The value of this object provides the Minor High alarm value
			    of the Offset Monitor Power Analog parameter.
			   This object is not used by this module and always returns invalid 
			   float value of 0xFFFFFFFF . This object is kept here for persistence."
			   ::= { gx2Lm1000sAnalogEntry 6}

		lm1000sminorLowOffsetNomMonitor           OBJECT-TYPE
			   SYNTAX           Float 
			   ACCESS           read-only
			   STATUS           obsolete
			   DESCRIPTION
			   "The value of this object provides the Minor Low alarm value
			    of the Offset Monitor Power Analog parameter.
			   This object is not used by this module and always returns invalid 
			   float value of 0xFFFFFFFF . This object is kept here for persistence."
			   ::= { gx2Lm1000sAnalogEntry 7}

		lm1000scurrentValueOffsetNomMonitor       OBJECT-TYPE
			   SYNTAX           Float 
			   ACCESS           read-only
			   STATUS           mandatory
			   DESCRIPTION
			   "The value of this object provides the Current value
			    of the Offset Monitor Power Analog parameter."
			   ::= { gx2Lm1000sAnalogEntry 8}

		lm1000sstateFlagOffsetNomMonitor          OBJECT-TYPE
			   SYNTAX           INTEGER
								{
								hidden(1),
								read-only(2),
								updateable(3)
								}
			   ACCESS           read-only
			   STATUS           mandatory
			   DESCRIPTION
			   "The value of this object provides the state
			    of the Offset Monitor Power Analog parameter. (1-hidden	
			          2-read-only, 3-updateable)."
			   ::= { gx2Lm1000sAnalogEntry 9}

		lm1000sminValueOffsetNomMonitor           OBJECT-TYPE
			   SYNTAX           Float
			   ACCESS           read-only
			   STATUS           mandatory
			   DESCRIPTION
			   "The value of this object provides the minimum value
			    the Offset Monitor Power Analog parameter can achive."
			   ::= { gx2Lm1000sAnalogEntry 10}

		lm1000smaxValueOffsetNomMonitor           OBJECT-TYPE
			   SYNTAX           Float
			   ACCESS           read-only
			   STATUS           mandatory
			   DESCRIPTION
			   "The value of this object provides the maximum value
			    the Offset Monitor Power Analog parameter can achive."
			   ::= { gx2Lm1000sAnalogEntry 11}

		lm1000salarmStateOffsetNomMonitor         OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Offset Monitor Power Analog parameter."
			   ::= { gx2Lm1000sAnalogEntry 12}
			   
-- New Parameter

		lm1000slabelLaserPower            OBJECT-TYPE
			   SYNTAX           DisplayString (SIZE (0..80))
			   ACCESS           read-only
			   STATUS           optional
			   DESCRIPTION
			   "The value of this object provides the label of the
			    Laser Optical Power Analog parameter."
			   ::= { gx2Lm1000sAnalogEntry 13}

		lm1000suomLaserPower              OBJECT-TYPE
			   SYNTAX           DisplayString (SIZE (0..80))
			   ACCESS           read-only
			   STATUS           optional
			   DESCRIPTION
			   "The value of this object provides the Unit of Measure of the
			    Laser Optical Power Analog parameter. The unit of measure for 
			    this parameter is dBm"
			   ::= { gx2Lm1000sAnalogEntry 14}

		lm1000smajorHighLaserPower        OBJECT-TYPE
			   SYNTAX           Float 
			   ACCESS           read-only
			   STATUS           mandatory
			   DESCRIPTION
			   "The value of this object provides the Major High alarm value
			    of the Laser Optical Power Analog parameter."
			   ::= { gx2Lm1000sAnalogEntry 15}


		lm1000smajorLowLaserPower         OBJECT-TYPE
			   SYNTAX           Float 
			   ACCESS           read-only
			   STATUS           mandatory
			   DESCRIPTION
			   "The value of this object provides the Major Low alarm value
			    of the Laser Optical Power Analog parameter."
			   ::= { gx2Lm1000sAnalogEntry 16}

		lm1000sminorHighLaserPower        OBJECT-TYPE
			   SYNTAX           Float
			   ACCESS           read-only
			   STATUS           obsolete
			   DESCRIPTION
			   "The value of this object provides the Minor High alarm value
			    of the Laser Optical Power Analog parameter.
			   This object is not used by this module and always returns invalid 
			   float value of 0xFFFFFFFF . This object is kept here for persistence."
			   ::= { gx2Lm1000sAnalogEntry 17}

		lm1000sminorLowLaserPower         OBJECT-TYPE
			   SYNTAX           Float 
			   ACCESS           read-only
			   STATUS           obsolete
			   DESCRIPTION
			   "The value of this object provides the Minor Low alarm value
			    of the Laser Optical Power Analog parameter.
			   This object is not used by this module and always returns invalid 
			   float value of 0xFFFFFFFF . This object is kept here for persistence."
			   ::= { gx2Lm1000sAnalogEntry 18}

		lm1000scurrentValueLaserPower     OBJECT-TYPE
			   SYNTAX           Float 
			   ACCESS           read-only
			   STATUS           mandatory
			   DESCRIPTION
			   "The value of this object provides the Current value
			    of the Laser Optical Power Analog parameter.
			   This value is a floating point number that is represented as 
			   an IEEE 32 bit number."
			   ::= { gx2Lm1000sAnalogEntry 19}

		lm1000sstateFlagLaserPower        OBJECT-TYPE
			   SYNTAX           INTEGER
								{
								hidden(1),
								read-only(2),
								updateable(3)
								}
			   ACCESS           read-only
			   STATUS           mandatory
			   DESCRIPTION
			   "The value of this object provides the state
			    of the Laser Optical Power Analog parameter.  (1-hidden	
			          2-read-only, 3-updateable)."
			   ::= { gx2Lm1000sAnalogEntry 20}

		lm1000sminValueLaserPower         OBJECT-TYPE
			   SYNTAX           Float
			   ACCESS           read-only
			   STATUS           mandatory
			   DESCRIPTION
			   "The value of this object provides the minimum value
			    the Laser Optical Power Analog parameter can achive."
			   ::= { gx2Lm1000sAnalogEntry 21}

		lm1000smaxValueLaserPower         OBJECT-TYPE
			   SYNTAX           Float
			   ACCESS           read-only
			   STATUS           mandatory
			   DESCRIPTION
			   "The value of this object provides the maximum value
			    the Laser Optical Power Analog parameter can achive."
			   ::= { gx2Lm1000sAnalogEntry 22}

		lm1000salarmStateLaserPower       OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Laser Optical Power Analog parameter."
			   ::= { gx2Lm1000sAnalogEntry 23}

-- New Parameter


		lm1000slabelLaserTemp           OBJECT-TYPE
			   SYNTAX           DisplayString (SIZE (0..80))
			   ACCESS           read-only
			   STATUS           optional
			   DESCRIPTION
			   "The value of this object provides the label of the
			    Laser Temperature Analog parameter."
			   ::= { gx2Lm1000sAnalogEntry 24}

		lm1000suomLaserTemp             OBJECT-TYPE
			   SYNTAX           DisplayString (SIZE (0..80))
			   ACCESS           read-only
			   STATUS           optional
			   DESCRIPTION
			   "The value of this object provides the Unit of Measure of the
			    Laser Temperature Analog parameter. The unit of measure for 
			    this parameter is degrees C"
			   ::= { gx2Lm1000sAnalogEntry 25}

		lm1000smajorHighLaserTemp       OBJECT-TYPE
			   SYNTAX           Float 
			   ACCESS           read-only
			   STATUS           mandatory
			   DESCRIPTION
			   "The value of this object provides the Major High alarm value
			    of the Laser Temperature Analog parameter."
			   ::= { gx2Lm1000sAnalogEntry 26}


		lm1000smajorLowLaserTemp        OBJECT-TYPE
			   SYNTAX           Float 
			   ACCESS           read-only
			   STATUS           mandatory
			   DESCRIPTION
			   "The value of this object provides the Major Low alarm value
			    of the Laser Temperature Analog parameter."
			   ::= { gx2Lm1000sAnalogEntry 27}

		lm1000sminorHighLaserTemp       OBJECT-TYPE
			   SYNTAX           Float
			   ACCESS           read-only
			   STATUS           obsolete
			   DESCRIPTION
			   "The value of this object provides the Minor High alarm value
			    of the Laser Temperature Analog parameter."
			   ::= { gx2Lm1000sAnalogEntry 28}

		lm1000sminorLowLaserTemp        OBJECT-TYPE
			   SYNTAX           Float 
			   ACCESS           read-only
			   STATUS           obsolete
			   DESCRIPTION
			   "The value of this object provides the Minor Low alarm value
			    of the Laser Temperature Analog parameter."
			   ::= { gx2Lm1000sAnalogEntry 29}

		lm1000scurrentValueLaserTemp    OBJECT-TYPE
			   SYNTAX           Float 
			   ACCESS           read-only
			   STATUS           mandatory
			   DESCRIPTION
			   "The value of this object provides the Current value
			    of the Laser Temperature Analog parameter."
			   ::= { gx2Lm1000sAnalogEntry 30}

		lm1000sstateFlagLaserTemp       OBJECT-TYPE
			   SYNTAX           INTEGER
								{
								hidden(1),
								read-only(2),
								updateable(3)
								}
			   ACCESS           read-only
			   STATUS           mandatory
			   DESCRIPTION
			   "The value of this object provides the state
			    of the Laser Temperature Analog parameter.  (1-hidden	
			          2-read-only, 3-updateable)."
			   ::= { gx2Lm1000sAnalogEntry 31}

		lm1000sminValueLaserTemp        OBJECT-TYPE
			   SYNTAX           Float
			   ACCESS           read-only
			   STATUS           mandatory
			   DESCRIPTION
			   "The value of this object provides the minimum value
			    the Laser Temperature Analog parameter can achive."
			   ::= { gx2Lm1000sAnalogEntry 32}

		lm1000smaxValueLaserTemp        OBJECT-TYPE
			   SYNTAX           Float
			   ACCESS           read-only
			   STATUS           mandatory
			   DESCRIPTION
			   "The value of this object provides the maximum value
			    the Laser Temperature Analog parameter can achive."
			   ::= { gx2Lm1000sAnalogEntry 33}

		lm1000salarmStateLaserTemp      OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Laser Temperature Analog parameter."
			   ::= { gx2Lm1000sAnalogEntry 34}

-- New Parameter

		lm1000slabelLaserCurrent            OBJECT-TYPE
			   SYNTAX           DisplayString (SIZE (0..80))
			   ACCESS           read-only
			   STATUS           optional
			   DESCRIPTION
			   "The value of this object provides the label of the
			    Laser Bias Current Analog parameter."
			   ::= { gx2Lm1000sAnalogEntry 35}

		lm1000suomLaserCurrent              OBJECT-TYPE
			   SYNTAX           DisplayString (SIZE (0..80))
			   ACCESS           read-only
			   STATUS           optional
			   DESCRIPTION
			   "The value of this object provides the Unit of Measure of the
			    Laser Bias Current Analog parameter. The unit of measure for 
			    this parameter is mA"
			   ::= { gx2Lm1000sAnalogEntry 36}

		lm1000smajorHighLaserCurrent        OBJECT-TYPE
			   SYNTAX           Float 
			   ACCESS           read-only
			   STATUS           mandatory
			   DESCRIPTION
			   "The value of this object provides the Major High alarm value
			    of the Laser Bias Current Analog parameter."
			   ::= { gx2Lm1000sAnalogEntry 37}


		lm1000smajorLowLaserCurrent         OBJECT-TYPE
			   SYNTAX           Float 
			   ACCESS           read-only
			   STATUS           mandatory
			   DESCRIPTION
			   "The value of this object provides the Major Low alarm value
			    of the Laser Bias Current Analog parameter."
			   ::= { gx2Lm1000sAnalogEntry 38}

		lm1000sminorHighLaserCurrent        OBJECT-TYPE
			   SYNTAX           Float
			   ACCESS           read-only
			   STATUS           obsolete
			   DESCRIPTION
			   "The value of this object provides the Minor High alarm value
			    of the Laser Bias Current Analog parameter.
			   This object is not used by this module and always returns invalid 
			   float value of 0xFFFFFFFF . This object is kept here for persistence."
			   ::= { gx2Lm1000sAnalogEntry 39}

		lm1000sminorLowLaserCurrent         OBJECT-TYPE
			   SYNTAX           Float 
			   ACCESS           read-only
			   STATUS           obsolete
			   DESCRIPTION
			   "The value of this object provides the Minor Low alarm value
			    of the Laser Bias Current Analog parameter.
			   This object is not used by this module and always returns invalid 
			   float value of 0xFFFFFFFF . This object is kept here for persistence."
			   ::= { gx2Lm1000sAnalogEntry 40}

		lm1000scurrentValueLaserCurrent     OBJECT-TYPE
			   SYNTAX           Float 
			   ACCESS           read-only
			   STATUS           mandatory
			   DESCRIPTION
			   "The value of this object provides the Current value
			    of the Laser Bias Current Analog parameter."
			   ::= { gx2Lm1000sAnalogEntry 41}

		lm1000sstateFlagLaserCurrent        OBJECT-TYPE
			   SYNTAX           INTEGER
								{
								hidden(1),
								read-only(2),
								updateable(3)
								}
			   ACCESS           read-only
			   STATUS           mandatory
			   DESCRIPTION
			   "The value of this object provides the state
			    of the Laser Bias Current Analog parameter.  (1-hidden	
			          2-read-only, 3-updateable)."
			   ::= { gx2Lm1000sAnalogEntry 42}

		lm1000sminValueLaserCurrent         OBJECT-TYPE
			   SYNTAX           Float
			   ACCESS           read-only
			   STATUS           mandatory
			   DESCRIPTION
			   "The value of this object provides the minimum value
			    the Laser Bias Current Analog parameter can achive."
			   ::= { gx2Lm1000sAnalogEntry 43}

		lm1000smaxValueLaserCurrent         OBJECT-TYPE
			   SYNTAX           Float
			   ACCESS           read-only
			   STATUS           mandatory
			   DESCRIPTION
			   "The value of this object provides the maximum value
			    the Laser Bias Current Analog parameter can achive."
			   ::= { gx2Lm1000sAnalogEntry 44}

		lm1000salarmStateLaserCurrent       OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Laser Bias Current Analog parameter."
			   ::= { gx2Lm1000sAnalogEntry 45}

-- New Parameter

		lm1000slabelTecCurrent              OBJECT-TYPE
			   SYNTAX           DisplayString (SIZE (0..80))
			   ACCESS           read-only
			   STATUS           optional
			   DESCRIPTION
			   "The value of this object provides the label of the
			    TEC Current Analog parameter."
			   ::= { gx2Lm1000sAnalogEntry 46}

		lm1000suomTecCurrent                OBJECT-TYPE
			   SYNTAX           DisplayString (SIZE (0..80))
			   ACCESS           read-only
			   STATUS           optional
			   DESCRIPTION
			   "The value of this object provides the Unit of Measure of the
			    TEC Current Analog parameter. The unit of measure for 
			    this parameter is mA"
			   ::= { gx2Lm1000sAnalogEntry 47}

		lm1000smajorHighTecCurrent          OBJECT-TYPE
			   SYNTAX           Float 
			   ACCESS           read-only
			   STATUS           mandatory
			   DESCRIPTION
			   "The value of this object provides the Major High alarm value
			    of the TEC Current Analog parameter."
			   ::= { gx2Lm1000sAnalogEntry 48}


		lm1000smajorLowTecCurrent           OBJECT-TYPE
			   SYNTAX           Float 
			   ACCESS           read-only
			   STATUS           mandatory
			   DESCRIPTION
			   "The value of this object provides the Major Low alarm value
			    of the TEC Current Analog parameter."
			   ::= { gx2Lm1000sAnalogEntry 49}

		lm1000sminorHighTecCurrent          OBJECT-TYPE
			   SYNTAX           Float
			   ACCESS           read-only
			   STATUS           obsolete
			   DESCRIPTION
			   "The value of this object provides the Minor High alarm value
			    of the TEC Current Analog parameter.
			   This object is not used by this module and always returns invalid 
			   float value of 0xFFFFFFFF . This object is kept here for persistence."
			   ::= { gx2Lm1000sAnalogEntry 50}

		lm1000sminorLowTecCurrent           OBJECT-TYPE
			   SYNTAX           Float 
			   ACCESS           read-only
			   STATUS           obsolete
			   DESCRIPTION
			   "The value of this object provides the Minor Low alarm value
			    of the TEC Current Analog parameter.
			   This object is not used by this module and always returns invalid 
			   float value of 0xFFFFFFFF . This object is kept here for persistence."
			   ::= { gx2Lm1000sAnalogEntry 51}

		lm1000scurrentValueTecCurrent       OBJECT-TYPE
			   SYNTAX           Float 
			   ACCESS           read-only
			   STATUS           mandatory
			   DESCRIPTION
			   "The value of this object provides the Current value
			    of the TEC Current Analog parameter."
			   ::= { gx2Lm1000sAnalogEntry 52}

		lm1000sstateFlagTecCurrent          OBJECT-TYPE
			   SYNTAX           INTEGER
								{
								hidden(1),
								read-only(2),
								updateable(3)
								}
			   ACCESS           read-only
			   STATUS           mandatory
			   DESCRIPTION
			   "The value of this object provides the state
			    of the TEC Current Analog parameter.  (1-hidden	
			          2-read-only, 3-updateable)."
			   ::= { gx2Lm1000sAnalogEntry 53}

		lm1000sminValueTecCurrent           OBJECT-TYPE
			   SYNTAX           Float
			   ACCESS           read-only
			   STATUS           mandatory
			   DESCRIPTION
			   "The value of this object provides the minimum value
			    the TEC Current Analog parameter can achive."
			   ::= { gx2Lm1000sAnalogEntry 54}

		lm1000smaxValueTecCurrent           OBJECT-TYPE
			   SYNTAX           Float
			   ACCESS           read-only
			   STATUS           mandatory
			   DESCRIPTION
			   "The value of this object provides the maximum value
			    the TEC Current Analog parameter can achive."
			   ::= { gx2Lm1000sAnalogEntry 55}

		lm1000salarmStateTecCurrent         OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the TEC Current Analog parameter."
			   ::= { gx2Lm1000sAnalogEntry 56}

-- New Parameter

		lm1000slabelModTemp           OBJECT-TYPE
			   SYNTAX           DisplayString (SIZE (0..80))
			   ACCESS           read-only
			   STATUS           optional
			   DESCRIPTION
			   "The value of this object provides the label of the
			    Module Temperature Analog parameter."
			   ::= { gx2Lm1000sAnalogEntry 57}

		lm1000suomModTemp             OBJECT-TYPE
			   SYNTAX           DisplayString (SIZE (0..80))
			   ACCESS           read-only
			   STATUS           optional
			   DESCRIPTION
			   "The value of this object provides the Unit of Measure of the
			    Module Temperature Analog parameter. The unit of measure for 
			    this parameter is degrees C"
			   ::= { gx2Lm1000sAnalogEntry 58}

		lm1000smajorHighModTemp       OBJECT-TYPE
			   SYNTAX           Float 
			   ACCESS           read-only
			   STATUS           mandatory
			   DESCRIPTION
			   "The value of this object provides the Major High alarm value
			    of the Module Temperature Analog parameter."
			   ::= { gx2Lm1000sAnalogEntry 59}


		lm1000smajorLowModTemp        OBJECT-TYPE
			   SYNTAX           Float 
			   ACCESS           read-only
			   STATUS           mandatory
			   DESCRIPTION
			   "The value of this object provides the Major Low alarm value
			    of the Module Temperature Analog parameter."
			   ::= { gx2Lm1000sAnalogEntry 60}

		lm1000sminorHighModTemp       OBJECT-TYPE
			   SYNTAX           Float
			   ACCESS           read-only
			   STATUS           mandatory
			   DESCRIPTION
			   "The value of this object provides the Minor High alarm value
			    of the Module Temperature Analog parameter."
			   ::= { gx2Lm1000sAnalogEntry 61}

		lm1000sminorLowModTemp        OBJECT-TYPE
			   SYNTAX           Float 
			   ACCESS           read-only
			   STATUS           mandatory
			   DESCRIPTION
			   "The value of this object provides the Minor Low alarm value
			    of the Module Temperature Analog parameter."
			   ::= { gx2Lm1000sAnalogEntry 62}

		lm1000scurrentValueModTemp    OBJECT-TYPE
			   SYNTAX           Float 
			   ACCESS           read-only
			   STATUS           mandatory
			   DESCRIPTION
			   "The value of this object provides the Current value
			    of the Module Temperature Analog parameter."
			   ::= { gx2Lm1000sAnalogEntry 63}

		lm1000sstateFlagModTemp       OBJECT-TYPE
			   SYNTAX           INTEGER
								{
								hidden(1),
								read-only(2),
								updateable(3)
								}
			   ACCESS           read-only
			   STATUS           mandatory
			   DESCRIPTION
			   "The value of this object provides the state
			    of the Module Temperature Analog parameter.  (1-hidden	
			          2-read-only, 3-updateable)."
			   ::= { gx2Lm1000sAnalogEntry 64}

		lm1000sminValueModTemp        OBJECT-TYPE
			   SYNTAX           Float
			   ACCESS           read-only
			   STATUS           mandatory
			   DESCRIPTION
			   "The value of this object provides the minimum value  
			    the Module Temperature Analog parameter can achive."
			   ::= { gx2Lm1000sAnalogEntry 65}

		lm1000smaxValueModTemp        OBJECT-TYPE
			   SYNTAX           Float
			   ACCESS           read-only
			   STATUS           mandatory
			   DESCRIPTION
			   "The value of this object provides the maximum value
			    the Module Temperature Analog parameter can achive."
			   ::= { gx2Lm1000sAnalogEntry 66}

		lm1000salarmStateModTemp      OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Module Temperature Analog parameter."
			   ::= { gx2Lm1000sAnalogEntry 67}

-- New Parameter

		lm1000slabelFanCurrent               OBJECT-TYPE
			   SYNTAX           DisplayString (SIZE (0..80))
			   ACCESS           read-only
			   STATUS           optional
			   DESCRIPTION
			   "The value of this object provides the label of the
			    Fan Current Analog parameter."
			   ::= { gx2Lm1000sAnalogEntry 68}

		lm1000suomFanCurrent                 OBJECT-TYPE
			   SYNTAX           DisplayString (SIZE (0..80))
			   ACCESS           read-only
			   STATUS           optional
			   DESCRIPTION
			   "The value of this object provides the Unit of Measure of the
			    Fan Current Analog parameter. The unit of measure for 
			    this parameter is mA"
			   ::= { gx2Lm1000sAnalogEntry 69}

		lm1000smajorHighFanCurrent           OBJECT-TYPE
			   SYNTAX           Float 
			   ACCESS           read-only
			   STATUS           mandatory
			   DESCRIPTION
			   "The value of this object provides the Major High alarm value
			    of the Fan Current Analog parameter."
			   ::= { gx2Lm1000sAnalogEntry 70}


		lm1000smajorLowFanCurrent            OBJECT-TYPE
			   SYNTAX           Float 
			   ACCESS           read-only
			   STATUS           mandatory
			   DESCRIPTION
			   "The value of this object provides the Major Low alarm value
			    of the Fan Current Analog parameter."
			   ::= { gx2Lm1000sAnalogEntry 71}

		lm1000sminorHighFanCurrent           OBJECT-TYPE
			   SYNTAX           Float
			   ACCESS           read-only
			   STATUS           obsolete
			   DESCRIPTION
			   "The value of this object provides the Minor High alarm value
			    of the Fan Current Analog parameter.
			   This object is not used by this module and always returns invalid 
			   float value of 0xFFFFFFFF . This object is kept here for persistence."
			   ::= { gx2Lm1000sAnalogEntry 72}

		lm1000sminorLowFanCurrent            OBJECT-TYPE
			   SYNTAX           Float 
			   ACCESS           read-only
			   STATUS           obsolete
			   DESCRIPTION
			   "The value of this object provides the Minor Low alarm value
			    of the Fan Current Analog parameter.
			   This object is not used by this module and always returns invalid 
			   float value of 0xFFFFFFFF . This object is kept here for persistence."
			   ::= { gx2Lm1000sAnalogEntry 73}

		lm1000scurrentValueFanCurrent        OBJECT-TYPE
			   SYNTAX           Float 
			   ACCESS           read-only
			   STATUS           mandatory
			   DESCRIPTION
			   "The value of this object provides the Current value
			    of the Fan Current Analog parameter."
			   ::= { gx2Lm1000sAnalogEntry 74}

		lm1000sstateFlagFanCurrent           OBJECT-TYPE
			   SYNTAX           INTEGER
								{
								hidden(1),
								read-only(2),
								updateable(3)
								}
			   ACCESS           read-only
			   STATUS           mandatory
			   DESCRIPTION
			   "The value of this object provides the state
			    of the Fan Current Analog parameter.  (1-hidden	
			          2-read-only, 3-updateable)."
			   ::= { gx2Lm1000sAnalogEntry 75}

		lm1000sminValueFanCurrent            OBJECT-TYPE
			   SYNTAX           Float
			   ACCESS           read-only
			   STATUS           mandatory
			   DESCRIPTION
			   "The value of this object provides the minimum value
			    the Fan Current Analog parameter can achive."
			   ::= { gx2Lm1000sAnalogEntry 76}

		lm1000smaxValueFanCurrent            OBJECT-TYPE
			   SYNTAX           Float
			   ACCESS           read-only
			   STATUS           mandatory
			   DESCRIPTION
			   "The value of this object provides the maximum value
			    the Fan Current Analog parameter can achive."
			   ::= { gx2Lm1000sAnalogEntry 77}

		lm1000salarmStateFanCurrent          OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Fan Current Analog parameter."
			   ::= { gx2Lm1000sAnalogEntry 78}

-- ************************ Digital parameters **********************************

		gx2Lm1000sDigitalTableIndex              OBJECT-TYPE
			   SYNTAX           INTEGER (1..2147483647)
			   ACCESS           read-only
			   STATUS           mandatory
			   DESCRIPTION
			   "The value of this object identifies the network
			    element. This index is equal to the
			    hfcCommonTableIndex for the same element."
			   ::= { gx2Lm1000sDigitalEntry 1}

-- New parameter
		lm1000slabelRfInput                	OBJECT-TYPE
			   SYNTAX       		DisplayString (SIZE (0..80))         
			   ACCESS           	read-only
			   STATUS           	optional
			   DESCRIPTION
			   "The value of this object provides the label of the
			    RF Input Control  Digital parameter."
			   ::= { gx2Lm1000sDigitalEntry 2}

		lm1000senumRfInput               		OBJECT-TYPE
			   SYNTAX       		DisplayString (SIZE (0..80))         
			   ACCESS           	read-only
			   STATUS           	optional
			   DESCRIPTION
			   "The value of this object represents the Enumeration values
			    possible for the Digital parameter. Each Enumerated values is
			    separated by a common. The first value has a enumerated value of 1."
			   ::= { gx2Lm1000sDigitalEntry 3}

		lm1000svalueRfInput                	OBJECT-TYPE
			   SYNTAX       		INTEGER
					    		{
							off(1),
							on(2)
					    		}
			   ACCESS           	read-write
			   STATUS           	mandatory
			   DESCRIPTION
			   "The value of this object is the current value of the parameter."
			   ::= { gx2Lm1000sDigitalEntry 4}

		lm1000sstateflagRfInput              OBJECT-TYPE
			   SYNTAX       		INTEGER
								{
								hidden(1),
								read-only(2),
								updateable(3)
								}
			   ACCESS           	read-only
			   STATUS           	mandatory
			   DESCRIPTION
			   "The value of this object provides the state
			    of the RF Input Control  Digital parameter.  (1-hidden	
			          2-read-only, 3-updateable)."
			   ::= { gx2Lm1000sDigitalEntry 5}

-- New parameter
		lm1000slabelOptOutput                OBJECT-TYPE
			   SYNTAX       		DisplayString (SIZE (0..80))         
			   ACCESS           	read-only
			   STATUS           	optional
			   DESCRIPTION
			   "The value of this object provides the label of the
			    Optical Output Control  Digital parameter."
			   ::= { gx2Lm1000sDigitalEntry 6}

		lm1000senumOptOutput               	      OBJECT-TYPE
			   SYNTAX          	DisplayString (SIZE (0..80))         
			   ACCESS           	read-only
			   STATUS           	optional
			   DESCRIPTION
			   "The value of this object represents the Enumeration values
			    possible for the Digital parameter. Each Enumerated values is
			    separated by a common. The first value has a enumerated value of 1."
			   ::= { gx2Lm1000sDigitalEntry 7}

		lm1000svalueOptOutput                OBJECT-TYPE
			   SYNTAX       		INTEGER
					    		{
							off(1),
							on(2)
					    		}
			   ACCESS           	read-write
			   STATUS           	mandatory
			   DESCRIPTION
			   "The value of this object is the current value of the parameter."
			   ::= { gx2Lm1000sDigitalEntry 8}

		lm1000sstateflagOptOutput            OBJECT-TYPE
			   SYNTAX      		INTEGER
								{
								hidden(1),
								read-only(2),
								updateable(3)
								}
			   ACCESS           	read-only
			   STATUS           	mandatory
			   DESCRIPTION
			   "The value of this object provides the state
			    of the the parameter.  (1-hidden, 2-read-only, 3-updateable)."
			   ::= { gx2Lm1000sDigitalEntry 9}
-- New parameter
		lm1000slabelAttnSetting               OBJECT-TYPE
			   SYNTAX         	DisplayString (SIZE (0..80))         
			   ACCESS           	read-only
			   STATUS           	optional
			   DESCRIPTION
			   "The value of this object provides the label of the
			   Attenuation Setting Digital parameter."
			   ::= { gx2Lm1000sDigitalEntry 10}

		lm1000senumAttnSetting              	OBJECT-TYPE
			   SYNTAX         	DisplayString (SIZE (0..80))         
			   ACCESS           	read-only
			   STATUS           	optional
			   DESCRIPTION
			   "The value of this object represents the Enumeration values
			    possible for the Digital parameter. Each Enumerated values is
			    separated by a common. The first value has a enumerated value of 1."
			   ::= { gx2Lm1000sDigitalEntry 11}

		lm1000svalueAttnSetting               OBJECT-TYPE
			   SYNTAX       		INTEGER
					    		{
							dB00-0(1),
							db00-5(2),
							db01-0(3),
							db01-5(4),
							db02-0(5),
							db02-5(6),
							db03-0(7),
							db03-5(8),
							db04-0(9),
							db04-5(10),
							db05-0(11),
							db05-5(12),
							db06-0(13),
							db06-5(14),
							db07-0(15),
							db07-5(16),
							db08-0(17),
							db08-5(18),
							db09-0(19),
							db09-5(20),
							db10-0(21),
							db10-5(22),
							db11-0(23),
							db11-5(24),
							db12-0(25),
							db12-5(26),
							db13-0(27),
							db13-5(28),
							db14-0(29),
							db14-5(30),
							db15-0(31)
					    		}
			   ACCESS           	read-write
			   STATUS           	mandatory
			   DESCRIPTION
			   "The value of this object is the current value of the parameter. Each step indicates a .5dB change in attenuation Its range is 0 to 15 dB"
			   ::= { gx2Lm1000sDigitalEntry 12}

		lm1000sstateflagAttnSetting           OBJECT-TYPE
			   SYNTAX         	INTEGER
								{
								hidden(1),
								read-only(2),
								updateable(3)
								}
			   ACCESS           	read-only
			   STATUS           	mandatory
			   DESCRIPTION
			   "The value of this object provides the state
			    of the the parameter. (1-hidden, 2-read-only, 3-updateable)."
			   ::= { gx2Lm1000sDigitalEntry 13}
-- New parameter
		lm1000slabelFactoryDefault            	OBJECT-TYPE
			   SYNTAX       	      DisplayString (SIZE (0..80))         
			   ACCESS           	read-only
			   STATUS           	optional
			   DESCRIPTION
			   "The value of this object provides the label of the
			    Factory Default Digital parameter."
			   ::= { gx2Lm1000sDigitalEntry 14}

		lm1000senumFactoryDefault               	OBJECT-TYPE
			   SYNTAX       	      DisplayString (SIZE (0..80))         
			   ACCESS           	read-only
			   STATUS           	optional
			   DESCRIPTION
			   "The value of this object represents the Enumeration values
			    possible for the Digital parameter. Each Enumerated values is
			    separated by a common. The first value has a enumerated value 
				of 1.."
			   ::= { gx2Lm1000sDigitalEntry 15}

		lm1000svalueFactoryDefault              OBJECT-TYPE
			   SYNTAX       		INTEGER
					    		{
							off(1),
							on(2)
					    		}
			   ACCESS           	read-write
			   STATUS           	mandatory
			   DESCRIPTION
			   "The value of this object is the current value of the parameter.
			   Return value is meaningless"
			   ::= { gx2Lm1000sDigitalEntry 16}

		lm1000sstateflagFactoryDefault        	OBJECT-TYPE
			   SYNTAX       		INTEGER
								{
								hidden(1),
								read-only(2),
								updateable(3)
								}
			   ACCESS           	read-only
			   STATUS           	mandatory
			   DESCRIPTION
			   "The value of this object provides the state
			    of the the parameter. (1-hidden, 2-read-only, 3-updateable)."
			   ::= { gx2Lm1000sDigitalEntry 17}

-- *********** STATUS *****************
		gx2Lm1000sStatusTableIndex			OBJECT-TYPE
			   SYNTAX				INTEGER (1..2147483647)
			   ACCESS				read-only
			   STATUS				mandatory
			   DESCRIPTION			
			   "The value of this object identifies the network
			    element. This index is equal to the
			    hfcCommonTableIndex for the same element."
			   ::= { gx2Lm1000sStatusEntry 1}

--New Parameter
		lm1000slabelBoot               	OBJECT-TYPE
			   SYNTAX       		DisplayString (SIZE (0..80))         
			   ACCESS           	read-only
			   STATUS           	optional
			   DESCRIPTION
			   "The value of this object provides the label of the
			    Boot Status  Status parameter."
			   ::= { gx2Lm1000sStatusEntry 2}

		lm1000svalueBoot              		OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (1-ok, 2-undetermined
			    3-warning, 4-minor, 5-major, 6-critical)."
			   ::= { gx2Lm1000sStatusEntry 3}

		lm1000sstateflagBoot     	OBJECT-TYPE
			   SYNTAX       		INTEGER
								{
								hidden(1),
								read-only(2),
								updateable(3)
								}
			   ACCESS           	read-only
			   STATUS           	mandatory
			   DESCRIPTION
			   "The value of this object provides the state
			    of the the parameter. (1-hidden, 2-read-only, 3-updateable)."
			   ::= { gx2Lm1000sStatusEntry  4}



--New Parameter
		lm1000slabelFlash               	OBJECT-TYPE
			   SYNTAX       		DisplayString (SIZE (0..80))         
			   ACCESS           	read-only
			   STATUS           	optional
			   DESCRIPTION
			   "The value of this object provides the label of the
			    Flash Status  Status parameter."
			   ::= { gx2Lm1000sStatusEntry 5}

		lm1000svalueFlash              	OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (1-ok, 2-undetermined
			    3-warning, 4-minor, 5-major, 6-critical)."
			   ::= { gx2Lm1000sStatusEntry 6}

		lm1000sstateflagFlash     	OBJECT-TYPE
			   SYNTAX       		INTEGER
								{
								hidden(1),
								read-only(2),
								updateable(3)
								}
			   ACCESS           	read-only
			   STATUS           	mandatory
			   DESCRIPTION
			   "The value of this object provides the state
			    of the the parameter. (1-hidden, 2-read-only, 3-updateable)."
			   ::= { gx2Lm1000sStatusEntry  7}

--New Parameter
		lm1000slabelFactoryDataCRC           OBJECT-TYPE
			   SYNTAX       		DisplayString (SIZE (0..80))         
			   ACCESS           	read-only
			   STATUS           	optional
			   DESCRIPTION
			   "The value of this object provides the label of the
			    Factory Data CRC Status parameter."
			   ::= { gx2Lm1000sStatusEntry 8}

		lm1000svalueFactoryDataCRC          	OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (1-ok, 2-undetermined
			    3-warning, 4-minor, 5-major, 6-critical)."
			   ::= { gx2Lm1000sStatusEntry 9}

		lm1000sstateflagFactoryDataCRC     	OBJECT-TYPE
			   SYNTAX       		INTEGER
								{
								hidden(1),
								read-only(2),
								updateable(3)
								}
			   ACCESS           	read-only
			   STATUS           	mandatory
			   DESCRIPTION
			   "The value of this object provides the state
			    of the the parameter. (1-hidden, 2-read-only, 3-updateable)."
			   ::= { gx2Lm1000sStatusEntry  10}


--New Parameter
		lm1000slabelLaserDataCRC           OBJECT-TYPE
			   SYNTAX       		DisplayString (SIZE (0..80))         
			   ACCESS           	read-only
			   STATUS           	optional
			   DESCRIPTION
			   "The value of this object provides the label of the
			    Laser Data CRC Status parameter."
			   ::= { gx2Lm1000sStatusEntry 11}

		lm1000svalueLaserDataCRC          	OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (1-ok, 2-undetermined
			    3-warning, 4-minor, 5-major, 6-critical)."
			   ::= { gx2Lm1000sStatusEntry 12}

		lm1000sstateflagLaserDataCRC     	OBJECT-TYPE
			   SYNTAX       		INTEGER
								{
								hidden(1),
								read-only(2),
								updateable(3)
								}
			   ACCESS           	read-only
			   STATUS           	mandatory
			   DESCRIPTION
			   "The value of this object provides the state
			    of the the parameter. (1-hidden, 2-read-only, 3-updateable)."
			   ::= { gx2Lm1000sStatusEntry  13}



--New Parameter
		lm1000slabelAlarmDataCrc               	      OBJECT-TYPE
			   SYNTAX       		DisplayString (SIZE (0..80))         
			   ACCESS           	read-only
			   STATUS           	optional
			   DESCRIPTION
			   "The value of this object provides the label of the
			    Alarm Data Crc parameter."
			   ::= { gx2Lm1000sStatusEntry 14}

		lm1000svalueAlarmDataCrc              		OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (1-ok, 2-undetermined
			    3-warning, 4-minor, 5-major, 6-critical)."
			   ::= { gx2Lm1000sStatusEntry 15}

		lm1000sstateflagAlarmDataCrc     	OBJECT-TYPE
			   SYNTAX       		INTEGER
								{
								hidden(1),
								read-only(2),
								updateable(3)
								}
			   ACCESS           	read-only
			   STATUS           	mandatory
			   DESCRIPTION
			   "The value of this object provides the state
			    of the the parameter. (1-hidden, 2-read-only, 3-updateable)."
			   ::= { gx2Lm1000sStatusEntry  16}

 
 --New Parameter
		lm1000slabelRFInputStatus               	      OBJECT-TYPE
			   SYNTAX       		DisplayString (SIZE (0..80))         
			   ACCESS           	read-only
			   STATUS           	optional
			   DESCRIPTION
			   "The value of this object provides the label of the
			    Alarm Data Crc parameter."
			   ::= { gx2Lm1000sStatusEntry 17}

		lm1000svalueRFInputStatus              		OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (1-ok, 2-undetermined
			    3-warning, 4-minor, 5-major, 6-critical)."
			   ::= { gx2Lm1000sStatusEntry 18}

		lm1000sstateflagRFInputStatus     	OBJECT-TYPE
			   SYNTAX       		INTEGER
								{
								hidden(1),
								read-only(2),
								updateable(3)
								}
			   ACCESS           	read-only
			   STATUS           	mandatory
			   DESCRIPTION
			   "The value of this object provides the state
			    of the the parameter. (1-hidden, 2-read-only, 3-updateable)."
			   ::= { gx2Lm1000sStatusEntry  19}        
			   
            -- ************ FACTORY DATA ****************
		gx2Lm1000sFactoryTableIndex			OBJECT-TYPE
			   SYNTAX				INTEGER (1..2147483647)
			   ACCESS				read-only
			   STATUS				mandatory
			   DESCRIPTION			
			   "The value of this object identifies the network
			    element. This index is equal to the
			    hfcCommonTableIndex for the same element."
			   ::= { gx2Lm1000sFactoryEntry 1}

		lm1000sbootControlByte          	OBJECT-TYPE
			   SYNTAX       		INTEGER
			   ACCESS           	read-only
			   STATUS           	mandatory
			   DESCRIPTION
			   "The value of this object indicates which bank the firmware
			    is currently being boot from."
			   ::= { gx2Lm1000sFactoryEntry 2}

		lm1000sbootStatusByte          	OBJECT-TYPE
			   SYNTAX       		INTEGER
			   ACCESS           	read-only
			   STATUS           	mandatory
			   DESCRIPTION
			   "This object indicates the status of the last boot.  Bit 2 = 
			   Bank 0/1 Active (0 = Bank 0, 1 = Bank 1), Bit 1 = Bank 1 Fail 
			   and Bit 0 = Bank 0 Fail (0 = Pass, 1 = Fail)"
			   ::= { gx2Lm1000sFactoryEntry 3}

		lm1000sbank1CRC          		OBJECT-TYPE
			   SYNTAX       		INTEGER
			   ACCESS           	read-only
			   STATUS           	mandatory
			   DESCRIPTION
			   "This object provides the CRC code of bank 0.  The display 
			   formate for the data is Hex."
			   ::= { gx2Lm1000sFactoryEntry 4}

		lm1000sbank2CRC          		OBJECT-TYPE
			   SYNTAX       		INTEGER
			   ACCESS           	read-only
			   STATUS           	mandatory
			   DESCRIPTION
			   "This object provides the CRC code of bank 1.The display 
			   formate for the data is Hex."
			   ::= { gx2Lm1000sFactoryEntry 5}

		lm1000sprgEEPROMByte          		OBJECT-TYPE
			   SYNTAX       		INTEGER
			   ACCESS           	read-only
			   STATUS           	mandatory
			   DESCRIPTION
			   "This object indicates if the EEPROM has been programmed"
			   ::= { gx2Lm1000sFactoryEntry 6}

		lm1000sfactoryCRC          		OBJECT-TYPE
			   SYNTAX       		INTEGER
			   ACCESS           	read-only
			   STATUS           	mandatory
			   DESCRIPTION
			   "This object provides the CRC code for the Factory data."
			   ::= { gx2Lm1000sFactoryEntry 7}

		lm1000scalculateCRC          		OBJECT-TYPE
			   SYNTAX       		INTEGER
					    		{
							factory(1),
							na(2),
							alarm(3)
					    		}
			   ACCESS           	read-only
			   STATUS           	obsolete
			   DESCRIPTION
			   "This object indicates which of the Enums will have the CRC 
			   calculated."
			   ::= { gx2Lm1000sFactoryEntry 8}

		lm1000shourMeter          		OBJECT-TYPE
			   SYNTAX       		INTEGER
			   ACCESS           	read-only
			   STATUS           	mandatory
			   DESCRIPTION
			   "This object provides the hour meter reading of the module."
			   ::= { gx2Lm1000sFactoryEntry 9}

		lm1000sflashPrgCntA          		OBJECT-TYPE
			   SYNTAX       		INTEGER
			   ACCESS           	read-only
			   STATUS           	mandatory
			   DESCRIPTION
			   "This object provides the number of times Bank 1 flash has been 
                      programmed."
			   ::= { gx2Lm1000sFactoryEntry 10}

		lm1000sflashPrgCntB          		OBJECT-TYPE
			   SYNTAX       		INTEGER
			   ACCESS           	read-only
			   STATUS           	mandatory
			   DESCRIPTION
			   "This object provides the number of times Bank 1 flash has been 
                      programmed."
			   ::= { gx2Lm1000sFactoryEntry 11}

		lm1000sflashBankARev          		OBJECT-TYPE
			   SYNTAX       		DisplayString (SIZE (0..80))
			   ACCESS           	read-only
			   STATUS           	mandatory
			   DESCRIPTION
			   "This object provides the revision of flash bank 0.  The rev is
			   2 characters."
			   ::= { gx2Lm1000sFactoryEntry 12}

		lm1000sflashBankBRev          		OBJECT-TYPE
			   SYNTAX       		DisplayString (SIZE (0..80))
			   ACCESS           	read-only
			   STATUS           	mandatory
			   DESCRIPTION
			   "This object provides the revision of flash bank 1.  The rev is
			   2 characters."
			   ::= { gx2Lm1000sFactoryEntry 13}



-- ****************************************************************
--
-- TRAP DEFINITIONS
--
--
-- Every trap generated by an HFC agents will include first 9 identical
-- fields. If particular variable is not supported in
-- particular TRAP-TYPE then default value will be returned.
--
-- DESCRIPTION will include explanation of use of generic
-- variables (trapAdditionalInfo******.)  If no
-- DESCRIPTION is given then generic variables will contain
-- default values.
--
-- *****************************************************************

-- **************************************************************************
--                        LM1000S Module traps
-- **************************************************************************
   trapLM1000SConfigChangeInteger TRAP-TYPE
       ENTERPRISE gx2Lm1000s
       VARIABLES
	       {       
		trapIdentifier,
		trapNetworkElemModelNumber,
		trapNetworkElemSerialNum,
		trapPerceivedSeverity,
		trapNetworkElemOperState,
		trapNetworkElemAlarmStatus,  
		trapNetworkElemAdminState,
		trapNetworkElemAvailStatus,
		trapText,
		trapChangedObjectId,
		trapChangedValueInteger,
		trapNETrapLastTrapTimeStamp
	       }
       DESCRIPTION
	"This trap is issued if configuration of a single variable
	 with integer type was changed (via ANY interface).  
	 TrapChangedValueInteger variable may contain current reading
	 of that variable.
	 trapPerceivedSeverity - 'indeterminate'"
  ::= 1

   trapLM1000SConfigChangeDisplayString TRAP-TYPE
       ENTERPRISE gx2Lm1000s
       VARIABLES
	       {       
		trapIdentifier,
		trapNetworkElemModelNumber,
		trapNetworkElemSerialNum,
		trapPerceivedSeverity,
		trapNetworkElemOperState,
		trapNetworkElemAlarmStatus,  
		trapNetworkElemAdminState,
		trapNetworkElemAvailStatus,
		trapText,
		trapChangedObjectId,
		trapChangedValueDisplayString,
		trapNETrapLastTrapTimeStamp
	       }
       DESCRIPTION
	"This trap is issued if configuration of a single variable
	 with DispalayString type was changed (via ANY interface).  
	 TrapChangedValueDisplayString variable may contain current reading
	 of that variable.
	 trapPerceivedSeverity - 'indeterminate'"
  ::= 2

  trapLM1000SfanCurrentAlarm TRAP-TYPE
	ENTERPRISE gx2Lm1000s
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Fan Current 
	 parameter goes out of range.
	 trapAdditionalInfoInteger variable contains current reading of 
	 the this parameter."
  ::= 3

  trapLM1000SModuleTempAlarm TRAP-TYPE
	ENTERPRISE gx2Lm1000s
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Module Temperature parameter goes out of range.
	 trapAdditionalInfoInteger variable contains current reading of 
	 the this parameter."
  ::= 4

  trapLM1000SomiOffsetAlarm TRAP-TYPE
	ENTERPRISE gx2Lm1000s
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the OMI Offset goes out of range."
  ::= 5

  trapLM1000StecCurrentAlarm TRAP-TYPE
	ENTERPRISE gx2Lm1000s
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the TEC Current parameter 
	 goes out of range.
	 trapAdditionalInfoInteger variable contains current reading of 
	 the this parameter."
  ::= 6

  trapLM1000SLaserCurrentAlarm TRAP-TYPE
	ENTERPRISE gx2Lm1000s
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Laser Current parameter 
	 goes out of range.
	 trapAdditionalInfoInteger variable contains current reading of 
	 the this parameter."
  ::= 7

  trapLM1000SLaserTempAlarm TRAP-TYPE
	ENTERPRISE gx2Lm1000s
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Laser Temp parameter 
	 goes out of range.
	 trapAdditionalInfoInteger variable contains current reading of 
	 the this parameter."
  ::= 8

  trapLM1000SLaserPowerAlarm TRAP-TYPE
	ENTERPRISE gx2Lm1000s
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Laser Power parameter 
	 goes out of range.
	 trapAdditionalInfoInteger variable contains current reading of 
	 the this parameter."
  ::= 9

  trapLM1000SFlashAlarm TRAP-TYPE
	ENTERPRISE gx2Lm1000s
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Laser Modules detects an error during
	Flash memory operations."
  ::= 10

  trapLM1000SBankBootAlarm TRAP-TYPE
	ENTERPRISE gx2Lm1000s
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Laser Modules detects an error while booting
	from bank 0 or bank 1."
  ::= 11

	trapLM1000SAlarmDataCRCAlarm TRAP-TYPE
	ENTERPRISE gx2Lm1000s
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Alarm Data CRC is incorrect."
  ::= 12

	trapLM1000SFactoryDataCRCAlarm TRAP-TYPE
	ENTERPRISE gx2Lm1000s
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Factory Data CRC is incorrect."
  ::= 13

	trapLM1000SCalDataCRCAlarm TRAP-TYPE
	ENTERPRISE gx2Lm1000s
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Cal Data CRC is incorrect."
  ::= 14


    trapLM1000SResetFacDefault TRAP-TYPE
	ENTERPRISE gx2Lm1000s
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
      DESCRIPTION
      "This trap is issued when the LM1000S resets to factory defaults"
  ::= 15

 	trapLM1000SUserRFOffAlarm TRAP-TYPE
	ENTERPRISE gx2Lm1000s
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the the User RF is turned off."
  ::= 16

	trapLM1000SUserOpticalOffAlarm TRAP-TYPE
	ENTERPRISE gx2Lm1000s
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the User Optical Power is turned off."
  ::= 17

	trapLM1000SUserSBSOffAlarm TRAP-TYPE
	ENTERPRISE gx2Lm1000s
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the User SBS is turned off."
  ::= 18

  trapLM1000SRFInputAlarm TRAP-TYPE
	ENTERPRISE gx2Lm1000s
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Laser Modules RF input parameter 
	 goes out of range.
	 trapAdditionalInfoInteger variable contains current reading of 
	 the this parameter."
  ::= 19
  
  trapLM1000SRFOverloadAlarm TRAP-TYPE
	ENTERPRISE gx2Lm1000s
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Laser Modules RF overload parameter 
	 goes out of range.
	 trapAdditionalInfoInteger variable contains current reading of 
	 the this parameter."
  ::= 20

  END
