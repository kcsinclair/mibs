----------------------------------------------
-- NOVELSAT-ROOT.mib                  --
-- MIB generated by naamab, Novelsat        --
-- Sunday, September 12, 2010 at 15:46:00   --
----------------------------------------------


NOVELSAT-ROOT-MIB DEFINITIONS ::= BEGIN
 
IMPORTS
	enterprises, MODULE-IDENTITY, OBJECT-TYPE			
		FROM SNMPv2-SMI;
	
----------------------
-- Node definitions --
----------------------
	
-- 1.3.6.1.4.1.37576
nsRoot MODULE-IDENTITY
        LAST-UPDATED "201009121500Z"
        ORGANIZATION
                "Novelsat"
        CONTACT-INFO
                "21 Ha'taasiya St.,
                Ra'anana 43654,Israel
                --------------------------
                Tel: +972-9-7889730
                Fax: +972-9-
                e-mail: info@novelsat.com, support@novelsat.com
                http://www.novelsat.com
                --------------------------
                "
        DESCRIPTION
                "Main novelsat global MIB"

        REVISION "201009121500Z"
        DESCRIPTION
                "Version 1.0.0.X"
::= { enterprises 37576 }

nsMibVersion  OBJECT-TYPE
        SYNTAX  OCTET STRING
        MAX-ACCESS  read-only
        STATUS  current
        DESCRIPTION
                "This parameter holds the current version of this propietary MIB."
        ::= { nsRoot 1 }

END
