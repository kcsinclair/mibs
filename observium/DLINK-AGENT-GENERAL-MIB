-- *****************************************************************************
-- revision 2.43
-- 2008/11/05 by King
-- [1]add agentGratuitousARPTrap.
-- *****************************************************************************
-- revision 2.42
-- 2008/10/29 
-- [1]add agentTrustHostTable.
-- [2]add ",RowStatus" in the module  BEGIN   "TruthValue,RowStatus   FROM SNMPv2-TC"
-- *****************************************************************************
-- *****************************************************************************
-- revision 2.41
-- 2008/09/22 by King
-- [1]add agentFDBMgmt and agentARPMgmt.
-- [2]add agentPORTutilizationTable agentDRAMutilizationTable agentFLASHutilizationTable
-- *****************************************************************************
-- revision 2.4
-- 2006/12/24 by Yan for DGS3400/3600
-- [1]add agentBscSwFileCtrlUnitID and agentBscSwFileIPv6Addr in agentBscSwFileTable.
-- [2]add swMultiImageCtrlTable.
-- [3]add config-as-bootup-cfg for swMultiCfgAction.
-- [4]update the description of agentBscSwFileCtrlID and swMultiImageInfoID.
-- *****************************************************************************
-- revision 2.3
-- 2005/10/24 02:20
-- remove swDualConfigInfoTable  , conflict with swMultiImageInfoTable
-- *****************************************************************************
-- revision 2.2
-- 2005/10/24 02:20
-- modify object agentBscSwFileCtrl ,change 'config-as-bootup-fw' to 'config-as-bootup and' 
--          add 'apply' selection   
-- add swDualConfigInfoTable 
-- *****************************************************************************
-- Revision 2.11 
-- 2005/9/28 
-- change object name agentMultiImageCtrlID to agentMultiImageCtrlID 
-- add swMultiCfgCurrentUsed and swMultiCfgBootUp objects

-- *****************************************************************************
-- Revision 2.1 
-- 2005/9/26 
-- modify object agentSaveCfg
-- change syntax "cfg" to "cfg-id1(2)" and "cfg-id2(3)"
-- add add agentMultiCfgMgmt subtree for dual config feature

-- *****************************************************************************
-- Revision 2.0 
-- 2005/8/4 05:33
-- added object agentDualImageStatus.
-- modify object agentSaveCfg

-- ***************************************************************************** 
-- Revision 1.93 
-- 2004/9/22 11:01 By Scott Sung
-- MAX-ACCESS of agentBscSwFileIndex is modified as read-only.

-- *****************************************************************************
-- Revision 1.92  
-- 2004/9/13 11:51
-- Remove mib object "systemSeverityControl" 
-- Add group "systemSeverityControlMgmt" in "agentBasicConfig"

-- *****************************************************************************
-- Revision 1.91  
-- 2004/7/7 16:03
-- change mib object name "systemTrapSeverity" to "systemSeverityControl" 
-- remove mib object  systemRestartTrapSeverity,saveToNVRAMTrapSeverity, fileTransferStatusChangeTrapSeverity
--  , setToFactoryDefaultTrapSeverity
-- By Chrissy

-- ***************************************************************************** 
-- Revision 1.9  
-- 2004/3/17 12:18
-- change mib module name to "AGENT-GENERAL-MIB"
-- change mib file name to "Genmgmt.mib"
-- By Chrissy

-- *****************************************************************************
-- Revision 1.83  
-- 2004/1/12 11:50 
-- Add a object 'agentBscSwFileBIncrement' in agentBscSwFileTable
-- Add group 'agentCPUutilization'
-- Add swMultiImageCtrlTable

-- *****************************************************************************
-- Revision 1.82 
-- 2003/5/14 02:11 
-- re-arrange the agentNotify subtree

-- *****************************************************************************
-- Revision 1.81 
-- 2003/3/24 03:09
-- remove  status "changed-not-save(4)"  in object agentStatusSaveCfg
-- change object  MAX-ACCESS of agentTrapManagerIpAddr  from read-only to read-write 

-- *****************************************************************************
-- Revision 1.8  
-- 2003/1/21 11:21
-- Modified  Common traps and management

-- *****************************************************************************
-- Revision 1.7
-- Copyright 2000 D-Link Inc.
-- All rights reserved.
-- Remove agentConsoleModeManager , agentSlipModeManager
-- Add Common traps management
-- *****************************************************************************


AGENT-GENERAL-MIB  DEFINITIONS ::= BEGIN

    IMPORTS
        IpAddress			        FROM RFC1155-SMI
        MODULE-IDENTITY, OBJECT-TYPE,
        Integer32		 	FROM SNMPv2-SMI
        TruthValue,RowStatus,MacAddress          FROM SNMPv2-TC
        DisplayString		FROM RFC1213-MIB      
--        AgentNotifyLevel    FROM DLINK-ID-REC-MIB      
        dlink-common-mgmt	FROM DLINK-ID-REC-MIB;        
    	
      agentGeneralMgmt MODULE-IDENTITY
	    LAST-UPDATED "0007150000Z"
	    ORGANIZATION ""
	    CONTACT-INFO
	        "http://support.dlink.com"
	    DESCRIPTION
		    "The Structure of general management information for enterprise."
        ::= {  dlink-common-mgmt 1 }
        
-- *****************************************************************************
-- Textual Conventions
-- *****************************************************************************
-- This definition may be excluded if IPv6 is not supported
Ipv6Address ::= TEXTUAL-CONVENTION
	DISPLAY-HINT "2x:"
	STATUS       current
	DESCRIPTION
		"This data type is used to model IPv6 addresses.
		This is a binary string of 16 octets in network
		byte-order."
	SYNTAX       OCTET STRING (SIZE (16))  
	
UnitList                ::= OCTET STRING(SIZE (0..3))

AgentNotifyLevel ::= TEXTUAL-CONVENTION
        STATUS  current
        DESCRIPTION
        	"Notification  leveling."
        SYNTAX  INTEGER {
        	critical(0),
        	warning(1),
        	information(2)
     }
     
    -- ****************
    -- agentBasicInfo *
    -- ****************
    agentBasicInfo          OBJECT IDENTIFIER ::= { agentGeneralMgmt 1 }
        
    agentMgmtProtocolCapability OBJECT-TYPE
        SYNTAX  INTEGER {   
                    other(1),
                    snmp-ip(2),
                    snmp-ipx(3),
                    snmp-ip-ipx(4)
                }
        MAX-ACCESS  read-only
        STATUS  current
        DESCRIPTION
            "The network management protocol(s) supported by this agent."
        ::= { agentBasicInfo 1 }


    -- *************************
    -- agentMibcapabilityTable *
    -- *************************

    agentMibCapabilityTable OBJECT-TYPE
        SYNTAX  SEQUENCE OF AgentMibCapabilityEntry
        MAX-ACCESS  not-accessible
        STATUS  current
        DESCRIPTION
            "A list of MIB capability entries supported by this agent."    
        ::= { agentBasicInfo 2 }

    agentMibCapabilityEntry OBJECT-TYPE
        SYNTAX  AgentMibCapabilityEntry
        MAX-ACCESS  not-accessible
        STATUS  current
        DESCRIPTION
            "A MIB capability entry contains objects describing a particular MIB
             supported by this agent."
        INDEX   { agentMibCapabilityIndex }
        ::= { agentMibCapabilityTable 1 }

    AgentMibCapabilityEntry ::= 
        SEQUENCE {
            agentMibCapabilityIndex
                Integer32,
            agentMibCapabilityDescr
                DisplayString,
            agentMibCapabilityVersion
                Integer32,
            agentMibCapabilityType
                INTEGER
        }

    agentMibCapabilityIndex OBJECT-TYPE
        SYNTAX  Integer32
        MAX-ACCESS  read-only
        STATUS  current
        DESCRIPTION
            "A list of agentMibCapabilityDescr entries."
        ::= { agentMibCapabilityEntry 1 }

    agentMibCapabilityDescr OBJECT-TYPE
        SYNTAX  DisplayString (SIZE (0..35))
        MAX-ACCESS  read-only
        STATUS  current
        DESCRIPTION
            "The name of the MIB supported by the agent."
        ::= { agentMibCapabilityEntry 2 }

    agentMibCapabilityVersion OBJECT-TYPE
        SYNTAX  Integer32
        MAX-ACCESS  read-only
        STATUS  current
        DESCRIPTION
            "The version of the MIB specified in this entry."
        ::= { agentMibCapabilityEntry 3 }

    agentMibCapabilityType OBJECT-TYPE
        SYNTAX  INTEGER {
                    other(1),
                    standard(2),
                    proprietary(3),
                    experiment(4)
                }
        MAX-ACCESS  read-only
        STATUS  current
        DESCRIPTION
            "The type of the MIB specified in this entry."
        ::= { agentMibCapabilityEntry 4 }


    agentStatusConsoleInUse   OBJECT-TYPE
        SYNTAX INTEGER {
               other(1),
               in-use(2),
               not-in-use(3)
               }
        MAX-ACCESS read-only
        STATUS current
        DESCRIPTION
            "This indicates whether console is currently in-use."
        ::= { agentBasicInfo 3 }

    agentStatusSaveCfg OBJECT-TYPE
        SYNTAX INTEGER {
               other(1),
               proceeding(2),
               completed(3),
               failed(4)
               }
        MAX-ACCESS read-only
        STATUS current
        DESCRIPTION
            "This indicates the status of the device configuration.
            
            other(1) - This entry is currently in use but the conditions under 
            	     which it will remain are determined by each of the following values.
            proceeding(2) - the device configuration is being currently saved into the NV-RAM.
            completed(3) - all of the device configuration parameters have been
                     saved into NV-RAM.
            failed(4) - The process to save the device configuration has failed."
        ::= { agentBasicInfo 4 }

    agentStatusFileTransfer OBJECT-TYPE
        SYNTAX  INTEGER {
                    other(1) ,
                    in-process(2),
                    invalid-file(3),
                    violation(4),
                    file-not-found(5),
                    disk-full(6),
                    complete(7),
                    time-out(8),
                    not-format(9),
                    memory-full(10)
                }
        MAX-ACCESS  read-only
        STATUS  current
        DESCRIPTION
            "The status of the firmware download control. If the value is stated as 'other', 
             the firmware has never been updated since the device was started." 
        ::= { agentBasicInfo 5 } 
 
    -- *************************
    -- agentCPUutilizationTable *
    -- *************************
    agentCPUutilization          OBJECT IDENTIFIER ::= { agentBasicInfo 6 }
    

    agentCPUutilizationIn5sec OBJECT-TYPE
        SYNTAX  Integer32
        MAX-ACCESS  read-only
        STATUS  current
        DESCRIPTION
            "The time scale is set at 5 second intervals.
             The value will be between 0%(idle) and 100%(very busy)."
        ::= { agentCPUutilization 1 }

    agentCPUutilizationIn1min OBJECT-TYPE
        SYNTAX  Integer32

        MAX-ACCESS  read-only
        STATUS  current
        DESCRIPTION
            "The time scale is set at 1 minute intervals.
             The value will be between 0%(idle) and 100%(very busy)."
        ::= { agentCPUutilization 2 }

    agentCPUutilizationIn5min OBJECT-TYPE
        SYNTAX  Integer32
        MAX-ACCESS  read-only
        STATUS  current
        DESCRIPTION
            "The time scale is set at 5 minute intervals.
             The value will be between 0%(idle) and 100%(very busy)."
        ::= { agentCPUutilization 3 }
        
   agentDualImageStatus OBJECT-TYPE
        SYNTAX  INTEGER {
                    not-supported(0) ,
                    supported(1)
                }
        MAX-ACCESS  read-only
        STATUS  current
        DESCRIPTION
            "The dual image status." 
        ::= { agentBasicInfo 7 }

-- -----------------------------------------------------------------------------
-- agentPORTutilizationTable
-- -----------------------------------------------------------------------------
    agentPORTutilizationTable OBJECT-TYPE
        SYNTAX  SEQUENCE OF AgentPORTutilizationEntry
        MAX-ACCESS  not-accessible
        STATUS  current
        DESCRIPTION
            "This table specifies the current utilization of a specified port."
        ::= { agentBasicInfo 8 }

    agentPORTutilizationEntry OBJECT-TYPE
        SYNTAX  AgentPORTutilizationEntry
        MAX-ACCESS  not-accessible
        STATUS  current
        DESCRIPTION
            "A list of information regarding the port utilization function."
        INDEX   { agentPORTutilizationProtIndex }
        ::= { agentPORTutilizationTable 1 }

    AgentPORTutilizationEntry ::=
        SEQUENCE {
            agentPORTutilizationProtIndex
                INTEGER,
            agentPORTutilizationTX
                INTEGER,
            agentPORTutilizationRX
                INTEGER,
            agentPORTutilizationUtil
                INTEGER
        }

    agentPORTutilizationProtIndex OBJECT-TYPE
        SYNTAX  INTEGER (1..65535)
        MAX-ACCESS  read-only
        STATUS  current
        DESCRIPTION
            "This object indicates the module's port number."
        ::= { agentPORTutilizationEntry 1 }

    agentPORTutilizationTX OBJECT-TYPE
        SYNTAX  INTEGER
        MAX-ACCESS  read-only
        STATUS  current
        DESCRIPTION
            "The current rate of transmitted frames on the specified port."
        ::= { agentPORTutilizationEntry 2 }

    agentPORTutilizationRX OBJECT-TYPE
        SYNTAX  INTEGER
        MAX-ACCESS  read-only
        STATUS  current
        DESCRIPTION
            "The current rate of received frames on the specified port."
        ::= { agentPORTutilizationEntry 3 }

    agentPORTutilizationUtil OBJECT-TYPE
        SYNTAX  INTEGER (0..100)
        UNITS       "%"
        MAX-ACCESS  read-only
        STATUS  current
        DESCRIPTION
            "The current percentages regarding port statistics."
        ::= { agentPORTutilizationEntry 4 }

-- -----------------------------------------------------------------------------
    agentDRAMutilizationTable OBJECT-TYPE
        SYNTAX  SEQUENCE OF AgentDRAMutilizationEntry
        MAX-ACCESS not-accessible
        STATUS  current
        DESCRIPTION
             "Information about DRAM memory."
        ::={agentBasicInfo 9}

     agentDRAMutilizationEntry OBJECT-TYPE
        SYNTAX   AgentDRAMutilizationEntry
        MAX-ACCESS not-accessible
        STATUS   current
        DESCRIPTION
            "A list of information about DRAM memory."
        INDEX {agentDRAMutilizationUnitID}
        ::={agentDRAMutilizationTable 1}

     AgentDRAMutilizationEntry ::=
        SEQUENCE {
                agentDRAMutilizationUnitID
                         INTEGER,
                agentDRAMutilizationTotalDRAM
                         INTEGER,
                agentDRAMutilizationUsedDRAM
                         INTEGER,
                agentDRAMutilization
                         INTEGER
                 }

     agentDRAMutilizationUnitID OBJECT-TYPE
        SYNTAX  INTEGER
        MAX-ACCESS read-only
        STATUS  current
        DESCRIPTION
             "Specifies the unit ID.
              If the ID equals zero, it means the current device."
        ::={ agentDRAMutilizationEntry 1 }

     agentDRAMutilizationTotalDRAM OBJECT-TYPE
        SYNTAX  INTEGER
        UNITS	"KB"
        MAX-ACCESS read-only
        STATUS current
        DESCRIPTION
            "The size of total DRAM memory."
        ::={agentDRAMutilizationEntry 2}

     agentDRAMutilizationUsedDRAM OBJECT-TYPE
        SYNTAX  INTEGER
        UNITS	"KB"
        MAX-ACCESS read-only
        STATUS current
        DESCRIPTION
            "The size of used DRAM memory."
        ::={agentDRAMutilizationEntry 3}

     agentDRAMutilization OBJECT-TYPE
        SYNTAX  INTEGER
        MAX-ACCESS read-only
        STATUS  current
        DESCRIPTION
             "The percentage of used DRAM memory of the total DRAM memory available.
              The value will be between 0% (idle) and 100% (very busy)."
        ::={agentDRAMutilizationEntry 4}

-- -----------------------------------------------------------------------------
    agentFLASHutilizationTable OBJECT-TYPE
        SYNTAX  SEQUENCE OF AgentFLASHutilizationEntry
        MAX-ACCESS not-accessible
        STATUS  current
        DESCRIPTION
             "Information about FLASH memory."
        ::={agentBasicInfo 10}

     agentFLASHutilizationEntry OBJECT-TYPE
        SYNTAX   AgentFLASHutilizationEntry
        MAX-ACCESS not-accessible
        STATUS   current
        DESCRIPTION
            "Information about FLASH memory."
        INDEX {agentFLASHutilizationUnitID}
        ::={agentFLASHutilizationTable 1}

     AgentFLASHutilizationEntry ::=
        SEQUENCE {
                 agentFLASHutilizationUnitID
                         INTEGER,
                 agentFLASHutilizationTotalFLASH
                         INTEGER,
                 agentFLASHutilizationUsedFLASH
                         INTEGER,
                 agentFLASHutilization
                         INTEGER
                 }

     agentFLASHutilizationUnitID OBJECT-TYPE
        SYNTAX  INTEGER
        MAX-ACCESS read-only
        STATUS  current
        DESCRIPTION
             "Specifies the unit ID.
              If the ID equals zero, it means the current device."
        ::={ agentFLASHutilizationEntry 1 }

     agentFLASHutilizationTotalFLASH OBJECT-TYPE
        SYNTAX  INTEGER
        UNITS	"KB"
        MAX-ACCESS read-only
        STATUS current
        DESCRIPTION
            "The total size of FLASH memory."
        ::={agentFLASHutilizationEntry 2}

     agentFLASHutilizationUsedFLASH OBJECT-TYPE
        SYNTAX  INTEGER
        UNITS	"KB"
        MAX-ACCESS read-only
        STATUS current
        DESCRIPTION
            "The size of the used FLASH memory."
        ::={agentFLASHutilizationEntry 3}

     agentFLASHutilization OBJECT-TYPE
        SYNTAX  INTEGER
        MAX-ACCESS read-only
        STATUS  current
        DESCRIPTION
             "The percentage of used FLASH memory in total FLASH memory.
              The value will be between 0% (idle) and 100% (very busy)."
        ::={agentFLASHutilizationEntry 4}


    agentSerialNumber OBJECT-TYPE
        SYNTAX DisplayString
        MAX-ACCESS read-only
        STATUS current
        DESCRIPTION
            "A textual string containing the serial number of this device."
        ::= { agentBasicInfo 12 }
 
    -- ******************
    -- agentBasicConfig *
    -- ******************
    agentBasicConfig        OBJECT IDENTIFIER ::= { agentGeneralMgmt 2 }   

    agentBscSwFileTable OBJECT-TYPE
        SYNTAX  SEQUENCE OF AgentBscSwFileEntry
        MAX-ACCESS  not-accessible
        STATUS  current
        DESCRIPTION
            "A list of MIB Basic Config entries supported files updated by this agent."    
        ::= { agentBasicConfig 1 }    
        
    agentBscSwFileEntry OBJECT-TYPE
        SYNTAX  AgentBscSwFileEntry
        MAX-ACCESS  not-accessible
        STATUS  current
        DESCRIPTION
            "A basic config entry containing objects describing a particular MIB
             supported by this agent."
        INDEX   { agentBscSwFileIndex }
        ::= { agentBscSwFileTable 1 }        

    AgentBscSwFileEntry ::=
    	SEQUENCE {
    		agentBscSwFileIndex
    			Integer32,
    		agentBscSwFileDscr
    			DisplayString,
    		agentBscSwFileAddr
    			IpAddress,
    		agentBscSwFileTransferType
    			INTEGER,
        	agentBscSwFile
        		DisplayString,
        	agentBscSwFileLocateId
        		INTEGER,
        	agentBscSwFileLoadType
        		INTEGER,
        	agentBscSwFileCtrl
        		INTEGER,
        	agentBscSwFileBIncrement
        	    	TruthValue,
        	agentBscSwFileCtrlID
        		INTEGER,
        	agentBscSwFileCtrlUnitID
        		UnitList,	
        	agentBscSwFileIPv6Addr
    			Ipv6Address
    				
		
        }

    agentBscSwFileIndex OBJECT-TYPE
    	SYNTAX	Integer32
    	MAX-ACCESS	read-only
    	STATUS	current
    	DESCRIPTION
    		"The table index for the file entry"
    	::= { agentBscSwFileEntry 1 }

    agentBscSwFileDscr OBJECT-TYPE
        SYNTAX  DisplayString  (SIZE (0..64))
        MAX-ACCESS  read-write
        STATUS  current
        DESCRIPTION
            "The description of the purpose of the software file in this entry.
	     Note: For systems which do not support change of this object, setting a value to 
	     this object will cause the system to return bad-value error messages."
        ::= { agentBscSwFileEntry 2 }
        
    agentBscSwFileAddr OBJECT-TYPE
        SYNTAX  IpAddress
        MAX-ACCESS  read-write
        STATUS  current
        DESCRIPTION
            "The IP address where the file to be downloaded is located, or the IP address
            where the file will be uploaded to."
        ::= {  agentBscSwFileEntry 3 }
            	
    agentBscSwFileTransferType OBJECT-TYPE
        SYNTAX  INTEGER {
                    other(1),
                    network-load(2),
                    out-of-band-load(3)
                }
        MAX-ACCESS  read-write
        STATUS  current
        DESCRIPTION
            "The channel through which the file will be downloaded or uploaded. 
	     Note:For systems which do not support all channels, setting a value to the unsupported
	     channel will cause the system to return bad-value error messages."
        ::= { agentBscSwFileEntry 4 }

    agentBscSwFile OBJECT-TYPE
        SYNTAX  DisplayString  (SIZE (0..128))
        MAX-ACCESS  read-write
        STATUS  current
        DESCRIPTION
            "The name of the file to be downloaded from the TFTP server, or to be uploaded
            to."
        ::= { agentBscSwFileEntry 5 }
        
     agentBscSwFileLocateId OBJECT-TYPE
        SYNTAX  INTEGER (1..16)
        MAX-ACCESS  read-write
        STATUS  current
        DESCRIPTION
            "This object describes the type of the file.
             runtime-code(1),
             log-file(2),
             cfg-file(3)
             Note: For systems which do not support change of this object, setting a value to 
             this object will cause the system to return bad-value error messages." 
        ::= { agentBscSwFileEntry 6 }
        
     agentBscSwFileLoadType OBJECT-TYPE
        SYNTAX  INTEGER {
                    other(1),
                    upload(2),
                    download(3)
                }
        MAX-ACCESS  read-write
        STATUS  current
        DESCRIPTION
        	"This object provides the user with a choice of uploading or downloading the selected file.
		 Note: For systems which do not support change of this object, setting a value to this object 
		 will cause the system to return bad-value error messages."
        ::= { agentBscSwFileEntry 7 }
                                               
     agentBscSwFileCtrl OBJECT-TYPE
        SYNTAX  INTEGER {
                    other(1),
                    inactive(2),
                    start(3),
                    delete(4),
                    config-as-bootup(5)
--                    apply(6)
                }
        MAX-ACCESS  read-write
        STATUS  current
        DESCRIPTION
            "This object gives the user the option to download runtime software. The setting will take effect 
             when the system restarts. See Note(1) below
 		  
			 Note:
			 For systems which do not support change of this object, setting a value to this object 
			 will cause the system to return bad-value error messages.
			
			start - activate firmware.
	        delete(4) - delete the firmware by indicated firmware ID.
	        config-as-bootup(5) - configured as bootup firmware by indicated 
            firmware(ID)."
--            apply(6) - apply the configuration to be the active configuration by indicated config ID."
        ::= { agentBscSwFileEntry 8 }

    agentBscSwFileBIncrement OBJECT-TYPE
        SYNTAX     TruthValue
        MAX-ACCESS read-write
        STATUS current
        DESCRIPTION
            "This object indicates whether the previous configuration will remain 
             valid or not after downloading the config file.
             True : keep valid
             False : erase. "
        ::= { agentBscSwFileEntry 9 }       

    agentBscSwFileCtrlID OBJECT-TYPE
        SYNTAX  INTEGER
        MAX-ACCESS  read-write
        STATUS  current
        DESCRIPTION
            "The section ID of firmware image or configuration file.
             A value of 0 indicates the bootup firmware image or configuration file."
        ::= { agentBscSwFileEntry 10 }

    agentBscSwFileCtrlUnitID OBJECT-TYPE
        SYNTAX   UnitList
        MAX-ACCESS  read-write
        STATUS  current
        DESCRIPTION
            "Specifies to which unit of the stack switch the firmware image will be downloaded.              
             One or more units can be set to this list. Each bit from left to right represents the 
             switch from unit ID 1 to unit ID 12.
             The list sets as NULL represents all stack switchs."
        ::= { agentBscSwFileEntry 11 }

    agentBscSwFileIPv6Addr OBJECT-TYPE
        SYNTAX  Ipv6Address
        MAX-ACCESS  read-write
        STATUS  current
        DESCRIPTION
            "The IPv6 address where the file is to be downloaded or uploaded."
        ::= {  agentBscSwFileEntry 12 }


--	agentFileTransfer OBJECT-TYPE
--		SYNTAX INTEGER {
--				other(1),
--				start(2),
--				start-and-reset(3),
--				noaction(4)
--			}
--		MAX-ACCESS read-write
--		STATUS obsolete
--		DESCRIPTION
--			"This object will execute the download or upload action. If start(2), it will
--			begin to download/upload, but no reset to follow. If start-and-reset(3), then
--			the reset will be activated after completing the download or upload. No action if(4). 
--
--			 Note:
--			 Because these functions will be limited by the support for the system in question, 
--			 some of the selected items will be invalid. When the user selects an invalid entry, 
--			 the system will respond with a bad-value status."
--		::= { agentBasicConfig 2 }
				
    agentSystemReset OBJECT-TYPE
        SYNTAX  INTEGER {
                    other(1),
                    cold-start(2),
                    warm-start(3),
                    no-reset(4)
                }
        MAX-ACCESS  read-write
        STATUS  current
        DESCRIPTION
            "This object indicates the agent system reset state. Setting this
             object to no-reset(4) has no effect. Setting this object to
             cold-start(2) or warm-start(3) will reset the agent. The agent 
             always returns to no-reset(4) when this object is read."
        ::= { agentBasicConfig 3 }

    agentRs232PortConfig OBJECT-TYPE
        SYNTAX  INTEGER  {
                    other(1),
                    console(2),
                    out-of-band(3),
					notAvail(4)
                }
        MAX-ACCESS  read-write
        STATUS  current
        DESCRIPTION
            "This object indicates the RS-232C mode once the device has restarted."
        ::= { agentBasicConfig 4 }

--    agentOutOfBandBaudRateConfig OBJECT-TYPE
--        SYNTAX  INTEGER {
--                    other(1),
--                    baudRate-2400 (2),
--                    baudRate-9600 (3),
--                    baudRate-19200(4),
--                    baudRate-38400(5),
--                    baudRate-115200(6)
--                }
--        MAX-ACCESS  read-write
--        STATUS  obsolete
--        DESCRIPTION
--            "This object allows the user to specify an out-of-band baud rate which 
--             will take effect upon system restart. 
--			 
--			 Note:
--			 Because these functions will be limited by the support for the system 
--			 in question, some of the selected items will be invalid. When the user 
--			 selects an invalid entry, the system will respond with a bad-value status.			 
--			 "
--        ::= { agentBasicConfig 5 }
        
        

     agentSaveCfg OBJECT-TYPE
        SYNTAX INTEGER {
        			other(1),
        			cfg-id1(2),
        			cfg-id2(3),
        			log(4),
        			all(5)
        		}
        MAX-ACCESS read-write
        STATUS current
        DESCRIPTION
            "This object indicates the type of save command to be executed, when saving to the NV-RAM.
             other(1) - none of the following. 
             cfg-id1(2) - save configuration ID1.
             cfg-id2(3)- save configuration ID2
             log(4) - save log.
             all(5) - save both ( active configuration & log)."
        ::= { agentBasicConfig 6 }      	                   
     

--***************************************************************************
--swMultiImageInfoTable
--***************************************************************************
    swMultiImageInfoTable OBJECT-TYPE
        SYNTAX  SEQUENCE OF SwMultiImageInfoEntry
        MAX-ACCESS  not-accessible
        STATUS  current
        DESCRIPTION
            ""
        ::= { agentBasicConfig 7 }
        
    swMultiImageInfoEntry OBJECT-TYPE
        SYNTAX  SwMultiImageInfoEntry
        MAX-ACCESS  not-accessible
        STATUS  current
        DESCRIPTION
            "A list of information about multiple image management."
        INDEX  { swMultiImageInfoID }
        ::= { swMultiImageInfoTable 1 }
      
    SwMultiImageInfoEntry ::= 
        SEQUENCE {
        	swMultiImageInfoID
        		INTEGER,
            swMultiImageVersion
                DisplayString,
            swMultiImageSize
                Integer32,
            swMultiImageUpdateTime
                DisplayString,
            swMultiImageFrom
                DisplayString,               
            swMultiImageSendUser
                DisplayString                                                 
        }
    swMultiImageInfoID OBJECT-TYPE
        SYNTAX  INTEGER
        MAX-ACCESS  read-only
        STATUS  current
        DESCRIPTION
            "The stacking section ID of the firmware image. 
             The stacking section ID = 256 * Unit ID + Image File ID."
        ::= { swMultiImageInfoEntry 1 }
             
    swMultiImageVersion OBJECT-TYPE
        SYNTAX  DisplayString  (SIZE (0..32))
        MAX-ACCESS  read-only
        STATUS  current
        DESCRIPTION
            "The recorded downloaded firmware version."
        ::= { swMultiImageInfoEntry 2 }
        
    swMultiImageSize OBJECT-TYPE
        SYNTAX  Integer32
        MAX-ACCESS  read-only
        STATUS  current
        DESCRIPTION
            "The recorded downloaded firmware size."
        ::= { swMultiImageInfoEntry 3 }

    swMultiImageUpdateTime OBJECT-TYPE
        SYNTAX  DisplayString  (SIZE (0..32))
        MAX-ACCESS  read-only
        STATUS  current
        DESCRIPTION
            "The recorded firmware updated time."
        ::= { swMultiImageInfoEntry 4 }

    swMultiImageFrom OBJECT-TYPE
        SYNTAX  DisplayString  (SIZE (0..32))
        MAX-ACCESS  read-only
        STATUS  current
        DESCRIPTION
            "The recorded IP address of the TFTP server"
        ::= { swMultiImageInfoEntry 5 }

    swMultiImageSendUser OBJECT-TYPE
        SYNTAX  DisplayString  (SIZE (0..32))
        MAX-ACCESS  read-only
        STATUS  current
        DESCRIPTION
            "The record of the user who downloaded the firmware."
        ::= { swMultiImageInfoEntry 6 }

 -- ************************************************************************************************       
    agentMultiCfgMgmt OBJECT IDENTIFIER ::= { agentBasicConfig 8 }    	
   	    
   	    
    swMultiCfgInfoTable OBJECT-TYPE
        SYNTAX  SEQUENCE OF SwMultiCfgInfoEntry
        MAX-ACCESS  not-accessible
        STATUS  current
        DESCRIPTION
            ""
        ::= { agentMultiCfgMgmt 1 }
        
    swMultiCfgInfoEntry OBJECT-TYPE
        SYNTAX  SwMultiCfgInfoEntry
        MAX-ACCESS  not-accessible
        STATUS  current
        DESCRIPTION
            "A list of information about multiple configuration files ."
        INDEX  { swMultiCfgInfoID }
        ::= { swMultiCfgInfoTable 1 }
      
    SwMultiCfgInfoEntry ::= 
        SEQUENCE {
            swMultiCfgInfoID
        	INTEGER,
            swMultiCfgVersion
                DisplayString,
            swMultiCfgSize
                Integer32,
            swMultiCFgUpdateTime
                DisplayString,
            swMultiCfgFrom
                DisplayString,               
            swMultiCfgSendUser
                DisplayString                                                 
        }
    swMultiCfgInfoID OBJECT-TYPE
        SYNTAX  INTEGER
        MAX-ACCESS  read-only
        STATUS  current
        DESCRIPTION
            "The section ID of the configuration files."
        ::= { swMultiCfgInfoEntry 1 }
             
    swMultiCfgVersion OBJECT-TYPE
        SYNTAX  DisplayString  (SIZE (0..32))
        MAX-ACCESS  read-only
        STATUS  current
        DESCRIPTION
            "The recorded downloaded configuration version."
        ::= { swMultiCfgInfoEntry 2 }
        
    swMultiCfgSize OBJECT-TYPE
        SYNTAX  Integer32
        MAX-ACCESS  read-only
        STATUS  current
        DESCRIPTION
            "The recorded downloaded configuration size(in bytes).
             "
        ::= { swMultiCfgInfoEntry 3 }

    swMultiCFgUpdateTime OBJECT-TYPE
        SYNTAX  DisplayString  (SIZE (0..32))
        MAX-ACCESS  read-only
        STATUS  current
        DESCRIPTION
            "The recorded configuration update time
            display in string format, i.e. yyyy/mon/dd hh:mm:ss."
        ::= { swMultiCfgInfoEntry 4 }

    swMultiCfgFrom OBJECT-TYPE
        SYNTAX  DisplayString (SIZE (0..32))
        MAX-ACCESS  read-only
        STATUS  current
        DESCRIPTION
            "The recorded IP address of the TFTP server."
        ::= { swMultiCfgInfoEntry 5 }

    swMultiCfgSendUser OBJECT-TYPE
        SYNTAX  DisplayString  (SIZE (0..32))
        MAX-ACCESS  read-only
        STATUS  current
        DESCRIPTION
            "The record of the user who downloaded the configuration file"
        ::= { swMultiCfgInfoEntry 6 }
        
 --*************************************************************************** 
        
    swMultiCfgCurrentUsed OBJECT-TYPE
        SYNTAX     INTEGER
        MAX-ACCESS  read-only
        STATUS  current
        DESCRIPTION
            "The indicated configuration file ID of the system currently in use."
        ::= { agentMultiCfgMgmt 2 }              
        
     swMultiCfgBootUp OBJECT-TYPE
        SYNTAX     INTEGER
        MAX-ACCESS  read-only
        STATUS  current
        DESCRIPTION
            "This object indicates the configuration file ID which will take effect upon the next reboot."
        ::= { agentMultiCfgMgmt 3 }            
 
        
        
--***************************************************************************
--swMultiCfgCtrlTable
--***************************************************************************
    swMultiCfgCtrlTable OBJECT-TYPE
        SYNTAX  SEQUENCE OF SwMultiCfgCtrlEntry
        MAX-ACCESS  not-accessible
        STATUS  current
        DESCRIPTION
            ""
        ::= { agentMultiCfgMgmt 4 }
        
    swMultiCfgCtrlEntry OBJECT-TYPE
        SYNTAX  SwMultiCfgCtrlEntry
        MAX-ACCESS  not-accessible
        STATUS  current
        DESCRIPTION
            "A list of information about multiple configuration management."
        INDEX  { swMultiCfgCtrlID }
        ::= { swMultiCfgCtrlTable 1 }
      
    SwMultiCfgCtrlEntry ::= 
        SEQUENCE {
            swMultiCfgCtrlID
        	INTEGER,                   
            swMultiCfgAction
                INTEGER                                                        
        }
    swMultiCfgCtrlID OBJECT-TYPE
        SYNTAX  INTEGER{
        	cfgId-1(1),
        	cfgId-2(2)
        }
        MAX-ACCESS  read-only
        STATUS  current
        DESCRIPTION
            "The section ID of the configuration file."
        ::= { swMultiCfgCtrlEntry 1 }
      
   swMultiCfgAction OBJECT-TYPE
        SYNTAX  INTEGER
   	     {   	     	
   	     	active(1),
   	     	delete(2),
   	     	config-as-bootup-cfg(3),
   	     	none(4)
   	     }
        MAX-ACCESS  read-write
        STATUS  current
        DESCRIPTION
            "
            	save : Save configuration to active configuration ID when the parameter is omitted.
   	    	active: Set any valid configuration to be the active configuration.
   	    	delete : Removes the configuration from the flash memory. This configuration 
   	    		 cannot be the active or current configuration file.
   	    	config-as-bootup-cfg: configured as bootup configuratation by indicated configuratation(ID)."
        ::= { swMultiCfgCtrlEntry 2 }   


--***************************************************************************
--swMultiImageCtrlTable
--***************************************************************************
--    swMultiImageCtrlTable OBJECT-TYPE
--        SYNTAX  SEQUENCE OF SwMultiImageCtrlEntry
--        MAX-ACCESS  not-accessible
--        STATUS  current
--        DESCRIPTION
--            ""
--        ::= { agentBasicConfig 8 }
        
--    swMultiImageCtrlEntry OBJECT-TYPE
--        SYNTAX  SwMultiImageCtrlEntry
--        MAX-ACCESS  not-accessible
--        STATUS  current
--        DESCRIPTION
--            "A list of information about multiple image management."
--        INDEX  { swMultiImageID }
--        ::= { swMultiImageCtrlTable 1 }
      
--    SwMultiImageCtrlEntry ::= 
--        SEQUENCE {
--        	swMultiImageCtrlID
--        		INTEGER,
--            swMultiImageSourceAddr
--                IpAddress,
--            swMultiImageFileName
--                DisplayString,        
--            swMultiImageAction
--                INTEGER                                                        
--        }
--    swMultiImageCtrlID OBJECT-TYPE
--        SYNTAX  INTEGER
--        MAX-ACCESS  read-write
--        STATUS  current
--        DESCRIPTION
--            "The section ID of firmware image."
--        ::= { swMultiImageCtrlEntry 1 }
      
--    swMultiImageSourceAddr OBJECT-TYPE
--        SYNTAX  IpAddress
--        MAX-ACCESS  read-write
--        STATUS  current
--        DESCRIPTION
--            "The IP address where the new firmware image file is located."
--        ::= { swMultiImageCtrlEntry 2 }
        
--    swMultiImageFileName OBJECT-TYPE
--        SYNTAX  DisplayString  (SIZE (0..64))
--        MAX-ACCESS  read-write
--        STATUS  current
--        DESCRIPTION
--            "The full name of the firmware image file to be downloaded."
--        ::= { swMultiImageCtrlEntry 3 }
        
--    swMultiImageAction OBJECT-TYPE
--		SYNTAX  INTEGER {
--               other(1),
--               update(2),
--               delete(3),
--               config-as-bootup-fw(4)
--               }
--        MAX-ACCESS  read-write
--        STATUS  current
--        DESCRIPTION
--            "This object indicates the status of multiImageTable actions. 

--            other(1) - .
--            update(2) - download firmware to indicated section.
--            delete(3) - delete the firmware by indicated firmware ID.
--            config-as-bootup-fw(4) - configured as bootup firmware by indicated firmware(ID)."
--        ::= { swMultiImageCtrlEntry 4 }   

-- ******************************************************************************************	
-- Add common severity control management
-- ******************************************************************************************	
      
   systemSeverityControlMgmt	OBJECT IDENTIFIER ::= { agentBasicConfig 9 }  	

    systemSeverityTrapControl OBJECT-TYPE
        SYNTAX  AgentNotifyLevel 
        MAX-ACCESS  read-write
        STATUS  current
        DESCRIPTION
            "Indicates the level of trap severity control. The system has a severity level control 
             and each trap should have a severity control set. When trap events occur and its severity 
             is higher than the system severity control level, the trap works as defined. If the event 
             severity is lower than the system severity control level, the event is ignored as if it 
             did not occur."
        ::= { systemSeverityControlMgmt 1 }                
        
    systemSeverityLogControl OBJECT-TYPE
        SYNTAX  AgentNotifyLevel 
        MAX-ACCESS  read-write
        STATUS  current
        DESCRIPTION
            "Indicates the level of trap severity control. The system has a severity level control and 
             each trap should have a severity control set. When trap events occur and its severity is 
             higher than the system severity control level, the trap works as defined. If the event 
             severity is lower than the system severity control level, the event is ignored as if 
             it did not occur."
        ::= { systemSeverityControlMgmt 2 }   

-- -----------------------------------------------------------------------------
-- agentTrustHostMgmt
-- -----------------------------------------------------------------------------
    agentTrustHostMgmt       OBJECT IDENTIFIER ::= { agentBasicConfig 10 }

    agentTrustHostTable OBJECT-TYPE
        SYNTAX  SEQUENCE OF AgentTrustHostEntry
        MAX-ACCESS  not-accessible
        STATUS  current
        DESCRIPTION
            "This table contains Trust Host information."
        ::= { agentTrustHostMgmt 1 }

    agentTrustHostEntry OBJECT-TYPE
        SYNTAX  AgentTrustHostEntry
        MAX-ACCESS  not-accessible
        STATUS  current
        DESCRIPTION
            "A list of information about Trust Host."
        INDEX  { agentTrustHostIndex }
        ::= { agentTrustHostTable 1 }

    AgentTrustHostEntry ::=
        SEQUENCE {
            agentTrustHostIndex
                INTEGER,
            agentTrustHostIPAddress
                IpAddress,
            agentTrustHostRowStatus
                RowStatus,
            agentTrustHostIPSubnetMask
                IpAddress
        }

    agentTrustHostIndex OBJECT-TYPE
        SYNTAX  INTEGER (1..10)
        MAX-ACCESS  read-only
        STATUS  current
        DESCRIPTION
            "The index of Trust Host entry."
        ::= { agentTrustHostEntry 1 }

    agentTrustHostIPAddress OBJECT-TYPE
        SYNTAX  IpAddress
        MAX-ACCESS  read-create
        STATUS  current
        DESCRIPTION
            "Specifies the IP address of the Trust Host."
        ::= { agentTrustHostEntry 2 }

    agentTrustHostRowStatus OBJECT-TYPE
        SYNTAX  RowStatus
        MAX-ACCESS  read-create
        STATUS  current
        DESCRIPTION
            "Indicates the status of this entry. When creating a Trust Host
             entry, the IP address should too be set."
        ::= { agentTrustHostEntry 3 }

    agentTrustHostIPSubnetMask OBJECT-TYPE
        SYNTAX  IpAddress
        MAX-ACCESS  read-create
        STATUS  current
        DESCRIPTION
            "Specifies the IP subnet mask of the Trust Host."
        ::= { agentTrustHostEntry 4 }
   -- -----------------------------------------------------------------------------
-- agentTrustHostDelAllState
-- -----------------------------------------------------------------------------
    agentTrustHostDelAllState OBJECT-TYPE
        SYNTAX	INTEGER{
			    		none(1),
			    		start(2)
			    		}
        MAX-ACCESS  read-write
        STATUS      current
        DESCRIPTION
            "Used to delete all Trust Host entries."
        ::= { agentTrustHostMgmt 2 }
     
-- -----------------------------------------------------------------------------
-- agentFDBMgmt
-- -----------------------------------------------------------------------------
    agentFDBMgmt       OBJECT IDENTIFIER ::= { agentBasicConfig 11 }
    agentFDBClearAllState OBJECT-TYPE
        SYNTAX  INTEGER{
    		other(1),
    		start(2)
    		}
        MAX-ACCESS  read-write
        STATUS  current
        DESCRIPTION
            "Used to clear all FDB entries."
        ::= { agentFDBMgmt 1 }

-- -----------------------------------------------------------------------------
-- agentARPMgmt
-- -----------------------------------------------------------------------------
    agentARPMgmt       OBJECT IDENTIFIER ::= { agentBasicConfig 12 }
    agentARPClearAllState OBJECT-TYPE
        SYNTAX  INTEGER{
    		other(1),
    		start(2)
    		}
        MAX-ACCESS  read-write
        STATUS  current
        DESCRIPTION
            "Used to clear all ARP entries."
        ::= { agentARPMgmt 1 }

 agentGratuitousARPMgmt  OBJECT IDENTIFIER ::={agentARPMgmt 2}

      agentGratuitousARPSendIpifStatusUpState OBJECT-TYPE
        SYNTAX  INTEGER{
                   enabled(1),
                   disabled(2)
                }
        MAX-ACCESS read-write
        STATUS  current
        DESCRIPTION
              "It is used to enable/disable sending of gratuitous ARP request
              packet while IPIF interface become up,this is used to automatically
              announce the interface's IP addressto other nodes. By default,
               the state is enabled, and only one ARP packet will be broadcast."
       DEFVAL { enabled }
         ::={ agentGratuitousARPMgmt 1}

      agentGratuitousARPSendDupIpDetectedState OBJECT-TYPE
       SYNTAX INTEGER{
                      enabled(1),
                      disabled(2)
                     }
         MAX-ACCESS read-write
         STATUS  current
         DESCRIPTION
               "It is used to enable/disable sending of gratuitous ARP request
                packet while duplicate IP is detected. By default, the state is enabled,
                the duplicate IP detected means that the system received a ARP request
                packet that is sent by an IP address that match the system's own IP address.
                In this case, the system knows that some body out there use a IP address
                that is conflict with the system. In order to reclaim the correct host
                of this IP address, the system can send out the gratuitous ARP request
                packet for this duplicate IP address."
        DEFVAL { enabled }
         ::={ agentGratuitousARPMgmt 2}

      agentGratuitousARPLearningState OBJECT-TYPE
       SYNTAX INTEGER{
                      enabled(1),
                      disabled(2)
                     }
         MAX-ACCESS read-write
         STATUS  current
         DESCRIPTION
                  "It is used to enable/disable learning of ARP entry in ARP
                  cache based on the received gratuitous ARP packet,If switch
                  receives a gratuitous arp request/reply packet and the sender's
                  IP address in its ARP table.it should update the ARP entry.
                   By default, the state is disabled."
         DEFVAL { disabled }
         ::={ agentGratuitousARPMgmt 3}

      agentGratuitousARPTable OBJECT-TYPE
         SYNTAX SEQUENCE OF AgentGratuitousARPEntry
         MAX-ACCESS not-accessible
         STATUS current
         DESCRIPTION
           "Some information of Gratuitous ARP Table."
         ::={ agentGratuitousARPMgmt 4}

      agentGratuitousARPEntry OBJECT-TYPE
        SYNTAX  AgentGratuitousARPEntry
        MAX-ACCESS not-accessible
        STATUS current
        DESCRIPTION
            "a list of information of Gratuitous ARP Table."
        INDEX {
                 agentGratuitousARPInterfaceName
              }
        ::={ agentGratuitousARPTable 1 }

       AgentGratuitousARPEntry ::=
          SEQUENCE {
                     agentGratuitousARPInterfaceName
                          DisplayString,
                     agentGratuitousARPPeriodicalSendInterval
                            INTEGER,
                       agentGratuitousARPTrapState
                            INTEGER,
                       agentGratuitousARPLogState
                            INTEGER
                   }

       agentGratuitousARPInterfaceName  OBJECT-TYPE
            SYNTAX  DisplayString
            MAX-ACCESS read-only
            STATUS  current
            DESCRIPTION
               "The name of the IP interface ."
            ::={agentGratuitousARPEntry 1}

          agentGratuitousARPPeriodicalSendInterval OBJECT-TYPE
               SYNTAX  INTEGER (0..65535)
               UNITS        "seconds"
               MAX-ACCESS read-write
               STATUS  current
               DESCRIPTION
                 "It is used to configure the interval for periodical sending of
                 gratuitous ARP request packet.
                 0 means not send gratuitous ARP periodically."
               DEFVAL { 0 }
                ::={agentGratuitousARPEntry  2}

         agentGratuitousARPTrapState   OBJECT-TYPE
               SYNTAX  INTEGER{
                             enabled(1),
                             disabled(2)
                             }
               MAX-ACCESS read-write
               STATUS  current
               DESCRIPTION
                    "It indicates the state of gratuitous ARP trap, the switch can
                    trap the IP conflict event to inform the administrator.
                     By default, trap is disabled ."
                 DEFVAL { disabled }
                ::={agentGratuitousARPEntry 3}

         agentGratuitousARPLogState OBJECT-TYPE
               SYNTAX  INTEGER{
                             enabled(1),
                             disabled(2)
                             }
               MAX-ACCESS read-write
               STATUS  current
               DESCRIPTION
                    "It indicates the state of gratuitous Log trap,the switch can
                     log the IP conflict event to inform the administrator.
                     By default,event log is enabled."
               DEFVAL { enabled }
                ::={agentGratuitousARPEntry 4}
                
--***************************************************************************
--swMultiImageCtrlTable
--***************************************************************************
    swMultiImageCtrlTable OBJECT-TYPE
        SYNTAX  SEQUENCE OF SwMultiImageCtrlEntry
        MAX-ACCESS  not-accessible
        STATUS  current
        DESCRIPTION
            ""
        ::= { agentBasicConfig 13 }
      
    swMultiImageCtrlEntry OBJECT-TYPE
        SYNTAX  SwMultiImageCtrlEntry
        MAX-ACCESS  not-accessible
        STATUS  current
        DESCRIPTION
            "A list of information about multiple image management."
        INDEX  { swMultiImageCtrlID }
        ::= { swMultiImageCtrlTable 1 }
    
    SwMultiImageCtrlEntry ::= 
        SEQUENCE {
        	swMultiImageCtrlID
        		INTEGER, 
            	swMultiImageCtrlAction
                	INTEGER                                                        
        	}  
 
    swMultiImageCtrlID OBJECT-TYPE
        SYNTAX  INTEGER
        MAX-ACCESS  read-only
        STATUS  current
        DESCRIPTION
            "The stacking section ID Of the firmware image. 
             The stacking section ID = 256 * Unit ID + Image File ID."
        ::= { swMultiImageCtrlEntry 1 }   

    swMultiImageCtrlAction OBJECT-TYPE
        SYNTAX  INTEGER{
        	config-as-bootup-fw(1),
        	delete(2),
        	none(3)
        	}
        MAX-ACCESS  read-write
        STATUS  current
        DESCRIPTION
            "This object indicates the running status of the image which is 
             specified by the swMultiImageCtrlID and swMultiImageCtrlUnitID.
             
             config-as-bootup-fw(1) - configured as bootup firmware by indicated firmware(ID).
             delete(2) - delete the firmware by indicated firmware ID.
             none(3) - no action.
             "
        ::= { swMultiImageCtrlEntry 2 }
                                                      
--***************************************************************************
--swDualConfigInfoTable
--***************************************************************************
                  
                       
                       
    -- ***********************
    -- agentIpProtocolConfig *
    -- ***********************
    agentIpProtoConfig      OBJECT IDENTIFIER ::= { agentGeneralMgmt 3 }

    agentIpNumOfIf OBJECT-TYPE
        SYNTAX  Integer32
        MAX-ACCESS  read-only
        STATUS  current
        DESCRIPTION
            "The total number of IP interfaces supported by this agent."
        ::= {  agentIpProtoConfig 1 }

--    agentIpTftpServerAddr OBJECT-TYPE
--        SYNTAX  IpAddress
--        MAX-ACCESS  read-write
--        STATUS  obsolete
--        DESCRIPTION
--            "The IP Address of TFTP Server."
--        ::= {  agentIpProtoConfig 2 }
	
    agentIpGetIpFrom OBJECT-TYPE
        SYNTAX  INTEGER {
                    other(1),
                    disabled(2),
                    bootp(3),
                    dhcp(4)
                }
        MAX-ACCESS  read-write
        STATUS  current
        DESCRIPTION
            "This object indicates if the agent gets its system IP address
             from Bootp/DHCP server at start up."
        ::= { agentIpProtoConfig 3 }	

	-- End of agentIpIfTable ---------        
    -- ************************
    -- agentIptrapMangerTable *
    -- ************************

--	agentIpTrapManager	OBJECT IDENTIFIER ::= { agentGeneralMgmt 4 }
	
--    agentIpTrapManagerTable OBJECT-TYPE-
--        SYNTAX  SEQUENCE OF AgentIpTrapManagerEntry
--        MAX-ACCESS  not-accessible
--        STATUS  current
--        DESCRIPTION
--            "A list of trap managers to which SNMP traps will be sent."
--        ::= {  agentIpTrapManager 1 }

--    agentIpTrapManagerEntry OBJECT-TYPE
--        SYNTAX  AgentIpTrapManagerEntry
--        MAX-ACCESS  not-accessible
--        STATUS  obsolete
--        DESCRIPTION
--            "Each entry contains the particular trap manager settings."
--        INDEX   { agentIpTrapManagerIpAddr }
--        ::= { agentIpTrapManagerTable 1 }

-- *****************************************************************************
--
-- *****************************************************************************
        
--    agentTrapManagerTable OBJECT-TYPE
--        SYNTAX  SEQUENCE OF AgentTrapManagerEntry
--        MAX-ACCESS  not-accessible
--        STATUS  current
--        DESCRIPTION
--            "A list of trap managers to which SNMP traps will be sent."
--        ::= {  agentIpTrapManager 2 }
--
--    agentTrapManagerEntry OBJECT-TYPE
--        SYNTAX  AgentTrapManagerEntry
--        MAX-ACCESS  not-accessible
--        STATUS  current
--        DESCRIPTION
--            "Each entry contains the particular trap manager settings."
--        INDEX   { agentTrapManagerIndex }
--        ::= { agentTrapManagerTable 1 }
--
--    AgentTrapManagerEntry ::= 
--        SEQUENCE {
--				    agentTrapManagerIndex
--				        INTEGER,
--                    agentTrapManagerIpAddr
--                        IpAddress,
--                    agentTrapManagerComm
--                        DisplayString,
--                    agentTrapManagerMsgVer
--                        INTEGER,
--                    agentTrapManagerStatus
--                        INTEGER
--        }
--
--	agentTrapManagerIndex  OBJECT-TYPE
--	    SYNTAX     INTEGER (1..65535)
--	    MAX-ACCESS not-accessible
--	    STATUS     current
--	    DESCRIPTION
--	        "A value that uniquely identifies this trapDestEntry."
--	    ::= { agentTrapManagerEntry 1 }
--    
--    agentTrapManagerIpAddr OBJECT-TYPE
--        SYNTAX  IpAddress
--        MAX-ACCESS  read-write
--        STATUS  current
--        DESCRIPTION
--            "The IP address where SNMP traps will be destined for"
--        ::= { agentTrapManagerEntry 2 }
--
--    agentTrapManagerComm OBJECT-TYPE
--        SYNTAX  DisplayString (SIZE (0..20))
--        MAX-ACCESS  read-write
--        STATUS  current
--        DESCRIPTION
--            "The community string used to encode SNMP trap packets to be sent to the trap
--             manager."
--        ::= { agentTrapManagerEntry 3 }
--        
--    agentTrapManagerMsgVer OBJECT-TYPE
--        SYNTAX  INTEGER {
--                    snmpAgentVersionDependent(1),
--                    v1Trap(2),
--                    v2Trap(3)
--                }
--        MAX-ACCESS  read-write
--        STATUS  current
--        DESCRIPTION
--            "This object indicates the version of trap packets to be sent to
--             this trap manager. The default setting is SNMPAgentVersionDependent .
--             
--			 Note:
--			 Because some of these functions will be limited by the support of 
--			 the system in question, some selected items may be invalid. If one 
--			 of these items is selected a bad value error message will be prompted
--			 to the user,	             "
--        ::= { agentTrapManagerEntry 4 }               
--
--    agentTrapManagerStatus OBJECT-TYPE
--        SYNTAX  INTEGER {
--                    other(1),
--                    disabled(2),
--                    enabled(3)
--                }
--        MAX-ACCESS  read-write
--        STATUS  current
--        DESCRIPTION
--            "This object indicates whether or not the trap should be sent to
--             this trap manager."
--        ::= { agentTrapManagerEntry 5 }	          
        

--
-- Add for Slip_Console mode swtich 11-9-2001 WindChen
--
--	agentConsoleModeManager	OBJECT IDENTIFIER ::= { agentGeneralMgmt 5 }
	

        
--
-- Slip Mode Manager
--	
--	agentSlipModeManager	OBJECT IDENTIFIER ::= { agentGeneralMgmt 6 }


        

-- ******************************************************************************************	
-- Add common trap management 
-- ******************************************************************************************	
     
        
	agentNotify	OBJECT IDENTIFIER ::= { agentGeneralMgmt 7 }  
	  
	  
	  
--	agentNotifMgmt      OBJECT IDENTIFIER ::= { agentNotify 1 }  
	agentNotifFirmware   OBJECT IDENTIFIER ::= { agentNotify 2 }  
	
	
	
	agentNotifyPrefix OBJECT IDENTIFIER ::= { agentNotifFirmware 0 }  

	

	
-- ******************************************************************************************	
--	agentNotifMgmt
-- ******************************************************************************************

--  systemSeverityControl OBJECT-TYPE
--      SYNTAX  AgentNotifyLevel 
--      MAX-ACCESS  read-write
--      STATUS  current
--      DESCRIPTION
--          "Indicates the level of trap severity control. The system has a severity level control 
--           and each trap should have a severity control set. When trap events occur and its severity 
--           is higher than the system severity control level, the trap works as defined. If the event 
--           severity is lower than the system severity control level, the event is ignored as if it did not occur. 
--	"
--      ::= { agentNotifMgmt 1 }

--	notifFirmwareMgmt OBJECT IDENTIFIER ::= { agentNotifMgmt 2 }  
     
-- ******************************************************************************************	

       
        
   	

-- ******************************************************************************************        

-- agentNotifFirmware OBJECT IDENTIFIER ::= { agentNotifyPrefix 0 }

-- ******************************************************************************************	
--	agentNotifFirmware
-- ******************************************************************************************
	
--    agentsystemRestart NOTIFICATION-TYPE
--        OBJECTS {
--              trapInfosystemRestart
--        		}
--        STATUS  current        		
--        DESCRIPTION
--            "This trap contains reboot information."
--
--		::= { agentNotifyPrefix 1 }          
        
		
--    agentSaveToNVRAM NOTIFICATION-TYPE
--        OBJECTS         { unitID
--                        }        
--        STATUS  current
--        DESCRIPTION
--            "The trap is sent whenever save all configuration of device to NV-RAM has been processed . "
--             
--        ::= { agentNotifyPrefix 2 }    
        
--    agentFileTransferStatusChange NOTIFICATION-TYPE
--        OBJECTS         { 
--        					unitID,
--                          agentStatusFileTransfer
--                        }
--        STATUS          current
--        DESCRIPTION     "File transfer status change notification."
--        ::= { agentNotifyPrefix 3 }	
        
--    agentSetToFactoryDefault NOTIFICATION-TYPE
--        OBJECTS         { unitID
--                        }        
--        STATUS  current
--        DESCRIPTION
--            "The trap is sent whenever the 'set to factory default' setting has been processed . "
--             
--        ::= { agentNotifyPrefix 4 }           
        
    agentGratuitousARPTrap  NOTIFICATION-TYPE
        OBJECTS   {

                    agentGratuitousARPIpAddr,
                    agentGratuitousARPMacAddr,
                    agentGratuitousARPPortNumber,
                    agentGratuitousARPInterfaceName
                  }
        STATUS  current
        DESCRIPTION
           "This trap is sent when there is an IP address conflict."
        ::={agentNotifyPrefix 5}

-- ******************************************************************************************	
--	agentNotifEquipment
-- ******************************************************************************************        
   
      
-- ******************************************************************************************	
--	notificationBidings
-- ******************************************************************************************        		 
	 
    notificationBidings OBJECT IDENTIFIER ::= { agentNotifFirmware 1 }
                
--    unitID OBJECT-TYPE
--        SYNTAX     INTEGER
--        MAX-ACCESS accessible-for-notify
--        STATUS     current
--        DESCRIPTION
--            "The Unit ID of the device which triggered the event"
--        ::= { notificationBidings 1 }                          
        
           	        
--    trapInfosystemRestart   OBJECT-TYPE
--        SYNTAX  DisplayString (SIZE (0..64))
--        MAX-ACCESS  read-only
--        STATUS  current
--        DESCRIPTION
--            "This object indicates the last time the device rebooted.
--            "
--        ::= { notificationBidings 2 }         
	 
    agentGratuitousARPIpAddr       OBJECT-TYPE
       SYNTAX      IpAddress
       MAX-ACCESS  accessible-for-notify
        STATUS  current
        DESCRIPTION
           "A duplicate IP address with the switch already exists."
        ::={notificationBidings 3}

    agentGratuitousARPMacAddr     OBJECT-TYPE
       SYNTAX    MacAddress
       MAX-ACCESS accessible-for-notify
        STATUS  current
        DESCRIPTION
           "This object is the MAC address of the device which has the duplicate IP address."
        ::={notificationBidings 4}

   agentGratuitousARPPortNumber   OBJECT-TYPE
        SYNTAX   DisplayString
        MAX-ACCESS accessible-for-notify
        STATUS  current
        DESCRIPTION
            "This indicates the portNum with a string.
             For example, if the device is in standalone mode, and the port
             number is 23, the string should be 23.
             If the device is in stacking mode, and the unit ID is 2, and the
             port number is 3, the string should be 2:3.
	    "
        ::={notificationBidings 5}   
	        
END
