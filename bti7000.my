------------------------------------------------------------------------
------------------------------------------------------------------------
--
-- Copyright (C) BTI Systems Inc. 2003-2010. All Rights Reserved.
--
-- The information contained herein is the property of BTI Systems Inc.
-- and is strictly confidential. Except as expressly authorized in
-- writing by BTI Systems Inc., the holder shall keep all information
-- contained herein confidential, shall disclose the information only
-- to its employees with a need to know, and shall protect the
-- information, in whole or in part, from disclosure and dissemination
-- to third parties with the same degree of care it uses to protect
-- its own confidential information, but with no less than reasonable
-- care. Except as expressly authorized in writing by BTI Systems Inc.,
-- the holder is granted no rights to use the information contained
-- herein.
--
-- Unpublished. All rights reserved under the copyright laws of
-- Canada.
-- 
-- OSS Integration 
-- BTI Systems Inc. can provide customers with direct access to 
-- network element SNMP MIBs for use for integration to OSS systems. 
-- Customers must note the following caveats:
--
-- 1) Performance: The BTI Systems Inc. MIBS are performance tested for
-- use with the BTI Systems proNX 900 Node Controller and proNX 9000 
-- Network Manager. Customers are responsible for conducting their 
-- own testing to ensure that the BTI Systems Inc. NE interfaces meet 
-- the needs of their proposed usage. BTI Systems Inc. makes no
-- guarantees that any proposed usage will meet customer requirements.
--
-- 2) Changes between releases: BTI Systems Inc. SNMP MIBs are subject 
-- to change as support for new functionality is introduced. BTI  
-- Systems Inc. strives to maintain backward compatibility of MIBs 
-- across releases but this is not guaranteed and BTI Systems Inc. 
-- reserves the right to deprecate or remove support for obsolete 
-- MIB elements. OSS integrators must be careful not to rely on 
-- functionality that is marked as deprecated as it may be unsupported 
-- in a subsequent release. Customers that integrate directly to BTI 
-- Systems Inc. MIBs are responsible for all OSS development and 
-- integration testing that may arise from MIB changes between releases 
-- of BTI Systems Inc. software.
--
------------------------------------------------------------------------
------------------------------------------------------------------------

BTI-7000-MIB DEFINITIONS ::= BEGIN

IMPORTS
    MODULE-IDENTITY, OBJECT-TYPE, NOTIFICATION-TYPE, IpAddress, Gauge32,
    Integer32, Unsigned32
        FROM SNMPv2-SMI
    TEXTUAL-CONVENTION, DateAndTime, DisplayString, MacAddress, TruthValue,
    RowStatus
        FROM SNMPv2-TC
    btiModules, bti7000
        FROM BTI-MIB
    FixedX10, FixedX100, ShelfType, ShelfConfigType, SlotType, CpType,
    OaType, XcvrType, AmdType, AmdPortType, CondReportType, CondSeverity,
    CondServiceAffecting, FiberType, WDMGrid, TimeZone,
    AdminStatus, OperStatus, OperStatQlfr, HoursAndMinutes, PassivePortType,
    XcvrProtocolType, PMIntervalType, PMValidity, BERType, ProtSwEvtType,
    OcnType, StsnType, StmnType, VcnType, MediaRateType, DuplexModeType,
    XCType, ProtectionStatusType, Unsigned64, PMMontype, UpgradeCompleteStage,
    ProtSwOpCmd, InitializeCmd, OdunType, SwitchIdxType,
    PvxL1PortType,PvxPortType,PowerFeedModeType, SyncSwEvtType,
    NotifObjectType, NotifCodeType, AreaID, DesignatedRouterPriority,
    InetAddressType, InetAddress, EnvNotifCodeType, MirrorConfigType, LoopbackType,
    LldpChassisIdSubtype, LldpChassisId, LldpPortIdSubtype, LldpPortId
        FROM BTI-TC-MIB;

bti7000Mib MODULE-IDENTITY
    LAST-UPDATED "201210091200Z"  -- Tuesday, October 09, 12:00:00 EST 2012
    ORGANIZATION "BTI Systems Inc."
    CONTACT-INFO "Technical Support
                  BTI Systems Inc.
                  200-1000 Innovation Drive
                  Kanata, Ontario, Canada, K2K 3E7
                  (613) 287-1700
                  support@btisystems.com"
    DESCRIPTION  "The external MIB definitions for the BTI 7000 series
                  products."
    REVISION     "201210091200Z"  -- Tuesday, October 09, 12:00:00 EST 2012
    DESCRIPTION  "MIB Updates for BTI 7000 Rel 10.3.0:
                 - added ethIntfLldpAdminStatus"
    REVISION     "201208291200Z"  -- Wednesday, August 29, 12:00:00 EST 2012
    DESCRIPTION  "MIB Updates for BTI 7000 Rel 10.2.0:
                 - added missing import of LoopbackType"
    REVISION     "201202101200Z"  -- Friday, February 10, 12:00:00 EST 2012
    DESCRIPTION  "MIB Updates for BTI 7000 Rel 9.2.0:
                 - neAutoDeProv object status changed to obsolete
                 - in support of Remote ID feature, added new objects oaRemoteId
                   xcvrRemoteId, passivePortRemoteId, ocnRemoteId, stmnRemoteId,
                   geRemoteId, feRemoteId, fcRemoteId, ethIntfRemoteId, briRemoteId
                 - added new xcvrLoopbackType object
                 - added new value oprTerminalLpbk to xcvrLpbkOpCmd object
                 - added new tl1LogTable and latestTl1LogNum object
                 - deprecated pvxL2IntfIngressFiltering field in pvxL2IntfTable
                 - added new objects pvxL2IntfBcastLimit, pvxL2IntfMcastLimit, and
                   pvxL2IntfDlfLimit
                 - cpDbApplyResultEvt trap status changed to obsolete
                 - added new traps xcvrLFCond and xcvrLFClear"
    REVISION     "201109261200Z"  -- Monday, September 26, 12:00:00 EST 2011
    DESCRIPTION  "MIB Updates for BTI 7000 Rel 9.1.0:
                 - added opticalLayer branch for all dynamic optical layer
                   managament objects
                 - added slotInvDataTable
                 - expanded value range of cpShelfIdx and cpSlotIdx to
                   support provisioning of D40MD modules
                 - added cpDegradeCond and cpDegradeClear traps
                 - added tl1LogTable"
    REVISION     "201104261200Z"  -- Tuesday, April 26, 12:00:00 EST 2011
    DESCRIPTION  "MIB Updates for BTI 7000 Rel 8.2.0:
                 - added eptree and evptree to pvxEthSrvcType to support 
                   ETREE services
                 - added pvxSrvsUNIForwarding to PvxServiceUNIEntry to 
                   support ETREE services
                 - added attributes to the PVXSwitchModule and PVXSwitchMember
                   tables to support stacking
                 - port numbering changes on multiple tables: Static Multicast,
                   Static Unicast, Multicast Group, MSTPXstTable
                 - added pvxLGMaxLinks to support Active/Standby LAG
                 - added service-Map to pvxClassMapType to support per-flow
                   services
                 - added pvxSrvcUNIServiceMap and pvxSrvcUNIFilterSequence
                   to support per-flow services
                 - added pvxSrvcUNIEFPSDEnabled to support EFPSD
                 - added new tables pvSLAMeasurementProfileTable, 
                   pvxEServiceSlaCrntPMTable, pvxEServiceSlaHistPMTable,
                   pvxEServieSlaPMThresholdTable, pvxSLAThroughputTestTable,
                   pvxSLAMsmtInitiatorDBTable, and pvxSLAMsmtResponderDBTable 
                   to support the Y.1731 SLA Measurement feature
                 - added trap pvxSrvcUNIEFPSDLocalEFPSDStateChangeEvent"
    REVISION     "201103281200Z"  -- Monday, March 28, 12:00:00 EST 2011
    DESCRIPTION  "MIB Updates for BTI 7000 Rel 8.1.4:
                 - added support for sftp protocol for use with the software
                   upgrade and database backup/restore operations."
    REVISION     "201102251200Z"  -- Friday, February 25, 12:00:00 EST 2011
    DESCRIPTION  "MIB Updates for BTI 7000 Rel 8.1.3:
                 - added two new traps for NTP. One for indicating timing 
                   ref change and the other for when NTP updates the system 
                   date/time."
    REVISION     "201009171200Z"  -- Friday, September 17, 12:00:00 EST 2010
    DESCRIPTION  "MIB Updates for BTI 7000 Rel 8.1.1:
                 - added snmpTrapRcvTable for administration of configured
                   recipients of traps generated by the SNMP agent"
    REVISION     "201008061200Z"  -- Friday, August 6, 12:00:00 EST 2010
    DESCRIPTION  "MIB Updates for BTI 7000 Rel 8.1.0:
                 - changed range of objects representing a slot number
                   to support new 7200 shelf which has 20 slots
                 - added neFPDetect object to control Pack Missing alarms
                 - changed status of shelfInvConfig, shelfProvConfig and
                   shelfDiscConfig objects and shelfConfigurationMismatchCond
                   and shelfConfigurationMismatchClear notifications to deprecated
                 - increased size range of vcgTimeSlotIndices string to
                   support longer list of indices
                 - added new UAS PM objects in SONET OC-n (ocn), SDH STM-N (stmn),
                   Gigabit Ethernet (ge), Fiber Channel (fc), ethernet Layer 1
                   (ethL1IF)
                 - added ospfGeneralTable, ospfIfTable, ospfLsdbTable and
                   ospfNbrTable tables for management of OSPF
                 - added slotInvCoolingUnitMismatchCond and
                   slotInvCoolingUnitMismatchClear notifications"
    REVISION     "201006181200Z"  -- Friday, June 18, 12:00:00 EST 2010
    DESCRIPTION  "MIB Updates for BTI 7000 Rel 7.3.2:
                 - added envCondAttrTable for managing environmental alarms
                 - added all environmental alarm traps under
                   envCondNotifications branch"
    REVISION     "201002121200Z"  -- Friday, February 12, 12:00:00 EST 2010
    DESCRIPTION  "MIB Updates for BTI 7000 Rel 7.3.0:
                 - added objects pluggableInvWavelengthMin,
                   pluggableInvWavelengthMax and pluggableInvWavelengthSpacing
                   in support of tuneable pluggables
                 - added ocn, stmn, and ols versions of
                   'WavelengthNotAchievable' traps
                 - added ocnTransparencyChannel and stsnTransparencyChannel
                   objects to support DCC configuration on Muxponders
                 - added values sdSdi through dvbAsi to SYNTAX of briProtocol
                 - modified range of the IntervalType index field of all
                   historical PM tables from 1..32 to 1..96 in accordance
                   with increased binning support
                 - added objects to support new BER and average BER PM stats
                   in transceiver (XCVR), SONET OC-n (ocn), SDH STM-N (stmn),
                   and ethernet Layer 1 (ethL1IF) curent and historical PM tables
                 - added objects to support 64-bit versions of NBITCR and NBYTCR
                   stats in transceiver (XCVR), SONET OC-n (ocn), SDH STM-N (stmn),
                   and ethernet Layer 1 (ethL1IF) current and historical PM tables
                 - added gcc0ConfigTable and ipExtInterfaceTable
                 - marked the applyRestore value of the DbBackupAndRestoreCmd
                   textual convention as obsolete
                 - added cpSynchronizationPrimRefBasicSSM and
                   cpSynchronizationSecRefBasicSSM objects to support
                   synchronization status messages
                 - added cpSynchronizationSwitchEvt trap
                 - added briTxLockingCond and briTxLockingClear traps
                   to notify of when Bit-rate-independent facilities on
                   the Muxponder are in the process of locking."
    REVISION     "200901191200Z"  -- Friday, June 19, 12:00:00 EST 2009
    DESCRIPTION  "MIB Updates for BTI 7000 Rel 7.2.0:
                 - added all objects under ntpClient branch for management
                   of Network Time Protocol
                 - added ocnDCCTransparency and stmnDCCTransparency objects
                 - added values vc42v, sts1c6v and sts3c2v to vcgType object
                 - added odunTable table for management of ODU-N facilities
                   on Muxponder circuit packs
                 - added briTable table for management of Bit Rate
                   Independent facilities on Muxponder circuit packs
                 - replaced references to SwitchIdxType TC with an integer
                   range of 1..11
                 - added btiCrntPMTable and briHistPMTable for retrieval of
                   current and historical PMs on BRI facilities
                 - added condObjectType and condCodeType objects to all 
                   condition Trap varbind lists, added evtDescription,
                   evtObjectType and evtCodeType objects to all event Trap
                   varbind lists, added actCondObjectType and actCondCodeType
                   objects to actCondTable, and added actAlarmObjectType and
                   actAlarmCodeType objects to actAlarmTable to support
                   enhanced event/alarm/condition information feature.
                 - added briLpbkOpTable for BRI facility loopback management
                 - added new objects pvxL2IntfIsUNI to pvxL2IntfTrustIncomingDscp
                   in pvxL2IntfTable
                 - changed DEFVAL value of pvxL2IntfType from cep to pnp
                 - added setErrorInfo objects for reporting of error information
                   in response to failed set requests
                 - added condNotifCtrlTable and eventNotifState objects for
                   management of configurable alarm severity feature
                 - added new PVX Ethernet Interface Traps olsLossOfFrameCond to
                   olsOTUTrailTraceMismatchClear
                 - added new set of Traps under odunCondNotifications branch
                 - added new set of Traps under briCondNotifications branch
                 - added new set of Traps under ntpcCondNotifications branch"
    REVISION     "200812191200Z"  -- Friday, December 19, 12:00:00 EST 2008
    DESCRIPTION  "MIB Updates for BTI 7000 Rel 7.1.2:
                  - corrected OID for slotInvUpgradeStage, slotInvUpgradeResult, 
                    and slotInvPackUSI objects
                  - corrected DEFVAL clause for shelfPowerFeedA, shelfPowerFeedB
                  - added new values to ocnLineMapping/stmnLineMapping objects
                  - changed SYNTAX of vcgTimeSlotIndices object
                  - added ethIntMACAddr object
                  - changed ethIntfLineMapping value of none to tenglan
                  - added ethL1IFCrntPMTable, ethL1IFHistPMTable, and
                    ethL1IFPMThresholdTable for performance management
                    of Ethernet Layer 1 interfaces on PVX cards
                  - corrected MAX-ACCESS of all protection entity objects
                    in XC tables to read-create
                  - replaced otunProtGrpTable and otunProtSwOpTable with
                    ocnProtGrpTable, stmnProtGrpTable, ocnProtSwOpTable and
                    stmnProtSwOpTable
                  - added ocnProtSwitchEvt and stmnProtSwitchEvt traps
                  - added ethL1IFStatusChangeEvt and ethL1IFTcaEvt traps
                  - removed all unused otun and odun related objects"
    REVISION     "200810101200Z"  -- Friday, October 10, 12:00:00 EST 2008
    DESCRIPTION  "MIB Updates for BTI 7000 Rel 7.1.1:
                  - added shelfInvUSI, slotInvPackUSI, and pluggableInvUSI objects
                  - added shelfPowerFeedA, shelfPowerFeedB objects
                  - removed NBITCR, NBYTCR from PM Threshold tables for
                    XCVRx, OCn, and STMn
                  - added EthIntfTable and pvxL2IntfTable for management of
                    Ethernet Layer 1 and Layer 2 interfaces respectively on
                    PVX card
                  - added pvxL2IFCrntPMTable, pvxL2IFHistPMTable, and
                    pvxL2IFPMThresholdTable for performance management
                    of Ethernet Layer 2 interfaces on PVX cards
                  - added the condDescription varbind to all condition
                    raise and clear traps
                  - added varbinds to shelfInvPlugin, slotInvPlugin and
                    pluggableInvPlugin event traps to provide detailed
                    data for the newly plugged in inventory item
                  - added ocnOTNPayloadMismatchCond and stmnOTNPayloadMismatchCond
                    condition traps
                  - added new condition traps under ethPortCondNotifications 
                    and pvxL2PortCondNotifications OID branches"
    REVISION     "200805301200Z"  -- Friday, May 30, 12:00:00 EST 2008
    DESCRIPTION  "MIB Updates for BTI 7000 Rel 7.1.0:
                  - replaced references to Netstender with BTI 7000
                  - added SDBERTh and Trace-related objects to xcvrTable
                  - added initialization objects for all PM value objects
                  - added TOHTransparency and LineMapping objects to ocnTable
                  and stmnTable
                  - added GFPMode and FlowControl objects to geTable
                  - modified vcgTable to allow creation of row entries
                  - added fcTable for Fiber Channel facilities on MXP cards
                  - added odunTable to support Traps on MXP cards
                  - added SUPPLY2, and OTU PMs to XCVR PM Tables
                  - added SONET Line layer, OTU, and FEC PMs to OC-N PM Tables
                  - added SDH MS layer, OTU, and FEC PMs to STM-N PM Tables
                  - added additional Layer 2 PMs to GE PM Tables
                  - added Fiber Channel PM Tables
                  - added several new Traps for TPR and 10GMXP packs"
    REVISION     "200709141200Z"  -- Tuesday, September 18, 12:00:00 EST 2007
    DESCRIPTION  "MIB Updates for Netstender Rel 6.2.0: Completion of SNMP
                  coverage for all cards including all Wavelength Conversion,
                  2.5G Muxponder and AMD circuit packs. Addition of full
                  management support including Muxponder facilities, protocol
                  PMs, synchronization management, and database change messages.
                  New and expanded tables and other objects include:
                  - amdTable
                  - ocnTable
                  - stsnTable
                  - stmnTable
                  - vcnTable
                  - geTable
                  - feTable
                  - vcgTable
                  - serialTable
                  - xcvrCrntPMTable
                  - xcvrHistPMTable
                  - xcvrPMThresholdTable
                  - amdCrntPMTable
                  - amdHistPMTable
                  - ocnCrntPMTable
                  - ocnHistPMTable
                  - ocnPMThresholdTable
                  - stsnCrntPMTable
                  - stsnHistPMTable
                  - stsnPMThresholdByPortTable
                  - stmnCrntPMTable
                  - stmnHistPMTable
                  - stmnPMThresholdTable
                  - vcnCrntPMTable
                  - vcnHistPMTable
                  - vcnPMThresholdByPortTable
                  - geCrntPMTable
                  - geHistPMTable
                  - gePMThresholdTable
                  - vcgXCTable
                  - ocnLpbkOpTable
                  - stsnProtSwOpTable
                  - stmnLpbkOpTable
                  - vcnProtSwOpTable
                  - geLpbkOpTable
                  - cpSynchronizationTable
                  - networkNeighborTable
                  - Threshold crossing alert notifications and supporting
                  objects
                  - Database change messages and supporting objects"
    REVISION     "200707161200Z"  -- Monday, July 16, 12:00:00 EST 2007
    DESCRIPTION  "MIB updates for Netstender Rel. 6.1: Added tables and traps in
                  support of new 2.5G Muxponder card.
                  - ocnTable, stsnTable, stmnTable, vcnTable, geTable
                  - stsnProtSwitchEvt, vcnProtSwitchEvt
                  - all condition notifications under ocnCondNotifications,
                  stsnCondNotifications, stmnCondNotifications,
                  vcnCondNotifications, geCondNotifications
                  - shelfInvAssemblyPEC object marked obsolete"
    REVISION     "200703091200Z"  -- Friday, March 9, 12:00:00 EST 2007
    DESCRIPTION  "MIB Updates for Netstender Rel 5.1.1: Addition of full SNMP
                  support for management of inventory, equipment, optical
                  amplifiers, 2.5G wavelength conversion transceivers and
                  passive cards. New and expanded tables and other objects
                  include:
                  - networkElement group
                  - shelfInvTable
                  - slotInvTable
                  - pluggableInvTable
                  - shelfTable
                  - cpTable
                  - oaTable
                  - xcvrTable
                  - passivePortTable
                  - oscTable
                  - netMgmtTable
                  - oaCrntPMTable
                  - oaHistPMTable
                  - xcvrCrntPMTable
                  - xcvrHistPMTable
                  - xcvrXCTable
                  - xcvrProtGrpTable
                  - commitESOpTable
                  - cpRestartOpTable
                  - oaOOBRSDOpTable
                  - xcvrLpbkOpTable
                  - xcvrProtSwOpTable
                  - dataCommsPingTable
                  - addition of several Traps and supporting objects under
                  eventNotifications branch"
    REVISION     "200608251200Z"  -- Friday, August 25, 12:00:00 EST 2006
    DESCRIPTION  "MIB Updates for Netstender Rel 5.1:
                  - generalized naming of SFP Inventory related objects and
                  notifications to allow for inclusion of XFPs as well as SFPs
                  - added Traps for Forced Switch, Lockout and Temp conditions
                  - added read-only support for Optical Amplifer Performance
                  Monitoring
                  - removed obsolete Red and Blue type OA notifications"
    REVISION     "200512051200Z"  -- Monday, December 5, 12:00:00 EST 2005
    DESCRIPTION  "MIB Updates for Netstender Rel 4.1:
                  - changed actCondTable Index fields MAX-ACCESS to read-only
                  - added support for new multi-shelf, AMD, and XCVR Traps
                  - added TL1 IP Lockout, DspCommCond and Unsupported Pack traps
                  - marked some unused shelf-related Traps as obsolete"
    REVISION     "200507251200Z"  -- Monday, July 25, 12:00:00 EST 2005
    DESCRIPTION  "MIB Updates for Netstender Rel 3.1.1:
                  - added support for TL1 User Lockout Traps
                  - added actCondTable to support retrieval of active conditions
                  on Netstender
                  - updated Contact Info in Module Identity"
    REVISION     "200501071200Z"  -- Monday, February 7, 12:00:00 EST 2005
    DESCRIPTION  "MIB Updates for Netstender Rel 3.1:
                  - changed Shutdown terminology to Safety for OBR Traps
                  - added sfpInvTable, xcvrTable and new Traps for SFPs"
    REVISION     "200409231200Z"  -- Thursday, September 23, 12:00:00 EST 2004
    DESCRIPTION  "MIB Updates for Netstender Rel 3.0:
                  - generalized object names to Netstender to support both
                  Netstender 2060 and Netstender 1030
                  - changed name of file from net2060.my to netstender.my
                  - changed name of MIB from NETSTENDER-2060-MIB to
                  NETSTENDER-MIB
                  - eliminated unnecessary textual conventions
                  - redefined several enumerations as textual conventions and
                  moved to BTI-TC-MIB
                  - corrected the descriptions for several objects"
    REVISION     "200409091434Z"  -- Thursday, September 9, 14:34:00 EST 2004
    DESCRIPTION  "MIB Updates for Netstender 2060 Rel 2.2:
                  - added new Single Channel Booster Amp card types and OA type
                  - changed OIDs of SNMPv2c notifications to make them reverse
                  mapable: SNMPv2c -> SNMPv1 -> SNMPv2c
                  - defined new OA Back Reflection Shutdown notifications"
    REVISION     "200404142235Z"  -- Wednesday, April 14, 22:35:00 EST 2004
    DESCRIPTION  "MIB Updates for Netstender 2060 Rel 2.1.3:
                  - added new supported card types and optical amplifier types
                  - added new Red and Blue type objects to OA Table
                  - defined new Red and Blue type OA notifications
                  - corrected the descriptions for several notifications"
    REVISION     "200312011200Z"  -- Monday, December 1, 12:00:00 EST 2003
    DESCRIPTION  "The initial version of this MIB module, released with the
                  Netstender 2060 Rel 2.1 product."

    ::= { btiModules 3 }


objects                       OBJECT IDENTIFIER ::= { bti7000 1 }

networkElement                OBJECT IDENTIFIER ::= { objects 1 }
inventory                     OBJECT IDENTIFIER ::= { objects 2 }
equipment                     OBJECT IDENTIFIER ::= { objects 3 }
facilities                    OBJECT IDENTIFIER ::= { objects 4 }
dataComms                     OBJECT IDENTIFIER ::= { objects 5 }
performance                   OBJECT IDENTIFIER ::= { objects 6 }
conditions                    OBJECT IDENTIFIER ::= { objects 7 }
administration                OBJECT IDENTIFIER ::= { objects 8 }
connections                   OBJECT IDENTIFIER ::= { objects 9 }
protection                    OBJECT IDENTIFIER ::= { objects 10 }
operations                    OBJECT IDENTIFIER ::= { objects 11 }
synchronization               OBJECT IDENTIFIER ::= { objects 12 }
topology                      OBJECT IDENTIFIER ::= { objects 13 }
pvxObjects                    OBJECT IDENTIFIER ::= { objects 14 } 
miscellaneous                 OBJECT IDENTIFIER ::= { objects 15 }
opticalLayer                  OBJECT IDENTIFIER ::= { objects 16 }
    
pvxBridge	 				  OBJECT IDENTIFIER ::= { pvxObjects 1 }
pvxNotificationObjects        OBJECT IDENTIFIER ::= { pvxObjects 4 }

mstpNotificationObjects       OBJECT IDENTIFIER ::= { pvxNotificationObjects 1 }

notifications                 OBJECT IDENTIFIER ::= { bti7000 2 }
eventNotifications            OBJECT IDENTIFIER ::= { notifications 1 }
conditionNotifications        OBJECT IDENTIFIER ::= { notifications 2 }
dbChangeNotifications         OBJECT IDENTIFIER ::= { notifications 3 }
notificationObjects           OBJECT IDENTIFIER ::= { notifications 4 }
notificationControl           OBJECT IDENTIFIER ::= { notifications 5 }

evtNotificationObjects        OBJECT IDENTIFIER ::= { eventNotifications 1 }
neEvtNotifications            OBJECT IDENTIFIER ::= { eventNotifications 2 }
shelfInvEvtNotifications      OBJECT IDENTIFIER ::= { eventNotifications 3 }
slotInvEvtNotifications       OBJECT IDENTIFIER ::= { eventNotifications 4 }
shelfEvtNotifications         OBJECT IDENTIFIER ::= { eventNotifications 5 }
cpEvtNotifications            OBJECT IDENTIFIER ::= { eventNotifications 6 }
oaEvtNotifications            OBJECT IDENTIFIER ::= { eventNotifications 7 }
dataCommsEvtNotifications     OBJECT IDENTIFIER ::= { eventNotifications 8 }
pluggableInvEvtNotifications  OBJECT IDENTIFIER ::= { eventNotifications 9 }
xcvrEvtNotifications          OBJECT IDENTIFIER ::= { eventNotifications 10 }
adminEvtNotifications         OBJECT IDENTIFIER ::= { eventNotifications 11 }
amdEvtNotifications           OBJECT IDENTIFIER ::= { eventNotifications 12 }
ocnEvtNotifications           OBJECT IDENTIFIER ::= { eventNotifications 13 }
stsnEvtNotifications          OBJECT IDENTIFIER ::= { eventNotifications 14 }
stmnEvtNotifications          OBJECT IDENTIFIER ::= { eventNotifications 15 }
vcnEvtNotifications           OBJECT IDENTIFIER ::= { eventNotifications 16 }
geEvtNotifications            OBJECT IDENTIFIER ::= { eventNotifications 17 }
fcEvtNotifications            OBJECT IDENTIFIER ::= { eventNotifications 18 }
ethPortEvtNotifications       OBJECT IDENTIFIER ::= { eventNotifications 21 }
pvxL2EvtNotifications         OBJECT IDENTIFIER ::= { eventNotifications 22 }
mstpEvtNotifications          OBJECT IDENTIFIER ::= { eventNotifications 23 }
briEvtNotifications           OBJECT IDENTIFIER ::= { eventNotifications 24 }
cpSynchronizationEvtNotifications OBJECT IDENTIFIER ::= { eventNotifications 25 }
pvxESrvcBWPrflEvtNotifications OBJECT IDENTIFIER ::= { eventNotifications 26 }
pvxESrvcEvtNotifications       OBJECT IDENTIFIER ::= { eventNotifications 27 }
pvxERPSSrvcNNIEvtNotifications OBJECT IDENTIFIER ::= { eventNotifications 28 }
pvxERPSSrvcEvtNotifications    OBJECT IDENTIFIER ::= { eventNotifications 29 }
pvxSlaMsmtEvtNotifications    OBJECT IDENTIFIER ::= { eventNotifications 30 }
ntpcEvtNotifications          OBJECT IDENTIFIER  ::= { eventNotifications 31 }
pvxSUniEvtNotifications       OBJECT IDENTIFIER  ::= { eventNotifications 32 }
olEvtNotifications            OBJECT IDENTIFIER ::= { eventNotifications 33 }
pvxLldpEvtNotifications       OBJECT IDENTIFIER ::= { eventNotifications 34 }

neCondNotifications           OBJECT IDENTIFIER ::= { conditionNotifications 1 }
shelfInvCondNotifications     OBJECT IDENTIFIER ::= { conditionNotifications 2 }
slotInvCondNotifications      OBJECT IDENTIFIER ::= { conditionNotifications 3 }
shelfCondNotifications        OBJECT IDENTIFIER ::= { conditionNotifications 4 }
cpCondNotifications           OBJECT IDENTIFIER ::= { conditionNotifications 5 }
oaCondNotifications           OBJECT IDENTIFIER ::= { conditionNotifications 6 }
dataCommsCondNotifications    OBJECT IDENTIFIER ::= { conditionNotifications 7 }
pluggableInvCondNotifications OBJECT IDENTIFIER ::= { conditionNotifications 8 }
xcvrCondNotifications         OBJECT IDENTIFIER ::= { conditionNotifications 9 }
adminCondNotifications        OBJECT IDENTIFIER ::= { conditionNotifications 10 }
amdCondNotifications          OBJECT IDENTIFIER ::= { conditionNotifications 11 }
ocnCondNotifications          OBJECT IDENTIFIER ::= { conditionNotifications 12 }
stsnCondNotifications         OBJECT IDENTIFIER ::= { conditionNotifications 13 }
stmnCondNotifications         OBJECT IDENTIFIER ::= { conditionNotifications 14 }
vcnCondNotifications          OBJECT IDENTIFIER ::= { conditionNotifications 15 }
geCondNotifications           OBJECT IDENTIFIER ::= { conditionNotifications 16 }
fcCondNotifications           OBJECT IDENTIFIER ::= { conditionNotifications 17 }
ethPortCondNotifications      OBJECT IDENTIFIER ::= { conditionNotifications 20 }
pvxL2PortCondNotifications    OBJECT IDENTIFIER ::= { conditionNotifications 21 }
mstpCondNotifications         OBJECT IDENTIFIER ::= { conditionNotifications 22 }
lagCondNotifications          OBJECT IDENTIFIER ::= { conditionNotifications 23 }
odunCondNotifications         OBJECT IDENTIFIER ::= { conditionNotifications 24 }
briCondNotifications          OBJECT IDENTIFIER ::= { conditionNotifications 25 }
ntpcCondNotifications         OBJECT IDENTIFIER ::= { conditionNotifications 26 }
envCondNotifications          OBJECT IDENTIFIER ::= { conditionNotifications 27 }
olCondNotifications           OBJECT IDENTIFIER ::= { conditionNotifications 28 }
erpsCondNotifications         OBJECT IDENTIFIER ::= { conditionNotifications 29 }
swMemberCondNotifications     OBJECT IDENTIFIER ::= { conditionNotifications 30 }


condNotifCtrl                 OBJECT IDENTIFIER ::= { notificationControl 1 }
eventNotifCtrl                OBJECT IDENTIFIER ::= { notificationControl 2 }

neOperations                  OBJECT IDENTIFIER ::= { operations 1 }
shelfInvOperations            OBJECT IDENTIFIER ::= { operations 2 }
slotInvOperations             OBJECT IDENTIFIER ::= { operations 3 }
shelfOperations               OBJECT IDENTIFIER ::= { operations 4 }
cpOperations                  OBJECT IDENTIFIER ::= { operations 5 }
oaOperations                  OBJECT IDENTIFIER ::= { operations 6 }
dataCommsOperations           OBJECT IDENTIFIER ::= { operations 7 }
pluggableInvOperations        OBJECT IDENTIFIER ::= { operations 8 }
xcvrOperations                OBJECT IDENTIFIER ::= { operations 9 }
adminOperations               OBJECT IDENTIFIER ::= { operations 10 }
amdOperations                 OBJECT IDENTIFIER ::= { operations 11 }
ocnOperations                 OBJECT IDENTIFIER ::= { operations 12 }
stsnOperations                OBJECT IDENTIFIER ::= { operations 13 }
stmnOperations                OBJECT IDENTIFIER ::= { operations 14 }
vcnOperations                 OBJECT IDENTIFIER ::= { operations 15 }
geOperations                  OBJECT IDENTIFIER ::= { operations 16 }
fcOperations                  OBJECT IDENTIFIER ::= { operations 17 }
briOperations                 OBJECT IDENTIFIER ::= { operations 18 }




-----------------------------------------------------------------------
-----------------------------------------------------------------------
-- Managed object definitions.
-----------------------------------------------------------------------
-----------------------------------------------------------------------


-----------------------------------------------------------------------
-- Objects related to the Network Element as a whole
-- 
-- The following table lists the system level parameters supported by 
-- BTI 7000 Series under the networkElement branch of the MIB. These
-- objects are in addition to those supported under the system group
-- of MIB-II.
-----------------------------------------------------------------------


neSWVersion OBJECT-TYPE
    SYNTAX       DisplayString (SIZE (0..32))
    MAX-ACCESS   read-only
    STATUS       current
    DESCRIPTION  "The software version that is active on the NE currently."
    ::= { networkElement 1 }


neNum OBJECT-TYPE
    SYNTAX       INTEGER (0..65535)
    MAX-ACCESS   read-write
    STATUS       current
    DESCRIPTION  "This is a unique network element number used to identify the
                  network element and to differentiate it from other NEs in the
                  management domain."
    ::= { networkElement 2 }


neSiteNum OBJECT-TYPE
    SYNTAX       INTEGER (0..65535)
    MAX-ACCESS   read-write
    STATUS       current
    DESCRIPTION  "This is a network element site number used to uniquely
                  identify the site of the NE and to differentiate it from other
                  NE sites in the management domain."
    ::= { networkElement 3 }


neDateAndTime OBJECT-TYPE
    SYNTAX       DateAndTime
    MAX-ACCESS   read-write
    STATUS       current
    DESCRIPTION  "The current system date and time, without time zone
                  information."
    ::= { networkElement 4 }


neTimeZone OBJECT-TYPE
    SYNTAX       TimeZone
    MAX-ACCESS   read-write
    STATUS       current
    DESCRIPTION  "The time zone in which the local time of this system is to be
                  reported. Typically, the time zone is the one in which the
                  system is physically located."
    ::= { networkElement 5 }


neAutoDST OBJECT-TYPE
    SYNTAX       INTEGER { on  (1),
                           off (2) }
    MAX-ACCESS   read-write
    STATUS       current
    DESCRIPTION  "A setting that indicates whether the system time should be
                  updated automatically in accordance with the daylight savings
                  time characteristics of the current time zone."
    ::= { networkElement 6 }


neGateway OBJECT-TYPE
    SYNTAX       IpAddress
    MAX-ACCESS   read-write
    STATUS       current
    DESCRIPTION  "The default IP routing gateway for network management
                  interfaces on the node. If not specified, this object returns
                  a value of 0.0.0.0."
    ::= { networkElement 7 }


neSecGateway OBJECT-TYPE
    SYNTAX       IpAddress
    MAX-ACCESS   read-write
    STATUS       current
    DESCRIPTION  "The secondary IP routing gateway for network management
                  interfaces on the node. If not specified, this object returns
                  a value of 0.0.0.0."
    ::= { networkElement 8 }


neActiveGateway OBJECT-TYPE
    SYNTAX       IpAddress
    MAX-ACCESS   read-only
    STATUS       current
    DESCRIPTION  "The IP routing gateway that is currently active on the node.
                  If no gateway is active, this object returns a value of
                  0.0.0.0."
    ::= { networkElement 9 }


neAutoProv OBJECT-TYPE
    SYNTAX       INTEGER { enabled     (1),
                           disabled    (2),
                           autoEnabled (3),
                           autoProvOff (4) }
    MAX-ACCESS   read-write
    STATUS       current
    DESCRIPTION  "A setting that specifies if automatic provisioning of
                  equipment and facilities is enabled. If automatic provisioning
                  is enabled, this object indicates the default administration
                  status. The possible values include:
                  - enabled: Applicable entities are auto provisioned with the
                  initial state enabled.
                  - disabled: Applicable entities are auto provisioned with the
                  initial state disabled.
                  - autoEnabled: Applicable entities are auto provisioned and
                  placed into the auto-enabled state.
                  - autoProvOff: Auto provisioning is disabled."
    ::= { networkElement 10 }


neAutoDeProv OBJECT-TYPE
    SYNTAX       HoursAndMinutes
    MAX-ACCESS   read-write
    STATUS       obsolete -- Obsolete as of release 8.2.0
    DESCRIPTION  "The time delay after a physical shelf or circuit pack is
                  removed from the NE before the provisioned entities that are
                  supported by the removed equipment are automatically
                  deprovisioned. If this object is set to a value of 000-00,
                  auto deprovisioning is disabled."
    ::= { networkElement 11 }


neAutoEnabledTimer OBJECT-TYPE
    SYNTAX       HoursAndMinutes
    MAX-ACCESS   read-write
    STATUS       current
    DESCRIPTION  "The system wide default auto-enable timer value. This timer
                  specifies a time delay after a provisioned facility in the
                  auto-enabled state is cleared of all alarms before the state
                  of the facility transitions to enabled. The default value can
                  be overridden by a facility-specific value that is specified
                  when the facility is either provisioned or edited in its
                  respective table."
    ::= { networkElement 12 }


ntpClient OBJECT IDENTIFIER ::= { networkElement 13 }

ntpClientPollingRate OBJECT-TYPE
    SYNTAX       HoursAndMinutes
    MAX-ACCESS   read-write
    STATUS       current
    DESCRIPTION  "The polling rate for the NTP client to periodically fetch the
                  system time from the list of NTP servers configured."
    ::= { ntpClient 1 }

ntpClientAuthKey OBJECT-TYPE
    SYNTAX       INTEGER (0..65535)
    MAX-ACCESS   read-write
    STATUS       obsolete
    DESCRIPTION  "The NTP authentication key ID, if authentication is required."
    ::= { ntpClient 2 }

ntpClientSyncState OBJECT-TYPE
    SYNTAX       DisplayString (SIZE (0..32))
    MAX-ACCESS   read-only
    STATUS       current
    DESCRIPTION  "Status indicating if the node is in sync with one of the time
                  servers. Either Y or N."
    ::= { ntpClient 3 }

ntpClientStratum OBJECT-TYPE
    SYNTAX       INTEGER (0..65535)
    MAX-ACCESS   read-only
    STATUS       current
    DESCRIPTION  "Specifies the stratum of the timer server the node in in sync
                  with."
    ::= { ntpClient 4 }

ntpClientRefIPAddr OBJECT-TYPE
    SYNTAX       DisplayString (SIZE (0..16))
    MAX-ACCESS   read-only
    STATUS       current
    DESCRIPTION  "The IP address of the time server the node is in sync with."
    ::= { ntpClient 5 }

ntpClientAssocTable OBJECT-TYPE
    SYNTAX       SEQUENCE OF NTPClientAssocEntry
    MAX-ACCESS   not-accessible
    STATUS       current
    DESCRIPTION  "A list of NTP servers to poll for the system time. The NTP
                  client then decides which is best clock source."
    ::= { ntpClient 6 }

ntpClientAssocEntry OBJECT-TYPE
    SYNTAX       NTPClientAssocEntry
    MAX-ACCESS   not-accessible
    STATUS       current
    DESCRIPTION  "The list entry for an NTP server."
    INDEX        { ntpClientAssocIdx }
    ::= { ntpClientAssocTable 1 }

NTPClientAssocEntry ::= SEQUENCE { ntpClientAssocIdx       IpAddress,
                                   ntpClientAssocRowStatus RowStatus }

ntpClientAssocIdx OBJECT-TYPE
    SYNTAX       IpAddress
    MAX-ACCESS   not-accessible
    STATUS       current
    DESCRIPTION  "The IP address of the NTP server."
    ::= { ntpClientAssocEntry 1 }
    
ntpClientAssocRowStatus OBJECT-TYPE
    SYNTAX       RowStatus
    MAX-ACCESS   read-create
    STATUS       current
    DESCRIPTION  "Used to control the addition and deletion of entries in the
                  NTP client association table."
    ::= { ntpClientAssocEntry 100 }

ntpOldTimeAndDate OBJECT-TYPE
    SYNTAX       DateAndTime
    MAX-ACCESS   accessible-for-notify
    STATUS       current
    DESCRIPTION  "The date and time of the system before the NTP client updated the
                  system clock."
    ::= { ntpClient 7 }

ntpNewTimeAndDate OBJECT-TYPE
    SYNTAX       DateAndTime
    MAX-ACCESS   accessible-for-notify
    STATUS       current
    DESCRIPTION  "The new system date and time updated by the NTP client."
    ::= { ntpClient 8 }

ntpRefIP OBJECT-TYPE
    SYNTAX       IpAddress
    MAX-ACCESS   accessible-for-notify
    STATUS       current
    DESCRIPTION  "This the NTP server being used as the clock reference for the system."
    ::= { ntpClient 9 }

ntpRefStratum OBJECT-TYPE
    SYNTAX       Unsigned32
    MAX-ACCESS   accessible-for-notify
    STATUS       current
    DESCRIPTION  "This is the stratum of the NTP server being used as the clock
                  reference for the system."
    ::= { ntpClient 10 }

neFPDetect OBJECT-TYPE
    SYNTAX       INTEGER { on  (1),
                           off (2) }
    MAX-ACCESS   read-write
    STATUS       current
    DESCRIPTION  "A setting that indicates whether the system should report pack
                  missing alarms."
    ::= { networkElement 14 }

neHTAutoShutdown OBJECT-TYPE
    SYNTAX       INTEGER { on  (1),
                           off (2) }
    MAX-ACCESS   read-write
    STATUS       current
    DESCRIPTION  "A system wide setting that specifies whether the circuit pack 
                  pack high temperature automatic shutdown (HTAS) is enabled. 
                  When enabled, the circuit packs which support the HTAS feature
                  will be automatically powered down if the shutdown temperature
                  threshold for that circuit pack is exceeded. 
                  There will be alarms indicating that the shutdown has occurred.
                  The default setting is enabled."
    ::= { networkElement 15 }



-----------------------------------------------------------------------
-- Objects related to the physical shelf inventory on the system
-- 
-- A listing of physically detected BTI 7000 Series shelves can be 
-- retrieved from the shelfInvTable. The following table lists the 
-- readable objects in each entry of the
-- shelfInvTable.
-----------------------------------------------------------------------


shelfInvTable OBJECT-TYPE
    SYNTAX       SEQUENCE OF ShelfInvEntry
    MAX-ACCESS   not-accessible
    STATUS       current
    DESCRIPTION  "This table contains one row for every physically detected
                  shelf on the NE. Each row contains a list of attributes that
                  pertain to a physical shelf."
    ::= { inventory 1 }


shelfInvEntry OBJECT-TYPE
    SYNTAX       ShelfInvEntry
    MAX-ACCESS   not-accessible
    STATUS       current
    DESCRIPTION  "The conceptual row object of the shelf inventory table."
    INDEX        { shelfInvIdx }
    ::= { shelfInvTable 1 }


ShelfInvEntry ::= SEQUENCE { shelfInvIdx                    INTEGER,
                             shelfInvExpectedNEName         DisplayString,
                             shelfInvExpectedIPAddress      DisplayString,
                             shelfInvExpectedShelfNum       INTEGER,
                             shelfInvExpectedMSISerialNum   DisplayString,
                             shelfInvDiscoveredNEName       DisplayString,
                             shelfInvDiscoveredIPAddress    DisplayString,
                             shelfInvDiscoveredShelfNum     INTEGER,
                             shelfInvDiscoveredMSISerialNum DisplayString,
                             shelfInvType                   ShelfType,
                             shelfInvShortName              DisplayString,
                             shelfInvName                   DisplayString,
                             shelfInvChassisPEC             DisplayString,
                             shelfInvChassisCLEI            DisplayString,
                             shelfInvAssemblyPEC            DisplayString,
                             shelfInvRev                    INTEGER,
                             shelfInvConfig                 ShelfConfigType,
			     shelfInvUSI                    DisplayString,
			     shelfInvSerialNum              DisplayString,
                             shelfInvMfgDate                DisplayString,
                             shelfInvMfgLoc                 DisplayString,
                             shelfInvTestDate               DisplayString,
                             shelfInvTestLoc                DisplayString}



shelfInvIdx OBJECT-TYPE
    SYNTAX       INTEGER (1|11|21|31)
    MAX-ACCESS   accessible-for-notify
    STATUS       current
    DESCRIPTION  "The number of the shelf. It is set to 1 for the main shelf,
                  otherwise the object is based on the expansion shelf port on
                  which the shelf is detected, and the number of hops from the
                  main shelf."
    ::= { shelfInvEntry 1 }


shelfInvExpectedNEName OBJECT-TYPE
    SYNTAX       DisplayString (SIZE (0..20))
    MAX-ACCESS   accessible-for-notify
    STATUS       current
    DESCRIPTION  "The NE name expected by the main shelf to be reported by the
                  expansion shelf as the name of the NE to which it belongs."
    ::= { shelfInvEntry 2 }


shelfInvExpectedIPAddress OBJECT-TYPE
    SYNTAX       DisplayString (SIZE (0..15))
    MAX-ACCESS   accessible-for-notify
    STATUS       current
    DESCRIPTION  "The string representation of the NE NMS IP address that is
                  expected by the main shelf to be reported by the expansion
                  shelf as the IP address of the NE to which it belongs."
    ::= { shelfInvEntry 3 }


shelfInvExpectedShelfNum OBJECT-TYPE
    SYNTAX       INTEGER (11|21|31)
    MAX-ACCESS   accessible-for-notify
    STATUS       current
    DESCRIPTION  "The number of the expansion shelf that is expected by the main
                  shelf to be reported by the attached shelf."
    ::= { shelfInvEntry 4 }


shelfInvExpectedMSISerialNum OBJECT-TYPE
    SYNTAX       DisplayString (SIZE (0..16))
    MAX-ACCESS   accessible-for-notify
    STATUS       current
    DESCRIPTION  "The serial number of the Main Shelf Interface circuit pack
                  that is expected by the main shelf to be reported by the
                  expansion shelf as the MSI serial number of the NE main shelf
                  to which it belongs."
    ::= { shelfInvEntry 5 }


shelfInvDiscoveredNEName OBJECT-TYPE
    SYNTAX       DisplayString (SIZE (0..20))
    MAX-ACCESS   accessible-for-notify
    STATUS       current
    DESCRIPTION  "The actual NE name reported by the expansion shelf as the name
                  of the NE to which it belongs."
    ::= { shelfInvEntry 6 }


shelfInvDiscoveredIPAddress OBJECT-TYPE
    SYNTAX       DisplayString (SIZE (0..15))
    MAX-ACCESS   accessible-for-notify
    STATUS       current
    DESCRIPTION  "The string representation of the actual NE NMS IP address
                  reported by the expansion shelf as the IP address of the NE to
                  which it belongs."
    ::= { shelfInvEntry 7 }


shelfInvDiscoveredShelfNum OBJECT-TYPE
    SYNTAX       INTEGER (11|21|31)
    MAX-ACCESS   accessible-for-notify
    STATUS       current
    DESCRIPTION  "The actual number of the expansion shelf reported by the
                  attached shelf."
    ::= { shelfInvEntry 8 }


shelfInvDiscoveredMSISerialNum OBJECT-TYPE
    SYNTAX       DisplayString (SIZE (0..16))
    MAX-ACCESS   accessible-for-notify
    STATUS       current
    DESCRIPTION  "The actual serial number of the Main Shelf Interface circuit
                  pack reported by the expansion shelf as the MSI serial number
                  of the NE main shelf to which it belongs."
    ::= { shelfInvEntry 9 }


shelfInvType OBJECT-TYPE
    SYNTAX       ShelfType
    MAX-ACCESS   read-only
    STATUS       current
    DESCRIPTION  "Indicates if the shelf functions as a main shelf or an
                  expansion shelf."
    ::= { shelfInvEntry 10 }


shelfInvShortName OBJECT-TYPE
    SYNTAX       DisplayString (SIZE (0..8))
    MAX-ACCESS   read-only
    STATUS       current
    DESCRIPTION  "A concise representation of the shelf brand name."
    ::= { shelfInvEntry 11 }


shelfInvName OBJECT-TYPE
    SYNTAX       DisplayString (SIZE (0..64))
    MAX-ACCESS   read-only
    STATUS       current
    DESCRIPTION  "The full representation of the shelf brand name."
    ::= { shelfInvEntry 12 }


shelfInvChassisPEC OBJECT-TYPE
    SYNTAX       DisplayString (SIZE (0..32))
    MAX-ACCESS   read-only
    STATUS       current
    DESCRIPTION  "A string representation of the Product Equipment Code for the
                  shelf chassis alone."
    ::= { shelfInvEntry 13 }


shelfInvChassisCLEI OBJECT-TYPE
    SYNTAX       DisplayString (SIZE (0..32))
    MAX-ACCESS   read-only
    STATUS       current
    DESCRIPTION  "A string representation of the Telcordia Common Language
                  Equipment Identifier for the shelf chassis alone."
    ::= { shelfInvEntry 14 }


shelfInvAssemblyPEC OBJECT-TYPE
    SYNTAX       DisplayString (SIZE (0..32))
    MAX-ACCESS   read-only
    STATUS       obsolete
    DESCRIPTION  "A string representation of the Product Equipment Code for the
                  shelf assembly, which bundles the shelf chassis, shelf
                  interface pack, and cooling unit."
    ::= { shelfInvEntry 15 }


shelfInvRev OBJECT-TYPE
    SYNTAX       INTEGER (1..65535)
    MAX-ACCESS   read-only
    STATUS       current
    DESCRIPTION  "The shelf hardware revision number. A value of 0 indicates
                  that the revision is unspecified."
    ::= { shelfInvEntry 16 }


shelfInvConfig OBJECT-TYPE
    SYNTAX       ShelfConfigType
    MAX-ACCESS   read-only
    STATUS       deprecated
    DESCRIPTION  "The shelf configuration with respect to the number of slots
                  for holding replaceable circuit packs.
                  
                  Note: This object is no longer supported as of BTI 7000
                  Release 8.1.0, and is maintained in the MIB for backwards-
                  compatibility for management of pre-8.1 nodes."
    ::= { shelfInvEntry 17 }

shelfInvUSI OBJECT-TYPE
    SYNTAX       DisplayString (SIZE (0..32))
    MAX-ACCESS   read-only
    STATUS       current
    DESCRIPTION  "The Unique Serial Identifier (only for FNC-branded equipment)"
    ::= { shelfInvEntry 18 }

shelfInvSerialNum OBJECT-TYPE
    SYNTAX       DisplayString (SIZE (0..32))
    MAX-ACCESS   read-only
    STATUS       current
    DESCRIPTION  "The serial number of the unit."
    ::= { shelfInvEntry 19 }

shelfInvMfgDate OBJECT-TYPE
    SYNTAX       DisplayString (SIZE (0..16))
    MAX-ACCESS   read-only
    STATUS       current
    DESCRIPTION  "The shelf manufacture date in the format YYYY-MM-DD."
    ::= { shelfInvEntry 20 }


shelfInvMfgLoc OBJECT-TYPE
    SYNTAX       DisplayString (SIZE (0..32))
    MAX-ACCESS   read-only
    STATUS       current
    DESCRIPTION  "The shelf manufacture location."
    ::= { shelfInvEntry 21 }


shelfInvTestDate OBJECT-TYPE
    SYNTAX       DisplayString (SIZE (0..16))
    MAX-ACCESS   read-only
    STATUS       current
    DESCRIPTION  "The shelf test date in the format YYYY-MM-DD."
    ::= { shelfInvEntry 22 }


shelfInvTestLoc OBJECT-TYPE
    SYNTAX       DisplayString (SIZE (0..32))
    MAX-ACCESS   read-only
    STATUS       current
    DESCRIPTION  "The shelf test location."
    ::= { shelfInvEntry 23 }
                   
-----------------------------------------------------------------------
-- Objects related to the physical circuit packs inventory within
-- the slots of the system
-- 
-- A listing of the physically detected circuit packs and other
-- replaceable units can be retrieved from the slotInvTable. The following
-- table lists the readable objects in each entry of the slotInvTable.
-----------------------------------------------------------------------


slotInvTable OBJECT-TYPE
    SYNTAX       SEQUENCE OF SlotInvEntry
    MAX-ACCESS   not-accessible
    STATUS       current
    DESCRIPTION  "This table contains one row for every slot on every shelf of
                  the NE in which a circuit pack or other replaceable unit is
                  seated. Each row contains a list of attributes that pertain to
                  the circuit pack within the slot."
    ::= { inventory 2 }


slotInvEntry OBJECT-TYPE
    SYNTAX       SlotInvEntry
    MAX-ACCESS   not-accessible
    STATUS       current
    DESCRIPTION  "The conceptual row object of the slot inventory table."
    INDEX        { slotInvShelfIdx,
                   slotInvSlotTypeIdx,
                   slotInvSlotIdx }
    ::= { slotInvTable 1 }


SlotInvEntry ::= SEQUENCE { slotInvShelfIdx         INTEGER,
                            slotInvSlotTypeIdx      SlotType,
                            slotInvSlotIdx          INTEGER,
                            slotInvSWVersion        DisplayString,
                            slotInvPackShortName    DisplayString,
                            slotInvPackName         DisplayString,
                            slotInvPackPEC          DisplayString,
                            slotInvPackCLEI         DisplayString,
                            slotInvPackSerialNum    DisplayString,
                            slotInvPackRev          INTEGER,
                            slotInvPackMfgDate      DisplayString,
                            slotInvPackMfgLoc       DisplayString,
                            slotInvPackTestDate     DisplayString,
                            slotInvPackTestLoc      DisplayString,
                            slotInvUpgradeStage     UpgradeCompleteStage,
                            slotInvUpgradeResult    INTEGER,
                            slotInvPackUSI          DisplayString,
                            slotInvTempHighTh       INTEGER,
                            slotInvTempShutdownTh   INTEGER}


slotInvShelfIdx OBJECT-TYPE
    SYNTAX       INTEGER (1|11|21|31)
    MAX-ACCESS   accessible-for-notify
    STATUS       current
    DESCRIPTION  "The number of the shelf on which the slot inventory item is
                  detected."
    ::= { slotInvEntry 1 }


slotInvSlotTypeIdx OBJECT-TYPE
    SYNTAX       SlotType
    MAX-ACCESS   accessible-for-notify
    STATUS       current
    DESCRIPTION  "The type of slot that contains the inventory item."
    ::= { slotInvEntry 2 }


slotInvSlotIdx OBJECT-TYPE
    SYNTAX       INTEGER (0..20)
    MAX-ACCESS   accessible-for-notify
    STATUS       current
    DESCRIPTION  "The number of the slot within the shelf containing the
                  inventory item. The number is from 1 to 20 for regular circuit
                  pack slots. For main shelf interface type slots, the number
                  is set to 0. For 7060/7030/7020 expansion shelf interface and 
                  cooling unit type slots, the number is set to 0. 
                  For 7200 common communications module type slots, the number 
                  is 1 or 2. For 7200 cooling unit type slots, the number is 
                  from 1 to 4."
    ::= { slotInvEntry 3 }


slotInvSWVersion OBJECT-TYPE
    SYNTAX       DisplayString (SIZE (0..32))
    MAX-ACCESS   accessible-for-notify
    STATUS       current
    DESCRIPTION  "The version of the software running on the circuit pack in the
                  given slot."
    ::= { slotInvEntry 4 }


slotInvPackShortName OBJECT-TYPE
    SYNTAX       DisplayString (SIZE (0..8))
    MAX-ACCESS   read-only
    STATUS       current
    DESCRIPTION  "A concise representation of the name of the circuit pack or
                  unit."
    ::= { slotInvEntry 5 }


slotInvPackName OBJECT-TYPE
    SYNTAX       DisplayString (SIZE (0..64))
    MAX-ACCESS   read-only
    STATUS       current
    DESCRIPTION  "The full name of the circuit pack or unit."
    ::= { slotInvEntry 6 }


slotInvPackPEC OBJECT-TYPE
    SYNTAX       DisplayString (SIZE (0..32))
    MAX-ACCESS   read-only
    STATUS       current
    DESCRIPTION  "The Product Equipment Code for the circuit pack or unit."
    ::= { slotInvEntry 7 }


slotInvPackCLEI OBJECT-TYPE
    SYNTAX       DisplayString (SIZE (0..32))
    MAX-ACCESS   read-only
    STATUS       current
    DESCRIPTION  "The Telcordia Common Language Equipment Identifier for the
                  circuit pack or unit."
    ::= { slotInvEntry 8 }


slotInvPackSerialNum OBJECT-TYPE
    SYNTAX       DisplayString (SIZE (0..32))
    MAX-ACCESS   read-only
    STATUS       current
    DESCRIPTION  "The serial number of the unit."
    ::= { slotInvEntry 9 }


slotInvPackRev OBJECT-TYPE
    SYNTAX       INTEGER (1..65535)
    MAX-ACCESS   read-only
    STATUS       current
    DESCRIPTION  "The circuit pack or unit hardware revision number. A value of
                  0 indicates that the revision is unspecified."
    ::= { slotInvEntry 10 }


slotInvPackMfgDate OBJECT-TYPE
    SYNTAX       DisplayString (SIZE (0..16))
    MAX-ACCESS   read-only
    STATUS       current
    DESCRIPTION  "The circuit pack manufacture date in the format YYYY-MM-DD."
    ::= { slotInvEntry 11 }


slotInvPackMfgLoc OBJECT-TYPE
    SYNTAX       DisplayString (SIZE (0..32))
    MAX-ACCESS   read-only
    STATUS       current
    DESCRIPTION  "The circuit pack manufacture location."
    ::= { slotInvEntry 12 }


slotInvPackTestDate OBJECT-TYPE
    SYNTAX       DisplayString (SIZE (0..16))
    MAX-ACCESS   read-only
    STATUS       current
    DESCRIPTION  "The circuit pack test date in the format YYYY-MM-DD."
    ::= { slotInvEntry 13 }


slotInvPackTestLoc OBJECT-TYPE
    SYNTAX       DisplayString (SIZE (0..32))
    MAX-ACCESS   read-only
    STATUS       current
    DESCRIPTION  "The circuit pack test location."
    ::= { slotInvEntry 14 }


slotInvUpgradeStage OBJECT-TYPE
    SYNTAX       UpgradeCompleteStage
    MAX-ACCESS   accessible-for-notify
    STATUS       current
    DESCRIPTION  "The stage of the circuit pack upgrade process that has been
                  completed."
    ::= { slotInvEntry 15 }


slotInvUpgradeResult OBJECT-TYPE
    SYNTAX       INTEGER { success (1),
                           failure (2) }
    MAX-ACCESS   accessible-for-notify
    STATUS       current
    DESCRIPTION  "Indicates if the identified stage of the circuit pack upgrade
                  process has resulted in success or failure."
    ::= { slotInvEntry 16 }


slotInvPackUSI OBJECT-TYPE
    SYNTAX       DisplayString (SIZE (0..32))
    MAX-ACCESS   read-only
    STATUS       current
    DESCRIPTION  "The Unique Serial Identifier (only for FNC-branded equipment)"
    ::= { slotInvEntry 17 }

slotInvTempHighTh OBJECT-TYPE
    SYNTAX       INTEGER (1..65535)
    UNITS        "degrees Celsius"
    MAX-ACCESS   read-only
    STATUS       current
    DESCRIPTION  "The circuit pack high temperature threshold."
    ::= { slotInvEntry 18 }

slotInvTempShutdownTh OBJECT-TYPE
    SYNTAX       INTEGER (1..65535)
    UNITS        "degrees Celsius"
    MAX-ACCESS   read-only
    STATUS       current
    DESCRIPTION  "The circuit pack shutdown temperature threshold."
    ::= { slotInvEntry 19 }

-----------------------------------------------------------------------
-- Objects related to the physical SFP (Small Formfactor Pluggable),
-- XFP (10 Gigabit Small Formfactor Pluggable) inventory or other
-- pluggable transceivers within the circuit packs of the system
-- 
-- A listing of pluggable transceiver devices that are physically
-- present can be retrieved from the pluggableInvTable. Pluggable
-- transceivers consist of SFPs and XFPs that are on the following types
-- of circuit packs:
--   Multiport System Control Processor (MSCP) circuit pack
--   Expansion Shelf Interface (ESI) circuit pack
--   Wavelength conversion (WM, WR and WT) circuit packs
--   Transponder (TPR) circuit packs
-- 
-- The following table lists the readable objects in each entry of the
-- pluggableInvTable.
-----------------------------------------------------------------------


pluggableInvTable OBJECT-TYPE
    SYNTAX       SEQUENCE OF PluggableInvEntry
    MAX-ACCESS   not-accessible
    STATUS       current
    DESCRIPTION  "This table contains one row for every SFP/XFP or other
                  pluggable present on any circuit pack or other replaceable
                  unit present in the NE. Each row contains a list of attributes
                  that pertain to the detected SFP/XFP."
    ::= { inventory 3 }


pluggableInvEntry OBJECT-TYPE
    SYNTAX       PluggableInvEntry
    MAX-ACCESS   not-accessible
    STATUS       current
    DESCRIPTION  "The conceptual row object of the pluggable inventory table."
    INDEX        { pluggableInvShelfIdx,
                   pluggableInvSlotTypeIdx,
                   pluggableInvSlotIdx,
                   pluggableInvPortIdx }
    ::= { pluggableInvTable 1 }


PluggableInvEntry ::= SEQUENCE { pluggableInvShelfIdx          INTEGER,
                                 pluggableInvSlotTypeIdx       SlotType,
                                 pluggableInvSlotIdx           INTEGER,
                                 pluggableInvPortIdx           INTEGER,
                                 pluggableInvType              INTEGER,
                                 pluggableInvPEC               DisplayString,
                                 pluggableInvCLEI              DisplayString,
                                 pluggableInvVendorName        DisplayString,
                                 pluggableInvVendorOUI         DisplayString,
                                 pluggableInvVendorPartNum     DisplayString,
                                 pluggableInvVendorRev         DisplayString,
                                 pluggableInvVendorSerialNum   DisplayString,
                                 pluggableInvMfgDate           DisplayString,
                                 pluggableInvConnectorType     INTEGER,
                                 pluggableInvMinBitRate        INTEGER,
                                 pluggableInvMaxBitRate        INTEGER,
                                 pluggableInvNomBitRate        INTEGER,
                                 pluggableInvEncoding          DisplayString,
                                 pluggableInvWavelength        FixedX100,
                                 pluggableInvReach             INTEGER,
                                 pluggableInvTxFaultImpl       TruthValue,
                                 pluggableInvLOSImpl           TruthValue,
                                 pluggableInvDDiagImpl         TruthValue,
                                 pluggableInvTxDisableImpl     TruthValue,
                                 pluggableInvMedia             INTEGER, 
                                 pluggableInvUSI               DisplayString,
                                 pluggableInvWavelengthMin     FixedX100,
                                 pluggableInvWavelengthMax     FixedX100,
                                 pluggableInvWavelengthSpacing INTEGER }


pluggableInvShelfIdx OBJECT-TYPE
    SYNTAX       INTEGER (1|11|21|31)
    MAX-ACCESS   accessible-for-notify
    STATUS       current
    DESCRIPTION  "The number of the shelf on which the pluggable inventory item
                  resides."
    ::= { pluggableInvEntry 1 }


pluggableInvSlotTypeIdx OBJECT-TYPE
    SYNTAX       SlotType
    MAX-ACCESS   accessible-for-notify
    STATUS       current
    DESCRIPTION  "The type of slot containing the pluggable inventory item."
    ::= { pluggableInvEntry 2 }


pluggableInvSlotIdx OBJECT-TYPE
    SYNTAX       INTEGER (1..20)
    MAX-ACCESS   accessible-for-notify
    STATUS       current
    DESCRIPTION  "The number of the slot that contains the pluggable inventory
                  item."
    ::= { pluggableInvEntry 3 }


pluggableInvPortIdx OBJECT-TYPE
    SYNTAX       INTEGER (1..5)
    MAX-ACCESS   accessible-for-notify
    STATUS       current
    DESCRIPTION  "The number of the port on the circuit pack that contains the
                  pluggable inventory item."
    ::= { pluggableInvEntry 4 }


pluggableInvType OBJECT-TYPE
    SYNTAX       INTEGER { unknown (1),
                           sfp     (2),
                           xfp     (3) }
    MAX-ACCESS   read-only
    STATUS       current
    DESCRIPTION  "The type of small form-factor pluggable inventory item."
    ::= { pluggableInvEntry 5 }


pluggableInvPEC OBJECT-TYPE
    SYNTAX       DisplayString (SIZE (0..32))
    MAX-ACCESS   read-only
    STATUS       current
    DESCRIPTION  "The Product Equipment Code for the pluggable inventory item."
    ::= { pluggableInvEntry 6 }


pluggableInvCLEI OBJECT-TYPE
    SYNTAX       DisplayString (SIZE (0..32))
    MAX-ACCESS   read-only
    STATUS       current
    DESCRIPTION  "The Telcordia Common Language Equipment Identifier for the
                  pluggable inventory item."
    ::= { pluggableInvEntry 7 }


pluggableInvVendorName OBJECT-TYPE
    SYNTAX       DisplayString (SIZE (0..20))
    MAX-ACCESS   read-only
    STATUS       current
    DESCRIPTION  "The Vendor Name of the pluggable inventory item."
    ::= { pluggableInvEntry 8 }


pluggableInvVendorOUI OBJECT-TYPE
    SYNTAX       DisplayString (SIZE (0..8))
    MAX-ACCESS   read-only
    STATUS       current
    DESCRIPTION  "The Vendor IEEE Organizationally Unique Identifier."
    ::= { pluggableInvEntry 9 }


pluggableInvVendorPartNum OBJECT-TYPE
    SYNTAX       DisplayString (SIZE (0..20))
    MAX-ACCESS   read-only
    STATUS       current
    DESCRIPTION  "The Vendor Part Number."
    ::= { pluggableInvEntry 10 }


pluggableInvVendorRev OBJECT-TYPE
    SYNTAX       DisplayString (SIZE (0..8))
    MAX-ACCESS   read-only
    STATUS       current
    DESCRIPTION  "The Vendor Revision Number."
    ::= { pluggableInvEntry 11 }


pluggableInvVendorSerialNum OBJECT-TYPE
    SYNTAX       DisplayString (SIZE (0..32))
    MAX-ACCESS   read-only
    STATUS       current
    DESCRIPTION  "The Vendor Serial Number."
    ::= { pluggableInvEntry 12 }


pluggableInvMfgDate OBJECT-TYPE
    SYNTAX       DisplayString (SIZE (0..16))
    MAX-ACCESS   read-only
    STATUS       current
    DESCRIPTION  "The manufacture date in the format YYYY-MM-DD.."
    ::= { pluggableInvEntry 13 }


pluggableInvConnectorType OBJECT-TYPE
    SYNTAX       INTEGER { unknown (1),   -- Unknown or unspecified
                           sc      (2),   -- SC
                           fcs1cc  (3),   -- Fibre Channel Style 1 Copper Connector
                           fcs2cc  (4),   -- Fibre Channel Style 2 Copper Connector
                           bnctnc  (5),   -- BNC/TNC
                           fcch    (6),   -- Fibre Channel Coaxial Headers
                           fj      (7),   -- FiberJack
                           lc      (8),   -- LC
                           mtrj    (9),   -- MT-RJ
                           mu      (10),  -- MU
                           sg      (11),  -- SG
                           op      (12),  -- Optical Pigtail
                           hssdc2  (13),  -- HSSDC II
                           cp      (14),  -- Copper Pigtail
                           vs      (15) } -- Vendor Specific
    MAX-ACCESS   read-only
    STATUS       current
    DESCRIPTION  "The type of connector on the pluggable unit."
    ::= { pluggableInvEntry 14 }


pluggableInvMinBitRate OBJECT-TYPE
    SYNTAX       INTEGER (0..65535)
    UNITS        "MBits/sec"
    MAX-ACCESS   read-only
    STATUS       current
    DESCRIPTION  "The minimum bit rate supported by the pluggable. A value of 0
                  means unspecified."
    ::= { pluggableInvEntry 15 }


pluggableInvMaxBitRate OBJECT-TYPE
    SYNTAX       INTEGER (0..65535)
    UNITS        "MBits/sec"
    MAX-ACCESS   read-only
    STATUS       current
    DESCRIPTION  "The maximum bit rate supported by the pluggable. A value of 0
                  means unspecified."
    ::= { pluggableInvEntry 16 }


pluggableInvNomBitRate OBJECT-TYPE
    SYNTAX       INTEGER (0..65535)
    UNITS        "MBits/sec"
    MAX-ACCESS   read-only
    STATUS       current
    DESCRIPTION  "The nominal bit rate supported by the pluggable. A value of 0
                  means unspecified."
    ::= { pluggableInvEntry 17 }


pluggableInvEncoding OBJECT-TYPE
    SYNTAX       DisplayString (SIZE (0..64))
    MAX-ACCESS   read-only
    STATUS       current
    DESCRIPTION  "A textual comma-delimited list of serial encoding mechanisms
                  supported by the pluggable."
    ::= { pluggableInvEntry 18 }


pluggableInvWavelength OBJECT-TYPE
    SYNTAX       FixedX100
    UNITS        "nanometers/100"
    MAX-ACCESS   read-only
    STATUS       current
    DESCRIPTION  "The wavelength transmitted by the pluggable. A value of 0
                  means unspecified."
    ::= { pluggableInvEntry 19 }


pluggableInvReach OBJECT-TYPE
    SYNTAX       INTEGER (0..65535)
    UNITS        "kilometers"
    MAX-ACCESS   read-only
    STATUS       current
    DESCRIPTION  "The reach supported by the pluggable. A value of 0 means
                  unspecified."
    ::= { pluggableInvEntry 20 }


pluggableInvTxFaultImpl OBJECT-TYPE
    SYNTAX       TruthValue
    MAX-ACCESS   read-only
    STATUS       current
    DESCRIPTION  "Indicates if the pluggable implements the Transmit Fault
                  signal."
    ::= { pluggableInvEntry 21 }


pluggableInvLOSImpl OBJECT-TYPE
    SYNTAX       TruthValue
    MAX-ACCESS   read-only
    STATUS       current
    DESCRIPTION  "Indicates if the pluggable implements the Loss of Signal
                  signal."
    ::= { pluggableInvEntry 22 }


pluggableInvDDiagImpl OBJECT-TYPE
    SYNTAX       TruthValue
    MAX-ACCESS   read-only
    STATUS       current
    DESCRIPTION  "Indicates if the pluggable implements support for Digital
                  Diagnostics."
    ::= { pluggableInvEntry 23 }


pluggableInvTxDisableImpl OBJECT-TYPE
    SYNTAX       TruthValue
    MAX-ACCESS   read-only
    STATUS       current
    DESCRIPTION  "Indicates if the pluggable implements support for disabling
                  the transmit laser."
    ::= { pluggableInvEntry 24 }


pluggableInvMedia OBJECT-TYPE
    SYNTAX       INTEGER { unknown    (1),
                           electrical (2),
                           optical    (3) }
    MAX-ACCESS   read-only
    STATUS       current
    DESCRIPTION  "The physical media type of the pluggable"
    ::= { pluggableInvEntry 25 }

pluggableInvUSI OBJECT-TYPE
    SYNTAX       DisplayString (SIZE (0..32))
    MAX-ACCESS   read-only
    STATUS       current
    DESCRIPTION  "The Unique Serial Identifier (only for FNC-branded equipment)"
    ::= { pluggableInvEntry 26 }

pluggableInvWavelengthMin OBJECT-TYPE
    SYNTAX       FixedX100
    UNITS        "nanometers/100"
    MAX-ACCESS   read-only
    STATUS       current
    DESCRIPTION  "The wavelength minimum for the tunable pluggable. A value of 0
                  means unspecified. "
    ::= { pluggableInvEntry 27 }

pluggableInvWavelengthMax OBJECT-TYPE
    SYNTAX       FixedX100
    UNITS        "nanometers/100"
    MAX-ACCESS   read-only
    STATUS       current
    DESCRIPTION  "The wavelength maximum for the tunable pluggable.A value of 0
                  means unspecified."
    ::= { pluggableInvEntry 28 }

pluggableInvWavelengthSpacing OBJECT-TYPE
    SYNTAX       INTEGER ( 0 | 50 | 100 )
    UNITS        "GHz"
    MAX-ACCESS   read-only
    STATUS       current
    DESCRIPTION  "The wavelength spacing for the tunable pluggable. A value of 0
                  means unspecified."
    ::= { pluggableInvEntry 29 }


-----------------------------------------------------------------------
-- Objects related to the physical XFP (10 Gigabit Small Formfactor Pluggable)
-- inventory within the circuit packs of the system
-- 
-- A listing of pluggable transceiver devices that are physically
-- present can be retrieved from the pluggableInvTable. Pluggable
-- transceivers consist of XFPs that are on the following types
-- of circuit packs:
-- � Wavelength conversion (WM, WR and WT) circuit packs
-- � Transponder (TPR) circuit packs
-- 
-- The pluggableInvRestartOpTable is used to perform pluggable restarts. There is one row in
-- the table for every restartable pluggable that is provisioned on the system. The
-- pluggable restart is performed by setting the pluggableInvRestartOpCmd for the targeted
-- pluggable row to perform a coldRestart.
-- 
-- The following table lists the objects in each entry of the pluggableInvRestartOpTable.
-----------------------------------------------------------------------

pluggableInvRestartOpTable OBJECT-TYPE
    SYNTAX       SEQUENCE OF PluggableInvRestartOpEntry
    MAX-ACCESS   not-accessible
    STATUS       current
    DESCRIPTION  "This table contains one row for every provisioned restartable
                  pluggable on a circuit pack."
    ::= { pluggableInvOperations 1 }


pluggableInvRestartOpEntry OBJECT-TYPE
    SYNTAX       PluggableInvRestartOpEntry
    MAX-ACCESS   not-accessible
    STATUS       current
    DESCRIPTION  "The conceptual row object of the pluggable restart
                  operation table."
    INDEX        { pluggableInvRestartOpTypeIdx,
                   pluggableInvRestartOpShelfIdx,
                   pluggableInvRestartOpSlotIdx,
                   pluggableInvRestartOpPortIdx }
    ::= { pluggableInvRestartOpTable 1 }


PluggableInvRestartOpEntry ::= SEQUENCE { pluggableInvRestartOpTypeIdx    INTEGER,
                                          pluggableInvRestartOpShelfIdx   INTEGER,
					  pluggableInvRestartOpSlotIdx    INTEGER,
					  pluggableInvRestartOpPortIdx    INTEGER,
					  pluggableInvRestartOpCmd        INTEGER }


pluggableInvRestartOpTypeIdx OBJECT-TYPE
    SYNTAX       INTEGER { unknown (1),
                           xfp     (3) }
    MAX-ACCESS   not-accessible
    STATUS       current
    DESCRIPTION  "The type of small form-factor pluggable inventory item targeted for the restart
                  operation."
    ::= { pluggableInvRestartOpEntry 1 }

pluggableInvRestartOpShelfIdx OBJECT-TYPE
    SYNTAX       INTEGER (1|11|21|31)
    MAX-ACCESS   not-accessible
    STATUS       current
    DESCRIPTION  "The number of the shelf on which the pluggable inventory item
                  resides targeted for the restart operation is provisioned."
    ::= { pluggableInvRestartOpEntry 2 }

pluggableInvRestartOpSlotIdx OBJECT-TYPE
    SYNTAX       INTEGER (1..20)
    MAX-ACCESS   not-accessible
    STATUS       current
    DESCRIPTION  "The number of the slot that contains the pluggable inventory
                  item targeted for the restart operation is provisioned."
    ::= { pluggableInvRestartOpEntry 3 }

pluggableInvRestartOpPortIdx OBJECT-TYPE
    SYNTAX       INTEGER (1..28)
    MAX-ACCESS   not-accessible
    STATUS       current
    DESCRIPTION  "The number of the port on the circuit pack that contains the
                  pluggable inventory item."
    ::= { pluggableInvRestartOpEntry 4 }

pluggableInvRestartOpCmd OBJECT-TYPE
    SYNTAX       INTEGER { noOp        (1),
                           coldRestart (2) }
    MAX-ACCESS   read-write
    STATUS       current
    DESCRIPTION  "Used to perform a restart operation as follows.
                  - coldRestart causes a pluggable restart

                  When this object is read, the value noOp is returned."
    ::= { pluggableInvRestartOpEntry 5 }


-----------------------------------------------------------------------
-- The slotInvDataTable provides a listing of any specialized data
-- records available for slot inventory entries on the system.
-----------------------------------------------------------------------


slotInvDataTable OBJECT-TYPE
    SYNTAX       SEQUENCE OF SlotInvDataEntry
    MAX-ACCESS   not-accessible
    STATUS       current
    DESCRIPTION  "This table contains a listing of any specialized data
                  records available for the slot inventory entries on the
                  system. Each row contains a single item of data for a
                  specialized data record for a slot inventory entry."
    ::= { inventory 4 }


slotInvDataEntry OBJECT-TYPE
    SYNTAX       SlotInvDataEntry
    MAX-ACCESS   not-accessible
    STATUS       current
    DESCRIPTION  "The conceptual row object of the slot inventory data table."
    INDEX        { slotInvDataShelfIdx,
                   slotInvDataSlotTypeIdx,
                   slotInvDataSlotIdx,
                   slotInvDataRecordIdx,
                   slotInvDataNameIdx }
    ::= { slotInvDataTable 1 }


SlotInvDataEntry ::= SEQUENCE { slotInvDataShelfIdx         INTEGER,
                                slotInvDataSlotTypeIdx      SlotType,
                                slotInvDataSlotIdx          INTEGER,
                                slotInvDataRecordIdx        Unsigned32,
                                slotInvDataNameIdx          INTEGER,
                                slotInvDataValue            DisplayString }


slotInvDataShelfIdx OBJECT-TYPE
    SYNTAX       INTEGER (1|11|21|31)
    MAX-ACCESS   not-accessible
    STATUS       current
    DESCRIPTION  "The number of the shelf on which the slot inventory item is
                  detected."
    ::= { slotInvDataEntry 1 }


slotInvDataSlotTypeIdx OBJECT-TYPE
    SYNTAX       SlotType
    MAX-ACCESS   not-accessible
    STATUS       current
    DESCRIPTION  "The type of slot that contains the inventory item."
    ::= { slotInvDataEntry 2 }


slotInvDataSlotIdx OBJECT-TYPE
    SYNTAX       INTEGER (0..20)
    MAX-ACCESS   not-accessible
    STATUS       current
    DESCRIPTION  "The number of the slot within the shelf containing the
                  inventory item. The number is from 1 to 20 for regular circuit
                  pack slots. For shelfInterface and coolingUnit type slots, the
                  number is set to 0."
    ::= { slotInvDataEntry 3 }


slotInvDataRecordIdx OBJECT-TYPE
    SYNTAX       Unsigned32
    MAX-ACCESS   not-accessible
    STATUS       current
    DESCRIPTION  "The specialized data record index."
    ::= { slotInvDataEntry 4 }


slotInvDataNameIdx OBJECT-TYPE
    SYNTAX       INTEGER { wavelength  (1),
                           loss        (2),
                           dispersion  (3) }
    MAX-ACCESS   not-accessible
    STATUS       current
    DESCRIPTION  "The name of the data item."
    ::= { slotInvDataEntry 5 }


slotInvDataValue OBJECT-TYPE
    SYNTAX       DisplayString
    MAX-ACCESS   read-only
    STATUS       current
    DESCRIPTION  "The value of the data item."
    ::= { slotInvDataEntry 6 }



-----------------------------------------------------------------------
-- Objects related to provisioned shelves on the system
-- 
-- A listing of provisioned shelves is contained in the shelfTable of
-- the BTI 7000 Series MIB. When retrieved, this table lists one row 
-- for every provisioned shelf. There is at least one row for the main 
-- shelf that is auto provisioned and it can never be deprovisioned.
-- There is also one additional row for each provisioned expansion
-- shelf.
-- 
-- To manually provision an expansion shelf, a row must be created in
-- the shelfTable. To deprovision an expansion shelf, its row must be
-- destroyed. The following table lists the objects in each entry of
-- the shelfTable.
-----------------------------------------------------------------------


shelfTable OBJECT-TYPE
    SYNTAX       SEQUENCE OF ShelfEntry
    MAX-ACCESS   not-accessible
    STATUS       current
    DESCRIPTION  "This table contains one row for every provisioned shelf on the
                  NE. Each row contains a list of attributes that pertain to a
                  provisioned shelf."
    ::= { equipment 1 }


shelfEntry OBJECT-TYPE
    SYNTAX       ShelfEntry
    MAX-ACCESS   not-accessible
    STATUS       current
    DESCRIPTION  "The conceptual row object of the shelf table."
    INDEX        { shelfIdx }
    ::= { shelfTable 1 }


ShelfEntry ::= SEQUENCE { shelfIdx           INTEGER,
                          shelfProvConfig    ShelfConfigType,
                          shelfDiscConfig    ShelfConfigType,
                          shelfType          ShelfType,
                          shelfPEC           DisplayString,
                          shelfAdminStatus   AdminStatus,
                          shelfOperStatus    OperStatus,
                          shelfOperStatQlfr  OperStatQlfr,
                          shelfId            DisplayString,
                          shelfCustom1       DisplayString,
                          shelfCustom2       DisplayString,
                          shelfCustom3       DisplayString,
			  shelfPowerFeedA    PowerFeedModeType,
			  shelfPowerFeedB    PowerFeedModeType,
                          shelfRowStatus     RowStatus }


shelfIdx OBJECT-TYPE
    SYNTAX       INTEGER (1|11|21|31)
    MAX-ACCESS   accessible-for-notify
    STATUS       current
    DESCRIPTION  "The number of the shelf that has been provisioned. This is set
                  to 1 for the main shelf. Otherwise, the number is based on the
                  expansion shelf port number on which this shelf is expected to
                  be detected and the number of hops from the main shelf."
    ::= { shelfEntry 1 }

shelfProvConfig OBJECT-TYPE
    SYNTAX       ShelfConfigType
    MAX-ACCESS   read-create
    STATUS       deprecated
    DESCRIPTION  "The provisioned configuration for the shelf.
                  
                  Note: This object is no longer supported as of BTI 7000
                  Release 8.1.0, and is maintained in the MIB for backwards-
                  compatibility for management of pre-8.1 nodes."
    DEFVAL       { sixSlot }
    ::= { shelfEntry 2 }


shelfDiscConfig OBJECT-TYPE
    SYNTAX       ShelfConfigType
    MAX-ACCESS   accessible-for-notify
    STATUS       deprecated
    DESCRIPTION  "The configuration of the actual shelf discovered.
                  
                  Note: This object is no longer supported as of BTI 7000
                  Release 8.1.0, and is maintained in the MIB for backwards-
                  compatibility for management of pre-8.1 nodes."
    ::= { shelfEntry 3 }

shelfType OBJECT-TYPE
    SYNTAX       ShelfType
    MAX-ACCESS   read-create
    STATUS       current
    DESCRIPTION  "Indicates if the provisioned shelf is a main or expansion
                  shelf. Only expansion shelves can be created. The main shelf
                  is automatically provisioned and can never be de-provisioned."
    DEFVAL       { expansion }
    ::= { shelfEntry 4 }


shelfPEC OBJECT-TYPE
    SYNTAX       DisplayString (SIZE (1..32))
    MAX-ACCESS   read-create
    STATUS       current
    DESCRIPTION  "Indicates the provisioned shelf Product Equipment Code. This
                  is a mandatory object when a row of the shelf table is
                  created. The PEC can only be set at the time of row creation,
                  and it cannot be edited later."
    ::= { shelfEntry 5 }


shelfAdminStatus OBJECT-TYPE
    SYNTAX       AdminStatus
    MAX-ACCESS   read-create
    STATUS       current
    DESCRIPTION  "The administrative status of the shelf."
    DEFVAL       { enabled }
    ::= { shelfEntry 6 }


shelfOperStatus OBJECT-TYPE
    SYNTAX       OperStatus
    MAX-ACCESS   read-only
    STATUS       current
    DESCRIPTION  "The reported operational status of the shelf."
    ::= { shelfEntry 7 }


shelfOperStatQlfr OBJECT-TYPE
    SYNTAX       OperStatQlfr
    MAX-ACCESS   read-only
    STATUS       current
    DESCRIPTION  "A textual list of qualifiers of the reported operational
                  status of the shelf."
    ::= { shelfEntry 8 }


shelfId OBJECT-TYPE
    SYNTAX       DisplayString (SIZE (0..20))
    MAX-ACCESS   read-create
    STATUS       current
    DESCRIPTION  "Textual data recorded by the user to describe the provisioned
                  shelf in a manner useful to the user such as the location
                  where the shelf is installed."
    DEFVAL       { "" }
    ::= { shelfEntry 9 }


shelfCustom1 OBJECT-TYPE
    SYNTAX       DisplayString
    MAX-ACCESS   read-create
    STATUS       current
    DESCRIPTION  "A variable length text string for operating company use."
    DEFVAL       { "" }
    ::= { shelfEntry 10 }


shelfCustom2 OBJECT-TYPE
    SYNTAX       DisplayString
    MAX-ACCESS   read-create
    STATUS       current
    DESCRIPTION  "A variable length text string for operating company use."
    DEFVAL       { "" }
    ::= { shelfEntry 11 }


shelfCustom3 OBJECT-TYPE
    SYNTAX       DisplayString
    MAX-ACCESS   read-create
    STATUS       current
    DESCRIPTION  "A variable length text string for operating company use."
    DEFVAL       { "" }
    ::= { shelfEntry 12 }

shelfPowerFeedA OBJECT-TYPE
    SYNTAX       PowerFeedModeType
    MAX-ACCESS   read-create
    STATUS       current
    DESCRIPTION  "The power feed mode for rail A."
    DEFVAL       { dc }
    ::= { shelfEntry 13 }

shelfPowerFeedB OBJECT-TYPE
    SYNTAX       PowerFeedModeType
    MAX-ACCESS   read-create
    STATUS       current
    DESCRIPTION  "The power feed mode for rail B."
    DEFVAL       { dc }
    ::= { shelfEntry 14 }

shelfRowStatus OBJECT-TYPE
    SYNTAX       RowStatus
    MAX-ACCESS   read-create
    STATUS       current
    DESCRIPTION  "Used to control the addition and deletion of entries in the
                  shelf table, which in turn controls provisioning and
                  deprovisioning of shelf objects."
    ::= { shelfEntry 100 }



-----------------------------------------------------------------------
-- Objects related to provisioned circuit packs on the system
-- 
-- A listing of provisioned circuit packs is contained in the cpTable
-- of the BTI 7000 Series MIB. When retrieved, this table includes one
-- row for every provisioned circuit pack. There is at least one row 
-- for the System Control Processor (SCP) circuit pack that is auto
-- provisioned in slot 5 of the main shelf (This circuit pack
-- cannot be deprovisioned.). There is also an additional row for every
-- other provisioned circuit pack.
-- 
-- To manually provision a circuit pack, a row must be created in the
-- cpTable. To deprovision a circuit pack, its row must be destroyed.
-- 
-- Note: Circuit packs can only be provisioned in slots of the type
-- described as regular in the slotInvTable. Shelf interface and 
-- cooling units do not need to be provisioned.
-- 
-- The following table lists the objects in each entry of the cpTable.
-----------------------------------------------------------------------


cpTable OBJECT-TYPE
    SYNTAX       SEQUENCE OF CpEntry
    MAX-ACCESS   not-accessible
    STATUS       current
    DESCRIPTION  "This table contains one row for every provisioned circuit pack
                  on the NE. Each row contains a list of attributes that pertain
                  to a provisioned circuit pack."
    ::= { equipment 2 }


cpEntry OBJECT-TYPE
    SYNTAX       CpEntry
    MAX-ACCESS   not-accessible
    STATUS       current
    DESCRIPTION  "The conceptual row object of the circuit pack table."
    INDEX        { cpTypeIdx,
                   cpShelfIdx,
                   cpSlotIdx }
    ::= { cpTable 1 }


CpEntry ::= SEQUENCE { cpTypeIdx       CpType,
                       cpShelfIdx      INTEGER,
                       cpSlotIdx       INTEGER,
                       cpPEC           DisplayString,
                       cpAdminStatus   AdminStatus,
                       cpOperStatus    OperStatus,
                       cpOperStatQlfr  OperStatQlfr,
                       cpId            DisplayString,
                       cpCustom1       DisplayString,
                       cpCustom2       DisplayString,
                       cpCustom3       DisplayString,
                       cpUpgradeStage  UpgradeCompleteStage,
                       cpUpgradeResult INTEGER,
                       cpRowStatus     RowStatus }


cpTypeIdx OBJECT-TYPE
    SYNTAX       CpType
    MAX-ACCESS   accessible-for-notify
    STATUS       current
    DESCRIPTION  "The specific type of circuit pack provisioned."
    ::= { cpEntry 1 }


cpShelfIdx OBJECT-TYPE
    SYNTAX       INTEGER (0|1|11|21|31)
    MAX-ACCESS   accessible-for-notify
    STATUS       current
    DESCRIPTION  "The number of the shelf on which the circuit pack is
                  provisioned."
    ::= { cpEntry 2 }


cpSlotIdx OBJECT-TYPE
    SYNTAX       INTEGER (1..255)
    MAX-ACCESS   accessible-for-notify
    STATUS       current
    DESCRIPTION  "The number of the slot in which the circuit pack is
                  provisioned."
    ::= { cpEntry 3 }


cpPEC OBJECT-TYPE
    SYNTAX       DisplayString (SIZE (1..32))
    MAX-ACCESS   read-create
    STATUS       current
    DESCRIPTION  "Indicates the provisioned circuit pack Product Equipment Code.
                  This is a mandatory object when a row of the circuit pack
                  table is created. The PEC can only be set at the time of row
                  creation, and it cannot be edited later."
    ::= { cpEntry 4 }


cpAdminStatus OBJECT-TYPE
    SYNTAX       AdminStatus
    MAX-ACCESS   read-create
    STATUS       current
    DESCRIPTION  "The administrative status of the circuit pack."
    DEFVAL       { enabled }
    ::= { cpEntry 5 }


cpOperStatus OBJECT-TYPE
    SYNTAX       OperStatus
    MAX-ACCESS   read-only
    STATUS       current
    DESCRIPTION  "The reported operational status of the circuit pack."
    ::= { cpEntry 6 }


cpOperStatQlfr OBJECT-TYPE
    SYNTAX       OperStatQlfr
    MAX-ACCESS   read-only
    STATUS       current
    DESCRIPTION  "A textual list of qualifiers of the reported operational
                  status of the circuit pack."
    ::= { cpEntry 7 }


cpId OBJECT-TYPE
    SYNTAX       DisplayString (SIZE (0..20))
    MAX-ACCESS   read-create
    STATUS       current
    DESCRIPTION  "Textual data recorded by the user to describe the provisioned
                  circuit pack in a manner useful to the user."
    DEFVAL       { "" }
    ::= { cpEntry 8 }



cpCustom1 OBJECT-TYPE
    SYNTAX       DisplayString
    MAX-ACCESS   read-create
    STATUS       current
    DESCRIPTION  "A variable length text string for operating company use."
    DEFVAL       { "" }
    ::= { cpEntry 9 }


cpCustom2 OBJECT-TYPE
    SYNTAX       DisplayString
    MAX-ACCESS   read-create
    STATUS       current
    DESCRIPTION  "A variable length text string for operating company use."
    DEFVAL       { "" }
    ::= { cpEntry 10 }


cpCustom3 OBJECT-TYPE
    SYNTAX       DisplayString
    MAX-ACCESS   read-create
    STATUS       current
    DESCRIPTION  "A variable length text string for operating company use."
    DEFVAL       { "" }
    ::= { cpEntry 11 }


cpUpgradeStage OBJECT-TYPE
    SYNTAX       UpgradeCompleteStage
    MAX-ACCESS   accessible-for-notify
    STATUS       current
    DESCRIPTION  "Used in notifications sent during the circuit pack software
                  upgrade process. It indicates the stage of the circuit pack
                  upgrade process that has been completed."
    ::= { cpEntry 12 }


cpUpgradeResult OBJECT-TYPE
    SYNTAX       INTEGER { success (1),
                           failure (2) }
    MAX-ACCESS   accessible-for-notify
    STATUS       current
    DESCRIPTION  "Indicates if the identified stage of the circuit pack upgrade
                  process has resulted in success or failure."
    ::= { cpEntry 13 }



cpRowStatus OBJECT-TYPE
    SYNTAX       RowStatus
    MAX-ACCESS   read-create
    STATUS       current
    DESCRIPTION  "Used to control the addition and deletion of entries in the
                  circuit pack table, which in turn controls the provisioning
                  and de-provisioning of circuit pack objects."
    ::= { cpEntry 100 }



-----------------------------------------------------------------------
-- Objects related to provisioned Optical Amplifier facilities
-- 
-- A listing of provisioned optical amplifiers is contained in the 
-- oaTable of the BTI 7000 Series MIB. When retrieved, this table
-- provides one row for each provisioned optical amplifier.
-- 
-- To manually provision a optical amplifier, a row must be created in
-- the oaTable. To deprovision a optical amplifier, its row must be
-- destroyed. 
-- 
-- The following table lists the objects in each entry of the oaTable.
-----------------------------------------------------------------------


oaTable OBJECT-TYPE
    SYNTAX       SEQUENCE OF OaEntry
    MAX-ACCESS   not-accessible
    STATUS       current
    DESCRIPTION  "This table contains one row for every provisioned optical
                  amplifier facility on the NE. Each row contains a list of
                  attributes that pertain to the optical amplifier."
    ::= { facilities 1 }


oaEntry OBJECT-TYPE
    SYNTAX       OaEntry
    MAX-ACCESS   not-accessible
    STATUS       current
    DESCRIPTION  "The conceptual row object of the optical amplifier table."
    INDEX        { oaTypeIdx,
                   oaShelfIdx,
                   oaSlotIdx,
                   oaIdx }
    ::= { oaTable 1 }


OaEntry ::= SEQUENCE { oaTypeIdx                        OaType,
                       oaShelfIdx                       INTEGER,
                       oaSlotIdx                        INTEGER,
                       oaIdx                            INTEGER,
                       oaCaseTempMaxTh                  INTEGER,
                       oaCaseTempMaxShutdownTh          INTEGER,
                       oaLaserTempMinShutdownTh         INTEGER,
                       oaLaserTempMaxShutdownTh         INTEGER,
                       oaOpticalPwrReceivedMinTh        FixedX10,
                       oaOpticalPwrReceivedMaxTh        FixedX10,
                       oaSSIOpticalPwrReceivedMaxTh     FixedX10,
                       oaOpticalPwrTransmittedMinTh     FixedX10,
                       oaOpticalPwrTransmittedMaxTh     FixedX10,
                       oaBackReflectionSafetyTh         FixedX10,
                       oaMSInsertionLossMaxTh           FixedX10,
                       oaCaseTemp                       INTEGER,
                       oaLaser1Temp                     INTEGER,
                       oaLaser2Temp                     INTEGER,
                       oaOpticalPwrReceived             FixedX10,
                       oaSSIOpticalPwrReceived          FixedX10,
                       oaOpticalPwrTransmitted          FixedX10,
                       oaMSInsertionLoss                FixedX10,
                       oaEffectiveGain                  FixedX10,
                       oaFSOOpticalPwrTransmitted       FixedX10,
                       oaLaser1Current                  FixedX10,
                       oaLaser2Current                  FixedX10,
                       oaLaser1Power                    FixedX10,
                       oaLaser2Power                    FixedX10,
                       oaOpticalBackReflection          FixedX10,
                       oaVariableOpticalAttenuation     FixedX10,
                       oaAdminStatus                    AdminStatus,
                       oaOperStatus                     OperStatus,
                       oaOperStatQlfr                   OperStatQlfr,
                       oaAutoEnableTimer                HoursAndMinutes,
                       oaActAutoEnableTimer             HoursAndMinutes,
                       oaModeSetting                    INTEGER,
                       oaGainSetting                    FixedX10,
                       oaPwrSetting                     FixedX10,
                       oaTiltCompSetting                FixedX10,
                       oaStatus                         INTEGER,
                       oaLaserStatus                    INTEGER,
                       oaId1                            DisplayString,
                       oaId2                            DisplayString,
                       oaFiberType                      FiberType,
                       oaGrid                           WDMGrid,
                       oaNumChannels                    INTEGER,
                       oaCustom1                        DisplayString,
                       oaCustom2                        DisplayString,
                       oaCustom3                        DisplayString,
                       oaWavelength                     FixedX100,  
                       oaRemoteId                       DisplayString,                     
                       oaRowStatus                      RowStatus }


oaTypeIdx OBJECT-TYPE
    SYNTAX       OaType
    MAX-ACCESS   accessible-for-notify
    STATUS       current
    DESCRIPTION  "The specific type of optical amplifier provisioned."
    ::= { oaEntry 1 }


oaShelfIdx OBJECT-TYPE
    SYNTAX       INTEGER (1|11|21|31)
    MAX-ACCESS   accessible-for-notify
    STATUS       current
    DESCRIPTION  "The number of the shelf on which the optical amplifier
                  facility is provisioned."
    ::= { oaEntry 2 }


oaSlotIdx OBJECT-TYPE
    SYNTAX       INTEGER (1..20)
    MAX-ACCESS   accessible-for-notify
    STATUS       current
    DESCRIPTION  "The number of the slot in which the optical amplifier facility
                  is provisioned."
    ::= { oaEntry 3 }


oaIdx OBJECT-TYPE
    SYNTAX       INTEGER (1..1)
    MAX-ACCESS   accessible-for-notify
    STATUS       current
    DESCRIPTION  "The number of the port on the circuit pack on which the
                  optical amplifier facility is provisioned."
    ::= { oaEntry 4 }


oaCaseTempMaxTh OBJECT-TYPE
    SYNTAX       INTEGER (-32768..32767)
    UNITS        "degrees Celsius"
    MAX-ACCESS   read-create
    STATUS       current
    DESCRIPTION  "The case temperature threshold."
    DEFVAL       { 60 }
    ::= { oaEntry 5 }


oaCaseTempMaxShutdownTh OBJECT-TYPE
    SYNTAX       INTEGER (-32768..32767)
    UNITS        "degrees Celsius"
    MAX-ACCESS   read-only
    STATUS       current
    DESCRIPTION  "The case temperature shutdown threshold."
    ::= { oaEntry 6 }


oaLaserTempMinShutdownTh OBJECT-TYPE
    SYNTAX       INTEGER (-32768..32767)
    UNITS        "degrees Celsius"
    MAX-ACCESS   read-only
    STATUS       current
    DESCRIPTION  "The laser temperature minimum shutdown threshold. A default
                  value is provided when the optical amplifier is created based
                  on the optical amplifier type provisioned."
    ::= { oaEntry 7 }


oaLaserTempMaxShutdownTh OBJECT-TYPE
    SYNTAX       INTEGER (-32768..32767)
    UNITS        "degrees Celsius"
    MAX-ACCESS   read-only
    STATUS       current
    DESCRIPTION  "The laser temperature maximum shutdown threshold. A default
                  value is provided when the optical amplifier is created based
                  on the optical amplifier type provisioned."
    ::= { oaEntry 8 }


oaOpticalPwrReceivedMinTh OBJECT-TYPE
    SYNTAX       FixedX10
    UNITS        "dBm/10"
    MAX-ACCESS   read-create
    STATUS       current
    DESCRIPTION  "The optical power received minimum threshold. A default value
                  is provided when the optical amplifier is created based on the
                  optical amplifier type provisioned."
    ::= { oaEntry 9 }


oaOpticalPwrReceivedMaxTh OBJECT-TYPE
    SYNTAX       FixedX10
    UNITS        "dBm/10"
    MAX-ACCESS   read-create
    STATUS       current
    DESCRIPTION  "The optical power received maximum threshold. A default value
                  is provided when the optical amplifier is created based on the
                  optical amplifier type provisioned."
    ::= { oaEntry 10 }


oaSSIOpticalPwrReceivedMaxTh OBJECT-TYPE
    SYNTAX       FixedX10
    UNITS        "dBm/10"
    MAX-ACCESS   read-create
    STATUS       current
    DESCRIPTION  "The secondary stage input optical power received maximum
                  threshold. This object is applicable only to OLAM type
                  amplifiers."
    DEFVAL       { 55 }
    ::= { oaEntry 11 }


oaOpticalPwrTransmittedMinTh OBJECT-TYPE
    SYNTAX       FixedX10
    UNITS        "dBm/10"
    MAX-ACCESS   read-create
    STATUS       current
    DESCRIPTION  "The optical power transmitted minimum threshold. A default
                  value is provided when the optical amplifier is created based
                  on the optical amplifier type provisioned."
    ::= { oaEntry 12 }


oaOpticalPwrTransmittedMaxTh OBJECT-TYPE
    SYNTAX       FixedX10
    UNITS        "dBm/10"
    MAX-ACCESS   read-create
    STATUS       current
    DESCRIPTION  "The optical power transmitted maximum threshold. A default
                  value is provided when the optical amplifier is created based
                  on the optical amplifier type provisioned."
    ::= { oaEntry 13 }


oaBackReflectionSafetyTh OBJECT-TYPE
    SYNTAX       FixedX10
    UNITS        "dBm/10"
    MAX-ACCESS   read-only
    STATUS       current
    DESCRIPTION  "The optical back reflection safety threshold."
    ::= { oaEntry 14 }


oaMSInsertionLossMaxTh OBJECT-TYPE
    SYNTAX       FixedX10
    UNITS        "dB/10"
    MAX-ACCESS   read-create
    STATUS       current
    DESCRIPTION  "This is the mid-stage maximum insertion loss signal threshold.
                  It applies to mid-stage access amplifiers only."
    DEFVAL       { 150 }
    ::= { oaEntry 15 }


oaCaseTemp OBJECT-TYPE
    SYNTAX       INTEGER (-32768..32767)
    UNITS        "degrees Celsius"
    MAX-ACCESS   read-only
    STATUS       current
    DESCRIPTION  "The optical amplifier case temperature."
    ::= { oaEntry 16 }


oaLaser1Temp OBJECT-TYPE
    SYNTAX       INTEGER (-32768..32767)
    UNITS        "degrees Celsius"
    MAX-ACCESS   read-only
    STATUS       current
    DESCRIPTION  "The temperature of the optical amplifier laser 1."
    ::= { oaEntry 17 }


oaLaser2Temp OBJECT-TYPE
    SYNTAX       INTEGER (-32768..32767)
    UNITS        "degrees Celsius"
    MAX-ACCESS   read-only
    STATUS       current
    DESCRIPTION  "The temperature of the optical amplifier laser 2."
    ::= { oaEntry 18 }


oaOpticalPwrReceived OBJECT-TYPE
    SYNTAX       FixedX10
    UNITS        "dBm/10"
    MAX-ACCESS   read-only
    STATUS       current
    DESCRIPTION  "The optical power received on the input of the amplifier."
    ::= { oaEntry 19 }


oaSSIOpticalPwrReceived OBJECT-TYPE
    SYNTAX       FixedX10
    UNITS        "dBm/10"
    MAX-ACCESS   read-only
    STATUS       current
    DESCRIPTION  "The optical power received on the second stage of the
                  amplifier. It applies to mid-stage access amplifiers only."
    ::= { oaEntry 20 }


oaOpticalPwrTransmitted OBJECT-TYPE
    SYNTAX       FixedX10
    UNITS        "dBm/10"
    MAX-ACCESS   read-only
    STATUS       current
    DESCRIPTION  "The optical power transmitted at the output of the amplifier."
    ::= { oaEntry 21 }


oaMSInsertionLoss OBJECT-TYPE
    SYNTAX       FixedX10
    UNITS        "dB/10"
    MAX-ACCESS   read-only
    STATUS       current
    DESCRIPTION  "The mid-stage insertion loss. This object is only applicable
                  to OLAM type amplifiers."
    ::= { oaEntry 22 }


oaEffectiveGain OBJECT-TYPE
    SYNTAX       FixedX10
    UNITS        "dB/10"
    MAX-ACCESS   read-only
    STATUS       current
    DESCRIPTION  "The effective gain level of the optical amplifier."
    ::= { oaEntry 33 }


oaFSOOpticalPwrTransmitted OBJECT-TYPE
    SYNTAX       FixedX10
    UNITS        "dBm/10"
    MAX-ACCESS   read-only
    STATUS       current
    DESCRIPTION  "The optical power transmitted at the output of the first stage
                  of the amplifier. It applies to mid-stage access amplifiers
                  only."
    ::= { oaEntry 34 }


oaLaser1Current OBJECT-TYPE
    SYNTAX       FixedX10
    UNITS        "mAmp/10"
    MAX-ACCESS   read-only
    STATUS       current
    DESCRIPTION  "The optical amplifier laser 1 current."
    ::= { oaEntry 35 }


oaLaser2Current OBJECT-TYPE
    SYNTAX       FixedX10
    UNITS        "mAmp/10"
    MAX-ACCESS   read-only
    STATUS       current
    DESCRIPTION  "The optical amplifier laser 2 current."
    ::= { oaEntry 36 }


oaLaser1Power OBJECT-TYPE
    SYNTAX       FixedX10
    UNITS        "mWatts/10"
    MAX-ACCESS   read-only
    STATUS       current
    DESCRIPTION  "The optical amplifier laser 1 power."
    ::= { oaEntry 37 }


oaLaser2Power OBJECT-TYPE
    SYNTAX       FixedX10
    UNITS        "mWatts/10"
    MAX-ACCESS   read-only
    STATUS       current
    DESCRIPTION  "The optical amplifier laser 2 power."
    ::= { oaEntry 38 }


oaOpticalBackReflection OBJECT-TYPE
    SYNTAX       FixedX10
    UNITS        "dB/10"
    MAX-ACCESS   read-only
    STATUS       current
    DESCRIPTION  "The optical back reflection of the amplifier."
    ::= { oaEntry 39 }


oaVariableOpticalAttenuation OBJECT-TYPE
    SYNTAX       FixedX10
    UNITS        "dB/10"
    MAX-ACCESS   read-only
    STATUS       current
    DESCRIPTION  "The variable optical attenuation of the amplifier."
    ::= { oaEntry 40 }


oaAdminStatus OBJECT-TYPE
    SYNTAX       AdminStatus
    MAX-ACCESS   read-create
    STATUS       current
    DESCRIPTION  "The administrative status of the optical amplifier."
    DEFVAL       { enabled }
    ::= { oaEntry 41 }


oaOperStatus OBJECT-TYPE
    SYNTAX       OperStatus
    MAX-ACCESS   read-only
    STATUS       current
    DESCRIPTION  "The reported operational status of the optical amplifier."
    ::= { oaEntry 42 }


oaOperStatQlfr OBJECT-TYPE
    SYNTAX       OperStatQlfr
    MAX-ACCESS   read-only
    STATUS       current
    DESCRIPTION  "A textual list of qualifiers of the reported operational
                  status of the optical amplifier."
    ::= { oaEntry 43 }


oaAutoEnableTimer OBJECT-TYPE
    SYNTAX       HoursAndMinutes
    MAX-ACCESS   read-create
    STATUS       current
    DESCRIPTION  "Specifies the auto-enable timer for the targeted optical
                  amplifier. This value only applies if the oaAdminStatus object
                  is set to autoEnabled. Otherwise, the value returned is
                  000-00. The supported range of values is 000-00 to 096-00."
    DEFVAL       { "008-00" }
    ::= { oaEntry 44 }


oaActAutoEnableTimer OBJECT-TYPE
    SYNTAX       HoursAndMinutes
    MAX-ACCESS   read-only
    STATUS       current
    DESCRIPTION  "Indicates the time remaining on the auto-enable timer, if it
                  is actively counting down. Otherwise, the value returned is
                  000-00."
    ::= { oaEntry 45 }


oaModeSetting OBJECT-TYPE
    SYNTAX       INTEGER { constantGain  (2),
                           constantPower (3) }
    MAX-ACCESS   read-create
    STATUS       current
    DESCRIPTION  "The desired mode of operation to which this optical amplifier
                  is set."
    DEFVAL       { constantGain }
    ::= { oaEntry 46 }


oaGainSetting OBJECT-TYPE
    SYNTAX       FixedX10
    UNITS        "dB"
    MAX-ACCESS   read-create
    STATUS       current
    DESCRIPTION  "The effective gain (excluding ASE) set point. A default value
                  is provided when the optical amplifier is created based on the
                  optical amplifier type provisioned."
    ::= { oaEntry 47 }


oaPwrSetting OBJECT-TYPE
    SYNTAX       FixedX10
    UNITS        "dBm"
    MAX-ACCESS   read-create
    STATUS       current
    DESCRIPTION  "The signal output power (excluding ASE) set point. A default
                  value is provided when the optical amplifier is created based
                  on the optical amplifier type provisioned."
    ::= { oaEntry 48 }


oaTiltCompSetting OBJECT-TYPE
    SYNTAX       FixedX10
    UNITS        "dB"
    MAX-ACCESS   read-create
    STATUS       current
    DESCRIPTION  "The desired tilt compensation to which this optical amplifier
                  is set."
    DEFVAL       { 0 }
    ::= { oaEntry 49 }


oaStatus OBJECT-TYPE
    SYNTAX       INTEGER { none                    (1),
                           constantGain            (2),
                           constantPower           (3),
                           eyeSafe                 (4),
                           shutdown                (5),
                           constantGainOff         (6),
                           constantPowerOff        (7),
                           constantLaserCurrent    (8),
                           constantLaserCurrentOff (9),
                           constantLaserPower      (10),
                           constantLaserPowerOff   (11) }
    MAX-ACCESS   read-only
    STATUS       current
    DESCRIPTION  "The specific operational status of the amplifier."
    ::= { oaEntry 50 }


oaLaserStatus OBJECT-TYPE
    SYNTAX       INTEGER { on  (1),
                           off (2) }
    MAX-ACCESS   read-only
    STATUS       current
    DESCRIPTION  "The actual operational status of the optical amplifier laser."
    ::= { oaEntry 51 }


oaId1 OBJECT-TYPE
    SYNTAX       DisplayString (SIZE (0..32))
    MAX-ACCESS   read-create
    STATUS       current
    DESCRIPTION  "Textual data recorded by the user to describe the provisioned
                  optical amplifier in a manner useful to the user."
    DEFVAL       { "" }
    ::= { oaEntry 52 }


oaId2 OBJECT-TYPE
    SYNTAX       DisplayString (SIZE (0..32))
    MAX-ACCESS   read-create
    STATUS       current
    DESCRIPTION  "Textual data recorded by the user to describe the provisioned
                  optical amplifier in a manner useful to the user."
    DEFVAL       { "" }
    ::= { oaEntry 53 }


oaFiberType OBJECT-TYPE
    SYNTAX       FiberType
    MAX-ACCESS   read-create
    STATUS       current
    DESCRIPTION  "An optional specification of the fiber type that interfaces
                  with the optical amplifier."
    DEFVAL       { none }
    ::= { oaEntry 54 }


oaGrid OBJECT-TYPE
    SYNTAX       WDMGrid
    MAX-ACCESS   read-create
    STATUS       current
    DESCRIPTION  "An optional indication of the WDM grid to which the link
                  conforms."
    DEFVAL       { none }
    ::= { oaEntry 55 }


oaNumChannels OBJECT-TYPE
    SYNTAX       INTEGER (0..40)
    MAX-ACCESS   read-create
    STATUS       current
    DESCRIPTION  "An optional indication of the number of channels that the link
                  is carrying."
    DEFVAL       { 0 }
    ::= { oaEntry 56 }


oaCustom1 OBJECT-TYPE
    SYNTAX       DisplayString
    MAX-ACCESS   read-create
    STATUS       current
    DESCRIPTION  "A variable length text string for operating company use."
    DEFVAL       { "" }
    ::= { oaEntry 57 }


oaCustom2 OBJECT-TYPE
    SYNTAX       DisplayString
    MAX-ACCESS   read-create
    STATUS       current
    DESCRIPTION  "A variable length text string for operating company use."
    DEFVAL       { "" }
    ::= { oaEntry 58 }


oaCustom3 OBJECT-TYPE
    SYNTAX       DisplayString
    MAX-ACCESS   read-create
    STATUS       current
    DESCRIPTION  "A variable length text string for operating company use."
    DEFVAL       { "" }
    ::= { oaEntry 59 }


oaWavelength OBJECT-TYPE
    SYNTAX       FixedX100
    MAX-ACCESS   read-create
    STATUS       current
    DESCRIPTION  "The wavelength transmitted from the OA port. This object
                  applies only to single channel amplifiers (sba, spa)."
    ::= { oaEntry 60 }


oaRemoteId OBJECT-TYPE
    SYNTAX       DisplayString
    MAX-ACCESS   read-create
    STATUS       current
    DESCRIPTION  "Identifies the remote node and port to which the
                  optical amplifier port is connected, in the format
                  prescribed by the PSM network management system."
    DEFVAL       { "" }
    ::= { oaEntry 61 }


oaRowStatus OBJECT-TYPE
    SYNTAX       RowStatus
    MAX-ACCESS   read-create
    STATUS       current
    DESCRIPTION  "Used to control the addition and deletion of entries in the
                  optical amplifier table, which in turn controls provisioning
                  and deprovisioning of optical amplifier facilities."
    ::= { oaEntry 100 }



-----------------------------------------------------------------------
-- Objects related to provisioned Optical Transceivers on
-- Wavelength Conversion Circuit Packs
-- 
-- A listing of provisioned optical transceiver ports is contained in the
-- xcvrTable of the BTI 7000 Series MIB. When retrieved, this table includes one
-- row for each provisioned transceiver port entity.
-- 
-- Optical transceiver ports are provisioned on wavelength conversion circuit
-- packs that include:
-- � Wavelength Manager (WM)
-- � Wavelength Regenerator (WR)
-- � Wavelength Translator (WT)
-- � Transponder (TPR)
-- The following table lists the objects in each entry of the xcvrTable.
-----------------------------------------------------------------------


xcvrTable OBJECT-TYPE
    SYNTAX       SEQUENCE OF XcvrEntry
    MAX-ACCESS   not-accessible
    STATUS       current
    DESCRIPTION  "This table contains one row for every provisioned optical
                  transceiver on a wavelength translator, regenerator or manager
                  card. Each row contains a list of attributes that pertain to
                  the transceiver."
    ::= { facilities 2 }


xcvrEntry OBJECT-TYPE
    SYNTAX       XcvrEntry
    MAX-ACCESS   not-accessible
    STATUS       current
    DESCRIPTION  "The conceptual row object of the optical transceiver table."
    INDEX        { xcvrTypeIdx,
                   xcvrShelfIdx,
                   xcvrSlotIdx,
                   xcvrIdx }
    ::= { xcvrTable 1 }


XcvrEntry ::= SEQUENCE { xcvrTypeIdx                     XcvrType,
                         xcvrShelfIdx                    INTEGER,
                         xcvrSlotIdx                     INTEGER,
                         xcvrIdx                         INTEGER,
                         xcvrOpticalPwrReceivedMinTh     FixedX10,
                         xcvrOpticalPwrReceivedMaxTh     FixedX10,
                         xcvrOpticalPwrTransmittedMinTh  FixedX10,
                         xcvrOpticalPwrTransmittedMaxTh  FixedX10,
                         xcvrOpticalPwrReceived          FixedX10,
                         xcvrOpticalPwrTransmitted       FixedX10,
                         xcvrProtSwEvtType               ProtSwEvtType,
                         xcvrPEC                         DisplayString,
                         xcvrAdminStatus                 AdminStatus,
                         xcvrOperStatus                  OperStatus,
                         xcvrOperStatQlfr                OperStatQlfr,
                         xcvrAutoEnableTimer             HoursAndMinutes,
                         xcvrActAutoEnableTimer          HoursAndMinutes,
                         xcvrProtocol                    XcvrProtocolType,
                         xcvrWavelength                  FixedX100,
                         xcvrVendorPN1                   DisplayString,
                         xcvrVendorPN2                   DisplayString,
                         xcvrVendorPN3                   DisplayString,
                         xcvrPhyPMMon                    INTEGER,
                         xcvrFPSD                        INTEGER,
                         xcvrLaserStatus                 INTEGER,
                         xcvrId1                         DisplayString,
                         xcvrId2                         DisplayString,
                         xcvrFiberType                   FiberType,
                         xcvrGrid                        WDMGrid,
                         xcvrCustom1                     DisplayString,
                         xcvrCustom2                     DisplayString,
                         xcvrCustom3                     DisplayString,
                         xcvrTraceLabel                  DisplayString,
                         xcvrExpectedTraceLabel          DisplayString,
                         xcvrReceivedTraceLabel          DisplayString,
			             xcvrSDBERTh                     BERType,
                         xcvrLoopbackType                LoopbackType,
			             xcvrRemoteId                    DisplayString,
                         xcvrRowStatus                   RowStatus }


xcvrTypeIdx OBJECT-TYPE
    SYNTAX       XcvrType
    MAX-ACCESS   accessible-for-notify
    STATUS       current
    DESCRIPTION  "The specific type of wavelength conversion function of the
                  circuit pack on which the transceiver is provisioned."
    ::= { xcvrEntry 1 }


xcvrShelfIdx OBJECT-TYPE
    SYNTAX       INTEGER (1|11|21|31)
    MAX-ACCESS   accessible-for-notify
    STATUS       current
    DESCRIPTION  "The number of the shelf on which the transceiver is
                  provisioned."
    ::= { xcvrEntry 2 }


xcvrSlotIdx OBJECT-TYPE
    SYNTAX       INTEGER (1..20)
    MAX-ACCESS   accessible-for-notify
    STATUS       current
    DESCRIPTION  "The number of the slot within which the transceiver is
                  provisioned."
    ::= { xcvrEntry 3 }


xcvrIdx OBJECT-TYPE
    SYNTAX       INTEGER (1..4)
    MAX-ACCESS   accessible-for-notify
    STATUS       current
    DESCRIPTION  "The number of the port on the circuit pack on which the
                  transceiver is provisioned."
    ::= { xcvrEntry 4 }


xcvrOpticalPwrReceivedMinTh OBJECT-TYPE
    SYNTAX       FixedX10
    UNITS        "dBm/10"
    MAX-ACCESS   read-only
    STATUS       current
    DESCRIPTION  "This is the optical power received minimum threshold."
    ::= { xcvrEntry 5 }


xcvrOpticalPwrReceivedMaxTh OBJECT-TYPE
    SYNTAX       FixedX10
    UNITS        "dBm/10"
    MAX-ACCESS   read-only
    STATUS       current
    DESCRIPTION  "This is the optical power received maximum threshold."
    ::= { xcvrEntry 6 }


xcvrOpticalPwrTransmittedMinTh OBJECT-TYPE
    SYNTAX       FixedX10
    UNITS        "dBm/10"
    MAX-ACCESS   read-only
    STATUS       current
    DESCRIPTION  "This is the optical power transmitted minimum threshold."
    ::= { xcvrEntry 7 }


xcvrOpticalPwrTransmittedMaxTh OBJECT-TYPE
    SYNTAX       FixedX10
    UNITS        "dBm/10"
    MAX-ACCESS   read-only
    STATUS       current
    DESCRIPTION  "This is the optical power transmitted maximum threshold."
    ::= { xcvrEntry 8 }


xcvrOpticalPwrReceived OBJECT-TYPE
    SYNTAX       FixedX10
    UNITS        "dBm/10"
    MAX-ACCESS   accessible-for-notify
    STATUS       current
    DESCRIPTION  "The optical power received on the input of the transceiver."
    ::= { xcvrEntry 9 }


xcvrOpticalPwrTransmitted OBJECT-TYPE
    SYNTAX       FixedX10
    UNITS        "dBm/10"
    MAX-ACCESS   accessible-for-notify
    STATUS       current
    DESCRIPTION  "The optical power transmitted at the output of the
                  transceiver."
    ::= { xcvrEntry 10 }


xcvrProtSwEvtType OBJECT-TYPE
    SYNTAX       ProtSwEvtType
    MAX-ACCESS   accessible-for-notify
    STATUS       current
    DESCRIPTION  "Indicates the type of protection switching event that has
                  occured on an optical transceiver port."
    ::= { xcvrEntry 11 }


xcvrPEC OBJECT-TYPE
    SYNTAX       DisplayString (SIZE (0..32))
    MAX-ACCESS   read-create
    STATUS       current
    DESCRIPTION  "An optionally provisioned transceiver Product Equipment Code
                  used to validate the physically present transceiver."
    DEFVAL       { "" }
    ::= { xcvrEntry 12 }


xcvrAdminStatus OBJECT-TYPE
    SYNTAX       AdminStatus
    MAX-ACCESS   read-create
    STATUS       current
    DESCRIPTION  "The administrative status of the optical transceiver."
    DEFVAL       { enabled }
    ::= { xcvrEntry 13 }


xcvrOperStatus OBJECT-TYPE
    SYNTAX       OperStatus
    MAX-ACCESS   read-only
    STATUS       current
    DESCRIPTION  "The reported operational status of the optical transceiver."
    ::= { xcvrEntry 14 }


xcvrOperStatQlfr OBJECT-TYPE
    SYNTAX       OperStatQlfr
    MAX-ACCESS   read-only
    STATUS       current
    DESCRIPTION  "This is a textual list of qualifiers about the reported
                  operational status of the optical transceiver."
    ::= { xcvrEntry 15 }


xcvrAutoEnableTimer OBJECT-TYPE
    SYNTAX       HoursAndMinutes
    MAX-ACCESS   read-create
    STATUS       current
    DESCRIPTION  "Specifies the auto-enable timer for the targeted optical
                  transceiver. This value only applies if the xcvrAdminStatus
                  object is set to autoEnabled. Otherwise, the value returned is
                  000-00."
    DEFVAL       { "008-00" }
    ::= { xcvrEntry 16 }


xcvrActAutoEnableTimer OBJECT-TYPE
    SYNTAX       HoursAndMinutes
    MAX-ACCESS   read-only
    STATUS       current
    DESCRIPTION  "Indicates the time remaining on the auto-enable timer if it is
                  actively counting down. Otherwise, the value returned is
                  000-00."
    ::= { xcvrEntry 17 }


xcvrProtocol OBJECT-TYPE
    SYNTAX       XcvrProtocolType
    MAX-ACCESS   read-create
    STATUS       current
    DESCRIPTION  "The protocol of the service to be carried by the port. This is
                  a mandatory object when a row of the transceiver table is
                  created."
    ::= { xcvrEntry 18 }


xcvrWavelength OBJECT-TYPE
    SYNTAX       FixedX100
    MAX-ACCESS   read-create
    STATUS       current
    DESCRIPTION  "The wavelength to be transmitted by the transceiver port. This
                  is a mandatory object when a row of the transceiver table is
                  created for ports that have a pluggable transceiver."
    ::= { xcvrEntry 19 }


xcvrVendorPN1 OBJECT-TYPE
    SYNTAX       DisplayString (SIZE (0..20))
    MAX-ACCESS   read-create
    STATUS       current
    DESCRIPTION  "An optionally provisioned part number used to validate the
                  physically present transceiver."
    DEFVAL       { "" }
    ::= { xcvrEntry 20 }


xcvrVendorPN2 OBJECT-TYPE
    SYNTAX       DisplayString (SIZE (0..20))
    MAX-ACCESS   read-create
    STATUS       current
    DESCRIPTION  "An optionally provisioned part number used to validate the
                  physically present transceiver."
    DEFVAL       { "" }
    ::= { xcvrEntry 21 }


xcvrVendorPN3 OBJECT-TYPE
    SYNTAX       DisplayString (SIZE (0..20))
    MAX-ACCESS   read-create
    STATUS       current
    DESCRIPTION  "An optionally provisioned part number used to validate the
                  physically present transceiver."
    DEFVAL       { "" }
    ::= { xcvrEntry 22 }


xcvrPhyPMMon OBJECT-TYPE
    SYNTAX       INTEGER { enabled  (1),
                           disabled (2) }
    MAX-ACCESS   read-create
    STATUS       current
    DESCRIPTION  "Indicates if the port is configured to report threshold
                  crossing conditions for physical layer performance monitoring
                  parameters."
    DEFVAL       { disabled }
    ::= { xcvrEntry 23 }


xcvrFPSD OBJECT-TYPE
    SYNTAX       INTEGER { enabled  (1),
                           disabled (2) }
    MAX-ACCESS   read-create
    STATUS       current
    DESCRIPTION  "Indicates if the port is configured for Fault Propagation Shut
                  Down."
    DEFVAL       { disabled }
    ::= { xcvrEntry 24 }


xcvrLaserStatus OBJECT-TYPE
    SYNTAX       INTEGER { on      (1),
                           off     (2),
                           idle    (3),
                           aisl    (4),
                           msais   (5),
                           odu2ais (6),
                           prbs    (7),
                           remoteFault (8),
                           odu2lck (9),
                           odu2oci (10) }
    MAX-ACCESS   read-only
    STATUS       current
    DESCRIPTION  "An indication of the operational status of the transceiver
                  laser."
    ::= { xcvrEntry 25 }


xcvrId1 OBJECT-TYPE
    SYNTAX       DisplayString (SIZE (0..32))
    MAX-ACCESS   read-create
    STATUS       current
    DESCRIPTION  "Textual data recorded by the user to describe the provisioned
                  optical transceiver in a manner useful to the user."
    DEFVAL       { "" }
    ::= { xcvrEntry 26 }


xcvrId2 OBJECT-TYPE
    SYNTAX       DisplayString (SIZE (0..32))
    MAX-ACCESS   read-create
    STATUS       current
    DESCRIPTION  "Textual data recorded by the user to describe the provisioned
                  optical transceiver in a manner useful to the user."
    DEFVAL       { "" }
    ::= { xcvrEntry 27 }


xcvrFiberType OBJECT-TYPE
    SYNTAX       FiberType
    MAX-ACCESS   read-create
    STATUS       current
    DESCRIPTION  "An optional specification of the fiber type that interfaces to
                  the optical transceiver."
    DEFVAL       { none }
    ::= { xcvrEntry 28 }


xcvrGrid OBJECT-TYPE
    SYNTAX       WDMGrid
    MAX-ACCESS   read-create
    STATUS       current
    DESCRIPTION  "An optical indication of the WDM grid the link conforms."
    DEFVAL       { none }
    ::= { xcvrEntry 29 }


xcvrCustom1 OBJECT-TYPE
    SYNTAX       DisplayString
    MAX-ACCESS   read-create
    STATUS       current
    DESCRIPTION  "A variable length text string for operating company use."
    DEFVAL       { "" }
    ::= { xcvrEntry 30 }


xcvrCustom2 OBJECT-TYPE
    SYNTAX       DisplayString
    MAX-ACCESS   read-create
    STATUS       current
    DESCRIPTION  "A variable length text string for operating company use."
    DEFVAL       { "" }
    ::= { xcvrEntry 31 }


xcvrCustom3 OBJECT-TYPE
    SYNTAX       DisplayString
    MAX-ACCESS   read-create
    STATUS       current
    DESCRIPTION  "A variable length text string for operating company use."
    DEFVAL       { "" }
    ::= { xcvrEntry 32 }


xcvrTraceLabel OBJECT-TYPE
    SYNTAX       DisplayString (SIZE (0..16))
    MAX-ACCESS   read-create
    STATUS       current
    DESCRIPTION  "If specified, this attribute will describe the trace label to
                  be used in the outgoing OTN or SONET/SDH trace."
    DEFVAL       { "" }
    ::= { xcvrEntry 33 }


xcvrExpectedTraceLabel OBJECT-TYPE
    SYNTAX       DisplayString (SIZE (0..16))
    MAX-ACCESS   read-create
    STATUS       current
    DESCRIPTION  "This attribute will describe the trace label that is expected
                  to be received in the incoming OTN or SONET/SDH trace. If
                  specified, this expected trace label will be compared to the
                  actual value for xcvrReceivedTraceLabel, and a trace mismatch
                  alarm will be raised if the two trace labels do not match."
    DEFVAL       { "" }
    ::= { xcvrEntry 34 }


xcvrReceivedTraceLabel OBJECT-TYPE
    SYNTAX       DisplayString (SIZE (0..16))
    MAX-ACCESS   read-only
    STATUS       current
    DESCRIPTION  "The actual received trace label on the incoming OTN or
                  SONET/SDH trace."
    ::= { xcvrEntry 35 }

xcvrSDBERTh OBJECT-TYPE
    SYNTAX       BERType
    MAX-ACCESS   read-create
    STATUS       current
    DESCRIPTION  "The Bit Error Rate threshold above which the Signal Degrade
                  condition is raised."
    DEFVAL { none }
    ::= { xcvrEntry 36 }

xcvrLoopbackType OBJECT-TYPE
    SYNTAX       LoopbackType
    MAX-ACCESS   read-only
    STATUS       current
    DESCRIPTION  "The loopback type that is currently active on the xcvr"
    DEFVAL { noLoopback }
    ::= { xcvrEntry 37 }

xcvrRemoteId OBJECT-TYPE
    SYNTAX       DisplayString
    MAX-ACCESS   read-create
    STATUS       current
    DESCRIPTION  "Identifies the remote node and port to which the
                  transceiver port is connected, in the format
                  prescribed by the PSM network management system."
    DEFVAL       { "" }
    ::= { xcvrEntry 38 }

xcvrRowStatus OBJECT-TYPE
    SYNTAX       RowStatus
    MAX-ACCESS   read-create
    STATUS       current
    DESCRIPTION  "Used to control the addition and deletion of entries in the
                  Transceiver table, which in turn controls provisioning and
                  deprovisioning of optical transceiver facilities."
    ::= { xcvrEntry 100 }



-----------------------------------------------------------------------
-- Objects related to provisioned Active Multiplexer-Demultiplexer
-- ports on AMD cards
-- 
-- A listing of provisioned active multiplexer-demultiplexer ports is
-- contained in the amdTable of the BTI 7000 Series MIB. When retrieved,
-- this table includes one row for each port on active
-- multiplexer-demultiplexer packs.
-- 
-- All entries in the amdTable are created and deleted automatically as
-- a result of the creation and deletion of the supporting entry in
-- the cpTable.
-- 
-- The following table lists the objects in each entry of the amdTable.
-----------------------------------------------------------------------


amdTable OBJECT-TYPE
    SYNTAX       SEQUENCE OF AmdEntry
    MAX-ACCESS   not-accessible
    STATUS       obsolete
    DESCRIPTION  "This table contains one row for every provisioned active
                  multiplexer-demultiplexer facility. AMD facilities include AMD
                  line facilities and AMD channel facilities. Each row contains
                  a list of attributes that pertain to one facility."
    ::= { facilities 3 }


amdEntry OBJECT-TYPE
    SYNTAX       AmdEntry
    MAX-ACCESS   not-accessible
    STATUS       obsolete
    DESCRIPTION  "The conceptual row object of the Active Mux-Demux table."
    INDEX        { amdTypeIdx,
                   amdShelfIdx,
                   amdSlotIdx,
                   amdLineIdx,
                   amdPortIdx }
    ::= { amdTable 1 }


AmdEntry ::= SEQUENCE { amdTypeIdx                      AmdType,
                        amdShelfIdx                     INTEGER,
                        amdSlotIdx                      INTEGER,
                        amdLineIdx                      INTEGER,
                        amdPortIdx                      AmdPortType,
                        amdOpticalPwrReceivedMinTh      FixedX10,
                        amdOpticalPwrReceivedMaxTh      FixedX10,
                        amdOpticalPwrTransmittedTarget  FixedX10,
                        amdOpticalAttenuationTarget     FixedX10,
                        amdOpticalPwrReceived           FixedX10,
                        amdOpticalPwrTransmitted        FixedX10,
                        amdOpticalAttentuation          FixedX10,
                        amdAdminStatus                  AdminStatus,
                        amdOperStatus                   OperStatus,
                        amdOperStatQlfr                 OperStatQlfr,
                        amdAutoEnableTimer              HoursAndMinutes,
                        amdActAutoEnableTimer           HoursAndMinutes,
                        amdWavelength                   FixedX100,
                        amdId1                          DisplayString,
                        amdId2                          DisplayString,
                        amdFiberType                    FiberType,
                        amdGrid                         WDMGrid,
                        amdCustom1                      DisplayString,
                        amdCustom2                      DisplayString,
                        amdCustom3                      DisplayString,
                        amdRowStatus                    RowStatus }


amdTypeIdx OBJECT-TYPE
    SYNTAX       AmdType
    MAX-ACCESS   accessible-for-notify
    STATUS       obsolete
    DESCRIPTION  "The specific type of active multiplexer-demultiplexer circuit
                  pack on which the facility is provisioned."
    ::= { amdEntry 1 }


amdShelfIdx OBJECT-TYPE
    SYNTAX       INTEGER (1|11|21|31)
    MAX-ACCESS   accessible-for-notify
    STATUS       obsolete
    DESCRIPTION  "The number of the shelf on which the active
                  multiplexer-demultiplexer facility is provisioned."
    ::= { amdEntry 2 }


amdSlotIdx OBJECT-TYPE
    SYNTAX       INTEGER (1|3|5|7|9|11|13|15|17|19)
    MAX-ACCESS   accessible-for-notify
    STATUS       obsolete
    DESCRIPTION  "The number of the slot within which the active
                  multiplexer-demultiplexer facility is provisioned."
    ::= { amdEntry 3 }


amdLineIdx OBJECT-TYPE
    SYNTAX       INTEGER (1..1)
    MAX-ACCESS   accessible-for-notify
    STATUS       obsolete
    DESCRIPTION  "The number of the multiplexed wavelength line on the AMD
                  circuit pack."
    ::= { amdEntry 4 }


amdPortIdx OBJECT-TYPE
    SYNTAX       AmdPortType
    MAX-ACCESS   accessible-for-notify
    STATUS       obsolete
    DESCRIPTION  "Identifies a specific port on the identified line of the AMD
                  circuit pack."
    ::= { amdEntry 5 }


amdOpticalPwrReceivedMinTh OBJECT-TYPE
    SYNTAX       FixedX10
    UNITS        "dBm/10"
    MAX-ACCESS   read-write
    STATUS       obsolete
    DESCRIPTION  "This is the optical power received minimum threshold."
    ::= { amdEntry 6 }


amdOpticalPwrReceivedMaxTh OBJECT-TYPE
    SYNTAX       FixedX10
    UNITS        "dBm/10"
    MAX-ACCESS   read-write
    STATUS       obsolete
    DESCRIPTION  "This is the optical power received maximum threshold."
    ::= { amdEntry 7 }


amdOpticalPwrTransmittedTarget OBJECT-TYPE
    SYNTAX       FixedX10
    UNITS        "dBm/10"
    MAX-ACCESS   read-write
    STATUS       obsolete
    DESCRIPTION  "This is the optical power transmitted target level."
    ::= { amdEntry 8 }


amdOpticalAttenuationTarget OBJECT-TYPE
    SYNTAX       FixedX10
    UNITS        "dB/10"
    MAX-ACCESS   read-write
    STATUS       obsolete
    DESCRIPTION  "This is the optical power attenuation target level."
    ::= { amdEntry 9 }


amdOpticalPwrReceived OBJECT-TYPE
    SYNTAX       FixedX10
    UNITS        "dBm/10"
    MAX-ACCESS   accessible-for-notify
    STATUS       obsolete
    DESCRIPTION  "The optical input power received for the channel."
    ::= { amdEntry 10 }


amdOpticalPwrTransmitted OBJECT-TYPE
    SYNTAX       FixedX10
    UNITS        "dBm/10"
    MAX-ACCESS   accessible-for-notify
    STATUS       obsolete
    DESCRIPTION  "The optical power level transmitted for the channel."
    ::= { amdEntry 11 }


amdOpticalAttentuation OBJECT-TYPE
    SYNTAX       FixedX10
    UNITS        "dB/10"
    MAX-ACCESS   accessible-for-notify
    STATUS       obsolete
    DESCRIPTION  "The optical power attenuation for the line."
    ::= { amdEntry 12 }


amdAdminStatus OBJECT-TYPE
    SYNTAX       AdminStatus
    MAX-ACCESS   read-write
    STATUS       obsolete
    DESCRIPTION  "The administrative status of the AMD port."
    DEFVAL       { enabled }
    ::= { amdEntry 13 }


amdOperStatus OBJECT-TYPE
    SYNTAX       OperStatus
    MAX-ACCESS   read-only 
    STATUS       obsolete
    DESCRIPTION  "The reported operational status of the AMD port."
    ::= { amdEntry 14 }


amdOperStatQlfr OBJECT-TYPE
    SYNTAX       OperStatQlfr
    MAX-ACCESS   read-only
    STATUS       obsolete
    DESCRIPTION  "This is a textual list of qualifiers about the reported
                  operational status of the AMD port."
    ::= { amdEntry 15 }


amdAutoEnableTimer OBJECT-TYPE
    SYNTAX       HoursAndMinutes
    MAX-ACCESS   read-write
    STATUS       obsolete
    DESCRIPTION  "Specifies the auto-enable timer for the targeted AMD port.
                  This value only applies if the amdAdminStatus object is set to
                  autoEnabled. Otherwise, the value returned is 000-00."
    DEFVAL       { "008-00" }
    ::= { amdEntry 16 }


amdActAutoEnableTimer OBJECT-TYPE
    SYNTAX       HoursAndMinutes
    MAX-ACCESS   read-only
    STATUS       obsolete
    DESCRIPTION  "Indicates the time remaining on the auto-enable timer if it is
                  actively counting down. Otherwise, the value returned is
                  000-00."
    ::= { amdEntry 17 }


amdWavelength OBJECT-TYPE
    SYNTAX       FixedX100
    MAX-ACCESS   read-only
    STATUS       obsolete
    DESCRIPTION  "The wavelength transmitted from the AMD port. This object
                  applies only to channel ports."
    ::= { amdEntry 18 }


amdId1 OBJECT-TYPE
    SYNTAX       DisplayString (SIZE (0..32))
    MAX-ACCESS   read-write
    STATUS       obsolete
    DESCRIPTION  "Textual data recorded by the user to describe the provisioned
                  optical transceiver in a manner useful to the user."
    DEFVAL       { "" }
    ::= { amdEntry 19 }


amdId2 OBJECT-TYPE
    SYNTAX       DisplayString (SIZE (0..32))
    MAX-ACCESS   read-write
    STATUS       obsolete
    DESCRIPTION  "Textual data recorded by the user to describe the provisioned
                  optical transceiver in a manner useful to the user."
    DEFVAL       { "" }
    ::= { amdEntry 20 }


amdFiberType OBJECT-TYPE
    SYNTAX       FiberType
    MAX-ACCESS   read-write
    STATUS       obsolete
    DESCRIPTION  "An optional specification of the fiber type that interfaces to
                  the AMD port."
    DEFVAL       { none }
    ::= { amdEntry 21 }


amdGrid OBJECT-TYPE
    SYNTAX       WDMGrid
    MAX-ACCESS   read-write
    STATUS       obsolete
    DESCRIPTION  "An optical indication of the WDM grid to which the AMD port
                  link conforms."
    DEFVAL       { none }
    ::= { amdEntry 22 }


amdCustom1 OBJECT-TYPE
    SYNTAX       DisplayString
    MAX-ACCESS   read-write
    STATUS       obsolete
    DESCRIPTION  "A variable length text string for operating company use."
    DEFVAL       { "" }
    ::= { amdEntry 23 }


amdCustom2 OBJECT-TYPE
    SYNTAX       DisplayString
    MAX-ACCESS   read-write
    STATUS       obsolete
    DESCRIPTION  "A variable length text string for operating company use."
    DEFVAL       { "" }
    ::= { amdEntry 24 }


amdCustom3 OBJECT-TYPE
    SYNTAX       DisplayString
    MAX-ACCESS   read-write
    STATUS       obsolete
    DESCRIPTION  "A variable length text string for operating company use."
    DEFVAL       { "" }
    ::= { amdEntry 25 }


amdRowStatus OBJECT-TYPE
    SYNTAX       RowStatus
    MAX-ACCESS   accessible-for-notify
    STATUS       obsolete
    DESCRIPTION  "The active multiplexer-demultiplexer table RowStatus object is
                  not readable or writeable because all entries in the AMD table
                  are automatically created and deleted when the AMD circuit
                  pack is created or deleted. This AMD row status object is used
                  only in database change notifications to indicate if the row
                  has been created or deleted."
    ::= { amdEntry 100 }



-----------------------------------------------------------------------
-- Objects related to optical facilities carried on the ports of
-- provisioned passive circuit packs.
-- 
-- A listing of provisioned passive circuit pack ports is contained
-- in the assivePortTable of the BTI 7000 Series MIB. When retrieved,
-- this table includes one row for each port on passive packs.
-- 
-- All entries in the passivePortTable are created and deleted
-- automatically as a result of the creation and deletion of the
-- supporting entry in the cpTable.
-- 
-- The following table lists the objects in each entry of the
-- passivePortTable.
-----------------------------------------------------------------------


passivePortTable OBJECT-TYPE
    SYNTAX       SEQUENCE OF PassivePortEntry
    MAX-ACCESS   not-accessible
    STATUS       current
    DESCRIPTION  "This table contains one row for each port on every provisioned
                  passive circuit pack on the NE. Each list contains a list of
                  attributes that pertain to the passive port."
    ::= { facilities 4 }


passivePortEntry OBJECT-TYPE
    SYNTAX       PassivePortEntry
    MAX-ACCESS   not-accessible
    STATUS       current
    DESCRIPTION  "The conceptual row object of the passive circuit pack port
                  table."
    INDEX        { passivePortCpTypeIdx,
                   passivePortShelfIdx,
                   passivePortSlotIdx,
                   passivePortLineIdx,
                   passivePortTypeIdx }
    ::= { passivePortTable 1 }


PassivePortEntry ::= SEQUENCE { passivePortCpTypeIdx      CpType,
                                passivePortShelfIdx       INTEGER,
                                passivePortSlotIdx        INTEGER,
                                passivePortLineIdx        INTEGER,
                                passivePortTypeIdx        PassivePortType,
                                passivePortId1            DisplayString,
                                passivePortId2            DisplayString,
                                passivePortFiberType      FiberType,
                                passivePortGrid           WDMGrid,
                                passivePortNumChannels    INTEGER,
                                passivePortWavelength     FixedX100,
                                passivePortCustom1        DisplayString,
                                passivePortCustom2        DisplayString,
                                passivePortCustom3        DisplayString,
                                passivePortRemoteId       DisplayString,
                                passivePortRowStatus      RowStatus }


passivePortCpTypeIdx OBJECT-TYPE
    SYNTAX       CpType
    MAX-ACCESS   not-accessible
    STATUS       current
    DESCRIPTION  "The type of circuit pack on which the passive port is found."
    ::= { passivePortEntry 1 }


passivePortShelfIdx OBJECT-TYPE
    SYNTAX       INTEGER (1|11|21|31)
    MAX-ACCESS   not-accessible
    STATUS       current
    DESCRIPTION  "The number of the shelf on which the passive circuit pack port
                  is provisioned."
    ::= { passivePortEntry 2 }


passivePortSlotIdx OBJECT-TYPE
    SYNTAX       INTEGER (1..20)
    MAX-ACCESS   not-accessible
    STATUS       current
    DESCRIPTION  "The number of the slot within which the passive circuit pack
                  port is provisioned."
    ::= { passivePortEntry 3 }

passivePortLineIdx OBJECT-TYPE
    SYNTAX       INTEGER (1..4)
    MAX-ACCESS   not-accessible
    STATUS       current
    DESCRIPTION  "Identifies the multiplexed multi-channel optical facility
                  instance associated with the targeted passive port."
    ::= { passivePortEntry 4 }


passivePortTypeIdx OBJECT-TYPE
    SYNTAX       PassivePortType
    MAX-ACCESS   not-accessible
    STATUS       current
    DESCRIPTION  "Identifies the specific passive port on the circuit pack
                  according to function."
    ::= { passivePortEntry 5 }


passivePortId1 OBJECT-TYPE
    SYNTAX       DisplayString (SIZE (0..32))
    MAX-ACCESS   read-write
    STATUS       current
    DESCRIPTION  "An optional name used to identify the passive circuit pack
                  port facility."
    ::= { passivePortEntry 6 }


passivePortId2 OBJECT-TYPE
    SYNTAX       DisplayString (SIZE (0..32))
    MAX-ACCESS   read-write
    STATUS       current
    DESCRIPTION  "An optional identifier for the passive circuit pack port
                  circuit."
    ::= { passivePortEntry 7 }


passivePortFiberType OBJECT-TYPE
    SYNTAX       FiberType
    MAX-ACCESS   read-write
    STATUS       current
    DESCRIPTION  "An optional specification of the fiber type interfacing the
                  passive circuit pack port."
    ::= { passivePortEntry 8 }


passivePortGrid OBJECT-TYPE
    SYNTAX       WDMGrid
    MAX-ACCESS   read-write
    STATUS       current
    DESCRIPTION  "An optional indication of the DWM grid that the link conforms
                  to."
    ::= { passivePortEntry 9 }


passivePortNumChannels OBJECT-TYPE
    SYNTAX       INTEGER (1..65536)
    MAX-ACCESS   read-write
    STATUS       current
    DESCRIPTION  "An optional indication of the number of channels that the link
                  is carrying. This field does not apply to individual channel
                  type ports."
    ::= { passivePortEntry 10 }


passivePortWavelength OBJECT-TYPE
    SYNTAX       FixedX100
    MAX-ACCESS   read-only
    STATUS       current
    DESCRIPTION  "An indication of the wavelength that the port is carrying."
    ::= { passivePortEntry 11 }


passivePortCustom1 OBJECT-TYPE
    SYNTAX       DisplayString
    MAX-ACCESS   read-write
    STATUS       current
    DESCRIPTION  "A variable length text string for operating company use."
    ::= { passivePortEntry 12 }


passivePortCustom2 OBJECT-TYPE
    SYNTAX       DisplayString
    MAX-ACCESS   read-write
    STATUS       current
    DESCRIPTION  "A variable length text string for operating company use."
    ::= { passivePortEntry 13 }


passivePortCustom3 OBJECT-TYPE
    SYNTAX       DisplayString
    MAX-ACCESS   read-write
    STATUS       current
    DESCRIPTION  "A variable length text string for operating company use."
    ::= { passivePortEntry 14 }


passivePortRemoteId OBJECT-TYPE
    SYNTAX       DisplayString
    MAX-ACCESS   read-create
    STATUS       current
    DESCRIPTION  "Identifies the remote node and port to which the
                  passive card port is connected, in the format
                  prescribed by the PSM network management system."
    DEFVAL       { "" }
    ::= { passivePortEntry 15 }


passivePortRowStatus OBJECT-TYPE
    SYNTAX       RowStatus
    MAX-ACCESS   accessible-for-notify
    STATUS       current
    DESCRIPTION  "The passive port table RowStatus object is not readable or
                  writeable because all entries in the passive port table are
                  automatically created and deleted when the circuit pack is
                  created or deleted. This passive port row status object is
                  used only in database change notifications to indicate if the
                  row has been created or deleted."
    ::= { passivePortEntry 100 }



-----------------------------------------------------------------------
-- Objects related to provisioned SONET OC-N facilities on
-- Muxponder Circuit Packs
-- 
-- A listing of provisioned SONET OC-N ports is contained in the
-- ocnTable of the BTI 7000 Series MIB. When retrieved, this table
-- includes one row for each provisioned SONET OC-N port facility, that
-- includes OC-48 and OC-192 facilities.
-- 
-- Note: The ocnTable manages the OC-N facilities on muxponder circuit
-- packs. It is not used for OC-N services on wavelength conversion type
-- circuit packs. For management of these facilities, the xcvrTable is
-- used.
-- 
-- To manually provision an OC-48 or OC-192 facility, a row must be
-- created in the ocnTable. To deprovision an OC-N facility, its row must
-- be destroyed.
-- 
-- The following table lists the objects in each entry of the ocnTable.
-----------------------------------------------------------------------


ocnTable OBJECT-TYPE
    SYNTAX       SEQUENCE OF OcnEntry
    MAX-ACCESS   not-accessible
    STATUS       current
    DESCRIPTION  "This table contains one row for every provisioned SONET OC-N
                  facility on the system. Each row contains a list of attributes
                  that pertain to the facility."
    ::= { facilities 5 }


ocnEntry OBJECT-TYPE
    SYNTAX       OcnEntry
    MAX-ACCESS   not-accessible
    STATUS       current
    DESCRIPTION  "The conceptual row object of the OC-N table."
    INDEX        { ocnTypeIdx,
                   ocnShelfIdx,
                   ocnSlotIdx,
                   ocnPortIdx }
    ::= { ocnTable 1 }


OcnEntry ::= SEQUENCE { ocnTypeIdx                     OcnType,
                        ocnShelfIdx                    INTEGER,
                        ocnSlotIdx                     INTEGER,
                        ocnPortIdx                     INTEGER,
                        ocnOpticalPwrReceivedMinTh     FixedX10,
                        ocnOpticalPwrReceivedMaxTh     FixedX10,
                        ocnOpticalPwrTransmittedMinTh  FixedX10,
                        ocnOpticalPwrTransmittedMaxTh  FixedX10,
                        ocnOpticalPwrReceived          FixedX10,
                        ocnOpticalPwrTransmitted       FixedX10,
                        ocnBER                         BERType,
                        ocnBERTh                       BERType,
                        ocnPEC                         DisplayString,
                        ocnAdminStatus                 AdminStatus,
                        ocnOperStatus                  OperStatus,
                        ocnOperStatQlfr                OperStatQlfr,
                        ocnAutoEnableTimer             HoursAndMinutes,
                        ocnActAutoEnableTimer          HoursAndMinutes,
                        ocnWavelength                  FixedX100,
                        ocnVendorPN1                   DisplayString,
                        ocnVendorPN2                   DisplayString,
                        ocnVendorPN3                   DisplayString,
                        ocnPhyPMMon                    INTEGER,
                        ocnLaserStatus                 INTEGER,
                        ocnId1                         DisplayString,
                        ocnFiberType                   FiberType,
                        ocnCustom1                     DisplayString,
                        ocnTOHTransparency             INTEGER,
                        ocnLineMapping                 INTEGER,
                        ocnProtSwEvtType               ProtSwEvtType,
                        ocnDCCTransparency             INTEGER,
                        ocnTransparencyChannel         INTEGER,
                        ocnRemoteId                    DisplayString,
                        ocnRowStatus                   RowStatus }


ocnTypeIdx OBJECT-TYPE
    SYNTAX       OcnType
    MAX-ACCESS   accessible-for-notify
    STATUS       current
    DESCRIPTION  "The specific type of OC-N signal which is provisioned."
    ::= { ocnEntry 1 }


ocnShelfIdx OBJECT-TYPE
    SYNTAX       INTEGER (1|11|21|31)
    MAX-ACCESS   accessible-for-notify
    STATUS       current
    DESCRIPTION  "The number of the shelf on which the OC-N facility is
                  provisioned."
    ::= { ocnEntry 2 }


ocnSlotIdx OBJECT-TYPE
    SYNTAX       INTEGER (1..20)
    MAX-ACCESS   accessible-for-notify
    STATUS       current
    DESCRIPTION  "The number of the slot within which the OC-N facility is
                  provisioned."
    ::= { ocnEntry 3 }


ocnPortIdx OBJECT-TYPE
    SYNTAX       INTEGER (1..6)
    MAX-ACCESS   accessible-for-notify
    STATUS       current
    DESCRIPTION  "The number of the port on the circuit pack on which the OC-N
                  facility is provisioned."
    ::= { ocnEntry 4 }


ocnOpticalPwrReceivedMinTh OBJECT-TYPE
    SYNTAX       FixedX10
    UNITS        "dBm/10"
    MAX-ACCESS   read-only
    STATUS       current
    DESCRIPTION  "This is the optical power received minimum threshold."
    ::= { ocnEntry 5 }


ocnOpticalPwrReceivedMaxTh OBJECT-TYPE
    SYNTAX       FixedX10
    UNITS        "dBm/10"
    MAX-ACCESS   read-only
    STATUS       current
    DESCRIPTION  "This is the optical power received maximum threshold."
    ::= { ocnEntry 6 }


ocnOpticalPwrTransmittedMinTh OBJECT-TYPE
    SYNTAX       FixedX10
    UNITS        "dBm/10"
    MAX-ACCESS   read-only
    STATUS       current
    DESCRIPTION  "This is the optical power transmitted minimum threshold."
    ::= { ocnEntry 7 }


ocnOpticalPwrTransmittedMaxTh OBJECT-TYPE
    SYNTAX       FixedX10
    UNITS        "dBm/10"
    MAX-ACCESS   read-only
    STATUS       current
    DESCRIPTION  "This is the optical power transmitted maximum threshold."
    ::= { ocnEntry 8 }


ocnOpticalPwrReceived OBJECT-TYPE
    SYNTAX       FixedX10
    UNITS        "dBm/10"
    MAX-ACCESS   accessible-for-notify
    STATUS       current
    DESCRIPTION  "The optical power received on the input of the transceiver."
    ::= { ocnEntry 9 }


ocnOpticalPwrTransmitted OBJECT-TYPE
    SYNTAX       FixedX10
    UNITS        "dBm/10"
    MAX-ACCESS   accessible-for-notify
    STATUS       current
    DESCRIPTION  "The optical power transmitted at the output of the
                  transceiver."
    ::= { ocnEntry 10 }


ocnBER OBJECT-TYPE
    SYNTAX       BERType
    MAX-ACCESS   accessible-for-notify
    STATUS       current
    DESCRIPTION  "The Bit Error Rate measured on the received signal."
    ::= { ocnEntry 11 }


ocnBERTh OBJECT-TYPE
    SYNTAX       BERType
    MAX-ACCESS   read-create
    STATUS       current
    DESCRIPTION  "The Bit Error Rate threshold above which the Signal Degrade
                  condition is raised."
    DEFVAL { tenExpMinus5 }
    ::= { ocnEntry 12 }


ocnPEC OBJECT-TYPE
    SYNTAX       DisplayString (SIZE (0..32))
    MAX-ACCESS   read-create
    STATUS       current
    DESCRIPTION  "An optionally provisioned Product Equipment Code used to
                  validate the physically present optical transceiver on the
                  OC-N port."
    DEFVAL       { "" }
    ::= { ocnEntry 13 }


ocnAdminStatus OBJECT-TYPE
    SYNTAX       AdminStatus
    MAX-ACCESS   read-create
    STATUS       current
    DESCRIPTION  "The administrative status of the OC-N facility."
    DEFVAL       { enabled }
    ::= { ocnEntry 14 }


ocnOperStatus OBJECT-TYPE
    SYNTAX       OperStatus
    MAX-ACCESS   read-only
    STATUS       current
    DESCRIPTION  "The reported operational status of the OC-N facility."
    ::= { ocnEntry 15 }


ocnOperStatQlfr OBJECT-TYPE
    SYNTAX       OperStatQlfr
    MAX-ACCESS   read-only
    STATUS       current
    DESCRIPTION  "This is a textual list of qualifiers about the reported
                  operational status of the OC-N facility."
    ::= { ocnEntry 16 }


ocnAutoEnableTimer OBJECT-TYPE
    SYNTAX       HoursAndMinutes
    MAX-ACCESS   read-create
    STATUS       current
    DESCRIPTION  "Specifies the auto-enable timer for the targeted OC-N
                  facility. This value only applies if the ocnAdminStatus object
                  is set to autoEnabled. Otherwise, the value returned is
                  000-00."
    DEFVAL       { "008-00" }
    ::= { ocnEntry 17 }


ocnActAutoEnableTimer OBJECT-TYPE
    SYNTAX       HoursAndMinutes
    MAX-ACCESS   read-only
    STATUS       current
    DESCRIPTION  "Indicates the time remaining on the auto-enable timer if it is
                  actively counting down. Otherwise, the value returned is
                  000-00."
    ::= { ocnEntry 18 }


ocnWavelength OBJECT-TYPE
    SYNTAX       FixedX100
    MAX-ACCESS   read-create
    STATUS       current
    DESCRIPTION  "The wavelength to be transmitted by the transceiver on the
                  OC-N facility port. This is a mandatory object when a row of
                  the OC-N table is created."
    ::= { ocnEntry 19 }


ocnVendorPN1 OBJECT-TYPE
    SYNTAX       DisplayString (SIZE (0..20))
    MAX-ACCESS   read-create
    STATUS       current
    DESCRIPTION  "An optionally provisioned part number used to validate the
                  optical transceiver on the OC-N facility port."
    DEFVAL       { "" }
    ::= { ocnEntry 20 }


ocnVendorPN2 OBJECT-TYPE
    SYNTAX       DisplayString (SIZE (0..20))
    MAX-ACCESS   read-create
    STATUS       current
    DESCRIPTION  "An optionally provisioned part number used to validate the
                  optical transceiver on the OC-N facility port."
    DEFVAL       { "" }
    ::= { ocnEntry 21 }


ocnVendorPN3 OBJECT-TYPE
    SYNTAX       DisplayString (SIZE (0..20))
    MAX-ACCESS   read-create
    STATUS       current
    DESCRIPTION  "An optionally provisioned part number used to validate the
                  optical transceiver on the OC-N facility port."
    DEFVAL       { "" }
    ::= { ocnEntry 22 }


ocnPhyPMMon OBJECT-TYPE
    SYNTAX       INTEGER { enabled  (1),
                           disabled (2) }
    MAX-ACCESS   read-create
    STATUS       current
    DESCRIPTION  "Indicates if the OC-N facility is configured to report
                  threshold crossing conditions for physical layer performance
                  monitoring parameters."
    DEFVAL       { disabled }
    ::= { ocnEntry 23 }


ocnLaserStatus OBJECT-TYPE
    SYNTAX       INTEGER { on    (1),
                           off   (2) }
    MAX-ACCESS   read-only
    STATUS       current
    DESCRIPTION  "An indication of the operational status of the transceiver
                  laser on the OC-N facility port."
    ::= { ocnEntry 24 }


ocnId1 OBJECT-TYPE
    SYNTAX       DisplayString (SIZE (0..32))
    MAX-ACCESS   read-create
    STATUS       current
    DESCRIPTION  "Textual data recorded by the user to describe the provisioned
                  OC-N facility in a manner useful to the user."
    DEFVAL       { "" }
    ::= { ocnEntry 25 }


ocnFiberType OBJECT-TYPE
    SYNTAX       FiberType
    MAX-ACCESS   read-create
    STATUS       current
    DESCRIPTION  "An optional specification of the fiber type that interfaces to
                  the OC-N facility port."
    DEFVAL       { none }
    ::= { ocnEntry 26 }


ocnCustom1 OBJECT-TYPE
    SYNTAX       DisplayString
    MAX-ACCESS   read-create
    STATUS       current
    DESCRIPTION  "A variable length text string for operating company use."
    DEFVAL       { "" }
    ::= { ocnEntry 27 }


ocnTOHTransparency OBJECT-TYPE
    SYNTAX       INTEGER { yes (1),
                           no  (2) }
    MAX-ACCESS   read-create
    STATUS       current
    DESCRIPTION  "Used to configure whether the transport overhead of the the
                  SONET OC-N facility is to be handled transparently or if it is
                  to be terminated and regenerated. This object only applies to
                  OC-48 client facilities on the 10G MXP circuit pack and the OC-12
                  and OC-3 client facilities on the 8-port 2.5G MXP circuit pack."

    DEFVAL       { no }
    ::= { ocnEntry 28 }


ocnLineMapping OBJECT-TYPE
    SYNTAX       INTEGER { unmapped      (1),
                           odu1ToOtu2    (2),
                           otu2          (3),
                           subOdu1ToOtu1 (4),
                           otu1          (5) }
    MAX-ACCESS   read-create
    STATUS       current
    DESCRIPTION  "Used to configure the OTN configuration of the line port. If
                  set to unmapped, there is no OTN digital wrapper added to the
                  OC-192 or OC-48 facility. 

                  The odu1ToOtu2 and otu2 mapping is applicable to OC-192 line
                  ports as follows:

                  odu1ToOtu2 - the line port is configured as an OTN digitally 
                               wrapped OTU2 facility containing 4 ODU1 units. 

                  otu2 - the line port is configured as an OTN digitally 
                         wrapped OTU2 facility to which an OC-192 facility is 
                         directly mapped. 
                  
                  The subOdu1ToOtu1 and otu1 mapping is applicable to OC-48 line
                  ports as follows:
 
                  subOdu1ToOtu1 - the line port is configured as an OTN digitally 
                                  wrapped ODU1 facility containing 4 sub-ODU1 units. 

                  otu1 - the line port is configured as an OTN digitally wrapped 
                         OTU1 facility to which an OC-48 facility is directly mapped.
                 
                  This object applies only to the OC-192 line port of the 10G MXP 
                  circuit pack and the OC-48 line port of the 8-port 2.5G circuit pack."
    DEFVAL       { otu2 }
    ::= { ocnEntry 29 }
    
    
ocnProtSwEvtType OBJECT-TYPE
    SYNTAX       ProtSwEvtType
    MAX-ACCESS   accessible-for-notify
    STATUS       current
    DESCRIPTION  "Indicates the type of protection switching event that has
                  occured on an OC-N facility."
    ::= { ocnEntry 30 }


ocnDCCTransparency OBJECT-TYPE
    SYNTAX       INTEGER { yes (1),
                           no  (2) }
    MAX-ACCESS   read-create
    STATUS       current
    DESCRIPTION  "Used to configure whether the Data Communications Channel (DCC)
                  is transported transparently through the circuit pack. Specifically,
                  this refers to the D1, D2 and D3 section DCC bytes.
                  This object only applies to OC-48 client facilities on the 
                  10G MXP circuit pack and the OC-12 client facilities on the 
                  8-port 2.5G MXP circuit pack."

    DEFVAL       { no }
    ::= { ocnEntry 31 }


ocnTransparencyChannel OBJECT-TYPE
    SYNTAX       INTEGER (1..48)
    MAX-ACCESS   read-create
    STATUS       current
    DESCRIPTION  "Used to configure the STS1 channel number on which the DCC
                  is transported. This object only applies to OC-48 client facilities 
                  on the 10G MXP circuit pack and the OC-12 client facilities on the 
                  8-port 2.5G MXP circuit pack."

    DEFVAL       { 1 }
    ::= { ocnEntry 32 }
    
    
ocnRemoteId OBJECT-TYPE
    SYNTAX       DisplayString
    MAX-ACCESS   read-create
    STATUS       current
    DESCRIPTION  "Identifies the remote node and port to which the
                  OC-n port is connected, in the format prescribed
                  by the PSM network management system."
    DEFVAL       { "" }
    ::= { ocnEntry 33 }


ocnRowStatus OBJECT-TYPE
    SYNTAX       RowStatus
    MAX-ACCESS   read-create
    STATUS       current
    DESCRIPTION  "Used to control the addition and deletion of entries in the
                  OC-N table, which in turn controls provisioning and
                  deprovisioning of OC-N facilities."
    ::= { ocnEntry 100 }


-----------------------------------------------------------------------
-- Objects related to created SONET STS-N facilities on
-- Muxponder Circuit Packs
-- 
-- A listing of SONET STS-N path entities that are created on the
-- BTI 7000 Series system. STS-1 path facilities are employed on the
-- SONET version of the Dual GbE Muxponder circuit pack. Only STS-1
-- paths involved in protected VCG configurations on the muxponder card
-- are listed in the stsnTable.
-- 
-- The following table lists the objects in each entry of the
-- stsnTable.
-----------------------------------------------------------------------


stsnTable OBJECT-TYPE
    SYNTAX       SEQUENCE OF StsnEntry
    MAX-ACCESS   not-accessible
    STATUS       current
    DESCRIPTION  "This table contains one row for every created SONET STS-N
                  facility on the system. Each row contains a list of attributes
                  that pertain to the facility."
    ::= { facilities 6 }


stsnEntry OBJECT-TYPE
    SYNTAX       StsnEntry
    MAX-ACCESS   not-accessible
    STATUS       current
    DESCRIPTION  "The conceptual row object of the STS-N table."
    INDEX        { stsnTypeIdx,
                   stsnShelfIdx,
                   stsnSlotIdx,
                   stsnPortIdx,
                   stsnIdx }
    ::= { stsnTable 1 }


StsnEntry ::= SEQUENCE { stsnTypeIdx        StsnType,
                         stsnShelfIdx       INTEGER,
                         stsnSlotIdx        INTEGER,
                         stsnPortIdx        INTEGER,
                         stsnIdx            INTEGER,
                         stsnProtSwEvtType  ProtSwEvtType,
                         stsnBER            BERType,
                         stsnBERTh          BERType,
                         stsnProtSwStatus   OperStatQlfr }


stsnTypeIdx OBJECT-TYPE
    SYNTAX       StsnType
    MAX-ACCESS   accessible-for-notify
    STATUS       current
    DESCRIPTION  "The specific type of STS-N signal which is created."
    ::= { stsnEntry 1 }


stsnShelfIdx OBJECT-TYPE
    SYNTAX       INTEGER (1|11|21|31)
    MAX-ACCESS   accessible-for-notify
    STATUS       current
    DESCRIPTION  "The number of the shelf on which the STS-N facility exists."
    ::= { stsnEntry 2 }


stsnSlotIdx OBJECT-TYPE
    SYNTAX       INTEGER (1..20)
    MAX-ACCESS   accessible-for-notify
    STATUS       current
    DESCRIPTION  "The number of the slot within which the STS-N facility
                  exists."
    ::= { stsnEntry 3 }


stsnPortIdx OBJECT-TYPE
    SYNTAX       INTEGER (1..2)
    MAX-ACCESS   accessible-for-notify
    STATUS       current
    DESCRIPTION  "The number of the port on the circuit pack on which the STS-N
                  facility exists."
    ::= { stsnEntry 4 }


stsnIdx OBJECT-TYPE
    SYNTAX       INTEGER (1..192)
    MAX-ACCESS   accessible-for-notify
    STATUS       current
    DESCRIPTION  "The stsn channel number within the port in which the STS-N
                  facility exists."
    ::= { stsnEntry 5 }


stsnProtSwEvtType OBJECT-TYPE
    SYNTAX       ProtSwEvtType
    MAX-ACCESS   accessible-for-notify
    STATUS       current
    DESCRIPTION  "Indicates the type of protection switching event that has
                  occured on an STS-N facility."
    ::= { stsnEntry 6 }


stsnBER OBJECT-TYPE
    SYNTAX       BERType
    MAX-ACCESS   accessible-for-notify
    STATUS       current
    DESCRIPTION  "The Bit Error Rate measured on the received channel."
    ::= { stsnEntry 7 }


stsnBERTh OBJECT-TYPE
    SYNTAX       BERType
    MAX-ACCESS   accessible-for-notify
    STATUS       current
    DESCRIPTION  "The Bit Error Rate threshold above which the Signal Degrade
                  condition is raised."
    ::= { stsnEntry 8 }


stsnProtSwStatus OBJECT-TYPE
    SYNTAX       OperStatQlfr
    MAX-ACCESS   read-only
    STATUS       current
    DESCRIPTION  "If the STS-N facility is configured as part of a protection
                  grouping, this object indicates its protection status."
    ::= { stsnEntry 9 }



-----------------------------------------------------------------------
-- Objects related to provisioned SDH STM-N facilities on
-- Muxponder Circuit Packs
-- 
-- A listing of provisioned SDH STM-N ports is contained in the
-- stmnTable of the BTI 7000 Series MIB. When retrieved, this table
-- includes one row for each provisioned SDH STM-N port facility, 
-- which includes STM-16 and STM-64 facilities.
-- 
-- Note: The stmnTable manages STM-N facilities on muxponder circuit
-- packs, and is not used for wavelength conversion type circuit packs. 
-- For management of these facilities, the xcvrTable is used.
-- 
-- To manually provision an STM-16 or STM-64 facility, a row must be
-- created in the stmnTable. To deprovision an STM-N facility, its row
-- must be destroyed. 
-- 
-- The following table lists the objects in each entry of the
-- stmnTable.
-----------------------------------------------------------------------


stmnTable OBJECT-TYPE
    SYNTAX       SEQUENCE OF StmnEntry
    MAX-ACCESS   not-accessible
    STATUS       current
    DESCRIPTION  "This table contains one row for every provisioned SDH STM-N
                  facility on the system. Each row contains a list of attributes
                  that pertain to the facility."
    ::= { facilities 7 }


stmnEntry OBJECT-TYPE
    SYNTAX       StmnEntry
    MAX-ACCESS   not-accessible
    STATUS       current
    DESCRIPTION  "The conceptual row object of the STM-N table."
    INDEX        { stmnTypeIdx,
                   stmnShelfIdx,
                   stmnSlotIdx,
                   stmnPortIdx }
    ::= { stmnTable 1 }


StmnEntry ::= SEQUENCE { stmnTypeIdx                     StmnType,
                         stmnShelfIdx                    INTEGER,
                         stmnSlotIdx                     INTEGER,
                         stmnPortIdx                     INTEGER,
                         stmnOpticalPwrReceivedMinTh     FixedX10,
                         stmnOpticalPwrReceivedMaxTh     FixedX10,
                         stmnOpticalPwrTransmittedMinTh  FixedX10,
                         stmnOpticalPwrTransmittedMaxTh  FixedX10,
                         stmnOpticalPwrReceived          FixedX10,
                         stmnOpticalPwrTransmitted       FixedX10,
                         stmnBER                         BERType,
                         stmnBERTh                       BERType,
                         stmnPEC                         DisplayString,
                         stmnAdminStatus                 AdminStatus,
                         stmnOperStatus                  OperStatus,
                         stmnOperStatQlfr                OperStatQlfr,
                         stmnAutoEnableTimer             HoursAndMinutes,
                         stmnActAutoEnableTimer          HoursAndMinutes,
                         stmnWavelength                  FixedX100,
                         stmnVendorPN1                   DisplayString,
                         stmnVendorPN2                   DisplayString,
                         stmnVendorPN3                   DisplayString,
                         stmnPhyPMMon                    INTEGER,
                         stmnLaserStatus                 INTEGER,
                         stmnId1                         DisplayString,
                         stmnFiberType                   FiberType,
                         stmnCustom1                     DisplayString,
                         stmnTOHTransparency             INTEGER,
                         stmnLineMapping                 INTEGER,
                         stmnProtSwEvtType               ProtSwEvtType,
                         stmnDCCTransparency             INTEGER,
                         stmnTransparencyChannel         INTEGER,
                         stmnRemoteId                    DisplayString,
                         stmnRowStatus                   RowStatus }


stmnTypeIdx OBJECT-TYPE
    SYNTAX       StmnType
    MAX-ACCESS   accessible-for-notify
    STATUS       current
    DESCRIPTION  "The specific type of STM-N signal which is provisioned."
    ::= { stmnEntry 1 }


stmnShelfIdx OBJECT-TYPE
    SYNTAX       INTEGER (1|11|21|31)
    MAX-ACCESS   accessible-for-notify
    STATUS       current
    DESCRIPTION  "The number of the shelf on which the STM-N facility is
                  provisioned."
    ::= { stmnEntry 2 }


stmnSlotIdx OBJECT-TYPE
    SYNTAX       INTEGER (1..20)
    MAX-ACCESS   accessible-for-notify
    STATUS       current
    DESCRIPTION  "The number of the slot within which the STM-N facility is
                  provisioned."
    ::= { stmnEntry 3 }


stmnPortIdx OBJECT-TYPE
    SYNTAX       INTEGER (1..6)
    MAX-ACCESS   accessible-for-notify
    STATUS       current
    DESCRIPTION  "The number of the port on the circuit pack on which the STM-N
                  facility is provisioned."
    ::= { stmnEntry 4 }


stmnOpticalPwrReceivedMinTh OBJECT-TYPE
    SYNTAX       FixedX10
    UNITS        "dBm/10"
    MAX-ACCESS   read-only
    STATUS       current
    DESCRIPTION  "This is the optical power received minimum threshold."
    ::= { stmnEntry 5 }


stmnOpticalPwrReceivedMaxTh OBJECT-TYPE
    SYNTAX       FixedX10
    UNITS        "dBm/10"
    MAX-ACCESS   read-only
    STATUS       current
    DESCRIPTION  "This is the optical power received maximum threshold."
    ::= { stmnEntry 6 }


stmnOpticalPwrTransmittedMinTh OBJECT-TYPE
    SYNTAX       FixedX10
    UNITS        "dBm/10"
    MAX-ACCESS   read-only
    STATUS       current
    DESCRIPTION  "This is the optical power transmitted minimum threshold."
    ::= { stmnEntry 7 }


stmnOpticalPwrTransmittedMaxTh OBJECT-TYPE
    SYNTAX       FixedX10
    UNITS        "dBm/10"
    MAX-ACCESS   read-only
    STATUS       current
    DESCRIPTION  "This is the optical power transmitted maximum threshold."
    ::= { stmnEntry 8 }


stmnOpticalPwrReceived OBJECT-TYPE
    SYNTAX       FixedX10
    UNITS        "dBm/10"
    MAX-ACCESS   accessible-for-notify
    STATUS       current
    DESCRIPTION  "The optical power received on the input of the transceiver."
    ::= { stmnEntry 9 }


stmnOpticalPwrTransmitted OBJECT-TYPE
    SYNTAX       FixedX10
    UNITS        "dBm/10"
    MAX-ACCESS   accessible-for-notify
    STATUS       current
    DESCRIPTION  "The optical power transmitted at the output of the
                  transceiver."
    ::= { stmnEntry 10 }


stmnBER OBJECT-TYPE
    SYNTAX       BERType
    MAX-ACCESS   accessible-for-notify
    STATUS       current
    DESCRIPTION  "The Bit Error Rate measured on the received signal."
    ::= { stmnEntry 11 }


stmnBERTh OBJECT-TYPE
    SYNTAX       BERType
    MAX-ACCESS   read-create
    STATUS       current
    DESCRIPTION  "The Bit Error Rate threshold above which the Signal Degrade
                  condition is raised."
    DEFVAL { tenExpMinus6 }
    ::= { stmnEntry 12 }


stmnPEC OBJECT-TYPE
    SYNTAX       DisplayString (SIZE (0..32))
    MAX-ACCESS   read-create
    STATUS       current
    DESCRIPTION  "An optionally provisioned Product Equipment Code used to
                  validate the physically present optical transceiver on the
                  STM-N port."
    DEFVAL       { "" }
    ::= { stmnEntry 13 }


stmnAdminStatus OBJECT-TYPE
    SYNTAX       AdminStatus
    MAX-ACCESS   read-create
    STATUS       current
    DESCRIPTION  "The administrative status of the STM-N facility."
    DEFVAL       { enabled }
    ::= { stmnEntry 14 }


stmnOperStatus OBJECT-TYPE
    SYNTAX       OperStatus
    MAX-ACCESS   read-only
    STATUS       current
    DESCRIPTION  "The reported operational status of the STM-N facility."
    ::= { stmnEntry 15 }


stmnOperStatQlfr OBJECT-TYPE
    SYNTAX       OperStatQlfr
    MAX-ACCESS   read-only
    STATUS       current
    DESCRIPTION  "This is a textual list of qualifiers about the reported
                  operational status of the STM-N facility."
    ::= { stmnEntry 16 }


stmnAutoEnableTimer OBJECT-TYPE
    SYNTAX       HoursAndMinutes
    MAX-ACCESS   read-create
    STATUS       current
    DESCRIPTION  "Specifies the auto-enable timer for the targeted STM-N
                  facility. This value only applies if the stmnAdminStatus
                  object is set to autoEnabled. Otherwise, the value returned is
                  000-00."
    DEFVAL       { "008-00" }
    ::= { stmnEntry 17 }


stmnActAutoEnableTimer OBJECT-TYPE
    SYNTAX       HoursAndMinutes
    MAX-ACCESS   read-only
    STATUS       current
    DESCRIPTION  "Indicates the time remaining on the auto-enable timer if it is
                  actively counting down. Otherwise, the value returned is
                  000-00."
    ::= { stmnEntry 18 }


stmnWavelength OBJECT-TYPE
    SYNTAX       FixedX100
    MAX-ACCESS   read-create
    STATUS       current
    DESCRIPTION  "The wavelength to be transmitted by the transceiver on the
                  STM-N facility port. This is a mandatory object when a row of
                  the STM-N table is created."
    ::= { stmnEntry 19 }


stmnVendorPN1 OBJECT-TYPE
    SYNTAX       DisplayString (SIZE (0..20))
    MAX-ACCESS   read-create
    STATUS       current
    DESCRIPTION  "An optionally provisioned part number used to validate the
                  optical transceiver on the STM-N facility port."
    DEFVAL       { "" }
    ::= { stmnEntry 20 }


stmnVendorPN2 OBJECT-TYPE
    SYNTAX       DisplayString (SIZE (0..20))
    MAX-ACCESS   read-create
    STATUS       current
    DESCRIPTION  "An optionally provisioned part number used to validate the
                  optical transceiver on the STM-N facility port."
    DEFVAL       { "" }
    ::= { stmnEntry 21 }


stmnVendorPN3 OBJECT-TYPE
    SYNTAX       DisplayString (SIZE (0..20))
    MAX-ACCESS   read-create
    STATUS       current
    DESCRIPTION  "An optionally provisioned part number used to validate the
                  optical transceiver on the STM-N facility port."
    DEFVAL       { "" }
    ::= { stmnEntry 22 }


stmnPhyPMMon OBJECT-TYPE
    SYNTAX       INTEGER { enabled  (1),
                           disabled (2) }
    MAX-ACCESS   read-create
    STATUS       current
    DESCRIPTION  "Indicates if the STM-N facility is configured to report
                  threshold crossing conditions for physical layer performance
                  monitoring parameters."
    DEFVAL       { disabled }
    ::= { stmnEntry 23 }


stmnLaserStatus OBJECT-TYPE
    SYNTAX       INTEGER { on    (1),
                           off   (2) }
    MAX-ACCESS   read-only
    STATUS       current
    DESCRIPTION  "An indication of the operational status of the transceiver
                  laser on the STM-N facility port."
    ::= { stmnEntry 24 }


stmnId1 OBJECT-TYPE
    SYNTAX       DisplayString (SIZE (0..32))
    MAX-ACCESS   read-create
    STATUS       current
    DESCRIPTION  "Textual data recorded by the user to describe the provisioned
                  STM-N facility in a manner useful to the user."
    DEFVAL       { "" }
    ::= { stmnEntry 25 }


stmnFiberType OBJECT-TYPE
    SYNTAX       FiberType
    MAX-ACCESS   read-create
    STATUS       current
    DESCRIPTION  "An optional specification of the fiber type that interfaces to
                  the STM-N facility port."
    DEFVAL       { none }
    ::= { stmnEntry 26 }


stmnCustom1 OBJECT-TYPE
    SYNTAX       DisplayString
    MAX-ACCESS   read-create
    STATUS       current
    DESCRIPTION  "A variable length text string for operating company use."
    DEFVAL       { "" }
    ::= { stmnEntry 27 }


stmnTOHTransparency OBJECT-TYPE
    SYNTAX       INTEGER { yes (1),
                           no  (2) }
    MAX-ACCESS   read-create
    STATUS       current
    DESCRIPTION  "Used to configure whether the transport overhead of the the
                  SDH STM-N facility is to be handled transparently or if it is
                  to be terminated and regenerated. This object only applies to
                  STM-16 client facilities on the 10G MXP circuit pack and the STM-4
                  and STM-1 client facilities on the 8-port 2.5G MXP circuit pack."

    DEFVAL       { no }
    ::= { stmnEntry 28 }


stmnLineMapping OBJECT-TYPE
    SYNTAX       INTEGER { unmapped      (1),
                           odu1ToOtu2    (2),
                           otu2          (3),
                           subOdu1ToOtu1 (4),
                           otu1          (5) }

    MAX-ACCESS   read-create
    STATUS       current
    DESCRIPTION  "Used to configure the OTN configuration of the line port. If
                  set to unmapped, there is no OTN digital wrapper added to the
                  STM-64 or STM-16 facility. 

                  The odu1ToOtu2 and otu2 mapping is applicable to STM-64 line
                  ports as follows:

                  odu1ToOtu2 - the line port is configured as an OTN digitally 
                               wrapped OTU2 facility containing 4 ODU1 units. 

                  otu2 - the line port is configured as an OTN digitally 
                         wrapped OTU2 facility to which an STM-64 facility is 
                         directly mapped. 
                  
                  The subOdu1ToOtu1 and otu1 mapping is applicable to STM-16 line
                  ports as follows:
 
                  subOdu1ToOtu1 - the line port is configured as an OTN digitally 
                                  wrapped ODU1 facility containing 4 sub-ODU1 units. 

                  otu1 - the line port is configured as an OTN digitally wrapped 
                         OTU1 facility to which an STM-16 facility is directly mapped.
                 
                  This object applies only to the STM-64 line port of the 10G MXP 
                  circuit pack and the STM-16 line port of the 8-port 2.5G circuit pack."
    DEFVAL       { otu2 }
    ::= { stmnEntry 29 }
    
    
stmnProtSwEvtType OBJECT-TYPE
    SYNTAX       ProtSwEvtType
    MAX-ACCESS   accessible-for-notify
    STATUS       current
    DESCRIPTION  "Indicates the type of protection switching event that has
                  occured on an STM-N facility."
    ::= { stmnEntry 30 }
    
    
stmnDCCTransparency OBJECT-TYPE
    SYNTAX       INTEGER { yes (1),
                           no  (2) }
    MAX-ACCESS   read-create
    STATUS       current
    DESCRIPTION  "Used to configure whether the Data Communications Channel (DCC)
                  is transported transparently through the circuit pack. Specifically,
                  this refers to the D1, D2 and D3 section DCC bytes.
                  This object only applies to STM-16 client facilities on the 
                  10G MXP circuit pack and the STM-4 client facilities on the 
                  8-port 2.5G MXP circuit pack."

    DEFVAL       { no }
    ::= { stmnEntry 31 }
    

stmnTransparencyChannel OBJECT-TYPE
    SYNTAX       INTEGER (1..16)
    MAX-ACCESS   read-create
    STATUS       current
    DESCRIPTION  "Used to configure the VC4 channel number on which the DCC
                  is transported. This object only applies to STM-16 client facilities 
                  on the 10G MXP circuit pack and the STM-4 client facilities on the 
                  8-port 2.5G MXP circuit pack."

    DEFVAL       { 1 }
    ::= { stmnEntry 32 }
    
    
stmnRemoteId OBJECT-TYPE
    SYNTAX       DisplayString
    MAX-ACCESS   read-create
    STATUS       current
    DESCRIPTION  "Identifies the remote node and port to which the
                  STM-n port is connected, in the format prescribed
                  by the PSM network management system."
    DEFVAL       { "" }
    ::= { stmnEntry 33 }


stmnRowStatus OBJECT-TYPE
    SYNTAX       RowStatus
    MAX-ACCESS   read-create
    STATUS       current
    DESCRIPTION  "Used to control the addition and deletion of entries in the
                  STM-N table, which in turn controls provisioning and
                  deprovisioning of STM-N facilities."
    ::= { stmnEntry 100 }



-----------------------------------------------------------------------
-- Objects related to created SDH VC-N facilities on
-- Muxponder Circuit Packs
-- 
-- The vcnTable lists the SDH VC-N path entities that are created on
-- the BTI 7000 Series system. VC4 path facilities are employed on SDH
-- versions of the Dual GbE Muxponder circuit pack.
-- 
-- Only VC4 paths involved in protected VCG configurations on the
-- muxponder card are listed in the stsnTable.
-- 
-- The following table lists the objects in each entry of the vcnTable.
-----------------------------------------------------------------------


vcnTable OBJECT-TYPE
    SYNTAX       SEQUENCE OF VcnEntry
    MAX-ACCESS   not-accessible
    STATUS       current
    DESCRIPTION  "This table contains one row for every created SDH VC-N
                  facility on the system. Each row contains a list of attributes
                  that pertain to the facility."
    ::= { facilities 8 }


vcnEntry OBJECT-TYPE
    SYNTAX       VcnEntry
    MAX-ACCESS   not-accessible
    STATUS       current
    DESCRIPTION  "The conceptual row object of the VC-N table."
    INDEX        { vcnTypeIdx,
                   vcnShelfIdx,
                   vcnSlotIdx,
                   vcnPortIdx,
                   vcnIdx }
    ::= { vcnTable 1 }


VcnEntry ::= SEQUENCE { vcnTypeIdx        VcnType,
                        vcnShelfIdx       INTEGER,
                        vcnSlotIdx        INTEGER,
                        vcnPortIdx        INTEGER,
                        vcnIdx            INTEGER,
                        vcnProtSwEvtType  ProtSwEvtType,
                        vcnBER            BERType,
                        vcnBERTh          BERType,
                        vcnProtSwStatus   OperStatQlfr }


vcnTypeIdx OBJECT-TYPE
    SYNTAX       VcnType
    MAX-ACCESS   accessible-for-notify
    STATUS       current
    DESCRIPTION  "The specific type of VC-N signal which is created."
    ::= { vcnEntry 1 }


vcnShelfIdx OBJECT-TYPE
    SYNTAX       INTEGER (1|11|21|31)
    MAX-ACCESS   accessible-for-notify
    STATUS       current
    DESCRIPTION  "The number of the shelf on which the VC-N facility exists."
    ::= { vcnEntry 2 }


vcnSlotIdx OBJECT-TYPE
    SYNTAX       INTEGER (1..20)
    MAX-ACCESS   accessible-for-notify
    STATUS       current
    DESCRIPTION  "The number of the slot within which the VC-N facility exists."
    ::= { vcnEntry 3 }


vcnPortIdx OBJECT-TYPE
    SYNTAX       INTEGER (1..2)
    MAX-ACCESS   accessible-for-notify
    STATUS       current
    DESCRIPTION  "The number of the port on the circuit pack on which the VC-N
                  facility exists."
    ::= { vcnEntry 4 }


vcnIdx OBJECT-TYPE
    SYNTAX       INTEGER (1..64)
    MAX-ACCESS   accessible-for-notify
    STATUS       current
    DESCRIPTION  "The vcn channel number within the port in which the VC-N
                  facility exists."
    ::= { vcnEntry 5 }


vcnProtSwEvtType OBJECT-TYPE
    SYNTAX       ProtSwEvtType
    MAX-ACCESS   accessible-for-notify
    STATUS       current
    DESCRIPTION  "Indicates the type of protection switching event that has
                  occured on a VC-N facility."
    ::= { vcnEntry 6 }


vcnBER OBJECT-TYPE
    SYNTAX       BERType
    MAX-ACCESS   accessible-for-notify
    STATUS       current
    DESCRIPTION  "The Bit Error Rate measured on the received channel."
    ::= { vcnEntry 7 }


vcnBERTh OBJECT-TYPE
    SYNTAX       BERType
    MAX-ACCESS   accessible-for-notify
    STATUS       current
    DESCRIPTION  "The Bit Error Rate threshold above which the Signal Degrade
                  condition is raised."
    ::= { vcnEntry 8 }


vcnProtSwStatus OBJECT-TYPE
    SYNTAX       OperStatQlfr
    MAX-ACCESS   read-only
    STATUS       current
    DESCRIPTION  "If the VC-N facility is configured as part of a protection
                  grouping, this object indicates its protection status."
    ::= { vcnEntry 9 }


-----------------------------------------------------------------------
-- Objects related to provisioned Gigabit Ethernet (GE) facilities on
-- Muxponder Circuit Packs
-- 
-- A listing of provisioned Gigabit Ethernet facilities is contained
-- in the geTable ofthe BTI 7000 Series MIB. When retrieved, this table
-- includes one  row for each provisioned Gigabit Ethernet port 
-- facility.
-- 
-- Note: The geTable manages Gigabit Ethernet facilities on muxponder
-- circuit packs, and is not used for wavelength conversion type circuit
-- packs. For management of these facilities, the xcvrTable is used.
-- 
-- To manually provision a Gigabit Ethernet facility, a row must be
-- created in the geTable. To deprovision a Gigabit Ethernet facility,
-- its row must be destroyed.
-- 
-- The following table lists the objects in each entry of the geTable.
-----------------------------------------------------------------------


geTable OBJECT-TYPE
    SYNTAX       SEQUENCE OF GeEntry
    MAX-ACCESS   not-accessible
    STATUS       current
    DESCRIPTION  "This table contains one row for every provisioned Gigabit
                  Ethernet (GE) facility on the system. Each row contains a list
                  of attributes that pertain to the facility."
    ::= { facilities 9 }


geEntry OBJECT-TYPE
    SYNTAX       GeEntry
    MAX-ACCESS   not-accessible
    STATUS       current
    DESCRIPTION  "The conceptual row object of the GE table."
    INDEX        { geShelfIdx,
                   geSlotIdx,
                   gePortIdx }
    ::= { geTable 1 }


GeEntry ::= SEQUENCE { geShelfIdx                    INTEGER,
                       geSlotIdx                     INTEGER,
                       gePortIdx                     INTEGER,
                       geOpticalPwrReceivedMinTh     FixedX10,
                       geOpticalPwrReceivedMaxTh     FixedX10,
                       geOpticalPwrTransmittedMinTh  FixedX10,
                       geOpticalPwrTransmittedMaxTh  FixedX10,
                       geOpticalPwrReceived          FixedX10,
                       geOpticalPwrTransmitted       FixedX10,
                       gePEC                         DisplayString,
                       geAdminStatus                 AdminStatus,
                       geOperStatus                  OperStatus,
                       geOperStatQlfr                OperStatQlfr,
                       geAutoEnableTimer             HoursAndMinutes,
                       geActAutoEnableTimer          HoursAndMinutes,
                       geWavelength                  FixedX100,
                       geVendorPN1                   DisplayString,
                       geVendorPN2                   DisplayString,
                       geVendorPN3                   DisplayString,
                       gePhyPMMon                    INTEGER,
                       geFPSD                        INTEGER,
                       geLaserStatus                 INTEGER,
                       geId1                         DisplayString,
                       geFiberType                   FiberType,
                       geCustom1                     DisplayString,
                       geSpeed                       Gauge32,
                       geDuplex                      DuplexModeType,
                       geMediaRate                   MediaRateType,
                       geMTU                         Integer32,
                       geMACAddr                     MacAddress,
                       geGfpMode                     INTEGER,
                       geFlowControl                 INTEGER,
                       geRemoteId                    DisplayString,
                       geRowStatus                   RowStatus }


geShelfIdx OBJECT-TYPE
    SYNTAX       INTEGER (1|11|21|31)
    MAX-ACCESS   accessible-for-notify
    STATUS       current
    DESCRIPTION  "The number of the shelf on which the GE facility is
                  provisioned."
    ::= { geEntry 1 }


geSlotIdx OBJECT-TYPE
    SYNTAX       INTEGER (1..20)
    MAX-ACCESS   accessible-for-notify
    STATUS       current
    DESCRIPTION  "The number of the slot within which the GE facility is
                  provisioned."
    ::= { geEntry 2 }


gePortIdx OBJECT-TYPE
    SYNTAX       INTEGER (3..12)
    MAX-ACCESS   accessible-for-notify
    STATUS       current
    DESCRIPTION  "The number of the port on the circuit pack on which the GE
                  facility is provisioned."
    ::= { geEntry 3 }


geOpticalPwrReceivedMinTh OBJECT-TYPE
    SYNTAX       FixedX10
    UNITS        "dBm/10"
    MAX-ACCESS    read-only 
    STATUS       current
    DESCRIPTION  "This is the optical power received minimum threshold."
    ::= { geEntry 4 }


geOpticalPwrReceivedMaxTh OBJECT-TYPE
    SYNTAX       FixedX10
    UNITS        "dBm/10"
    MAX-ACCESS   read-only
    STATUS       current
    DESCRIPTION  "This is the optical power received maximum threshold."
    ::= { geEntry 5 }


geOpticalPwrTransmittedMinTh OBJECT-TYPE
    SYNTAX       FixedX10
    UNITS        "dBm/10"
    MAX-ACCESS   read-only
    STATUS       current
    DESCRIPTION  "This is the optical power transmitted minimum threshold."
    ::= { geEntry 6 }


geOpticalPwrTransmittedMaxTh OBJECT-TYPE
    SYNTAX       FixedX10
    UNITS        "dBm/10"
    MAX-ACCESS   read-only
    STATUS       current
    DESCRIPTION  "This is the optical power transmitted maximum threshold."
    ::= { geEntry 7 }


geOpticalPwrReceived OBJECT-TYPE
    SYNTAX       FixedX10
    UNITS        "dBm/10"
    MAX-ACCESS   accessible-for-notify
    STATUS       current
    DESCRIPTION  "The optical power received on the input of the transceiver."
    ::= { geEntry 8 }


geOpticalPwrTransmitted OBJECT-TYPE
    SYNTAX       FixedX10
    UNITS        "dBm/10"
    MAX-ACCESS   accessible-for-notify
    STATUS       current
    DESCRIPTION  "The optical power transmitted at the output of the
                  transceiver."
    ::= { geEntry 9 }


gePEC OBJECT-TYPE
    SYNTAX       DisplayString (SIZE (0..32))
    MAX-ACCESS   read-create
    STATUS       current
    DESCRIPTION  "An optionally provisioned transceiver Product Equipment Code
                  used to validate the physically present transceiver on the
                  Gigabit Ethernet port."
    DEFVAL       { "" }
    ::= { geEntry 10 }


geAdminStatus OBJECT-TYPE
    SYNTAX       AdminStatus
    MAX-ACCESS   read-create
    STATUS       current
    DESCRIPTION  "The administrative status of the Gigabit Ethernet facility."
    DEFVAL       { enabled }
    ::= { geEntry 11 }


geOperStatus OBJECT-TYPE
    SYNTAX       OperStatus
    MAX-ACCESS   read-only
    STATUS       current
    DESCRIPTION  "The reported operational status of the Gigabit Ethernet
                  facility."
    ::= { geEntry 12 }


geOperStatQlfr OBJECT-TYPE
    SYNTAX       OperStatQlfr
    MAX-ACCESS   read-only
    STATUS       current
    DESCRIPTION  "This is a textual list of qualifiers about the reported
                  operational status of the Gigabit Ethernet facility."
    ::= { geEntry 13 }


geAutoEnableTimer OBJECT-TYPE
    SYNTAX       HoursAndMinutes
    MAX-ACCESS   read-create
    STATUS       current
    DESCRIPTION  "Specifies the auto-enable timer for the targeted Gigabit
                  Ethernet facility. This value only applies if the
                  geAdminStatus object is set to autoEnabled. Otherwise, the
                  value returned is 000-00."
    DEFVAL       { "008-00" }
    ::= { geEntry 14 }


geActAutoEnableTimer OBJECT-TYPE
    SYNTAX       HoursAndMinutes
    MAX-ACCESS   read-only
    STATUS       current
    DESCRIPTION  "Indicates the time remaining on the auto-enable timer if it is
                  actively counting down. Otherwise, the value returned is
                  000-00."
    ::= { geEntry 15 }


geWavelength OBJECT-TYPE
    SYNTAX       FixedX100
    MAX-ACCESS   read-create
    STATUS       current
    DESCRIPTION  "The wavelength to be transmitted by the transceiver on the
                  Gigabit Ethernet facility port. This is a mandatory object
                  when a row of the Gigabit Ethernet table is created."
    ::= { geEntry 16 }


geVendorPN1 OBJECT-TYPE
    SYNTAX       DisplayString (SIZE (0..20))
    MAX-ACCESS   read-create
    STATUS       current
    DESCRIPTION  "An optionally provisioned part number used to validate the
                  optical transceiver on the Gigabit Ethernet facility port."
    DEFVAL       { "" }
    ::= { geEntry 17 }


geVendorPN2 OBJECT-TYPE
    SYNTAX       DisplayString (SIZE (0..20))
    MAX-ACCESS   read-create
    STATUS       current
    DESCRIPTION  "An optionally provisioned part number used to validate the
                  optical transceiver on the Gigabit Ethernet facility port."
    DEFVAL       { "" }
    ::= { geEntry 18 }


geVendorPN3 OBJECT-TYPE
    SYNTAX       DisplayString (SIZE (0..20))
    MAX-ACCESS   read-create
    STATUS       current
    DESCRIPTION  "An optionally provisioned part number used to validate the
                  optical transceiver on the Gigabit Ethernet facility port."
    DEFVAL       { "" }
    ::= { geEntry 19 }


gePhyPMMon OBJECT-TYPE
    SYNTAX       INTEGER { enabled  (1),
                           disabled (2) }
    MAX-ACCESS   read-create
    STATUS       current
    DESCRIPTION  "Indicates if the Gigabit Ethernet facility is configured to
                  report threshold crossing conditions for physical layer
                  performance monitoring parameters."
    DEFVAL       { disabled }
    ::= { geEntry 20 }


geFPSD OBJECT-TYPE
    SYNTAX       INTEGER { enabled  (1),
                           disabled (2) }
    MAX-ACCESS   read-create
    STATUS       current
    DESCRIPTION  "Indicates if the Gigabit Ethernet facility is configured for
                  Fault Propagation Shut Down."
    DEFVAL       { disabled }
    ::= { geEntry 21 }


geLaserStatus OBJECT-TYPE
    SYNTAX       INTEGER { on    (1),
                           off   (2) }
    MAX-ACCESS   read-only
    STATUS       current
    DESCRIPTION  "An indication of the operational status of the transceiver
                  laser on the Gigabit Ethernet facility port."
    ::= { geEntry 22 }


geId1 OBJECT-TYPE
    SYNTAX       DisplayString (SIZE (0..32))
    MAX-ACCESS   read-create
    STATUS       current
    DESCRIPTION  "Textual data recorded by the user to describe the provisioned
                  Gigabit Ethernet facility in a manner useful to the user."
    DEFVAL       { "" }
    ::= { geEntry 23 }


geFiberType OBJECT-TYPE
    SYNTAX       FiberType
    MAX-ACCESS   read-create
    STATUS       current
    DESCRIPTION  "An optional specification of the fiber type that interfaces to
                  the Gigabit Ethernet facility port."
    DEFVAL       { none }
    ::= { geEntry 24 }


geCustom1 OBJECT-TYPE
    SYNTAX       DisplayString
    MAX-ACCESS   read-create
    STATUS       current
    DESCRIPTION  "A variable length text string for operating company use."
    DEFVAL       { "" }
    ::= { geEntry 25 }


geSpeed OBJECT-TYPE
    SYNTAX       Gauge32
    UNITS        "Mbps"
    MAX-ACCESS   read-only
    STATUS       current
    DESCRIPTION  "The speed of the Gigabit Ethernet facility link."
    ::= { geEntry 26 }


geDuplex OBJECT-TYPE
    SYNTAX       DuplexModeType
    MAX-ACCESS   read-only
    STATUS       current
    DESCRIPTION  "The duplex mode of the Gigabit Ethernet facility interface."
    ::= { geEntry 27 }


geMediaRate OBJECT-TYPE
    SYNTAX       MediaRateType
    MAX-ACCESS   read-create
    STATUS       current
    DESCRIPTION  "The configured media rate of the Gigabit Ethernet facility
                  interface."
    DEFVAL       { autoNegotiated  }
    ::= { geEntry 28 }



geMTU OBJECT-TYPE
    SYNTAX       Integer32
    MAX-ACCESS   read-only
    STATUS       current
    DESCRIPTION  "The MTU size for the Gigabit Ethernet facility interface."
    ::= { geEntry 29 }


geMACAddr OBJECT-TYPE
    SYNTAX       MacAddress
    MAX-ACCESS   read-only
    STATUS       current
    DESCRIPTION  "The MAC address of the Gigabit Ethernet facility interface."
    ::= { geEntry 30 }


geGfpMode OBJECT-TYPE
    SYNTAX       INTEGER { unmapped (1),
                           gfpf     (2),  -- GFP - Framed
                           gfpt     (3) } -- GFP - Transparent
    MAX-ACCESS   read-create
    STATUS       current
    DESCRIPTION  "Configures the mapping of GE facility port onto the line port
                  using either framed or transparent general framing protocol."
    DEFVAL       { gfpt }
    ::= { geEntry 31 }


geFlowControl OBJECT-TYPE
    SYNTAX       INTEGER { transparent (1),
                           local       (2) }
    MAX-ACCESS   read-create
    STATUS       current
    DESCRIPTION  "Configures the flow control setting of GE facility as
                  transparent or locally enabled."
    DEFVAL       { transparent }
    ::= { geEntry 32 }


geRemoteId OBJECT-TYPE
    SYNTAX       DisplayString
    MAX-ACCESS   read-create
    STATUS       current
    DESCRIPTION  "Identifies the remote node and port to which the
                  gigabit ethernet port is connected, in the format
                  prescribed by the PSM network management system."
    DEFVAL       { "" }
    ::= { geEntry 33 }


geRowStatus OBJECT-TYPE
    SYNTAX       RowStatus
    MAX-ACCESS   read-create
    STATUS       current
    DESCRIPTION  "Used to control the addition and deletion of entries in the
                  Gigabit Ethernet table, which in turn controls provisioning
                  and deprovisioning of Gigabit Ethernet facilities."
    ::= { geEntry 100 }



-----------------------------------------------------------------------
-- Objects related to provisioned Fast Ethernet (FE) facilities on
-- Muxponder Circuit Packs
-- 
-- A listing of provisioned Fast Ethernet facilities is contained in
-- the feTable of the BTI 7000 Series MIB. When retrieved, this table 
-- includes one row for each provisioned Fast Ethernet port facility.
-- 
-- To manually provision a Fast Ethernet facility, a row must be 
-- created in the feTable. To deprovision a Fast Ethernet facility, 
-- its row must be destroyed.
-- 
-- The following table lists the objects in each entry of the feTable.
-----------------------------------------------------------------------


feTable OBJECT-TYPE
    SYNTAX       SEQUENCE OF FeEntry
    MAX-ACCESS   not-accessible
    STATUS       current
    DESCRIPTION  "This table contains one row for every provisioned Fast
                  Ethernet (FE) facility on the system. Each row contains a list
                  of attributes that pertain to the facility."
    ::= { facilities 10 }


feEntry OBJECT-TYPE
    SYNTAX       FeEntry
    MAX-ACCESS   not-accessible
    STATUS       current
    DESCRIPTION  "The conceptual row object of the FE table."
    INDEX        { feShelfIdx,
                   feSlotIdx,
                   fePortIdx }
    ::= { feTable 1 }


FeEntry ::= SEQUENCE { feShelfIdx                    INTEGER,
                       feSlotIdx                     INTEGER,
                       fePortIdx                     INTEGER,
                       feId1                         DisplayString,
                       feCustom1                     DisplayString,
                       feSpeed                       Gauge32,
                       feDuplex                      DuplexModeType,
                       feMediaRate                   MediaRateType,
                       feMTU                         Integer32,
                       feMACAddr                     MacAddress,
                       feRemoteId                    DisplayString,
                       feRowStatus                   RowStatus }


feShelfIdx OBJECT-TYPE
    SYNTAX       INTEGER (1|11|21|31)
    MAX-ACCESS   accessible-for-notify
    STATUS       current
    DESCRIPTION  "The number of the shelf on which the FE facility is
                  provisioned."
    ::= { feEntry 1 }


feSlotIdx OBJECT-TYPE
    SYNTAX       INTEGER (1..20)
    MAX-ACCESS   accessible-for-notify
    STATUS       current
    DESCRIPTION  "The number of the slot within which the FE facility is
                  provisioned."
    ::= { feEntry 2 }


fePortIdx OBJECT-TYPE
    SYNTAX       INTEGER (5..6)
    MAX-ACCESS   accessible-for-notify
    STATUS       current
    DESCRIPTION  "The number of the port on the circuit pack on which the FE
                  facility is provisioned."
    ::= { feEntry 3 }


feId1 OBJECT-TYPE
    SYNTAX       DisplayString (SIZE (0..32))
    MAX-ACCESS   read-create
    STATUS       current
    DESCRIPTION  "Textual data recorded by the user to describe the provisioned
                  Fast Ethernet facility in a manner useful to the user."
    DEFVAL       { "" }
    ::= { feEntry 4 }


feCustom1 OBJECT-TYPE
    SYNTAX       DisplayString
    MAX-ACCESS   read-create
    STATUS       current
    DESCRIPTION  "A variable length text string for operating company use."
    DEFVAL       { "" }
    ::= { feEntry 5 }


feSpeed OBJECT-TYPE
    SYNTAX       Gauge32
    UNITS        "Mbps"
    MAX-ACCESS   read-only
    STATUS       current
    DESCRIPTION  "The speed of the Fast Ethernet facility link."
    ::= { feEntry 6 }


feDuplex OBJECT-TYPE
    SYNTAX       DuplexModeType
    MAX-ACCESS   read-only
    STATUS       current
    DESCRIPTION  "The duplex mode of the Fast Ethernet facility interface."
    ::= { feEntry 7 }


feMediaRate OBJECT-TYPE
    SYNTAX       MediaRateType
    MAX-ACCESS   read-only
    STATUS       current
    DESCRIPTION  "The configured media rate of the Fast Ethernet facility
                  interface."
    ::= { feEntry 8 }


feMTU OBJECT-TYPE
    SYNTAX       Integer32
    MAX-ACCESS   read-only
    STATUS       current
    DESCRIPTION  "The MTU size for the Fast Ethernet facility interface."
    ::= { feEntry 9 }


feMACAddr OBJECT-TYPE
    SYNTAX       MacAddress
    MAX-ACCESS   read-only
    STATUS       current
    DESCRIPTION  "The MAC address of the Fast Ethernet facility interface."
    ::= { feEntry 10 }


feRemoteId OBJECT-TYPE
    SYNTAX       DisplayString
    MAX-ACCESS   read-create
    STATUS       current
    DESCRIPTION  "Identifies the remote node and port to which the
                  fast ethernet port is connected, in the format
                  prescribed by the PSM network management system."
    DEFVAL       { "" }
    ::= { feEntry 11 }


feRowStatus OBJECT-TYPE
    SYNTAX       RowStatus
    MAX-ACCESS   read-create
    STATUS       current
    DESCRIPTION  "Used to control the addition and deletion of entries in the
                  Fast Ethernet table, which in turn controls provisioning and
                  deprovisioning of Fast Ethernet facilities."
    ::= { feEntry 100 }



-----------------------------------------------------------------------
-- Objects related to VCG entities on Muxponder Circuit Packs
-- 
-- A listing of Virtual Concatenation Group (VCG) entities is 
-- contained in the vcgTable of the BTI 7000 Series MIB. When retrieved, 
-- this table includes one row for each created VCG. VCG entities are 
-- created on muxponder circuit packs to facilitate cross connect 
-- management.
-- 
-- All VCGs are created and deleted automatically as a result of the 
-- creation and deletion of the supporting entity in the ocnTable or the
-- stmnTable. The following table lists the objects in each entry of the 
-- vcgTable.
-----------------------------------------------------------------------


vcgTable OBJECT-TYPE
    SYNTAX       SEQUENCE OF VcgEntry
    MAX-ACCESS   not-accessible
    STATUS       current
    DESCRIPTION  "This table contains one row for every provisioned Virtual
                  Concatenation Group (VCG) enitity on the system. Each row
                  contains a list of attributes that pertain to the VCG."
    ::= { facilities 11 }


vcgEntry OBJECT-TYPE
    SYNTAX       VcgEntry
    MAX-ACCESS   not-accessible
    STATUS       current
    DESCRIPTION  "The conceptual row object of the VCG table."
    INDEX        { vcgShelfIdx,
                   vcgSlotIdx,
                   vcgPortIdx,
                   vcgIdx }
    ::= { vcgTable 1 }


VcgEntry ::= SEQUENCE { vcgShelfIdx         INTEGER,
                        vcgSlotIdx          INTEGER,
                        vcgPortIdx          INTEGER,
                        vcgIdx              INTEGER,
                        vcgType           	INTEGER,
                        vcgTimeSlotIndices  DisplayString,
                        vcgRowStatus        RowStatus }


vcgShelfIdx OBJECT-TYPE
    SYNTAX       INTEGER (1|11|21|31)
    MAX-ACCESS   not-accessible
    STATUS       current
    DESCRIPTION  "The number of the shelf on which the VCG entity is located."
    ::= { vcgEntry 1 }


vcgSlotIdx OBJECT-TYPE
    SYNTAX       INTEGER (1..20)
    MAX-ACCESS   not-accessible
    STATUS       current
    DESCRIPTION  "The number of the slot within which the VCG entity is
                  located."
    ::= { vcgEntry 2 }


vcgPortIdx OBJECT-TYPE
    SYNTAX       INTEGER (1..2)
    MAX-ACCESS   not-accessible
    STATUS       current
    DESCRIPTION  "The number of the port on the circuit pack on which the VCG
                  entity is located."
    ::= { vcgEntry 3 }


vcgIdx OBJECT-TYPE
    SYNTAX       INTEGER (1..255)
    MAX-ACCESS   not-accessible
    STATUS       current
    DESCRIPTION  "The number of the VCG within the identified port."
    ::= { vcgEntry 4 }


vcgType OBJECT-TYPE
    SYNTAX       INTEGER { sts1c21v (1),
                           sts1c2v  (2),
                           sts3c7v  (3),
                           sts3c1v  (4),
                           vc47v    (5),
                           vc41v    (6),
                           sts1c3v  (7), 
                           sts1c19v (8),
                           sts1c22v (9),
                           sts1c37v (10),
                           sts1c74v (11),
                           sts3c6v  (12),
                           sts3c12v (13),
                           sts3c24v (14),
                           vc46v    (15),
                           vc412v   (16),
                           vc424v   (17),
                           vc42v    (18),
                           sts1c6v  (19),
                           sts3c2v  (20),
                           sts1c31v (21),
                           sts3c10v (22),
                           vc410v   (23) }
    MAX-ACCESS   read-create
    STATUS       current
    DESCRIPTION  "The format of the VCG."
    ::= { vcgEntry 5 }


vcgTimeSlotIndices OBJECT-TYPE
    SYNTAX       DisplayString (SIZE (1..511))
    MAX-ACCESS   read-create
    STATUS       current
    DESCRIPTION  "A textual listing of the time slot indices used for the VCG.
                  The information is formatted as a comma-separated list of of
                  individual time slot indices or time slot index ranges. For
                  example, a value of 'X-Y,Z' indicates that the VCG includes
                  all time slots in the range of X to Y, plus Z, when X, Y, and
                  Z are all integers."
    ::= { vcgEntry 6 }


vcgRowStatus OBJECT-TYPE
    SYNTAX       RowStatus
    MAX-ACCESS   read-create
    STATUS       current
    DESCRIPTION  "Used to control the addition and deletion of entries in the
                  VCG table, which in turn controls provisioning and
                  deprovisioning of Virtual Concatenation groups. Manual
                  creation and deletion of VCGs is supported only on the 10G
                  MXP, as all VCGs on the 2.5G MXP are auto-created and
                  deleted."
    ::= { vcgEntry 100 }



-----------------------------------------------------------------------
-- Objects related to provisioned fiber channel facilities on
-- Muxponder Circuit Packs
-- 
-- A listing of provisioned Fibre Channel facilities is contained in
-- the fcTable of the BTI 7000 Series MIB. When retrieved, this table
-- includes one row for each provisioned Fibre Channel port facility.
-- 
-- Note: The fcTable manages Fibre Channel facilities on muxponder
-- circuit packs, and is not used for wavelength conversion type
-- circuit packs. For management of these facilities, the xcvrTable
-- is used.
-- 
-- To manually provision a Fibre Channel facility, a row must be
-- created in the fcTable. To deprovision a Fibre Channel facility,
-- its row must be destroyed.
-- 
-- The following table lists the objects in each entry of the fcTable.
-----------------------------------------------------------------------


fcTable OBJECT-TYPE
    SYNTAX       SEQUENCE OF FcEntry
    MAX-ACCESS   not-accessible
    STATUS       current
    DESCRIPTION  "This table contains one row for every provisioned fiber
                  channel facility on the system. Each row contains a list of
                  attributes that pertain to the facility."
    ::= { facilities 12 }


fcEntry OBJECT-TYPE
    SYNTAX       FcEntry
    MAX-ACCESS   not-accessible
    STATUS       current
    DESCRIPTION  "The conceptual row object of the fiber channel table."
    INDEX        { fcShelfIdx,
                   fcSlotIdx,
                   fcPortIdx }
    ::= { fcTable 1 }


FcEntry ::= SEQUENCE { fcShelfIdx                    INTEGER,
                       fcSlotIdx                     INTEGER,
                       fcPortIdx                     INTEGER,
                       fcRate                        INTEGER,
                       fcOpticalPwrReceivedMinTh     FixedX10,
                       fcOpticalPwrReceivedMaxTh     FixedX10,
                       fcOpticalPwrTransmittedMinTh  FixedX10,
                       fcOpticalPwrTransmittedMaxTh  FixedX10,
                       fcOpticalPwrReceived          FixedX10,
                       fcOpticalPwrTransmitted       FixedX10,
                       fcPEC                         DisplayString,
                       fcAdminStatus                 AdminStatus,
                       fcOperStatus                  OperStatus,
                       fcOperStatQlfr                OperStatQlfr,
                       fcAutoEnableTimer             HoursAndMinutes,
                       fcActAutoEnableTimer          HoursAndMinutes,
                       fcWavelength                  FixedX100,
                       fcVendorPN1                   DisplayString,
                       fcVendorPN2                   DisplayString,
                       fcVendorPN3                   DisplayString,
                       fcPhyPMMon                    INTEGER,
                       fcFPSD                        INTEGER,
                       fcLaserStatus                 INTEGER,
                       fcId1                         DisplayString,
                       fcFiberType                   FiberType,
                       fcCustom1                     DisplayString,
                       fcGfpMode                     INTEGER,
                       fcRemoteId                    DisplayString,
                       fcRowStatus                   RowStatus }


fcShelfIdx OBJECT-TYPE
    SYNTAX       INTEGER (1|11|21|31)
    MAX-ACCESS   accessible-for-notify
    STATUS       current
    DESCRIPTION  "The number of the shelf on which the fiber channel facility is
                  provisioned."
    ::= { fcEntry 1 }


fcSlotIdx OBJECT-TYPE
    SYNTAX       INTEGER (1|3|5|7|9|11|13|15|17|19)
    MAX-ACCESS   accessible-for-notify
    STATUS       current
    DESCRIPTION  "The number of the slot within which the fiber channel facility
                  is provisioned."
    ::= { fcEntry 2 }


fcPortIdx OBJECT-TYPE
    SYNTAX       INTEGER (3..12)
    MAX-ACCESS   accessible-for-notify
    STATUS       current
    DESCRIPTION  "The number of the port on the circuit pack on which the fiber
                  channel facility is provisioned."
    ::= { fcEntry 3 }


fcRate OBJECT-TYPE
    SYNTAX       INTEGER { oneGbs  (1),
                           twoGbs  (2),
                           fourGbs (3) }
    MAX-ACCESS   read-create
    STATUS       current
    DESCRIPTION  "The rate of the fiber channel signal which is provisioned."
    ::= { fcEntry 4 }


fcOpticalPwrReceivedMinTh OBJECT-TYPE
    SYNTAX       FixedX10
    UNITS        "dBm/10"
    MAX-ACCESS   read-only
    STATUS       current
    DESCRIPTION  "This is the optical power received minimum threshold."
    ::= { fcEntry 5 }


fcOpticalPwrReceivedMaxTh OBJECT-TYPE
    SYNTAX       FixedX10
    UNITS        "dBm/10"
    MAX-ACCESS   read-only
    STATUS       current
    DESCRIPTION  "This is the optical power received maximum threshold."
    ::= { fcEntry 6 }


fcOpticalPwrTransmittedMinTh OBJECT-TYPE
    SYNTAX       FixedX10
    UNITS        "dBm/10"
    MAX-ACCESS   read-only
    STATUS       current
    DESCRIPTION  "This is the optical power transmitted minimum threshold."
    ::= { fcEntry 7 }


fcOpticalPwrTransmittedMaxTh OBJECT-TYPE
    SYNTAX       FixedX10
    UNITS        "dBm/10"
    MAX-ACCESS   read-only
    STATUS       current
    DESCRIPTION  "This is the optical power transmitted maximum threshold."
    ::= { fcEntry 8 }


fcOpticalPwrReceived OBJECT-TYPE
    SYNTAX       FixedX10
    UNITS        "dBm/10"
    MAX-ACCESS   accessible-for-notify
    STATUS       current
    DESCRIPTION  "The optical power received on the input of the transceiver."
    ::= { fcEntry 9 }


fcOpticalPwrTransmitted OBJECT-TYPE
    SYNTAX       FixedX10
    UNITS        "dBm/10"
    MAX-ACCESS   accessible-for-notify
    STATUS       current
    DESCRIPTION  "The optical power transmitted at the output of the
                  transceiver."
    ::= { fcEntry 10 }


fcPEC OBJECT-TYPE
    SYNTAX       DisplayString (SIZE (0..32))
    MAX-ACCESS   read-create
    STATUS       current
    DESCRIPTION  "An optionally provisioned Product Equipment Code used to
                  validate the physically present optical transceiver on the
                  fiber channel port."
    DEFVAL       { "" }
    ::= { fcEntry 11 }


fcAdminStatus OBJECT-TYPE
    SYNTAX       AdminStatus
    MAX-ACCESS   read-create
    STATUS       current
    DESCRIPTION  "The administrative status of the fiber channel facility."
    DEFVAL       { enabled }
    ::= { fcEntry 12 }


fcOperStatus OBJECT-TYPE
    SYNTAX       OperStatus
    MAX-ACCESS   read-only
    STATUS       current
    DESCRIPTION  "The reported operational status of the fiber channel
                  facility."
    ::= { fcEntry 13 }


fcOperStatQlfr OBJECT-TYPE
    SYNTAX       OperStatQlfr
    MAX-ACCESS   read-only
    STATUS       current
    DESCRIPTION  "This is a textual list of qualifiers about the reported
                  operational status of the fiber channel facility."
    ::= { fcEntry 14 }


fcAutoEnableTimer OBJECT-TYPE
    SYNTAX       HoursAndMinutes
    MAX-ACCESS   read-create
    STATUS       current
    DESCRIPTION  "Specifies the auto-enable timer for the targeted fiber channel
                  facility. This value only applies if the fcAdminStatus object
                  is set to autoEnabled. Otherwise, the value returned is
                  000-00."
    DEFVAL       { "008-00" }
    ::= { fcEntry 15 }


fcActAutoEnableTimer OBJECT-TYPE
    SYNTAX       HoursAndMinutes
    MAX-ACCESS   read-only
    STATUS       current
    DESCRIPTION  "Indicates the time remaining on the auto-enable timer if it is
                  actively counting down. Otherwise, the value returned is
                  000-00."
    ::= { fcEntry 16 }


fcWavelength OBJECT-TYPE
    SYNTAX       FixedX100
    MAX-ACCESS   read-create
    STATUS       current
    DESCRIPTION  "The wavelength to be transmitted by the transceiver on the
                  fiber channel facility port. This is a mandatory object when a
                  row of the fiber channel table is created."
    ::= { fcEntry 17 }


fcVendorPN1 OBJECT-TYPE
    SYNTAX       DisplayString (SIZE (0..20))
    MAX-ACCESS   read-create
    STATUS       current
    DESCRIPTION  "An optionally provisioned part number used to validate the
                  optical transceiver on the fiber channel facility port."
    DEFVAL       { "" }
    ::= { fcEntry 18 }


fcVendorPN2 OBJECT-TYPE
    SYNTAX       DisplayString (SIZE (0..20))
    MAX-ACCESS   read-create
    STATUS       current
    DESCRIPTION  "An optionally provisioned part number used to validate the
                  optical transceiver on the fiber channel facility port."
    DEFVAL       { "" }
    ::= { fcEntry 19 }


fcVendorPN3 OBJECT-TYPE
    SYNTAX       DisplayString (SIZE (0..20))
    MAX-ACCESS   read-create
    STATUS       current
    DESCRIPTION  "An optionally provisioned part number used to validate the
                  optical transceiver on the fiber channel facility port."
    DEFVAL       { "" }
    ::= { fcEntry 20 }


fcPhyPMMon OBJECT-TYPE
    SYNTAX       INTEGER { enabled  (1),
                           disabled (2) }
    MAX-ACCESS   read-create
    STATUS       current
    DESCRIPTION  "Indicates if the fiber channel facility is configured to
                  report threshold crossing conditions for physical layer
                  performance monitoring parameters."
    DEFVAL       { disabled }
    ::= { fcEntry 21 }


fcFPSD OBJECT-TYPE
    SYNTAX       INTEGER { enabled  (1),
                           disabled (2) }
    MAX-ACCESS   read-create
    STATUS       current
    DESCRIPTION  "Indicates if the Fiber Channel facility is configured for
                  Fault Propagation Shut Down."
    DEFVAL       { disabled }
    ::= { fcEntry 22 }


fcLaserStatus OBJECT-TYPE
    SYNTAX       INTEGER { on    (1),
                           off   (2) }
    MAX-ACCESS   read-only
    STATUS       current
    DESCRIPTION  "An indication of the operational status of the transceiver
                  laser on the fiber channel facility port."
    ::= { fcEntry 23 }


fcId1 OBJECT-TYPE
    SYNTAX       DisplayString (SIZE (0..32))
    MAX-ACCESS   read-create
    STATUS       current
    DESCRIPTION  "Textual data recorded by the user to describe the provisioned
                  fiber channel facility in a manner useful to the user."
    DEFVAL       { "" }
    ::= { fcEntry 24 }


fcFiberType OBJECT-TYPE
    SYNTAX       FiberType
    MAX-ACCESS   read-create
    STATUS       current
    DESCRIPTION  "An optional specification of the fiber type that interfaces to
                  the fiber channel facility port."
    DEFVAL       { none }
    ::= { fcEntry 25 }


fcCustom1 OBJECT-TYPE
    SYNTAX       DisplayString
    MAX-ACCESS   read-create
    STATUS       current
    DESCRIPTION  "A variable length text string for operating company use."
    DEFVAL       { "" }
    ::= { fcEntry 26 }


fcGfpMode OBJECT-TYPE
    SYNTAX       INTEGER { unmapped (1),
                           gfpt     (2) } -- GFP - Transparent
    MAX-ACCESS   read-create
    STATUS       current
    DESCRIPTION  "Configures the mapping of fiber channel facility port onto the
                  line port using GFP. Only the transparent mapping is supported
                  for fiber channel facilities."
    DEFVAL       { gfpt }
    ::= { fcEntry 27 }


fcRemoteId OBJECT-TYPE
    SYNTAX       DisplayString
    MAX-ACCESS   read-create
    STATUS       current
    DESCRIPTION  "Identifies the remote node and port to which the
                  fiber channel port is connected, in the format
                  prescribed by the PSM network management system."
    DEFVAL       { "" }
    ::= { fcEntry 28 }


fcRowStatus OBJECT-TYPE
    SYNTAX       RowStatus
    MAX-ACCESS   read-create
    STATUS       current
    DESCRIPTION  "Used to control the addition and deletion of entries in the
                  fiber channel table, which in turn controls provisioning and
                  deprovisioning of fiber channel facilities."
    ::= { fcEntry 100 }


-----------------------------------------------------------------------
-- Objects related to Optical Service Channel entities
-- on the system
-- 
-- A listing of provisioned optical supervisory channel (OSC)
-- facilities is contained in the oscTable of the BTI 7000 Series MIB. 
-- When retrieved, this table provides one row for each provisioned OSC
-- interface. There is up to two entries in this table.
-- 
-- The following table lists the objects in each entry of the oscTable.
-----------------------------------------------------------------------


oscTable OBJECT-TYPE
    SYNTAX       SEQUENCE OF OscEntry
    MAX-ACCESS   not-accessible
    STATUS       current
    DESCRIPTION  "This table contains one row for every provisioned optical
                  supervisory channel interface on the NE. Each row contains a
                  list of attributes that pertain to the OSC."
    ::= { dataComms 1 }


oscEntry OBJECT-TYPE
    SYNTAX       OscEntry
    MAX-ACCESS   not-accessible
    STATUS       current
    DESCRIPTION  "The conceptual row object of the optical supervisory channel
                  table."
    INDEX        { oscShelfIdx,
                   oscSlotIdx,
                   oscIdx }
    ::= { oscTable 1 }


OscEntry ::= SEQUENCE { oscShelfIdx      INTEGER,
                        oscSlotIdx       INTEGER,
                        oscIdx           INTEGER,
                        oscAdminStatus   AdminStatus,
                        oscOperStatus    OperStatus,
                        oscOperStatQlfr  OperStatQlfr,
                        oscCustom1       DisplayString,
                        oscType          INTEGER,
                        oscUnmbrd        TruthValue,
                        oscSpeed         Gauge32,
                        oscDuplex        DuplexModeType,
                        oscMediaRate     MediaRateType,
                        oscMTU           Integer32,
                        oscMACAddr       MacAddress,
                        oscIPAddr        IpAddress,
                        oscIPMask        IpAddress,
                        oscIPBcast       IpAddress,
                        oscRowStatus     RowStatus }


oscShelfIdx OBJECT-TYPE
    SYNTAX       INTEGER (1|11|21|31)
    MAX-ACCESS   accessible-for-notify
    STATUS       current
    DESCRIPTION  "The number of the shelf on which the OSC is provisioned."
    ::= { oscEntry 1 }


oscSlotIdx OBJECT-TYPE
    SYNTAX       INTEGER (1..20)
    MAX-ACCESS   accessible-for-notify
    STATUS       current
    DESCRIPTION  "The number of the slot in which the OSC is provisioned."
    ::= { oscEntry 2 }


oscIdx OBJECT-TYPE
    SYNTAX       INTEGER (1..2)
    MAX-ACCESS   accessible-for-notify
    STATUS       current
    DESCRIPTION  "The number of the port on the circuit pack on which the OSC is
                  provisioned."
    ::= { oscEntry 3 }


oscAdminStatus OBJECT-TYPE
    SYNTAX       AdminStatus
    MAX-ACCESS   read-create
    STATUS       current
    DESCRIPTION  "The administrative status of the OSC interface."
    DEFVAL       { enabled }
    ::= { oscEntry 4 }


oscOperStatus OBJECT-TYPE
    SYNTAX       OperStatus
    MAX-ACCESS   read-only
    STATUS       current
    DESCRIPTION  "The reported operational status of the OSC interface."
    ::= { oscEntry 5 }


oscOperStatQlfr OBJECT-TYPE
    SYNTAX       OperStatQlfr
    MAX-ACCESS   read-only
    STATUS       current
    DESCRIPTION  "A textual list of qualifiers for the reported operational
                  status of the OSC interface."
    ::= { oscEntry 6 }


oscCustom1 OBJECT-TYPE
    SYNTAX       DisplayString
    MAX-ACCESS   read-create
    STATUS       current
    DESCRIPTION  "A variable length text string for operating company use."
    DEFVAL       { "" }
    ::= { oscEntry 7 }


oscType OBJECT-TYPE
    SYNTAX       INTEGER { optical    (1),
                           electrical (2),
                           logical    (3) }
    MAX-ACCESS   read-only
    STATUS       current
    DESCRIPTION  "The type of physical communication medium attached to the OSC
                  interface."
    ::= { oscEntry 8 }


oscUnmbrd OBJECT-TYPE
    SYNTAX       TruthValue
    MAX-ACCESS   read-only
    STATUS       current
    DESCRIPTION  "Indicates whether or not the OSC interface is the type that
                  requires an IP address to be assigned."
    ::= { oscEntry 9 }


oscSpeed OBJECT-TYPE
    SYNTAX       Gauge32
    UNITS        "Mbps"
    MAX-ACCESS   read-only
    STATUS       current
    DESCRIPTION  "The speed of the OSC link."
    ::= { oscEntry 10 }


oscDuplex OBJECT-TYPE
    SYNTAX       DuplexModeType
    MAX-ACCESS   read-only
    STATUS       current
    DESCRIPTION  "The duplex mode of the OSC interface."
    ::= { oscEntry 11 }


oscMediaRate OBJECT-TYPE
    SYNTAX       MediaRateType
    MAX-ACCESS   read-only
    STATUS       current
    DESCRIPTION  "The configured media rate of the OSC interface."
    ::= { oscEntry 12 }


oscMTU OBJECT-TYPE
    SYNTAX       Integer32
    MAX-ACCESS   read-only
    STATUS       current
    DESCRIPTION  "The MTU size for the OSC interface."
    ::= { oscEntry 13 }


oscMACAddr OBJECT-TYPE
    SYNTAX       MacAddress
    MAX-ACCESS   read-only
    STATUS       current
    DESCRIPTION  "The MAC address of the OSC interface."
    ::= { oscEntry 14 }


oscIPAddr OBJECT-TYPE
    SYNTAX       IpAddress
    MAX-ACCESS   read-create
    STATUS       current
    DESCRIPTION  "The IP Address of the OSC interface. A value of 0.0.0.0
                  indicates that the interface is not assigned an IP address."
    ::= { oscEntry 15 }


oscIPMask OBJECT-TYPE
    SYNTAX       IpAddress
    MAX-ACCESS   read-create
    STATUS       current
    DESCRIPTION  "The IP Subnet Mask of the OSC interface."
    ::= { oscEntry 16 }


oscIPBcast OBJECT-TYPE
    SYNTAX       IpAddress
    MAX-ACCESS   read-only
    STATUS       current
    DESCRIPTION  "The IP broadcast address of the OSC interface."
    ::= { oscEntry 17 }


oscRowStatus OBJECT-TYPE
    SYNTAX       RowStatus
    MAX-ACCESS   read-create
    STATUS       current
    DESCRIPTION  "Used to control the addition and deletion of entries in the
                  OSC table, which in turn controls provisioning and
                  deprovisioning of OSC interfaces."
    ::= { oscEntry 100 }



-----------------------------------------------------------------------
-- Objects related to the Network Management Interfaces
-- on the system
-- 
-- A listing of the network management interface entities on the
-- BTI 7000 Series is contained in the netMgmtTable of the BTI-7000-MIB.
-- When retrieved, this table provides one row for each network
-- management interface. There are two entries in this table:
-- 
-- � one for the network management system (NMS) interface
-- � one for the craft interface
-- 
-- The following table lists the objects in each entry of the
-- netMgmtTable.
-----------------------------------------------------------------------


netMgmtTable OBJECT-TYPE
    SYNTAX       SEQUENCE OF NetMgmtEntry
    MAX-ACCESS   not-accessible
    STATUS       current
    DESCRIPTION  "This table contains one row for every network management
                  interface on the NE. Each row contains a list of attributes
                  that pertain to the interface."
    ::= { dataComms 2 }


netMgmtEntry OBJECT-TYPE
    SYNTAX       NetMgmtEntry
    MAX-ACCESS   not-accessible
    STATUS       current
    DESCRIPTION  "The conceptual row object of the network management interface
                  table."
    INDEX        { netMgmtIdx }
    ::= { netMgmtTable 1 }


NetMgmtEntry ::= SEQUENCE { netMgmtIdx           INTEGER,
                            netMgmtAdminStatus   AdminStatus,
                            netMgmtOperStatus    OperStatus,
                            netMgmtOperStatQlfr  OperStatQlfr,
                            netMgmtIPAddr        IpAddress,
                            netMgmtIPMask        IpAddress,
                            netMgmtIPBcast       IpAddress,
                            netMgmtCustom1       DisplayString,
                            netMgmtType          INTEGER,
                            netMgmtUnmbrd        TruthValue,
                            netMgmtSpeed         Gauge32,
                            netMgmtDuplex        DuplexModeType,
                            netMgmtMediaRate     MediaRateType,
                            netMgmtMTU           Integer32,
                            netMgmtMACAddr       MacAddress }


netMgmtIdx OBJECT-TYPE
    SYNTAX       INTEGER { nms   (1),
                           craft (2) }
    MAX-ACCESS   not-accessible
    STATUS       current
    DESCRIPTION  "Identifies the specific management interface."
    ::= { netMgmtEntry 1 }


netMgmtAdminStatus OBJECT-TYPE
    SYNTAX       AdminStatus
    MAX-ACCESS   read-write
    STATUS       current
    DESCRIPTION  "The administrative status of the management interface."
    DEFVAL       { enabled }
    ::= { netMgmtEntry 2 }


netMgmtOperStatus OBJECT-TYPE
    SYNTAX       OperStatus
    MAX-ACCESS   read-only
    STATUS       current
    DESCRIPTION  "The reported operational status of the management interface."
    ::= { netMgmtEntry 3 }


netMgmtOperStatQlfr OBJECT-TYPE
    SYNTAX       OperStatQlfr
    MAX-ACCESS   read-only
    STATUS       current
    DESCRIPTION  "A textual list of qualifiers for the reported operational
                  status of the management interface."
    ::= { netMgmtEntry 4 }


netMgmtIPAddr OBJECT-TYPE
    SYNTAX       IpAddress
    MAX-ACCESS   read-write
    STATUS       current
    DESCRIPTION  "The IP Address of the management interface."
    ::= { netMgmtEntry 5 }


netMgmtIPMask OBJECT-TYPE
    SYNTAX       IpAddress
    MAX-ACCESS   read-write
    STATUS       current
    DESCRIPTION  "The IP Subnet Mask of the management interface."
    ::= { netMgmtEntry 6 }


netMgmtIPBcast OBJECT-TYPE
    SYNTAX       IpAddress
    MAX-ACCESS   read-only
    STATUS       current
    DESCRIPTION  "The IP broadcast address of the management interface."
    ::= { netMgmtEntry 7 }


netMgmtCustom1 OBJECT-TYPE
    SYNTAX       DisplayString
    MAX-ACCESS   read-write
    STATUS       current
    DESCRIPTION  "A variable length text string for operating company use."
    DEFVAL       { "" }
    ::= { netMgmtEntry 8 }


netMgmtType OBJECT-TYPE
    SYNTAX       INTEGER { optical    (1),
                           electrical (2),
                           logical    (3) }
    MAX-ACCESS   read-only
    STATUS       current
    DESCRIPTION  "The type of physical communication medium attached to the
                  management interface."
    ::= { netMgmtEntry 9 }


netMgmtUnmbrd OBJECT-TYPE
    SYNTAX       TruthValue
    MAX-ACCESS   read-only
    STATUS       current
    DESCRIPTION  "Indicates whether or not the management interface is the type
                  that requires an IP address to be assigned."
    ::= { netMgmtEntry 10 }


netMgmtSpeed OBJECT-TYPE
    SYNTAX       Gauge32
    UNITS        "Mbps"
    MAX-ACCESS   read-only
    STATUS       current
    DESCRIPTION  "The speed of the management interface link."
    ::= { netMgmtEntry 11 }


netMgmtDuplex OBJECT-TYPE
    SYNTAX       DuplexModeType
    MAX-ACCESS   read-only
    STATUS       current
    DESCRIPTION  "The duplex mode of the management interface."
    ::= { netMgmtEntry 12 }


netMgmtMediaRate OBJECT-TYPE
    SYNTAX       MediaRateType
    MAX-ACCESS   read-only
    STATUS       current
    DESCRIPTION  "The configured media rate of the management interface."
    ::= { netMgmtEntry 13 }


netMgmtMTU OBJECT-TYPE
    SYNTAX       Integer32
    MAX-ACCESS   read-only
    STATUS       current
    DESCRIPTION  "The MTU size for this management interface."
    ::= { netMgmtEntry 14 }


netMgmtMACAddr OBJECT-TYPE
    SYNTAX       MacAddress
    MAX-ACCESS   read-only
    STATUS       current
    DESCRIPTION  "The MAC address of the management interface."
    ::= { netMgmtEntry 15 }


-----------------------------------------------------------------------
-- Objects related to serial communications ports
-- 
-- The serialTable contains a listing of serial communications ports 
-- on the BTI 7000 Series that can be used for a management interface
-- to the system. Currently, a single entry is supported in the table
-- for the serial port on the 
-- shelf controller circuit pack faceplate.
-- 
-- The following table lists the objects in each entry of the
-- serialTable.
-----------------------------------------------------------------------


serialTable OBJECT-TYPE
    SYNTAX       SEQUENCE OF SerialEntry
    MAX-ACCESS   not-accessible
    STATUS       current
    DESCRIPTION  "A table of serial communication ports on the network element.
                  Each row contains a list of attributes that pertain to a given
                  serial port."
    ::= { dataComms 3 }


serialEntry OBJECT-TYPE
    SYNTAX       SerialEntry
    MAX-ACCESS   not-accessible
    STATUS       current
    DESCRIPTION  "The conceptual row object for the serial port table."
    INDEX        { serialPortIdx }
    ::= { serialTable 1 }


SerialEntry ::= SEQUENCE { serialPortIdx    INTEGER,
                           serialBaudRate   Unsigned32,
                           serialDataBits   INTEGER,
                           serialParity     INTEGER,
                           serialStopBits   INTEGER }

serialPortIdx OBJECT-TYPE
    SYNTAX       INTEGER (1..1)
    MAX-ACCESS   not-accessible
    STATUS       current
    DESCRIPTION  "The serial port instance on the NE."
    ::= { serialEntry 1 }


serialBaudRate OBJECT-TYPE
    SYNTAX       Unsigned32
    MAX-ACCESS   read-write
    STATUS       current
    DESCRIPTION  "The baud rate of the serial port."
    ::= { serialEntry 2 }


serialDataBits OBJECT-TYPE
    SYNTAX       INTEGER (1..255)
    MAX-ACCESS   read-write
    STATUS       current
    DESCRIPTION  "The number of data bits of the serial port."
    ::= { serialEntry 3 }


serialParity OBJECT-TYPE
    SYNTAX       INTEGER { none (1),
                           odd  (2),
                           even (3) }
    MAX-ACCESS   read-write
    STATUS       current
    DESCRIPTION  "The parity value of the serial port."
    ::= { serialEntry 4 }


serialStopBits OBJECT-TYPE
    SYNTAX       INTEGER { one         (1),
                           two         (2) }
    MAX-ACCESS   read-write
    STATUS       current
    DESCRIPTION  "The number of stop bits of the serial port."
    ::= { serialEntry 5 }

-----------------------------------------------------------------------
-- Objects related to provisioned Ethernet facilities 
------------------------------------------------------------------------
ethIntfTable OBJECT-TYPE
    SYNTAX       SEQUENCE OF EthIntfEntry
    MAX-ACCESS   not-accessible
    STATUS       current
    DESCRIPTION  "This table contains one row for every provisioned Ethernet
                  facility on the system. Each row contains a list of attributes
                  that pertain to the facility."
    ::= { facilities 14 }

ethIntfEntry OBJECT-TYPE
    SYNTAX       EthIntfEntry
    MAX-ACCESS   not-accessible
    STATUS       current
    DESCRIPTION  "The conceptual row object of the ethIntfTable table."
    INDEX        { ethIntfShelfIdx,
                   ethIntfSlotIdx,
                   ethIntfPortTypeIdx,
                   ethIntfPortIdx }
    ::= { ethIntfTable 1 }

EthIntfEntry ::= SEQUENCE { ethIntfShelfIdx                    INTEGER,
                            ethIntfSlotIdx                     INTEGER,
                            ethIntfPortTypeIdx                 PvxL1PortType,
                            ethIntfPortIdx                     INTEGER,
                            ethIntfOpticalPwrReceivedMinTh     FixedX10,
                            ethIntfOpticalPwrReceivedMaxTh     FixedX10,
                            ethIntfOpticalPwrTransmittedMinTh  FixedX10,
                            ethIntfOpticalPwrTransmittedMaxTh  FixedX10,
                            ethIntfOpticalPwrReceived          FixedX10,
                            ethIntfOpticalPwrTransmitted       FixedX10,
                            ethIntfPEC                         DisplayString,
                            ethIntfAdminStatus                 AdminStatus,
                            ethIntfOperStatus                  OperStatus,
                            ethIntfOperStatQlfr                OperStatQlfr,
                            ethIntfAutoEnableTimer             HoursAndMinutes,
                            ethIntfActAutoEnableTimer          HoursAndMinutes,
                            ethIntfWavelength                  FixedX100,
                            ethIntfVendorPN1                   DisplayString,
                            ethIntfVendorPN2                   DisplayString,
                            ethIntfVendorPN3                   DisplayString,
                            ethIntfPhyPMMon                    INTEGER,
                            ethIntfFPSD                        INTEGER,
                            ethIntfLaserStatus                 INTEGER,
                            ethIntfId1                         DisplayString,
                            ethIntfFiberType                   FiberType,
                            ethIntfCustom1                     DisplayString,
                            ethIntfSpeed                       Gauge32,
                            ethIntfDuplex                      INTEGER,
                            ethIntfMediaRate                   MediaRateType,
                            ethIntfMTU                         INTEGER,
                            ethIntfLinkStatus                  INTEGER,
                            ethIntfLagId                       INTEGER,
                            ethIntfLagPortPriority             Integer32,
                            ethIntfBER                         BERType, 
                            ethIntfMACAddr                     MacAddress,
                            ethIntfLineMapping                 INTEGER,
                            ethIntfErrorCorrection             INTEGER,
                            ethIntfLpbkOpCmd                   INTEGER,
                            ethIntfRemoteId                    DisplayString,
                            ethIntfMirrorConfig                MirrorConfigType,
                            ethIntfLldpAdminStatus             INTEGER,
                            ethIntfLldpRemChassisIdSubtype     LldpChassisIdSubtype,
                            ethIntfLldpRemChassisId            LldpChassisId,
                            ethIntfLldpRemPortIdSubtype        LldpPortIdSubtype,
                            ethIntfLldpRemPortId               LldpPortId,
                            ethIntfBouncingStateChangeCount    Integer32,
                            ethIntfRowStatus                   RowStatus }

ethIntfShelfIdx OBJECT-TYPE
    SYNTAX    INTEGER (1 | 11 | 21 | 31)
    MAX-ACCESS   accessible-for-notify
    STATUS       current
    DESCRIPTION  "The number of the shelf in which the Ethernet facility 
                  resides."
    ::= { ethIntfEntry 1 }

ethIntfSlotIdx OBJECT-TYPE
    SYNTAX    INTEGER (1..20)
    MAX-ACCESS   accessible-for-notify
    STATUS       current
    DESCRIPTION  "The number of the slot in which the Ethernet facility 
                  resides."
    ::= { ethIntfEntry 2 }
    
ethIntfPortTypeIdx OBJECT-TYPE
    SYNTAX      PvxL1PortType 
    MAX-ACCESS   accessible-for-notify
    STATUS       current
    DESCRIPTION  "The type of the port on the circuit pack."
    ::= {ethIntfEntry 3 }

ethIntfPortIdx OBJECT-TYPE
    SYNTAX       INTEGER (1..24)
    MAX-ACCESS   accessible-for-notify
    STATUS       current
    DESCRIPTION  "The number of the port on the circuit pack on which the
                  ethernet facility is provisioned."
    ::= { ethIntfEntry 4 }

ethIntfOpticalPwrReceivedMinTh OBJECT-TYPE
    SYNTAX       FixedX10
    UNITS        "dBm/10"
    MAX-ACCESS    read-only 
    STATUS       current
    DESCRIPTION  "This is the optical power received minimum threshold."
    ::= { ethIntfEntry 5 }

ethIntfOpticalPwrReceivedMaxTh OBJECT-TYPE
    SYNTAX       FixedX10
    UNITS        "dBm/10"
    MAX-ACCESS   read-only
    STATUS       current
    DESCRIPTION  "This is the optical power received maximum threshold."
    ::= { ethIntfEntry 6 }

ethIntfOpticalPwrTransmittedMinTh OBJECT-TYPE
    SYNTAX       FixedX10
    UNITS        "dBm/10"
    MAX-ACCESS   read-only
    STATUS       current
    DESCRIPTION  "This is the optical power transmitted minimum threshold."
    ::= { ethIntfEntry 7 }

ethIntfOpticalPwrTransmittedMaxTh OBJECT-TYPE
    SYNTAX       FixedX10
    UNITS        "dBm/10"
    MAX-ACCESS   read-only
    STATUS       current
    DESCRIPTION  "This is the optical power transmitted maximum threshold."
    ::= { ethIntfEntry 8 }

ethIntfOpticalPwrReceived OBJECT-TYPE
    SYNTAX       FixedX10
    UNITS        "dBm/10"
    MAX-ACCESS   accessible-for-notify
    STATUS       current
    DESCRIPTION  "The optical power received on the input of the transceiver."
    ::= { ethIntfEntry 9 }

ethIntfOpticalPwrTransmitted OBJECT-TYPE
    SYNTAX       FixedX10
    UNITS        "dBm/10"
    MAX-ACCESS   accessible-for-notify
    STATUS       current
    DESCRIPTION  "The optical power transmitted at the output of the
                  transceiver."
    ::= { ethIntfEntry 10 }

ethIntfPEC OBJECT-TYPE
    SYNTAX       DisplayString (SIZE (0..32))
    MAX-ACCESS   read-create
    STATUS       current
    DESCRIPTION  "An optionally provisioned transceiver Product Equipment Code
                  used to validate the physically present transceiver on the
                  Ethernet port."
    DEFVAL       { "" }
    ::= { ethIntfEntry 11 }
    
ethIntfAdminStatus OBJECT-TYPE
    SYNTAX       INTEGER { enabled  (1),
                           disabled (2) }
    MAX-ACCESS   read-create
    STATUS       current
    DESCRIPTION  "The administrative status of the Ethernet facility."
    DEFVAL       { enabled }
    ::= { ethIntfEntry 12 }

ethIntfOperStatus OBJECT-TYPE
    SYNTAX       OperStatus
    MAX-ACCESS   read-only
    STATUS       current
    DESCRIPTION  "The reported operational status of the Ethernet facility."
    ::= { ethIntfEntry 13 }

ethIntfOperStatQlfr OBJECT-TYPE
    SYNTAX       OperStatQlfr
    MAX-ACCESS   read-only
    STATUS       current
    DESCRIPTION  "This is a textual list of qualifiers about the reported
                  operational status of the Ethernet facility."
    ::= { ethIntfEntry 14 }

ethIntfAutoEnableTimer OBJECT-TYPE
    SYNTAX       HoursAndMinutes
    MAX-ACCESS   read-create
    STATUS       current
    DESCRIPTION  "Specifies the auto-enable timer for the targeted Ethernet
                  facility. This value only applies if the AdminStatus object is
                  set to autoEnabled. Otherwise, the value returned is 000-00."
    DEFVAL       { "008-00" }
    ::= { ethIntfEntry 15 }

ethIntfActAutoEnableTimer OBJECT-TYPE
    SYNTAX       HoursAndMinutes
    MAX-ACCESS   read-only
    STATUS       current
    DESCRIPTION  "Indicates the time remaining on the auto-enable timer if it is
                  actively counting down. Otherwise, the value returned is
                  000-00."
    ::= { ethIntfEntry 16 }

ethIntfWavelength OBJECT-TYPE
    SYNTAX       FixedX100
    MAX-ACCESS   read-create
    STATUS       current
    DESCRIPTION  "The wavelength to be transmitted by the transceiver on the
                  Gigabit Ethernet facility port. This is a mandatory object
                  when a row of the Ethernet table is created."
    ::= { ethIntfEntry 17 }

ethIntfVendorPN1 OBJECT-TYPE
    SYNTAX       DisplayString (SIZE (0..20))
    MAX-ACCESS   read-create
    STATUS       current
    DESCRIPTION  "An optionally provisioned part number used to validate the
                  optical transceiver on the Ethernet facility port."
    DEFVAL       { "" }
    ::= { ethIntfEntry 18 }

ethIntfVendorPN2 OBJECT-TYPE
    SYNTAX       DisplayString (SIZE (0..20))
    MAX-ACCESS   read-create
    STATUS       current
    DESCRIPTION  "An optionally provisioned part number used to validate the
                  optical transceiver on the Ethernet facility port."
    DEFVAL       { "" }
    ::= { ethIntfEntry 19 }

ethIntfVendorPN3 OBJECT-TYPE
    SYNTAX       DisplayString (SIZE (0..20))
    MAX-ACCESS   read-create
    STATUS       current
    DESCRIPTION  "An optionally provisioned part number used to validate the
                  optical transceiver on the Ethernet facility port."
    DEFVAL       { "" }
    ::= { ethIntfEntry 20 }

ethIntfPhyPMMon OBJECT-TYPE
    SYNTAX       INTEGER { enabled  (1),
                           disabled (2) }
    MAX-ACCESS   read-create
    STATUS       current
    DESCRIPTION  "Indicates if the Ethernet facility is configured to report
                  threshold crossing conditions for physical layer performance
                  monitoring parameters."
    DEFVAL       { disabled }
    ::= { ethIntfEntry 21 }

ethIntfFPSD OBJECT-TYPE
    SYNTAX       INTEGER { enabled  (1),
                           disabled (2) }
    MAX-ACCESS   read-create
    STATUS       current
    DESCRIPTION  "Indicates if the Ethernet facility is configured for Fault
                  Propagation Shut Down."
    DEFVAL       { disabled }
    ::= { ethIntfEntry 22 }

ethIntfLaserStatus OBJECT-TYPE
    SYNTAX       INTEGER { on      (1),
                           off     (2) }
    MAX-ACCESS   read-only
    STATUS       current
    DESCRIPTION  "An indication of the operational status of the transceiver
                  laser on the Ethernet facility port."
    ::= { ethIntfEntry 23 }

ethIntfId1 OBJECT-TYPE
    SYNTAX       DisplayString (SIZE (0..32))
    MAX-ACCESS   read-create
    STATUS       current
    DESCRIPTION  "Textual data recorded by the user to describe the provisioned
                  facility in a manner useful to the user."
    DEFVAL       { "" }
    ::= { ethIntfEntry 24 }

ethIntfFiberType OBJECT-TYPE
    SYNTAX       FiberType
    MAX-ACCESS   read-create
    STATUS       current
    DESCRIPTION  "An optional specification of the fiber type that interfaces to
                  the Ethernet facility port."
    DEFVAL       { none }
    ::= { ethIntfEntry 25 }

ethIntfCustom1 OBJECT-TYPE
    SYNTAX       DisplayString
    MAX-ACCESS   read-create
    STATUS       current
    DESCRIPTION  "A variable length text string for operating company use."
    DEFVAL       { "" }
    ::= { ethIntfEntry 26 }

ethIntfSpeed OBJECT-TYPE
    SYNTAX       Gauge32
    UNITS        "Mbps"
    MAX-ACCESS   read-only
    STATUS       current
    DESCRIPTION  "The speed of the Ethernet facility link. This object is
                  mandatory to create a new facility and determines the type of
                  interface, based on speed."
    ::= { ethIntfEntry 27 }

ethIntfDuplex OBJECT-TYPE
    SYNTAX       INTEGER { half (1),
                           full (2),
                           both (3) }
    MAX-ACCESS   read-only
    STATUS       current
    DESCRIPTION  "The duplex mode of the Ethernet facility interface."
    ::= { ethIntfEntry 28 }

ethIntfMediaRate OBJECT-TYPE
    SYNTAX       MediaRateType
    MAX-ACCESS   read-create
    STATUS       current
    DESCRIPTION  "The configured media rate of the Ethernet facility interface.
                  For 10 GE interfaces, the media rate can only be autoNegotiated."
    DEFVAL       { autoNegotiated  }
    ::= { ethIntfEntry 29 }

ethIntfMTU OBJECT-TYPE
    SYNTAX       INTEGER (1518..9600)
    MAX-ACCESS   read-create
    STATUS       current
    DESCRIPTION  "The MTU size for the Ethernet facility interface."
    DEFVAL       { 1518  }
    ::= { ethIntfEntry 30 }

ethIntfLinkStatus OBJECT-TYPE
    SYNTAX       INTEGER { up   (1),
                           down (2) }
    MAX-ACCESS   read-only
    STATUS       current
    DESCRIPTION  "This object provides the link status information regarding the
                  particular interface."
    ::= { ethIntfEntry 31 }

ethIntfLagId OBJECT-TYPE
    SYNTAX       INTEGER (1..10)
    MAX-ACCESS   read-only
    STATUS       current
    DESCRIPTION  "This object provides the information regarding the LAG Id of
                  the particular interface."
    ::= { ethIntfEntry 32 }  
    
ethIntfLagPortPriority OBJECT-TYPE
    SYNTAX       Integer32
    MAX-ACCESS   read-create
    STATUS       current
    DESCRIPTION  "This object provides the information for lag port priority of
                  the particular interface."
    ::= { ethIntfEntry 33 }      

-- ethIntfEntry 34 DELETED!

ethIntfBER OBJECT-TYPE 
    SYNTAX       BERType
    MAX-ACCESS   read-create
    STATUS       current
    DESCRIPTION  "The Signal Degrade Bit Error Ratio (SDBER) is used to
                  configure the error rate threshold above which a Signal
                  Degrade is declared."
    DEFVAL { tenExpMinus5 }
    ::= { ethIntfEntry 37 }
    

-- ethIntfEntry 38 DELETED!
    
ethIntfMACAddr OBJECT-TYPE
    SYNTAX       MacAddress
    MAX-ACCESS   read-only
    STATUS       current
    DESCRIPTION  "The MAC address of the interface."
    ::= { ethIntfEntry 39 }

ethIntfLineMapping OBJECT-TYPE 
    SYNTAX       INTEGER { tenglanphy    (1),
                           otu2gfp1      (2),
                           notApplicable (3),
                           stacking      (4)
                         }
    MAX-ACCESS   read-create
    STATUS       current
    DESCRIPTION  "For 10 GE interfaces, both 10 GE LAN PHY and OTU2 encapsulated
                  10GE LAN PHY will be supported. The line mapping attribute
                  allow provisioning of either of the protocol. This attributes 
                  applies to 10 GE interfaces only. When a 10 GE interface is configured
                  as a stacking port, this field is set to stacking.

                  NOTE:  This parameter does not apply to gigabitEthernet type
                  interfaces, attempts to set this for gigE port types will fail.

                  Reading this object for non-10GigE interfaces will return 
                  notApplicable."
    DEFVAL       { tenglanphy }
    ::= { ethIntfEntry 40 }

ethIntfErrorCorrection OBJECT-TYPE 
    SYNTAX       INTEGER { none  (1),
                           fec   (2),
                           efec  (3)
                         }
    MAX-ACCESS   read-create
    STATUS       current
    DESCRIPTION  "For 10G in OTU2 line-mapping mode, this object specifies 
                  the error correction mode. For interfaces in tenlanphy
                  line-mapping mode, this object must be none. Attempts to
                  set it to any other value while in tenglanphy mode will fail.

                  NOTE:  This parameter does not apply to gigabitEthernet type
                  interfaces, attempts to set this for gigE port types will fail."
    DEFVAL       { none }
    ::= { ethIntfEntry 41 }

ethIntfLpbkOpCmd OBJECT-TYPE
    SYNTAX       INTEGER { noOp    (1),
                           oprLpbk (2),
                           rlsLpbk (3) }
    MAX-ACCESS   read-write
    STATUS       current
    DESCRIPTION  "Used to perform a loopback operation on a transceiver facility
                  as follows:
                  - oprLpbk: operates a loopback on the transceiver
                  - rlsLpbk: causes a previously invoked loopback to be released
                  
                  When read, this object returns noOp."
    ::= { ethIntfEntry 42 }

ethIntfRemoteId OBJECT-TYPE
    SYNTAX       DisplayString
    MAX-ACCESS   read-create
    STATUS       current
    DESCRIPTION  "Identifies the remote node and port to which the
                  PVX ethernet port is connected, in the format
                  prescribed by the PSM network management system."
    DEFVAL       { "" }
    ::= { ethIntfEntry 43 }

ethIntfMirrorConfig OBJECT-TYPE
    SYNTAX       MirrorConfigType
    MAX-ACCESS   read-write
    STATUS       current
    DESCRIPTION  "Mirror configuration for the physical ethernet port"
    DEFVAL       { none }
    ::= { ethIntfEntry 44 }

ethIntfLldpAdminStatus  OBJECT-TYPE 
    SYNTAX INTEGER { 
       enabled(1), 
       disabled(2)
    }
    MAX-ACCESS read-write 
    STATUS     current 
    DESCRIPTION "The administratively desired status of the local LLDP agent.

            If the associated ethIntfLldpAdminStatus object has a
            value of 'enabled(1)', then the LLDP agent will transmit
            and receive LLDP frames on this port.

            If the associated ethIntfLldpAdminStatus object has a
            value of 'disabled(2)', then LLDP agent will not transmit or
            receive LLDP frames on this port.  If there is remote systems
            information which is received on this port and stored in
            other tables, before the port's ethIntfLldpAdminStatus
            becomes disabled, then the information will naturally age out."
--    REFERENCE "IEEE 802.1AB-2005 10.5.1"
    DEFVAL  { enabled }
   ::= { ethIntfEntry 45 } 

ethIntfLldpRemChassisIdSubtype  OBJECT-TYPE
    SYNTAX      LldpChassisIdSubtype
    MAX-ACCESS  read-only
    STATUS      current
    DESCRIPTION "The type of encoding used to identify the chassis associated
            with the remote system."
--    REFERENCE "IEEE 802.1AB-2005 9.5.2.2"
    ::= { ethIntfEntry 46 }

ethIntfLldpRemChassisId  OBJECT-TYPE
    SYNTAX      LldpChassisId
    MAX-ACCESS  read-only
    STATUS      current
    DESCRIPTION "The string value used to identify the chassis component
            associated with the remote system."
--    REFERENCE "IEEE 802.1AB-2005 9.5.2.3"
    ::= { ethIntfEntry 47 }

ethIntfLldpRemPortIdSubtype  OBJECT-TYPE
    SYNTAX      LldpPortIdSubtype
    MAX-ACCESS  read-only
    STATUS      current
    DESCRIPTION "The type of port identifier encoding used in the associated
            'ethIntfLldpRemPortId' object."
--    REFERENCE "IEEE 802.1AB-2005 9.5.3.2"
    ::= { ethIntfEntry 48 }

ethIntfLldpRemPortId  OBJECT-TYPE
    SYNTAX      LldpPortId
    MAX-ACCESS  read-only
    STATUS      current
    DESCRIPTION "The string value used to identify the port component
            associated with the remote system."
--    REFERENCE "IEEE 802.1AB-2005 9.5.3.3"
    ::= { ethIntfEntry 49 }

ethIntfBouncingStateChangeCount OBJECT-TYPE
    SYNTAX       Integer32
    MAX-ACCESS   read-only
    STATUS       current
    DESCRIPTION  " Count of the Ethernet facility operational state changes sinse last reboot"
    ::= { ethIntfEntry 50 }

ethIntfRowStatus OBJECT-TYPE
    SYNTAX       RowStatus
    MAX-ACCESS   read-create
    STATUS       current
    DESCRIPTION  "Used to control the addition and deletion of entries in the
                  Ethernet table, which in turn controls provisioning and
                  deprovisioning of Ethernet facilities."
    ::= { ethIntfEntry 100 }

-----------------------------------------------------------------------
-- Objects related to ODU-N facilities on Muxponder Circuit Packs
-----------------------------------------------------------------------

odunTable OBJECT-TYPE
    SYNTAX       SEQUENCE OF OdunEntry
    MAX-ACCESS   not-accessible
    STATUS       current
    DESCRIPTION  "This table contains one row for every ODU-N
                  facility on the system."
    ::= { facilities 15 }


odunEntry OBJECT-TYPE
    SYNTAX       OdunEntry
    MAX-ACCESS   not-accessible
    STATUS       current
    DESCRIPTION  "The conceptual row object of the ODU-N table."
    INDEX        { odunTypeIdx,
                   odunShelfIdx,
                   odunSlotIdx,
                   odunPortIdx }
    ::= { odunTable 1 }


OdunEntry ::= SEQUENCE { odunTypeIdx                   OdunType,
                         odunShelfIdx                  INTEGER,
                         odunSlotIdx                   INTEGER,
                         odunPortIdx                   INTEGER, 
                         odunIdx                       INTEGER }           

odunTypeIdx OBJECT-TYPE
    SYNTAX       OdunType
    MAX-ACCESS   accessible-for-notify
    STATUS       current
    DESCRIPTION  "The specific type of ODU-N which is provisioned."
    ::= { odunEntry 1 }


odunShelfIdx OBJECT-TYPE
    SYNTAX       INTEGER (1|11|21|31)
    MAX-ACCESS   accessible-for-notify
    STATUS       current
    DESCRIPTION  "The number of the shelf on which the ODU-N facility is
                  provisioned."
    ::= { odunEntry 2 }


odunSlotIdx OBJECT-TYPE
    SYNTAX       INTEGER (1..20)
    MAX-ACCESS   accessible-for-notify
    STATUS       current
    DESCRIPTION  "The number of the slot within which the ODU-N facility is
                  provisioned."
    ::= { odunEntry 3 }


odunPortIdx OBJECT-TYPE
    SYNTAX       INTEGER (1..6)
    MAX-ACCESS   accessible-for-notify
    STATUS       current
    DESCRIPTION  "The number of the port on the circuit pack on which the ODU-N
                  facility is provisioned."
    ::= { odunEntry 4 }
    
    
odunIdx OBJECT-TYPE
    SYNTAX       INTEGER (1..4)
    MAX-ACCESS   accessible-for-notify
    STATUS       current
    DESCRIPTION  "The ODU-N channel number within the port in which the ODU-N
                  facility exists."
    ::= { odunEntry 5 }
    

-----------------------------------------------------------------------
-- Objects related to provisioned Bit Rate Independent (BRI)
-- facilities on Muxponder Circuit Packs
-----------------------------------------------------------------------


briTable OBJECT-TYPE
    SYNTAX       SEQUENCE OF BriEntry
    MAX-ACCESS   not-accessible
    STATUS       current
    DESCRIPTION  "This table contains one row for every provisioned 
                  Bit Rate Independent (BRI) facility on the system. 
                  Each row contains a list of attributes that pertain 
                  to the facility."
    ::= { facilities 16 }


briEntry OBJECT-TYPE
    SYNTAX       BriEntry
    MAX-ACCESS   not-accessible
    STATUS       current
    DESCRIPTION  "The conceptual row object of the BRI table."
    INDEX        { briShelfIdx,
                   briSlotIdx,
                   briPortIdx }
    ::= { briTable 1 }


BriEntry ::= SEQUENCE { briShelfIdx                    INTEGER,
                        briSlotIdx                     INTEGER,
                        briPortIdx                     INTEGER,
                        briProtocol                    INTEGER,
                        briOpticalPwrReceivedMinTh     FixedX10,
                        briOpticalPwrReceivedMaxTh     FixedX10,
                        briOpticalPwrTransmittedMinTh  FixedX10,
                        briOpticalPwrTransmittedMaxTh  FixedX10,
                        briOpticalPwrReceived          FixedX10,
                        briOpticalPwrTransmitted       FixedX10,
                        briPEC                         DisplayString,
                        briAdminStatus                 AdminStatus,
                        briOperStatus                  OperStatus,
                        briOperStatQlfr                OperStatQlfr,
                        briAutoEnableTimer             HoursAndMinutes,
                        briActAutoEnableTimer          HoursAndMinutes,
                        briWavelength                  FixedX100,
                        briVendorPN1                   DisplayString,
                        briVendorPN2                   DisplayString,
                        briVendorPN3                   DisplayString,
                        briPhyPMMon                    INTEGER,
                        briLaserStatus                 INTEGER,
                        briId1                         DisplayString,
                        briFiberType                   FiberType,
                        briCustom1                     DisplayString,
                        briBitRate                     FixedX100,
                        briRemoteId                    DisplayString,
                        briRowStatus                   RowStatus }


briShelfIdx OBJECT-TYPE
    SYNTAX       INTEGER (1|11|21|31)
    MAX-ACCESS   accessible-for-notify
    STATUS       current
    DESCRIPTION  "The number of the shelf on which the BRI facility is
                  provisioned."
    ::= { briEntry 1 }


briSlotIdx OBJECT-TYPE
    SYNTAX       INTEGER (1|3|5|7|9|11|13|15|17|19)
    MAX-ACCESS   accessible-for-notify
    STATUS       current
    DESCRIPTION  "The number of the slot within which the BRI facility
                  is provisioned."
    ::= { briEntry 2 }


briPortIdx OBJECT-TYPE
    SYNTAX       INTEGER (3..12)
    MAX-ACCESS   accessible-for-notify
    STATUS       current
    DESCRIPTION  "The number of the port on the circuit pack on which the
                  BRI facility is provisioned."
    ::= { briEntry 3 }


briProtocol OBJECT-TYPE
    SYNTAX       INTEGER { fx100     (1),
                           escon     (2),
                           sdSdi     (3),
                           hdSdi     (4),
                           hdSdi1001 (5),
                           dvbAsi    (6)}
    MAX-ACCESS   read-create
    STATUS       current
    DESCRIPTION  "The protocol of the BRI signal which is provisioned."
    ::= { briEntry 4 }


briOpticalPwrReceivedMinTh OBJECT-TYPE
    SYNTAX       FixedX10
    UNITS        "dBm/10"
    MAX-ACCESS   read-only
    STATUS       current
    DESCRIPTION  "This is the optical power received minimum threshold."
    ::= { briEntry 5 }


briOpticalPwrReceivedMaxTh OBJECT-TYPE
    SYNTAX       FixedX10
    UNITS        "dBm/10"
    MAX-ACCESS   read-only
    STATUS       current
    DESCRIPTION  "This is the optical power received maximum threshold."
    ::= { briEntry 6 }


briOpticalPwrTransmittedMinTh OBJECT-TYPE
    SYNTAX       FixedX10
    UNITS        "dBm/10"
    MAX-ACCESS   read-only
    STATUS       current
    DESCRIPTION  "This is the optical power transmitted minimum threshold."
    ::= { briEntry 7 }


briOpticalPwrTransmittedMaxTh OBJECT-TYPE
    SYNTAX       FixedX10
    UNITS        "dBm/10"
    MAX-ACCESS   read-only
    STATUS       current
    DESCRIPTION  "This is the optical power transmitted maximum threshold."
    ::= { briEntry 8 }


briOpticalPwrReceived OBJECT-TYPE
    SYNTAX       FixedX10
    UNITS        "dBm/10"
    MAX-ACCESS   accessible-for-notify
    STATUS       current
    DESCRIPTION  "The optical power received on the input of the transceiver."
    ::= { briEntry 9 }


briOpticalPwrTransmitted OBJECT-TYPE
    SYNTAX       FixedX10
    UNITS        "dBm/10"
    MAX-ACCESS   accessible-for-notify
    STATUS       current
    DESCRIPTION  "The optical power transmitted at the output of the
                  transceiver."
    ::= { briEntry 10 }


briPEC OBJECT-TYPE
    SYNTAX       DisplayString (SIZE (0..32))
    MAX-ACCESS   read-create
    STATUS       current
    DESCRIPTION  "An optionally provisioned Product Equipment Code used to
                  validate the physically present optical transceiver on the
                  BRI port."
    DEFVAL       { "" }
    ::= { briEntry 11 }


briAdminStatus OBJECT-TYPE
    SYNTAX       AdminStatus
    MAX-ACCESS   read-create
    STATUS       current
    DESCRIPTION  "The administrative status of the BRI facility."
    DEFVAL       { enabled }
    ::= { briEntry 12 }


briOperStatus OBJECT-TYPE
    SYNTAX       OperStatus
    MAX-ACCESS   read-only
    STATUS       current
    DESCRIPTION  "The reported operational status of the BRI facility."
    ::= { briEntry 13 }


briOperStatQlfr OBJECT-TYPE
    SYNTAX       OperStatQlfr
    MAX-ACCESS   read-only
    STATUS       current
    DESCRIPTION  "This is a textual list of qualifiers about the reported
                  operational status of the BRI facility."
    ::= { briEntry 14 }


briAutoEnableTimer OBJECT-TYPE
    SYNTAX       HoursAndMinutes
    MAX-ACCESS   read-create
    STATUS       current
    DESCRIPTION  "Specifies the auto-enable timer for the targeted BRI
                  facility. This value only applies if the briAdminStatus object
                  is set to autoEnabled. Otherwise, the value returned is
                  000-00."
    DEFVAL       { "008-00" }
    ::= { briEntry 15 }


briActAutoEnableTimer OBJECT-TYPE
    SYNTAX       HoursAndMinutes
    MAX-ACCESS   read-only
    STATUS       current
    DESCRIPTION  "Indicates the time remaining on the auto-enable timer if it is
                  actively counting down. Otherwise, the value returned is
                  000-00."
    ::= { briEntry 16 }


briWavelength OBJECT-TYPE
    SYNTAX       FixedX100
    MAX-ACCESS   read-create
    STATUS       current
    DESCRIPTION  "The wavelength to be transmitted by the transceiver on the
                  BRI facility port. This is a mandatory object when a
                  row of the fiber channel table is created."
    ::= { briEntry 17 }


briVendorPN1 OBJECT-TYPE
    SYNTAX       DisplayString (SIZE (0..20))
    MAX-ACCESS   read-create
    STATUS       current
    DESCRIPTION  "An optionally provisioned part number used to validate the
                  optical transceiver on the BRI facility port."
    DEFVAL       { "" }
    ::= { briEntry 18 }


briVendorPN2 OBJECT-TYPE
    SYNTAX       DisplayString (SIZE (0..20))
    MAX-ACCESS   read-create
    STATUS       current
    DESCRIPTION  "An optionally provisioned part number used to validate the
                  optical transceiver on the BRI facility port."
    DEFVAL       { "" }
    ::= { briEntry 19 }


briVendorPN3 OBJECT-TYPE
    SYNTAX       DisplayString (SIZE (0..20))
    MAX-ACCESS   read-create
    STATUS       current
    DESCRIPTION  "An optionally provisioned part number used to validate the
                  optical transceiver on the BRI facility port."
    DEFVAL       { "" }
    ::= { briEntry 20 }


briPhyPMMon OBJECT-TYPE
    SYNTAX       INTEGER { enabled  (1),
                           disabled (2) }
    MAX-ACCESS   read-create
    STATUS       current
    DESCRIPTION  "Indicates if the BRI facility is configured to
                  report threshold crossing conditions for physical layer
                  performance monitoring parameters."
    DEFVAL       { disabled }
    ::= { briEntry 21 }


briLaserStatus OBJECT-TYPE
    SYNTAX       INTEGER { on    (1),
                           off   (2) }
    MAX-ACCESS   read-only
    STATUS       current
    DESCRIPTION  "An indication of the operational status of the transceiver
                  laser on the BRI facility port."
    ::= { briEntry 22 }


briId1 OBJECT-TYPE
    SYNTAX       DisplayString (SIZE (0..32))
    MAX-ACCESS   read-create
    STATUS       current
    DESCRIPTION  "Textual data recorded by the user to describe the provisioned
                  BRI facility in a manner useful to the user."
    DEFVAL       { "" }
    ::= { briEntry 23 }


briFiberType OBJECT-TYPE
    SYNTAX       FiberType
    MAX-ACCESS   read-create
    STATUS       current
    DESCRIPTION  "An optional specification of the fiber type that interfaces to
                  the BRI facility port."
    DEFVAL       { none }
    ::= { briEntry 24 }


briCustom1 OBJECT-TYPE
    SYNTAX       DisplayString
    MAX-ACCESS   read-create
    STATUS       current
    DESCRIPTION  "A variable length text string for operating company use."
    DEFVAL       { "" }
    ::= { briEntry 25 }


briBitRate OBJECT-TYPE
    SYNTAX       FixedX100
    MAX-ACCESS   read-only
    STATUS       current
    DESCRIPTION  "The bit rate transmitted by the BRI facility port in Mbps."
    ::= { briEntry 26 }


briRemoteId OBJECT-TYPE
    SYNTAX       DisplayString
    MAX-ACCESS   read-create
    STATUS       current
    DESCRIPTION  "Identifies the remote node and port to which the
                  Bitrate Independent port is connected, in the
                  format prescribed by the PSM network management
                  system."
    DEFVAL       { "" }
    ::= { briEntry 27 }


briRowStatus OBJECT-TYPE
    SYNTAX       RowStatus
    MAX-ACCESS   read-create
    STATUS       current
    DESCRIPTION  "Used to control the addition and deletion of entries in the
                  BRI table, which in turn controls provisioning and
                  deprovisioning of BRI facilities."
    ::= { briEntry 100 }

        
-----------------------------------------------------------------------
-- Objects used to retrieve current Optical Amplifier
-- Performance Monitoring statistics
-- 
-- A listing of current optical amplifier PM values are contained in
-- the oaCrntPMTable of the BTI 7000 Series MIB. When retrieved, this
-- table provides one row for each set of current optical amplifier
-- PM data. The following table lists the objects in each entry of the
-- oaCrntPMTable.
-----------------------------------------------------------------------


oaCrntPMTable OBJECT-TYPE
    SYNTAX       SEQUENCE OF OaCrntPMEntry
    MAX-ACCESS   not-accessible
    STATUS       current
    DESCRIPTION  "A table of current performance monitoring statistics collected
                  for the optical amplifier facilities on the NE."
    ::= { performance 1 }


oaCrntPMEntry OBJECT-TYPE
    SYNTAX       OaCrntPMEntry
    MAX-ACCESS   not-accessible
    STATUS       current
    DESCRIPTION  "The row entry object of the optical amplifier current
                  performance monitoring table. Each row of this table contains
                  a full set of PM statistics and related data for a current
                  measurement interval for a given optical amplifier."
    INDEX        { oaCrntPMOaTypeIdx,
                   oaCrntPMShelfIdx,
                   oaCrntPMSlotIdx,
                   oaCrntPMOaIdx,
                   oaCrntPMIntervalTypeIdx }
    ::= { oaCrntPMTable 1 }


OaCrntPMEntry ::= SEQUENCE { oaCrntPMOaTypeIdx               OaType,
                             oaCrntPMShelfIdx                INTEGER,
                             oaCrntPMSlotIdx                 INTEGER,
                             oaCrntPMOaIdx                   INTEGER,
                             oaCrntPMIntervalTypeIdx         PMIntervalType,
                             oaCrntPMCaseTempValue           INTEGER,
                             oaCrntPMCaseTempTimeStamp       DateAndTime,
                             oaCrntPMCaseTempValidity        PMValidity,
                             oaCrntPMLaser1TempValue         INTEGER,
                             oaCrntPMLaser1TempTimeStamp     DateAndTime,
                             oaCrntPMLaser1TempValidity      PMValidity,
                             oaCrntPMLaser2TempValue         INTEGER,
                             oaCrntPMLaser2TempTimeStamp     DateAndTime,
                             oaCrntPMLaser2TempValidity      PMValidity,
                             oaCrntPMOPRValue                FixedX10,
                             oaCrntPMOPRTimeStamp            DateAndTime,
                             oaCrntPMOPRValidity             PMValidity,
                             oaCrntPMSSIOPRValue             FixedX10,
                             oaCrntPMSSIOPRTimeStamp         DateAndTime,
                             oaCrntPMSSIOPRValidity          PMValidity,
                             oaCrntPMOPTValue                FixedX10,
                             oaCrntPMOPTTimeStamp            DateAndTime,
                             oaCrntPMOPTValidity             PMValidity,
                             oaCrntPMMSInsLossValue          FixedX10,
                             oaCrntPMMSInsLossTimeStamp      DateAndTime,
                             oaCrntPMMSInsLossValidity       PMValidity,
                             oaCrntPMEffectiveGainValue      FixedX10,
                             oaCrntPMEffectiveGainTimeStamp  DateAndTime,
                             oaCrntPMEffectiveGainValidity   PMValidity,
                             oaCrntPMFSOOPTValue             FixedX10,
                             oaCrntPMFSOOPTTimeStamp         DateAndTime,
                             oaCrntPMFSOOPTValidity          PMValidity,
                             oaCrntPMLaser1CurrentValue      FixedX10,
                             oaCrntPMLaser1CurrentTimeStamp  DateAndTime,
                             oaCrntPMLaser1CurrentValidity   PMValidity,
                             oaCrntPMLaser2CurrentValue      FixedX10,
                             oaCrntPMLaser2CurrentTimeStamp  DateAndTime,
                             oaCrntPMLaser2CurrentValidity   PMValidity,
                             oaCrntPMLaser1PowerValue        FixedX10,
                             oaCrntPMLaser1PowerTimeStamp    DateAndTime,
                             oaCrntPMLaser1PowerValidity     PMValidity,
                             oaCrntPMLaser2PowerValue        FixedX10,
                             oaCrntPMLaser2PowerTimeStamp    DateAndTime,
                             oaCrntPMLaser2PowerValidity     PMValidity,
                             oaCrntPMOBRValue                FixedX10,
                             oaCrntPMOBRTimeStamp            DateAndTime,
                             oaCrntPMOBRValidity             PMValidity,
                             oaCrntPMVOAValue                FixedX10,
                             oaCrntPMVOATimeStamp            DateAndTime,
                             oaCrntPMVOAValidity             PMValidity }


oaCrntPMOaTypeIdx OBJECT-TYPE
    SYNTAX       OaType
    MAX-ACCESS   not-accessible
    STATUS       current
    DESCRIPTION  "The type of the optical amplifier targeted for PM retrieval."
    ::= { oaCrntPMEntry 1 }


oaCrntPMShelfIdx OBJECT-TYPE
    SYNTAX       INTEGER (1|11|21|31)
    MAX-ACCESS   not-accessible
    STATUS       current
    DESCRIPTION  "The number of the shelf on which the amplifier targeted for
                  PMs is provisioned."
    ::= { oaCrntPMEntry 2 }

oaCrntPMSlotIdx OBJECT-TYPE
    SYNTAX       INTEGER (1..20)
    MAX-ACCESS   not-accessible
    STATUS       current
    DESCRIPTION  "The number of the slot within which the optical amplifier
                  targeted for PMs is provisioned."
    ::= { oaCrntPMEntry 3 }


oaCrntPMOaIdx OBJECT-TYPE
    SYNTAX       INTEGER (1..1)
    MAX-ACCESS   not-accessible
    STATUS       current
    DESCRIPTION  "The number of the amplifier port on which the circuit pack for
                  PMs is targeted."
    ::= { oaCrntPMEntry 4 }


oaCrntPMIntervalTypeIdx OBJECT-TYPE
    SYNTAX       PMIntervalType
    MAX-ACCESS   not-accessible
    STATUS       current
    DESCRIPTION  "The type of PM bin according to interval length."
    ::= { oaCrntPMEntry 5 }


oaCrntPMCaseTempValue OBJECT-TYPE
    SYNTAX       INTEGER (-32768..32767)
    UNITS        "degrees Celsius"
    MAX-ACCESS   read-only
    STATUS       current
    DESCRIPTION  "The optical amplifier case temperature."
    ::= { oaCrntPMEntry 6 }


oaCrntPMCaseTempTimeStamp OBJECT-TYPE
    SYNTAX       DateAndTime
    MAX-ACCESS   read-only
    STATUS       current
    DESCRIPTION  "The date and time stamp of the case temperature value."
    ::= { oaCrntPMEntry 7 }


oaCrntPMCaseTempValidity OBJECT-TYPE
    SYNTAX       PMValidity
    MAX-ACCESS   read-only
    STATUS       current
    DESCRIPTION  "Indicates the validity of the provided case temperature
                  value."
    ::= { oaCrntPMEntry 8 }


oaCrntPMLaser1TempValue OBJECT-TYPE
    SYNTAX       INTEGER (-32768..32767)
    UNITS        "degrees Celsius"
    MAX-ACCESS   read-only
    STATUS       current
    DESCRIPTION  "The optical amplifier laser 1 temperature."
    ::= { oaCrntPMEntry 9 }


oaCrntPMLaser1TempTimeStamp OBJECT-TYPE
    SYNTAX       DateAndTime
    MAX-ACCESS   read-only
    STATUS       current
    DESCRIPTION  "The date and time stamp of the laser 1 temperature value."
    ::= { oaCrntPMEntry 10 }


oaCrntPMLaser1TempValidity OBJECT-TYPE
    SYNTAX       PMValidity
    MAX-ACCESS   read-only
    STATUS       current
    DESCRIPTION  "Indicates the validity of the provided laser 1 temperature
                  value."
    ::= { oaCrntPMEntry 11 }


oaCrntPMLaser2TempValue OBJECT-TYPE
    SYNTAX       INTEGER (-32768..32767)
    UNITS        "degrees Celsius"
    MAX-ACCESS   read-only
    STATUS       current
    DESCRIPTION  "The optical amplifier laser 2 temperature."
    ::= { oaCrntPMEntry 12 }


oaCrntPMLaser2TempTimeStamp OBJECT-TYPE
    SYNTAX       DateAndTime
    MAX-ACCESS   read-only
    STATUS       current
    DESCRIPTION  "The date and time stamp of the laser 2 temperature value."
    ::= { oaCrntPMEntry 13 }


oaCrntPMLaser2TempValidity OBJECT-TYPE
    SYNTAX       PMValidity
    MAX-ACCESS   read-only
    STATUS       current
    DESCRIPTION  "Indicates the validity of the provided laser 2 temperature
                  value."
    ::= { oaCrntPMEntry 14 }


oaCrntPMOPRValue OBJECT-TYPE
    SYNTAX       FixedX10
    UNITS        "dBm/10"
    MAX-ACCESS   read-only
    STATUS       current
    DESCRIPTION  "The optical power received on the input of the amplifer."
    ::= { oaCrntPMEntry 15 }


oaCrntPMOPRTimeStamp OBJECT-TYPE
    SYNTAX       DateAndTime
    MAX-ACCESS   read-only
    STATUS       current
    DESCRIPTION  "The date and time stamp of the optical power received value."
    ::= { oaCrntPMEntry 16 }


oaCrntPMOPRValidity OBJECT-TYPE
    SYNTAX       PMValidity
    MAX-ACCESS   read-only
    STATUS       current
    DESCRIPTION  "Indicates the validity of the provided optical power received
                  value."
    ::= { oaCrntPMEntry 17 }


oaCrntPMSSIOPRValue OBJECT-TYPE
    SYNTAX       FixedX10
    UNITS        "dBm/10"
    MAX-ACCESS   read-only
    STATUS       current
    DESCRIPTION  "The optical power received on the input of the second stage of
                  the amplifier."
    ::= { oaCrntPMEntry 18 }


oaCrntPMSSIOPRTimeStamp OBJECT-TYPE
    SYNTAX       DateAndTime
    MAX-ACCESS   read-only
    STATUS       current
    DESCRIPTION  "The date and time stamp of the second stage input optical
                  power received value."
    ::= { oaCrntPMEntry 19 }


oaCrntPMSSIOPRValidity OBJECT-TYPE
    SYNTAX       PMValidity
    MAX-ACCESS   read-only
    STATUS       current
    DESCRIPTION  "Indicates the validity of the provided second stage input
                  optical power received value."
    ::= { oaCrntPMEntry 20 }


oaCrntPMOPTValue OBJECT-TYPE
    SYNTAX       FixedX10
    UNITS        "dBm/10"
    MAX-ACCESS   read-only
    STATUS       current
    DESCRIPTION  "The optical power transmitted at the output of the amplifier."
    ::= { oaCrntPMEntry 21 }


oaCrntPMOPTTimeStamp OBJECT-TYPE
    SYNTAX       DateAndTime
    MAX-ACCESS   read-only
    STATUS       current
    DESCRIPTION  "The date and time stamp of the optical power transmitted
                  value."
    ::= { oaCrntPMEntry 22 }


oaCrntPMOPTValidity OBJECT-TYPE
    SYNTAX       PMValidity
    MAX-ACCESS   read-only
    STATUS       current
    DESCRIPTION  "Indicates the validity of the provided optical power
                  transmitted value."
    ::= { oaCrntPMEntry 23 }


oaCrntPMMSInsLossValue OBJECT-TYPE
    SYNTAX       FixedX10
    UNITS        "dB/10"
    MAX-ACCESS   read-only
    STATUS       current
    DESCRIPTION  "The mid-stage insertion loss."
    ::= { oaCrntPMEntry 24 }


oaCrntPMMSInsLossTimeStamp OBJECT-TYPE
    SYNTAX       DateAndTime
    MAX-ACCESS   read-only
    STATUS       current
    DESCRIPTION  "The date and time stamp of the mid-stage insertion loss
                  value."
    ::= { oaCrntPMEntry 25 }


oaCrntPMMSInsLossValidity OBJECT-TYPE
    SYNTAX       PMValidity
    MAX-ACCESS   read-only
    STATUS       current
    DESCRIPTION  "Indicates the validity of the provided mid-stage insertion
                  loss value."
    ::= { oaCrntPMEntry 26 }


oaCrntPMEffectiveGainValue OBJECT-TYPE
    SYNTAX       FixedX10
    UNITS        "dB/10"
    MAX-ACCESS   read-only
    STATUS       current
    DESCRIPTION  "The effective gain of the optical amplifier. This reading is
                  compensated for amplified spontaneous emissions."
    ::= { oaCrntPMEntry 27 }


oaCrntPMEffectiveGainTimeStamp OBJECT-TYPE
    SYNTAX       DateAndTime
    MAX-ACCESS   read-only
    STATUS       current
    DESCRIPTION  "The date and time stamp of the effective gain value."
    ::= { oaCrntPMEntry 28 }


oaCrntPMEffectiveGainValidity OBJECT-TYPE
    SYNTAX       PMValidity
    MAX-ACCESS   read-only
    STATUS       current
    DESCRIPTION  "Indicates the validity of the provided effective gain value."
    ::= { oaCrntPMEntry 29 }


oaCrntPMFSOOPTValue OBJECT-TYPE
    SYNTAX       FixedX10
    UNITS        "dBm/10"
    MAX-ACCESS   read-only
    STATUS       current
    DESCRIPTION  "The optical power transmitted at the output of the first stage
                  of the amplifier."
    ::= { oaCrntPMEntry 30 }


oaCrntPMFSOOPTTimeStamp OBJECT-TYPE
    SYNTAX       DateAndTime
    MAX-ACCESS   read-only
    STATUS       current
    DESCRIPTION  "The date and time stamp of the first stage output optical
                  power transmitted value."
    ::= { oaCrntPMEntry 31 }


oaCrntPMFSOOPTValidity OBJECT-TYPE
    SYNTAX       PMValidity
    MAX-ACCESS   read-only
    STATUS       current
    DESCRIPTION  "Indicates the validity of the provided first stage output
                  optical power transmitted value."
    ::= { oaCrntPMEntry 32 }


oaCrntPMLaser1CurrentValue OBJECT-TYPE
    SYNTAX       FixedX10
    UNITS        "mAmp/10"
    MAX-ACCESS   read-only
    STATUS       current
    DESCRIPTION  "The optical amplifier laser 1 current."
    ::= { oaCrntPMEntry 33 }


oaCrntPMLaser1CurrentTimeStamp OBJECT-TYPE
    SYNTAX       DateAndTime
    MAX-ACCESS   read-only
    STATUS       current
    DESCRIPTION  "The date and time stamp of the laser 1 current value."
    ::= { oaCrntPMEntry 34 }


oaCrntPMLaser1CurrentValidity OBJECT-TYPE
    SYNTAX       PMValidity
    MAX-ACCESS   read-only
    STATUS       current
    DESCRIPTION  "Indicates the validity of the provided laser 1 current value."
    ::= { oaCrntPMEntry 35 }


oaCrntPMLaser2CurrentValue OBJECT-TYPE
    SYNTAX       FixedX10
    UNITS        "mAmp/10"
    MAX-ACCESS   read-only
    STATUS       current
    DESCRIPTION  "The optical amplifier laser 2 current."
    ::= { oaCrntPMEntry 36 }


oaCrntPMLaser2CurrentTimeStamp OBJECT-TYPE
    SYNTAX       DateAndTime
    MAX-ACCESS   read-only
    STATUS       current
    DESCRIPTION  "The date and time stamp of the laser 2 current value."
    ::= { oaCrntPMEntry 37 }


oaCrntPMLaser2CurrentValidity OBJECT-TYPE
    SYNTAX       PMValidity
    MAX-ACCESS   read-only
    STATUS       current
    DESCRIPTION  "Indicates the validity of the provided laser 2 current value."
    ::= { oaCrntPMEntry 38 }


oaCrntPMLaser1PowerValue OBJECT-TYPE
    SYNTAX       FixedX10
    UNITS        "mWatts/10"
    MAX-ACCESS   read-only
    STATUS       current
    DESCRIPTION  "The optical amplifier laser 1 power."
    ::= { oaCrntPMEntry 39 }


oaCrntPMLaser1PowerTimeStamp OBJECT-TYPE
    SYNTAX       DateAndTime
    MAX-ACCESS   read-only
    STATUS       current
    DESCRIPTION  "The date and time stamp of the laser 1 power value."
    ::= { oaCrntPMEntry 40 }


oaCrntPMLaser1PowerValidity OBJECT-TYPE
    SYNTAX       PMValidity
    MAX-ACCESS   read-only
    STATUS       current
    DESCRIPTION  "Indicates the validity of the provided laser 1 power value."
    ::= { oaCrntPMEntry 41 }


oaCrntPMLaser2PowerValue OBJECT-TYPE
    SYNTAX       FixedX10
    UNITS        "mWatts/10"
    MAX-ACCESS   read-only
    STATUS       current
    DESCRIPTION  "The optical amplifier laser 2 power."
    ::= { oaCrntPMEntry 42 }


oaCrntPMLaser2PowerTimeStamp OBJECT-TYPE
    SYNTAX       DateAndTime
    MAX-ACCESS   read-only
    STATUS       current
    DESCRIPTION  "The date and time stamp of the laser 2 power value."
    ::= { oaCrntPMEntry 43 }


oaCrntPMLaser2PowerValidity OBJECT-TYPE
    SYNTAX       PMValidity
    MAX-ACCESS   read-only
    STATUS       current
    DESCRIPTION  "Indicates the validity of the provided laser 2 power value."
    ::= { oaCrntPMEntry 44 }


oaCrntPMOBRValue OBJECT-TYPE
    SYNTAX       FixedX10
    UNITS        "dB/10"
    MAX-ACCESS   read-only
    STATUS       current
    DESCRIPTION  "The back reflected optical power measured at the output of the
                  second stage of the optical amplifier."
    ::= { oaCrntPMEntry 45 }


oaCrntPMOBRTimeStamp OBJECT-TYPE
    SYNTAX       DateAndTime
    MAX-ACCESS   read-only
    STATUS       current
    DESCRIPTION  "The date and time stamp of the optical back reflection value."
    ::= { oaCrntPMEntry 46 }


oaCrntPMOBRValidity OBJECT-TYPE
    SYNTAX       PMValidity
    MAX-ACCESS   read-only
    STATUS       current
    DESCRIPTION  "Indicates the validity of the provided optical back reflection
                  value."
    ::= { oaCrntPMEntry 47 }


oaCrntPMVOAValue OBJECT-TYPE
    SYNTAX       FixedX10
    UNITS        "dB/10"
    MAX-ACCESS   read-only
    STATUS       current
    DESCRIPTION  "The variable optical attenuation of the amplifier."
    ::= { oaCrntPMEntry 48 }


oaCrntPMVOATimeStamp OBJECT-TYPE
    SYNTAX       DateAndTime
    MAX-ACCESS   read-only
    STATUS       current
    DESCRIPTION  "The date and time stamp of the variable optical attenuation
                  value."
    ::= { oaCrntPMEntry 49 }


oaCrntPMVOAValidity OBJECT-TYPE
    SYNTAX       PMValidity
    MAX-ACCESS   read-only
    STATUS       current
    DESCRIPTION  "Indicates the validity of the provided variable optical
                  attenuation value."
    ::= { oaCrntPMEntry 50 }



-----------------------------------------------------------------------
-- Objects used to retrieve historical Optical Amplifier
-- Performance Monitoring statistics
-- 
-- A listing of historical optical amplifier PM values are contained in 
-- the oaHistPMTable of the BTI 7000 Series MIB. When retrieved, this
-- table provides one row for each set of historical optical amplifier
-- PM data.
-- 
-- The following table lists the objects in each entry of the 
-- oaHistPMTable.
-----------------------------------------------------------------------


oaHistPMTable OBJECT-TYPE
    SYNTAX       SEQUENCE OF OaHistPMEntry
    MAX-ACCESS   not-accessible
    STATUS       current
    DESCRIPTION  "A table of historical performance monitoring statistics
                  collected for the optical amplifier facilities on the NE."
    ::= { performance 2 }


oaHistPMEntry OBJECT-TYPE
    SYNTAX       OaHistPMEntry
    MAX-ACCESS   not-accessible
    STATUS       current
    DESCRIPTION  "The row entry object of the optical amplifier historical
                  performance monitoring table. Each row of this table contains
                  a full set of PM statistics and related data for a historical
                  measurement interval for a given optical amplifier."
    INDEX        { oaHistPMOaTypeIdx,
                   oaHistPMShelfIdx,
                   oaHistPMSlotIdx,
                   oaHistPMOaIdx,
                   oaHistPMIntervalTypeIdx,
                   oaHistPMIntervalIdx }
    ::= { oaHistPMTable 1 }


OaHistPMEntry ::= SEQUENCE { oaHistPMOaTypeIdx               OaType,
                             oaHistPMShelfIdx                INTEGER,
                             oaHistPMSlotIdx                 INTEGER,
                             oaHistPMOaIdx                   INTEGER,
                             oaHistPMIntervalTypeIdx         PMIntervalType,
                             oaHistPMIntervalIdx             INTEGER,
                             oaHistPMCaseTempValue           INTEGER,
                             oaHistPMCaseTempTimeStamp       DateAndTime,
                             oaHistPMCaseTempValidity        PMValidity,
                             oaHistPMLaser1TempValue         INTEGER,
                             oaHistPMLaser1TempTimeStamp     DateAndTime,
                             oaHistPMLaser1TempValidity      PMValidity,
                             oaHistPMLaser2TempValue         INTEGER,
                             oaHistPMLaser2TempTimeStamp     DateAndTime,
                             oaHistPMLaser2TempValidity      PMValidity,
                             oaHistPMOPRValue                FixedX10,
                             oaHistPMOPRTimeStamp            DateAndTime,
                             oaHistPMOPRValidity             PMValidity,
                             oaHistPMSSIOPRValue             FixedX10,
                             oaHistPMSSIOPRTimeStamp         DateAndTime,
                             oaHistPMSSIOPRValidity          PMValidity,
                             oaHistPMOPTValue                FixedX10,
                             oaHistPMOPTTimeStamp            DateAndTime,
                             oaHistPMOPTValidity             PMValidity,
                             oaHistPMMSInsLossValue          FixedX10,
                             oaHistPMMSInsLossTimeStamp      DateAndTime,
                             oaHistPMMSInsLossValidity       PMValidity,
                             oaHistPMEffectiveGainValue      FixedX10,
                             oaHistPMEffectiveGainTimeStamp  DateAndTime,
                             oaHistPMEffectiveGainValidity   PMValidity,
                             oaHistPMFSOOPTValue             FixedX10,
                             oaHistPMFSOOPTTimeStamp         DateAndTime,
                             oaHistPMFSOOPTValidity          PMValidity,
                             oaHistPMLaser1CurrentValue      FixedX10,
                             oaHistPMLaser1CurrentTimeStamp  DateAndTime,
                             oaHistPMLaser1CurrentValidity   PMValidity,
                             oaHistPMLaser2CurrentValue      FixedX10,
                             oaHistPMLaser2CurrentTimeStamp  DateAndTime,
                             oaHistPMLaser2CurrentValidity   PMValidity,
                             oaHistPMLaser1PowerValue        FixedX10,
                             oaHistPMLaser1PowerTimeStamp    DateAndTime,
                             oaHistPMLaser1PowerValidity     PMValidity,
                             oaHistPMLaser2PowerValue        FixedX10,
                             oaHistPMLaser2PowerTimeStamp    DateAndTime,
                             oaHistPMLaser2PowerValidity     PMValidity,
                             oaHistPMOBRValue                FixedX10,
                             oaHistPMOBRTimeStamp            DateAndTime,
                             oaHistPMOBRValidity             PMValidity,
                             oaHistPMVOAValue                FixedX10,
                             oaHistPMVOATimeStamp            DateAndTime,
                             oaHistPMVOAValidity             PMValidity }


oaHistPMOaTypeIdx OBJECT-TYPE
    SYNTAX       OaType
    MAX-ACCESS   not-accessible
    STATUS       current
    DESCRIPTION  "The type of the optical amplifier targeted for PM retrieval."
    ::= { oaHistPMEntry 1 }


oaHistPMShelfIdx OBJECT-TYPE
    SYNTAX       INTEGER (1|11|21|31)
    MAX-ACCESS   not-accessible
    STATUS       current
    DESCRIPTION  "The number of the shelf on which the amplifier targeted for
                  PMs is provisioned."
    ::= { oaHistPMEntry 2 }


oaHistPMSlotIdx OBJECT-TYPE
    SYNTAX       INTEGER (1..20)
    MAX-ACCESS   not-accessible
    STATUS       current
    DESCRIPTION  "The number of the slot within which the optical amplifier
                  targeted for PMs is provisioned."
    ::= { oaHistPMEntry 3 }


oaHistPMOaIdx OBJECT-TYPE
    SYNTAX       INTEGER (1..1)
    MAX-ACCESS   not-accessible
    STATUS       current
    DESCRIPTION  "The number of the amplifier port on the circuit pack targeted
                  for PMs."
    ::= { oaHistPMEntry 4 }


oaHistPMIntervalTypeIdx OBJECT-TYPE
    SYNTAX       PMIntervalType
    MAX-ACCESS   not-accessible
    STATUS       current
    DESCRIPTION  "The type of PM bin according to interval length."
    ::= { oaHistPMEntry 5 }


oaHistPMIntervalIdx OBJECT-TYPE
    SYNTAX       INTEGER (1..96)
    MAX-ACCESS   not-accessible
    STATUS       current
    DESCRIPTION  "The specific PM bin number. The range is 1..96 for 15-minute
                  bins, and for 1-day historical bins, the value is 1."
    ::= { oaHistPMEntry 6 }


oaHistPMCaseTempValue OBJECT-TYPE
    SYNTAX       INTEGER (-32768..32767)
    UNITS        "degrees Celsius"
    MAX-ACCESS   read-only
    STATUS       current
    DESCRIPTION  "The optical amplifier case temperature."
    ::= { oaHistPMEntry 7 }


oaHistPMCaseTempTimeStamp OBJECT-TYPE
    SYNTAX       DateAndTime
    MAX-ACCESS   read-only
    STATUS       current
    DESCRIPTION  "The date and time stamp of the case temperature value."
    ::= { oaHistPMEntry 8 }


oaHistPMCaseTempValidity OBJECT-TYPE
    SYNTAX       PMValidity
    MAX-ACCESS   read-only
    STATUS       current
    DESCRIPTION  "Indicates the validity of the provided case temperature
                  value."
    ::= { oaHistPMEntry 9 }


oaHistPMLaser1TempValue OBJECT-TYPE
    SYNTAX       INTEGER (-32768..32767)
    UNITS        "degrees Celsius"
    MAX-ACCESS   read-only
    STATUS       current
    DESCRIPTION  "The optical amplifier laser 1 temperature."
    ::= { oaHistPMEntry 10 }


oaHistPMLaser1TempTimeStamp OBJECT-TYPE
    SYNTAX       DateAndTime
    MAX-ACCESS   read-only
    STATUS       current
    DESCRIPTION  "The date and time stamp of the laser 1 temperature value."
    ::= { oaHistPMEntry 11 }


oaHistPMLaser1TempValidity OBJECT-TYPE
    SYNTAX       PMValidity
    MAX-ACCESS   read-only
    STATUS       current
    DESCRIPTION  "Indicates the validity of the provided laser 1 temperature
                  value."
    ::= { oaHistPMEntry 12 }


oaHistPMLaser2TempValue OBJECT-TYPE
    SYNTAX       INTEGER (-32768..32767)
    UNITS        "degrees Celsius"
    MAX-ACCESS   read-only
    STATUS       current
    DESCRIPTION  "The optical amplifier laser 2 temperature."
    ::= { oaHistPMEntry 13 }


oaHistPMLaser2TempTimeStamp OBJECT-TYPE
    SYNTAX       DateAndTime
    MAX-ACCESS   read-only
    STATUS       current
    DESCRIPTION  "The date and time stamp of the laser 2 temperature value."
    ::= { oaHistPMEntry 14 }


oaHistPMLaser2TempValidity OBJECT-TYPE
    SYNTAX       PMValidity
    MAX-ACCESS   read-only
    STATUS       current
    DESCRIPTION  "Indicates the validity of the provided laser 2 temperature
                  value."
    ::= { oaHistPMEntry 15 }


oaHistPMOPRValue OBJECT-TYPE
    SYNTAX       FixedX10
    UNITS        "dBm/10"
    MAX-ACCESS   read-only
    STATUS       current
    DESCRIPTION  "The optical power received on the input of the amplifer."
    ::= { oaHistPMEntry 16 }


oaHistPMOPRTimeStamp OBJECT-TYPE
    SYNTAX       DateAndTime
    MAX-ACCESS   read-only
    STATUS       current
    DESCRIPTION  "The date and time stamp of the optical power received value."
    ::= { oaHistPMEntry 17 }


oaHistPMOPRValidity OBJECT-TYPE
    SYNTAX       PMValidity
    MAX-ACCESS   read-only
    STATUS       current
    DESCRIPTION  "Indicates the validity of the provided optical power received
                  value."
    ::= { oaHistPMEntry 18 }


oaHistPMSSIOPRValue OBJECT-TYPE
    SYNTAX       FixedX10
    UNITS        "dBm/10"
    MAX-ACCESS   read-only
    STATUS       current
    DESCRIPTION  "The optical power received on the input of the second stage of
                  the amplifier."
    ::= { oaHistPMEntry 19 }


oaHistPMSSIOPRTimeStamp OBJECT-TYPE
    SYNTAX       DateAndTime
    MAX-ACCESS   read-only
    STATUS       current
    DESCRIPTION  "The date and time stamp of the second stage input optical
                  power received value."
    ::= { oaHistPMEntry 20 }


oaHistPMSSIOPRValidity OBJECT-TYPE
    SYNTAX       PMValidity
    MAX-ACCESS   read-only
    STATUS       current
    DESCRIPTION  "Indicates the validity of the provided second stage input
                  optical power received value."
    ::= { oaHistPMEntry 21 }


oaHistPMOPTValue OBJECT-TYPE
    SYNTAX       FixedX10
    UNITS        "dBm/10"
    MAX-ACCESS   read-only
    STATUS       current
    DESCRIPTION  "The optical power transmitted at the output of the amplifier."
    ::= { oaHistPMEntry 22 }


oaHistPMOPTTimeStamp OBJECT-TYPE
    SYNTAX       DateAndTime
    MAX-ACCESS   read-only
    STATUS       current
    DESCRIPTION  "The date and time stamp of the optical power transmitted
                  value."
    ::= { oaHistPMEntry 23 }


oaHistPMOPTValidity OBJECT-TYPE
    SYNTAX       PMValidity
    MAX-ACCESS   read-only
    STATUS       current
    DESCRIPTION  "Indicates the validity of the provided optical power
                  transmitted value."
    ::= { oaHistPMEntry 24 }


oaHistPMMSInsLossValue OBJECT-TYPE
    SYNTAX       FixedX10
    UNITS        "dB/10"
    MAX-ACCESS   read-only
    STATUS       current
    DESCRIPTION  "The mid-stage insertion loss."
    ::= { oaHistPMEntry 25 }


oaHistPMMSInsLossTimeStamp OBJECT-TYPE
    SYNTAX       DateAndTime
    MAX-ACCESS   read-only
    STATUS       current
    DESCRIPTION  "The date and time stamp of the mid-stage insertion loss
                  value."
    ::= { oaHistPMEntry 26 }


oaHistPMMSInsLossValidity OBJECT-TYPE
    SYNTAX       PMValidity
    MAX-ACCESS   read-only
    STATUS       current
    DESCRIPTION  "Indicates the validity of the provided mid-stage insertion
                  loss value."
    ::= { oaHistPMEntry 27 }


oaHistPMEffectiveGainValue OBJECT-TYPE
    SYNTAX       FixedX10
    UNITS        "dB/10"
    MAX-ACCESS   read-only
    STATUS       current
    DESCRIPTION  "The effective gain of the optical amplifier. This reading is
                  compensated for amplified spontaneous emissions."
    ::= { oaHistPMEntry 28 }


oaHistPMEffectiveGainTimeStamp OBJECT-TYPE
    SYNTAX       DateAndTime
    MAX-ACCESS   read-only
    STATUS       current
    DESCRIPTION  "The date and time stamp of the effective gain value."
    ::= { oaHistPMEntry 29 }


oaHistPMEffectiveGainValidity OBJECT-TYPE
    SYNTAX       PMValidity
    MAX-ACCESS   read-only
    STATUS       current
    DESCRIPTION  "Indicates the validity of the provided effective gain value."
    ::= { oaHistPMEntry 30 }


oaHistPMFSOOPTValue OBJECT-TYPE
    SYNTAX       FixedX10
    UNITS        "dBm/10"
    MAX-ACCESS   read-only
    STATUS       current
    DESCRIPTION  "The optical power transmitted at the output of the first stage
                  of the amplifier."
    ::= { oaHistPMEntry 31 }


oaHistPMFSOOPTTimeStamp OBJECT-TYPE
    SYNTAX       DateAndTime
    MAX-ACCESS   read-only
    STATUS       current
    DESCRIPTION  "The date and time stamp of the first stage output optical
                  power transmitted value."
    ::= { oaHistPMEntry 32 }


oaHistPMFSOOPTValidity OBJECT-TYPE
    SYNTAX       PMValidity
    MAX-ACCESS   read-only
    STATUS       current
    DESCRIPTION  "Indicates the validity of the provided first stage output
                  optical power transmitted value."
    ::= { oaHistPMEntry 33 }


oaHistPMLaser1CurrentValue OBJECT-TYPE
    SYNTAX       FixedX10
    UNITS        "mAmp/10"
    MAX-ACCESS   read-only
    STATUS       current
    DESCRIPTION  "The optical amplifier laser 1 current."
    ::= { oaHistPMEntry 34 }


oaHistPMLaser1CurrentTimeStamp OBJECT-TYPE
    SYNTAX       DateAndTime
    MAX-ACCESS   read-only
    STATUS       current
    DESCRIPTION  "The date and time stamp of the laser 1 current value."
    ::= { oaHistPMEntry 35 }


oaHistPMLaser1CurrentValidity OBJECT-TYPE
    SYNTAX       PMValidity
    MAX-ACCESS   read-only
    STATUS       current
    DESCRIPTION  "Indicates the validity of the provided laser 1 current value."
    ::= { oaHistPMEntry 36 }


oaHistPMLaser2CurrentValue OBJECT-TYPE
    SYNTAX       FixedX10
    UNITS        "mAmp/10"
    MAX-ACCESS   read-only
    STATUS       current
    DESCRIPTION  "The optical amplifier laser 2 current."
    ::= { oaHistPMEntry 37 }


oaHistPMLaser2CurrentTimeStamp OBJECT-TYPE
    SYNTAX       DateAndTime
    MAX-ACCESS   read-only
    STATUS       current
    DESCRIPTION  "The date and time stamp of the laser 2 current value."
    ::= { oaHistPMEntry 38 }


oaHistPMLaser2CurrentValidity OBJECT-TYPE
    SYNTAX       PMValidity
    MAX-ACCESS   read-only
    STATUS       current
    DESCRIPTION  "Indicates the validity of the provided laser 2 current value."
    ::= { oaHistPMEntry 39 }


oaHistPMLaser1PowerValue OBJECT-TYPE
    SYNTAX       FixedX10
    UNITS        "mWatts/10"
    MAX-ACCESS   read-only
    STATUS       current
    DESCRIPTION  "The optical amplifier laser 1 power."
    ::= { oaHistPMEntry 40 }


oaHistPMLaser1PowerTimeStamp OBJECT-TYPE
    SYNTAX       DateAndTime
    MAX-ACCESS   read-only
    STATUS       current
    DESCRIPTION  "The date and time stamp of the laser 1 power value."
    ::= { oaHistPMEntry 41 }


oaHistPMLaser1PowerValidity OBJECT-TYPE
    SYNTAX       PMValidity
    MAX-ACCESS   read-only
    STATUS       current
    DESCRIPTION  "Indicates the validity of the provided laser 1 power value."
    ::= { oaHistPMEntry 42 }


oaHistPMLaser2PowerValue OBJECT-TYPE
    SYNTAX       FixedX10
    UNITS        "mWatts/10"
    MAX-ACCESS   read-only
    STATUS       current
    DESCRIPTION  "The optical amplifier laser 2 power."
    ::= { oaHistPMEntry 43 }


oaHistPMLaser2PowerTimeStamp OBJECT-TYPE
    SYNTAX       DateAndTime
    MAX-ACCESS   read-only
    STATUS       current
    DESCRIPTION  "The date and time stamp of the laser 2 power value."
    ::= { oaHistPMEntry 44 }


oaHistPMLaser2PowerValidity OBJECT-TYPE
    SYNTAX       PMValidity
    MAX-ACCESS   read-only
    STATUS       current
    DESCRIPTION  "Indicates the validity of the provided laser 2 power value."
    ::= { oaHistPMEntry 45 }


oaHistPMOBRValue OBJECT-TYPE
    SYNTAX       FixedX10
    UNITS        "dB/10"
    MAX-ACCESS   read-only
    STATUS       current
    DESCRIPTION  "The back reflected optical power measured at the output of the
                  second stage of the optical amplifier."
    ::= { oaHistPMEntry 46 }


oaHistPMOBRTimeStamp OBJECT-TYPE
    SYNTAX       DateAndTime
    MAX-ACCESS   read-only
    STATUS       current
    DESCRIPTION  "The date and time stamp of the optical back reflection value."
    ::= { oaHistPMEntry 47 }


oaHistPMOBRValidity OBJECT-TYPE
    SYNTAX       PMValidity
    MAX-ACCESS   read-only
    STATUS       current
    DESCRIPTION  "Indicates the validity of the provided optical back reflection
                  value."
    ::= { oaHistPMEntry 48 }


oaHistPMVOAValue OBJECT-TYPE
    SYNTAX       FixedX10
    UNITS        "dB/10"
    MAX-ACCESS   read-only
    STATUS       current
    DESCRIPTION  "The variable optical attenuation of the amplifier."
    ::= { oaHistPMEntry 49 }


oaHistPMVOATimeStamp OBJECT-TYPE
    SYNTAX       DateAndTime
    MAX-ACCESS   read-only
    STATUS       current
    DESCRIPTION  "The date and time stamp of the variable optical attenuation
                  value."
    ::= { oaHistPMEntry 50 }


oaHistPMVOAValidity OBJECT-TYPE
    SYNTAX       PMValidity
    MAX-ACCESS   read-only
    STATUS       current
    DESCRIPTION  "Indicates the validity of the provided variable optical
                  attenuation value."
    ::= { oaHistPMEntry 51 }



-----------------------------------------------------------------------
-- Objects used to retrieve current Optical Transceiver
-- Performance Monitoring statistics
-- 
-- A listing of current transceiver PM values are contained in the 
-- xcvrCrntPMTable of the BTI 7000 Series MIB. When retrieved, this 
-- table provides one row for eachset of current transceiver PM data.
-- 
-- The following table lists the objects in each entry of the 
-- xcvrCrntPMTable.
-----------------------------------------------------------------------


xcvrCrntPMTable OBJECT-TYPE
    SYNTAX       SEQUENCE OF XcvrCrntPMEntry
    MAX-ACCESS   not-accessible
    STATUS       current
    DESCRIPTION  "A table of current performance monitoring statistics collected
                  for the optical transceiver facilities on the NE."
    ::= { performance 3 }


xcvrCrntPMEntry OBJECT-TYPE
    SYNTAX       XcvrCrntPMEntry
    MAX-ACCESS   not-accessible
    STATUS       current
    DESCRIPTION  "The row entry object of the optical transceiver current
                  performance monitoring table. Each row of this table contains
                  a full set of PM statistics and related data for a current
                  measurement interval for a given optical transceiver."
    INDEX        { xcvrCrntPMTypeIdx,
                   xcvrCrntPMShelfIdx,
                   xcvrCrntPMSlotIdx,
                   xcvrCrntPMIdx,
                   xcvrCrntPMIntervalTypeIdx }
    ::= { xcvrCrntPMTable 1 }


XcvrCrntPMEntry ::= SEQUENCE { xcvrCrntPMTypeIdx                   XcvrType,
                               xcvrCrntPMShelfIdx                  INTEGER,
                               xcvrCrntPMSlotIdx                   INTEGER,
                               xcvrCrntPMIdx                       INTEGER,
                               xcvrCrntPMIntervalTypeIdx           PMIntervalType,
                               xcvrCrntPMOPRValue                  FixedX10,
                               xcvrCrntPMOPRTimeStamp              DateAndTime,
                               xcvrCrntPMOPRValidity               PMValidity,
                               xcvrCrntPMOPTValue                  FixedX10,
                               xcvrCrntPMOPTTimeStamp              DateAndTime,
                               xcvrCrntPMOPTValidity               PMValidity,
                               xcvrCrntPMTempValue                 INTEGER,
                               xcvrCrntPMTempTimeStamp             DateAndTime,
                               xcvrCrntPMTempValidity              PMValidity,
                               xcvrCrntPMSupplyVoltageValue        FixedX10,
                               xcvrCrntPMSupplyVoltageTimeStamp    DateAndTime,
                               xcvrCrntPMSupplyVoltageValidity     PMValidity,
                               xcvrCrntPMLBCValue                  INTEGER,
                               xcvrCrntPMLBCTimeStamp              DateAndTime,
                               xcvrCrntPMLBCValidity               PMValidity,
                               xcvrCrntPMCVSValue                  Unsigned32,
                               xcvrCrntPMCVSTimeStamp              DateAndTime,
                               xcvrCrntPMCVSValidity               PMValidity,
                               xcvrCrntPMESSValue                  Unsigned32,
                               xcvrCrntPMESSTimeStamp              DateAndTime,
                               xcvrCrntPMESSValidity               PMValidity,
                               xcvrCrntPMSESSValue                 Unsigned32,
                               xcvrCrntPMSESSTimeStamp             DateAndTime,
                               xcvrCrntPMSESSValidity              PMValidity,
                               xcvrCrntPMSEFSSValue                Unsigned32,
                               xcvrCrntPMSEFSSTimeStamp            DateAndTime,
                               xcvrCrntPMSEFSSValidity             PMValidity,
                               xcvrCrntPMRSEBValue                 Unsigned32,
                               xcvrCrntPMRSEBTimeStamp             DateAndTime,
                               xcvrCrntPMRSEBValidity              PMValidity,
                               xcvrCrntPMRSBBEValue                Unsigned32,
                               xcvrCrntPMRSBBETimeStamp            DateAndTime,
                               xcvrCrntPMRSBBEValidity             PMValidity,
                               xcvrCrntPMRSESValue                 Unsigned32,
                               xcvrCrntPMRSESTimeStamp             DateAndTime,
                               xcvrCrntPMRSESValidity              PMValidity,
                               xcvrCrntPMRSSESValue                Unsigned32,
                               xcvrCrntPMRSSESTimeStamp            DateAndTime,
                               xcvrCrntPMRSSESValidity             PMValidity,
                               xcvrCrntPMRSOFSValue                Unsigned32,
                               xcvrCrntPMRSOFSTimeStamp            DateAndTime,
                               xcvrCrntPMRSOFSValidity             PMValidity,
                               xcvrCrntPMCVValue                   Unsigned32,
                               xcvrCrntPMCVTimeStamp               DateAndTime,
                               xcvrCrntPMCVValidity                PMValidity,
                               xcvrCrntPMESValue                   Unsigned32,
                               xcvrCrntPMESTimeStamp               DateAndTime,
                               xcvrCrntPMESValidity                PMValidity,
                               xcvrCrntPMSESValue                  Unsigned32,
                               xcvrCrntPMSESTimeStamp              DateAndTime,
                               xcvrCrntPMSESValidity               PMValidity,
                               xcvrCrntPMINVBLKValue               Unsigned32,
                               xcvrCrntPMINVBLKTimeStamp           DateAndTime,
                               xcvrCrntPMINVBLKValidity            PMValidity,
                               xcvrCrntPMNBITCRValue               Unsigned32,
                               xcvrCrntPMNBITCRTimeStamp           DateAndTime,
                               xcvrCrntPMNBITCRValidity            PMValidity,
                               xcvrCrntPMNBYTCRValue               Unsigned32,
                               xcvrCrntPMNBYTCRTimeStamp           DateAndTime,
                               xcvrCrntPMNBYTCRValidity            PMValidity,
                               xcvrCrntPMUNCRCDWValue              Unsigned32,
                               xcvrCrntPMUNCRCDWTimeStamp          DateAndTime,
                               xcvrCrntPMUNCRCDWValidity           PMValidity,
                               xcvrCrntPMTBYCRXValue               Unsigned64,
                               xcvrCrntPMTBYCRXTimeStamp           DateAndTime,
                               xcvrCrntPMTBYCRXValidity            PMValidity,
                               xcvrCrntPMTBYCRXInitialize          InitializeCmd,
                               xcvrCrntPMTFRCRXValue               Unsigned64,
                               xcvrCrntPMTFRCRXTimeStamp           DateAndTime,
                               xcvrCrntPMTFRCRXValidity            PMValidity,
                               xcvrCrntPMTFRCRXInitialize          InitializeCmd,
                               xcvrCrntPMBCSTValue                 Unsigned64,
                               xcvrCrntPMBCSTTimeStamp             DateAndTime,
                               xcvrCrntPMBCSTValidity              PMValidity,
                               xcvrCrntPMBCSTInitialize            InitializeCmd,
                               xcvrCrntPMMCSTValue                 Unsigned64,
                               xcvrCrntPMMCSTTimeStamp             DateAndTime,
                               xcvrCrntPMMCSTValidity              PMValidity,
                               xcvrCrntPMMCSTInitialize            InitializeCmd,
                               xcvrCrntPMSIZE64Value               Unsigned64,
                               xcvrCrntPMSIZE64TimeStamp           DateAndTime,
                               xcvrCrntPMSIZE64Validity            PMValidity,
                               xcvrCrntPMSIZE64Initialize          InitializeCmd,
                               xcvrCrntPMSIZE65To127Value          Unsigned64,
                               xcvrCrntPMSIZE65To127TimeStamp      DateAndTime,
                               xcvrCrntPMSIZE65To127Validity       PMValidity,
                               xcvrCrntPMSIZE65To127Initialize     InitializeCmd,
                               xcvrCrntPMSIZE128To255Value         Unsigned64,
                               xcvrCrntPMSIZE128To255TimeStamp     DateAndTime,
                               xcvrCrntPMSIZE128To255Validity      PMValidity,
                               xcvrCrntPMSIZE128To255Initialize    InitializeCmd,
                               xcvrCrntPMSIZE256To511Value         Unsigned64,
                               xcvrCrntPMSIZE256To511TimeStamp     DateAndTime,
                               xcvrCrntPMSIZE256To511Validity      PMValidity,
                               xcvrCrntPMSIZE256To511Initialize    InitializeCmd,
                               xcvrCrntPMSIZE512To1023Value        Unsigned64,
                               xcvrCrntPMSIZE512To1023TimeStamp    DateAndTime,
                               xcvrCrntPMSIZE512To1023Validity     PMValidity,
                               xcvrCrntPMSIZE512To1023Initialize   InitializeCmd,
                               xcvrCrntPMSIZE1024To1518Value       Unsigned64,
                               xcvrCrntPMSIZE1024To1518TimeStamp   DateAndTime,
                               xcvrCrntPMSIZE1024To1518Validity    PMValidity,
                               xcvrCrntPMSIZE1024To1518Initialize  InitializeCmd,
                               xcvrCrntPMSIZEOver1518Value         Unsigned64,
                               xcvrCrntPMSIZEOver1518TimeStamp     DateAndTime,
                               xcvrCrntPMSIZEOver1518Validity      PMValidity,
                               xcvrCrntPMSIZEOver1518Initialize    InitializeCmd,
                               xcvrCrntPMFCSEValue                 Unsigned32,
                               xcvrCrntPMFCSETimeStamp             DateAndTime,
                               xcvrCrntPMFCSEValidity              PMValidity,
                               xcvrCrntPMFRDRValue                 Unsigned32,
                               xcvrCrntPMFRDRTimeStamp             DateAndTime,
                               xcvrCrntPMFRDRValidity              PMValidity,
                               xcvrCrntPMUSIZEValue                Unsigned32,
                               xcvrCrntPMUSIZETimeStamp            DateAndTime,
                               xcvrCrntPMUSIZEValidity             PMValidity,
                               xcvrCrntPMOSIZEValue                Unsigned32,
                               xcvrCrntPMOSIZETimeStamp            DateAndTime,
                               xcvrCrntPMOSIZEValidity             PMValidity,
                               xcvrCrntPMFRGTValue                 Unsigned32,
                               xcvrCrntPMFRGTTimeStamp             DateAndTime,
                               xcvrCrntPMFRGTValidity              PMValidity,
                               xcvrCrntPMJABRValue                 Unsigned32,
                               xcvrCrntPMJABRTimeStamp             DateAndTime,
                               xcvrCrntPMJABRValidity              PMValidity,
                               xcvrCrntPMOTUEBValue                Unsigned32,
                               xcvrCrntPMOTUEBTimeStamp            DateAndTime,
                               xcvrCrntPMOTUEBValidity             PMValidity,
                               xcvrCrntPMOTUBBEValue               Unsigned32,
                               xcvrCrntPMOTUBBETimeStamp           DateAndTime,
                               xcvrCrntPMOTUBBEValidity            PMValidity,
                               xcvrCrntPMOTUESValue                Unsigned32,
                               xcvrCrntPMOTUESTimeStamp            DateAndTime,
                               xcvrCrntPMOTUESValidity             PMValidity,
                               xcvrCrntPMOTUSESValue               Unsigned32,
                               xcvrCrntPMOTUSESTimeStamp           DateAndTime,
                               xcvrCrntPMOTUSESValidity            PMValidity,
                               xcvrCrntPMOTUOFSValue               Unsigned32,
                               xcvrCrntPMOTUOFSTimeStamp           DateAndTime,
                               xcvrCrntPMOTUOFSValidity            PMValidity,
                               xcvrCrntPMSupplyVoltage2Value       FixedX10,
                               xcvrCrntPMSupplyVoltage2TimeStamp   DateAndTime,
                               xcvrCrntPMSupplyVoltage2Validity    PMValidity,
                               xcvrCrntPMCVSInitialize             InitializeCmd,
                               xcvrCrntPMESSInitialize             InitializeCmd,
                               xcvrCrntPMSESSInitialize            InitializeCmd,
                               xcvrCrntPMSEFSSInitialize           InitializeCmd,
                               xcvrCrntPMRSEBInitialize            InitializeCmd,
                               xcvrCrntPMRSBBEInitialize           InitializeCmd,
                               xcvrCrntPMRSESInitialize            InitializeCmd,
                               xcvrCrntPMRSSESInitialize           InitializeCmd,
                               xcvrCrntPMRSOFSInitialize           InitializeCmd,
                               xcvrCrntPMCVInitialize              InitializeCmd,
                               xcvrCrntPMESInitialize              InitializeCmd,
                               xcvrCrntPMSESInitialize             InitializeCmd,
                               xcvrCrntPMINVBLKInitialize          InitializeCmd,
                               xcvrCrntPMNBITCRInitialize          InitializeCmd,
                               xcvrCrntPMNBYTCRInitialize          InitializeCmd,
                               xcvrCrntPMUNCRCDWInitialize         InitializeCmd,
                               xcvrCrntPMFCSEInitialize            InitializeCmd,
                               xcvrCrntPMFRDRInitialize            InitializeCmd,
                               xcvrCrntPMUSIZEInitialize           InitializeCmd,
                               xcvrCrntPMOSIZEInitialize           InitializeCmd,
                               xcvrCrntPMFRGTInitialize            InitializeCmd,
                               xcvrCrntPMJABRInitialize            InitializeCmd,
                               xcvrCrntPMOTUEBInitialize           InitializeCmd,
                               xcvrCrntPMOTUBBEInitialize          InitializeCmd,
                               xcvrCrntPMOTUESInitialize           InitializeCmd,
                               xcvrCrntPMOTUSESInitialize          InitializeCmd,
                               xcvrCrntPMOTUOFSInitialize          InitializeCmd,
                               xcvrCrntPMUASSValue                 Unsigned32,
                               xcvrCrntPMUASSTimeStamp             DateAndTime,
                               xcvrCrntPMUASSValidity              PMValidity,
                               xcvrCrntPMUASSInitialize            InitializeCmd,
                               xcvrCrntPMRSUASValue                Unsigned32,
                               xcvrCrntPMRSUASTimeStamp            DateAndTime,
                               xcvrCrntPMRSUASValidity             PMValidity,
                               xcvrCrntPMRSUASInitialize           InitializeCmd,
                               xcvrCrntPMUASValue                  Unsigned32,
                               xcvrCrntPMUASTimeStamp              DateAndTime,
                               xcvrCrntPMUASValidity               PMValidity,
                               xcvrCrntPMUASInitialize             InitializeCmd,
                               xcvrCrntPMOTUUASValue               Unsigned32,
                               xcvrCrntPMOTUUASTimeStamp           DateAndTime,
                               xcvrCrntPMOTUUASValidity            PMValidity,
                               xcvrCrntPMOTUUASInitialize          InitializeCmd,
                               xcvrCrntPMOTNBERValue               DisplayString,
                               xcvrCrntPMOTNBERTimeStamp           DateAndTime,
                               xcvrCrntPMOTNBERValidity            PMValidity,
                               xcvrCrntPMOTNBERInitialize          InitializeCmd,
                               xcvrCrntPMOTNAVGBERValue            DisplayString,
                               xcvrCrntPMOTNAVGBERTimeStamp        DateAndTime,
                               xcvrCrntPMOTNAVGBERValidity         PMValidity,
                               xcvrCrntPMOTNAVGBERInitialize       InitializeCmd,
                               xcvrCrntPMNBITCR64BitValue          Unsigned64,
                               xcvrCrntPMNBITCR64BitTimeStamp      DateAndTime,
                               xcvrCrntPMNBITCR64BitValidity       PMValidity,
                               xcvrCrntPMNBITCR64BitInitialize     InitializeCmd,
                               xcvrCrntPMNBYTCR64BitValue          Unsigned64,
                               xcvrCrntPMNBYTCR64BitTimeStamp      DateAndTime,
                               xcvrCrntPMNBYTCR64BitValidity       PMValidity,
                               xcvrCrntPMNBYTCR64BitInitialize     InitializeCmd,
                               xcvrCrntPMOPRMinValue               FixedX10,
                               xcvrCrntPMOPRMinTimeStamp           DateAndTime,
                               xcvrCrntPMOPRMinValidity            PMValidity,
                               xcvrCrntPMOPRMinInitialize          InitializeCmd,
                               xcvrCrntPMOPRMaxValue               FixedX10,
                               xcvrCrntPMOPRMaxTimeStamp           DateAndTime,
                               xcvrCrntPMOPRMaxValidity            PMValidity,
                               xcvrCrntPMOPRMaxInitialize          InitializeCmd,
                               xcvrCrntPMOPRAvgValue               FixedX10,
                               xcvrCrntPMOPRAvgTimeStamp           DateAndTime,
                               xcvrCrntPMOPRAvgValidity            PMValidity,
                               xcvrCrntPMOPRAvgInitialize          InitializeCmd,
                               xcvrCrntPMOPTMinValue               FixedX10,
                               xcvrCrntPMOPTMinTimeStamp           DateAndTime,
                               xcvrCrntPMOPTMinValidity            PMValidity,
                               xcvrCrntPMOPTMinInitialize          InitializeCmd,
                               xcvrCrntPMOPTMaxValue               FixedX10,
                               xcvrCrntPMOPTMaxTimeStamp           DateAndTime,
                               xcvrCrntPMOPTMaxValidity            PMValidity,
                               xcvrCrntPMOPTMaxInitialize          InitializeCmd,
                               xcvrCrntPMOPTAvgValue               FixedX10,
                               xcvrCrntPMOPTAvgTimeStamp           DateAndTime,
                               xcvrCrntPMOPTAvgValidity            PMValidity,
                               xcvrCrntPMOPTAvgInitialize          InitializeCmd }


xcvrCrntPMTypeIdx OBJECT-TYPE
    SYNTAX       XcvrType
    MAX-ACCESS   not-accessible
    STATUS       current
    DESCRIPTION  "The type of the optical transceiver targeted for PMs."
    ::= { xcvrCrntPMEntry 1 }


xcvrCrntPMShelfIdx OBJECT-TYPE
    SYNTAX       INTEGER (1|11|21|31)
    MAX-ACCESS   not-accessible
    STATUS       current
    DESCRIPTION  "The shelf number on which the optical transceiver targeted for
                  PMs is provisioned."
    ::= { xcvrCrntPMEntry 2 }


xcvrCrntPMSlotIdx OBJECT-TYPE
    SYNTAX       INTEGER (1..20)
    MAX-ACCESS   not-accessible
    STATUS       current
    DESCRIPTION  "The slot number on which the optical transceiver targeted for
                  PMs is provisioned."
    ::= { xcvrCrntPMEntry 3 }


xcvrCrntPMIdx OBJECT-TYPE
    SYNTAX       INTEGER (1..4)
    MAX-ACCESS   not-accessible
    STATUS       current
    DESCRIPTION  "The optical transceiver port number on the circuit pack that
                  is targeted for PMs."
    ::= { xcvrCrntPMEntry 4 }


xcvrCrntPMIntervalTypeIdx OBJECT-TYPE
    SYNTAX       PMIntervalType
    MAX-ACCESS   not-accessible
    STATUS       current
    DESCRIPTION  "The type of PM bin according to interval length."
    ::= { xcvrCrntPMEntry 5 }


xcvrCrntPMOPRValue OBJECT-TYPE
    SYNTAX       FixedX10
    UNITS        "dBm/10"
    MAX-ACCESS   read-only
    STATUS       current
    DESCRIPTION  "The optical power received on the input of the transceiver."
    ::= { xcvrCrntPMEntry 6 }


xcvrCrntPMOPRTimeStamp OBJECT-TYPE
    SYNTAX       DateAndTime
    MAX-ACCESS   read-only
    STATUS       current
    DESCRIPTION  "The date and time stamp of the optical power received value."
    ::= { xcvrCrntPMEntry 7 }


xcvrCrntPMOPRValidity OBJECT-TYPE
    SYNTAX       PMValidity
    MAX-ACCESS   read-only
    STATUS       current
    DESCRIPTION  "Indicates the validity of the provided optical power received
                  value."
    ::= { xcvrCrntPMEntry 8 }


xcvrCrntPMOPTValue OBJECT-TYPE
    SYNTAX       FixedX10
    UNITS        "dBm/10"
    MAX-ACCESS   read-only
    STATUS       current
    DESCRIPTION  "The optical power transmitted at the output of the
                  transceiver."
    ::= { xcvrCrntPMEntry 9 }


xcvrCrntPMOPTTimeStamp OBJECT-TYPE
    SYNTAX       DateAndTime
    MAX-ACCESS   read-only
    STATUS       current
    DESCRIPTION  "The date and time stamp of the optical power transmitted
                  value."
    ::= { xcvrCrntPMEntry 10 }


xcvrCrntPMOPTValidity OBJECT-TYPE
    SYNTAX       PMValidity
    MAX-ACCESS   read-only
    STATUS       current
    DESCRIPTION  "Indicates the validity of the provided optical power
                  transmitted value."
    ::= { xcvrCrntPMEntry 11 }


xcvrCrntPMTempValue OBJECT-TYPE
    SYNTAX       INTEGER (-32768..32767)
    UNITS        "degrees Celsius"
    MAX-ACCESS   read-only
    STATUS       current
    DESCRIPTION  "The optical transceiver temperature."
    ::= { xcvrCrntPMEntry 12 }


xcvrCrntPMTempTimeStamp OBJECT-TYPE
    SYNTAX       DateAndTime
    MAX-ACCESS   read-only
    STATUS       current
    DESCRIPTION  "The date and time stamp of the temperature value."
    ::= { xcvrCrntPMEntry 13 }


xcvrCrntPMTempValidity OBJECT-TYPE
    SYNTAX       PMValidity
    MAX-ACCESS   read-only
    STATUS       current
    DESCRIPTION  "Indicates the validity of the provided temperature value."
    ::= { xcvrCrntPMEntry 14 }


xcvrCrntPMSupplyVoltageValue OBJECT-TYPE
    SYNTAX       FixedX10
    UNITS        "mVolts/10"
    MAX-ACCESS   read-only
    STATUS       current
    DESCRIPTION  "The transceiver supply voltage."
    ::= { xcvrCrntPMEntry 15 }


xcvrCrntPMSupplyVoltageTimeStamp OBJECT-TYPE
    SYNTAX       DateAndTime
    MAX-ACCESS   read-only
    STATUS       current
    DESCRIPTION  "The date and time stamp of the supply voltage value."
    ::= { xcvrCrntPMEntry 16 }


xcvrCrntPMSupplyVoltageValidity OBJECT-TYPE
    SYNTAX       PMValidity
    MAX-ACCESS   read-only
    STATUS       current
    DESCRIPTION  "Indicates the validity of the provided supply voltage value."
    ::= { xcvrCrntPMEntry 17 }


xcvrCrntPMLBCValue OBJECT-TYPE
    SYNTAX       INTEGER (-32768..32767)
    UNITS        "mAmp"
    MAX-ACCESS   read-only
    STATUS       current
    DESCRIPTION  "The transceiver laser bias current."
    ::= { xcvrCrntPMEntry 18 }


xcvrCrntPMLBCTimeStamp OBJECT-TYPE
    SYNTAX       DateAndTime
    MAX-ACCESS   read-only
    STATUS       current
    DESCRIPTION  "The date and time stamp of the laser bias current value."
    ::= { xcvrCrntPMEntry 19 }


xcvrCrntPMLBCValidity OBJECT-TYPE
    SYNTAX       PMValidity
    MAX-ACCESS   read-only
    STATUS       current
    DESCRIPTION  "Indicates the validity of the provided laser bias current
                  value."
    ::= { xcvrCrntPMEntry 20 }


xcvrCrntPMCVSValue OBJECT-TYPE
    SYNTAX       Unsigned32 
    MAX-ACCESS   read-write
    STATUS       current
    DESCRIPTION  "The count of coding violations at the section layer. This
                  object applies only to transciever ports provisioned for a
                  SONET OC-N protocol."
    ::= { xcvrCrntPMEntry 21 }


xcvrCrntPMCVSTimeStamp OBJECT-TYPE
    SYNTAX       DateAndTime
    MAX-ACCESS   read-only
    STATUS       current
    DESCRIPTION  "The date and time stamp of the section layer coding violations
                  value."
    ::= { xcvrCrntPMEntry 22 }


xcvrCrntPMCVSValidity OBJECT-TYPE
    SYNTAX       PMValidity
    MAX-ACCESS   read-only
    STATUS       current
    DESCRIPTION  "Indicates the validity of the provided section layer coding
                  violations value."
    ::= { xcvrCrntPMEntry 23 }


xcvrCrntPMESSValue OBJECT-TYPE
    SYNTAX       Unsigned32
    MAX-ACCESS   read-write
    STATUS       current
    DESCRIPTION  "The count of errored seconds at the section layer. This object
                  applies only to transciever ports provisioned for a SONET OC-N
                  protocol."
    ::= { xcvrCrntPMEntry 24 }


xcvrCrntPMESSTimeStamp OBJECT-TYPE
    SYNTAX       DateAndTime
    MAX-ACCESS   read-only
    STATUS       current
    DESCRIPTION  "The date and time stamp of the section layer errored seconds
                  value."
    ::= { xcvrCrntPMEntry 25 }


xcvrCrntPMESSValidity OBJECT-TYPE
    SYNTAX       PMValidity
    MAX-ACCESS   read-only
    STATUS       current
    DESCRIPTION  "Indicates the validity of the provided section layer errored
                  seconds value."
    ::= { xcvrCrntPMEntry 26 }


xcvrCrntPMSESSValue OBJECT-TYPE
    SYNTAX       Unsigned32
    MAX-ACCESS   read-write
    STATUS       current
    DESCRIPTION  "The count of severely errored seconds at the section layer.
                  This object applies only to transciever ports provisioned for
                  a SONET OC-N protocol."
    ::= { xcvrCrntPMEntry 27 }


xcvrCrntPMSESSTimeStamp OBJECT-TYPE
    SYNTAX       DateAndTime
    MAX-ACCESS   read-only
    STATUS       current
    DESCRIPTION  "The date and time stamp of the section layer severely errored
                  seconds value."
    ::= { xcvrCrntPMEntry 28 }


xcvrCrntPMSESSValidity OBJECT-TYPE
    SYNTAX       PMValidity
    MAX-ACCESS   read-only
    STATUS       current
    DESCRIPTION  "Indicates the validity of the provided section layer severely
                  errored seconds value."
    ::= { xcvrCrntPMEntry 29 }


xcvrCrntPMSEFSSValue OBJECT-TYPE
    SYNTAX       Unsigned32
    MAX-ACCESS   read-write
    STATUS       current
    DESCRIPTION  "The count of severely errored framing seconds at the section
                  layer. This object applies only to transciever ports
                  provisioned for a SONET OC-N protocol."
    ::= { xcvrCrntPMEntry 30 }


xcvrCrntPMSEFSSTimeStamp OBJECT-TYPE
    SYNTAX       DateAndTime
    MAX-ACCESS   read-only
    STATUS       current
    DESCRIPTION  "The date and time stamp of the section layer severely errored
                  framing seconds value."
    ::= { xcvrCrntPMEntry 31 }


xcvrCrntPMSEFSSValidity OBJECT-TYPE
    SYNTAX       PMValidity
    MAX-ACCESS   read-only
    STATUS       current
    DESCRIPTION  "Indicates the validity of the provided section layer severely
                  errored framing seconds value."
    ::= { xcvrCrntPMEntry 32 }


xcvrCrntPMRSEBValue OBJECT-TYPE
    SYNTAX       Unsigned32
    MAX-ACCESS   read-write
    STATUS       current
    DESCRIPTION  "The count of regenerator section errored blocks. This object
                  applies only to transciever ports provisioned for a SDH STM-N
                  protocol."
    ::= { xcvrCrntPMEntry 33 }


xcvrCrntPMRSEBTimeStamp OBJECT-TYPE
    SYNTAX       DateAndTime
    MAX-ACCESS   read-only
    STATUS       current
    DESCRIPTION  "The date and time stamp of the regenerator section errored
                  blocks value."
    ::= { xcvrCrntPMEntry 34 }


xcvrCrntPMRSEBValidity OBJECT-TYPE
    SYNTAX       PMValidity
    MAX-ACCESS   read-only
    STATUS       current
    DESCRIPTION  "Indicates the validity of the provided regenerator section
                  errored blocks value."
    ::= { xcvrCrntPMEntry 35 }


xcvrCrntPMRSBBEValue OBJECT-TYPE
    SYNTAX       Unsigned32
    MAX-ACCESS   read-write
    STATUS       current
    DESCRIPTION  "The count of regenerator section background block errors. This
                  object applies only to transciever ports provisioned for a SDH
                  STM-N protocol."
    ::= { xcvrCrntPMEntry 36 }


xcvrCrntPMRSBBETimeStamp OBJECT-TYPE
    SYNTAX       DateAndTime
    MAX-ACCESS   read-only
    STATUS       current
    DESCRIPTION  "The date and time stamp of the regenerator section background
                  block errors value."
    ::= { xcvrCrntPMEntry 37 }


xcvrCrntPMRSBBEValidity OBJECT-TYPE
    SYNTAX       PMValidity
    MAX-ACCESS   read-only
    STATUS       current
    DESCRIPTION  "Indicates the validity of the provided regenerator section
                  background block errors value."
    ::= { xcvrCrntPMEntry 38 }


xcvrCrntPMRSESValue OBJECT-TYPE
    SYNTAX       Unsigned32
    MAX-ACCESS   read-write
    STATUS       current
    DESCRIPTION  "The count of regenerator section errored seconds. This object
                  applies only to transciever ports provisioned for a SDH STM-N
                  protocol."
    ::= { xcvrCrntPMEntry 39 }


xcvrCrntPMRSESTimeStamp OBJECT-TYPE
    SYNTAX       DateAndTime
    MAX-ACCESS   read-only
    STATUS       current
    DESCRIPTION  "The date and time stamp of the regenerator section errored
                  seconds value."
    ::= { xcvrCrntPMEntry 40 }


xcvrCrntPMRSESValidity OBJECT-TYPE
    SYNTAX       PMValidity
    MAX-ACCESS   read-only
    STATUS       current
    DESCRIPTION  "Indicates the validity of the provided regenerator section
                  errored seconds value."
    ::= { xcvrCrntPMEntry 41 }


xcvrCrntPMRSSESValue OBJECT-TYPE
    SYNTAX       Unsigned32
    MAX-ACCESS   read-write
    STATUS       current
    DESCRIPTION  "The count of regenerator section severely errored seconds.
                  This object applies only to transciever ports provisioned for
                  a SDH STM-N protocol."
    ::= { xcvrCrntPMEntry 42 }


xcvrCrntPMRSSESTimeStamp OBJECT-TYPE
    SYNTAX       DateAndTime
    MAX-ACCESS   read-only
    STATUS       current
    DESCRIPTION  "The date and time stamp of the regenerator section severely
                  errored seconds value."
    ::= { xcvrCrntPMEntry 43 }


xcvrCrntPMRSSESValidity OBJECT-TYPE
    SYNTAX       PMValidity
    MAX-ACCESS   read-only
    STATUS       current
    DESCRIPTION  "Indicates the validity of the provided regenerator section
                  severely errored seconds value."
    ::= { xcvrCrntPMEntry 44 }


xcvrCrntPMRSOFSValue OBJECT-TYPE
    SYNTAX       Unsigned32
    MAX-ACCESS   read-write
    STATUS       current
    DESCRIPTION  "The count of regenerator section out-of-frame seconds. This
                  object applies only to transciever ports provisioned for a SDH
                  STM-N protocol."
    ::= { xcvrCrntPMEntry 45 }


xcvrCrntPMRSOFSTimeStamp OBJECT-TYPE
    SYNTAX       DateAndTime
    MAX-ACCESS   read-only
    STATUS       current
    DESCRIPTION  "The date and time stamp of the regenerator section
                  out-of-frame seconds value."
    ::= { xcvrCrntPMEntry 46 }


xcvrCrntPMRSOFSValidity OBJECT-TYPE
    SYNTAX       PMValidity
    MAX-ACCESS   read-only
    STATUS       current
    DESCRIPTION  "Indicates the validity of the provided regenerator section
                  out-of-frame seconds value."
    ::= { xcvrCrntPMEntry 47 }


xcvrCrntPMCVValue OBJECT-TYPE
    SYNTAX       Unsigned32
    MAX-ACCESS   read-write
    STATUS       current
    DESCRIPTION  "The count of coding violations. This object applies only to
                  transciever ports provisioned for the gigabit ethernet
                  protocol or a fiber channel protocol."
    ::= { xcvrCrntPMEntry 48 }


xcvrCrntPMCVTimeStamp OBJECT-TYPE
    SYNTAX       DateAndTime
    MAX-ACCESS   read-only
    STATUS       current
    DESCRIPTION  "The date and time stamp of the coding violations value."
    ::= { xcvrCrntPMEntry 49 }


xcvrCrntPMCVValidity OBJECT-TYPE
    SYNTAX       PMValidity
    MAX-ACCESS   read-only
    STATUS       current
    DESCRIPTION  "Indicates the validity of the provided coding violations
                  value."
    ::= { xcvrCrntPMEntry 50 }


xcvrCrntPMESValue OBJECT-TYPE
    SYNTAX       Unsigned32
    MAX-ACCESS   read-write
    STATUS       current
    DESCRIPTION  "The count of errored seconds. This object applies only to
                  transciever ports provisioned for an ethernet protocol
                  or a fiber channel protocol."
    ::= { xcvrCrntPMEntry 51 }


xcvrCrntPMESTimeStamp OBJECT-TYPE
    SYNTAX       DateAndTime
    MAX-ACCESS   read-only
    STATUS       current
    DESCRIPTION  "The date and time stamp of the errored seconds value."
    ::= { xcvrCrntPMEntry 52 }


xcvrCrntPMESValidity OBJECT-TYPE
    SYNTAX       PMValidity
    MAX-ACCESS   read-only
    STATUS       current
    DESCRIPTION  "Indicates the validity of the provided errored seconds value."
    ::= { xcvrCrntPMEntry 53 }


xcvrCrntPMSESValue OBJECT-TYPE
    SYNTAX       Unsigned32
    MAX-ACCESS   read-write
    STATUS       current
    DESCRIPTION  "The count of severely errored seconds. This object applies
                  only to transciever ports provisioned for an ethernet
                  protocol or a fiber channel protocol."
    ::= { xcvrCrntPMEntry 54 }


xcvrCrntPMSESTimeStamp OBJECT-TYPE
    SYNTAX       DateAndTime
    MAX-ACCESS   read-only
    STATUS       current
    DESCRIPTION  "The date and time stamp of the severely errored seconds
                  value."
    ::= { xcvrCrntPMEntry 55 }


xcvrCrntPMSESValidity OBJECT-TYPE
    SYNTAX       PMValidity
    MAX-ACCESS   read-only
    STATUS       current
    DESCRIPTION  "Indicates the validity of the provided severely errored
                  seconds value."
    ::= { xcvrCrntPMEntry 56 }


xcvrCrntPMINVBLKValue OBJECT-TYPE
    SYNTAX       Unsigned32
    MAX-ACCESS   read-write
    STATUS       current
    DESCRIPTION  "The count of invalid blocks. This object applies only to
                  transciever ports provisioned for the 10 gigabit ethernet LAN
                  protocol."
    ::= { xcvrCrntPMEntry 57 }


xcvrCrntPMINVBLKTimeStamp OBJECT-TYPE
    SYNTAX       DateAndTime
    MAX-ACCESS   read-only
    STATUS       current
    DESCRIPTION  "The date and time stamp of the invalid blocks value."
    ::= { xcvrCrntPMEntry 58 }


xcvrCrntPMINVBLKValidity OBJECT-TYPE
    SYNTAX       PMValidity
    MAX-ACCESS   read-only
    STATUS       current
    DESCRIPTION  "Indicates the validity of the provided invalid blocks value."
    ::= { xcvrCrntPMEntry 59 }


xcvrCrntPMNBITCRValue OBJECT-TYPE
    SYNTAX       Unsigned32
    MAX-ACCESS   read-write
    STATUS       current
    DESCRIPTION  "The count of the number of bits corrected. This object
                  applies only to transciever ports provisioned for a protocol
                  that includes Forward Error Correction (FEC)."
    ::= { xcvrCrntPMEntry 60 }


xcvrCrntPMNBITCRTimeStamp OBJECT-TYPE
    SYNTAX       DateAndTime
    MAX-ACCESS   read-only
    STATUS       current
    DESCRIPTION  "The date and time stamp of the number of bits corrected
                  value."
    ::= { xcvrCrntPMEntry 61 }


xcvrCrntPMNBITCRValidity OBJECT-TYPE
    SYNTAX       PMValidity
    MAX-ACCESS   read-only
    STATUS       current
    DESCRIPTION  "Indicates the validity of the provided number of bits
                  corrected value."
    ::= { xcvrCrntPMEntry 62 }


xcvrCrntPMNBYTCRValue OBJECT-TYPE
    SYNTAX       Unsigned32
    MAX-ACCESS   read-write
    STATUS       current
    DESCRIPTION  "The count of the number of bytes corrected. This object
                  applies only to transciever ports provisioned for a protocol
                  that includes Forward Error Correction (FEC)."
    ::= { xcvrCrntPMEntry 63 }


xcvrCrntPMNBYTCRTimeStamp OBJECT-TYPE
    SYNTAX       DateAndTime
    MAX-ACCESS   read-only
    STATUS       current
    DESCRIPTION  "The date and time stamp of the number of bytes corrected
                  value."
    ::= { xcvrCrntPMEntry 64 }


xcvrCrntPMNBYTCRValidity OBJECT-TYPE
    SYNTAX       PMValidity
    MAX-ACCESS   read-only
    STATUS       current
    DESCRIPTION  "Indicates the validity of the provided number of bytes
                  corrected value."
    ::= { xcvrCrntPMEntry 65 }


xcvrCrntPMUNCRCDWValue OBJECT-TYPE
    SYNTAX       Unsigned32
    MAX-ACCESS   read-write
    STATUS       current
    DESCRIPTION  "The count of uncorrectable codewords. This object
                  applies only to transciever ports provisioned for a protocol
                  that includes Forward Error Correction (FEC)."
    ::= { xcvrCrntPMEntry 66 }


xcvrCrntPMUNCRCDWTimeStamp OBJECT-TYPE
    SYNTAX       DateAndTime
    MAX-ACCESS   read-only
    STATUS       current
    DESCRIPTION  "The date and time stamp of the uncorrectable codewords value."
    ::= { xcvrCrntPMEntry 67 }


xcvrCrntPMUNCRCDWValidity OBJECT-TYPE
    SYNTAX       PMValidity
    MAX-ACCESS   read-only
    STATUS       current
    DESCRIPTION  "Indicates the validity of the provided uncorrectable codewords
                  value."
    ::= { xcvrCrntPMEntry 68 }


xcvrCrntPMTBYCRXValue OBJECT-TYPE
    SYNTAX       Unsigned64
    MAX-ACCESS   read-only
    STATUS       current
    DESCRIPTION  "The total number of bytes of data (including those in bad
                  frames) received (excluding framing bits but including FCS
                  octets). This object applies only to transceiver ports
                  provisioned for the 10 gigabit ethernet LAN protocol."
    ::= { xcvrCrntPMEntry 69 }


xcvrCrntPMTBYCRXTimeStamp OBJECT-TYPE
    SYNTAX       DateAndTime
    MAX-ACCESS   read-only
    STATUS       current
    DESCRIPTION  "The date and time stamp of the received bytes count value."
    ::= { xcvrCrntPMEntry 70 }


xcvrCrntPMTBYCRXValidity OBJECT-TYPE
    SYNTAX       PMValidity
    MAX-ACCESS   read-only
    STATUS       current
    DESCRIPTION  "Indicates the validity of the provided received bytes count
                  value."
    ::= { xcvrCrntPMEntry 71 }


xcvrCrntPMTBYCRXInitialize OBJECT-TYPE
    SYNTAX       InitializeCmd
    MAX-ACCESS   read-write
    STATUS       current
    DESCRIPTION  "Used to initialize the value of the xcvrCrntPMTBYCRXValue
                  object to 0."
    ::= { xcvrCrntPMEntry 72 }


xcvrCrntPMTFRCRXValue OBJECT-TYPE
    SYNTAX       Unsigned64
    MAX-ACCESS   read-only
    STATUS       current
    DESCRIPTION  "The total number of received frames (incl. bad frames,
                  broadcast frames, and multicast frames received). This object
                  applies only to transceiver ports provisioned for the 10
                  gigabit ethernet LAN protocol."
    ::= { xcvrCrntPMEntry 73 }


xcvrCrntPMTFRCRXTimeStamp OBJECT-TYPE
    SYNTAX       DateAndTime
    MAX-ACCESS   read-only
    STATUS       current
    DESCRIPTION  "The date and time stamp of the total received frames count
                  value."
    ::= { xcvrCrntPMEntry 74 }


xcvrCrntPMTFRCRXValidity OBJECT-TYPE
    SYNTAX       PMValidity
    MAX-ACCESS   read-only
    STATUS       current
    DESCRIPTION  "Indicates the validity of the provided received frames count
                  value."
    ::= { xcvrCrntPMEntry 75 }


xcvrCrntPMTFRCRXInitialize OBJECT-TYPE
    SYNTAX       InitializeCmd
    MAX-ACCESS   read-write
    STATUS       current
    DESCRIPTION  "Used to initialize the value of the xcvrCrntPMTFRCRXValue
                  object to 0."
    ::= { xcvrCrntPMEntry 76 }


xcvrCrntPMBCSTValue OBJECT-TYPE
    SYNTAX       Unsigned64
    MAX-ACCESS   read-only
    STATUS       current
    DESCRIPTION  "The total number of good frames received that were directed to
                  the broadcast address. Note that this does not include
                  multicast frames. This object applies only to transceiver
                  ports provisioned for the 10 gigabit ethernet LAN protocol."
    ::= { xcvrCrntPMEntry 77 }


xcvrCrntPMBCSTTimeStamp OBJECT-TYPE
    SYNTAX       DateAndTime
    MAX-ACCESS   read-only
    STATUS       current
    DESCRIPTION  "The date and time stamp of the broadcast packets received
                  count value."
    ::= { xcvrCrntPMEntry 78 }


xcvrCrntPMBCSTValidity OBJECT-TYPE
    SYNTAX       PMValidity
    MAX-ACCESS   read-only
    STATUS       current
    DESCRIPTION  "Indicates the validity of the provided broadcast packets
                  received count value."
    ::= { xcvrCrntPMEntry 79 }


xcvrCrntPMBCSTInitialize OBJECT-TYPE
    SYNTAX       InitializeCmd
    MAX-ACCESS   read-write
    STATUS       current
    DESCRIPTION  "Used to initialize the value of the xcvrCrntPMBCSTValue object
                  to 0."
    ::= { xcvrCrntPMEntry 80 }


xcvrCrntPMMCSTValue OBJECT-TYPE
    SYNTAX       Unsigned64
    MAX-ACCESS   read-only
    STATUS       current
    DESCRIPTION  "The total number of good frames received that were directed to
                  a multicast address. Note that this number does not include
                  frames directed to the broadcast address. This object applies
                  only to transceiver ports provisioned for the 10 gigabit
                  ethernet LAN protocol."
    ::= { xcvrCrntPMEntry 81 }


xcvrCrntPMMCSTTimeStamp OBJECT-TYPE
    SYNTAX       DateAndTime
    MAX-ACCESS   read-only
    STATUS       current
    DESCRIPTION  "The date and time stamp of the multicast packets received
                  count value."
    ::= { xcvrCrntPMEntry 82 }


xcvrCrntPMMCSTValidity OBJECT-TYPE
    SYNTAX       PMValidity
    MAX-ACCESS   read-only
    STATUS       current
    DESCRIPTION  "Indicates the validity of the provided multicast packets
                  received count value."
    ::= { xcvrCrntPMEntry 83 }


xcvrCrntPMMCSTInitialize OBJECT-TYPE
    SYNTAX       InitializeCmd
    MAX-ACCESS   read-write
    STATUS       current
    DESCRIPTION  "Used to initialize the value of the xcvrCrntPMMCSTValue object
                  to 0."
    ::= { xcvrCrntPMEntry 84 }


xcvrCrntPMSIZE64Value OBJECT-TYPE
    SYNTAX       Unsigned64
    MAX-ACCESS   read-only
    STATUS       current
    DESCRIPTION  "The total number of 64 byte frames received (excluding framing
                  bits but including FCS octets). This object applies only to
                  transceiver ports provisioned for the 10 gigabit ethernet LAN
                  protocol."
    ::= { xcvrCrntPMEntry 85 }


xcvrCrntPMSIZE64TimeStamp OBJECT-TYPE
    SYNTAX       DateAndTime
    MAX-ACCESS   read-only
    STATUS       current
    DESCRIPTION  "The date and time stamp of the count of 64-byte packets
                  received."
    ::= { xcvrCrntPMEntry 86 }


xcvrCrntPMSIZE64Validity OBJECT-TYPE
    SYNTAX       PMValidity
    MAX-ACCESS   read-only
    STATUS       current
    DESCRIPTION  "Indicates the validity of the provided count of 64-byte
                  packets packets received."
    ::= { xcvrCrntPMEntry 87 }


xcvrCrntPMSIZE64Initialize OBJECT-TYPE
    SYNTAX       InitializeCmd
    MAX-ACCESS   read-write
    STATUS       current
    DESCRIPTION  "Used to initialize the value of the xcvrCrntPMSIZE64Value
                  object to 0."
    ::= { xcvrCrntPMEntry 88 }


xcvrCrntPMSIZE65To127Value OBJECT-TYPE
    SYNTAX       Unsigned64
    MAX-ACCESS   read-only
    STATUS       current
    DESCRIPTION  "The total number of frames received that are 65 to 127 bytes
                  inclusive in length (excluding framing bits but including FCS
                  octets). This object applies only to transceiver ports
                  provisioned for the 10 gigabit ethernet LAN protocol."
    ::= { xcvrCrntPMEntry 89 }


xcvrCrntPMSIZE65To127TimeStamp OBJECT-TYPE
    SYNTAX       DateAndTime
    MAX-ACCESS   read-only
    STATUS       current
    DESCRIPTION  "The date and time stamp of the count of packets between 65 and
                  127 bytes."
    ::= { xcvrCrntPMEntry 90 }


xcvrCrntPMSIZE65To127Validity OBJECT-TYPE
    SYNTAX       PMValidity
    MAX-ACCESS   read-only
    STATUS       current
    DESCRIPTION  "Indicates the validity of the provided count of packets
                  between 65 and 127 bytes."
    ::= { xcvrCrntPMEntry 91 }


xcvrCrntPMSIZE65To127Initialize OBJECT-TYPE
    SYNTAX       InitializeCmd
    MAX-ACCESS   read-write
    STATUS       current
    DESCRIPTION  "Used to initialize the value of the xcvrCrntPMSIZE65To127Value
                  object to 0."
    ::= { xcvrCrntPMEntry 92 }


xcvrCrntPMSIZE128To255Value OBJECT-TYPE
    SYNTAX       Unsigned64
    MAX-ACCESS   read-only
    STATUS       current
    DESCRIPTION  "The total number of frames received that are 128 to 255 bytes
                  inclusive in length (excluding framing bits but including FCS
                  octets). This object applies only to transceiver ports
                  provisioned for the 10 gigabit ethernet LAN protocol."
    ::= { xcvrCrntPMEntry 93 }


xcvrCrntPMSIZE128To255TimeStamp OBJECT-TYPE
    SYNTAX       DateAndTime
    MAX-ACCESS   read-only
    STATUS       current
    DESCRIPTION  "The date and time stamp of the count of packets between 128
                  and 255 bytes."
    ::= { xcvrCrntPMEntry 94 }


xcvrCrntPMSIZE128To255Validity OBJECT-TYPE
    SYNTAX       PMValidity
    MAX-ACCESS   read-only
    STATUS       current
    DESCRIPTION  "Indicates the validity of the provided count of packets
                  between 128 and 255 bytes."
    ::= { xcvrCrntPMEntry 95 }


xcvrCrntPMSIZE128To255Initialize OBJECT-TYPE
    SYNTAX       InitializeCmd
    MAX-ACCESS   read-write
    STATUS       current
    DESCRIPTION  "Used to initialize the value of the
                  xcvrCrntPMSIZE128To255Value object to 0."
    ::= { xcvrCrntPMEntry 96 }


xcvrCrntPMSIZE256To511Value OBJECT-TYPE
    SYNTAX       Unsigned64
    MAX-ACCESS   read-only
    STATUS       current
    DESCRIPTION  "The total number of frames received that are 256 to 511 bytes
                  inclusive in length (excluding framing bits but including FCS
                  octets). This object applies only to transceiver ports
                  provisioned for the 10 gigabit ethernet LAN protocol."
    ::= { xcvrCrntPMEntry 97 }


xcvrCrntPMSIZE256To511TimeStamp OBJECT-TYPE
    SYNTAX       DateAndTime
    MAX-ACCESS   read-only
    STATUS       current
    DESCRIPTION  "The date and time stamp of the count of packets between 256
                  and 511 bytes."
    ::= { xcvrCrntPMEntry 98 }


xcvrCrntPMSIZE256To511Validity OBJECT-TYPE
    SYNTAX       PMValidity
    MAX-ACCESS   read-only
    STATUS       current
    DESCRIPTION  "Indicates the validity of the provided count of packets
                  between 256 and 511 bytes."
    ::= { xcvrCrntPMEntry 99 }


xcvrCrntPMSIZE256To511Initialize OBJECT-TYPE
    SYNTAX       InitializeCmd
    MAX-ACCESS   read-write
    STATUS       current
    DESCRIPTION  "Used to initialize the value of the
                  xcvrCrntPMSIZE256To511Value object to 0."
    ::= { xcvrCrntPMEntry 100 }


xcvrCrntPMSIZE512To1023Value OBJECT-TYPE
    SYNTAX       Unsigned64
    MAX-ACCESS   read-only
    STATUS       current
    DESCRIPTION  "The total number of frames received that are 512 to 1023 bytes
                  inclusive in length (excluding framing bits but including FCS
                  octets). This object applies only to transceiver ports
                  provisioned for the 10 gigabit ethernet LAN protocol."
    ::= { xcvrCrntPMEntry 101 }


xcvrCrntPMSIZE512To1023TimeStamp OBJECT-TYPE
    SYNTAX       DateAndTime
    MAX-ACCESS   read-only
    STATUS       current
    DESCRIPTION  "The date and time stamp of the count of packets between 512
                  and 1023 bytes."
    ::= { xcvrCrntPMEntry 102 }


xcvrCrntPMSIZE512To1023Validity OBJECT-TYPE
    SYNTAX       PMValidity
    MAX-ACCESS   read-only
    STATUS       current
    DESCRIPTION  "Indicates the validity of the provided count of packets
                  between 512 and 1023 bytes."
    ::= { xcvrCrntPMEntry 103 }


xcvrCrntPMSIZE512To1023Initialize OBJECT-TYPE
    SYNTAX       InitializeCmd
    MAX-ACCESS   read-write
    STATUS       current
    DESCRIPTION  "Used to initialize the value of the
                  xcvrCrntPMSIZE512To1023Value object to 0."
    ::= { xcvrCrntPMEntry 104 }


xcvrCrntPMSIZE1024To1518Value OBJECT-TYPE
    SYNTAX       Unsigned64
    MAX-ACCESS   read-only
    STATUS       current
    DESCRIPTION  "The total number of frames received that are 1024 to 1518
                  bytes inclusive in length (excluding framing bits but
                  including FCS octets). This object applies only to transceiver
                  ports provisioned for the 10 gigabit ethernet LAN protocol."
    ::= { xcvrCrntPMEntry 105 }


xcvrCrntPMSIZE1024To1518TimeStamp OBJECT-TYPE
    SYNTAX       DateAndTime
    MAX-ACCESS   read-only
    STATUS       current
    DESCRIPTION  "The date and time stamp of the count of packets between 1024
                  and 1518 bytes."
    ::= { xcvrCrntPMEntry 106 }


xcvrCrntPMSIZE1024To1518Validity OBJECT-TYPE
    SYNTAX       PMValidity
    MAX-ACCESS   read-only
    STATUS       current
    DESCRIPTION  "Indicates the validity of the provided count of packets
                  between 1024 and 1518 bytes."
    ::= { xcvrCrntPMEntry 107 }


xcvrCrntPMSIZE1024To1518Initialize OBJECT-TYPE
    SYNTAX       InitializeCmd
    MAX-ACCESS   read-write
    STATUS       current
    DESCRIPTION  "Used to initialize the value of the
                  xcvrCrntPMSIZE1024To1518Value object to 0."
    ::= { xcvrCrntPMEntry 108 }


xcvrCrntPMSIZEOver1518Value OBJECT-TYPE
    SYNTAX       Unsigned64
    MAX-ACCESS   read-only
    STATUS       current
    DESCRIPTION  "The total number of frames received that are greater than or
                  equal to 1519 bytes in length (excluding framing bits but
                  including FCS octets). This object applies only to transceiver
                  ports provisioned for the 10 gigabit ethernet LAN protocol."
    ::= { xcvrCrntPMEntry 109 }


xcvrCrntPMSIZEOver1518TimeStamp OBJECT-TYPE
    SYNTAX       DateAndTime
    MAX-ACCESS   read-only
    STATUS       current
    DESCRIPTION  "The date and time stamp of the count of packets over 1518
                  bytes."
    ::= { xcvrCrntPMEntry 110 }


xcvrCrntPMSIZEOver1518Validity OBJECT-TYPE
    SYNTAX       PMValidity
    MAX-ACCESS   read-only
    STATUS       current
    DESCRIPTION  "Indicates the validity of the provided count of packets over
                  1518 bytes."
    ::= { xcvrCrntPMEntry 111 }


xcvrCrntPMSIZEOver1518Initialize OBJECT-TYPE
    SYNTAX       InitializeCmd
    MAX-ACCESS   read-write
    STATUS       current
    DESCRIPTION  "Used to initialize the value of the
                  xcvrCrntPMSIZEOver1518Value object to 0."
    ::= { xcvrCrntPMEntry 112 }


xcvrCrntPMFCSEValue OBJECT-TYPE
    SYNTAX       Unsigned32
    MAX-ACCESS   read-write
    STATUS       current
    DESCRIPTION  "The count of packets that had a valid length but had either a
                  Frame Check Sequence (FCS) or a bad FCS with a non-integral
                  number of octets (Alignment Error) . This object applies only
                  to transceiver ports provisioned for the 10 gigabit ethernet
                  LAN protocol."
    ::= { xcvrCrntPMEntry 113 }


xcvrCrntPMFCSETimeStamp OBJECT-TYPE
    SYNTAX       DateAndTime
    MAX-ACCESS   read-only
    STATUS       current
    DESCRIPTION  "The date and time stamp of the count of packets with bad FCS
                  or alignment error."
    ::= { xcvrCrntPMEntry 114 }


xcvrCrntPMFCSEValidity OBJECT-TYPE
    SYNTAX       PMValidity
    MAX-ACCESS   read-only
    STATUS       current
    DESCRIPTION  "Indicates the validity of the provided count of packets with
                  bad FCS or alignment error."
    ::= { xcvrCrntPMEntry 115 }


xcvrCrntPMFRDRValue OBJECT-TYPE
    SYNTAX       Unsigned32
    MAX-ACCESS   read-write
    STATUS       current
    DESCRIPTION  "The total number of dropped frames due to lack of resources or
                  otherwise. Note that this number is not necessarily the number
                  of frames dropped; it is just the number of times that it
                  could be detected. This object applies only to transceiver
                  ports provisioned for the 10 gigabit ethernet LAN protocol."
    ::= { xcvrCrntPMEntry 116 }


xcvrCrntPMFRDRTimeStamp OBJECT-TYPE
    SYNTAX       DateAndTime
    MAX-ACCESS   read-only
    STATUS       current
    DESCRIPTION  "The date and time stamp of the count of dropped packets."
    ::= { xcvrCrntPMEntry 117 }


xcvrCrntPMFRDRValidity OBJECT-TYPE
    SYNTAX       PMValidity
    MAX-ACCESS   read-only
    STATUS       current
    DESCRIPTION  "Indicates the validity of the provided count of dropped
                  packets."
    ::= { xcvrCrntPMEntry 118 }


xcvrCrntPMUSIZEValue OBJECT-TYPE
    SYNTAX       Unsigned32
    MAX-ACCESS   read-write
    STATUS       current
    DESCRIPTION  "The total number of frames received that were less than 64
                  octets long (excluding framing bits, but including FCS octets)
                  and were otherwise well formed. This object applies only to
                  transceiver ports provisioned for the 10 gigabit ethernet LAN
                  protocol."
    ::= { xcvrCrntPMEntry 119 }


xcvrCrntPMUSIZETimeStamp OBJECT-TYPE
    SYNTAX       DateAndTime
    MAX-ACCESS   read-only
    STATUS       current
    DESCRIPTION  "The date and time stamp of the count of undersized packets."
    ::= { xcvrCrntPMEntry 120 }


xcvrCrntPMUSIZEValidity OBJECT-TYPE
    SYNTAX       PMValidity
    MAX-ACCESS   read-only
    STATUS       current
    DESCRIPTION  "Indicates the validity of the provided count of undersized
                  packets."
    ::= { xcvrCrntPMEntry 121 }


xcvrCrntPMOSIZEValue OBJECT-TYPE
    SYNTAX       Unsigned32
    MAX-ACCESS   read-write
    STATUS       current
    DESCRIPTION  "The total number of frames received that were longer than 9600
                  octets (excluding framing bits, but including FCS octets) and
                  were otherwise well formed. This object applies only to
                  transceiver ports provisioned for the 10 gigabit ethernet LAN
                  protocol."
    ::= { xcvrCrntPMEntry 122 }


xcvrCrntPMOSIZETimeStamp OBJECT-TYPE
    SYNTAX       DateAndTime
    MAX-ACCESS   read-only
    STATUS       current
    DESCRIPTION  "The date and time stamp of the count of oversized packets."
    ::= { xcvrCrntPMEntry 123 }


xcvrCrntPMOSIZEValidity OBJECT-TYPE
    SYNTAX       PMValidity
    MAX-ACCESS   read-only
    STATUS       current
    DESCRIPTION  "Indicates the validity of the provided count of oversized
                  packets."
    ::= { xcvrCrntPMEntry 124 }


xcvrCrntPMFRGTValue OBJECT-TYPE
    SYNTAX       Unsigned32
    MAX-ACCESS   read-write
    STATUS       current
    DESCRIPTION  "The total number of frames received that were less than 64
                  octets in length (excluding framing bits but including FCS
                  octets) and had either a bad Frame Check Sequence (FCS) with
                  an integral number of octets (FCS Error) or a bad FCS with a
                  non-integral number of octets (Alignment Error). This object
                  applies only to transceiver ports provisioned for the 10
                  gigabit ethernet LAN protocol."
    ::= { xcvrCrntPMEntry 125 }


xcvrCrntPMFRGTTimeStamp OBJECT-TYPE
    SYNTAX       DateAndTime
    MAX-ACCESS   read-only
    STATUS       current
    DESCRIPTION  "The date and time stamp of the count of received packet
                  fragments."
    ::= { xcvrCrntPMEntry 126 }


xcvrCrntPMFRGTValidity OBJECT-TYPE
    SYNTAX       PMValidity
    MAX-ACCESS   read-only
    STATUS       current
    DESCRIPTION  "Indicates the validity of the provided count of received
                  packet fragments."
    ::= { xcvrCrntPMEntry 127 }


xcvrCrntPMJABRValue OBJECT-TYPE
    SYNTAX       Unsigned32
    MAX-ACCESS   read-write
    STATUS       current
    DESCRIPTION  "The total number of frames received that were longer than
                  14336 9600 octets (excluding framing bits, but including FCS
                  octets), and had either a bad Frame Check Sequence (FCS) with
                  an integral number of octets (FCS Error) or a bad FCS with
                  non-integral number of octets (Alignment Error). This object
                  applies only to transceiver ports provisioned for the 10
                  gigabit ethernet LAN protocol."
    ::= { xcvrCrntPMEntry 128 }


xcvrCrntPMJABRTimeStamp OBJECT-TYPE
    SYNTAX       DateAndTime
    MAX-ACCESS   read-only
    STATUS       current
    DESCRIPTION  "The date and time stamp of the count of received jabbers."
    ::= { xcvrCrntPMEntry 129 }


xcvrCrntPMJABRValidity OBJECT-TYPE
    SYNTAX       PMValidity
    MAX-ACCESS   read-only
    STATUS       current
    DESCRIPTION  "Indicates the validity of the provided count of received
                  jabbers."
    ::= { xcvrCrntPMEntry 130 }


xcvrCrntPMOTUEBValue OBJECT-TYPE
    SYNTAX       Unsigned32 
    MAX-ACCESS   read-write
    STATUS       current
    DESCRIPTION  "The count of OTN digital wrapper layer errored blocks."
    ::= { xcvrCrntPMEntry 131 }


xcvrCrntPMOTUEBTimeStamp OBJECT-TYPE
    SYNTAX       DateAndTime
    MAX-ACCESS   read-only
    STATUS       current
    DESCRIPTION  "The date and time stamp of the OTN digital wrapper layer
                  errored blocks value."
    ::= { xcvrCrntPMEntry 132 }


xcvrCrntPMOTUEBValidity OBJECT-TYPE
    SYNTAX       PMValidity
    MAX-ACCESS   read-only
    STATUS       current
    DESCRIPTION  "Indicates the validity of the provided OTN digital wrapper
                  layer errored blocks value."
    ::= { xcvrCrntPMEntry 133 }


xcvrCrntPMOTUBBEValue OBJECT-TYPE
    SYNTAX       Unsigned32 
    MAX-ACCESS   read-write
    STATUS       current
    DESCRIPTION  "The count of OTN digital wrapper layer background block
                  errors."
    ::= { xcvrCrntPMEntry 134 }


xcvrCrntPMOTUBBETimeStamp OBJECT-TYPE
    SYNTAX       DateAndTime
    MAX-ACCESS   read-only
    STATUS       current
    DESCRIPTION  "The date and time stamp of the OTN digital wrapper layer
                  background block errors."
    ::= { xcvrCrntPMEntry 135 }


xcvrCrntPMOTUBBEValidity OBJECT-TYPE
    SYNTAX       PMValidity
    MAX-ACCESS   read-only
    STATUS       current
    DESCRIPTION  "Indicates the validity of the provided OTN digital wrapper
                  layer background block errors value."
    ::= { xcvrCrntPMEntry 136 }


xcvrCrntPMOTUESValue OBJECT-TYPE
    SYNTAX       Unsigned32
    MAX-ACCESS   read-write
    STATUS       current
    DESCRIPTION  "The count of errored seconds at the OTN digital wrapper
                  layer."
    ::= { xcvrCrntPMEntry 137 }


xcvrCrntPMOTUESTimeStamp OBJECT-TYPE
    SYNTAX       DateAndTime
    MAX-ACCESS   read-only
    STATUS       current
    DESCRIPTION  "The date and time stamp of the OTN digital wrapper layer
                  errored seconds value."
    ::= { xcvrCrntPMEntry 138 }


xcvrCrntPMOTUESValidity OBJECT-TYPE
    SYNTAX       PMValidity
    MAX-ACCESS   read-only
    STATUS       current
    DESCRIPTION  "Indicates the validity of the provided OTN digital wrapper
                  layer errored seconds value."
    ::= { xcvrCrntPMEntry 139 }


xcvrCrntPMOTUSESValue OBJECT-TYPE
    SYNTAX       Unsigned32
    MAX-ACCESS   read-write
    STATUS       current
    DESCRIPTION  "The count of severely errored seconds at the OTN digital
                  wrapper layer."
    ::= { xcvrCrntPMEntry 140 }


xcvrCrntPMOTUSESTimeStamp OBJECT-TYPE
    SYNTAX       DateAndTime
    MAX-ACCESS   read-only
    STATUS       current
    DESCRIPTION  "The date and time stamp of the OTN digital wrapper layer
                  severely errored seconds value."
    ::= { xcvrCrntPMEntry 141 }


xcvrCrntPMOTUSESValidity OBJECT-TYPE
    SYNTAX       PMValidity
    MAX-ACCESS   read-only
    STATUS       current
    DESCRIPTION  "Indicates the validity of the provided OTN digital wrapper
                  layer severely errored seconds value."
    ::= { xcvrCrntPMEntry 142 }


xcvrCrntPMOTUOFSValue OBJECT-TYPE
    SYNTAX       Unsigned32
    MAX-ACCESS   read-write
    STATUS       current
    DESCRIPTION  "The count of Out-Of-Frame seconds at the OTN digital wrapper
                  layer."
    ::= { xcvrCrntPMEntry 143 }


xcvrCrntPMOTUOFSTimeStamp OBJECT-TYPE
    SYNTAX       DateAndTime
    MAX-ACCESS   read-only
    STATUS       current
    DESCRIPTION  "The date and time stamp of the OTN digital wrapper layer
                  Out-Of-Frame seconds value."
    ::= { xcvrCrntPMEntry 144 }


xcvrCrntPMOTUOFSValidity OBJECT-TYPE
    SYNTAX       PMValidity
    MAX-ACCESS   read-only
    STATUS       current
    DESCRIPTION  "Indicates the validity of the provided OTN digital wrapper
                  layer Out-of-Frame seconds value."
    ::= { xcvrCrntPMEntry 145 }


xcvrCrntPMSupplyVoltage2Value OBJECT-TYPE
    SYNTAX       FixedX10
    UNITS        "mVolts/10"
    MAX-ACCESS   read-only
    STATUS       current
    DESCRIPTION  "A second supply voltage value on the transceiver."
    ::= { xcvrCrntPMEntry 146 }


xcvrCrntPMSupplyVoltage2TimeStamp OBJECT-TYPE
    SYNTAX       DateAndTime
    MAX-ACCESS   read-only
    STATUS       current
    DESCRIPTION  "The date and time stamp of the second supply voltage value."
    ::= { xcvrCrntPMEntry 147 }


xcvrCrntPMSupplyVoltage2Validity OBJECT-TYPE
    SYNTAX       PMValidity
    MAX-ACCESS   read-only
    STATUS       current
    DESCRIPTION  "Indicates the validity of the provided second supply voltage
                  value."
    ::= { xcvrCrntPMEntry 148 }


xcvrCrntPMCVSInitialize OBJECT-TYPE
    SYNTAX       InitializeCmd
    MAX-ACCESS   read-write
    STATUS       current
    DESCRIPTION  "Used to initialize the value of the xcvrCrntPMCVSValue object
                  to 0."
    ::= { xcvrCrntPMEntry 149 }


xcvrCrntPMESSInitialize OBJECT-TYPE
    SYNTAX       InitializeCmd
    MAX-ACCESS   read-write
    STATUS       current
    DESCRIPTION  "Used to initialize the value of the xcvrCrntPMESSValue object
                  to 0."
    ::= { xcvrCrntPMEntry 150 }


xcvrCrntPMSESSInitialize OBJECT-TYPE
    SYNTAX       InitializeCmd
    MAX-ACCESS   read-write
    STATUS       current
    DESCRIPTION  "Used to initialize the value of the xcvrCrntPMSESSValue object
                  to 0."
    ::= { xcvrCrntPMEntry 151 }


xcvrCrntPMSEFSSInitialize OBJECT-TYPE
    SYNTAX       InitializeCmd
    MAX-ACCESS   read-write
    STATUS       current
    DESCRIPTION  "Used to initialize the value of the xcvrCrntPMSEFSSValue
                  object to 0."
    ::= { xcvrCrntPMEntry 152 }


xcvrCrntPMRSEBInitialize OBJECT-TYPE
    SYNTAX       InitializeCmd
    MAX-ACCESS   read-write
    STATUS       current
    DESCRIPTION  "Used to initialize the value of the xcvrCrntPMRSEBValue object
                  to 0."
    ::= { xcvrCrntPMEntry 153 }


xcvrCrntPMRSBBEInitialize OBJECT-TYPE
    SYNTAX       InitializeCmd
    MAX-ACCESS   read-write
    STATUS       current
    DESCRIPTION  "Used to initialize the value of the xcvrCrntPMRSBBEValue
                  object to 0."
    ::= { xcvrCrntPMEntry 154 }


xcvrCrntPMRSESInitialize OBJECT-TYPE
    SYNTAX       InitializeCmd
    MAX-ACCESS   read-write
    STATUS       current
    DESCRIPTION  "Used to initialize the value of the xcvrCrntPMRSESValue object
                  to 0."
    ::= { xcvrCrntPMEntry 155 }


xcvrCrntPMRSSESInitialize OBJECT-TYPE
    SYNTAX       InitializeCmd
    MAX-ACCESS   read-write
    STATUS       current
    DESCRIPTION  "Used to initialize the value of the xcvrCrntPMRSSESValue
                  object to 0."
    ::= { xcvrCrntPMEntry 156 }


xcvrCrntPMRSOFSInitialize OBJECT-TYPE
    SYNTAX       InitializeCmd
    MAX-ACCESS   read-write
    STATUS       current
    DESCRIPTION  "Used to initialize the value of the xcvrCrntPMRSOFSValue
                  object to 0."
    ::= { xcvrCrntPMEntry 157 }


xcvrCrntPMCVInitialize OBJECT-TYPE
    SYNTAX       InitializeCmd
    MAX-ACCESS   read-write
    STATUS       current
    DESCRIPTION  "Used to initialize the value of the xcvrCrntPMCVValue object
                  to 0."
    ::= { xcvrCrntPMEntry 158 }


xcvrCrntPMESInitialize OBJECT-TYPE
    SYNTAX       InitializeCmd
    MAX-ACCESS   read-write
    STATUS       current
    DESCRIPTION  "Used to initialize the value of the xcvrCrntPMESValue object
                  to 0."
    ::= { xcvrCrntPMEntry 159 }


xcvrCrntPMSESInitialize OBJECT-TYPE
    SYNTAX       InitializeCmd
    MAX-ACCESS   read-write
    STATUS       current
    DESCRIPTION  "Used to initialize the value of the xcvrCrntPMSESValue object
                  to 0."
    ::= { xcvrCrntPMEntry 160 }


xcvrCrntPMINVBLKInitialize OBJECT-TYPE
    SYNTAX       InitializeCmd
    MAX-ACCESS   read-write
    STATUS       current
    DESCRIPTION  "Used to initialize the value of the xcvrCrntPMINVBLKValue
                  object to 0."
    ::= { xcvrCrntPMEntry 161 }


xcvrCrntPMNBITCRInitialize OBJECT-TYPE
    SYNTAX       InitializeCmd
    MAX-ACCESS   read-write
    STATUS       current
    DESCRIPTION  "Used to initialize the value of the xcvrCrntPMNBITCRValue
                  object to 0."
    ::= { xcvrCrntPMEntry 162 }


xcvrCrntPMNBYTCRInitialize OBJECT-TYPE
    SYNTAX       InitializeCmd
    MAX-ACCESS   read-write
    STATUS       current
    DESCRIPTION  "Used to initialize the value of the xcvrCrntPMNBYTCRValue
                  object to 0."
    ::= { xcvrCrntPMEntry 163 }


xcvrCrntPMUNCRCDWInitialize OBJECT-TYPE
    SYNTAX       InitializeCmd
    MAX-ACCESS   read-write
    STATUS       current
    DESCRIPTION  "Used to initialize the value of the xcvrCrntPMUNCRCDWValue
                  object to 0."
    ::= { xcvrCrntPMEntry 164 }


xcvrCrntPMFCSEInitialize OBJECT-TYPE
    SYNTAX       InitializeCmd
    MAX-ACCESS   read-write
    STATUS       current
    DESCRIPTION  "Used to initialize the value of the xcvrCrntPMFCSEValue object
                  to 0."
    ::= { xcvrCrntPMEntry 165 }


xcvrCrntPMFRDRInitialize OBJECT-TYPE
    SYNTAX       InitializeCmd
    MAX-ACCESS   read-write
    STATUS       current
    DESCRIPTION  "Used to initialize the value of the xcvrCrntPMFRDRValue object
                  to 0."
    ::= { xcvrCrntPMEntry 166 }


xcvrCrntPMUSIZEInitialize OBJECT-TYPE
    SYNTAX       InitializeCmd
    MAX-ACCESS   read-write
    STATUS       current
    DESCRIPTION  "Used to initialize the value of the xcvrCrntPMUSIZEValue
                  object to 0."
    ::= { xcvrCrntPMEntry 167 }


xcvrCrntPMOSIZEInitialize OBJECT-TYPE
    SYNTAX       InitializeCmd
    MAX-ACCESS   read-write
    STATUS       current
    DESCRIPTION  "Used to initialize the value of the xcvrCrntPMOSIZEValue
                  object to 0."
    ::= { xcvrCrntPMEntry 168 }


xcvrCrntPMFRGTInitialize OBJECT-TYPE
    SYNTAX       InitializeCmd
    MAX-ACCESS   read-write
    STATUS       current
    DESCRIPTION  "Used to initialize the value of the xcvrCrntPMFRGTValue object
                  to 0."
    ::= { xcvrCrntPMEntry 169 }


xcvrCrntPMJABRInitialize OBJECT-TYPE
    SYNTAX       InitializeCmd
    MAX-ACCESS   read-write
    STATUS       current
    DESCRIPTION  "Used to initialize the value of the xcvrCrntPMJABRValue object
                  to 0."
    ::= { xcvrCrntPMEntry 170 }


xcvrCrntPMOTUEBInitialize OBJECT-TYPE
    SYNTAX       InitializeCmd
    MAX-ACCESS   read-write
    STATUS       current
    DESCRIPTION  "Used to initialize the value of the xcvrCrntPMOTUEBValue
                  object to 0."
    ::= { xcvrCrntPMEntry 171 }


xcvrCrntPMOTUBBEInitialize OBJECT-TYPE
    SYNTAX       InitializeCmd
    MAX-ACCESS   read-write
    STATUS       current
    DESCRIPTION  "Used to initialize the value of the xcvrCrntPMOTUBBEValue
                  object to 0."
    ::= { xcvrCrntPMEntry 172 }


xcvrCrntPMOTUESInitialize OBJECT-TYPE
    SYNTAX       InitializeCmd
    MAX-ACCESS   read-write
    STATUS       current
    DESCRIPTION  "Used to initialize the value of the xcvrCrntPMOTUESValue
                  object to 0."
    ::= { xcvrCrntPMEntry 173 }


xcvrCrntPMOTUSESInitialize OBJECT-TYPE
    SYNTAX       InitializeCmd
    MAX-ACCESS   read-write
    STATUS       current
    DESCRIPTION  "Used to initialize the value of the xcvrCrntPMOTUSESValue
                  object to 0."
    ::= { xcvrCrntPMEntry 174 }


xcvrCrntPMOTUOFSInitialize OBJECT-TYPE
    SYNTAX       InitializeCmd
    MAX-ACCESS   read-write
    STATUS       current
    DESCRIPTION  "Used to initialize the value of the xcvrCrntPMOTUOFSValue
                  object to 0."
    ::= { xcvrCrntPMEntry 175 }


xcvrCrntPMUASSValue OBJECT-TYPE
    SYNTAX       Unsigned32
    MAX-ACCESS   read-write
    STATUS       current
    DESCRIPTION  "The count of unavailable seconds at the section layer.
                  This object applies only to transciever ports provisioned for
                  a SONET OC-N protocol."
    ::= { xcvrCrntPMEntry 176 }


xcvrCrntPMUASSTimeStamp OBJECT-TYPE
    SYNTAX       DateAndTime
    MAX-ACCESS   read-only
    STATUS       current
    DESCRIPTION  "The date and time stamp of the section layer unavailable
                  seconds value."
    ::= { xcvrCrntPMEntry 177 }


xcvrCrntPMUASSValidity OBJECT-TYPE
    SYNTAX       PMValidity
    MAX-ACCESS   read-only
    STATUS       current
    DESCRIPTION  "Indicates the validity of the provided section layer
                  unavailable seconds value."
    ::= { xcvrCrntPMEntry 178 }


xcvrCrntPMUASSInitialize OBJECT-TYPE
    SYNTAX       InitializeCmd
    MAX-ACCESS   read-write
    STATUS       current
    DESCRIPTION  "Used to initialize the value of the xcvrCrntPMUASSValue
                  object to 0."
    ::= { xcvrCrntPMEntry 179 }


xcvrCrntPMRSUASValue OBJECT-TYPE
    SYNTAX       Unsigned32
    MAX-ACCESS   read-write
    STATUS       current
    DESCRIPTION  "The count of regenerator section unavailable seconds.
                  This object applies only to transciever ports provisioned for
                  a SDH STM-N protocol."
    ::= { xcvrCrntPMEntry 180 }


xcvrCrntPMRSUASTimeStamp OBJECT-TYPE
    SYNTAX       DateAndTime
    MAX-ACCESS   read-only
    STATUS       current
    DESCRIPTION  "The date and time stamp of the regenerator section
                  unavailable seconds value."
    ::= { xcvrCrntPMEntry 181 }


xcvrCrntPMRSUASValidity OBJECT-TYPE
    SYNTAX       PMValidity
    MAX-ACCESS   read-only
    STATUS       current
    DESCRIPTION  "Indicates the validity of the provided regenerator section
                  unavailable seconds value."
    ::= { xcvrCrntPMEntry 182 }


xcvrCrntPMRSUASInitialize OBJECT-TYPE
    SYNTAX       InitializeCmd
    MAX-ACCESS   read-write
    STATUS       current
    DESCRIPTION  "Used to initialize the value of the xcvrCrntPMRSUASValue
                  object to 0."
    ::= { xcvrCrntPMEntry 183 }


xcvrCrntPMUASValue OBJECT-TYPE
    SYNTAX       Unsigned32
    MAX-ACCESS   read-write
    STATUS       current
    DESCRIPTION  "The count of unavailable seconds. This object applies
                  only to transciever ports provisioned for the gigabit ethernet
                  protocol or a fiber channel protocol."
    ::= { xcvrCrntPMEntry 184 }


xcvrCrntPMUASTimeStamp OBJECT-TYPE
    SYNTAX       DateAndTime
    MAX-ACCESS   read-only
    STATUS       current
    DESCRIPTION  "The date and time stamp of the unavailable seconds
                  value."
    ::= { xcvrCrntPMEntry 185 }


xcvrCrntPMUASValidity OBJECT-TYPE
    SYNTAX       PMValidity
    MAX-ACCESS   read-only
    STATUS       current
    DESCRIPTION  "Indicates the validity of the provided unavailable
                  seconds value."
    ::= { xcvrCrntPMEntry 186 }


xcvrCrntPMUASInitialize OBJECT-TYPE
    SYNTAX       InitializeCmd
    MAX-ACCESS   read-write
    STATUS       current
    DESCRIPTION  "Used to initialize the value of the xcvrCrntPMUASValue
                  object to 0."
    ::= { xcvrCrntPMEntry 187 }


xcvrCrntPMOTUUASValue OBJECT-TYPE
    SYNTAX       Unsigned32
    MAX-ACCESS   read-write
    STATUS       current
    DESCRIPTION  "The count of unavailable seconds at the OTN digital
                  wrapper layer."
    ::= { xcvrCrntPMEntry 188 }


xcvrCrntPMOTUUASTimeStamp OBJECT-TYPE
    SYNTAX       DateAndTime
    MAX-ACCESS   read-only
    STATUS       current
    DESCRIPTION  "The date and time stamp of the OTN digital wrapper layer
                  unavailable seconds value."
    ::= { xcvrCrntPMEntry 189 }


xcvrCrntPMOTUUASValidity OBJECT-TYPE
    SYNTAX       PMValidity
    MAX-ACCESS   read-only
    STATUS       current
    DESCRIPTION  "Indicates the validity of the provided OTN digital wrapper
                  layer unavailable seconds value."
    ::= { xcvrCrntPMEntry 190 }


xcvrCrntPMOTUUASInitialize OBJECT-TYPE
    SYNTAX       InitializeCmd
    MAX-ACCESS   read-write
    STATUS       current
    DESCRIPTION  "Used to initialize the value of the xcvrCrntPMOTUUASValue
                  object to 0."
    ::= { xcvrCrntPMEntry 191 }


xcvrCrntPMOTNBERValue OBJECT-TYPE
    SYNTAX       DisplayString
    MAX-ACCESS   read-only
    STATUS       current
    DESCRIPTION  "The instantaneous BER of transciever ports provisioned for the 10 gigabit
                  ethernet LAN with FEC protocol."
    ::= { xcvrCrntPMEntry 192 }


xcvrCrntPMOTNBERTimeStamp OBJECT-TYPE
    SYNTAX       DateAndTime
    MAX-ACCESS   read-only
    STATUS       current
    DESCRIPTION  "The date and time stamp of the instantaneous BER."
    ::= { xcvrCrntPMEntry 193 }


xcvrCrntPMOTNBERValidity OBJECT-TYPE
    SYNTAX       PMValidity
    MAX-ACCESS   read-only
    STATUS       current
    DESCRIPTION  "Indicates the validity of the provided instantaneous BER."
    ::= { xcvrCrntPMEntry 194 }


xcvrCrntPMOTNBERInitialize OBJECT-TYPE
    SYNTAX       InitializeCmd
    MAX-ACCESS   read-write
    STATUS       current
    DESCRIPTION  "Used to initialize the value of the xcvrCrntPMOTNBERValue
                  object to 0."
    ::= { xcvrCrntPMEntry 195 }


xcvrCrntPMOTNAVGBERValue OBJECT-TYPE
    SYNTAX       DisplayString
    MAX-ACCESS   read-only
    STATUS       current
    DESCRIPTION  "The average/interval BER of transciever ports provisioned for the 10 gigabit
                  ethernet LAN with FEC protocol."
    ::= { xcvrCrntPMEntry 196 }


xcvrCrntPMOTNAVGBERTimeStamp OBJECT-TYPE
    SYNTAX       DateAndTime
    MAX-ACCESS   read-only
    STATUS       current
    DESCRIPTION  "The date and time stamp of the average/interval BER."
    ::= { xcvrCrntPMEntry 197 }


xcvrCrntPMOTNAVGBERValidity OBJECT-TYPE
    SYNTAX       PMValidity
    MAX-ACCESS   read-only
    STATUS       current
    DESCRIPTION  "Indicates the validity of the provided average/interval BER."
    ::= { xcvrCrntPMEntry 198 }


xcvrCrntPMOTNAVGBERInitialize OBJECT-TYPE
    SYNTAX       InitializeCmd
    MAX-ACCESS   read-write
    STATUS       current
    DESCRIPTION  "Used to initialize the value of the xcvrCrntPMOTNAVGBERValue
                  object to 0."
    ::= { xcvrCrntPMEntry 199 }


xcvrCrntPMNBITCR64BitValue OBJECT-TYPE
    SYNTAX       Unsigned64
    MAX-ACCESS   read-only
    STATUS       current
    DESCRIPTION  "The 64-bit count of the number of bits corrected. This object
                  applies only to transciever ports provisioned for a protocol
                  that includes Forward Error Correction (FEC)."
    ::= { xcvrCrntPMEntry 200 }


xcvrCrntPMNBITCR64BitTimeStamp OBJECT-TYPE
    SYNTAX       DateAndTime
    MAX-ACCESS   read-only
    STATUS       current
    DESCRIPTION  "The date and time stamp of the 64-bit number of bits
                  corrected value."
    ::= { xcvrCrntPMEntry 201 }


xcvrCrntPMNBITCR64BitValidity OBJECT-TYPE
    SYNTAX       PMValidity
    MAX-ACCESS   read-only
    STATUS       current
    DESCRIPTION  "Indicates the validity of the provided 64-bit number
                  of bits corrected value."
    ::= { xcvrCrntPMEntry 202 }


xcvrCrntPMNBITCR64BitInitialize OBJECT-TYPE
    SYNTAX       InitializeCmd
    MAX-ACCESS   read-write
    STATUS       current
    DESCRIPTION  "Used to initialize the value of the xcvrCrntPMNBITCR64BitValue
                  object to 0."
    ::= { xcvrCrntPMEntry 203 }


xcvrCrntPMNBYTCR64BitValue OBJECT-TYPE
    SYNTAX       Unsigned64
    MAX-ACCESS   read-only
    STATUS       current
    DESCRIPTION  "The 64-bit count of the number of bytes corrected. This object
                  applies only to transciever ports provisioned for a protocol
                  that includes Forward Error Correction (FEC)."
    ::= { xcvrCrntPMEntry 204 }


xcvrCrntPMNBYTCR64BitTimeStamp OBJECT-TYPE
    SYNTAX       DateAndTime
    MAX-ACCESS   read-only
    STATUS       current
    DESCRIPTION  "The date and time stamp of the 64-bit number of bytes
                  corrected value."
    ::= { xcvrCrntPMEntry 205 }


xcvrCrntPMNBYTCR64BitValidity OBJECT-TYPE
    SYNTAX       PMValidity
    MAX-ACCESS   read-only
    STATUS       current
    DESCRIPTION  "Indicates the validity of the provided 64-bit number of
                  bytes corrected value."
    ::= { xcvrCrntPMEntry 206 }


xcvrCrntPMNBYTCR64BitInitialize OBJECT-TYPE
    SYNTAX       InitializeCmd
    MAX-ACCESS   read-write
    STATUS       current
    DESCRIPTION  "Used to initialize the value of the xcvrCrntPMNBYTCR64BitValue
                  object to 0."
    ::= { xcvrCrntPMEntry 207 }


xcvrCrntPMOPRMinValue OBJECT-TYPE
    SYNTAX       FixedX10
    UNITS        "dBm/10"
    MAX-ACCESS   read-only
    STATUS       current
    DESCRIPTION  "The minimum optical power received on the input of the transceiver."
    ::= { xcvrCrntPMEntry 208 }


xcvrCrntPMOPRMinTimeStamp OBJECT-TYPE
    SYNTAX       DateAndTime
    MAX-ACCESS   read-only
    STATUS       current
    DESCRIPTION  "The date and time stamp of the minimum optical power received value."
    ::= { xcvrCrntPMEntry 209 }


xcvrCrntPMOPRMinValidity OBJECT-TYPE
    SYNTAX       PMValidity
    MAX-ACCESS   read-only
    STATUS       current
    DESCRIPTION  "Indicates the validity of the provided minimum optical power received
                  value."
    ::= { xcvrCrntPMEntry 210 }

xcvrCrntPMOPRMinInitialize OBJECT-TYPE
    SYNTAX       InitializeCmd
    MAX-ACCESS   read-write
    STATUS       current
    DESCRIPTION  "Used to initialize the value of the xcvrCrntPMOPRMinValue
                  object to 0."
    ::= { xcvrCrntPMEntry 211 }

xcvrCrntPMOPRMaxValue OBJECT-TYPE
    SYNTAX       FixedX10
    UNITS        "dBm/10"
    MAX-ACCESS   read-only
    STATUS       current
    DESCRIPTION  "The maximum optical power received on the input of the transceiver."
    ::= { xcvrCrntPMEntry 212 }


xcvrCrntPMOPRMaxTimeStamp OBJECT-TYPE
    SYNTAX       DateAndTime
    MAX-ACCESS   read-only
    STATUS       current
    DESCRIPTION  "The date and time stamp of the maximum optical power received value."
    ::= { xcvrCrntPMEntry 213 }


xcvrCrntPMOPRMaxValidity OBJECT-TYPE
    SYNTAX       PMValidity
    MAX-ACCESS   read-only
    STATUS       current
    DESCRIPTION  "Indicates the validity of the provided maximum optical power received
                  value."
    ::= { xcvrCrntPMEntry 214 }

xcvrCrntPMOPRMaxInitialize OBJECT-TYPE
    SYNTAX       InitializeCmd
    MAX-ACCESS   read-write
    STATUS       current
    DESCRIPTION  "Used to initialize the value of the xcvrCrntPMOPRMaxValue
                  object to 0."
    ::= { xcvrCrntPMEntry 215 }

xcvrCrntPMOPRAvgValue OBJECT-TYPE
    SYNTAX       FixedX10
    UNITS        "dBm/10"
    MAX-ACCESS   read-only
    STATUS       current
    DESCRIPTION  "The average optical power received on the input of the transceiver."
    ::= { xcvrCrntPMEntry 216 }


xcvrCrntPMOPRAvgTimeStamp OBJECT-TYPE
    SYNTAX       DateAndTime
    MAX-ACCESS   read-only
    STATUS       current
    DESCRIPTION  "The date and time stamp of the average optical power received value."
    ::= { xcvrCrntPMEntry 217 }


xcvrCrntPMOPRAvgValidity OBJECT-TYPE
    SYNTAX       PMValidity
    MAX-ACCESS   read-only
    STATUS       current
    DESCRIPTION  "Indicates the validity of the provided average optical power received
                  value."
    ::= { xcvrCrntPMEntry 218 }

xcvrCrntPMOPRAvgInitialize OBJECT-TYPE
    SYNTAX       InitializeCmd
    MAX-ACCESS   read-write
    STATUS       current
    DESCRIPTION  "Used to initialize the value of the xcvrCrntPMOPRAvgValue
                  object to 0."
    ::= { xcvrCrntPMEntry 219 }

xcvrCrntPMOPTMinValue OBJECT-TYPE
    SYNTAX       FixedX10
    UNITS        "dBm/10"
    MAX-ACCESS   read-only
    STATUS       current
    DESCRIPTION  "The minimum optical power transmitted at the output of the
                  transceiver."
    ::= { xcvrCrntPMEntry 220 }

xcvrCrntPMOPTMinTimeStamp OBJECT-TYPE
    SYNTAX       DateAndTime
    MAX-ACCESS   read-only
    STATUS       current
    DESCRIPTION  "The date and time stamp of the minimum optical power transmitted
                  value."
    ::= { xcvrCrntPMEntry 221 }


xcvrCrntPMOPTMinValidity OBJECT-TYPE
    SYNTAX       PMValidity
    MAX-ACCESS   read-only
    STATUS       current
    DESCRIPTION  "Indicates the validity of the provided minimum optical power
                  transmitted value."
    ::= { xcvrCrntPMEntry 222 }

xcvrCrntPMOPTMinInitialize OBJECT-TYPE
    SYNTAX       InitializeCmd
    MAX-ACCESS   read-write
    STATUS       current
    DESCRIPTION  "Used to initialize the value of the xcvrCrntPMOPTMinValue
                  object to 0."
    ::= { xcvrCrntPMEntry 223 }

xcvrCrntPMOPTMaxValue OBJECT-TYPE
    SYNTAX       FixedX10
    UNITS        "dBm/10"
    MAX-ACCESS   read-only
    STATUS       current
    DESCRIPTION  "The maximum optical power transmitted at the output of the
                  transceiver."
    ::= { xcvrCrntPMEntry 224 }


xcvrCrntPMOPTMaxTimeStamp OBJECT-TYPE
    SYNTAX       DateAndTime
    MAX-ACCESS   read-only
    STATUS       current
    DESCRIPTION  "The date and time stamp of the maximum optical power transmitted
                  value."
    ::= { xcvrCrntPMEntry 225 }


xcvrCrntPMOPTMaxValidity OBJECT-TYPE
    SYNTAX       PMValidity
    MAX-ACCESS   read-only
    STATUS       current
    DESCRIPTION  "Indicates the validity of the provided maximum optical power
                  transmitted value."
    ::= { xcvrCrntPMEntry 226 }

xcvrCrntPMOPTMaxInitialize OBJECT-TYPE
    SYNTAX       InitializeCmd
    MAX-ACCESS   read-write
    STATUS       current
    DESCRIPTION  "Used to initialize the value of the xcvrCrntPMOPTMaxValue
                  object to 0."
    ::= { xcvrCrntPMEntry 227 }

xcvrCrntPMOPTAvgValue OBJECT-TYPE
    SYNTAX       FixedX10
    UNITS        "dBm/10"
    MAX-ACCESS   read-only
    STATUS       current
    DESCRIPTION  "The average optical power transmitted at the output of the
                  transceiver."
    ::= { xcvrCrntPMEntry 228 }


xcvrCrntPMOPTAvgTimeStamp OBJECT-TYPE
    SYNTAX       DateAndTime
    MAX-ACCESS   read-only
    STATUS       current
    DESCRIPTION  "The date and time stamp of the average optical power transmitted
                  value."
    ::= { xcvrCrntPMEntry 229 }

xcvrCrntPMOPTAvgValidity OBJECT-TYPE
    SYNTAX       PMValidity
    MAX-ACCESS   read-only
    STATUS       current
    DESCRIPTION  "Indicates the validity of the provided average optical power
                  transmitted value."
    ::= { xcvrCrntPMEntry 230 }

xcvrCrntPMOPTAvgInitialize OBJECT-TYPE
    SYNTAX       InitializeCmd
    MAX-ACCESS   read-write
    STATUS       current
    DESCRIPTION  "Used to initialize the value of the xcvrCrntPMOPTAvgValue
                  object to 0."
    ::= { xcvrCrntPMEntry 231 }


-----------------------------------------------------------------------
-- Objects used to retrieve historical Optical Transceiver
-- Performance Monitoring statistics
-- 
-- A listing of historical transceiver PM values are contained in the 
-- xcvrHistPMTable of the BTI 7000 Series MIB. When retrieved, this 
-- table provides one row for each set of historical transceiver 
-- PM data.
-- 
-- The following table lists the objects in each entry of the xcvrHistPMTable.
-----------------------------------------------------------------------


xcvrHistPMTable OBJECT-TYPE
    SYNTAX       SEQUENCE OF XcvrHistPMEntry
    MAX-ACCESS   not-accessible
    STATUS       current
    DESCRIPTION  "A table of historical performance monitoring statistics
                  collected for the optical transceiver facilities on the NE."
    ::= { performance 4 }


xcvrHistPMEntry OBJECT-TYPE
    SYNTAX       XcvrHistPMEntry
    MAX-ACCESS   not-accessible
    STATUS       current
    DESCRIPTION  "The row entry object of the optical transceiver historical
                  performance monitoring table. Each row of this table contains
                  a full set of PM statistics and related data for a historical
                  measurement interval for a given optical transceiver."
    INDEX        { xcvrHistPMTypeIdx,
                   xcvrHistPMShelfIdx,
                   xcvrHistPMSlotIdx,
                   xcvrHistPMIdx,
                   xcvrHistPMIntervalTypeIdx,
                   xcvrHistPMIntervalIdx }
    ::= { xcvrHistPMTable 1 }


XcvrHistPMEntry ::= SEQUENCE { xcvrHistPMTypeIdx                   XcvrType,
                               xcvrHistPMShelfIdx                  INTEGER,
                               xcvrHistPMSlotIdx                   INTEGER,
                               xcvrHistPMIdx                       INTEGER,
                               xcvrHistPMIntervalTypeIdx           PMIntervalType,
                               xcvrHistPMIntervalIdx               INTEGER,
                               xcvrHistPMOPRValue                  FixedX10,
                               xcvrHistPMOPRTimeStamp              DateAndTime,
                               xcvrHistPMOPRValidity               PMValidity,
                               xcvrHistPMOPTValue                  FixedX10,
                               xcvrHistPMOPTTimeStamp              DateAndTime,
                               xcvrHistPMOPTValidity               PMValidity,
                               xcvrHistPMTempValue                 INTEGER,
                               xcvrHistPMTempTimeStamp             DateAndTime,
                               xcvrHistPMTempValidity              PMValidity,
                               xcvrHistPMSupplyVoltageValue        FixedX10,
                               xcvrHistPMSupplyVoltageTimeStamp    DateAndTime,
                               xcvrHistPMSupplyVoltageValidity     PMValidity,
                               xcvrHistPMLBCValue                  INTEGER,
                               xcvrHistPMLBCTimeStamp              DateAndTime,
                               xcvrHistPMLBCValidity               PMValidity,
                               xcvrHistPMCVSValue                  Unsigned32,
                               xcvrHistPMCVSTimeStamp              DateAndTime,
                               xcvrHistPMCVSValidity               PMValidity,
                               xcvrHistPMESSValue                  Unsigned32,
                               xcvrHistPMESSTimeStamp              DateAndTime,
                               xcvrHistPMESSValidity               PMValidity,
                               xcvrHistPMSESSValue                 Unsigned32,
                               xcvrHistPMSESSTimeStamp             DateAndTime,
                               xcvrHistPMSESSValidity              PMValidity,
                               xcvrHistPMSEFSSValue                Unsigned32,
                               xcvrHistPMSEFSSTimeStamp            DateAndTime,
                               xcvrHistPMSEFSSValidity             PMValidity,
                               xcvrHistPMRSEBValue                 Unsigned32,
                               xcvrHistPMRSEBTimeStamp             DateAndTime,
                               xcvrHistPMRSEBValidity              PMValidity,
                               xcvrHistPMRSBBEValue                Unsigned32,
                               xcvrHistPMRSBBETimeStamp            DateAndTime,
                               xcvrHistPMRSBBEValidity             PMValidity,
                               xcvrHistPMRSESValue                 Unsigned32,
                               xcvrHistPMRSESTimeStamp             DateAndTime,
                               xcvrHistPMRSESValidity              PMValidity,
                               xcvrHistPMRSSESValue                Unsigned32,
                               xcvrHistPMRSSESTimeStamp            DateAndTime,
                               xcvrHistPMRSSESValidity             PMValidity,
                               xcvrHistPMRSOFSValue                Unsigned32,
                               xcvrHistPMRSOFSTimeStamp            DateAndTime,
                               xcvrHistPMRSOFSValidity             PMValidity,
                               xcvrHistPMCVValue                   Unsigned32,
                               xcvrHistPMCVTimeStamp               DateAndTime,
                               xcvrHistPMCVValidity                PMValidity,
                               xcvrHistPMESValue                   Unsigned32,
                               xcvrHistPMESTimeStamp               DateAndTime,
                               xcvrHistPMESValidity                PMValidity,
                               xcvrHistPMSESValue                  Unsigned32,
                               xcvrHistPMSESTimeStamp              DateAndTime,
                               xcvrHistPMSESValidity               PMValidity,
                               xcvrHistPMINVBLKValue               Unsigned32,
                               xcvrHistPMINVBLKTimeStamp           DateAndTime,
                               xcvrHistPMINVBLKValidity            PMValidity,
                               xcvrHistPMNBITCRValue               Unsigned32,
                               xcvrHistPMNBITCRTimeStamp           DateAndTime,
                               xcvrHistPMNBITCRValidity            PMValidity,
                               xcvrHistPMNBYTCRValue               Unsigned32,
                               xcvrHistPMNBYTCRTimeStamp           DateAndTime,
                               xcvrHistPMNBYTCRValidity            PMValidity,
                               xcvrHistPMUNCRCDWValue              Unsigned32,
                               xcvrHistPMUNCRCDWTimeStamp          DateAndTime,
                               xcvrHistPMUNCRCDWValidity           PMValidity,
                               xcvrHistPMTBYCRXValue               Unsigned64,
                               xcvrHistPMTBYCRXTimeStamp           DateAndTime,
                               xcvrHistPMTBYCRXValidity            PMValidity,
                               xcvrHistPMTBYCRXInitialize          InitializeCmd,
                               xcvrHistPMTFRCRXValue               Unsigned64,
                               xcvrHistPMTFRCRXTimeStamp           DateAndTime,
                               xcvrHistPMTFRCRXValidity            PMValidity,
                               xcvrHistPMTFRCRXInitialize          InitializeCmd,
                               xcvrHistPMBCSTValue                 Unsigned64,
                               xcvrHistPMBCSTTimeStamp             DateAndTime,
                               xcvrHistPMBCSTValidity              PMValidity,
                               xcvrHistPMBCSTInitialize            InitializeCmd,
                               xcvrHistPMMCSTValue                 Unsigned64,
                               xcvrHistPMMCSTTimeStamp             DateAndTime,
                               xcvrHistPMMCSTValidity              PMValidity,
                               xcvrHistPMMCSTInitialize            InitializeCmd,
                               xcvrHistPMSIZE64Value               Unsigned64,
                               xcvrHistPMSIZE64TimeStamp           DateAndTime,
                               xcvrHistPMSIZE64Validity            PMValidity,
                               xcvrHistPMSIZE64Initialize          InitializeCmd,
                               xcvrHistPMSIZE65To127Value          Unsigned64,
                               xcvrHistPMSIZE65To127TimeStamp      DateAndTime,
                               xcvrHistPMSIZE65To127Validity       PMValidity,
                               xcvrHistPMSIZE65To127Initialize     InitializeCmd,
                               xcvrHistPMSIZE128To255Value         Unsigned64,
                               xcvrHistPMSIZE128To255TimeStamp     DateAndTime,
                               xcvrHistPMSIZE128To255Validity      PMValidity,
                               xcvrHistPMSIZE128To255Initialize    InitializeCmd,
                               xcvrHistPMSIZE256To511Value         Unsigned64,
                               xcvrHistPMSIZE256To511TimeStamp     DateAndTime,
                               xcvrHistPMSIZE256To511Validity      PMValidity,
                               xcvrHistPMSIZE256To511Initialize    InitializeCmd,
                               xcvrHistPMSIZE512To1023Value        Unsigned64,
                               xcvrHistPMSIZE512To1023TimeStamp    DateAndTime,
                               xcvrHistPMSIZE512To1023Validity     PMValidity,
                               xcvrHistPMSIZE512To1023Initialize   InitializeCmd,
                               xcvrHistPMSIZE1024To1518Value       Unsigned64,
                               xcvrHistPMSIZE1024To1518TimeStamp   DateAndTime,
                               xcvrHistPMSIZE1024To1518Validity    PMValidity,
                               xcvrHistPMSIZE1024To1518Initialize  InitializeCmd,
                               xcvrHistPMSIZEOver1518Value         Unsigned64,
                               xcvrHistPMSIZEOver1518TimeStamp     DateAndTime,
                               xcvrHistPMSIZEOver1518Validity      PMValidity,
                               xcvrHistPMSIZEOver1518Initialize    InitializeCmd,
                               xcvrHistPMFCSEValue                 Unsigned32,
                               xcvrHistPMFCSETimeStamp             DateAndTime,
                               xcvrHistPMFCSEValidity              PMValidity,
                               xcvrHistPMFRDRValue                 Unsigned32,
                               xcvrHistPMFRDRTimeStamp             DateAndTime,
                               xcvrHistPMFRDRValidity              PMValidity,
                               xcvrHistPMUSIZEValue                Unsigned32,
                               xcvrHistPMUSIZETimeStamp            DateAndTime,
                               xcvrHistPMUSIZEValidity             PMValidity,
                               xcvrHistPMOSIZEValue                Unsigned32,
                               xcvrHistPMOSIZETimeStamp            DateAndTime,
                               xcvrHistPMOSIZEValidity             PMValidity,
                               xcvrHistPMFRGTValue                 Unsigned32,
                               xcvrHistPMFRGTTimeStamp             DateAndTime,
                               xcvrHistPMFRGTValidity              PMValidity,
                               xcvrHistPMJABRValue                 Unsigned32,
                               xcvrHistPMJABRTimeStamp             DateAndTime,
                               xcvrHistPMJABRValidity              PMValidity,
                               xcvrHistPMOTUEBValue                Unsigned32,
                               xcvrHistPMOTUEBTimeStamp            DateAndTime,
                               xcvrHistPMOTUEBValidity             PMValidity,
                               xcvrHistPMOTUBBEValue               Unsigned32,
                               xcvrHistPMOTUBBETimeStamp           DateAndTime,
                               xcvrHistPMOTUBBEValidity            PMValidity,
                               xcvrHistPMOTUESValue                Unsigned32,
                               xcvrHistPMOTUESTimeStamp            DateAndTime,
                               xcvrHistPMOTUESValidity             PMValidity,
                               xcvrHistPMOTUSESValue               Unsigned32,
                               xcvrHistPMOTUSESTimeStamp           DateAndTime,
                               xcvrHistPMOTUSESValidity            PMValidity,
                               xcvrHistPMOTUOFSValue               Unsigned32,
                               xcvrHistPMOTUOFSTimeStamp           DateAndTime,
                               xcvrHistPMOTUOFSValidity            PMValidity,
                               xcvrHistPMSupplyVoltage2Value       FixedX10,
                               xcvrHistPMSupplyVoltage2TimeStamp   DateAndTime,
                               xcvrHistPMSupplyVoltage2Validity    PMValidity,
                               xcvrHistPMCVSInitialize             InitializeCmd,
                               xcvrHistPMESSInitialize             InitializeCmd,
                               xcvrHistPMSESSInitialize            InitializeCmd,
                               xcvrHistPMSEFSSInitialize           InitializeCmd,
                               xcvrHistPMRSEBInitialize            InitializeCmd,
                               xcvrHistPMRSBBEInitialize           InitializeCmd,
                               xcvrHistPMRSESInitialize            InitializeCmd,
                               xcvrHistPMRSSESInitialize           InitializeCmd,
                               xcvrHistPMRSOFSInitialize           InitializeCmd,
                               xcvrHistPMCVInitialize              InitializeCmd,
                               xcvrHistPMESInitialize              InitializeCmd,
                               xcvrHistPMSESInitialize             InitializeCmd,
                               xcvrHistPMINVBLKInitialize          InitializeCmd,
                               xcvrHistPMNBITCRInitialize          InitializeCmd,
                               xcvrHistPMNBYTCRInitialize          InitializeCmd,
                               xcvrHistPMUNCRCDWInitialize         InitializeCmd,
                               xcvrHistPMFCSEInitialize            InitializeCmd,
                               xcvrHistPMFRDRInitialize            InitializeCmd,
                               xcvrHistPMUSIZEInitialize           InitializeCmd,
                               xcvrHistPMOSIZEInitialize           InitializeCmd,
                               xcvrHistPMFRGTInitialize            InitializeCmd,
                               xcvrHistPMJABRInitialize            InitializeCmd,
                               xcvrHistPMOTUEBInitialize           InitializeCmd,
                               xcvrHistPMOTUBBEInitialize          InitializeCmd,
                               xcvrHistPMOTUESInitialize           InitializeCmd,
                               xcvrHistPMOTUSESInitialize          InitializeCmd,
                               xcvrHistPMOTUOFSInitialize          InitializeCmd,
                               xcvrHistPMUASSValue                 Unsigned32,
                               xcvrHistPMUASSTimeStamp             DateAndTime,
                               xcvrHistPMUASSValidity              PMValidity,
                               xcvrHistPMUASSInitialize            InitializeCmd,
                               xcvrHistPMRSUASValue                Unsigned32,
                               xcvrHistPMRSUASTimeStamp            DateAndTime,
                               xcvrHistPMRSUASValidity             PMValidity,
                               xcvrHistPMRSUASInitialize           InitializeCmd,
                               xcvrHistPMUASValue                  Unsigned32,
                               xcvrHistPMUASTimeStamp              DateAndTime,
                               xcvrHistPMUASValidity               PMValidity,
                               xcvrHistPMUASInitialize             InitializeCmd,
                               xcvrHistPMOTUUASValue               Unsigned32,
                               xcvrHistPMOTUUASTimeStamp           DateAndTime,
                               xcvrHistPMOTUUASValidity            PMValidity,
                               xcvrHistPMOTUUASInitialize          InitializeCmd,
                               xcvrHistPMOTNBERValue               DisplayString,
                               xcvrHistPMOTNBERTimeStamp           DateAndTime,
                               xcvrHistPMOTNBERValidity            PMValidity,
                               xcvrHistPMOTNBERInitialize          InitializeCmd,
                               xcvrHistPMOTNAVGBERValue            DisplayString,
                               xcvrHistPMOTNAVGBERTimeStamp        DateAndTime,
                               xcvrHistPMOTNAVGBERValidity         PMValidity,
                               xcvrHistPMOTNAVGBERInitialize       InitializeCmd,
                               xcvrHistPMNBITCR64BitValue          Unsigned64,
                               xcvrHistPMNBITCR64BitTimeStamp      DateAndTime,
                               xcvrHistPMNBITCR64BitValidity       PMValidity,
                               xcvrHistPMNBITCR64BitInitialize     InitializeCmd,
                               xcvrHistPMNBYTCR64BitValue          Unsigned64,
                               xcvrHistPMNBYTCR64BitTimeStamp      DateAndTime,
                               xcvrHistPMNBYTCR64BitValidity       PMValidity,
                               xcvrHistPMNBYTCR64BitInitialize     InitializeCmd,
                               xcvrHistPMOPRMinValue               FixedX10,
                               xcvrHistPMOPRMinTimeStamp           DateAndTime,
                               xcvrHistPMOPRMinValidity            PMValidity,
                               xcvrHistPMOPRMinInitialize          InitializeCmd,
                               xcvrHistPMOPRMaxValue               FixedX10,
                               xcvrHistPMOPRMaxTimeStamp           DateAndTime,
                               xcvrHistPMOPRMaxValidity            PMValidity,
                               xcvrHistPMOPRMaxInitialize          InitializeCmd,
                               xcvrHistPMOPRAvgValue               FixedX10,
                               xcvrHistPMOPRAvgTimeStamp           DateAndTime,
                               xcvrHistPMOPRAvgValidity            PMValidity,
                               xcvrHistPMOPRAvgInitialize          InitializeCmd,
                               xcvrHistPMOPTMinValue               FixedX10,
                               xcvrHistPMOPTMinTimeStamp           DateAndTime,
                               xcvrHistPMOPTMinValidity            PMValidity,
                               xcvrHistPMOPTMinInitialize          InitializeCmd,
                               xcvrHistPMOPTMaxValue               FixedX10,
                               xcvrHistPMOPTMaxTimeStamp           DateAndTime,
                               xcvrHistPMOPTMaxValidity            PMValidity,
                               xcvrHistPMOPTMaxInitialize          InitializeCmd,
                               xcvrHistPMOPTAvgValue               FixedX10,
                               xcvrHistPMOPTAvgTimeStamp           DateAndTime,
                               xcvrHistPMOPTAvgValidity            PMValidity,
                               xcvrHistPMOPTAvgInitialize          InitializeCmd }


xcvrHistPMTypeIdx OBJECT-TYPE
    SYNTAX       XcvrType
    MAX-ACCESS   not-accessible
    STATUS       current
    DESCRIPTION  "The type of the optical transceiver targeted for PMs."
    ::= { xcvrHistPMEntry 1 }


xcvrHistPMShelfIdx OBJECT-TYPE
    SYNTAX       INTEGER (1|11|21|31)
    MAX-ACCESS   not-accessible
    STATUS       current
    DESCRIPTION  "The number of the shelf on which the optical transceiver
                  targeted for PMs is provisioned."
    ::= { xcvrHistPMEntry 2 }


xcvrHistPMSlotIdx OBJECT-TYPE
    SYNTAX       INTEGER (1..20)
    MAX-ACCESS   not-accessible
    STATUS       current
    DESCRIPTION  "The number of the slot within which the optical transceiver
                  targeted for PMs is provisioned."
    ::= { xcvrHistPMEntry 3 }


xcvrHistPMIdx OBJECT-TYPE
    SYNTAX       INTEGER (1..4)
    MAX-ACCESS   not-accessible
    STATUS       current
    DESCRIPTION  "The number of the transceiver port targeted for PMs."
    ::= { xcvrHistPMEntry 4 }


xcvrHistPMIntervalTypeIdx OBJECT-TYPE
    SYNTAX       PMIntervalType
    MAX-ACCESS   not-accessible
    STATUS       current
    DESCRIPTION  "The type of PM bin according to interval length."
    ::= { xcvrHistPMEntry 5 }


xcvrHistPMIntervalIdx OBJECT-TYPE
    SYNTAX       INTEGER (1..96)
    MAX-ACCESS   not-accessible
    STATUS       current
    DESCRIPTION  "The specific PM bin number. The range is 1 to 96 for the
                  15-minute historical bins. For the 1-day historical bin, the
                  value is 1."
    ::= { xcvrHistPMEntry 6 }


xcvrHistPMOPRValue OBJECT-TYPE
    SYNTAX       FixedX10
    UNITS        "dBm/10"
    MAX-ACCESS   read-only
    STATUS       current
    DESCRIPTION  "The optical power received on the input of the transceiver."
    ::= { xcvrHistPMEntry 7 }


xcvrHistPMOPRTimeStamp OBJECT-TYPE
    SYNTAX       DateAndTime
    MAX-ACCESS   read-only
    STATUS       current
    DESCRIPTION  "The date and time stamp of the optical power received value."
    ::= { xcvrHistPMEntry 8 }


xcvrHistPMOPRValidity OBJECT-TYPE
    SYNTAX       PMValidity
    MAX-ACCESS   read-only
    STATUS       current
    DESCRIPTION  "Indicates the validity of the provided optical power received
                  value."
    ::= { xcvrHistPMEntry 9 }


xcvrHistPMOPTValue OBJECT-TYPE
    SYNTAX       FixedX10
    UNITS        "dBm/10"
    MAX-ACCESS   read-only
    STATUS       current
    DESCRIPTION  "The optical power transmitted at the output of the
                  transceiver."
    ::= { xcvrHistPMEntry 10 }


xcvrHistPMOPTTimeStamp OBJECT-TYPE
    SYNTAX       DateAndTime
    MAX-ACCESS   read-only
    STATUS       current
    DESCRIPTION  "The date and time stamp of the optical power transmitted
                  value."
    ::= { xcvrHistPMEntry 11 }


xcvrHistPMOPTValidity OBJECT-TYPE
    SYNTAX       PMValidity
    MAX-ACCESS   read-only
    STATUS       current
    DESCRIPTION  "Indicates the validity of the provided optical power
                  transmitted value."
    ::= { xcvrHistPMEntry 12 }


xcvrHistPMTempValue OBJECT-TYPE
    SYNTAX       INTEGER (-32768..32767)
    UNITS        "degrees Celsius"
    MAX-ACCESS   read-only
    STATUS       current
    DESCRIPTION  "The optical transceiver temperature."
    ::= { xcvrHistPMEntry 13 }


xcvrHistPMTempTimeStamp OBJECT-TYPE
    SYNTAX       DateAndTime
    MAX-ACCESS   read-only
    STATUS       current
    DESCRIPTION  "The date and time stamp of the temperature value."
    ::= { xcvrHistPMEntry 14 }


xcvrHistPMTempValidity OBJECT-TYPE
    SYNTAX       PMValidity
    MAX-ACCESS   read-only
    STATUS       current
    DESCRIPTION  "Indicates the validity of the provided temperature value."
    ::= { xcvrHistPMEntry 15 }


xcvrHistPMSupplyVoltageValue OBJECT-TYPE
    SYNTAX       FixedX10
    UNITS        "mVolts/10"
    MAX-ACCESS   read-only
    STATUS       current
    DESCRIPTION  "The transceiver supply voltage."
    ::= { xcvrHistPMEntry 16 }


xcvrHistPMSupplyVoltageTimeStamp OBJECT-TYPE
    SYNTAX       DateAndTime
    MAX-ACCESS   read-only
    STATUS       current
    DESCRIPTION  "The date and time stamp of the supply voltage value."
    ::= { xcvrHistPMEntry 17 }


xcvrHistPMSupplyVoltageValidity OBJECT-TYPE
    SYNTAX       PMValidity
    MAX-ACCESS   read-only
    STATUS       current
    DESCRIPTION  "Indicates the validity of the provided supply voltage value."
    ::= { xcvrHistPMEntry 18 }


xcvrHistPMLBCValue OBJECT-TYPE
    SYNTAX       INTEGER (-32768..32767)
    UNITS        "mAmp"
    MAX-ACCESS   read-only
    STATUS       current
    DESCRIPTION  "The transceiver laser bias current."
    ::= { xcvrHistPMEntry 19 }


xcvrHistPMLBCTimeStamp OBJECT-TYPE
    SYNTAX       DateAndTime
    MAX-ACCESS   read-only
    STATUS       current
    DESCRIPTION  "The date and time stamp of the laser bias current value."
    ::= { xcvrHistPMEntry 20 }


xcvrHistPMLBCValidity OBJECT-TYPE
    SYNTAX       PMValidity
    MAX-ACCESS   read-only
    STATUS       current
    DESCRIPTION  "Indicates the validity of the provided laser bias current
                  value."
    ::= { xcvrHistPMEntry 21 }


xcvrHistPMCVSValue OBJECT-TYPE
    SYNTAX       Unsigned32
    MAX-ACCESS   read-write
    STATUS       current
    DESCRIPTION  "The count of coding violations at the section layer. This
                  object applies only to transciever ports provisioned for a
                  SONET OC-N protocol."
    ::= { xcvrHistPMEntry 22 }


xcvrHistPMCVSTimeStamp OBJECT-TYPE
    SYNTAX       DateAndTime
    MAX-ACCESS   read-only
    STATUS       current
    DESCRIPTION  "The date and time stamp of the section layer coding violations
                  value."
    ::= { xcvrHistPMEntry 23 }


xcvrHistPMCVSValidity OBJECT-TYPE
    SYNTAX       PMValidity
    MAX-ACCESS   read-only
    STATUS       current
    DESCRIPTION  "Indicates the validity of the provided section layer coding
                  violations value."
    ::= { xcvrHistPMEntry 24 }


xcvrHistPMESSValue OBJECT-TYPE
    SYNTAX       Unsigned32
    MAX-ACCESS   read-write
    STATUS       current
    DESCRIPTION  "The count of errored seconds at the section layer. This object
                  applies only to transciever ports provisioned for a SONET OC-N
                  protocol."
    ::= { xcvrHistPMEntry 25 }


xcvrHistPMESSTimeStamp OBJECT-TYPE
    SYNTAX       DateAndTime
    MAX-ACCESS   read-only
    STATUS       current
    DESCRIPTION  "The date and time stamp of the section layer errored seconds
                  value."
    ::= { xcvrHistPMEntry 26 }


xcvrHistPMESSValidity OBJECT-TYPE
    SYNTAX       PMValidity
    MAX-ACCESS   read-only
    STATUS       current
    DESCRIPTION  "Indicates the validity of the provided section layer errored
                  seconds value."
    ::= { xcvrHistPMEntry 27 }


xcvrHistPMSESSValue OBJECT-TYPE
    SYNTAX       Unsigned32
    MAX-ACCESS   read-write
    STATUS       current
    DESCRIPTION  "The count of severely errored seconds at the section layer.
                  This object applies only to transciever ports provisioned for
                  a SONET OC-N protocol."
    ::= { xcvrHistPMEntry 28 }


xcvrHistPMSESSTimeStamp OBJECT-TYPE
    SYNTAX       DateAndTime
    MAX-ACCESS   read-only
    STATUS       current
    DESCRIPTION  "The date and time stamp of the section layer severely errored
                  seconds value."
    ::= { xcvrHistPMEntry 29 }


xcvrHistPMSESSValidity OBJECT-TYPE
    SYNTAX       PMValidity
    MAX-ACCESS   read-only
    STATUS       current
    DESCRIPTION  "Indicates the validity of the provided section layer severely
                  errored seconds value."
    ::= { xcvrHistPMEntry 30 }


xcvrHistPMSEFSSValue OBJECT-TYPE
    SYNTAX       Unsigned32
    MAX-ACCESS   read-write
    STATUS       current
    DESCRIPTION  "The count of severely errored framing seconds at the section
                  layer. This object applies only to transciever ports
                  provisioned for a SONET OC-N protocol."
    ::= { xcvrHistPMEntry 31 }


xcvrHistPMSEFSSTimeStamp OBJECT-TYPE
    SYNTAX       DateAndTime
    MAX-ACCESS   read-only
    STATUS       current
    DESCRIPTION  "The date and time stamp of the section layer severely errored
                  framing seconds value."
    ::= { xcvrHistPMEntry 32 }


xcvrHistPMSEFSSValidity OBJECT-TYPE
    SYNTAX       PMValidity
    MAX-ACCESS   read-only
    STATUS       current
    DESCRIPTION  "Indicates the validity of the provided section layer severely
                  errored framing seconds value."
    ::= { xcvrHistPMEntry 33 }


xcvrHistPMRSEBValue OBJECT-TYPE
    SYNTAX       Unsigned32
    MAX-ACCESS   read-write
    STATUS       current
    DESCRIPTION  "The count of regenerator section errored blocks. This object
                  applies only to transciever ports provisioned for a SDH STM-N
                  protocol."
    ::= { xcvrHistPMEntry 34 }


xcvrHistPMRSEBTimeStamp OBJECT-TYPE
    SYNTAX       DateAndTime
    MAX-ACCESS   read-only
    STATUS       current
    DESCRIPTION  "The date and time stamp of the regenerator section errored
                  blocks value."
    ::= { xcvrHistPMEntry 35 }


xcvrHistPMRSEBValidity OBJECT-TYPE
    SYNTAX       PMValidity
    MAX-ACCESS   read-only
    STATUS       current
    DESCRIPTION  "Indicates the validity of the provided regenerator section
                  errored blocks value."
    ::= { xcvrHistPMEntry 36 }


xcvrHistPMRSBBEValue OBJECT-TYPE
    SYNTAX       Unsigned32
    MAX-ACCESS   read-write
    STATUS       current
    DESCRIPTION  "The count of regenerator section background block errors. This
                  object applies only to transciever ports provisioned for a SDH
                  STM-N protocol."
    ::= { xcvrHistPMEntry 37 }


xcvrHistPMRSBBETimeStamp OBJECT-TYPE
    SYNTAX       DateAndTime
    MAX-ACCESS   read-only
    STATUS       current
    DESCRIPTION  "The date and time stamp of the regenerator section background
                  block errors value."
    ::= { xcvrHistPMEntry 38 }


xcvrHistPMRSBBEValidity OBJECT-TYPE
    SYNTAX       PMValidity
    MAX-ACCESS   read-only
    STATUS       current
    DESCRIPTION  "Indicates the validity of the provided regenerator section
                  background block errors value."
    ::= { xcvrHistPMEntry 39 }


xcvrHistPMRSESValue OBJECT-TYPE
    SYNTAX       Unsigned32
    MAX-ACCESS   read-write
    STATUS       current
    DESCRIPTION  "The count of regenerator section errored seconds. This object
                  applies only to transciever ports provisioned for a SDH STM-N
                  protocol."
    ::= { xcvrHistPMEntry 40 }


xcvrHistPMRSESTimeStamp OBJECT-TYPE
    SYNTAX       DateAndTime
    MAX-ACCESS   read-only
    STATUS       current
    DESCRIPTION  "The date and time stamp of the regenerator section errored
                  seconds value."
    ::= { xcvrHistPMEntry 41 }


xcvrHistPMRSESValidity OBJECT-TYPE
    SYNTAX       PMValidity
    MAX-ACCESS   read-only
    STATUS       current
    DESCRIPTION  "Indicates the validity of the provided regenerator section
                  errored seconds value."
    ::= { xcvrHistPMEntry 42 }


xcvrHistPMRSSESValue OBJECT-TYPE
    SYNTAX       Unsigned32
    MAX-ACCESS   read-write
    STATUS       current
    DESCRIPTION  "The count of regenerator section severely errored seconds.
                  This object applies only to transciever ports provisioned for
                  a SDH STM-N protocol."
    ::= { xcvrHistPMEntry 43 }


xcvrHistPMRSSESTimeStamp OBJECT-TYPE
    SYNTAX       DateAndTime
    MAX-ACCESS   read-only
    STATUS       current
    DESCRIPTION  "The date and time stamp of the regenerator section severely
                  errored seconds value."
    ::= { xcvrHistPMEntry 44 }


xcvrHistPMRSSESValidity OBJECT-TYPE
    SYNTAX       PMValidity
    MAX-ACCESS   read-only
    STATUS       current
    DESCRIPTION  "Indicates the validity of the provided regenerator section
                  severely errored seconds value."
    ::= { xcvrHistPMEntry 45 }


xcvrHistPMRSOFSValue OBJECT-TYPE
    SYNTAX       Unsigned32
    MAX-ACCESS   read-write
    STATUS       current
    DESCRIPTION  "The count of regenerator section out-of-frame seconds. This
                  object applies only to transciever ports provisioned for a SDH
                  STM-N protocol."
    ::= { xcvrHistPMEntry 46 }


xcvrHistPMRSOFSTimeStamp OBJECT-TYPE
    SYNTAX       DateAndTime
    MAX-ACCESS   read-only
    STATUS       current
    DESCRIPTION  "The date and time stamp of the regenerator section
                  out-of-frame seconds value."
    ::= { xcvrHistPMEntry 47 }


xcvrHistPMRSOFSValidity OBJECT-TYPE
    SYNTAX       PMValidity
    MAX-ACCESS   read-only
    STATUS       current
    DESCRIPTION  "Indicates the validity of the provided regenerator section
                  out-of-frame seconds value."
    ::= { xcvrHistPMEntry 48 }


xcvrHistPMCVValue OBJECT-TYPE
    SYNTAX       Unsigned32
    MAX-ACCESS   read-write
    STATUS       current
    DESCRIPTION  "The count of coding violations. This object applies only to
                  transciever ports provisioned for the gigabit ethernet
                  protocol or a fiber channel protocol."
    ::= { xcvrHistPMEntry 49 }


xcvrHistPMCVTimeStamp OBJECT-TYPE
    SYNTAX       DateAndTime
    MAX-ACCESS   read-only
    STATUS       current
    DESCRIPTION  "The date and time stamp of the coding violations value."
    ::= { xcvrHistPMEntry 50 }


xcvrHistPMCVValidity OBJECT-TYPE
    SYNTAX       PMValidity
    MAX-ACCESS   read-only
    STATUS       current
    DESCRIPTION  "Indicates the validity of the provided coding violations
                  value."
    ::= { xcvrHistPMEntry 51 }


xcvrHistPMESValue OBJECT-TYPE
    SYNTAX       Unsigned32
    MAX-ACCESS   read-write
    STATUS       current
    DESCRIPTION  "The count of errored seconds. This object applies only to
                  transciever ports provisioned for an ethernet protocol
                  or a fiber channel protocol."
    ::= { xcvrHistPMEntry 52 }


xcvrHistPMESTimeStamp OBJECT-TYPE
    SYNTAX       DateAndTime
    MAX-ACCESS   read-only
    STATUS       current
    DESCRIPTION  "The date and time stamp of the errored seconds value."
    ::= { xcvrHistPMEntry 53 }


xcvrHistPMESValidity OBJECT-TYPE
    SYNTAX       PMValidity
    MAX-ACCESS   read-only
    STATUS       current
    DESCRIPTION  "Indicates the validity of the provided errored seconds value."
    ::= { xcvrHistPMEntry 54 }


xcvrHistPMSESValue OBJECT-TYPE
    SYNTAX       Unsigned32
    MAX-ACCESS   read-write
    STATUS       current
    DESCRIPTION  "The count of severely errored seconds. This object applies
                  only to transciever ports provisioned for an ethernet
                  protocol or a fiber channel protocol."
    ::= { xcvrHistPMEntry 55 }


xcvrHistPMSESTimeStamp OBJECT-TYPE
    SYNTAX       DateAndTime
    MAX-ACCESS   read-only
    STATUS       current
    DESCRIPTION  "The date and time stamp of the severely errored seconds
                  value."
    ::= { xcvrHistPMEntry 56 }


xcvrHistPMSESValidity OBJECT-TYPE
    SYNTAX       PMValidity
    MAX-ACCESS   read-only
    STATUS       current
    DESCRIPTION  "Indicates the validity of the provided severely errored
                  seconds value."
    ::= { xcvrHistPMEntry 57 }


xcvrHistPMINVBLKValue OBJECT-TYPE
    SYNTAX       Unsigned32
    MAX-ACCESS   read-write
    STATUS       current
    DESCRIPTION  "The count of invalid blocks. This object applies only to
                  transciever ports provisioned for the 10 gigabit ethernet LAN
                  protocol."
    ::= { xcvrHistPMEntry 58 }


xcvrHistPMINVBLKTimeStamp OBJECT-TYPE
    SYNTAX       DateAndTime
    MAX-ACCESS   read-only
    STATUS       current
    DESCRIPTION  "The date and time stamp of the invalid blocks value."
    ::= { xcvrHistPMEntry 59 }


xcvrHistPMINVBLKValidity OBJECT-TYPE
    SYNTAX       PMValidity
    MAX-ACCESS   read-only
    STATUS       current
    DESCRIPTION  "Indicates the validity of the provided invalid blocks value."
    ::= { xcvrHistPMEntry 60 }


xcvrHistPMNBITCRValue OBJECT-TYPE
    SYNTAX       Unsigned32
    MAX-ACCESS   read-write
    STATUS       current
    DESCRIPTION  "The count of the number of bits corrected. This object
                  applies only to transciever ports provisioned for a protocol
                  that includes Forward Error Correction (FEC)."
    ::= { xcvrHistPMEntry 61 }


xcvrHistPMNBITCRTimeStamp OBJECT-TYPE
    SYNTAX       DateAndTime
    MAX-ACCESS   read-only
    STATUS       current
    DESCRIPTION  "The date and time stamp of the number of bits corrected
                  value."
    ::= { xcvrHistPMEntry 62 }


xcvrHistPMNBITCRValidity OBJECT-TYPE
    SYNTAX       PMValidity
    MAX-ACCESS   read-only
    STATUS       current
    DESCRIPTION  "Indicates the validity of the provided number of bits
                  corrected value."
    ::= { xcvrHistPMEntry 63 }


xcvrHistPMNBYTCRValue OBJECT-TYPE
    SYNTAX       Unsigned32
    MAX-ACCESS   read-write
    STATUS       current
    DESCRIPTION  "The count of the number of bytes corrected. This object
                  applies only to transciever ports provisioned for a protocol
                  that includes Forward Error Correction (FEC)."
    ::= { xcvrHistPMEntry 64 }


xcvrHistPMNBYTCRTimeStamp OBJECT-TYPE
    SYNTAX       DateAndTime
    MAX-ACCESS   read-only
    STATUS       current
    DESCRIPTION  "The date and time stamp of the number of bytes corrected
                  value."
    ::= { xcvrHistPMEntry 65 }


xcvrHistPMNBYTCRValidity OBJECT-TYPE
    SYNTAX       PMValidity
    MAX-ACCESS   read-only
    STATUS       current
    DESCRIPTION  "Indicates the validity of the provided number of bytes
                  corrected value."
    ::= { xcvrHistPMEntry 66 }


xcvrHistPMUNCRCDWValue OBJECT-TYPE
    SYNTAX       Unsigned32
    MAX-ACCESS   read-write
    STATUS       current
    DESCRIPTION  "The count of uncorrectable codewords. This object
                  applies only to transciever ports provisioned for a protocol
                  that includes Forward Error Correction (FEC)."
    ::= { xcvrHistPMEntry 67 }


xcvrHistPMUNCRCDWTimeStamp OBJECT-TYPE
    SYNTAX       DateAndTime
    MAX-ACCESS   read-only
    STATUS       current
    DESCRIPTION  "The date and time stamp of the uncorrectable codewords value."
    ::= { xcvrHistPMEntry 68 }


xcvrHistPMUNCRCDWValidity OBJECT-TYPE
    SYNTAX       PMValidity
    MAX-ACCESS   read-only
    STATUS       current
    DESCRIPTION  "Indicates the validity of the provided uncorrectable codewords
                  value."
    ::= { xcvrHistPMEntry 69 }


xcvrHistPMTBYCRXValue OBJECT-TYPE
    SYNTAX       Unsigned64
    MAX-ACCESS   read-only
    STATUS       current
    DESCRIPTION  "The total number of bytes of data (including those in bad
                  frames) received (excluding framing bits but including FCS
                  bytes). This object applies only to transceiver ports
                  provisioned for the 10 gigabit ethernet LAN protocol."
    ::= { xcvrHistPMEntry 70 }


xcvrHistPMTBYCRXTimeStamp OBJECT-TYPE
    SYNTAX       DateAndTime
    MAX-ACCESS   read-only
    STATUS       current
    DESCRIPTION  "The date and time stamp of the received bytes count value."
    ::= { xcvrHistPMEntry 71 }


xcvrHistPMTBYCRXValidity OBJECT-TYPE
    SYNTAX       PMValidity
    MAX-ACCESS   read-only
    STATUS       current
    DESCRIPTION  "Indicates the validity of the provided received bytes count
                  value."
    ::= { xcvrHistPMEntry 72 }


xcvrHistPMTBYCRXInitialize OBJECT-TYPE
    SYNTAX       InitializeCmd
    MAX-ACCESS   read-write
    STATUS       current
    DESCRIPTION  "Used to initialize the value of the xcvrHistPMTBYCRXValue
                  object to 0."
    ::= { xcvrHistPMEntry 73 }


xcvrHistPMTFRCRXValue OBJECT-TYPE
    SYNTAX       Unsigned64
    MAX-ACCESS   read-only
    STATUS       current
    DESCRIPTION  "The total number of received frames (incl. bad frames,
                  broadcast frames, and multicast frames received). This object
                  applies only to transceiver ports provisioned for the 10
                  gigabit ethernet LAN protocol."
    ::= { xcvrHistPMEntry 74 }


xcvrHistPMTFRCRXTimeStamp OBJECT-TYPE
    SYNTAX       DateAndTime
    MAX-ACCESS   read-only
    STATUS       current
    DESCRIPTION  "The date and time stamp of the received frames count value."
    ::= { xcvrHistPMEntry 75 }


xcvrHistPMTFRCRXValidity OBJECT-TYPE
    SYNTAX       PMValidity
    MAX-ACCESS   read-only
    STATUS       current
    DESCRIPTION  "Indicates the validity of the provided received frames count
                  value."
    ::= { xcvrHistPMEntry 76 }


xcvrHistPMTFRCRXInitialize OBJECT-TYPE
    SYNTAX       InitializeCmd
    MAX-ACCESS   read-write
    STATUS       current
    DESCRIPTION  "Used to initialize the value of the xcvrHistPMTFRCRXValue
                  object to 0."
    ::= { xcvrHistPMEntry 77 }


xcvrHistPMBCSTValue OBJECT-TYPE
    SYNTAX       Unsigned64
    MAX-ACCESS   read-only
    STATUS       current
    DESCRIPTION  "The total number of good frames received that were directed to
                  the broadcast address. Note that this does not include
                  multicast frames. This object applies only to transceiver
                  ports provisioned for the 10 gigabit ethernet LAN protocol."
    ::= { xcvrHistPMEntry 78 }


xcvrHistPMBCSTTimeStamp OBJECT-TYPE
    SYNTAX       DateAndTime
    MAX-ACCESS   read-only
    STATUS       current
    DESCRIPTION  "The date and time stamp of the broadcast packets received
                  count value."
    ::= { xcvrHistPMEntry 79 }


xcvrHistPMBCSTValidity OBJECT-TYPE
    SYNTAX       PMValidity
    MAX-ACCESS   read-only
    STATUS       current
    DESCRIPTION  "Indicates the validity of the provided broadcast packets
                  received count value."
    ::= { xcvrHistPMEntry 80 }


xcvrHistPMBCSTInitialize OBJECT-TYPE
    SYNTAX       InitializeCmd
    MAX-ACCESS   read-write
    STATUS       current
    DESCRIPTION  "Used to initialize the value of the xcvrHistPMBCSTValue object
                  to 0."
    ::= { xcvrHistPMEntry 81 }


xcvrHistPMMCSTValue OBJECT-TYPE
    SYNTAX       Unsigned64
    MAX-ACCESS   read-only
    STATUS       current
    DESCRIPTION  "The total number of good frames received that were directed to
                  a multicast address. Note that this number does not include
                  frames directed to the broadcast address. This object applies
                  only to transceiver ports provisioned for the 10 gigabit
                  ethernet LAN protocol."
    ::= { xcvrHistPMEntry 82 }


xcvrHistPMMCSTTimeStamp OBJECT-TYPE
    SYNTAX       DateAndTime
    MAX-ACCESS   read-only
    STATUS       current
    DESCRIPTION  "The date and time stamp of the multicast packets received
                  count value."
    ::= { xcvrHistPMEntry 83 }


xcvrHistPMMCSTValidity OBJECT-TYPE
    SYNTAX       PMValidity
    MAX-ACCESS   read-only
    STATUS       current
    DESCRIPTION  "Indicates the validity of the provided multicast packets
                  received count value."
    ::= { xcvrHistPMEntry 84 }


xcvrHistPMMCSTInitialize OBJECT-TYPE
    SYNTAX       InitializeCmd
    MAX-ACCESS   read-write
    STATUS       current
    DESCRIPTION  "Used to initialize the value of the xcvrHistPMMCSTValue object
                  to 0."
    ::= { xcvrHistPMEntry 85 }


xcvrHistPMSIZE64Value OBJECT-TYPE
    SYNTAX       Unsigned64
    MAX-ACCESS   read-only
    STATUS       current
    DESCRIPTION  "The total number of 64 byte frames received (excluding framing
                  bits but including FCS octets). This object applies only to
                  transceiver ports provisioned for the 10 gigabit ethernet LAN
                  protocol."
    ::= { xcvrHistPMEntry 86 }


xcvrHistPMSIZE64TimeStamp OBJECT-TYPE
    SYNTAX       DateAndTime
    MAX-ACCESS   read-only
    STATUS       current
    DESCRIPTION  "The date and time stamp of the count of 64-byte packets
                  received."
    ::= { xcvrHistPMEntry 87 }


xcvrHistPMSIZE64Validity OBJECT-TYPE
    SYNTAX       PMValidity
    MAX-ACCESS   read-only
    STATUS       current
    DESCRIPTION  "Indicates the validity of the provided count of 64-byte
                  packets packets received."
    ::= { xcvrHistPMEntry 88 }


xcvrHistPMSIZE64Initialize OBJECT-TYPE
    SYNTAX       InitializeCmd
    MAX-ACCESS   read-write
    STATUS       current
    DESCRIPTION  "Used to initialize the value of the xcvrHistPMSIZE64Value
                  object to 0."
    ::= { xcvrHistPMEntry 89 }


xcvrHistPMSIZE65To127Value OBJECT-TYPE
    SYNTAX       Unsigned64
    MAX-ACCESS   read-only
    STATUS       current
    DESCRIPTION  "The total number of frames received that are 65 to 127 bytes
                  inclusive in length (excluding framing bits but including FCS
                  octets). This object applies only to transceiver ports
                  provisioned for the 10 gigabit ethernet LAN protocol."
    ::= { xcvrHistPMEntry 90 }


xcvrHistPMSIZE65To127TimeStamp OBJECT-TYPE
    SYNTAX       DateAndTime
    MAX-ACCESS   read-only
    STATUS       current
    DESCRIPTION  "The date and time stamp of the count of packets between 65 and
                  127 bytes."
    ::= { xcvrHistPMEntry 91 }


xcvrHistPMSIZE65To127Validity OBJECT-TYPE
    SYNTAX       PMValidity
    MAX-ACCESS   read-only
    STATUS       current
    DESCRIPTION  "Indicates the validity of the provided count of packets
                  between 65 and 127 bytes."
    ::= { xcvrHistPMEntry 92 }


xcvrHistPMSIZE65To127Initialize OBJECT-TYPE
    SYNTAX       InitializeCmd
    MAX-ACCESS   read-write
    STATUS       current
    DESCRIPTION  "Used to initialize the value of the xcvrHistPMSIZE65To127Value
                  object to 0."
    ::= { xcvrHistPMEntry 93 }


xcvrHistPMSIZE128To255Value OBJECT-TYPE
    SYNTAX       Unsigned64
    MAX-ACCESS   read-only
    STATUS       current
    DESCRIPTION  "The total number of frames received that are 128 to 255 bytes
                  inclusive in length (excluding framing bits but including FCS
                  octets). This object applies only to transceiver ports
                  provisioned for the 10 gigabit ethernet LAN protocol."
    ::= { xcvrHistPMEntry 94 }


xcvrHistPMSIZE128To255TimeStamp OBJECT-TYPE
    SYNTAX       DateAndTime
    MAX-ACCESS   read-only
    STATUS       current
    DESCRIPTION  "The date and time stamp of the count of packets between 128
                  and 255 bytes."
    ::= { xcvrHistPMEntry 95 }


xcvrHistPMSIZE128To255Validity OBJECT-TYPE
    SYNTAX       PMValidity
    MAX-ACCESS   read-only
    STATUS       current
    DESCRIPTION  "Indicates the validity of the provided count of packets
                  between 128 and 255 bytes."
    ::= { xcvrHistPMEntry 96 }


xcvrHistPMSIZE128To255Initialize OBJECT-TYPE
    SYNTAX       InitializeCmd
    MAX-ACCESS   read-write
    STATUS       current
    DESCRIPTION  "Used to initialize the value of the
                  xcvrHistPMSIZE128To255Value object to 0."
    ::= { xcvrHistPMEntry 97 }


xcvrHistPMSIZE256To511Value OBJECT-TYPE
    SYNTAX       Unsigned64
    MAX-ACCESS   read-only
    STATUS       current
    DESCRIPTION  "The total number of frames received that are 256 to 511 bytes
                  inclusive in length (excluding framing bits but including FCS
                  octets). This object applies only to transceiver ports
                  provisioned for the 10 gigabit ethernet LAN protocol."
    ::= { xcvrHistPMEntry 98 }


xcvrHistPMSIZE256To511TimeStamp OBJECT-TYPE
    SYNTAX       DateAndTime
    MAX-ACCESS   read-only
    STATUS       current
    DESCRIPTION  "The date and time stamp of the count of packets between 256
                  and 511 bytes."
    ::= { xcvrHistPMEntry 99 }


xcvrHistPMSIZE256To511Validity OBJECT-TYPE
    SYNTAX       PMValidity
    MAX-ACCESS   read-only
    STATUS       current
    DESCRIPTION  "Indicates the validity of the provided count of packets
                  between 256 and 511 bytes."
    ::= { xcvrHistPMEntry 100 }


xcvrHistPMSIZE256To511Initialize OBJECT-TYPE
    SYNTAX       InitializeCmd
    MAX-ACCESS   read-write
    STATUS       current
    DESCRIPTION  "Used to initialize the value of the
                  xcvrHistPMSIZE256To511Value object to 0."
    ::= { xcvrHistPMEntry 101 }


xcvrHistPMSIZE512To1023Value OBJECT-TYPE
    SYNTAX       Unsigned64
    MAX-ACCESS   read-only
    STATUS       current
    DESCRIPTION  "The total number of frames received that are 512 to 1023 bytes
                  inclusive in length (excluding framing bits but including FCS
                  octets). This object applies only to transceiver ports
                  provisioned for the 10 gigabit ethernet LAN protocol."
    ::= { xcvrHistPMEntry 102 }


xcvrHistPMSIZE512To1023TimeStamp OBJECT-TYPE
    SYNTAX       DateAndTime
    MAX-ACCESS   read-only
    STATUS       current
    DESCRIPTION  "The date and time stamp of the count of packets between 512
                  and 1023 bytes."
    ::= { xcvrHistPMEntry 103 }


xcvrHistPMSIZE512To1023Validity OBJECT-TYPE
    SYNTAX       PMValidity
    MAX-ACCESS   read-only
    STATUS       current
    DESCRIPTION  "Indicates the validity of the provided count of packets
                  between 512 and 1023 bytes."
    ::= { xcvrHistPMEntry 104 }


xcvrHistPMSIZE512To1023Initialize OBJECT-TYPE
    SYNTAX       InitializeCmd
    MAX-ACCESS   read-write
    STATUS       current
    DESCRIPTION  "Used to initialize the value of the
                  xcvrHistPMSIZE512To1023Value object to 0."
    ::= { xcvrHistPMEntry 105 }


xcvrHistPMSIZE1024To1518Value OBJECT-TYPE
    SYNTAX       Unsigned64
    MAX-ACCESS   read-only
    STATUS       current
    DESCRIPTION  "The total number of frames received that are 1024 to 1518
                  bytes inclusive in length (excluding framing bits but
                  including FCS octets). This object applies only to transceiver
                  ports provisioned for the 10 gigabit ethernet LAN protocol."
    ::= { xcvrHistPMEntry 106 }


xcvrHistPMSIZE1024To1518TimeStamp OBJECT-TYPE
    SYNTAX       DateAndTime
    MAX-ACCESS   read-only
    STATUS       current
    DESCRIPTION  "The date and time stamp of the count of packets between 1024
                  and 1518 bytes."
    ::= { xcvrHistPMEntry 107 }


xcvrHistPMSIZE1024To1518Validity OBJECT-TYPE
    SYNTAX       PMValidity
    MAX-ACCESS   read-only
    STATUS       current
    DESCRIPTION  "Indicates the validity of the provided count of packets
                  between 1024 and 1518 bytes."
    ::= { xcvrHistPMEntry 108 }


xcvrHistPMSIZE1024To1518Initialize OBJECT-TYPE
    SYNTAX       InitializeCmd
    MAX-ACCESS   read-write
    STATUS       current
    DESCRIPTION  "Used to initialize the value of the
                  xcvrHistPMSIZE1024To1518Value object to 0."
    ::= { xcvrHistPMEntry 109 }


xcvrHistPMSIZEOver1518Value OBJECT-TYPE
    SYNTAX       Unsigned64
    MAX-ACCESS   read-only
    STATUS       current
    DESCRIPTION  "The total number of frames received that are greater than or
                  equal to 1519 bytes in length (excluding framing bits but
                  including FCS octets). This object applies only to transceiver
                  ports provisioned for the 10 gigabit ethernet LAN protocol."
    ::= { xcvrHistPMEntry 110 }


xcvrHistPMSIZEOver1518TimeStamp OBJECT-TYPE
    SYNTAX       DateAndTime
    MAX-ACCESS   read-only
    STATUS       current
    DESCRIPTION  "The date and time stamp of the count of packets over 1518
                  bytes."
    ::= { xcvrHistPMEntry 111 }


xcvrHistPMSIZEOver1518Validity OBJECT-TYPE
    SYNTAX       PMValidity
    MAX-ACCESS   read-only
    STATUS       current
    DESCRIPTION  "Indicates the validity of the provided count of packets over
                  1518 bytes."
    ::= { xcvrHistPMEntry 112 }


xcvrHistPMSIZEOver1518Initialize OBJECT-TYPE
    SYNTAX       InitializeCmd
    MAX-ACCESS   read-write
    STATUS       current
    DESCRIPTION  "Used to initialize the value of the
                  xcvrHistPMSIZEOver1518Value object to 0."
    ::= { xcvrHistPMEntry 113 }


xcvrHistPMFCSEValue OBJECT-TYPE
    SYNTAX       Unsigned32
    MAX-ACCESS   read-write
    STATUS       current
    DESCRIPTION  "The count of packets that had a valid length but had either a
                  Frame Check Sequence (FCS) or a bad FCS with a non-integral
                  number of octets (Alignment Error) . This object applies only
                  to transceiver ports provisioned for the 10 gigabit ethernet
                  LAN protocol."
    ::= { xcvrHistPMEntry 114 }


xcvrHistPMFCSETimeStamp OBJECT-TYPE
    SYNTAX       DateAndTime
    MAX-ACCESS   read-only
    STATUS       current
    DESCRIPTION  "The date and time stamp of the count of packets with bad FCS
                  or alignment error."
    ::= { xcvrHistPMEntry 115 }


xcvrHistPMFCSEValidity OBJECT-TYPE
    SYNTAX       PMValidity
    MAX-ACCESS   read-only
    STATUS       current
    DESCRIPTION  "Indicates the validity of the provided count of packets with
                  bad FCS or alignment error."
    ::= { xcvrHistPMEntry 116 }


xcvrHistPMFRDRValue OBJECT-TYPE
    SYNTAX       Unsigned32
    MAX-ACCESS   read-write
    STATUS       current
    DESCRIPTION  "The total number of dropped frames due to lack of resources or
                  otherwise. Note that this number is not necessarily the number
                  of frames dropped; it is just the number of times that it
                  could be detected. This object applies only to transceiver
                  ports provisioned for the 10 gigabit ethernet LAN protocol."
    ::= { xcvrHistPMEntry 117 }


xcvrHistPMFRDRTimeStamp OBJECT-TYPE
    SYNTAX       DateAndTime
    MAX-ACCESS   read-only
    STATUS       current
    DESCRIPTION  "The date and time stamp of the count of dropped packets."
    ::= { xcvrHistPMEntry 118 }


xcvrHistPMFRDRValidity OBJECT-TYPE
    SYNTAX       PMValidity
    MAX-ACCESS   read-only
    STATUS       current
    DESCRIPTION  "Indicates the validity of the provided count of dropped
                  packets."
    ::= { xcvrHistPMEntry 119 }


xcvrHistPMUSIZEValue OBJECT-TYPE
    SYNTAX       Unsigned32
    MAX-ACCESS   read-write
    STATUS       current
    DESCRIPTION  "The total number of frames received that were less than 64
                  octets long (excluding framing bits, but including FCS octets)
                  and were otherwise well formed. This object applies only to
                  transceiver ports provisioned for the 10 gigabit ethernet LAN
                  protocol."
    ::= { xcvrHistPMEntry 120 }


xcvrHistPMUSIZETimeStamp OBJECT-TYPE
    SYNTAX       DateAndTime
    MAX-ACCESS   read-only
    STATUS       current
    DESCRIPTION  "The date and time stamp of the count of undersized packets."
    ::= { xcvrHistPMEntry 121 }


xcvrHistPMUSIZEValidity OBJECT-TYPE
    SYNTAX       PMValidity
    MAX-ACCESS   read-only
    STATUS       current
    DESCRIPTION  "Indicates the validity of the provided count of undersized
                  packets."
    ::= { xcvrHistPMEntry 122 }


xcvrHistPMOSIZEValue OBJECT-TYPE
    SYNTAX       Unsigned32
    MAX-ACCESS   read-write
    STATUS       current
    DESCRIPTION  "The total number of frames received that were longer than 9600
                  octets (excluding framing bits, but including FCS octets) and
                  were otherwise well formed. This object applies only to
                  transceiver ports provisioned for the 10 gigabit ethernet LAN
                  protocol."
    ::= { xcvrHistPMEntry 123 }


xcvrHistPMOSIZETimeStamp OBJECT-TYPE
    SYNTAX       DateAndTime
    MAX-ACCESS   read-only
    STATUS       current
    DESCRIPTION  "The date and time stamp of the count of oversized packets."
    ::= { xcvrHistPMEntry 124 }


xcvrHistPMOSIZEValidity OBJECT-TYPE
    SYNTAX       PMValidity
    MAX-ACCESS   read-only
    STATUS       current
    DESCRIPTION  "Indicates the validity of the provided count of oversized
                  packets."
    ::= { xcvrHistPMEntry 125 }


xcvrHistPMFRGTValue OBJECT-TYPE
    SYNTAX       Unsigned32
    MAX-ACCESS   read-write
    STATUS       current
    DESCRIPTION  "The total number of frames received that were less than 64
                  octets in length (excluding framing bits but including FCS
                  octets) and had either a bad Frame Check Sequence (FCS) with
                  an integral number of octets (FCS Error) or a bad FCS with a
                  non-integral number of octets (Alignment Error). This object
                  applies only to transceiver ports provisioned for the 10
                  gigabit ethernet LAN protocol."
    ::= { xcvrHistPMEntry 126 }


xcvrHistPMFRGTTimeStamp OBJECT-TYPE
    SYNTAX       DateAndTime
    MAX-ACCESS   read-only
    STATUS       current
    DESCRIPTION  "The date and time stamp of the count of received packet
                  fragments."
    ::= { xcvrHistPMEntry 127 }


xcvrHistPMFRGTValidity OBJECT-TYPE
    SYNTAX       PMValidity
    MAX-ACCESS   read-only
    STATUS       current
    DESCRIPTION  "Indicates the validity of the provided count of received
                  packet fragments."
    ::= { xcvrHistPMEntry 128 }


xcvrHistPMJABRValue OBJECT-TYPE
    SYNTAX       Unsigned32
    MAX-ACCESS   read-write
    STATUS       current
    DESCRIPTION  "The total number of frames received that were longer than
                  14336 9600 octets (excluding framing bits, but including FCS
                  octets), and had either a bad Frame Check Sequence (FCS) with
                  an integral number of octets (FCS Error) or a bad FCS with
                  non-integral number of octets (Alignment Error). This object
                  applies only to transceiver ports provisioned for the 10
                  gigabit ethernet LAN protocol."
    ::= { xcvrHistPMEntry 129 }


xcvrHistPMJABRTimeStamp OBJECT-TYPE
    SYNTAX       DateAndTime
    MAX-ACCESS   read-only
    STATUS       current
    DESCRIPTION  "The date and time stamp of the count of received jabbers."
    ::= { xcvrHistPMEntry 130 }


xcvrHistPMJABRValidity OBJECT-TYPE
    SYNTAX       PMValidity
    MAX-ACCESS   read-only
    STATUS       current
    DESCRIPTION  "Indicates the validity of the provided count of received
                  jabbers."
    ::= { xcvrHistPMEntry 131 }


xcvrHistPMOTUEBValue OBJECT-TYPE
    SYNTAX       Unsigned32 
    MAX-ACCESS   read-write
    STATUS       current
    DESCRIPTION  "The count of OTN digital wrapper layer errored blocks."
    ::= { xcvrHistPMEntry 132 }


xcvrHistPMOTUEBTimeStamp OBJECT-TYPE
    SYNTAX       DateAndTime
    MAX-ACCESS   read-only
    STATUS       current
    DESCRIPTION  "The date and time stamp of the OTN digital wrapper layer
                  errored blocks value."
    ::= { xcvrHistPMEntry 133 }


xcvrHistPMOTUEBValidity OBJECT-TYPE
    SYNTAX       PMValidity
    MAX-ACCESS   read-only
    STATUS       current
    DESCRIPTION  "Indicates the validity of the provided OTN digital wrapper
                  layer errored blocks value."
    ::= { xcvrHistPMEntry 134 }


xcvrHistPMOTUBBEValue OBJECT-TYPE
    SYNTAX       Unsigned32 
    MAX-ACCESS   read-write
    STATUS       current
    DESCRIPTION  "The count of OTN digital wrapper layer background block
                  errors."
    ::= { xcvrHistPMEntry 135 }


xcvrHistPMOTUBBETimeStamp OBJECT-TYPE
    SYNTAX       DateAndTime
    MAX-ACCESS   read-only
    STATUS       current
    DESCRIPTION  "The date and time stamp of the OTN digital wrapper layer
                  background block errors."
    ::= { xcvrHistPMEntry 136 }


xcvrHistPMOTUBBEValidity OBJECT-TYPE
    SYNTAX       PMValidity
    MAX-ACCESS   read-only
    STATUS       current
    DESCRIPTION  "Indicates the validity of the provided OTN digital wrapper
                  layer background block errors value."
    ::= { xcvrHistPMEntry 137 }


xcvrHistPMOTUESValue OBJECT-TYPE
    SYNTAX       Unsigned32
    MAX-ACCESS   read-write
    STATUS       current
    DESCRIPTION  "The count of errored seconds at the OTN digital wrapper
                  layer."
    ::= { xcvrHistPMEntry 138 }


xcvrHistPMOTUESTimeStamp OBJECT-TYPE
    SYNTAX       DateAndTime
    MAX-ACCESS   read-only
    STATUS       current
    DESCRIPTION  "The date and time stamp of the OTN digital wrapper layer
                  errored seconds value."
    ::= { xcvrHistPMEntry 139 }


xcvrHistPMOTUESValidity OBJECT-TYPE
    SYNTAX       PMValidity
    MAX-ACCESS   read-only
    STATUS       current
    DESCRIPTION  "Indicates the validity of the provided OTN digital wrapper
                  layer errored seconds value."
    ::= { xcvrHistPMEntry 140 }


xcvrHistPMOTUSESValue OBJECT-TYPE
    SYNTAX       Unsigned32
    MAX-ACCESS   read-write
    STATUS       current
    DESCRIPTION  "The count of severely errored seconds at the OTN digital
                  wrapper layer."
    ::= { xcvrHistPMEntry 141 }


xcvrHistPMOTUSESTimeStamp OBJECT-TYPE
    SYNTAX       DateAndTime
    MAX-ACCESS   read-only
    STATUS       current
    DESCRIPTION  "The date and time stamp of the OTN digital wrapper layer
                  severely errored seconds value."
    ::= { xcvrHistPMEntry 142 }


xcvrHistPMOTUSESValidity OBJECT-TYPE
    SYNTAX       PMValidity
    MAX-ACCESS   read-only
    STATUS       current
    DESCRIPTION  "Indicates the validity of the provided OTN digital wrapper
                  layer severely errored seconds value."
    ::= { xcvrHistPMEntry 143 }


xcvrHistPMOTUOFSValue OBJECT-TYPE
    SYNTAX       Unsigned32
    MAX-ACCESS   read-write
    STATUS       current
    DESCRIPTION  "The count of Out-Of-Frame seconds at the OTN digital wrapper
                  layer."
    ::= { xcvrHistPMEntry 144 }


xcvrHistPMOTUOFSTimeStamp OBJECT-TYPE
    SYNTAX       DateAndTime
    MAX-ACCESS   read-only
    STATUS       current
    DESCRIPTION  "The date and time stamp of the OTN digital wrapper layer
                  Out-Of-Frame seconds value."
    ::= { xcvrHistPMEntry 145 }


xcvrHistPMOTUOFSValidity OBJECT-TYPE
    SYNTAX       PMValidity
    MAX-ACCESS   read-only
    STATUS       current
    DESCRIPTION  "Indicates the validity of the provided OTN digital wrapper
                  layer Out-of-Frame seconds value."
    ::= { xcvrHistPMEntry 146 }


xcvrHistPMSupplyVoltage2Value OBJECT-TYPE
    SYNTAX       FixedX10
    UNITS        "mVolts/10"
    MAX-ACCESS   read-only
    STATUS       current
    DESCRIPTION  "A second supply voltage value on the transceiver."
    ::= { xcvrHistPMEntry 147 }


xcvrHistPMSupplyVoltage2TimeStamp OBJECT-TYPE
    SYNTAX       DateAndTime
    MAX-ACCESS   read-only
    STATUS       current
    DESCRIPTION  "The date and time stamp of the second supply voltage value."
    ::= { xcvrHistPMEntry 148 }


xcvrHistPMSupplyVoltage2Validity OBJECT-TYPE
    SYNTAX       PMValidity
    MAX-ACCESS   read-only
    STATUS       current
    DESCRIPTION  "Indicates the validity of the provided second supply voltage
                  value."
    ::= { xcvrHistPMEntry 149 }


xcvrHistPMCVSInitialize OBJECT-TYPE
    SYNTAX       InitializeCmd
    MAX-ACCESS   read-write
    STATUS       current
    DESCRIPTION  "Used to initialize the value of the xcvrHistPMCVSValue object
                  to 0."
    ::= { xcvrHistPMEntry 150 }


xcvrHistPMESSInitialize OBJECT-TYPE
    SYNTAX       InitializeCmd
    MAX-ACCESS   read-write
    STATUS       current
    DESCRIPTION  "Used to initialize the value of the xcvrHistPMESSValue object
                  to 0."
    ::= { xcvrHistPMEntry 151 }


xcvrHistPMSESSInitialize OBJECT-TYPE
    SYNTAX       InitializeCmd
    MAX-ACCESS   read-write
    STATUS       current
    DESCRIPTION  "Used to initialize the value of the xcvrHistPMSESSValue object
                  to 0."
    ::= { xcvrHistPMEntry 152 }


xcvrHistPMSEFSSInitialize OBJECT-TYPE
    SYNTAX       InitializeCmd
    MAX-ACCESS   read-write
    STATUS       current
    DESCRIPTION  "Used to initialize the value of the xcvrHistPMSEFSSValue
                  object to 0."
    ::= { xcvrHistPMEntry 153 }


xcvrHistPMRSEBInitialize OBJECT-TYPE
    SYNTAX       InitializeCmd
    MAX-ACCESS   read-write
    STATUS       current
    DESCRIPTION  "Used to initialize the value of the xcvrHistPMRSEBValue object
                  to 0."
    ::= { xcvrHistPMEntry 154 }


xcvrHistPMRSBBEInitialize OBJECT-TYPE
    SYNTAX       InitializeCmd
    MAX-ACCESS   read-write
    STATUS       current
    DESCRIPTION  "Used to initialize the value of the xcvrHistPMRSBBEValue
                  object to 0."
    ::= { xcvrHistPMEntry 155 }


xcvrHistPMRSESInitialize OBJECT-TYPE
    SYNTAX       InitializeCmd
    MAX-ACCESS   read-write
    STATUS       current
    DESCRIPTION  "Used to initialize the value of the xcvrHistPMRSESValue object
                  to 0."
    ::= { xcvrHistPMEntry 156 }


xcvrHistPMRSSESInitialize OBJECT-TYPE
    SYNTAX       InitializeCmd
    MAX-ACCESS   read-write
    STATUS       current
    DESCRIPTION  "Used to initialize the value of the xcvrHistPMRSSESValue
                  object to 0."
    ::= { xcvrHistPMEntry 157 }


xcvrHistPMRSOFSInitialize OBJECT-TYPE
    SYNTAX       InitializeCmd
    MAX-ACCESS   read-write
    STATUS       current
    DESCRIPTION  "Used to initialize the value of the xcvrHistPMRSOFSValue
                  object to 0."
    ::= { xcvrHistPMEntry 158 }


xcvrHistPMCVInitialize OBJECT-TYPE
    SYNTAX       InitializeCmd
    MAX-ACCESS   read-write
    STATUS       current
    DESCRIPTION  "Used to initialize the value of the xcvrHistPMCVValue object
                  to 0."
    ::= { xcvrHistPMEntry 159 }


xcvrHistPMESInitialize OBJECT-TYPE
    SYNTAX       InitializeCmd
    MAX-ACCESS   read-write
    STATUS       current
    DESCRIPTION  "Used to initialize the value of the xcvrHistPMESValue object
                  to 0."
    ::= { xcvrHistPMEntry 160 }


xcvrHistPMSESInitialize OBJECT-TYPE
    SYNTAX       InitializeCmd
    MAX-ACCESS   read-write
    STATUS       current
    DESCRIPTION  "Used to initialize the value of the xcvrHistPMSESValue object
                  to 0."
    ::= { xcvrHistPMEntry 161 }


xcvrHistPMINVBLKInitialize OBJECT-TYPE
    SYNTAX       InitializeCmd
    MAX-ACCESS   read-write
    STATUS       current
    DESCRIPTION  "Used to initialize the value of the xcvrHistPMINVBLKValue
                  object to 0."
    ::= { xcvrHistPMEntry 162 }


xcvrHistPMNBITCRInitialize OBJECT-TYPE
    SYNTAX       InitializeCmd
    MAX-ACCESS   read-write
    STATUS       current
    DESCRIPTION  "Used to initialize the value of the xcvrHistPMNBITCRValue
                  object to 0."
    ::= { xcvrHistPMEntry 163 }


xcvrHistPMNBYTCRInitialize OBJECT-TYPE
    SYNTAX       InitializeCmd
    MAX-ACCESS   read-write
    STATUS       current
    DESCRIPTION  "Used to initialize the value of the xcvrHistPMNBYTCRValue
                  object to 0."
    ::= { xcvrHistPMEntry 164 }


xcvrHistPMUNCRCDWInitialize OBJECT-TYPE
    SYNTAX       InitializeCmd
    MAX-ACCESS   read-write
    STATUS       current
    DESCRIPTION  "Used to initialize the value of the xcvrHistPMUNCRCDWValue
                  object to 0."
    ::= { xcvrHistPMEntry 165 }


xcvrHistPMFCSEInitialize OBJECT-TYPE
    SYNTAX       InitializeCmd
    MAX-ACCESS   read-write
    STATUS       current
    DESCRIPTION  "Used to initialize the value of the xcvrHistPMFCSEValue object
                  to 0."
    ::= { xcvrHistPMEntry 166 }


xcvrHistPMFRDRInitialize OBJECT-TYPE
    SYNTAX       InitializeCmd
    MAX-ACCESS   read-write
    STATUS       current
    DESCRIPTION  "Used to initialize the value of the xcvrHistPMFRDRValue object
                  to 0."
    ::= { xcvrHistPMEntry 167 }


xcvrHistPMUSIZEInitialize OBJECT-TYPE
    SYNTAX       InitializeCmd
    MAX-ACCESS   read-write
    STATUS       current
    DESCRIPTION  "Used to initialize the value of the xcvrHistPMUSIZEValue
                  object to 0."
    ::= { xcvrHistPMEntry 168 }


xcvrHistPMOSIZEInitialize OBJECT-TYPE
    SYNTAX       InitializeCmd
    MAX-ACCESS   read-write
    STATUS       current
    DESCRIPTION  "Used to initialize the value of the xcvrHistPMOSIZEValue
                  object to 0."
    ::= { xcvrHistPMEntry 169 }


xcvrHistPMFRGTInitialize OBJECT-TYPE
    SYNTAX       InitializeCmd
    MAX-ACCESS   read-write
    STATUS       current
    DESCRIPTION  "Used to initialize the value of the xcvrHistPMFRGTValue object
                  to 0."
    ::= { xcvrHistPMEntry 170 }


xcvrHistPMJABRInitialize OBJECT-TYPE
    SYNTAX       InitializeCmd
    MAX-ACCESS   read-write
    STATUS       current
    DESCRIPTION  "Used to initialize the value of the xcvrHistPMJABRValue object
                  to 0."
    ::= { xcvrHistPMEntry 171 }


xcvrHistPMOTUEBInitialize OBJECT-TYPE
    SYNTAX       InitializeCmd
    MAX-ACCESS   read-write
    STATUS       current
    DESCRIPTION  "Used to initialize the value of the xcvrHistPMOTUEBValue
                  object to 0."
    ::= { xcvrHistPMEntry 172 }


xcvrHistPMOTUBBEInitialize OBJECT-TYPE
    SYNTAX       InitializeCmd
    MAX-ACCESS   read-write
    STATUS       current
    DESCRIPTION  "Used to initialize the value of the xcvrHistPMOTUBBEValue
                  object to 0."
    ::= { xcvrHistPMEntry 173 }


xcvrHistPMOTUESInitialize OBJECT-TYPE
    SYNTAX       InitializeCmd
    MAX-ACCESS   read-write
    STATUS       current
    DESCRIPTION  "Used to initialize the value of the xcvrHistPMOTUESValue
                  object to 0."
    ::= { xcvrHistPMEntry 174 }


xcvrHistPMOTUSESInitialize OBJECT-TYPE
    SYNTAX       InitializeCmd
    MAX-ACCESS   read-write
    STATUS       current
    DESCRIPTION  "Used to initialize the value of the xcvrHistPMOTUSESValue
                  object to 0."
    ::= { xcvrHistPMEntry 175 }


xcvrHistPMOTUOFSInitialize OBJECT-TYPE
    SYNTAX       InitializeCmd
    MAX-ACCESS   read-write
    STATUS       current
    DESCRIPTION  "Used to initialize the value of the xcvrHistPMOTUOFSValue
                  object to 0."
    ::= { xcvrHistPMEntry 176 }


xcvrHistPMUASSValue OBJECT-TYPE
    SYNTAX       Unsigned32
    MAX-ACCESS   read-write
    STATUS       current
    DESCRIPTION  "The count of unavailable seconds at the section layer.
                  This object applies only to transciever ports provisioned for
                  a SONET OC-N protocol."
    ::= { xcvrHistPMEntry 177 }


xcvrHistPMUASSTimeStamp OBJECT-TYPE
    SYNTAX       DateAndTime
    MAX-ACCESS   read-only
    STATUS       current
    DESCRIPTION  "The date and time stamp of the section layer unavailable
                  seconds value."
    ::= { xcvrHistPMEntry 178 }


xcvrHistPMUASSValidity OBJECT-TYPE
    SYNTAX       PMValidity
    MAX-ACCESS   read-only
    STATUS       current
    DESCRIPTION  "Indicates the validity of the provided section layer
                  unavailable seconds value."
    ::= { xcvrHistPMEntry 179 }


xcvrHistPMUASSInitialize OBJECT-TYPE
    SYNTAX       InitializeCmd
    MAX-ACCESS   read-write
    STATUS       current
    DESCRIPTION  "Used to initialize the value of the xcvrHistPMUASSValue
                  object to 0."
    ::= { xcvrHistPMEntry 180 }


xcvrHistPMRSUASValue OBJECT-TYPE
    SYNTAX       Unsigned32
    MAX-ACCESS   read-write
    STATUS       current
    DESCRIPTION  "The count of regenerator section unavailable seconds.
                  This object applies only to transciever ports provisioned for
                  a SDH STM-N protocol."
    ::= { xcvrHistPMEntry 181 }


xcvrHistPMRSUASTimeStamp OBJECT-TYPE
    SYNTAX       DateAndTime
    MAX-ACCESS   read-only
    STATUS       current
    DESCRIPTION  "The date and time stamp of the regenerator section
                  unavailable seconds value."
    ::= { xcvrHistPMEntry 182 }


xcvrHistPMRSUASValidity OBJECT-TYPE
    SYNTAX       PMValidity
    MAX-ACCESS   read-only
    STATUS       current
    DESCRIPTION  "Indicates the validity of the provided regenerator section
                  unavailable seconds value."
    ::= { xcvrHistPMEntry 183 }


xcvrHistPMRSUASInitialize OBJECT-TYPE
    SYNTAX       InitializeCmd
    MAX-ACCESS   read-write
    STATUS       current
    DESCRIPTION  "Used to initialize the value of the xcvrHistPMRSUASValue
                  object to 0."
    ::= { xcvrHistPMEntry 184 }


xcvrHistPMUASValue OBJECT-TYPE
    SYNTAX       Unsigned32
    MAX-ACCESS   read-write
    STATUS       current
    DESCRIPTION  "The count of unavailable seconds. This object applies
                  only to transciever ports provisioned for the gigabit ethernet
                  protocol or a fiber channel protocol."
    ::= { xcvrHistPMEntry 185 }


xcvrHistPMUASTimeStamp OBJECT-TYPE
    SYNTAX       DateAndTime
    MAX-ACCESS   read-only
    STATUS       current
    DESCRIPTION  "The date and time stamp of the unavailable seconds
                  value."
    ::= { xcvrHistPMEntry 186 }


xcvrHistPMUASValidity OBJECT-TYPE
    SYNTAX       PMValidity
    MAX-ACCESS   read-only
    STATUS       current
    DESCRIPTION  "Indicates the validity of the provided unavailable
                  seconds value."
    ::= { xcvrHistPMEntry 187 }


xcvrHistPMUASInitialize OBJECT-TYPE
    SYNTAX       InitializeCmd
    MAX-ACCESS   read-write
    STATUS       current
    DESCRIPTION  "Used to initialize the value of the xcvrHistPMUASValue
                  object to 0."
    ::= { xcvrHistPMEntry 188 }


xcvrHistPMOTUUASValue OBJECT-TYPE
    SYNTAX       Unsigned32
    MAX-ACCESS   read-write
    STATUS       current
    DESCRIPTION  "The count of unavailable seconds at the OTN digital
                  wrapper layer."
    ::= { xcvrHistPMEntry 189 }


xcvrHistPMOTUUASTimeStamp OBJECT-TYPE
    SYNTAX       DateAndTime
    MAX-ACCESS   read-only
    STATUS       current
    DESCRIPTION  "The date and time stamp of the OTN digital wrapper layer
                  unavailable seconds value."
    ::= { xcvrHistPMEntry 190 }


xcvrHistPMOTUUASValidity OBJECT-TYPE
    SYNTAX       PMValidity
    MAX-ACCESS   read-only
    STATUS       current
    DESCRIPTION  "Indicates the validity of the provided OTN digital wrapper
                  layer unavailable seconds value."
    ::= { xcvrHistPMEntry 191 }


xcvrHistPMOTUUASInitialize OBJECT-TYPE
    SYNTAX       InitializeCmd
    MAX-ACCESS   read-write
    STATUS       current
    DESCRIPTION  "Used to initialize the value of the xcvrHistPMOTUUASValue
                  object to 0."
    ::= { xcvrHistPMEntry 192 }


xcvrHistPMOTNBERValue OBJECT-TYPE
    SYNTAX       DisplayString
    MAX-ACCESS   read-only
    STATUS       current
    DESCRIPTION  "The instantaneous BER of transciever ports provisioned for the 10 gigabit
                  ethernet LAN with FEC protocol."
    ::= { xcvrHistPMEntry 193 }


xcvrHistPMOTNBERTimeStamp OBJECT-TYPE
    SYNTAX       DateAndTime
    MAX-ACCESS   read-only
    STATUS       current
    DESCRIPTION  "The date and time stamp of the instantaneous BER."
    ::= { xcvrHistPMEntry 194 }


xcvrHistPMOTNBERValidity OBJECT-TYPE
    SYNTAX       PMValidity
    MAX-ACCESS   read-only
    STATUS       current
    DESCRIPTION  "Indicates the validity of the provided instantaneous BER."
    ::= { xcvrHistPMEntry 195 }

xcvrHistPMOTNBERInitialize OBJECT-TYPE
    SYNTAX       InitializeCmd
    MAX-ACCESS   read-write
    STATUS       current
    DESCRIPTION  "Used to initialize the value of the xcvrHistPMOTNBERValue
                  object to 0."
    ::= { xcvrHistPMEntry 196 }


xcvrHistPMOTNAVGBERValue OBJECT-TYPE
    SYNTAX       DisplayString
    MAX-ACCESS   read-only
    STATUS       current
    DESCRIPTION  "The interval/average BER of transciever ports provisioned for the 10 gigabit
                  ethernet LAN with FEC protocol."
    ::= { xcvrHistPMEntry 197 }


xcvrHistPMOTNAVGBERTimeStamp OBJECT-TYPE
    SYNTAX       DateAndTime
    MAX-ACCESS   read-only
    STATUS       current
    DESCRIPTION  "The date and time stamp of the interval/average BER."
    ::= { xcvrHistPMEntry 198 }


xcvrHistPMOTNAVGBERValidity OBJECT-TYPE
    SYNTAX       PMValidity
    MAX-ACCESS   read-only
    STATUS       current
    DESCRIPTION  "Indicates the validity of the provided interval/average BER."
    ::= { xcvrHistPMEntry 199 }


xcvrHistPMOTNAVGBERInitialize OBJECT-TYPE
    SYNTAX       InitializeCmd
    MAX-ACCESS   read-write
    STATUS       current
    DESCRIPTION  "Used to initialize the value of the xcvrHistPMOTNAVGBERValue
                  object to 0."
    ::= { xcvrHistPMEntry 200 }


xcvrHistPMNBITCR64BitValue OBJECT-TYPE
    SYNTAX       Unsigned64
    MAX-ACCESS   read-only
    STATUS       current
    DESCRIPTION  "The 64-bit count of the number of bits corrected. This object
                  applies only to transciever ports provisioned for a protocol
                  that includes Forward Error Correction (FEC)."
    ::= { xcvrHistPMEntry 201 }


xcvrHistPMNBITCR64BitTimeStamp OBJECT-TYPE
    SYNTAX       DateAndTime
    MAX-ACCESS   read-only
    STATUS       current
    DESCRIPTION  "The date and time stamp of the 64-bit number of bits
                  corrected value."
    ::= { xcvrHistPMEntry 202 }


xcvrHistPMNBITCR64BitValidity OBJECT-TYPE
    SYNTAX       PMValidity
    MAX-ACCESS   read-only
    STATUS       current
    DESCRIPTION  "Indicates the validity of the provided 64-bit number
                  of bits corrected value."
    ::= { xcvrHistPMEntry 203 }


xcvrHistPMNBITCR64BitInitialize OBJECT-TYPE
    SYNTAX       InitializeCmd
    MAX-ACCESS   read-write
    STATUS       current
    DESCRIPTION  "Used to initialize the value of the xcvrHistPMNBITCR64BitValue
                  object to 0."
    ::= { xcvrHistPMEntry 204 }


xcvrHistPMNBYTCR64BitValue OBJECT-TYPE
    SYNTAX       Unsigned64
    MAX-ACCESS   read-only
    STATUS       current
    DESCRIPTION  "The 64-bit count of the number of bytes corrected. This object
                  applies only to transciever ports provisioned for a protocol
                  that includes Forward Error Correction (FEC)."
    ::= { xcvrHistPMEntry 205 }


xcvrHistPMNBYTCR64BitTimeStamp OBJECT-TYPE
    SYNTAX       DateAndTime
    MAX-ACCESS   read-only
    STATUS       current
    DESCRIPTION  "The date and time stamp of the 64-bit number of bytes
                  corrected value."
    ::= { xcvrHistPMEntry 206 }


xcvrHistPMNBYTCR64BitValidity OBJECT-TYPE
    SYNTAX       PMValidity
    MAX-ACCESS   read-only
    STATUS       current
    DESCRIPTION  "Indicates the validity of the provided number of bytes
                  corrected value."
    ::= { xcvrHistPMEntry 207 }


xcvrHistPMNBYTCR64BitInitialize OBJECT-TYPE
    SYNTAX       InitializeCmd
    MAX-ACCESS   read-write
    STATUS       current
    DESCRIPTION  "Used to initialize the value of the xcvrHistPMNBYTCR64BitValue
                  object to 0."
    ::= { xcvrHistPMEntry 208 }

xcvrHistPMOPRMinValue OBJECT-TYPE
    SYNTAX       FixedX10
    UNITS        "dBm/10"
    MAX-ACCESS   read-only
    STATUS       current
    DESCRIPTION  "The minimum optical power received on the input of the transceiver."
    ::= { xcvrHistPMEntry 209 }


xcvrHistPMOPRMinTimeStamp OBJECT-TYPE
    SYNTAX       DateAndTime
    MAX-ACCESS   read-only
    STATUS       current
    DESCRIPTION  "The date and time stamp of the minimum optical power received value."
    ::= { xcvrHistPMEntry 210 }


xcvrHistPMOPRMinValidity OBJECT-TYPE
    SYNTAX       PMValidity
    MAX-ACCESS   read-only
    STATUS       current
    DESCRIPTION  "Indicates the validity of the provided minimum optical power received
                  value."
    ::= { xcvrHistPMEntry 211 }

xcvrHistPMOPRMinInitialize OBJECT-TYPE
    SYNTAX       InitializeCmd
    MAX-ACCESS   read-write
    STATUS       current
    DESCRIPTION  "Used to initialize the value of the xcvrHistPMOPRMinValue
                  object to 0."
    ::= { xcvrHistPMEntry 212 }

xcvrHistPMOPRMaxValue OBJECT-TYPE
    SYNTAX       FixedX10
    UNITS        "dBm/10"
    MAX-ACCESS   read-only
    STATUS       current
    DESCRIPTION  "The maximum optical power received on the input of the transceiver."
    ::= { xcvrHistPMEntry 213 }


xcvrHistPMOPRMaxTimeStamp OBJECT-TYPE
    SYNTAX       DateAndTime
    MAX-ACCESS   read-only
    STATUS       current
    DESCRIPTION  "The date and time stamp of the maximum optical power received value."
    ::= { xcvrHistPMEntry 214 }


xcvrHistPMOPRMaxValidity OBJECT-TYPE
    SYNTAX       PMValidity
    MAX-ACCESS   read-only
    STATUS       current
    DESCRIPTION  "Indicates the validity of the provided maximum optical power received
                  value."
    ::= { xcvrHistPMEntry 215 }

xcvrHistPMOPRMaxInitialize OBJECT-TYPE
    SYNTAX       InitializeCmd
    MAX-ACCESS   read-write
    STATUS       current
    DESCRIPTION  "Used to initialize the value of the xcvrHistPMOPRMaxValue
                  object to 0."
    ::= { xcvrHistPMEntry 216 }

xcvrHistPMOPRAvgValue OBJECT-TYPE
    SYNTAX       FixedX10
    UNITS        "dBm/10"
    MAX-ACCESS   read-only
    STATUS       current
    DESCRIPTION  "The average optical power received on the input of the transceiver."
    ::= { xcvrHistPMEntry 217 }


xcvrHistPMOPRAvgTimeStamp OBJECT-TYPE
    SYNTAX       DateAndTime
    MAX-ACCESS   read-only
    STATUS       current
    DESCRIPTION  "The date and time stamp of the average optical power received value."
    ::= { xcvrHistPMEntry 218 }


xcvrHistPMOPRAvgValidity OBJECT-TYPE
    SYNTAX       PMValidity
    MAX-ACCESS   read-only
    STATUS       current
    DESCRIPTION  "Indicates the validity of the provided average optical power received
                  value."
    ::= { xcvrHistPMEntry 219 }

xcvrHistPMOPRAvgInitialize OBJECT-TYPE
    SYNTAX       InitializeCmd
    MAX-ACCESS   read-write
    STATUS       current
    DESCRIPTION  "Used to initialize the value of the xcvrHistPMOPRAvgValue
                  object to 0."
    ::= { xcvrHistPMEntry 220 }

xcvrHistPMOPTMinValue OBJECT-TYPE
    SYNTAX       FixedX10
    UNITS        "dBm/10"
    MAX-ACCESS   read-only
    STATUS       current
    DESCRIPTION  "The minimum optical power transmitted at the output of the
                  transceiver."
    ::= { xcvrHistPMEntry 221 }

xcvrHistPMOPTMinTimeStamp OBJECT-TYPE
    SYNTAX       DateAndTime
    MAX-ACCESS   read-only
    STATUS       current
    DESCRIPTION  "The date and time stamp of the minimum optical power transmitted
                  value."
    ::= { xcvrHistPMEntry 222 }


xcvrHistPMOPTMinValidity OBJECT-TYPE
    SYNTAX       PMValidity
    MAX-ACCESS   read-only
    STATUS       current
    DESCRIPTION  "Indicates the validity of the provided minimum optical power
                  transmitted value."
    ::= { xcvrHistPMEntry 223 }

xcvrHistPMOPTMinInitialize OBJECT-TYPE
    SYNTAX       InitializeCmd
    MAX-ACCESS   read-write
    STATUS       current
    DESCRIPTION  "Used to initialize the value of the xcvrHistPMOPTMinValue
                  object to 0."
    ::= { xcvrHistPMEntry 224 }

xcvrHistPMOPTMaxValue OBJECT-TYPE
    SYNTAX       FixedX10
    UNITS        "dBm/10"
    MAX-ACCESS   read-only
    STATUS       current
    DESCRIPTION  "The maximum optical power transmitted at the output of the
                  transceiver."
    ::= { xcvrHistPMEntry 225 }


xcvrHistPMOPTMaxTimeStamp OBJECT-TYPE
    SYNTAX       DateAndTime
    MAX-ACCESS   read-only
    STATUS       current
    DESCRIPTION  "The date and time stamp of the maximum optical power transmitted
                  value."
    ::= { xcvrHistPMEntry 226 }


xcvrHistPMOPTMaxValidity OBJECT-TYPE
    SYNTAX       PMValidity
    MAX-ACCESS   read-only
    STATUS       current
    DESCRIPTION  "Indicates the validity of the provided maximum optical power
                  transmitted value."
    ::= { xcvrHistPMEntry 227 }

xcvrHistPMOPTMaxInitialize OBJECT-TYPE
    SYNTAX       InitializeCmd
    MAX-ACCESS   read-write
    STATUS       current
    DESCRIPTION  "Used to initialize the value of the xcvrHistPMOPTMaxValue
                  object to 0."
    ::= { xcvrHistPMEntry 228 }

xcvrHistPMOPTAvgValue OBJECT-TYPE
    SYNTAX       FixedX10
    UNITS        "dBm/10"
    MAX-ACCESS   read-only
    STATUS       current
    DESCRIPTION  "The average optical power transmitted at the output of the
                  transceiver."
    ::= { xcvrHistPMEntry 229 }


xcvrHistPMOPTAvgTimeStamp OBJECT-TYPE
    SYNTAX       DateAndTime
    MAX-ACCESS   read-only
    STATUS       current
    DESCRIPTION  "The date and time stamp of the average optical power transmitted
                  value."
    ::= { xcvrHistPMEntry 230 }

xcvrHistPMOPTAvgValidity OBJECT-TYPE
    SYNTAX       PMValidity
    MAX-ACCESS   read-only
    STATUS       current
    DESCRIPTION  "Indicates the validity of the provided average optical power
                  transmitted value."
    ::= { xcvrHistPMEntry 231 }

xcvrHistPMOPTAvgInitialize OBJECT-TYPE
    SYNTAX       InitializeCmd
    MAX-ACCESS   read-write
    STATUS       current
    DESCRIPTION  "Used to initialize the value of the xcvrHistPMOPTAvgValue
                  object to 0."
    ::= { xcvrHistPMEntry 232 }

-----------------------------------------------------------------------
-- Objects used to manage Optical Transceiver Performance
-- Monitoring Threshold Levels
-- 
-- A listing of transceiver PM threshold levels are contained in the
-- xcvrPMThresholdTable of the BTI 7000 Series MIB. When retrieved, this 
-- table provides one row for each optical transceiver, providing the 
-- PM threshold settings for that transceiver for a given interval type.
-- 
-- The following table lists the objects in each entry of the 
-- xcvrPMThresholdTable.
-----------------------------------------------------------------------


xcvrPMThresholdTable OBJECT-TYPE
    SYNTAX       SEQUENCE OF XcvrPMThresholdEntry
    MAX-ACCESS   not-accessible
    STATUS       current
    DESCRIPTION  "A table of threshold levels for performance monitoring counter
                  values on optical transceiver facilities, that are used in the
                  generation of threshold crossing alerts."
    ::= { performance 5 }


xcvrPMThresholdEntry OBJECT-TYPE
    SYNTAX       XcvrPMThresholdEntry
    MAX-ACCESS   not-accessible
    STATUS       current
    DESCRIPTION  "The row entry object of the optical transceiver performance
                  monitoring threshold table. Each row of this table contains a
                  set of PM thresholds for a given interval type that applies to
                  an individual optical transceiver."
    INDEX        { xcvrPMThresholdTypeIdx,
                   xcvrPMThresholdShelfIdx,
                   xcvrPMThresholdSlotIdx,
                   xcvrPMThresholdIdx,
                   xcvrPMThresholdIntervalTypeIdx }
    ::= { xcvrPMThresholdTable 1 }


XcvrPMThresholdEntry ::= SEQUENCE { xcvrPMThresholdTypeIdx          XcvrType,
                                    xcvrPMThresholdShelfIdx         INTEGER,
                                    xcvrPMThresholdSlotIdx          INTEGER,
                                    xcvrPMThresholdIdx              INTEGER,
                                    xcvrPMThresholdIntervalTypeIdx  PMIntervalType,
                                    xcvrPMThresholdCVSValue         Unsigned32,
                                    xcvrPMThresholdESSValue         Unsigned32,
                                    xcvrPMThresholdSESSValue        Unsigned32,
                                    xcvrPMThresholdSEFSSValue       Unsigned32,
                                    xcvrPMThresholdRSEBValue        Unsigned32,
                                    xcvrPMThresholdRSBBEValue       Unsigned32,
                                    xcvrPMThresholdRSESValue        Unsigned32,
                                    xcvrPMThresholdRSSESValue       Unsigned32,
                                    xcvrPMThresholdRSOFSValue       Unsigned32,
                                    xcvrPMThresholdCVValue          Unsigned32,
                                    xcvrPMThresholdESValue          Unsigned32,
                                    xcvrPMThresholdSESValue         Unsigned32,
                                    xcvrPMThresholdINVBLKValue      Unsigned32,
                                    xcvrPMThresholdUNCRCDWValue     Unsigned32,
                                    xcvrPMThresholdFCSEValue        Unsigned32,
                                    xcvrPMThresholdFRDRValue        Unsigned32,
                                    xcvrPMThresholdUSIZEValue       Unsigned32,
                                    xcvrPMThresholdOSIZEValue       Unsigned32,
                                    xcvrPMThresholdFRGTValue        Unsigned32,
                                    xcvrPMThresholdJABRValue        Unsigned32,
                                    xcvrPMThresholdOTUEBValue       Unsigned32,
                                    xcvrPMThresholdOTUBBEValue      Unsigned32,
                                    xcvrPMThresholdOTUESValue       Unsigned32,
                                    xcvrPMThresholdOTUSESValue      Unsigned32,
                                    xcvrPMThresholdOTUOFSValue      Unsigned32,
                                    xcvrPMThresholdUASSValue        Unsigned32,
                                    xcvrPMThresholdRSUASValue       Unsigned32,
                                    xcvrPMThresholdUASValue         Unsigned32,
                                    xcvrPMThresholdOTUUASValue      Unsigned32 }
      

xcvrPMThresholdTypeIdx OBJECT-TYPE
    SYNTAX       XcvrType
    MAX-ACCESS   not-accessible
    STATUS       current
    DESCRIPTION  "The type of the optical transceiver targeted for PM
                  thresholds."
    ::= { xcvrPMThresholdEntry 1 }


xcvrPMThresholdShelfIdx OBJECT-TYPE
    SYNTAX       INTEGER (1|11|21|31)
    MAX-ACCESS   not-accessible
    STATUS       current
    DESCRIPTION  "The shelf number on which the optical transceiver targeted for
                  PM thresholds is provisioned."
    ::= { xcvrPMThresholdEntry 2 }


xcvrPMThresholdSlotIdx OBJECT-TYPE
    SYNTAX       INTEGER (1..20)
    MAX-ACCESS   not-accessible
    STATUS       current
    DESCRIPTION  "The slot number on which the optical transceiver targeted for
                  PM thresholds is provisioned."
    ::= { xcvrPMThresholdEntry 3 }


xcvrPMThresholdIdx OBJECT-TYPE
    SYNTAX       INTEGER (1..4)
    MAX-ACCESS   not-accessible
    STATUS       current
    DESCRIPTION  "The optical transceiver port number on the circuit pack that
                  is targeted for PM thresholds."
    ::= { xcvrPMThresholdEntry 4 }


xcvrPMThresholdIntervalTypeIdx OBJECT-TYPE
    SYNTAX       PMIntervalType
    MAX-ACCESS   not-accessible
    STATUS       current
    DESCRIPTION  "The type of PM bin according to interval length. Thresholds
                  are supported for the 15-minute and 1-day PM bins only."
    ::= { xcvrPMThresholdEntry 5 }


xcvrPMThresholdCVSValue OBJECT-TYPE
    SYNTAX       Unsigned32
    MAX-ACCESS   read-write
    STATUS       current
    DESCRIPTION  "The threshold for the count of coding violations at the
                  section layer. This object applies only to transciever ports
                  provisioned for a SONET OC-N protocol."
    ::= { xcvrPMThresholdEntry 6 }


xcvrPMThresholdESSValue OBJECT-TYPE
    SYNTAX       Unsigned32
    MAX-ACCESS   read-write
    STATUS       current
    DESCRIPTION  "The threshold for the count of errored seconds at the section
                  layer. This object applies only to transciever ports
                  provisioned for a SONET OC-N protocol."
    ::= { xcvrPMThresholdEntry 7 }


xcvrPMThresholdSESSValue OBJECT-TYPE
    SYNTAX       Unsigned32
    MAX-ACCESS   read-write
    STATUS       current
    DESCRIPTION  "The threshold fro the count of severely errored seconds at the
                  section layer. This object applies only to transciever ports
                  provisioned for a SONET OC-N protocol."
    ::= { xcvrPMThresholdEntry 8 }


xcvrPMThresholdSEFSSValue OBJECT-TYPE
    SYNTAX       Unsigned32
    MAX-ACCESS   read-write
    STATUS       current
    DESCRIPTION  "The threshold for the count of severely errored framing
                  seconds at the section layer. This object applies only to
                  transciever ports provisioned for a SONET OC-N protocol."
    ::= { xcvrPMThresholdEntry 9 }


xcvrPMThresholdRSEBValue OBJECT-TYPE
    SYNTAX       Unsigned32
    MAX-ACCESS   read-write
    STATUS       current
    DESCRIPTION  "The threshold for the count of regenerator section errored
                  blocks. This object applies only to transciever ports
                  provisioned for a SDH STM-N protocol."
    ::= { xcvrPMThresholdEntry 10 }


xcvrPMThresholdRSBBEValue OBJECT-TYPE
    SYNTAX       Unsigned32
    MAX-ACCESS   read-write
    STATUS       current
    DESCRIPTION  "The threshold for the count of regenerator section background
                  block errors. This object applies only to transciever ports
                  provisioned for a SDH STM-N protocol."
    ::= { xcvrPMThresholdEntry 11 }


xcvrPMThresholdRSESValue OBJECT-TYPE
    SYNTAX       Unsigned32
    MAX-ACCESS   read-write
    STATUS       current
    DESCRIPTION  "The threshold for the count of regenerator section errored
                  seconds. This object applies only to transciever ports
                  provisioned for a SDH STM-N protocol."
    ::= { xcvrPMThresholdEntry 12 }


xcvrPMThresholdRSSESValue OBJECT-TYPE
    SYNTAX       Unsigned32
    MAX-ACCESS   read-write
    STATUS       current
    DESCRIPTION  "The threshold for the count of regenerator section severely
                  errored seconds. This object applies only to transciever ports
                  provisioned for a SDH STM-N protocol."
    ::= { xcvrPMThresholdEntry 13 }


xcvrPMThresholdRSOFSValue OBJECT-TYPE
    SYNTAX       Unsigned32
    MAX-ACCESS   read-write
    STATUS       current
    DESCRIPTION  "The threshold for the count of regenerator section
                  out-of-frame seconds. This object applies only to transciever
                  ports provisioned for a SDH STM-N protocol."
    ::= { xcvrPMThresholdEntry 14 }


xcvrPMThresholdCVValue OBJECT-TYPE
    SYNTAX       Unsigned32
    MAX-ACCESS   read-write
    STATUS       current
    DESCRIPTION  "The threshold for the count of coding violations. This object
                  applies only to transciever ports provisioned for the gigabit
                  ethernet protocol or a fiber channel protocol."
    ::= { xcvrPMThresholdEntry 15 }


xcvrPMThresholdESValue OBJECT-TYPE
    SYNTAX       Unsigned32
    MAX-ACCESS   read-write
    STATUS       current
    DESCRIPTION  "The threshold for the count of errored seconds. This object
                  applies only to transciever ports provisioned for an
                  ethernet protocol or a fiber channel protocol."
    ::= { xcvrPMThresholdEntry 16 }


xcvrPMThresholdSESValue OBJECT-TYPE
    SYNTAX       Unsigned32
    MAX-ACCESS   read-write
    STATUS       current
    DESCRIPTION  "The threshold for the count of severely errored seconds. This
                  object applies only to transciever ports provisioned for an
                  ethernet protocol or a fiber channel protocol."
    ::= { xcvrPMThresholdEntry 17 }


xcvrPMThresholdINVBLKValue OBJECT-TYPE
    SYNTAX       Unsigned32
    MAX-ACCESS   read-write
    STATUS       current
    DESCRIPTION  "The threshold for the count of invalid blocks. This object
                  applies only to transciever ports provisioned for the 10
                  gigabit ethernet LAN protocol."
    ::= { xcvrPMThresholdEntry 18 }


xcvrPMThresholdUNCRCDWValue OBJECT-TYPE
    SYNTAX       Unsigned32
    MAX-ACCESS   read-write
    STATUS       current
    DESCRIPTION  "The threshold for the count of uncorrectable codewords. This
                  object applies only to transciever ports provisioned for the
                  10 gigabit ethernet LAN with FEC protocol."
    ::= { xcvrPMThresholdEntry 21 }


xcvrPMThresholdFCSEValue OBJECT-TYPE
    SYNTAX       Unsigned32
    MAX-ACCESS   read-write
    STATUS       current
    DESCRIPTION  "The threshold for the count of FCSE packets. This object
                  applies only to transceiver ports provisioned for the 10
                  gigabit ethernet LAN protocol."
    ::= { xcvrPMThresholdEntry 22 }


xcvrPMThresholdFRDRValue OBJECT-TYPE
    SYNTAX       Unsigned32
    MAX-ACCESS   read-write
    STATUS       current
    DESCRIPTION  "The threshold for the count of dropped frames. This object
                  applies only to transceiver ports provisioned for the 10
                  gigabit ethernet LAN protocol."
    ::= { xcvrPMThresholdEntry 23 }


xcvrPMThresholdUSIZEValue OBJECT-TYPE
    SYNTAX       Unsigned32
    MAX-ACCESS   read-write
    STATUS       current
    DESCRIPTION  "The threshold for the count of undersized frames. This object
                  applies only to transceiver ports provisioned for the 10
                  gigabit ethernet LAN protocol."
    ::= { xcvrPMThresholdEntry 24 }


xcvrPMThresholdOSIZEValue OBJECT-TYPE
    SYNTAX       Unsigned32
    MAX-ACCESS   read-write
    STATUS       current
    DESCRIPTION  "The threshold for the count of oversized frames. This object
                  applies only to transceiver ports provisioned for the 10
                  gigabit ethernet LAN protocol."
    ::= { xcvrPMThresholdEntry 25 }


xcvrPMThresholdFRGTValue OBJECT-TYPE
    SYNTAX       Unsigned32
    MAX-ACCESS   read-write
    STATUS       current
    DESCRIPTION  "The threshold for the count of frame fragments. This object
                  applies only to transceiver ports provisioned for the 10
                  gigabit ethernet LAN protocol."
    ::= { xcvrPMThresholdEntry 26 }


xcvrPMThresholdJABRValue OBJECT-TYPE
    SYNTAX       Unsigned32
    MAX-ACCESS   read-write
    STATUS       current
    DESCRIPTION  "The threshold for the count of jabbers. This object applies
                  only to transceiver ports provisioned for the 10 gigabit
                  ethernet LAN protocol."
    ::= { xcvrPMThresholdEntry 27 }


xcvrPMThresholdOTUEBValue OBJECT-TYPE
    SYNTAX       Unsigned32
    MAX-ACCESS   read-write
    STATUS       current
    DESCRIPTION  "The threshold for the count of errored blocks at the OTN
                  digital wrapper layer."
    ::= { xcvrPMThresholdEntry 28 }


xcvrPMThresholdOTUBBEValue OBJECT-TYPE
    SYNTAX       Unsigned32
    MAX-ACCESS   read-write
    STATUS       current
    DESCRIPTION  "The threshold for the count of background block errors at the
                  OTN digital wrapper layer."
    ::= { xcvrPMThresholdEntry 29 }


xcvrPMThresholdOTUESValue OBJECT-TYPE
    SYNTAX       Unsigned32
    MAX-ACCESS   read-write
    STATUS       current
    DESCRIPTION  "The threshold for the count of errored seconds at the OTN
                  digital wrapper layer."
    ::= { xcvrPMThresholdEntry 30 }


xcvrPMThresholdOTUSESValue OBJECT-TYPE
    SYNTAX       Unsigned32
    MAX-ACCESS   read-write
    STATUS       current
    DESCRIPTION  "The threshold for the count of severely errored seconds at the
                  OTN digital wrapper layer."
    ::= { xcvrPMThresholdEntry 31 }


xcvrPMThresholdOTUOFSValue OBJECT-TYPE
    SYNTAX       Unsigned32
    MAX-ACCESS   read-write
    STATUS       current
    DESCRIPTION  "The threshold for the count of Out-of-Frame seconds at the OTN
                  digital wrapper layer."
    ::= { xcvrPMThresholdEntry 32 }


xcvrPMThresholdUASSValue OBJECT-TYPE
    SYNTAX       Unsigned32
    MAX-ACCESS   read-write
    STATUS       current
    DESCRIPTION  "The threshold for the count of unavailable seconds at the
                  section layer. This object applies only to transciever ports
                  provisioned for a SONET OC-N protocol."
    ::= { xcvrPMThresholdEntry 33 }


xcvrPMThresholdRSUASValue OBJECT-TYPE
    SYNTAX       Unsigned32
    MAX-ACCESS   read-write
    STATUS       current
    DESCRIPTION  "The threshold for the count of regenerator section
                  unavailable seconds. This object applies only to transciever
                  ports provisioned for a SDH STM-N protocol."
    ::= { xcvrPMThresholdEntry 34 }


xcvrPMThresholdUASValue OBJECT-TYPE
    SYNTAX       Unsigned32
    MAX-ACCESS   read-write
    STATUS       current
    DESCRIPTION  "The threshold for the count of unavailable seconds. This
                  object applies only to transciever ports provisioned for an
                  ethernet protocol or a fiber channel protocol."
    ::= { xcvrPMThresholdEntry 35 }


xcvrPMThresholdOTUUASValue OBJECT-TYPE
    SYNTAX       Unsigned32
    MAX-ACCESS   read-write
    STATUS       current
    DESCRIPTION  "The threshold for the count of unavailable seconds at the
                  OTN digital wrapper layer."
    ::= { xcvrPMThresholdEntry 36 }



-----------------------------------------------------------------------
-- Objects used to retrieve current Active Multiplexer-
-- Demultiplexer Performance Monitoring statistics
-- 
-- A listing of current active multiplexer-demultiplexer PM values is 
-- contained in the amdCrntPMTable of the BTI 7000 Series MIB. When 
-- retrieved, this table provides one row for each set of current active 
-- multiplexer-demultiplexer PM data.
-- 
-- The following table lists the objects in each entry of the 
-- amdCrntPMTable.
-----------------------------------------------------------------------


amdCrntPMTable OBJECT-TYPE
    SYNTAX       SEQUENCE OF AmdCrntPMEntry
    MAX-ACCESS   not-accessible
    STATUS       obsolete
    DESCRIPTION  "A table of current performance monitoring statistics collected
                  for the ports of active multiplexer-demultiplexer circuit
                  packs."
    ::= { performance 6 }


amdCrntPMEntry OBJECT-TYPE
    SYNTAX       AmdCrntPMEntry
    MAX-ACCESS   not-accessible
    STATUS       obsolete
    DESCRIPTION  "The row entry object of the active multiplexer-demultiplexer
                  current performance monitoring table. Each row of this table
                  contains a full set of PM statistics and related data for a
                  current measurement interval for a given AMD port."
    INDEX        { amdCrntPMTypeIdx,
                   amdCrntPMShelfIdx,
                   amdCrntPMSlotIdx,
                   amdCrntPMLineIdx,
                   amdCrntPMPortIdx,
                   amdCrntPMIntervalTypeIdx }
    ::= { amdCrntPMTable 1 }


AmdCrntPMEntry ::= SEQUENCE { amdCrntPMTypeIdx                 AmdType,
                              amdCrntPMShelfIdx                INTEGER,
                              amdCrntPMSlotIdx                 INTEGER,
                              amdCrntPMLineIdx                 INTEGER,
                              amdCrntPMPortIdx                 AmdPortType,
                              amdCrntPMIntervalTypeIdx         PMIntervalType,
                              amdCrntPMOPRValue                FixedX10,
                              amdCrntPMOPRTimeStamp            DateAndTime,
                              amdCrntPMOPRValidity             PMValidity,
                              amdCrntPMOPTValue                FixedX10,
                              amdCrntPMOPTTimeStamp            DateAndTime,
                              amdCrntPMOPTValidity             PMValidity,
                              amdCrntPMVOAValue                FixedX10,
                              amdCrntPMVOATimeStamp            DateAndTime,
                              amdCrntPMVOAValidity             PMValidity,
                              amdCrntPMLitChnValue             INTEGER,
                              amdCrntPMLitChnTimeStamp         DateAndTime,
                              amdCrntPMLitChnValidity          PMValidity }


amdCrntPMTypeIdx OBJECT-TYPE
    SYNTAX       AmdType
    MAX-ACCESS   not-accessible
    STATUS       obsolete
    DESCRIPTION  "The specific type of active multiplexer-demultiplexer circuit
                  pack on which the facility targeted for PMs is provisioned."
    ::= { amdCrntPMEntry 1 }


amdCrntPMShelfIdx OBJECT-TYPE
    SYNTAX       INTEGER (1|11|21|31)
    MAX-ACCESS   not-accessible
    STATUS       obsolete
    DESCRIPTION  "The number of the shelf on which the active
                  multiplexer-demultiplexer facility targeted for PMs is
                  provisioned."
    ::= { amdCrntPMEntry 2 }


amdCrntPMSlotIdx OBJECT-TYPE
    SYNTAX       INTEGER (1|3|5|7|9|11|13|15|17|19)
    MAX-ACCESS   not-accessible
    STATUS       obsolete
    DESCRIPTION  "The number of the slot within which the active
                  multiplexer-demultiplexer facility targeted for PMs is
                  provisioned."
    ::= { amdCrntPMEntry 3 }


amdCrntPMLineIdx OBJECT-TYPE
    SYNTAX       INTEGER (1..1)
    MAX-ACCESS   not-accessible
    STATUS       obsolete
    DESCRIPTION  "The number of the multiplexed wavelength line on the AMD
                  circuit pack that is targeted for PMs."
    ::= { amdCrntPMEntry 4 }


amdCrntPMPortIdx OBJECT-TYPE
    SYNTAX       AmdPortType
    MAX-ACCESS   not-accessible
    STATUS       obsolete
    DESCRIPTION  "Identifies a specific port on the identified line of the AMD
                  circuit pack that is targeted for PMs."
    ::= { amdCrntPMEntry 5 }


amdCrntPMIntervalTypeIdx OBJECT-TYPE
    SYNTAX       PMIntervalType
    MAX-ACCESS   not-accessible
    STATUS       obsolete
    DESCRIPTION  "The type of PM bin according to interval length."
    ::= { amdCrntPMEntry 6 }


amdCrntPMOPRValue OBJECT-TYPE
    SYNTAX       FixedX10
    UNITS        "dBm/10"
    MAX-ACCESS   read-only
    STATUS       obsolete
    DESCRIPTION  "The optical power received on the input of the AMD port."
    ::= { amdCrntPMEntry 7 }


amdCrntPMOPRTimeStamp OBJECT-TYPE
    SYNTAX       DateAndTime
    MAX-ACCESS   read-only
    STATUS       obsolete
    DESCRIPTION  "The date and time stamp of the optical power received value."
    ::= { amdCrntPMEntry 8 }


amdCrntPMOPRValidity OBJECT-TYPE
    SYNTAX       PMValidity
    MAX-ACCESS   read-only
    STATUS       obsolete
    DESCRIPTION  "Indicates the validity of the provided optical power received
                  value."
    ::= { amdCrntPMEntry 9 }


amdCrntPMOPTValue OBJECT-TYPE
    SYNTAX       FixedX10
    UNITS        "dBm/10"
    MAX-ACCESS   read-only
    STATUS       obsolete
    DESCRIPTION  "The optical power transmitted at the output of the AMD port."
    ::= { amdCrntPMEntry 10 }


amdCrntPMOPTTimeStamp OBJECT-TYPE
    SYNTAX       DateAndTime
    MAX-ACCESS   read-only
    STATUS       obsolete
    DESCRIPTION  "The date and time stamp of the optical power transmitted
                  value."
    ::= { amdCrntPMEntry 11 }


amdCrntPMOPTValidity OBJECT-TYPE
    SYNTAX       PMValidity
    MAX-ACCESS   read-only
    STATUS       obsolete
    DESCRIPTION  "Indicates the validity of the provided optical power
                  transmitted value."
    ::= { amdCrntPMEntry 12 }


amdCrntPMVOAValue OBJECT-TYPE
    SYNTAX       FixedX10
    UNITS        "dB/10"
    MAX-ACCESS   read-only
    STATUS       obsolete
    DESCRIPTION  "The variable optical attenuation of the AMD port."
    ::= { amdCrntPMEntry 13 }


amdCrntPMVOATimeStamp OBJECT-TYPE
    SYNTAX       DateAndTime
    MAX-ACCESS   read-only
    STATUS       obsolete
    DESCRIPTION  "The date and time stamp of the variable optical attenuation
                  value."
    ::= { amdCrntPMEntry 14 }


amdCrntPMVOAValidity OBJECT-TYPE
    SYNTAX       PMValidity
    MAX-ACCESS   read-only
    STATUS       obsolete
    DESCRIPTION  "Indicates the validity of the provided variable optical
                  attenuation value."
    ::= { amdCrntPMEntry 15 }


amdCrntPMLitChnValue OBJECT-TYPE
    SYNTAX       INTEGER(0..8)
    MAX-ACCESS   read-only
    STATUS       obsolete
    DESCRIPTION  "The number of muxed channels with light on the line port."
    ::= { amdCrntPMEntry 16 }


amdCrntPMLitChnTimeStamp OBJECT-TYPE
    SYNTAX       DateAndTime
    MAX-ACCESS   read-only
    STATUS       obsolete
    DESCRIPTION  "The date and time stamp of the number of lit channels value."
    ::= { amdCrntPMEntry 17 }


amdCrntPMLitChnValidity OBJECT-TYPE
    SYNTAX       PMValidity
    MAX-ACCESS   read-only
    STATUS       obsolete
    DESCRIPTION  "Indicates the validity of the provided number of lit channels
                  value."
    ::= { amdCrntPMEntry 18 }


-----------------------------------------------------------------------
-- Objects used to retrieve historical Active Multiplexer-
-- Demultiplexer Performance Monitoring statistics
-- 
-- A listing of historical active multiplexer-demultiplexer PM values is 
-- contained in the amdHistPMTable of the BTI 7000 Series MIB. When 
-- retrieved, this table provides one row for each set of historical 
-- active multiplexer-demultiplexer PM data.
-- 
-- The following table lists the objects in each entry of the 
-- amdHistPMTable.
-----------------------------------------------------------------------


amdHistPMTable OBJECT-TYPE
    SYNTAX       SEQUENCE OF AmdHistPMEntry
    MAX-ACCESS   not-accessible
    STATUS       obsolete
    DESCRIPTION  "A table of historical performance monitoring statistics
                  collected for the ports of active multiplexer-demultiplexer
                  circuit packs."
    ::= { performance 7 }


amdHistPMEntry OBJECT-TYPE
    SYNTAX       AmdHistPMEntry
    MAX-ACCESS   not-accessible
    STATUS       obsolete
    DESCRIPTION  "The row entry object of the active multiplexer-demultiplexer
                  historical performance monitoring table. Each row of this
                  table contains a full set of PM statistics and related data
                  for a historical measurement interval for a given AMD port."
    INDEX        { amdHistPMTypeIdx,
                   amdHistPMShelfIdx,
                   amdHistPMSlotIdx,
                   amdHistPMLineIdx,
                   amdHistPMPortIdx,
                   amdHistPMIntervalTypeIdx,
                   amdHistPMIntervalIdx }
    ::= { amdHistPMTable 1 }


AmdHistPMEntry ::= SEQUENCE { amdHistPMTypeIdx                 AmdType,
                              amdHistPMShelfIdx                INTEGER,
                              amdHistPMSlotIdx                 INTEGER,
                              amdHistPMLineIdx                 INTEGER,
                              amdHistPMPortIdx                 AmdPortType,
                              amdHistPMIntervalTypeIdx         PMIntervalType,
                              amdHistPMIntervalIdx             INTEGER,
                              amdHistPMOPRValue                FixedX10,
                              amdHistPMOPRTimeStamp            DateAndTime,
                              amdHistPMOPRValidity             PMValidity,
                              amdHistPMOPTValue                FixedX10,
                              amdHistPMOPTTimeStamp            DateAndTime,
                              amdHistPMOPTValidity             PMValidity,
                              amdHistPMVOAValue                FixedX10,
                              amdHistPMVOATimeStamp            DateAndTime,
                              amdHistPMVOAValidity             PMValidity,
                              amdHistPMLitChnValue             INTEGER,
                              amdHistPMLitChnTimeStamp         DateAndTime,
                              amdHistPMLitChnValidity          PMValidity }


amdHistPMTypeIdx OBJECT-TYPE
    SYNTAX       AmdType
    MAX-ACCESS   not-accessible
    STATUS       obsolete
    DESCRIPTION  "The specific type of active multiplexer-demultiplexer circuit
                  pack on which the facility targeted for PMs is provisioned."
    ::= { amdHistPMEntry 1 }


amdHistPMShelfIdx OBJECT-TYPE
    SYNTAX       INTEGER (1|11|21|31)
    MAX-ACCESS   not-accessible
    STATUS       obsolete
    DESCRIPTION  "The number of the shelf on which the active
                  multiplexer-demultiplexer facility targeted for PMs is
                  provisioned."
    ::= { amdHistPMEntry 2 }


amdHistPMSlotIdx OBJECT-TYPE
    SYNTAX       INTEGER (1|3|5|7|9|11|13|15|17|19)
    MAX-ACCESS   not-accessible
    STATUS       obsolete
    DESCRIPTION  "The number of the slot within which the active
                  multiplexer-demultiplexer facility targeted for PMs is
                  provisioned."
    ::= { amdHistPMEntry 3 }


amdHistPMLineIdx OBJECT-TYPE
    SYNTAX       INTEGER (1..1)
    MAX-ACCESS   not-accessible
    STATUS       obsolete
    DESCRIPTION  "The number of the multiplexed wavelength line on the AMD
                  circuit pack that is targeted for PMs."
    ::= { amdHistPMEntry 4 }


amdHistPMPortIdx OBJECT-TYPE
    SYNTAX       AmdPortType
    MAX-ACCESS   not-accessible
    STATUS       obsolete
    DESCRIPTION  "Identifies a specific port on the identified line of the AMD
                  circuit pack that is targeted for PMs."
    ::= { amdHistPMEntry 5 }


amdHistPMIntervalTypeIdx OBJECT-TYPE
    SYNTAX       PMIntervalType
    MAX-ACCESS   not-accessible
    STATUS       obsolete
    DESCRIPTION  "The type of PM bin according to interval length."
    ::= { amdHistPMEntry 6 }


amdHistPMIntervalIdx OBJECT-TYPE
    SYNTAX       INTEGER (1..96)
    MAX-ACCESS   not-accessible
    STATUS       obsolete
    DESCRIPTION  "The specific PM bin number. The range is 1 to 96 for the
                  15-minute historical bins. For the 1-day historical bin, the
                  value is 1."
    ::= { amdHistPMEntry 7 }


amdHistPMOPRValue OBJECT-TYPE
    SYNTAX       FixedX10
    UNITS        "dBm/10"
    MAX-ACCESS   read-only
    STATUS       obsolete
    DESCRIPTION  "The optical power received on the input of the AMD port."
    ::= { amdHistPMEntry 8 }


amdHistPMOPRTimeStamp OBJECT-TYPE
    SYNTAX       DateAndTime
    MAX-ACCESS   read-only
    STATUS       obsolete
    DESCRIPTION  "The date and time stamp of the optical power received value."
    ::= { amdHistPMEntry 9 }


amdHistPMOPRValidity OBJECT-TYPE
    SYNTAX       PMValidity
    MAX-ACCESS   read-only
    STATUS       obsolete
    DESCRIPTION  "Indicates the validity of the provided optical power received
                  value."
    ::= { amdHistPMEntry 10 }


amdHistPMOPTValue OBJECT-TYPE
    SYNTAX       FixedX10
    UNITS        "dBm/10"
    MAX-ACCESS   read-only
    STATUS       obsolete
    DESCRIPTION  "The optical power transmitted at the output of the AMD port."
    ::= { amdHistPMEntry 11 }


amdHistPMOPTTimeStamp OBJECT-TYPE
    SYNTAX       DateAndTime
    MAX-ACCESS   read-only
    STATUS       obsolete
    DESCRIPTION  "The date and time stamp of the optical power transmitted
                  value."
    ::= { amdHistPMEntry 12 }


amdHistPMOPTValidity OBJECT-TYPE
    SYNTAX       PMValidity
    MAX-ACCESS   read-only
    STATUS       obsolete
    DESCRIPTION  "Indicates the validity of the provided optical power
                  transmitted value."
    ::= { amdHistPMEntry 13 }


amdHistPMVOAValue OBJECT-TYPE
    SYNTAX       FixedX10
    UNITS        "dB/10"
    MAX-ACCESS   read-only
    STATUS       obsolete
    DESCRIPTION  "The variable optical attenuation of the AMD port."
    ::= { amdHistPMEntry 14 }


amdHistPMVOATimeStamp OBJECT-TYPE
    SYNTAX       DateAndTime
    MAX-ACCESS   read-only
    STATUS       obsolete
    DESCRIPTION  "The date and time stamp of the variable optical attenuation
                  value."
    ::= { amdHistPMEntry 15 }


amdHistPMVOAValidity OBJECT-TYPE
    SYNTAX       PMValidity
    MAX-ACCESS   read-only
    STATUS       obsolete
    DESCRIPTION  "Indicates the validity of the provided variable optical
                  attenuation valcue."
    ::= { amdHistPMEntry 16 }


amdHistPMLitChnValue OBJECT-TYPE
    SYNTAX       INTEGER(0..8)
    MAX-ACCESS   read-only
    STATUS       obsolete
    DESCRIPTION  "The number of muxed channels with light on the line port."
    ::= { amdHistPMEntry 17 }


amdHistPMLitChnTimeStamp OBJECT-TYPE
    SYNTAX       DateAndTime
    MAX-ACCESS   read-only
    STATUS       obsolete
    DESCRIPTION  "The date and time stamp of the number of lit channels value."
    ::= { amdHistPMEntry 18 }


amdHistPMLitChnValidity OBJECT-TYPE
    SYNTAX       PMValidity
    MAX-ACCESS   read-only
    STATUS       obsolete
    DESCRIPTION  "Indicates the validity of the provided number of lit channels
                  value."
    ::= { amdHistPMEntry 19 }


-----------------------------------------------------------------------
-- Objects used to retrieve current SONET OC-N
-- Performance Monitoring statistics
-- 
-- A listing of current SONET OC-N PM values is contained in the 
-- ocnCrntPMTable of the BTI 7000 Series MIB. When retrieved, this
-- table provides one row for each set of current SONET OC-N PM data.
-- 
-- The following table lists the objects in each entry of the 
-- ocnCrntPMTable.
-----------------------------------------------------------------------


ocnCrntPMTable OBJECT-TYPE
    SYNTAX       SEQUENCE OF OcnCrntPMEntry
    MAX-ACCESS   not-accessible
    STATUS       current
    DESCRIPTION  "A table of current performance monitoring statistics collected
                  for the SONET OC-N facilities on the NE."
    ::= { performance 8 }


ocnCrntPMEntry OBJECT-TYPE
    SYNTAX       OcnCrntPMEntry
    MAX-ACCESS   not-accessible
    STATUS       current
    DESCRIPTION  "The row entry object of the SONET OC-N current performance
                  monitoring table. Each row of this table contains a full set
                  of PM statistics and related data for a current measurement
                  interval for a given OC-N facility."
    INDEX        { ocnCrntPMTypeIdx,
                   ocnCrntPMShelfIdx,
                   ocnCrntPMSlotIdx,
                   ocnCrntPMPortIdx,
                   ocnCrntPMIntervalTypeIdx }
    ::= { ocnCrntPMTable 1 }


OcnCrntPMEntry ::= SEQUENCE { ocnCrntPMTypeIdx                 OcnType,
                              ocnCrntPMShelfIdx                INTEGER,
                              ocnCrntPMSlotIdx                 INTEGER,
                              ocnCrntPMPortIdx                 INTEGER,
                              ocnCrntPMIntervalTypeIdx         PMIntervalType,
                              ocnCrntPMOPRValue                FixedX10,
                              ocnCrntPMOPRTimeStamp            DateAndTime,
                              ocnCrntPMOPRValidity             PMValidity,
                              ocnCrntPMOPTValue                FixedX10,
                              ocnCrntPMOPTTimeStamp            DateAndTime,
                              ocnCrntPMOPTValidity             PMValidity,
                              ocnCrntPMTempValue               INTEGER,
                              ocnCrntPMTempTimeStamp           DateAndTime,
                              ocnCrntPMTempValidity            PMValidity,
                              ocnCrntPMSupplyVoltageValue      FixedX10,
                              ocnCrntPMSupplyVoltageTimeStamp  DateAndTime,
                              ocnCrntPMSupplyVoltageValidity   PMValidity,
                              ocnCrntPMLBCValue                INTEGER,
                              ocnCrntPMLBCTimeStamp            DateAndTime,
                              ocnCrntPMLBCValidity             PMValidity,
                              ocnCrntPMCVSValue                Unsigned32,
                              ocnCrntPMCVSTimeStamp            DateAndTime,
                              ocnCrntPMCVSValidity             PMValidity,
                              ocnCrntPMESSValue                Unsigned32,
                              ocnCrntPMESSTimeStamp            DateAndTime,
                              ocnCrntPMESSValidity             PMValidity,
                              ocnCrntPMSESSValue               Unsigned32,
                              ocnCrntPMSESSTimeStamp           DateAndTime,
                              ocnCrntPMSESSValidity            PMValidity,
                              ocnCrntPMSEFSSValue              Unsigned32,
                              ocnCrntPMSEFSSTimeStamp          DateAndTime,
                              ocnCrntPMSEFSSValidity           PMValidity,
                              ocnCrntPMSupplyVoltage2Value     FixedX10,
                              ocnCrntPMSupplyVoltage2TimeStamp DateAndTime,
                              ocnCrntPMSupplyVoltage2Validity  PMValidity,
                              ocnCrntPMCVLValue                Unsigned32,
                              ocnCrntPMCVLTimeStamp            DateAndTime,
                              ocnCrntPMCVLValidity             PMValidity,
                              ocnCrntPMESLValue                Unsigned32,
                              ocnCrntPMESLTimeStamp            DateAndTime,
                              ocnCrntPMESLValidity             PMValidity,
                              ocnCrntPMSESLValue               Unsigned32,
                              ocnCrntPMSESLTimeStamp           DateAndTime,
                              ocnCrntPMSESLValidity            PMValidity,
                              ocnCrntPMUASLValue               Unsigned32,
                              ocnCrntPMUASLTimeStamp           DateAndTime,
                              ocnCrntPMUASLValidity            PMValidity,
                              ocnCrntPMOTUEBValue              Unsigned32,
                              ocnCrntPMOTUEBTimeStamp          DateAndTime,
                              ocnCrntPMOTUEBValidity           PMValidity,
                              ocnCrntPMOTUBBEValue             Unsigned32,
                              ocnCrntPMOTUBBETimeStamp         DateAndTime,
                              ocnCrntPMOTUBBEValidity          PMValidity,
                              ocnCrntPMOTUESValue              Unsigned32,
                              ocnCrntPMOTUESTimeStamp          DateAndTime,
                              ocnCrntPMOTUESValidity           PMValidity,
                              ocnCrntPMOTUSESValue             Unsigned32,
                              ocnCrntPMOTUSESTimeStamp         DateAndTime,
                              ocnCrntPMOTUSESValidity          PMValidity,
                              ocnCrntPMOTUOFSValue             Unsigned32,
                              ocnCrntPMOTUOFSTimeStamp         DateAndTime,
                              ocnCrntPMOTUOFSValidity          PMValidity,
                              ocnCrntPMNBITCRValue             Unsigned32,
                              ocnCrntPMNBITCRTimeStamp         DateAndTime,
                              ocnCrntPMNBITCRValidity          PMValidity,
                              ocnCrntPMNBYTCRValue             Unsigned32,
                              ocnCrntPMNBYTCRTimeStamp         DateAndTime,
                              ocnCrntPMNBYTCRValidity          PMValidity,
                              ocnCrntPMUNCRCDWValue            Unsigned32,
                              ocnCrntPMUNCRCDWTimeStamp        DateAndTime,
                              ocnCrntPMUNCRCDWValidity         PMValidity,
                              ocnCrntPMCVSInitialize           InitializeCmd,
                              ocnCrntPMESSInitialize           InitializeCmd,
                              ocnCrntPMSESSInitialize          InitializeCmd,
                              ocnCrntPMSEFSSInitialize         InitializeCmd,
                              ocnCrntPMCVLInitialize           InitializeCmd,
                              ocnCrntPMESLInitialize           InitializeCmd,
                              ocnCrntPMSESLInitialize          InitializeCmd,
                              ocnCrntPMUASLInitialize          InitializeCmd,
                              ocnCrntPMOTUEBInitialize         InitializeCmd,
                              ocnCrntPMOTUBBEInitialize        InitializeCmd,
                              ocnCrntPMOTUESInitialize         InitializeCmd,
                              ocnCrntPMOTUSESInitialize        InitializeCmd,
                              ocnCrntPMOTUOFSInitialize        InitializeCmd,
                              ocnCrntPMNBITCRInitialize        InitializeCmd,
                              ocnCrntPMNBYTCRInitialize        InitializeCmd,
                              ocnCrntPMUNCRCDWInitialize       InitializeCmd,
                              ocnCrntPMOTNBERValue             DisplayString,
                              ocnCrntPMOTNBERTimeStamp         DateAndTime,
                              ocnCrntPMOTNBERValidity          PMValidity,
                              ocnCrntPMOTNBERInitialize        InitializeCmd,
                              ocnCrntPMOTNAVGBERValue          DisplayString,
                              ocnCrntPMOTNAVGBERTimeStamp      DateAndTime,
                              ocnCrntPMOTNAVGBERValidity       PMValidity,
                              ocnCrntPMOTNAVGBERInitialize     InitializeCmd,
                              ocnCrntPMNBITCR64BitValue        Unsigned64,
                              ocnCrntPMNBITCR64BitTimeStamp    DateAndTime,
                              ocnCrntPMNBITCR64BitValidity     PMValidity,
                              ocnCrntPMNBITCR64BitInitialize   InitializeCmd,
                              ocnCrntPMNBYTCR64BitValue        Unsigned64,
                              ocnCrntPMNBYTCR64BitTimeStamp    DateAndTime,
                              ocnCrntPMNBYTCR64BitValidity     PMValidity,
                              ocnCrntPMNBYTCR64BitInitialize   InitializeCmd,
                              ocnCrntPMUASSValue               Unsigned32,
                              ocnCrntPMUASSTimeStamp           DateAndTime,
                              ocnCrntPMUASSValidity            PMValidity,
                              ocnCrntPMUASSInitialize          InitializeCmd,
                              ocnCrntPMOTUUASValue             Unsigned32,
                              ocnCrntPMOTUUASTimeStamp         DateAndTime,
                              ocnCrntPMOTUUASValidity          PMValidity,
                              ocnCrntPMOTUUASInitialize        InitializeCmd,
                              ocnCrntPMOPRMinValue             FixedX10,
                              ocnCrntPMOPRMinTimeStamp         DateAndTime,
                              ocnCrntPMOPRMinValidity          PMValidity,
                              ocnCrntPMOPRMinInitialize        InitializeCmd,
                              ocnCrntPMOPRMaxValue             FixedX10,
                              ocnCrntPMOPRMaxTimeStamp         DateAndTime,
                              ocnCrntPMOPRMaxValidity          PMValidity,
                              ocnCrntPMOPRMaxInitialize        InitializeCmd,
                              ocnCrntPMOPRAvgValue             FixedX10,
                              ocnCrntPMOPRAvgTimeStamp         DateAndTime,
                              ocnCrntPMOPRAvgValidity          PMValidity,
                              ocnCrntPMOPRAvgInitialize        InitializeCmd,
                              ocnCrntPMOPTMinValue             FixedX10,
                              ocnCrntPMOPTMinTimeStamp         DateAndTime,
                              ocnCrntPMOPTMinValidity          PMValidity,
                              ocnCrntPMOPTMinInitialize        InitializeCmd,
                              ocnCrntPMOPTMaxValue             FixedX10,
                              ocnCrntPMOPTMaxTimeStamp         DateAndTime,
                              ocnCrntPMOPTMaxValidity          PMValidity,
                              ocnCrntPMOPTMaxInitialize        InitializeCmd,
                              ocnCrntPMOPTAvgValue             FixedX10,
                              ocnCrntPMOPTAvgTimeStamp         DateAndTime,
                              ocnCrntPMOPTAvgValidity          PMValidity,
                              ocnCrntPMOPTAvgInitialize        InitializeCmd }


ocnCrntPMTypeIdx OBJECT-TYPE
    SYNTAX       OcnType
    MAX-ACCESS   not-accessible
    STATUS       current
    DESCRIPTION  "The type of OC-N facility targeted for PMs."
    ::= { ocnCrntPMEntry 1 }


ocnCrntPMShelfIdx OBJECT-TYPE
    SYNTAX       INTEGER (1|11|21|31)
    MAX-ACCESS   not-accessible
    STATUS       current
    DESCRIPTION  "The number of the shelf on which the OC-N facility targeted
                  for PMs is provisioned."
    ::= { ocnCrntPMEntry 2 }


ocnCrntPMSlotIdx OBJECT-TYPE
    SYNTAX       INTEGER (1..20)
    MAX-ACCESS   not-accessible
    STATUS       current
    DESCRIPTION  "The number of the slot within which the OC-N facility targeted
                  for PMs is provisioned."
    ::= { ocnCrntPMEntry 3 }


ocnCrntPMPortIdx OBJECT-TYPE
    SYNTAX       INTEGER (1..6)
    MAX-ACCESS   not-accessible
    STATUS       current
    DESCRIPTION  "The number of the port on the circuit pack on which the OC-N
                  facility targeted for PMs is provisioned."
    ::= { ocnCrntPMEntry 4 }


ocnCrntPMIntervalTypeIdx OBJECT-TYPE
    SYNTAX       PMIntervalType
    MAX-ACCESS   not-accessible
    STATUS       current
    DESCRIPTION  "The type of PM bin according to interval length."
    ::= { ocnCrntPMEntry 5 }


ocnCrntPMOPRValue OBJECT-TYPE
    SYNTAX       FixedX10
    UNITS        "dBm/10"
    MAX-ACCESS   read-only
    STATUS       current
    DESCRIPTION  "The optical power received on the input of the OC-N facility
                  port."
    ::= { ocnCrntPMEntry 6 }


ocnCrntPMOPRTimeStamp OBJECT-TYPE
    SYNTAX       DateAndTime
    MAX-ACCESS   read-only
    STATUS       current
    DESCRIPTION  "The date and time stamp of the optical power received value."
    ::= { ocnCrntPMEntry 7 }


ocnCrntPMOPRValidity OBJECT-TYPE
    SYNTAX       PMValidity
    MAX-ACCESS   read-only
    STATUS       current
    DESCRIPTION  "Indicates the validity of the provided optical power received
                  value."
    ::= { ocnCrntPMEntry 8 }


ocnCrntPMOPTValue OBJECT-TYPE
    SYNTAX       FixedX10
    UNITS        "dBm/10"
    MAX-ACCESS   read-only
    STATUS       current
    DESCRIPTION  "The optical power transmitted at the output of the OC-N
                  facility port."
    ::= { ocnCrntPMEntry 9 }


ocnCrntPMOPTTimeStamp OBJECT-TYPE
    SYNTAX       DateAndTime
    MAX-ACCESS   read-only
    STATUS       current
    DESCRIPTION  "The date and time stamp of the optical power transmitted
                  value."
    ::= { ocnCrntPMEntry 10 }


ocnCrntPMOPTValidity OBJECT-TYPE
    SYNTAX       PMValidity
    MAX-ACCESS   read-only
    STATUS       current
    DESCRIPTION  "Indicates the validity of the provided optical power
                  transmitted value."
    ::= { ocnCrntPMEntry 11 }


ocnCrntPMTempValue OBJECT-TYPE
    SYNTAX       INTEGER (-32768..32767)
    UNITS        "degrees Celsius"
    MAX-ACCESS   read-only
    STATUS       current
    DESCRIPTION  "The temperature measured on the OC-N facility port."
    ::= { ocnCrntPMEntry 12 }


ocnCrntPMTempTimeStamp OBJECT-TYPE
    SYNTAX       DateAndTime
    MAX-ACCESS   read-only
    STATUS       current
    DESCRIPTION  "The date and time stamp of the temperature value."
    ::= { ocnCrntPMEntry 13 }


ocnCrntPMTempValidity OBJECT-TYPE
    SYNTAX       PMValidity
    MAX-ACCESS   read-only
    STATUS       current
    DESCRIPTION  "Indicates the validity of the provided temperature value."
    ::= { ocnCrntPMEntry 14 }


ocnCrntPMSupplyVoltageValue OBJECT-TYPE
    SYNTAX       FixedX10
    UNITS        "mVolts/10"
    MAX-ACCESS   read-only
    STATUS       current
    DESCRIPTION  "The supply voltage measured on the OC-N facility port."
    ::= { ocnCrntPMEntry 15 }


ocnCrntPMSupplyVoltageTimeStamp OBJECT-TYPE
    SYNTAX       DateAndTime
    MAX-ACCESS   read-only
    STATUS       current
    DESCRIPTION  "The date and time stamp of the supply voltage value."
    ::= { ocnCrntPMEntry 16 }


ocnCrntPMSupplyVoltageValidity OBJECT-TYPE
    SYNTAX       PMValidity
    MAX-ACCESS   read-only
    STATUS       current
    DESCRIPTION  "Indicates the validity of the provided supply voltage value."
    ::= { ocnCrntPMEntry 17 }


ocnCrntPMLBCValue OBJECT-TYPE
    SYNTAX       INTEGER (-32768..32767)
    UNITS        "mAmp"
    MAX-ACCESS   read-only
    STATUS       current
    DESCRIPTION  "The laser bias current measured on the OC-N facility port."
    ::= { ocnCrntPMEntry 18 }


ocnCrntPMLBCTimeStamp OBJECT-TYPE
    SYNTAX       DateAndTime
    MAX-ACCESS   read-only
    STATUS       current
    DESCRIPTION  "The date and time stamp of the laser bias current value."
    ::= { ocnCrntPMEntry 19 }


ocnCrntPMLBCValidity OBJECT-TYPE
    SYNTAX       PMValidity
    MAX-ACCESS   read-only
    STATUS       current
    DESCRIPTION  "Indicates the validity of the provided laser bias current
                  value."
    ::= { ocnCrntPMEntry 20 }


ocnCrntPMCVSValue OBJECT-TYPE
    SYNTAX       Unsigned32 
    MAX-ACCESS   read-write
    STATUS       current
    DESCRIPTION  "The count of coding violations at the section layer."
    ::= { ocnCrntPMEntry 21 }


ocnCrntPMCVSTimeStamp OBJECT-TYPE
    SYNTAX       DateAndTime
    MAX-ACCESS   read-only
    STATUS       current
    DESCRIPTION  "The date and time stamp of the section layer coding violations
                  value."
    ::= { ocnCrntPMEntry 22 }


ocnCrntPMCVSValidity OBJECT-TYPE
    SYNTAX       PMValidity
    MAX-ACCESS   read-only
    STATUS       current
    DESCRIPTION  "Indicates the validity of the provided section layer coding
                  violations value."
    ::= { ocnCrntPMEntry 23 }


ocnCrntPMESSValue OBJECT-TYPE
    SYNTAX       Unsigned32
    MAX-ACCESS   read-write
    STATUS       current
    DESCRIPTION  "The count of errored seconds at the section layer."
    ::= { ocnCrntPMEntry 24 }


ocnCrntPMESSTimeStamp OBJECT-TYPE
    SYNTAX       DateAndTime
    MAX-ACCESS   read-only
    STATUS       current
    DESCRIPTION  "The date and time stamp of the section layer errored seconds
                  value."
    ::= { ocnCrntPMEntry 25 }


ocnCrntPMESSValidity OBJECT-TYPE
    SYNTAX       PMValidity
    MAX-ACCESS   read-only
    STATUS       current
    DESCRIPTION  "Indicates the validity of the provided section layer errored
                  seconds value."
    ::= { ocnCrntPMEntry 26 }


ocnCrntPMSESSValue OBJECT-TYPE
    SYNTAX       Unsigned32
    MAX-ACCESS   read-write
    STATUS       current
    DESCRIPTION  "The count of severely errored seconds at the section layer."
    ::= { ocnCrntPMEntry 27 }


ocnCrntPMSESSTimeStamp OBJECT-TYPE
    SYNTAX       DateAndTime
    MAX-ACCESS   read-only
    STATUS       current
    DESCRIPTION  "The date and time stamp of the section layer severely errored
                  seconds value."
    ::= { ocnCrntPMEntry 28 }


ocnCrntPMSESSValidity OBJECT-TYPE
    SYNTAX       PMValidity
    MAX-ACCESS   read-only
    STATUS       current
    DESCRIPTION  "Indicates the validity of the provided section layer severely
                  errored seconds value."
    ::= { ocnCrntPMEntry 29 }


ocnCrntPMSEFSSValue OBJECT-TYPE
    SYNTAX       Unsigned32
    MAX-ACCESS   read-write
    STATUS       current
    DESCRIPTION  "The count of severely errored framing seconds at the section
                  layer."
    ::= { ocnCrntPMEntry 30 }


ocnCrntPMSEFSSTimeStamp OBJECT-TYPE
    SYNTAX       DateAndTime
    MAX-ACCESS   read-only
    STATUS       current
    DESCRIPTION  "The date and time stamp of the section layer severely errored
                  framing seconds value."
    ::= { ocnCrntPMEntry 31 }


ocnCrntPMSEFSSValidity OBJECT-TYPE
    SYNTAX       PMValidity
    MAX-ACCESS   read-only
    STATUS       current
    DESCRIPTION  "Indicates the validity of the provided section layer severely
                  errored framing seconds value."
    ::= { ocnCrntPMEntry 32 }


ocnCrntPMSupplyVoltage2Value OBJECT-TYPE
    SYNTAX       FixedX10
    UNITS        "mVolts/10"
    MAX-ACCESS   read-only
    STATUS       current
    DESCRIPTION  "The value of the second supply voltage source measured on the
                  OC-N facility port transceiver."
    ::= { ocnCrntPMEntry 33 }


ocnCrntPMSupplyVoltage2TimeStamp OBJECT-TYPE
    SYNTAX       DateAndTime
    MAX-ACCESS   read-only
    STATUS       current
    DESCRIPTION  "The date and time stamp of the second supply voltage value."
    ::= { ocnCrntPMEntry 34 }


ocnCrntPMSupplyVoltage2Validity OBJECT-TYPE
    SYNTAX       PMValidity
    MAX-ACCESS   read-only
    STATUS       current
    DESCRIPTION  "Indicates the validity of the provided second supply voltage
                  value."
    ::= { ocnCrntPMEntry 35 }


ocnCrntPMCVLValue OBJECT-TYPE
    SYNTAX       Unsigned32 
    MAX-ACCESS   read-write
    STATUS       current
    DESCRIPTION  "The count of coding violations at the line layer."
    ::= { ocnCrntPMEntry 36 }


ocnCrntPMCVLTimeStamp OBJECT-TYPE
    SYNTAX       DateAndTime
    MAX-ACCESS   read-only
    STATUS       current
    DESCRIPTION  "The date and time stamp of the line layer coding violations
                  value."
    ::= { ocnCrntPMEntry 37 }


ocnCrntPMCVLValidity OBJECT-TYPE
    SYNTAX       PMValidity
    MAX-ACCESS   read-only
    STATUS       current
    DESCRIPTION  "Indicates the validity of the provided line layer coding
                  violations value."
    ::= { ocnCrntPMEntry 38 }


ocnCrntPMESLValue OBJECT-TYPE
    SYNTAX       Unsigned32
    MAX-ACCESS   read-write
    STATUS       current
    DESCRIPTION  "The count of errored seconds at the line layer."
    ::= { ocnCrntPMEntry 39 }


ocnCrntPMESLTimeStamp OBJECT-TYPE
    SYNTAX       DateAndTime
    MAX-ACCESS   read-only
    STATUS       current
    DESCRIPTION  "The date and time stamp of the line layer errored seconds
                  value."
    ::= { ocnCrntPMEntry 40 }


ocnCrntPMESLValidity OBJECT-TYPE
    SYNTAX       PMValidity
    MAX-ACCESS   read-only
    STATUS       current
    DESCRIPTION  "Indicates the validity of the provided line layer errored
                  seconds value."
    ::= { ocnCrntPMEntry 41 }


ocnCrntPMSESLValue OBJECT-TYPE
    SYNTAX       Unsigned32
    MAX-ACCESS   read-write
    STATUS       current
    DESCRIPTION  "The count of severely errored seconds at the line layer."
    ::= { ocnCrntPMEntry 42 }


ocnCrntPMSESLTimeStamp OBJECT-TYPE
    SYNTAX       DateAndTime
    MAX-ACCESS   read-only
    STATUS       current
    DESCRIPTION  "The date and time stamp of the line layer severely errored
                  seconds value."
    ::= { ocnCrntPMEntry 43 }


ocnCrntPMSESLValidity OBJECT-TYPE
    SYNTAX       PMValidity
    MAX-ACCESS   read-only
    STATUS       current
    DESCRIPTION  "Indicates the validity of the provided line layer severely
                  errored seconds value."
    ::= { ocnCrntPMEntry 44 }


ocnCrntPMUASLValue OBJECT-TYPE
    SYNTAX       Unsigned32
    MAX-ACCESS   read-write
    STATUS       current
    DESCRIPTION  "The count of unavailable seconds at the line layer."
    ::= { ocnCrntPMEntry 45 }


ocnCrntPMUASLTimeStamp OBJECT-TYPE
    SYNTAX       DateAndTime
    MAX-ACCESS   read-only
    STATUS       current
    DESCRIPTION  "The date and time stamp of the line layer unavailable seconds
                  value."
    ::= { ocnCrntPMEntry 46 }


ocnCrntPMUASLValidity OBJECT-TYPE
    SYNTAX       PMValidity
    MAX-ACCESS   read-only
    STATUS       current
    DESCRIPTION  "Indicates the validity of the provided line layer unavailable
                  seconds value."
    ::= { ocnCrntPMEntry 47 }


ocnCrntPMOTUEBValue OBJECT-TYPE
    SYNTAX       Unsigned32 
    MAX-ACCESS   read-write
    STATUS       current
    DESCRIPTION  "The count of OTU digital wrapper layer errored blocks."
    ::= { ocnCrntPMEntry 48 }


ocnCrntPMOTUEBTimeStamp OBJECT-TYPE
    SYNTAX       DateAndTime
    MAX-ACCESS   read-only
    STATUS       current
    DESCRIPTION  "The date and time stamp of the OTU digital wrapper layer
                  errored blocks value."
    ::= { ocnCrntPMEntry 49 }


ocnCrntPMOTUEBValidity OBJECT-TYPE
    SYNTAX       PMValidity
    MAX-ACCESS   read-only
    STATUS       current
    DESCRIPTION  "Indicates the validity of the provided OTU digital wrapper
                  layer errored blocks value."
    ::= { ocnCrntPMEntry 50 }


ocnCrntPMOTUBBEValue OBJECT-TYPE
    SYNTAX       Unsigned32 
    MAX-ACCESS   read-write
    STATUS       current
    DESCRIPTION  "The count of OTU digital wrapper layer background block
                  errors."
    ::= { ocnCrntPMEntry 51 }


ocnCrntPMOTUBBETimeStamp OBJECT-TYPE
    SYNTAX       DateAndTime
    MAX-ACCESS   read-only
    STATUS       current
    DESCRIPTION  "The date and time stamp of the OTU digital wrapper layer
                  background block errors value."
    ::= { ocnCrntPMEntry 52 }


ocnCrntPMOTUBBEValidity OBJECT-TYPE
    SYNTAX       PMValidity
    MAX-ACCESS   read-only
    STATUS       current
    DESCRIPTION  "Indicates the validity of the provided OTU digital wrapper
                  layer background block errors value."
    ::= { ocnCrntPMEntry 53 }


ocnCrntPMOTUESValue OBJECT-TYPE
    SYNTAX       Unsigned32
    MAX-ACCESS   read-write
    STATUS       current
    DESCRIPTION  "The count of OTU digital wrapper layer errored seconds."
    ::= { ocnCrntPMEntry 54 }


ocnCrntPMOTUESTimeStamp OBJECT-TYPE
    SYNTAX       DateAndTime
    MAX-ACCESS   read-only
    STATUS       current
    DESCRIPTION  "The date and time stamp of the OTU digital wrapper layer
                  errored seconds value."
    ::= { ocnCrntPMEntry 55 }


ocnCrntPMOTUESValidity OBJECT-TYPE
    SYNTAX       PMValidity
    MAX-ACCESS   read-only
    STATUS       current
    DESCRIPTION  "Indicates the validity of the provided OTU digital wrapper
                  layer errored seconds value."
    ::= { ocnCrntPMEntry 56 }


ocnCrntPMOTUSESValue OBJECT-TYPE
    SYNTAX       Unsigned32
    MAX-ACCESS   read-write
    STATUS       current
    DESCRIPTION  "The count of OTU digital wrapper layer severely errored
                  seconds."
    ::= { ocnCrntPMEntry 57 }


ocnCrntPMOTUSESTimeStamp OBJECT-TYPE
    SYNTAX       DateAndTime
    MAX-ACCESS   read-only
    STATUS       current
    DESCRIPTION  "The date and time stamp of the OTU digital wrapper layer
                  severely errored seconds value."
    ::= { ocnCrntPMEntry 58 }


ocnCrntPMOTUSESValidity OBJECT-TYPE
    SYNTAX       PMValidity
    MAX-ACCESS   read-only
    STATUS       current
    DESCRIPTION  "Indicates the validity of the provided OTU digital wrapper
                  layer severely errored seconds value."
    ::= { ocnCrntPMEntry 59 }


ocnCrntPMOTUOFSValue OBJECT-TYPE
    SYNTAX       Unsigned32
    MAX-ACCESS   read-write
    STATUS       current
    DESCRIPTION  "The count of OTU digital wrapper layer out-of-frame seconds."
    ::= { ocnCrntPMEntry 60 }


ocnCrntPMOTUOFSTimeStamp OBJECT-TYPE
    SYNTAX       DateAndTime
    MAX-ACCESS   read-only
    STATUS       current
    DESCRIPTION  "The date and time stamp of the OTU digital wrapper layer
                  out-of-frame seconds value."
    ::= { ocnCrntPMEntry 61 }


ocnCrntPMOTUOFSValidity OBJECT-TYPE
    SYNTAX       PMValidity
    MAX-ACCESS   read-only
    STATUS       current
    DESCRIPTION  "Indicates the validity of the provided OTU digital wrapper
                  layer out-of-frame seconds value."
    ::= { ocnCrntPMEntry 62 }


ocnCrntPMNBITCRValue OBJECT-TYPE
    SYNTAX       Unsigned32
    MAX-ACCESS   read-write
    STATUS       current
    DESCRIPTION  "The count of the number of bits corrected. This object applies
                  only to OC-192 line port provisioned for OTN line mapping."
    ::= { ocnCrntPMEntry 63 }


ocnCrntPMNBITCRTimeStamp OBJECT-TYPE
    SYNTAX       DateAndTime
    MAX-ACCESS   read-only
    STATUS       current
    DESCRIPTION  "The date and time stamp of the number of bits corrected
                  value."
    ::= { ocnCrntPMEntry 64 }


ocnCrntPMNBITCRValidity OBJECT-TYPE
    SYNTAX       PMValidity
    MAX-ACCESS   read-only
    STATUS       current
    DESCRIPTION  "Indicates the validity of the provided number of bits
                  corrected value."
    ::= { ocnCrntPMEntry 65 }


ocnCrntPMNBYTCRValue OBJECT-TYPE
    SYNTAX       Unsigned32
    MAX-ACCESS   read-write
    STATUS       current
    DESCRIPTION  "The count of the number of bytes corrected. This object
                  applies only to OC-192 line port provisioned for OTN line
                  mapping."
    ::= { ocnCrntPMEntry 66 }


ocnCrntPMNBYTCRTimeStamp OBJECT-TYPE
    SYNTAX       DateAndTime
    MAX-ACCESS   read-only
    STATUS       current
    DESCRIPTION  "The date and time stamp of the number of bytes corrected
                  value."
    ::= { ocnCrntPMEntry 67 }


ocnCrntPMNBYTCRValidity OBJECT-TYPE
    SYNTAX       PMValidity
    MAX-ACCESS   read-only
    STATUS       current
    DESCRIPTION  "Indicates the validity of the provided number of bytes
                  corrected value."
    ::= { ocnCrntPMEntry 68 }


ocnCrntPMUNCRCDWValue OBJECT-TYPE
    SYNTAX       Unsigned32
    MAX-ACCESS   read-write
    STATUS       current
    DESCRIPTION  "The count of uncorrectable codewords. This object applies only
                  to OC-192 line port provisioned for OTN line mapping."
    ::= { ocnCrntPMEntry 69 }


ocnCrntPMUNCRCDWTimeStamp OBJECT-TYPE
    SYNTAX       DateAndTime
    MAX-ACCESS   read-only
    STATUS       current
    DESCRIPTION  "The date and time stamp of the uncorrectable codewords value."
    ::= { ocnCrntPMEntry 70 }


ocnCrntPMUNCRCDWValidity OBJECT-TYPE
    SYNTAX       PMValidity
    MAX-ACCESS   read-only
    STATUS       current
    DESCRIPTION  "Indicates the validity of the provided uncorrectable codewords
                  value."
    ::= { ocnCrntPMEntry 71 }


ocnCrntPMCVSInitialize OBJECT-TYPE
    SYNTAX       InitializeCmd
    MAX-ACCESS   read-write
    STATUS       current
    DESCRIPTION  "Used to initialize the value of the ocnCrntPMCVSValue object
                  to 0."
    ::= { ocnCrntPMEntry 72 }


ocnCrntPMESSInitialize OBJECT-TYPE
    SYNTAX       InitializeCmd
    MAX-ACCESS   read-write
    STATUS       current
    DESCRIPTION  "Used to initialize the value of the ocnCrntPMESSValue object
                  to 0."
    ::= { ocnCrntPMEntry 73 }


ocnCrntPMSESSInitialize OBJECT-TYPE
    SYNTAX       InitializeCmd
    MAX-ACCESS   read-write
    STATUS       current
    DESCRIPTION  "Used to initialize the value of the ocnCrntPMSESSValue object
                  to 0."
    ::= { ocnCrntPMEntry 74 }


ocnCrntPMSEFSSInitialize OBJECT-TYPE
    SYNTAX       InitializeCmd
    MAX-ACCESS   read-write
    STATUS       current
    DESCRIPTION  "Used to initialize the value of the ocnCrntPMSEFSSValue object
                  to 0."
    ::= { ocnCrntPMEntry 75 }


ocnCrntPMCVLInitialize OBJECT-TYPE
    SYNTAX       InitializeCmd
    MAX-ACCESS   read-write
    STATUS       current
    DESCRIPTION  "Used to initialize the value of the ocnCrntPMCVLValue object
                  to 0."
    ::= { ocnCrntPMEntry 76 }


ocnCrntPMESLInitialize OBJECT-TYPE
    SYNTAX       InitializeCmd
    MAX-ACCESS   read-write
    STATUS       current
    DESCRIPTION  "Used to initialize the value of the ocnCrntPMESLValue object
                  to 0."
    ::= { ocnCrntPMEntry 77 }


ocnCrntPMSESLInitialize OBJECT-TYPE
    SYNTAX       InitializeCmd
    MAX-ACCESS   read-write
    STATUS       current
    DESCRIPTION  "Used to initialize the value of the ocnCrntPMSESLValue object
                  to 0."
    ::= { ocnCrntPMEntry 78 }


ocnCrntPMUASLInitialize OBJECT-TYPE
    SYNTAX       InitializeCmd
    MAX-ACCESS   read-write
    STATUS       current
    DESCRIPTION  "Used to initialize the value of the ocnCrntPMUASLValue object
                  to 0."
    ::= { ocnCrntPMEntry 79 }


ocnCrntPMOTUEBInitialize OBJECT-TYPE
    SYNTAX       InitializeCmd
    MAX-ACCESS   read-write
    STATUS       current
    DESCRIPTION  "Used to initialize the value of the ocnCrntPMOTUEBValue object
                  to 0."
    ::= { ocnCrntPMEntry 80 }


ocnCrntPMOTUBBEInitialize OBJECT-TYPE
    SYNTAX       InitializeCmd
    MAX-ACCESS   read-write
    STATUS       current
    DESCRIPTION  "Used to initialize the value of the ocnCrntPMOTUBBEValue
                  object to 0."
    ::= { ocnCrntPMEntry 81 }


ocnCrntPMOTUESInitialize OBJECT-TYPE
    SYNTAX       InitializeCmd
    MAX-ACCESS   read-write
    STATUS       current
    DESCRIPTION  "Used to initialize the value of the ocnCrntPMOTUESValue object
                  to 0."
    ::= { ocnCrntPMEntry 82 }


ocnCrntPMOTUSESInitialize OBJECT-TYPE
    SYNTAX       InitializeCmd
    MAX-ACCESS   read-write
    STATUS       current
    DESCRIPTION  "Used to initialize the value of the ocnCrntPMOTUSESValue
                  object to 0."
    ::= { ocnCrntPMEntry 83 }


ocnCrntPMOTUOFSInitialize OBJECT-TYPE
    SYNTAX       InitializeCmd
    MAX-ACCESS   read-write
    STATUS       current
    DESCRIPTION  "Used to initialize the value of the ocnCrntPMOTUOFSValue
                  object to 0."
    ::= { ocnCrntPMEntry 84 }


ocnCrntPMNBITCRInitialize OBJECT-TYPE
    SYNTAX       InitializeCmd
    MAX-ACCESS   read-write
    STATUS       current
    DESCRIPTION  "Used to initialize the value of the ocnCrntPMNBITCRValue
                  object to 0."
    ::= { ocnCrntPMEntry 85 }


ocnCrntPMNBYTCRInitialize OBJECT-TYPE
    SYNTAX       InitializeCmd
    MAX-ACCESS   read-write
    STATUS       current
    DESCRIPTION  "Used to initialize the value of the ocnCrntPMNBYTCRValue
                  object to 0."
    ::= { ocnCrntPMEntry 86 }


ocnCrntPMUNCRCDWInitialize OBJECT-TYPE
    SYNTAX       InitializeCmd
    MAX-ACCESS   read-write
    STATUS       current
    DESCRIPTION  "Used to initialize the value of the ocnCrntPMUNCRCDWValue
                  object to 0."
    ::= { ocnCrntPMEntry 87 }


ocnCrntPMOTNBERValue OBJECT-TYPE
    SYNTAX       DisplayString
    MAX-ACCESS   read-only
    STATUS       current
    DESCRIPTION  "The instantaneous BER of OC-192 line port provisioned for OTN line mapping."
    ::= { ocnCrntPMEntry 88 }


ocnCrntPMOTNBERTimeStamp OBJECT-TYPE
    SYNTAX       DateAndTime
    MAX-ACCESS   read-only
    STATUS       current
    DESCRIPTION  "The date and time stamp of the instantaneous BER."
    ::= { ocnCrntPMEntry 89 }


ocnCrntPMOTNBERValidity OBJECT-TYPE
    SYNTAX       PMValidity
    MAX-ACCESS   read-only
    STATUS       current
    DESCRIPTION  "Indicates the validity of the provided instantaneous BER."
    ::= { ocnCrntPMEntry 90 }


ocnCrntPMOTNBERInitialize OBJECT-TYPE
    SYNTAX       InitializeCmd
    MAX-ACCESS   read-write
    STATUS       current
    DESCRIPTION  "Used to initialize the value of the ocnCrntPMOTNBERValue
                  object to 0."
    ::= { ocnCrntPMEntry 91 }


ocnCrntPMOTNAVGBERValue OBJECT-TYPE
    SYNTAX       DisplayString
    MAX-ACCESS   read-only
    STATUS       current
    DESCRIPTION  "The interval/average BER of OC-192 line port provisioned for OTN line mapping."
    ::= { ocnCrntPMEntry 92 }


ocnCrntPMOTNAVGBERTimeStamp OBJECT-TYPE
    SYNTAX       DateAndTime
    MAX-ACCESS   read-only
    STATUS       current
    DESCRIPTION  "The date and time stamp of the interval/average BER."
    ::= { ocnCrntPMEntry 93 }


ocnCrntPMOTNAVGBERValidity OBJECT-TYPE
    SYNTAX       PMValidity
    MAX-ACCESS   read-only
    STATUS       current
    DESCRIPTION  "Indicates the validity of the provided interval/average BER."
    ::= { ocnCrntPMEntry 94 }


ocnCrntPMOTNAVGBERInitialize OBJECT-TYPE
    SYNTAX       InitializeCmd
    MAX-ACCESS   read-write
    STATUS       current
    DESCRIPTION  "Used to initialize the value of the ocnCrntPMOTNAVGBERValue
                  object to 0."
    ::= { ocnCrntPMEntry 95 }


ocnCrntPMNBITCR64BitValue OBJECT-TYPE
    SYNTAX       Unsigned64
    MAX-ACCESS   read-only
    STATUS       current
    DESCRIPTION  "The 64-bit count of the number of bits corrected. This object
                  applies only to OC-192 line port provisioned for OTN line mapping."
    ::= { ocnCrntPMEntry 96 }


ocnCrntPMNBITCR64BitTimeStamp OBJECT-TYPE
    SYNTAX       DateAndTime
    MAX-ACCESS   read-only
    STATUS       current
    DESCRIPTION  "The date and time stamp of the 64-bit number of bits corrected
                  value."
    ::= { ocnCrntPMEntry 97 }


ocnCrntPMNBITCR64BitValidity OBJECT-TYPE
    SYNTAX       PMValidity
    MAX-ACCESS   read-only
    STATUS       current
    DESCRIPTION  "Indicates the validity of the provided 64-bit number of bits
                  corrected value."
    ::= { ocnCrntPMEntry 98 }


ocnCrntPMNBITCR64BitInitialize OBJECT-TYPE
    SYNTAX       InitializeCmd
    MAX-ACCESS   read-write
    STATUS       current
    DESCRIPTION  "Used to initialize the value of the ocnCrntPMNBITCR64BitValue
                  object to 0."
    ::= { ocnCrntPMEntry 99 }


ocnCrntPMNBYTCR64BitValue OBJECT-TYPE
    SYNTAX       Unsigned64
    MAX-ACCESS   read-only
    STATUS       current
    DESCRIPTION  "The 64-bit count of the number of bytes corrected. This object
                  applies only to OC-192 line port provisioned for OTN line
                  mapping."
    ::= { ocnCrntPMEntry 100 }


ocnCrntPMNBYTCR64BitTimeStamp OBJECT-TYPE
    SYNTAX       DateAndTime
    MAX-ACCESS   read-only
    STATUS       current
    DESCRIPTION  "The date and time stamp of the 64-bit number of bytes corrected
                  value."
    ::= { ocnCrntPMEntry 101 }


ocnCrntPMNBYTCR64BitValidity OBJECT-TYPE
    SYNTAX       PMValidity
    MAX-ACCESS   read-only
    STATUS       current
    DESCRIPTION  "Indicates the validity of the provided 64-bit number of bytes
                  corrected value."
    ::= { ocnCrntPMEntry 102 }


ocnCrntPMNBYTCR64BitInitialize OBJECT-TYPE
    SYNTAX       InitializeCmd
    MAX-ACCESS   read-write
    STATUS       current
    DESCRIPTION  "Used to initialize the value of the ocnCrntPMNBYTCR64BitValue
                  object to 0."
    ::= { ocnCrntPMEntry 103 }


ocnCrntPMUASSValue OBJECT-TYPE
    SYNTAX       Unsigned32
    MAX-ACCESS   read-write
    STATUS       current
    DESCRIPTION  "The count of unavailable seconds at the section layer.
                  This object applies only to OC-192 line port provisioned
                  for OTN line mapping."
    ::= { ocnCrntPMEntry 104 }

ocnCrntPMUASSTimeStamp OBJECT-TYPE
    SYNTAX       DateAndTime
    MAX-ACCESS   read-only
    STATUS       current
    DESCRIPTION  "The date and time stamp of the unavailable seconds at
                  the section layer"
    ::= { ocnCrntPMEntry 105 }

ocnCrntPMUASSValidity OBJECT-TYPE
    SYNTAX       PMValidity
    MAX-ACCESS   read-only
    STATUS       current
    DESCRIPTION  "Indicates the validity of the unavailable seconds at
                  the section layer."
    ::= { ocnCrntPMEntry 106 }

ocnCrntPMUASSInitialize OBJECT-TYPE
    SYNTAX       InitializeCmd
    MAX-ACCESS   read-write
    STATUS       current
    DESCRIPTION  "Used to initialize the value of the ocnCrntPMUASSValue
                  object to 0."
    ::= { ocnCrntPMEntry 107 }

ocnCrntPMOTUUASValue OBJECT-TYPE
    SYNTAX       Unsigned32
    MAX-ACCESS   read-write
    STATUS       current
    DESCRIPTION  "The count of OTU digital wrapper layer unavailable seconds."
    ::= { ocnCrntPMEntry 108 }


ocnCrntPMOTUUASTimeStamp OBJECT-TYPE
    SYNTAX       DateAndTime
    MAX-ACCESS   read-only
    STATUS       current
    DESCRIPTION  "The date and time stamp of the OTU digital wrapper layer
                  unavailable seconds value."
    ::= { ocnCrntPMEntry 109 }


ocnCrntPMOTUUASValidity OBJECT-TYPE
    SYNTAX       PMValidity
    MAX-ACCESS   read-only
    STATUS       current
    DESCRIPTION  "Indicates the validity of the provided OTU digital wrapper
                  layer unavailable seconds value."
    ::= { ocnCrntPMEntry 110 }

ocnCrntPMOTUUASInitialize OBJECT-TYPE
    SYNTAX       InitializeCmd
    MAX-ACCESS   read-write
    STATUS       current
    DESCRIPTION  "Used to initialize the value of the ocnCrntPMOTUUASValue
                  object to 0."
    ::= { ocnCrntPMEntry 111 }

ocnCrntPMOPRMinValue OBJECT-TYPE
    SYNTAX       FixedX10
    UNITS        "dBm/10"
    MAX-ACCESS   read-only
    STATUS       current
    DESCRIPTION  "The minimum optical power received on the input of the transceiver."
    ::= { ocnCrntPMEntry 112 }


ocnCrntPMOPRMinTimeStamp OBJECT-TYPE
    SYNTAX       DateAndTime
    MAX-ACCESS   read-only
    STATUS       current
    DESCRIPTION  "The date and time stamp of the minimum optical power received value."
    ::= { ocnCrntPMEntry 113 }


ocnCrntPMOPRMinValidity OBJECT-TYPE
    SYNTAX       PMValidity
    MAX-ACCESS   read-only
    STATUS       current
    DESCRIPTION  "Indicates the validity of the provided minimum optical power received
                  value."
    ::= { ocnCrntPMEntry 114 }

ocnCrntPMOPRMinInitialize OBJECT-TYPE
    SYNTAX       InitializeCmd
    MAX-ACCESS   read-write
    STATUS       current
    DESCRIPTION  "Used to initialize the value of the ocnCrntPMOPRMinValue
                  object to 0."
    ::= { ocnCrntPMEntry 115 }

ocnCrntPMOPRMaxValue OBJECT-TYPE
    SYNTAX       FixedX10
    UNITS        "dBm/10"
    MAX-ACCESS   read-only
    STATUS       current
    DESCRIPTION  "The maximum optical power received on the input of the transceiver."
    ::= { ocnCrntPMEntry 116 }


ocnCrntPMOPRMaxTimeStamp OBJECT-TYPE
    SYNTAX       DateAndTime
    MAX-ACCESS   read-only
    STATUS       current
    DESCRIPTION  "The date and time stamp of the maximum optical power received value."
    ::= { ocnCrntPMEntry 117 }


ocnCrntPMOPRMaxValidity OBJECT-TYPE
    SYNTAX       PMValidity
    MAX-ACCESS   read-only
    STATUS       current
    DESCRIPTION  "Indicates the validity of the provided maximum optical power received
                  value."
    ::= { ocnCrntPMEntry 118 }

ocnCrntPMOPRMaxInitialize OBJECT-TYPE
    SYNTAX       InitializeCmd
    MAX-ACCESS   read-write
    STATUS       current
    DESCRIPTION  "Used to initialize the value of the ocnCrntPMOPRMaxValue
                  object to 0."
    ::= { ocnCrntPMEntry 119 }

ocnCrntPMOPRAvgValue OBJECT-TYPE
    SYNTAX       FixedX10
    UNITS        "dBm/10"
    MAX-ACCESS   read-only
    STATUS       current
    DESCRIPTION  "The average optical power received on the input of the transceiver."
    ::= { ocnCrntPMEntry 120 }


ocnCrntPMOPRAvgTimeStamp OBJECT-TYPE
    SYNTAX       DateAndTime
    MAX-ACCESS   read-only
    STATUS       current
    DESCRIPTION  "The date and time stamp of the average optical power received value."
    ::= { ocnCrntPMEntry 121 }


ocnCrntPMOPRAvgValidity OBJECT-TYPE
    SYNTAX       PMValidity
    MAX-ACCESS   read-only
    STATUS       current
    DESCRIPTION  "Indicates the validity of the provided average optical power received
                  value."
    ::= { ocnCrntPMEntry 122 }

ocnCrntPMOPRAvgInitialize OBJECT-TYPE
    SYNTAX       InitializeCmd
    MAX-ACCESS   read-write
    STATUS       current
    DESCRIPTION  "Used to initialize the value of the ocnCrntPMOPRAvgValue
                  object to 0."
    ::= { ocnCrntPMEntry 123 }

ocnCrntPMOPTMinValue OBJECT-TYPE
    SYNTAX       FixedX10
    UNITS        "dBm/10"
    MAX-ACCESS   read-only
    STATUS       current
    DESCRIPTION  "The minimum optical power transmitted at the output of the
                  transceiver."
    ::= { ocnCrntPMEntry 124 }

ocnCrntPMOPTMinTimeStamp OBJECT-TYPE
    SYNTAX       DateAndTime
    MAX-ACCESS   read-only
    STATUS       current
    DESCRIPTION  "The date and time stamp of the minimum optical power transmitted
                  value."
    ::= { ocnCrntPMEntry 125 }


ocnCrntPMOPTMinValidity OBJECT-TYPE
    SYNTAX       PMValidity
    MAX-ACCESS   read-only
    STATUS       current
    DESCRIPTION  "Indicates the validity of the provided minimum optical power
                  transmitted value."
    ::= { ocnCrntPMEntry 126 }

ocnCrntPMOPTMinInitialize OBJECT-TYPE
    SYNTAX       InitializeCmd
    MAX-ACCESS   read-write
    STATUS       current
    DESCRIPTION  "Used to initialize the value of the ocnCrntPMOPTMinValue
                  object to 0."
    ::= { ocnCrntPMEntry 127 }

ocnCrntPMOPTMaxValue OBJECT-TYPE
    SYNTAX       FixedX10
    UNITS        "dBm/10"
    MAX-ACCESS   read-only
    STATUS       current
    DESCRIPTION  "The maximum optical power transmitted at the output of the
                  transceiver."
    ::= { ocnCrntPMEntry 128 }


ocnCrntPMOPTMaxTimeStamp OBJECT-TYPE
    SYNTAX       DateAndTime
    MAX-ACCESS   read-only
    STATUS       current
    DESCRIPTION  "The date and time stamp of the maximum optical power transmitted
                  value."
    ::= { ocnCrntPMEntry 129 }


ocnCrntPMOPTMaxValidity OBJECT-TYPE
    SYNTAX       PMValidity
    MAX-ACCESS   read-only
    STATUS       current
    DESCRIPTION  "Indicates the validity of the provided maximum optical power
                  transmitted value."
    ::= { ocnCrntPMEntry 130 }

ocnCrntPMOPTMaxInitialize OBJECT-TYPE
    SYNTAX       InitializeCmd
    MAX-ACCESS   read-write
    STATUS       current
    DESCRIPTION  "Used to initialize the value of the ocnCrntPMOPTMaxValue
                  object to 0."
    ::= { ocnCrntPMEntry 131 }

ocnCrntPMOPTAvgValue OBJECT-TYPE
    SYNTAX       FixedX10
    UNITS        "dBm/10"
    MAX-ACCESS   read-only
    STATUS       current
    DESCRIPTION  "The average optical power transmitted at the output of the
                  transceiver."
    ::= { ocnCrntPMEntry 132 }


ocnCrntPMOPTAvgTimeStamp OBJECT-TYPE
    SYNTAX       DateAndTime
    MAX-ACCESS   read-only
    STATUS       current
    DESCRIPTION  "The date and time stamp of the average optical power transmitted
                  value."
    ::= { ocnCrntPMEntry 133 }

ocnCrntPMOPTAvgValidity OBJECT-TYPE
    SYNTAX       PMValidity
    MAX-ACCESS   read-only
    STATUS       current
    DESCRIPTION  "Indicates the validity of the provided average optical power
                  transmitted value."
    ::= { ocnCrntPMEntry 134 }

ocnCrntPMOPTAvgInitialize OBJECT-TYPE
    SYNTAX       InitializeCmd
    MAX-ACCESS   read-write
    STATUS       current
    DESCRIPTION  "Used to initialize the value of the ocnCrntPMOPTAvgValue
                  object to 0."
    ::= { ocnCrntPMEntry 135 }

-----------------------------------------------------------------------
-- Objects used to retrieve historical SONET OC-N
-- Performance Monitoring statistics
-- 
-- A listing of historical SONET OC-N PM values is contained in the
-- ocnHistPMTable of the BTI 7000 Series MIB. When retrieved, this table 
-- provides one row for each set of current SONET OC-N PM data.
-- 
-- The following table lists the objects in each entry of the 
-- ocnHistPMTable.
-----------------------------------------------------------------------


ocnHistPMTable OBJECT-TYPE
    SYNTAX       SEQUENCE OF OcnHistPMEntry
    MAX-ACCESS   not-accessible
    STATUS       current
    DESCRIPTION  "A table of historical performance monitoring statistics
                  collected for the SONET OC-N facilities on the NE."
    ::= { performance 9 }


ocnHistPMEntry OBJECT-TYPE
    SYNTAX       OcnHistPMEntry
    MAX-ACCESS   not-accessible
    STATUS       current
    DESCRIPTION  "The row entry object of the SONET OC-N historical performance
                  monitoring table. Each row of this table contains a full set
                  of PM statistics and related data for a historical measurement
                  interval for a given OC-N facility."
    INDEX        { ocnHistPMTypeIdx,
                   ocnHistPMShelfIdx,
                   ocnHistPMSlotIdx,
                   ocnHistPMPortIdx,
                   ocnHistPMIntervalTypeIdx,
                   ocnHistPMIntervalIdx }
    ::= { ocnHistPMTable 1 }


OcnHistPMEntry ::= SEQUENCE { ocnHistPMTypeIdx                 OcnType,
                              ocnHistPMShelfIdx                INTEGER,
                              ocnHistPMSlotIdx                 INTEGER,
                              ocnHistPMPortIdx                 INTEGER,
                              ocnHistPMIntervalTypeIdx         PMIntervalType,
                              ocnHistPMIntervalIdx             INTEGER,
                              ocnHistPMOPRValue                FixedX10,
                              ocnHistPMOPRTimeStamp            DateAndTime,
                              ocnHistPMOPRValidity             PMValidity,
                              ocnHistPMOPTValue                FixedX10,
                              ocnHistPMOPTTimeStamp            DateAndTime,
                              ocnHistPMOPTValidity             PMValidity,
                              ocnHistPMTempValue               INTEGER,
                              ocnHistPMTempTimeStamp           DateAndTime,
                              ocnHistPMTempValidity            PMValidity,
                              ocnHistPMSupplyVoltageValue      FixedX10,
                              ocnHistPMSupplyVoltageTimeStamp  DateAndTime,
                              ocnHistPMSupplyVoltageValidity   PMValidity,
                              ocnHistPMLBCValue                INTEGER,
                              ocnHistPMLBCTimeStamp            DateAndTime,
                              ocnHistPMLBCValidity             PMValidity,
                              ocnHistPMCVSValue                Unsigned32,
                              ocnHistPMCVSTimeStamp            DateAndTime,
                              ocnHistPMCVSValidity             PMValidity,
                              ocnHistPMESSValue                Unsigned32,
                              ocnHistPMESSTimeStamp            DateAndTime,
                              ocnHistPMESSValidity             PMValidity,
                              ocnHistPMSESSValue               Unsigned32,
                              ocnHistPMSESSTimeStamp           DateAndTime,
                              ocnHistPMSESSValidity            PMValidity,
                              ocnHistPMSEFSSValue              Unsigned32,
                              ocnHistPMSEFSSTimeStamp          DateAndTime,
                              ocnHistPMSEFSSValidity           PMValidity,
                              ocnHistPMSupplyVoltage2Value     FixedX10,
                              ocnHistPMSupplyVoltage2TimeStamp DateAndTime,
                              ocnHistPMSupplyVoltage2Validity  PMValidity,
                              ocnHistPMCVLValue                Unsigned32,
                              ocnHistPMCVLTimeStamp            DateAndTime,
                              ocnHistPMCVLValidity             PMValidity,
                              ocnHistPMESLValue                Unsigned32,
                              ocnHistPMESLTimeStamp            DateAndTime,
                              ocnHistPMESLValidity             PMValidity,
                              ocnHistPMSESLValue               Unsigned32,
                              ocnHistPMSESLTimeStamp           DateAndTime,
                              ocnHistPMSESLValidity            PMValidity,
                              ocnHistPMUASLValue               Unsigned32,
                              ocnHistPMUASLTimeStamp           DateAndTime,
                              ocnHistPMUASLValidity            PMValidity,
                              ocnHistPMOTUEBValue              Unsigned32,
                              ocnHistPMOTUEBTimeStamp          DateAndTime,
                              ocnHistPMOTUEBValidity           PMValidity,
                              ocnHistPMOTUBBEValue             Unsigned32,
                              ocnHistPMOTUBBETimeStamp         DateAndTime,
                              ocnHistPMOTUBBEValidity          PMValidity,
                              ocnHistPMOTUESValue              Unsigned32,
                              ocnHistPMOTUESTimeStamp          DateAndTime,
                              ocnHistPMOTUESValidity           PMValidity,
                              ocnHistPMOTUSESValue             Unsigned32,
                              ocnHistPMOTUSESTimeStamp         DateAndTime,
                              ocnHistPMOTUSESValidity          PMValidity,
                              ocnHistPMOTUOFSValue             Unsigned32,
                              ocnHistPMOTUOFSTimeStamp         DateAndTime,
                              ocnHistPMOTUOFSValidity          PMValidity,
                              ocnHistPMNBITCRValue             Unsigned32,
                              ocnHistPMNBITCRTimeStamp         DateAndTime,
                              ocnHistPMNBITCRValidity          PMValidity,
                              ocnHistPMNBYTCRValue             Unsigned32,
                              ocnHistPMNBYTCRTimeStamp         DateAndTime,
                              ocnHistPMNBYTCRValidity          PMValidity,
                              ocnHistPMUNCRCDWValue            Unsigned32,
                              ocnHistPMUNCRCDWTimeStamp        DateAndTime,
                              ocnHistPMUNCRCDWValidity         PMValidity,
                              ocnHistPMCVSInitialize           InitializeCmd,
                              ocnHistPMESSInitialize           InitializeCmd,
                              ocnHistPMSESSInitialize          InitializeCmd,
                              ocnHistPMSEFSSInitialize         InitializeCmd,
                              ocnHistPMCVLInitialize           InitializeCmd,
                              ocnHistPMESLInitialize           InitializeCmd,
                              ocnHistPMSESLInitialize          InitializeCmd,
                              ocnHistPMUASLInitialize          InitializeCmd,
                              ocnHistPMOTUEBInitialize         InitializeCmd,
                              ocnHistPMOTUBBEInitialize        InitializeCmd,
                              ocnHistPMOTUESInitialize         InitializeCmd,
                              ocnHistPMOTUSESInitialize        InitializeCmd,
                              ocnHistPMOTUOFSInitialize        InitializeCmd,
                              ocnHistPMNBITCRInitialize        InitializeCmd,
                              ocnHistPMNBYTCRInitialize        InitializeCmd,
                              ocnHistPMUNCRCDWInitialize       InitializeCmd,
                              ocnHistPMOTNBERValue             DisplayString,
                              ocnHistPMOTNBERTimeStamp         DateAndTime,
                              ocnHistPMOTNBERValidity          PMValidity,
                              ocnHistPMOTNBERInitialize        InitializeCmd,
                              ocnHistPMOTNAVGBERValue          DisplayString,
                              ocnHistPMOTNAVGBERTimeStamp      DateAndTime,
                              ocnHistPMOTNAVGBERValidity       PMValidity,
                              ocnHistPMOTNAVGBERInitialize     InitializeCmd,
                              ocnHistPMNBITCR64BitValue        Unsigned64,
                              ocnHistPMNBITCR64BitTimeStamp    DateAndTime,
                              ocnHistPMNBITCR64BitValidity     PMValidity,
                              ocnHistPMNBITCR64BitInitialize   InitializeCmd,
                              ocnHistPMNBYTCR64BitValue        Unsigned64,
                              ocnHistPMNBYTCR64BitTimeStamp    DateAndTime,
                              ocnHistPMNBYTCR64BitValidity     PMValidity,
                              ocnHistPMNBYTCR64BitInitialize   InitializeCmd,
                              ocnHistPMUASSValue               Unsigned32,
                              ocnHistPMUASSTimeStamp           DateAndTime,
                              ocnHistPMUASSValidity            PMValidity,
                              ocnHistPMUASSInitialize          InitializeCmd,
                              ocnHistPMOTUUASValue             Unsigned32,
                              ocnHistPMOTUUASTimeStamp         DateAndTime,
                              ocnHistPMOTUUASValidity          PMValidity,
                              ocnHistPMOTUUASInitialize        InitializeCmd,
                              ocnHistPMOPRMinValue             FixedX10,
                              ocnHistPMOPRMinTimeStamp         DateAndTime,
                              ocnHistPMOPRMinValidity          PMValidity,
                              ocnHistPMOPRMinInitialize        InitializeCmd,
                              ocnHistPMOPRMaxValue             FixedX10,
                              ocnHistPMOPRMaxTimeStamp         DateAndTime,
                              ocnHistPMOPRMaxValidity          PMValidity,
                              ocnHistPMOPRMaxInitialize        InitializeCmd,
                              ocnHistPMOPRAvgValue             FixedX10,
                              ocnHistPMOPRAvgTimeStamp         DateAndTime,
                              ocnHistPMOPRAvgValidity          PMValidity,
                              ocnHistPMOPRAvgInitialize        InitializeCmd,
                              ocnHistPMOPTMinValue             FixedX10,
                              ocnHistPMOPTMinTimeStamp         DateAndTime,
                              ocnHistPMOPTMinValidity          PMValidity,
                              ocnHistPMOPTMinInitialize        InitializeCmd,
                              ocnHistPMOPTMaxValue             FixedX10,
                              ocnHistPMOPTMaxTimeStamp         DateAndTime,
                              ocnHistPMOPTMaxValidity          PMValidity,
                              ocnHistPMOPTMaxInitialize        InitializeCmd,
                              ocnHistPMOPTAvgValue             FixedX10,
                              ocnHistPMOPTAvgTimeStamp         DateAndTime,
                              ocnHistPMOPTAvgValidity          PMValidity,
                              ocnHistPMOPTAvgInitialize        InitializeCmd}


ocnHistPMTypeIdx OBJECT-TYPE
    SYNTAX       OcnType
    MAX-ACCESS   not-accessible
    STATUS       current
    DESCRIPTION  "The type of the OC-N facility targeted for PMs."
    ::= { ocnHistPMEntry 1 }


ocnHistPMShelfIdx OBJECT-TYPE
    SYNTAX       INTEGER (1|11|21|31)
    MAX-ACCESS   not-accessible
    STATUS       current
    DESCRIPTION  "The number of the shelf on which the OC-N facility targeted
                  for PMs is provisioned."
    ::= { ocnHistPMEntry 2 }


ocnHistPMSlotIdx OBJECT-TYPE
    SYNTAX       INTEGER (1..20)
    MAX-ACCESS   not-accessible
    STATUS       current
    DESCRIPTION  "The number of the slot within which the OC-N facility targeted
                  for PMs is provisioned."
    ::= { ocnHistPMEntry 3 }


ocnHistPMPortIdx OBJECT-TYPE
    SYNTAX       INTEGER (1..6)
    MAX-ACCESS   not-accessible
    STATUS       current
    DESCRIPTION  "The number of the port on the circuit pack on which the OC-N
                  facility targeted for PMs is provisioned."
    ::= { ocnHistPMEntry 4 }


ocnHistPMIntervalTypeIdx OBJECT-TYPE
    SYNTAX       PMIntervalType
    MAX-ACCESS   not-accessible
    STATUS       current
    DESCRIPTION  "The type of PM bin according to interval length."
    ::= { ocnHistPMEntry 5 }


ocnHistPMIntervalIdx OBJECT-TYPE
    SYNTAX       INTEGER (1..96)
    MAX-ACCESS   not-accessible
    STATUS       current
    DESCRIPTION  "The specific PM bin number. The range is 1 to 96 for the
                  15-minute historical bins. For the 1-day historical bin, the
                  value is 1."
    ::= { ocnHistPMEntry 6 }


ocnHistPMOPRValue OBJECT-TYPE
    SYNTAX       FixedX10
    UNITS        "dBm/10"
    MAX-ACCESS   read-only
    STATUS       current
    DESCRIPTION  "The optical power received on the input of the OC-N facility."
    ::= { ocnHistPMEntry 7 }


ocnHistPMOPRTimeStamp OBJECT-TYPE
    SYNTAX       DateAndTime
    MAX-ACCESS   read-only
    STATUS       current
    DESCRIPTION  "The date and time stamp of the optical power received value."
    ::= { ocnHistPMEntry 8 }


ocnHistPMOPRValidity OBJECT-TYPE
    SYNTAX       PMValidity
    MAX-ACCESS   read-only
    STATUS       current
    DESCRIPTION  "Indicates the validity of the provided optical power received
                  value."
    ::= { ocnHistPMEntry 9 }


ocnHistPMOPTValue OBJECT-TYPE
    SYNTAX       FixedX10
    UNITS        "dBm/10"
    MAX-ACCESS   read-only
    STATUS       current
    DESCRIPTION  "The optical power transmitted at the output of the OC-N
                  facility."
    ::= { ocnHistPMEntry 10 }


ocnHistPMOPTTimeStamp OBJECT-TYPE
    SYNTAX       DateAndTime
    MAX-ACCESS   read-only
    STATUS       current
    DESCRIPTION  "The date and time stamp of the optical power transmitted
                  value."
    ::= { ocnHistPMEntry 11 }


ocnHistPMOPTValidity OBJECT-TYPE
    SYNTAX       PMValidity
    MAX-ACCESS   read-only
    STATUS       current
    DESCRIPTION  "Indicates the validity of the provided optical power
                  transmitted value."
    ::= { ocnHistPMEntry 12 }


ocnHistPMTempValue OBJECT-TYPE
    SYNTAX       INTEGER (-32768..32767)
    UNITS        "degrees Celsius"
    MAX-ACCESS   read-only
    STATUS       current
    DESCRIPTION  "The temperature measured on the OC-N facility port."
    ::= { ocnHistPMEntry 13 }


ocnHistPMTempTimeStamp OBJECT-TYPE
    SYNTAX       DateAndTime
    MAX-ACCESS   read-only
    STATUS       current
    DESCRIPTION  "The date and time stamp of the temperature value."
    ::= { ocnHistPMEntry 14 }


ocnHistPMTempValidity OBJECT-TYPE
    SYNTAX       PMValidity
    MAX-ACCESS   read-only
    STATUS       current
    DESCRIPTION  "Indicates the validity of the provided temperature value."
    ::= { ocnHistPMEntry 15 }


ocnHistPMSupplyVoltageValue OBJECT-TYPE
    SYNTAX       FixedX10
    UNITS        "mVolts/10"
    MAX-ACCESS   read-only
    STATUS       current
    DESCRIPTION  "The supply voltage measured on the OC-N facility port."
    ::= { ocnHistPMEntry 16 }


ocnHistPMSupplyVoltageTimeStamp OBJECT-TYPE
    SYNTAX       DateAndTime
    MAX-ACCESS   read-only
    STATUS       current
    DESCRIPTION  "The date and time stamp of the supply voltage value."
    ::= { ocnHistPMEntry 17 }


ocnHistPMSupplyVoltageValidity OBJECT-TYPE
    SYNTAX       PMValidity
    MAX-ACCESS   read-only
    STATUS       current
    DESCRIPTION  "Indicates the validity of the provided supply voltage value."
    ::= { ocnHistPMEntry 18 }


ocnHistPMLBCValue OBJECT-TYPE
    SYNTAX       INTEGER (-32768..32767)
    UNITS        "mAmp"
    MAX-ACCESS   read-only
    STATUS       current
    DESCRIPTION  "The laser bias current measured on the OC-N facility port."
    ::= { ocnHistPMEntry 19 }


ocnHistPMLBCTimeStamp OBJECT-TYPE
    SYNTAX       DateAndTime
    MAX-ACCESS   read-only
    STATUS       current
    DESCRIPTION  "The date and time stamp of the laser bias current value."
    ::= { ocnHistPMEntry 20 }


ocnHistPMLBCValidity OBJECT-TYPE
    SYNTAX       PMValidity
    MAX-ACCESS   read-only
    STATUS       current
    DESCRIPTION  "Indicates the validity of the provided laser bias current
                  value."
    ::= { ocnHistPMEntry 21 }


ocnHistPMCVSValue OBJECT-TYPE
    SYNTAX       Unsigned32
    MAX-ACCESS   read-write
    STATUS       current
    DESCRIPTION  "The count of coding violations at the section layer."
    ::= { ocnHistPMEntry 22 }


ocnHistPMCVSTimeStamp OBJECT-TYPE
    SYNTAX       DateAndTime
    MAX-ACCESS   read-only
    STATUS       current
    DESCRIPTION  "The date and time stamp of the section layer coding violations
                  value."
    ::= { ocnHistPMEntry 23 }


ocnHistPMCVSValidity OBJECT-TYPE
    SYNTAX       PMValidity
    MAX-ACCESS   read-only
    STATUS       current
    DESCRIPTION  "Indicates the validity of the provided section layer coding
                  violations value."
    ::= { ocnHistPMEntry 24 }


ocnHistPMESSValue OBJECT-TYPE
    SYNTAX       Unsigned32
    MAX-ACCESS   read-write
    STATUS       current
    DESCRIPTION  "The count of errored seconds at the section layer."
    ::= { ocnHistPMEntry 25 }


ocnHistPMESSTimeStamp OBJECT-TYPE
    SYNTAX       DateAndTime
    MAX-ACCESS   read-only
    STATUS       current
    DESCRIPTION  "The date and time stamp of the section layer errored seconds
                  value."
    ::= { ocnHistPMEntry 26 }


ocnHistPMESSValidity OBJECT-TYPE
    SYNTAX       PMValidity
    MAX-ACCESS   read-only
    STATUS       current
    DESCRIPTION  "Indicates the validity of the provided section layer errored
                  seconds value."
    ::= { ocnHistPMEntry 27 }


ocnHistPMSESSValue OBJECT-TYPE
    SYNTAX       Unsigned32
    MAX-ACCESS   read-write
    STATUS       current
    DESCRIPTION  "The count of severely errored seconds at the section layer."
    ::= { ocnHistPMEntry 28 }


ocnHistPMSESSTimeStamp OBJECT-TYPE
    SYNTAX       DateAndTime
    MAX-ACCESS   read-only
    STATUS       current
    DESCRIPTION  "The date and time stamp of the section layer severely errored
                  seconds value."
    ::= { ocnHistPMEntry 29 }


ocnHistPMSESSValidity OBJECT-TYPE
    SYNTAX       PMValidity
    MAX-ACCESS   read-only
    STATUS       current
    DESCRIPTION  "Indicates the validity of the provided section layer severely
                  errored seconds value."
    ::= { ocnHistPMEntry 30 }


ocnHistPMSEFSSValue OBJECT-TYPE
    SYNTAX       Unsigned32
    MAX-ACCESS   read-write
    STATUS       current
    DESCRIPTION  "The count of severely errored framing seconds at the section
                  layer."
    ::= { ocnHistPMEntry 31 }


ocnHistPMSEFSSTimeStamp OBJECT-TYPE
    SYNTAX       DateAndTime
    MAX-ACCESS   read-only
    STATUS       current
    DESCRIPTION  "The date and time stamp of the section layer severely errored
                  framing seconds value."
    ::= { ocnHistPMEntry 32 }


ocnHistPMSEFSSValidity OBJECT-TYPE
    SYNTAX       PMValidity
    MAX-ACCESS   read-only
    STATUS       current
    DESCRIPTION  "Indicates the validity of the provided section layer severely
                  errored framing seconds value."
    ::= { ocnHistPMEntry 33 }


ocnHistPMSupplyVoltage2Value OBJECT-TYPE
    SYNTAX       FixedX10
    UNITS        "mVolts/10"
    MAX-ACCESS   read-only
    STATUS       current
    DESCRIPTION  "The value of the second supply voltage source measured on the
                  OC-N facility port transceiver."
    ::= { ocnHistPMEntry 34 }


ocnHistPMSupplyVoltage2TimeStamp OBJECT-TYPE
    SYNTAX       DateAndTime
    MAX-ACCESS   read-only
    STATUS       current
    DESCRIPTION  "The date and time stamp of the second supply voltage value."
    ::= { ocnHistPMEntry 35 }


ocnHistPMSupplyVoltage2Validity OBJECT-TYPE
    SYNTAX       PMValidity
    MAX-ACCESS   read-only
    STATUS       current
    DESCRIPTION  "Indicates the validity of the provided second supply voltage
                  value."
    ::= { ocnHistPMEntry 36 }


ocnHistPMCVLValue OBJECT-TYPE
    SYNTAX       Unsigned32
    MAX-ACCESS   read-write
    STATUS       current
    DESCRIPTION  "The count of coding violations at the line layer."
    ::= { ocnHistPMEntry 37 }


ocnHistPMCVLTimeStamp OBJECT-TYPE
    SYNTAX       DateAndTime
    MAX-ACCESS   read-only
    STATUS       current
    DESCRIPTION  "The date and time stamp of the line layer coding violations
                  value."
    ::= { ocnHistPMEntry 38 }


ocnHistPMCVLValidity OBJECT-TYPE
    SYNTAX       PMValidity
    MAX-ACCESS   read-only
    STATUS       current
    DESCRIPTION  "Indicates the validity of the provided line layer coding
                  violations value."
    ::= { ocnHistPMEntry 39 }


ocnHistPMESLValue OBJECT-TYPE
    SYNTAX       Unsigned32
    MAX-ACCESS   read-write
    STATUS       current
    DESCRIPTION  "The count of errored seconds at the line layer."
    ::= { ocnHistPMEntry 40 }


ocnHistPMESLTimeStamp OBJECT-TYPE
    SYNTAX       DateAndTime
    MAX-ACCESS   read-only
    STATUS       current
    DESCRIPTION  "The date and time stamp of the line layer errored seconds
                  value."
    ::= { ocnHistPMEntry 41 }


ocnHistPMESLValidity OBJECT-TYPE
    SYNTAX       PMValidity
    MAX-ACCESS   read-only
    STATUS       current
    DESCRIPTION  "Indicates the validity of the provided line layer errored
                  seconds value."
    ::= { ocnHistPMEntry 42 }


ocnHistPMSESLValue OBJECT-TYPE
    SYNTAX       Unsigned32
    MAX-ACCESS   read-write
    STATUS       current
    DESCRIPTION  "The count of severely errored seconds at the line layer."
    ::= { ocnHistPMEntry 43 }


ocnHistPMSESLTimeStamp OBJECT-TYPE
    SYNTAX       DateAndTime
    MAX-ACCESS   read-only
    STATUS       current
    DESCRIPTION  "The date and time stamp of the line layer severely errored
                  seconds value."
    ::= { ocnHistPMEntry 44 }


ocnHistPMSESLValidity OBJECT-TYPE
    SYNTAX       PMValidity
    MAX-ACCESS   read-only
    STATUS       current
    DESCRIPTION  "Indicates the validity of the provided line layer severely
                  errored seconds value."
    ::= { ocnHistPMEntry 45 }


ocnHistPMUASLValue OBJECT-TYPE
    SYNTAX       Unsigned32
    MAX-ACCESS   read-write
    STATUS       current
    DESCRIPTION  "The count of unavailable seconds at the line layer."
    ::= { ocnHistPMEntry 46 }


ocnHistPMUASLTimeStamp OBJECT-TYPE
    SYNTAX       DateAndTime
    MAX-ACCESS   read-only
    STATUS       current
    DESCRIPTION  "The date and time stamp of the line layer unavailable seconds
                  value."
    ::= { ocnHistPMEntry 47 }


ocnHistPMUASLValidity OBJECT-TYPE
    SYNTAX       PMValidity
    MAX-ACCESS   read-only
    STATUS       current
    DESCRIPTION  "Indicates the validity of the provided line layer unavailable
                  seconds value."
    ::= { ocnHistPMEntry 48 }


ocnHistPMOTUEBValue OBJECT-TYPE
    SYNTAX       Unsigned32 
    MAX-ACCESS   read-write
    STATUS       current
    DESCRIPTION  "The count of OTU digital wrapper layer errored blocks."
    ::= { ocnHistPMEntry 49 }


ocnHistPMOTUEBTimeStamp OBJECT-TYPE
    SYNTAX       DateAndTime
    MAX-ACCESS   read-only
    STATUS       current
    DESCRIPTION  "The date and time stamp of the OTU digital wrapper layer
                  errored blocks value."
    ::= { ocnHistPMEntry 50 }


ocnHistPMOTUEBValidity OBJECT-TYPE
    SYNTAX       PMValidity
    MAX-ACCESS   read-only
    STATUS       current
    DESCRIPTION  "Indicates the validity of the provided OTU digital wrapper
                  layer errored blocks value."
    ::= { ocnHistPMEntry 51 }


ocnHistPMOTUBBEValue OBJECT-TYPE
    SYNTAX       Unsigned32 
    MAX-ACCESS   read-write
    STATUS       current
    DESCRIPTION  "The count of OTU digital wrapper layer background block
                  errors."
    ::= { ocnHistPMEntry 52 }


ocnHistPMOTUBBETimeStamp OBJECT-TYPE
    SYNTAX       DateAndTime
    MAX-ACCESS   read-only
    STATUS       current
    DESCRIPTION  "The date and time stamp of the OTU digital wrapper layer
                  background block errors value."
    ::= { ocnHistPMEntry 53 }


ocnHistPMOTUBBEValidity OBJECT-TYPE
    SYNTAX       PMValidity
    MAX-ACCESS   read-only
    STATUS       current
    DESCRIPTION  "Indicates the validity of the provided OTU digital wrapper
                  layer background block errors value."
    ::= { ocnHistPMEntry 54 }


ocnHistPMOTUESValue OBJECT-TYPE
    SYNTAX       Unsigned32
    MAX-ACCESS   read-write
    STATUS       current
    DESCRIPTION  "The count of OTU digital wrapper layer errored seconds."
    ::= { ocnHistPMEntry 55 }


ocnHistPMOTUESTimeStamp OBJECT-TYPE
    SYNTAX       DateAndTime
    MAX-ACCESS   read-only
    STATUS       current
    DESCRIPTION  "The date and time stamp of the OTU digital wrapper layer
                  errored seconds value."
    ::= { ocnHistPMEntry 56 }


ocnHistPMOTUESValidity OBJECT-TYPE
    SYNTAX       PMValidity
    MAX-ACCESS   read-only
    STATUS       current
    DESCRIPTION  "Indicates the validity of the provided OTU digital wrapper
                  layer errored seconds value."
    ::= { ocnHistPMEntry 57 }


ocnHistPMOTUSESValue OBJECT-TYPE
    SYNTAX       Unsigned32
    MAX-ACCESS   read-write
    STATUS       current
    DESCRIPTION  "The count of OTU digital wrapper layer severely errored
                  seconds."
    ::= { ocnHistPMEntry 58 }


ocnHistPMOTUSESTimeStamp OBJECT-TYPE
    SYNTAX       DateAndTime
    MAX-ACCESS   read-only
    STATUS       current
    DESCRIPTION  "The date and time stamp of the OTU digital wrapper layer
                  severely errored seconds value."
    ::= { ocnHistPMEntry 59 }


ocnHistPMOTUSESValidity OBJECT-TYPE
    SYNTAX       PMValidity
    MAX-ACCESS   read-only
    STATUS       current
    DESCRIPTION  "Indicates the validity of the provided OTU digital wrapper
                  layer severely errored seconds value."
    ::= { ocnHistPMEntry 60 }


ocnHistPMOTUOFSValue OBJECT-TYPE
    SYNTAX       Unsigned32
    MAX-ACCESS   read-write
    STATUS       current
    DESCRIPTION  "The count of OTU digital wrapper layer out-of-frame seconds."
    ::= { ocnHistPMEntry 61 }


ocnHistPMOTUOFSTimeStamp OBJECT-TYPE
    SYNTAX       DateAndTime
    MAX-ACCESS   read-only
    STATUS       current
    DESCRIPTION  "The date and time stamp of the OTU digital wrapper layer
                  out-of-frame seconds value."
    ::= { ocnHistPMEntry 62 }


ocnHistPMOTUOFSValidity OBJECT-TYPE
    SYNTAX       PMValidity
    MAX-ACCESS   read-only
    STATUS       current
    DESCRIPTION  "Indicates the validity of the provided OTU digital wrapper
                  layer out-of-frame seconds value."
    ::= { ocnHistPMEntry 63 }


ocnHistPMNBITCRValue OBJECT-TYPE
    SYNTAX       Unsigned32
    MAX-ACCESS   read-write
    STATUS       current
    DESCRIPTION  "The count of the number of bits corrected. This object applies
                  only to OC-192 line port provisioned for OTN line mapping."
    ::= { ocnHistPMEntry 64 }


ocnHistPMNBITCRTimeStamp OBJECT-TYPE
    SYNTAX       DateAndTime
    MAX-ACCESS   read-only
    STATUS       current
    DESCRIPTION  "The date and time stamp of the number of bits corrected
                  value."
    ::= { ocnHistPMEntry 65 }


ocnHistPMNBITCRValidity OBJECT-TYPE
    SYNTAX       PMValidity
    MAX-ACCESS   read-only
    STATUS       current
    DESCRIPTION  "Indicates the validity of the provided number of bits
                  corrected value."
    ::= { ocnHistPMEntry 66 }


ocnHistPMNBYTCRValue OBJECT-TYPE
    SYNTAX       Unsigned32
    MAX-ACCESS   read-write
    STATUS       current
    DESCRIPTION  "The count of the number of bytes corrected. This object
                  applies only to OC-192 line port provisioned for OTN line
                  mapping."
    ::= { ocnHistPMEntry 67 }


ocnHistPMNBYTCRTimeStamp OBJECT-TYPE
    SYNTAX       DateAndTime
    MAX-ACCESS   read-only
    STATUS       current
    DESCRIPTION  "The date and time stamp of the number of bytes corrected
                  value."
    ::= { ocnHistPMEntry 68 }


ocnHistPMNBYTCRValidity OBJECT-TYPE
    SYNTAX       PMValidity
    MAX-ACCESS   read-only
    STATUS       current
    DESCRIPTION  "Indicates the validity of the provided number of bytes
                  corrected value."
    ::= { ocnHistPMEntry 69 }


ocnHistPMUNCRCDWValue OBJECT-TYPE
    SYNTAX       Unsigned32
    MAX-ACCESS   read-write
    STATUS       current
    DESCRIPTION  "The count of uncorrectable codewords. This object applies only
                  to OC-192 line port provisioned for OTN line mapping."
    ::= { ocnHistPMEntry 70 }


ocnHistPMUNCRCDWTimeStamp OBJECT-TYPE
    SYNTAX       DateAndTime
    MAX-ACCESS   read-only
    STATUS       current
    DESCRIPTION  "The date and time stamp of the uncorrectable codewords value."
    ::= { ocnHistPMEntry 71 }


ocnHistPMUNCRCDWValidity OBJECT-TYPE
    SYNTAX       PMValidity
    MAX-ACCESS   read-only
    STATUS       current
    DESCRIPTION  "Indicates the validity of the provided uncorrectable codewords
                  value."
    ::= { ocnHistPMEntry 72 }


ocnHistPMCVSInitialize OBJECT-TYPE
    SYNTAX       InitializeCmd
    MAX-ACCESS   read-write
    STATUS       current
    DESCRIPTION  "Used to initialize the value of the ocnHistPMCVSValue object
                  to 0."
    ::= { ocnHistPMEntry 73 }


ocnHistPMESSInitialize OBJECT-TYPE
    SYNTAX       InitializeCmd
    MAX-ACCESS   read-write
    STATUS       current
    DESCRIPTION  "Used to initialize the value of the ocnHistPMESSValue object
                  to 0."
    ::= { ocnHistPMEntry 74 }


ocnHistPMSESSInitialize OBJECT-TYPE
    SYNTAX       InitializeCmd
    MAX-ACCESS   read-write
    STATUS       current
    DESCRIPTION  "Used to initialize the value of the ocnHistPMSESSValue object
                  to 0."
    ::= { ocnHistPMEntry 75 }


ocnHistPMSEFSSInitialize OBJECT-TYPE
    SYNTAX       InitializeCmd
    MAX-ACCESS   read-write
    STATUS       current
    DESCRIPTION  "Used to initialize the value of the ocnHistPMSEFSSValue object
                  to 0."
    ::= { ocnHistPMEntry 76 }


ocnHistPMCVLInitialize OBJECT-TYPE
    SYNTAX       InitializeCmd
    MAX-ACCESS   read-write
    STATUS       current
    DESCRIPTION  "Used to initialize the value of the ocnHistPMCVLValue object
                  to 0."
    ::= { ocnHistPMEntry 77 }


ocnHistPMESLInitialize OBJECT-TYPE
    SYNTAX       InitializeCmd
    MAX-ACCESS   read-write
    STATUS       current
    DESCRIPTION  "Used to initialize the value of the ocnHistPMESLValue object
                  to 0."
    ::= { ocnHistPMEntry 78 }


ocnHistPMSESLInitialize OBJECT-TYPE
    SYNTAX       InitializeCmd
    MAX-ACCESS   read-write
    STATUS       current
    DESCRIPTION  "Used to initialize the value of the ocnHistPMSESLValue object
                  to 0."
    ::= { ocnHistPMEntry 79 }


ocnHistPMUASLInitialize OBJECT-TYPE
    SYNTAX       InitializeCmd
    MAX-ACCESS   read-write
    STATUS       current
    DESCRIPTION  "Used to initialize the value of the ocnHistPMUASLValue object
                  to 0."
    ::= { ocnHistPMEntry 80 }


ocnHistPMOTUEBInitialize OBJECT-TYPE
    SYNTAX       InitializeCmd
    MAX-ACCESS   read-write
    STATUS       current
    DESCRIPTION  "Used to initialize the value of the ocnHistPMOTUEBValue object
                  to 0."
    ::= { ocnHistPMEntry 81 }


ocnHistPMOTUBBEInitialize OBJECT-TYPE
    SYNTAX       InitializeCmd
    MAX-ACCESS   read-write
    STATUS       current
    DESCRIPTION  "Used to initialize the value of the ocnHistPMOTUBBEValue
                  object to 0."
    ::= { ocnHistPMEntry 82 }


ocnHistPMOTUESInitialize OBJECT-TYPE
    SYNTAX       InitializeCmd
    MAX-ACCESS   read-write
    STATUS       current
    DESCRIPTION  "Used to initialize the value of the ocnHistPMOTUESValue object
                  to 0."
    ::= { ocnHistPMEntry 83 }


ocnHistPMOTUSESInitialize OBJECT-TYPE
    SYNTAX       InitializeCmd
    MAX-ACCESS   read-write
    STATUS       current
    DESCRIPTION  "Used to initialize the value of the ocnHistPMOTUSESValue
                  object to 0."
    ::= { ocnHistPMEntry 84 }


ocnHistPMOTUOFSInitialize OBJECT-TYPE
    SYNTAX       InitializeCmd
    MAX-ACCESS   read-write
    STATUS       current
    DESCRIPTION  "Used to initialize the value of the ocnHistPMOTUOFSValue
                  object to 0."
    ::= { ocnHistPMEntry 85 }


ocnHistPMNBITCRInitialize OBJECT-TYPE
    SYNTAX       InitializeCmd
    MAX-ACCESS   read-write
    STATUS       current
    DESCRIPTION  "Used to initialize the value of the ocnHistPMNBITCRValue
                  object to 0."
    ::= { ocnHistPMEntry 86 }


ocnHistPMNBYTCRInitialize OBJECT-TYPE
    SYNTAX       InitializeCmd
    MAX-ACCESS   read-write
    STATUS       current
    DESCRIPTION  "Used to initialize the value of the ocnHistPMNBYTCRValue
                  object to 0."
    ::= { ocnHistPMEntry 87 }


ocnHistPMUNCRCDWInitialize OBJECT-TYPE
    SYNTAX       InitializeCmd
    MAX-ACCESS   read-write
    STATUS       current
    DESCRIPTION  "Used to initialize the value of the ocnHistPMUNCRCDWValue
                  object to 0."
    ::= { ocnHistPMEntry 88 }


ocnHistPMOTNBERValue OBJECT-TYPE
    SYNTAX       DisplayString
    MAX-ACCESS   read-only
    STATUS       current
    DESCRIPTION  "The instantaneous BER of OC-192 line port provisioned for OTN line mapping."
    ::= { ocnHistPMEntry 89 }


ocnHistPMOTNBERTimeStamp OBJECT-TYPE
    SYNTAX       DateAndTime
    MAX-ACCESS   read-only
    STATUS       current
    DESCRIPTION  "The date and time stamp of the instantaneous BER."
    ::= { ocnHistPMEntry 90 }


ocnHistPMOTNBERValidity OBJECT-TYPE
    SYNTAX       PMValidity
    MAX-ACCESS   read-only
    STATUS       current
    DESCRIPTION  "Indicates the validity of the provided instantaneous BER."
    ::= { ocnHistPMEntry 91 }


ocnHistPMOTNBERInitialize OBJECT-TYPE
    SYNTAX       InitializeCmd
    MAX-ACCESS   read-write
    STATUS       current
    DESCRIPTION  "Used to initialize the value of the ocnHistPMOTNBERValue
                  object to 0."
    ::= { ocnHistPMEntry 92 }


ocnHistPMOTNAVGBERValue OBJECT-TYPE
    SYNTAX       DisplayString
    MAX-ACCESS   read-only
    STATUS       current
    DESCRIPTION  "The interval/average BER of OC-192 line port provisioned for OTN line mapping."
    ::= { ocnHistPMEntry 93 }


ocnHistPMOTNAVGBERTimeStamp OBJECT-TYPE
    SYNTAX       DateAndTime
    MAX-ACCESS   read-only
    STATUS       current
    DESCRIPTION  "The date and time stamp of the interval/average BER."
    ::= { ocnHistPMEntry 94 }


ocnHistPMOTNAVGBERValidity OBJECT-TYPE
    SYNTAX       PMValidity
    MAX-ACCESS   read-only
    STATUS       current
    DESCRIPTION  "Indicates the validity of the provided interval/average BER."
    ::= { ocnHistPMEntry 95 }


ocnHistPMOTNAVGBERInitialize OBJECT-TYPE
    SYNTAX       InitializeCmd
    MAX-ACCESS   read-write
    STATUS       current
    DESCRIPTION  "Used to initialize the value of the ocnHistPMOTNAVGBERValue
                  object to 0."
    ::= { ocnHistPMEntry 96 }


ocnHistPMNBITCR64BitValue OBJECT-TYPE
    SYNTAX       Unsigned64
    MAX-ACCESS   read-only
    STATUS       current
    DESCRIPTION  "The 64-bit count of the number of bits corrected. This object
                  applies only to OC-192 line port provisioned for OTN line mapping."
    ::= { ocnHistPMEntry 97 }


ocnHistPMNBITCR64BitTimeStamp OBJECT-TYPE
    SYNTAX       DateAndTime
    MAX-ACCESS   read-only
    STATUS       current
    DESCRIPTION  "The date and time stamp of the 64-bit number of bits corrected
                  value."
    ::= { ocnHistPMEntry 98 }


ocnHistPMNBITCR64BitValidity OBJECT-TYPE
    SYNTAX       PMValidity
    MAX-ACCESS   read-only
    STATUS       current
    DESCRIPTION  "Indicates the validity of the provided 64-bit number of bits
                  corrected value."
    ::= { ocnHistPMEntry 99 }


ocnHistPMNBITCR64BitInitialize OBJECT-TYPE
    SYNTAX       InitializeCmd
    MAX-ACCESS   read-write
    STATUS       current
    DESCRIPTION  "Used to initialize the value of the ocnHistPMNBITCR64BitValue
                  object to 0."
    ::= { ocnHistPMEntry 100 }


ocnHistPMNBYTCR64BitValue OBJECT-TYPE
    SYNTAX       Unsigned64
    MAX-ACCESS   read-only
    STATUS       current
    DESCRIPTION  "The 64-bit count of the number of bytes corrected. This object
                  applies only to OC-192 line port provisioned for OTN line
                  mapping."
    ::= { ocnHistPMEntry 101 }


ocnHistPMNBYTCR64BitTimeStamp OBJECT-TYPE
    SYNTAX       DateAndTime
    MAX-ACCESS   read-only
    STATUS       current
    DESCRIPTION  "The date and time stamp of the 64-bit number of bytes corrected
                  value."
    ::= { ocnHistPMEntry 102 }


ocnHistPMNBYTCR64BitValidity OBJECT-TYPE
    SYNTAX       PMValidity
    MAX-ACCESS   read-only
    STATUS       current
    DESCRIPTION  "Indicates the validity of the provided 64-bit number of bytes
                  corrected value."
    ::= { ocnHistPMEntry 103 }


ocnHistPMNBYTCR64BitInitialize OBJECT-TYPE
    SYNTAX       InitializeCmd
    MAX-ACCESS   read-write
    STATUS       current
    DESCRIPTION  "Used to initialize the value of the ocnHistPMNBYTCR64BitValue
                  object to 0."
    ::= { ocnHistPMEntry 104 }


ocnHistPMUASSValue OBJECT-TYPE
    SYNTAX       Unsigned32
    MAX-ACCESS   read-write
    STATUS       current
    DESCRIPTION  "The count of unavailable seconds at the section layer.
                  This object applies only to OC-192 line port provisioned
                  for OTN line mapping."
    ::= { ocnHistPMEntry 105 }

ocnHistPMUASSTimeStamp OBJECT-TYPE
    SYNTAX       DateAndTime
    MAX-ACCESS   read-only
    STATUS       current
    DESCRIPTION  "The date and time stamp of the unavailable seconds at the section layer."
    ::= { ocnHistPMEntry 106 }

ocnHistPMUASSValidity OBJECT-TYPE
    SYNTAX       PMValidity
    MAX-ACCESS   read-only
    STATUS       current
    DESCRIPTION  "Indicates the validity of the unavailable seconds at the section layer."
    ::= { ocnHistPMEntry 107 }

ocnHistPMUASSInitialize OBJECT-TYPE
    SYNTAX       InitializeCmd
    MAX-ACCESS   read-write
    STATUS       current
    DESCRIPTION  "Used to initialize the value of the ocnHistPMUASSValue
                  object to 0."
    ::= { ocnHistPMEntry 108 }

ocnHistPMOTUUASValue OBJECT-TYPE
    SYNTAX       Unsigned32
    MAX-ACCESS   read-write
    STATUS       current
    DESCRIPTION  "The count of OTU digital wrapper layer unavailable seconds."
    ::= { ocnHistPMEntry 109 }


ocnHistPMOTUUASTimeStamp OBJECT-TYPE
    SYNTAX       DateAndTime
    MAX-ACCESS   read-only
    STATUS       current
    DESCRIPTION  "The date and time stamp of the OTU digital wrapper layer
                  unavailable seconds value."
    ::= { ocnHistPMEntry 110 }


ocnHistPMOTUUASValidity OBJECT-TYPE
    SYNTAX       PMValidity
    MAX-ACCESS   read-only
    STATUS       current
    DESCRIPTION  "Indicates the validity of the provided OTU digital wrapper
                  layer unavailable seconds value."
    ::= { ocnHistPMEntry 111 }

ocnHistPMOTUUASInitialize OBJECT-TYPE
    SYNTAX       InitializeCmd
    MAX-ACCESS   read-write
    STATUS       current
    DESCRIPTION  "Used to initialize the value of the ocnHistPMOTUUASValue
                  object to 0."
    ::= { ocnHistPMEntry 112 }

ocnHistPMOPRMinValue OBJECT-TYPE
    SYNTAX       FixedX10
    UNITS        "dBm/10"
    MAX-ACCESS   read-only
    STATUS       current
    DESCRIPTION  "The minimum optical power received on the input of the transceiver."
    ::= { ocnHistPMEntry 113 }


ocnHistPMOPRMinTimeStamp OBJECT-TYPE
    SYNTAX       DateAndTime
    MAX-ACCESS   read-only
    STATUS       current
    DESCRIPTION  "The date and time stamp of the minimum optical power received value."
    ::= { ocnHistPMEntry 114 }


ocnHistPMOPRMinValidity OBJECT-TYPE
    SYNTAX       PMValidity
    MAX-ACCESS   read-only
    STATUS       current
    DESCRIPTION  "Indicates the validity of the provided minimum optical power received
                  value."
    ::= { ocnHistPMEntry 115 }

ocnHistPMOPRMinInitialize OBJECT-TYPE
    SYNTAX       InitializeCmd
    MAX-ACCESS   read-write
    STATUS       current
    DESCRIPTION  "Used to initialize the value of the ocnHistPMOPRMinValue
                  object to 0."
    ::= { ocnHistPMEntry 116 }

ocnHistPMOPRMaxValue OBJECT-TYPE
    SYNTAX       FixedX10
    UNITS        "dBm/10"
    MAX-ACCESS   read-only
    STATUS       current
    DESCRIPTION  "The maximum optical power received on the input of the transceiver."
    ::= { ocnHistPMEntry 117 }


ocnHistPMOPRMaxTimeStamp OBJECT-TYPE
    SYNTAX       DateAndTime
    MAX-ACCESS   read-only
    STATUS       current
    DESCRIPTION  "The date and time stamp of the maximum optical power received value."
    ::= { ocnHistPMEntry 118 }


ocnHistPMOPRMaxValidity OBJECT-TYPE
    SYNTAX       PMValidity
    MAX-ACCESS   read-only
    STATUS       current
    DESCRIPTION  "Indicates the validity of the provided maximum optical power received
                  value."
    ::= { ocnHistPMEntry 119 }

ocnHistPMOPRMaxInitialize OBJECT-TYPE
    SYNTAX       InitializeCmd
    MAX-ACCESS   read-write
    STATUS       current
    DESCRIPTION  "Used to initialize the value of the ocnHistPMOPRMaxValue
                  object to 0."
    ::= { ocnHistPMEntry 120 }

ocnHistPMOPRAvgValue OBJECT-TYPE
    SYNTAX       FixedX10
    UNITS        "dBm/10"
    MAX-ACCESS   read-only
    STATUS       current
    DESCRIPTION  "The average optical power received on the input of the transceiver."
    ::= { ocnHistPMEntry 121 }


ocnHistPMOPRAvgTimeStamp OBJECT-TYPE
    SYNTAX       DateAndTime
    MAX-ACCESS   read-only
    STATUS       current
    DESCRIPTION  "The date and time stamp of the average optical power received value."
    ::= { ocnHistPMEntry 122 }


ocnHistPMOPRAvgValidity OBJECT-TYPE
    SYNTAX       PMValidity
    MAX-ACCESS   read-only
    STATUS       current
    DESCRIPTION  "Indicates the validity of the provided average optical power received
                  value."
    ::= { ocnHistPMEntry 123 }

ocnHistPMOPRAvgInitialize OBJECT-TYPE
    SYNTAX       InitializeCmd
    MAX-ACCESS   read-write
    STATUS       current
    DESCRIPTION  "Used to initialize the value of the ocnHistPMOPRAvgValue
                  object to 0."
    ::= { ocnHistPMEntry 124 }

ocnHistPMOPTMinValue OBJECT-TYPE
    SYNTAX       FixedX10
    UNITS        "dBm/10"
    MAX-ACCESS   read-only
    STATUS       current
    DESCRIPTION  "The minimum optical power transmitted at the output of the
                  transceiver."
    ::= { ocnHistPMEntry 125 }

ocnHistPMOPTMinTimeStamp OBJECT-TYPE
    SYNTAX       DateAndTime
    MAX-ACCESS   read-only
    STATUS       current
    DESCRIPTION  "The date and time stamp of the minimum optical power transmitted
                  value."
    ::= { ocnHistPMEntry 126 }


ocnHistPMOPTMinValidity OBJECT-TYPE
    SYNTAX       PMValidity
    MAX-ACCESS   read-only
    STATUS       current
    DESCRIPTION  "Indicates the validity of the provided minimum optical power
                  transmitted value."
    ::= { ocnHistPMEntry 127 }

ocnHistPMOPTMinInitialize OBJECT-TYPE
    SYNTAX       InitializeCmd
    MAX-ACCESS   read-write
    STATUS       current
    DESCRIPTION  "Used to initialize the value of the ocnHistPMOPTMinValue
                  object to 0."
    ::= { ocnHistPMEntry 128 }

ocnHistPMOPTMaxValue OBJECT-TYPE
    SYNTAX       FixedX10
    UNITS        "dBm/10"
    MAX-ACCESS   read-only
    STATUS       current
    DESCRIPTION  "The maximum optical power transmitted at the output of the
                  transceiver."
    ::= { ocnHistPMEntry 129 }


ocnHistPMOPTMaxTimeStamp OBJECT-TYPE
    SYNTAX       DateAndTime
    MAX-ACCESS   read-only
    STATUS       current
    DESCRIPTION  "The date and time stamp of the maximum optical power transmitted
                  value."
    ::= { ocnHistPMEntry 130 }


ocnHistPMOPTMaxValidity OBJECT-TYPE
    SYNTAX       PMValidity
    MAX-ACCESS   read-only
    STATUS       current
    DESCRIPTION  "Indicates the validity of the provided maximum optical power
                  transmitted value."
    ::= { ocnHistPMEntry 131 }

ocnHistPMOPTMaxInitialize OBJECT-TYPE
    SYNTAX       InitializeCmd
    MAX-ACCESS   read-write
    STATUS       current
    DESCRIPTION  "Used to initialize the value of the ocnHistPMOPTMaxValue
                  object to 0."
    ::= { ocnHistPMEntry 132 }

ocnHistPMOPTAvgValue OBJECT-TYPE
    SYNTAX       FixedX10
    UNITS        "dBm/10"
    MAX-ACCESS   read-only
    STATUS       current
    DESCRIPTION  "The average optical power transmitted at the output of the
                  transceiver."
    ::= { ocnHistPMEntry 133 }


ocnHistPMOPTAvgTimeStamp OBJECT-TYPE
    SYNTAX       DateAndTime
    MAX-ACCESS   read-only
    STATUS       current
    DESCRIPTION  "The date and time stamp of the average optical power transmitted
                  value."
    ::= { ocnHistPMEntry 134 }

ocnHistPMOPTAvgValidity OBJECT-TYPE
    SYNTAX       PMValidity
    MAX-ACCESS   read-only
    STATUS       current
    DESCRIPTION  "Indicates the validity of the provided average optical power
                  transmitted value."
    ::= { ocnHistPMEntry 135 }

ocnHistPMOPTAvgInitialize OBJECT-TYPE
    SYNTAX       InitializeCmd
    MAX-ACCESS   read-write
    STATUS       current
    DESCRIPTION  "Used to initialize the value of the ocnHistPMOPTAvgValue
                  object to 0."
    ::= { ocnHistPMEntry 136 }

-----------------------------------------------------------------------
-- Objects used to manage SONET OC-N Performance
-- Monitoring Threshold Levels
-- 
-- A listing of SONET OC-N PM threshold levels is contained in the
-- ocnPMThresholdTable of the BTI-7000-MIB. When retrieved, this table 
-- provides one row for each set of current SONET OC-N PM threshold 
-- data.
-- 
-- The following table lists the objects in each entry of the 
-- ocnPMThresholdTable.
-----------------------------------------------------------------------


ocnPMThresholdTable OBJECT-TYPE
    SYNTAX       SEQUENCE OF OcnPMThresholdEntry
    MAX-ACCESS   not-accessible
    STATUS       current
    DESCRIPTION  "A table of threshold levels for performance monitoring counter
                  values on SONET OC-N facilities, that are used in the
                  generation of threshold crossing alerts."
    ::= { performance 10 }


ocnPMThresholdEntry OBJECT-TYPE
    SYNTAX       OcnPMThresholdEntry
    MAX-ACCESS   not-accessible
    STATUS       current
    DESCRIPTION  "The row entry object of the SONET OC-N performance monitoring
                  threshold table. Each row of this table contains a set of PM
                  thresholds for a given interval type that applies to an
                  individual OC-N facility."
    INDEX        { ocnPMThresholdTypeIdx,
                   ocnPMThresholdShelfIdx,
                   ocnPMThresholdSlotIdx,
                   ocnPMThresholdPortIdx,
                   ocnPMThresholdIntervalTypeIdx }
    ::= { ocnPMThresholdTable 1 }


OcnPMThresholdEntry ::= SEQUENCE { ocnPMThresholdTypeIdx          OcnType,
                                   ocnPMThresholdShelfIdx         INTEGER,
                                   ocnPMThresholdSlotIdx          INTEGER,
                                   ocnPMThresholdPortIdx          INTEGER,
                                   ocnPMThresholdIntervalTypeIdx  PMIntervalType,
                                   ocnPMThresholdCVSValue         Unsigned32,
                                   ocnPMThresholdESSValue         Unsigned32,
                                   ocnPMThresholdSESSValue        Unsigned32,
                                   ocnPMThresholdSEFSSValue       Unsigned32,
                                   ocnPMThresholdCVLValue         Unsigned32,
                                   ocnPMThresholdESLValue         Unsigned32,
                                   ocnPMThresholdSESLValue        Unsigned32,
                                   ocnPMThresholdUASLValue        Unsigned32,
                                   ocnPMThresholdOTUEBValue       Unsigned32,
                                   ocnPMThresholdOTUBBEValue      Unsigned32,
                                   ocnPMThresholdOTUESValue       Unsigned32,
                                   ocnPMThresholdOTUSESValue      Unsigned32,
                                   ocnPMThresholdOTUOFSValue      Unsigned32,
                                   ocnPMThresholdUNCRCDWValue     Unsigned32,
                                   ocnPMThresholdUASSValue        Unsigned32,
                                   ocnPMThresholdOTUUASValue      Unsigned32 }
      

ocnPMThresholdTypeIdx OBJECT-TYPE
    SYNTAX       OcnType
    MAX-ACCESS   not-accessible
    STATUS       current
    DESCRIPTION  "The type of the OC-N facility targeted for PM thresholds."
    ::= { ocnPMThresholdEntry 1 }


ocnPMThresholdShelfIdx OBJECT-TYPE
    SYNTAX       INTEGER (1|11|21|31)
    MAX-ACCESS   not-accessible
    STATUS       current
    DESCRIPTION  "The shelf number on which the OC-N facility targeted for PM
                  thresholds is provisioned."
    ::= { ocnPMThresholdEntry 2 }


ocnPMThresholdSlotIdx OBJECT-TYPE
    SYNTAX       INTEGER (1..20)
    MAX-ACCESS   not-accessible
    STATUS       current
    DESCRIPTION  "The slot number on which the OC-N facility targeted for PM
                  thresholds is provisioned."
    ::= { ocnPMThresholdEntry 3 }


ocnPMThresholdPortIdx OBJECT-TYPE
    SYNTAX       INTEGER (1..6)
    MAX-ACCESS   not-accessible
    STATUS       current
    DESCRIPTION  "The number of the port on the circuit pack on which the OC-N
                  facility targeted for PM thresholds is provisioned."
    ::= { ocnPMThresholdEntry 4 }


ocnPMThresholdIntervalTypeIdx OBJECT-TYPE
    SYNTAX       PMIntervalType
    MAX-ACCESS   not-accessible
    STATUS       current
    DESCRIPTION  "The type of PM bin according to interval length. Thresholds
                  are supported for the 15-minute and 1-day PM bins only."
    ::= { ocnPMThresholdEntry 5 }


ocnPMThresholdCVSValue OBJECT-TYPE
    SYNTAX       Unsigned32
    MAX-ACCESS   read-write
    STATUS       current
    DESCRIPTION  "The threshold for the count of coding violations at the
                  section layer."
    ::= { ocnPMThresholdEntry 6 }


ocnPMThresholdESSValue OBJECT-TYPE
    SYNTAX       Unsigned32
    MAX-ACCESS   read-write
    STATUS       current
    DESCRIPTION  "The threshold for the count of errored seconds at the section
                  layer."
    ::= { ocnPMThresholdEntry 7 }


ocnPMThresholdSESSValue OBJECT-TYPE
    SYNTAX       Unsigned32
    MAX-ACCESS   read-write
    STATUS       current
    DESCRIPTION  "The threshold fro the count of severely errored seconds at the
                  section layer."
    ::= { ocnPMThresholdEntry 8 }


ocnPMThresholdSEFSSValue OBJECT-TYPE
    SYNTAX       Unsigned32
    MAX-ACCESS   read-write
    STATUS       current
    DESCRIPTION  "The threshold for the count of severely errored framing
                  seconds at the section layer."
    ::= { ocnPMThresholdEntry 9 }


ocnPMThresholdCVLValue OBJECT-TYPE
    SYNTAX       Unsigned32
    MAX-ACCESS   read-write
    STATUS       current
    DESCRIPTION  "The threshold for the count of coding violations at the line
                  layer."
    ::= { ocnPMThresholdEntry 10 }


ocnPMThresholdESLValue OBJECT-TYPE
    SYNTAX       Unsigned32
    MAX-ACCESS   read-write
    STATUS       current
    DESCRIPTION  "The threshold for the count of errored seconds at the line
                  layer."
    ::= { ocnPMThresholdEntry 11 }


ocnPMThresholdSESLValue OBJECT-TYPE
    SYNTAX       Unsigned32
    MAX-ACCESS   read-write
    STATUS       current
    DESCRIPTION  "The threshold for the count of severely errored seconds at the
                  line layer."
    ::= { ocnPMThresholdEntry 12 }


ocnPMThresholdUASLValue OBJECT-TYPE
    SYNTAX       Unsigned32
    MAX-ACCESS   read-write
    STATUS       current
    DESCRIPTION  "The threshold for the count of unavailable seconds at the line
                  layer."
    ::= { ocnPMThresholdEntry 13 }


ocnPMThresholdOTUEBValue OBJECT-TYPE
    SYNTAX       Unsigned32
    MAX-ACCESS   read-write
    STATUS       current
    DESCRIPTION  "The threshold for the count of errored blocks at the OTU
                  digital wrapper layer."
    ::= { ocnPMThresholdEntry 14 }


ocnPMThresholdOTUBBEValue OBJECT-TYPE
    SYNTAX       Unsigned32
    MAX-ACCESS   read-write
    STATUS       current
    DESCRIPTION  "The threshold for the count of background block errors at the
                  OTU digital wrapper layer."
    ::= { ocnPMThresholdEntry 15 }


ocnPMThresholdOTUESValue OBJECT-TYPE
    SYNTAX       Unsigned32
    MAX-ACCESS   read-write
    STATUS       current
    DESCRIPTION  "The threshold for the count of errored seconds at the OTU
                  digital wrapper layer."
    ::= { ocnPMThresholdEntry 16 }


ocnPMThresholdOTUSESValue OBJECT-TYPE
    SYNTAX       Unsigned32
    MAX-ACCESS   read-write
    STATUS       current
    DESCRIPTION  "The threshold for the count of severely errored seconds at the
                  OTU digital wrapper layer."
    ::= { ocnPMThresholdEntry 17 }


ocnPMThresholdOTUOFSValue OBJECT-TYPE
    SYNTAX       Unsigned32
    MAX-ACCESS   read-write
    STATUS       current
    DESCRIPTION  "The threshold for the count of out-of-frame seconds at the OTU
                  digital wrapper layer."
    ::= { ocnPMThresholdEntry 18 }


ocnPMThresholdUNCRCDWValue OBJECT-TYPE
    SYNTAX       Unsigned32
    MAX-ACCESS   read-write
    STATUS       current
    DESCRIPTION  "The threshold for the count of uncorrectable codewords."
    ::= { ocnPMThresholdEntry 21 }

ocnPMThresholdUASSValue OBJECT-TYPE
    SYNTAX       Unsigned32
    MAX-ACCESS   read-write
    STATUS       current
    DESCRIPTION  "The threshold for the count of unavailable seconds at the
                  section layer."
    ::= { ocnPMThresholdEntry 22 }

ocnPMThresholdOTUUASValue OBJECT-TYPE
    SYNTAX       Unsigned32
    MAX-ACCESS   read-write
    STATUS       current
    DESCRIPTION  "The threshold for the count of unavailable seconds at the
                  OTU digital wrapper layer."
    ::= { ocnPMThresholdEntry 23 }

-----------------------------------------------------------------------
-- Objects used to retrieve current SONET STS-N
-- Performance Monitoring statistics
-- 
-- A listing of current SONET STS-N PM values is contained in the
-- stsnCrntPMTable of the BTI 7000 Series MIB. When retrieved, this 
-- table provides one row for each set of current SONET STS-N PM data.
-- 
-- The following table lists the objects in each entry of the 
-- stsnCrntPMTable.
-----------------------------------------------------------------------


stsnCrntPMTable OBJECT-TYPE
    SYNTAX       SEQUENCE OF StsnCrntPMEntry
    MAX-ACCESS   not-accessible
    STATUS       current
    DESCRIPTION  "A table of current performance monitoring statistics collected
                  for the SONET STS-N facilities on the NE."
    ::= { performance 11 }


stsnCrntPMEntry OBJECT-TYPE
    SYNTAX       StsnCrntPMEntry
    MAX-ACCESS   not-accessible
    STATUS       current
    DESCRIPTION  "The row entry object of the SONET STS-N current performance
                  monitoring table. Each row of this table contains a full set
                  of PM statistics and related data for a current measurement
                  interval for a given STS-N facility."
    INDEX        { stsnCrntPMTypeIdx,
                   stsnCrntPMShelfIdx,
                   stsnCrntPMSlotIdx,
                   stsnCrntPMPortIdx,
                   stsnCrntPMIdx,
                   stsnCrntPMIntervalTypeIdx }
    ::= { stsnCrntPMTable 1 }


StsnCrntPMEntry ::= SEQUENCE { stsnCrntPMTypeIdx          StsnType,
                               stsnCrntPMShelfIdx         INTEGER,
                               stsnCrntPMSlotIdx          INTEGER,
                               stsnCrntPMPortIdx          INTEGER,
                               stsnCrntPMIdx              INTEGER,
                               stsnCrntPMIntervalTypeIdx  PMIntervalType,
                               stsnCrntPMCVPValue         Unsigned32,
                               stsnCrntPMCVPTimeStamp     DateAndTime,
                               stsnCrntPMCVPValidity      PMValidity,
                               stsnCrntPMESPValue         Unsigned32,
                               stsnCrntPMESPTimeStamp     DateAndTime,
                               stsnCrntPMESPValidity      PMValidity,
                               stsnCrntPMSESPValue        Unsigned32,
                               stsnCrntPMSESPTimeStamp    DateAndTime,
                               stsnCrntPMSESPValidity     PMValidity,
                               stsnCrntPMUASPValue        Unsigned32,
                               stsnCrntPMUASPTimeStamp    DateAndTime,
                               stsnCrntPMUASPValidity     PMValidity,
                               stsnCrntPMFCPValue         Unsigned32,
                               stsnCrntPMFCPTimeStamp     DateAndTime,
                               stsnCrntPMFCPValidity      PMValidity,
                               stsnCrntPMCVPInitialize    InitializeCmd,
                               stsnCrntPMESPInitialize    InitializeCmd,
                               stsnCrntPMSESPInitialize   InitializeCmd,
                               stsnCrntPMUASPInitialize   InitializeCmd,
                               stsnCrntPMFCPInitialize    InitializeCmd }
                               


stsnCrntPMTypeIdx OBJECT-TYPE
    SYNTAX       StsnType
    MAX-ACCESS   not-accessible
    STATUS       current
    DESCRIPTION  "The type of STS-N facility targeted for PMs."
    ::= { stsnCrntPMEntry 1 }


stsnCrntPMShelfIdx OBJECT-TYPE
    SYNTAX       INTEGER (1|11|21|31)
    MAX-ACCESS   not-accessible
    STATUS       current
    DESCRIPTION  "The number of the shelf of the STS-N facility targeted for
                  PMs."
    ::= { stsnCrntPMEntry 2 }


stsnCrntPMSlotIdx OBJECT-TYPE
    SYNTAX       INTEGER (1..20)
    MAX-ACCESS   not-accessible
    STATUS       current
    DESCRIPTION  "The number of the slot of the STS-N facility targeted for
                  PMs."
    ::= { stsnCrntPMEntry 3 }


stsnCrntPMPortIdx OBJECT-TYPE
    SYNTAX       INTEGER (1..2)
    MAX-ACCESS   not-accessible
    STATUS       current
    DESCRIPTION  "The number of the port on the circuit pack of the STS-N
                  facility targeted for PMs."
    ::= { stsnCrntPMEntry 4 }


stsnCrntPMIdx OBJECT-TYPE
    SYNTAX       INTEGER (1..192)
    MAX-ACCESS   not-accessible
    STATUS       current
    DESCRIPTION  "The sts index number of the STS-N facility targeted for PMs."
    ::= { stsnCrntPMEntry 5 }


stsnCrntPMIntervalTypeIdx OBJECT-TYPE
    SYNTAX       PMIntervalType
    MAX-ACCESS   not-accessible
    STATUS       current
    DESCRIPTION  "The type of PM bin according to interval length."
    ::= { stsnCrntPMEntry 6 }


stsnCrntPMCVPValue OBJECT-TYPE
    SYNTAX       Unsigned32 
    MAX-ACCESS   read-write
    STATUS       current
    DESCRIPTION  "The count of coding violations at the path layer."
    ::= { stsnCrntPMEntry 7 }


stsnCrntPMCVPTimeStamp OBJECT-TYPE
    SYNTAX       DateAndTime
    MAX-ACCESS   read-only
    STATUS       current
    DESCRIPTION  "The date and time stamp of the path layer coding violations
                  value."
    ::= { stsnCrntPMEntry 8 }


stsnCrntPMCVPValidity OBJECT-TYPE
    SYNTAX       PMValidity
    MAX-ACCESS   read-only
    STATUS       current
    DESCRIPTION  "Indicates the validity of the provided path layer coding
                  violations value."
    ::= { stsnCrntPMEntry 9 }


stsnCrntPMESPValue OBJECT-TYPE
    SYNTAX       Unsigned32
    MAX-ACCESS   read-write
    STATUS       current
    DESCRIPTION  "The count of errored seconds at the path layer."
    ::= { stsnCrntPMEntry 10 }


stsnCrntPMESPTimeStamp OBJECT-TYPE
    SYNTAX       DateAndTime
    MAX-ACCESS   read-only
    STATUS       current
    DESCRIPTION  "The date and time stamp of the path layer errored seconds
                  value."
    ::= { stsnCrntPMEntry 11 }


stsnCrntPMESPValidity OBJECT-TYPE
    SYNTAX       PMValidity
    MAX-ACCESS   read-only
    STATUS       current
    DESCRIPTION  "Indicates the validity of the provided path layer errored
                  seconds value."
    ::= { stsnCrntPMEntry 12 }


stsnCrntPMSESPValue OBJECT-TYPE
    SYNTAX       Unsigned32
    MAX-ACCESS   read-write
    STATUS       current
    DESCRIPTION  "The count of severely errored seconds at the path layer."
    ::= { stsnCrntPMEntry 13 }


stsnCrntPMSESPTimeStamp OBJECT-TYPE
    SYNTAX       DateAndTime
    MAX-ACCESS   read-only
    STATUS       current
    DESCRIPTION  "The date and time stamp of the path layer severely errored
                  seconds value."
    ::= { stsnCrntPMEntry 14 }


stsnCrntPMSESPValidity OBJECT-TYPE
    SYNTAX       PMValidity
    MAX-ACCESS   read-only
    STATUS       current
    DESCRIPTION  "Indicates the validity of the provided path layer severely
                  errored seconds value."
    ::= { stsnCrntPMEntry 15 }


stsnCrntPMUASPValue OBJECT-TYPE
    SYNTAX       Unsigned32
    MAX-ACCESS   read-write
    STATUS       current
    DESCRIPTION  "The count of unavailable seconds at the path layer."
    ::= { stsnCrntPMEntry 16 }


stsnCrntPMUASPTimeStamp OBJECT-TYPE
    SYNTAX       DateAndTime
    MAX-ACCESS   read-only
    STATUS       current
    DESCRIPTION  "The date and time stamp of the path layer unavailable seconds
                  value."
    ::= { stsnCrntPMEntry 17 }


stsnCrntPMUASPValidity OBJECT-TYPE
    SYNTAX       PMValidity
    MAX-ACCESS   read-only
    STATUS       current
    DESCRIPTION  "Indicates the validity of the provided path layer unavailable
                  seconds value."
    ::= { stsnCrntPMEntry 18 }


stsnCrntPMFCPValue OBJECT-TYPE
    SYNTAX       Unsigned32
    MAX-ACCESS   read-write
    STATUS       current
    DESCRIPTION  "The failure count at the path layer."
    ::= { stsnCrntPMEntry 19 }


stsnCrntPMFCPTimeStamp OBJECT-TYPE
    SYNTAX       DateAndTime
    MAX-ACCESS   read-only
    STATUS       current
    DESCRIPTION  "The date and time stamp of the path layer failure count
                  value."
    ::= { stsnCrntPMEntry 20 }


stsnCrntPMFCPValidity OBJECT-TYPE
    SYNTAX       PMValidity
    MAX-ACCESS   read-only
    STATUS       current
    DESCRIPTION  "Indicates the validity of the provided path layer failure
                  count value."
    ::= { stsnCrntPMEntry 21 }


stsnCrntPMCVPInitialize OBJECT-TYPE
    SYNTAX       InitializeCmd
    MAX-ACCESS   read-write
    STATUS       current
    DESCRIPTION  "Used to initialize the value of the stsnCrntPMCVPValue object
                  to 0."
    ::= { stsnCrntPMEntry 22 }


stsnCrntPMESPInitialize OBJECT-TYPE
    SYNTAX       InitializeCmd
    MAX-ACCESS   read-write
    STATUS       current
    DESCRIPTION  "Used to initialize the value of the stsnCrntPMESPValue object
                  to 0."
    ::= { stsnCrntPMEntry 23 }


stsnCrntPMSESPInitialize OBJECT-TYPE
    SYNTAX       InitializeCmd
    MAX-ACCESS   read-write
    STATUS       current
    DESCRIPTION  "Used to initialize the value of the stsnCrntPMSESPValue object
                  to 0."
    ::= { stsnCrntPMEntry 24 }


stsnCrntPMUASPInitialize OBJECT-TYPE
    SYNTAX       InitializeCmd
    MAX-ACCESS   read-write
    STATUS       current
    DESCRIPTION  "Used to initialize the value of the stsnCrntPMUASPValue object
                  to 0."
    ::= { stsnCrntPMEntry 25 }


stsnCrntPMFCPInitialize OBJECT-TYPE
    SYNTAX       InitializeCmd
    MAX-ACCESS   read-write
    STATUS       current
    DESCRIPTION  "Used to initialize the value of the stsnCrntPMFCPValue object
                  to 0."
    ::= { stsnCrntPMEntry 26 }



-----------------------------------------------------------------------
-- Objects used to retrieve historical SONET STS-N
-- Performance Monitoring statistics
-- 
-- A listing of historical SONET STS-N PM values is contained in the
-- stsnHistPMTable of the BTI 7000 Series MIB. When retrieved, this 
-- table provides one row for each set of historical SONET STS-N PM 
-- data.
-- 
-- The following table lists the objects in each entry of the 
-- stsnHistPMTable.
-----------------------------------------------------------------------


stsnHistPMTable OBJECT-TYPE
    SYNTAX       SEQUENCE OF StsnHistPMEntry
    MAX-ACCESS   not-accessible
    STATUS       current
    DESCRIPTION  "A table of historical performance monitoring statistics
                  collected for the SONET STS-N facilities on the NE."
    ::= { performance 12 }


stsnHistPMEntry OBJECT-TYPE
    SYNTAX       StsnHistPMEntry
    MAX-ACCESS   not-accessible
    STATUS       current
    DESCRIPTION  "The row entry object of the SONET STS-N historical performance
                  monitoring table. Each row of this table contains a full set
                  of PM statistics and related data for a historical measurement
                  interval for a given STS-N facility."
    INDEX        { stsnHistPMTypeIdx,
                   stsnHistPMShelfIdx,
                   stsnHistPMSlotIdx,
                   stsnHistPMPortIdx,
                   stsnHistPMIdx,
                   stsnHistPMIntervalTypeIdx,
                   stsnHistPMIntervalIdx }
    ::= { stsnHistPMTable 1 }


StsnHistPMEntry ::= SEQUENCE { stsnHistPMTypeIdx          StsnType,
                               stsnHistPMShelfIdx         INTEGER,
                               stsnHistPMSlotIdx          INTEGER,
                               stsnHistPMPortIdx          INTEGER,
                               stsnHistPMIdx              INTEGER,
                               stsnHistPMIntervalTypeIdx  PMIntervalType,
                               stsnHistPMIntervalIdx      INTEGER,
                               stsnHistPMCVPValue         Unsigned32,
                               stsnHistPMCVPTimeStamp     DateAndTime,
                               stsnHistPMCVPValidity      PMValidity,
                               stsnHistPMESPValue         Unsigned32,
                               stsnHistPMESPTimeStamp     DateAndTime,
                               stsnHistPMESPValidity      PMValidity,
                               stsnHistPMSESPValue        Unsigned32,
                               stsnHistPMSESPTimeStamp    DateAndTime,
                               stsnHistPMSESPValidity     PMValidity,
                               stsnHistPMUASPValue        Unsigned32,
                               stsnHistPMUASPTimeStamp    DateAndTime,
                               stsnHistPMUASPValidity     PMValidity,
                               stsnHistPMFCPValue         Unsigned32,
                               stsnHistPMFCPTimeStamp     DateAndTime,
                               stsnHistPMFCPValidity      PMValidity,
                               stsnHistPMCVPInitialize    InitializeCmd,
                               stsnHistPMESPInitialize    InitializeCmd,
                               stsnHistPMSESPInitialize   InitializeCmd,
                               stsnHistPMUASPInitialize   InitializeCmd,
                               stsnHistPMFCPInitialize    InitializeCmd }


stsnHistPMTypeIdx OBJECT-TYPE
    SYNTAX       StsnType
    MAX-ACCESS   not-accessible
    STATUS       current
    DESCRIPTION  "The type of the STS-N facility targeted for PMs."
    ::= { stsnHistPMEntry 1 }


stsnHistPMShelfIdx OBJECT-TYPE
    SYNTAX       INTEGER (1|11|21|31)
    MAX-ACCESS   not-accessible
    STATUS       current
    DESCRIPTION  "The number of the shelf of the STS-N facility targeted for
                  PMs."
    ::= { stsnHistPMEntry 2 }


stsnHistPMSlotIdx OBJECT-TYPE
    SYNTAX       INTEGER (1..20)
    MAX-ACCESS   not-accessible
    STATUS       current
    DESCRIPTION  "The number of the slot of the STS-N facility targeted for
                  PMs."
    ::= { stsnHistPMEntry 3 }


stsnHistPMPortIdx OBJECT-TYPE
    SYNTAX       INTEGER (1..2)
    MAX-ACCESS   not-accessible
    STATUS       current
    DESCRIPTION  "The number of the port on the circuit pack of the STS-N
                  facility targeted for PMs."
    ::= { stsnHistPMEntry 4 }


stsnHistPMIdx OBJECT-TYPE
    SYNTAX       INTEGER (1..192)
    MAX-ACCESS   not-accessible
    STATUS       current
    DESCRIPTION  "The sts index number of the STS-N facility targeted for PMs."
    ::= { stsnHistPMEntry 5 }


stsnHistPMIntervalTypeIdx OBJECT-TYPE
    SYNTAX       PMIntervalType
    MAX-ACCESS   not-accessible
    STATUS       current
    DESCRIPTION  "The type of PM bin according to interval length."
    ::= { stsnHistPMEntry 6 }


stsnHistPMIntervalIdx OBJECT-TYPE
    SYNTAX       INTEGER (1..96)
    MAX-ACCESS   not-accessible
    STATUS       current
    DESCRIPTION  "The specific PM bin number. The range is 1 to 96 for the
                  15-minute historical bins. For the 1-day historical bin, the
                  value is 1."
    ::= { stsnHistPMEntry 7 }


stsnHistPMCVPValue OBJECT-TYPE
    SYNTAX       Unsigned32
    MAX-ACCESS   read-write
    STATUS       current
    DESCRIPTION  "The count of coding violations at the path layer."
    ::= { stsnHistPMEntry 8 }


stsnHistPMCVPTimeStamp OBJECT-TYPE
    SYNTAX       DateAndTime
    MAX-ACCESS   read-only
    STATUS       current
    DESCRIPTION  "The date and time stamp of the path layer coding violations
                  value."
    ::= { stsnHistPMEntry 9 }


stsnHistPMCVPValidity OBJECT-TYPE
    SYNTAX       PMValidity
    MAX-ACCESS   read-only
    STATUS       current
    DESCRIPTION  "Indicates the validity of the provided path layer coding
                  violations value."
    ::= { stsnHistPMEntry 10 }


stsnHistPMESPValue OBJECT-TYPE
    SYNTAX       Unsigned32
    MAX-ACCESS   read-write
    STATUS       current
    DESCRIPTION  "The count of errored seconds at the path layer."
    ::= { stsnHistPMEntry 11 }


stsnHistPMESPTimeStamp OBJECT-TYPE
    SYNTAX       DateAndTime
    MAX-ACCESS   read-only
    STATUS       current
    DESCRIPTION  "The date and time stamp of the path layer errored seconds
                  value."
    ::= { stsnHistPMEntry 12 }


stsnHistPMESPValidity OBJECT-TYPE
    SYNTAX       PMValidity
    MAX-ACCESS   read-only
    STATUS       current
    DESCRIPTION  "Indicates the validity of the provided path layer errored
                  seconds value."
    ::= { stsnHistPMEntry 13 }


stsnHistPMSESPValue OBJECT-TYPE
    SYNTAX       Unsigned32
    MAX-ACCESS   read-write
    STATUS       current
    DESCRIPTION  "The count of severely errored seconds at the path layer."
    ::= { stsnHistPMEntry 14 }


stsnHistPMSESPTimeStamp OBJECT-TYPE
    SYNTAX       DateAndTime
    MAX-ACCESS   read-only
    STATUS       current
    DESCRIPTION  "The date and time stamp of the path layer severely errored
                  seconds value."
    ::= { stsnHistPMEntry 15 }


stsnHistPMSESPValidity OBJECT-TYPE
    SYNTAX       PMValidity
    MAX-ACCESS   read-only
    STATUS       current
    DESCRIPTION  "Indicates the validity of the provided path layer severely
                  errored seconds value."
    ::= { stsnHistPMEntry 16 }


stsnHistPMUASPValue OBJECT-TYPE
    SYNTAX       Unsigned32
    MAX-ACCESS   read-write
    STATUS       current
    DESCRIPTION  "The count of unavailable seconds at the path layer."
    ::= { stsnHistPMEntry 17 }


stsnHistPMUASPTimeStamp OBJECT-TYPE
    SYNTAX       DateAndTime
    MAX-ACCESS   read-only
    STATUS       current
    DESCRIPTION  "The date and time stamp of the path layer unavailable seconds
                  value."
    ::= { stsnHistPMEntry 18 }


stsnHistPMUASPValidity OBJECT-TYPE
    SYNTAX       PMValidity
    MAX-ACCESS   read-only
    STATUS       current
    DESCRIPTION  "Indicates the validity of the provided path layer unavailable
                  seconds value."
    ::= { stsnHistPMEntry 19 }


stsnHistPMFCPValue OBJECT-TYPE
    SYNTAX       Unsigned32
    MAX-ACCESS   read-write
    STATUS       current
    DESCRIPTION  "The failure count at the path layer."
    ::= { stsnHistPMEntry 20 }


stsnHistPMFCPTimeStamp OBJECT-TYPE
    SYNTAX       DateAndTime
    MAX-ACCESS   read-only
    STATUS       current
    DESCRIPTION  "The date and time stamp of the path layer failure count."
    ::= { stsnHistPMEntry 21 }


stsnHistPMFCPValidity OBJECT-TYPE
    SYNTAX       PMValidity
    MAX-ACCESS   read-only
    STATUS       current
    DESCRIPTION  "Indicates the validity of the provided path layer failure
                  count."
    ::= { stsnHistPMEntry 22 }
    

stsnHistPMCVPInitialize OBJECT-TYPE
    SYNTAX       InitializeCmd
    MAX-ACCESS   read-write
    STATUS       current
    DESCRIPTION  "Used to initialize the value of the stsnHistPMCVPValue object
                  to 0."
    ::= { stsnHistPMEntry 23 }


stsnHistPMESPInitialize OBJECT-TYPE
    SYNTAX       InitializeCmd
    MAX-ACCESS   read-write
    STATUS       current
    DESCRIPTION  "Used to initialize the value of the stsnHistPMESPValue object
                  to 0."
    ::= { stsnHistPMEntry 24 }


stsnHistPMSESPInitialize OBJECT-TYPE
    SYNTAX       InitializeCmd
    MAX-ACCESS   read-write
    STATUS       current
    DESCRIPTION  "Used to initialize the value of the stsnHistPMSESPValue object
                  to 0."
    ::= { stsnHistPMEntry 25 }


stsnHistPMUASPInitialize OBJECT-TYPE
    SYNTAX       InitializeCmd
    MAX-ACCESS   read-write
    STATUS       current
    DESCRIPTION  "Used to initialize the value of the stsnHistPMUASPValue object
                  to 0."
    ::= { stsnHistPMEntry 26 }


stsnHistPMFCPInitialize OBJECT-TYPE
    SYNTAX       InitializeCmd
    MAX-ACCESS   read-write
    STATUS       current
    DESCRIPTION  "Used to initialize the value of the stsnHistPMFCPValue object
                  to 0."
    ::= { stsnHistPMEntry 27 }



-----------------------------------------------------------------------
-- Objects used to manage SONET STS-N Performance
-- Monitoring Threshold Levels
-- 
-- A listing of SONET STS-N PM threshold levels is contained in the
-- stsnPMThresholdByPortTable of the BTI-7000-MIB. When retrieved, this 
-- table provides one row for each set of current SONET STS-N 
-- PM threshold data.
-- 
-- The following table lists the objects in each entry of the 
-- stsnPMThresholdByPortTable.
-----------------------------------------------------------------------


stsnPMThresholdByPortTable OBJECT-TYPE
    SYNTAX       SEQUENCE OF StsnPMThresholdByPortEntry
    MAX-ACCESS   not-accessible
    STATUS       current
    DESCRIPTION  "A table of threshold levels for performance monitoring counter
                  values on SONET STS-N facilities, that are used in the
                  generation of threshold crossing alerts. The STS-N threshold
                  settings will be the same for all STS channels on a given OC-N
                  facility port."
    ::= { performance 13 }


stsnPMThresholdByPortEntry OBJECT-TYPE
    SYNTAX       StsnPMThresholdByPortEntry
    MAX-ACCESS   not-accessible
    STATUS       current
    DESCRIPTION  "The row entry object of the SONET STS-N performance monitoring
                  threshold by port table. Each row of this table contains a set
                  of PM thresholds for a given interval type that applies to all
                  the STS-N channels on an OC-N facility port."
    INDEX        { stsnPMThresholdByPortTypeIdx,
                   stsnPMThresholdByPortShelfIdx,
                   stsnPMThresholdByPortSlotIdx,
                   stsnPMThresholdByPortIdx,
                   stsnPMThresholdByPortIntervalTypeIdx }
    ::= { stsnPMThresholdByPortTable 1 }


StsnPMThresholdByPortEntry ::= SEQUENCE { stsnPMThresholdByPortTypeIdx          StsnType,
                                          stsnPMThresholdByPortShelfIdx         INTEGER,
                                          stsnPMThresholdByPortSlotIdx          INTEGER,
                                          stsnPMThresholdByPortIdx              INTEGER,
                                          stsnPMThresholdByPortIntervalTypeIdx  PMIntervalType,
                                          stsnPMThresholdByPortCVPValue         Unsigned32,
                                          stsnPMThresholdByPortESPValue         Unsigned32,
                                          stsnPMThresholdByPortSESPValue        Unsigned32,
                                          stsnPMThresholdByPortUASPValue        Unsigned32,
                                          stsnPMThresholdByPortFCPValue         Unsigned32 }
      

stsnPMThresholdByPortTypeIdx OBJECT-TYPE
    SYNTAX       StsnType
    MAX-ACCESS   not-accessible
    STATUS       current
    DESCRIPTION  "The type of the STS-N facilities targeted for PM thresholds."
    ::= { stsnPMThresholdByPortEntry 1 }


stsnPMThresholdByPortShelfIdx OBJECT-TYPE
    SYNTAX       INTEGER (1|11|21|31)
    MAX-ACCESS   not-accessible
    STATUS       current
    DESCRIPTION  "The shelf number of the STS-N facilities targeted for PM
                  thresholds."
    ::= { stsnPMThresholdByPortEntry 2 }


stsnPMThresholdByPortSlotIdx OBJECT-TYPE
    SYNTAX       INTEGER (1..20)
    MAX-ACCESS   not-accessible
    STATUS       current
    DESCRIPTION  "The slot number of the STS-N facilities targeted for PM
                  thresholds."
    ::= { stsnPMThresholdByPortEntry 3 }


stsnPMThresholdByPortIdx OBJECT-TYPE
    SYNTAX       INTEGER (1..2)
    MAX-ACCESS   not-accessible
    STATUS       current
    DESCRIPTION  "The number of the port on the circuit pack of the STS-N
                  facilities targeted for PM thresholds."
    ::= { stsnPMThresholdByPortEntry 4 }


stsnPMThresholdByPortIntervalTypeIdx OBJECT-TYPE
    SYNTAX       PMIntervalType
    MAX-ACCESS   not-accessible
    STATUS       current
    DESCRIPTION  "The type of PM bin according to interval length. Thresholds
                  are supported for the 15-minute and 1-day PM bins only."
    ::= { stsnPMThresholdByPortEntry 5 }


stsnPMThresholdByPortCVPValue OBJECT-TYPE
    SYNTAX       Unsigned32
    MAX-ACCESS   read-write
    STATUS       current
    DESCRIPTION  "The threshold for the count of coding violations at the path
                  layer."
    ::= { stsnPMThresholdByPortEntry 6 }


stsnPMThresholdByPortESPValue OBJECT-TYPE
    SYNTAX       Unsigned32
    MAX-ACCESS   read-write
    STATUS       current
    DESCRIPTION  "The threshold for the count of errored seconds at the path
                  layer."
    ::= { stsnPMThresholdByPortEntry 9 }


stsnPMThresholdByPortSESPValue OBJECT-TYPE
    SYNTAX       Unsigned32
    MAX-ACCESS   read-write
    STATUS       current
    DESCRIPTION  "The threshold for the count of severely errored seconds at the
                  path layer."
    ::= { stsnPMThresholdByPortEntry 10 }


stsnPMThresholdByPortUASPValue OBJECT-TYPE
    SYNTAX       Unsigned32
    MAX-ACCESS   read-write
    STATUS       current
    DESCRIPTION  "The threshold for the count of unavailable seconds at the path
                  layer."
    ::= { stsnPMThresholdByPortEntry 11 }


stsnPMThresholdByPortFCPValue OBJECT-TYPE
    SYNTAX       Unsigned32
    MAX-ACCESS   read-write
    STATUS       current
    DESCRIPTION  "The threshold for the failure count at the path layer."
    ::= { stsnPMThresholdByPortEntry 12 }



-----------------------------------------------------------------------
-- Objects used to retrieve current SDH STM-N
-- Performance Monitoring statistics
-- 
-- A listing of current SDH STM-N PM values is contained in the 
-- StmnCrntPMEntry of the BTI 7000 Series MIB. When retrieved, this 
-- table provides one row for each set of current SDH STM-N PM data.
-- 
-- The following table lists the objects in each entry of the 
-- StmnCrntPMEntry.
-----------------------------------------------------------------------


stmnCrntPMTable OBJECT-TYPE
    SYNTAX       SEQUENCE OF StmnCrntPMEntry
    MAX-ACCESS   not-accessible
    STATUS       current
    DESCRIPTION  "A table of current performance monitoring statistics collected
                  for the SDH STM-N facilities on the NE."
    ::= { performance 14 }


stmnCrntPMEntry OBJECT-TYPE
    SYNTAX       StmnCrntPMEntry
    MAX-ACCESS   not-accessible
    STATUS       current
    DESCRIPTION  "The row entry object of the SDH STM-N current performance
                  monitoring table. Each row of this table contains a full set
                  of PM statistics and related data for a current measurement
                  interval for a given STM-N facility."
    INDEX        { stmnCrntPMTypeIdx,
                   stmnCrntPMShelfIdx,
                   stmnCrntPMSlotIdx,
                   stmnCrntPMPortIdx,
                   stmnCrntPMIntervalTypeIdx }
    ::= { stmnCrntPMTable 1 }


StmnCrntPMEntry ::= SEQUENCE { stmnCrntPMTypeIdx                 StmnType,
                               stmnCrntPMShelfIdx                INTEGER,
                               stmnCrntPMSlotIdx                 INTEGER,
                               stmnCrntPMPortIdx                 INTEGER,
                               stmnCrntPMIntervalTypeIdx         PMIntervalType,
                               stmnCrntPMOPRValue                FixedX10,
                               stmnCrntPMOPRTimeStamp            DateAndTime,
                               stmnCrntPMOPRValidity             PMValidity,
                               stmnCrntPMOPTValue                FixedX10,
                               stmnCrntPMOPTTimeStamp            DateAndTime,
                               stmnCrntPMOPTValidity             PMValidity,
                               stmnCrntPMTempValue               INTEGER,
                               stmnCrntPMTempTimeStamp           DateAndTime,
                               stmnCrntPMTempValidity            PMValidity,
                               stmnCrntPMSupplyVoltageValue      FixedX10,
                               stmnCrntPMSupplyVoltageTimeStamp  DateAndTime,
                               stmnCrntPMSupplyVoltageValidity   PMValidity,
                               stmnCrntPMLBCValue                INTEGER,
                               stmnCrntPMLBCTimeStamp            DateAndTime,
                               stmnCrntPMLBCValidity             PMValidity,
                               stmnCrntPMRSEBValue               Unsigned32,
                               stmnCrntPMRSEBTimeStamp           DateAndTime,
                               stmnCrntPMRSEBValidity            PMValidity,
                               stmnCrntPMRSBBEValue              Unsigned32,
                               stmnCrntPMRSBBETimeStamp          DateAndTime,
                               stmnCrntPMRSBBEValidity           PMValidity,
                               stmnCrntPMRSESValue               Unsigned32,
                               stmnCrntPMRSESTimeStamp           DateAndTime,
                               stmnCrntPMRSESValidity            PMValidity,
                               stmnCrntPMRSSESValue              Unsigned32,
                               stmnCrntPMRSSESTimeStamp          DateAndTime,
                               stmnCrntPMRSSESValidity           PMValidity,
                               stmnCrntPMRSOFSValue              Unsigned32,
                               stmnCrntPMRSOFSTimeStamp          DateAndTime,
                               stmnCrntPMRSOFSValidity           PMValidity,
                               stmnCrntPMSupplyVoltage2Value     FixedX10,
                               stmnCrntPMSupplyVoltage2TimeStamp DateAndTime,
                               stmnCrntPMSupplyVoltage2Validity  PMValidity,
                               stmnCrntPMMSEBValue               Unsigned32,
                               stmnCrntPMMSEBTimeStamp           DateAndTime,
                               stmnCrntPMMSEBValidity            PMValidity,
                               stmnCrntPMMSBBEValue              Unsigned32,
                               stmnCrntPMMSBBETimeStamp          DateAndTime,
                               stmnCrntPMMSBBEValidity           PMValidity,
                               stmnCrntPMMSESValue               Unsigned32,
                               stmnCrntPMMSESTimeStamp           DateAndTime,
                               stmnCrntPMMSESValidity            PMValidity,
                               stmnCrntPMMSSESValue              Unsigned32,
                               stmnCrntPMMSSESTimeStamp          DateAndTime,
                               stmnCrntPMMSSESValidity           PMValidity,
                               stmnCrntPMMSUASValue              Unsigned32,
                               stmnCrntPMMSUASTimeStamp          DateAndTime,
                               stmnCrntPMMSUASValidity           PMValidity,
                               stmnCrntPMOTUEBValue              Unsigned32,
                               stmnCrntPMOTUEBTimeStamp          DateAndTime,
                               stmnCrntPMOTUEBValidity           PMValidity,
                               stmnCrntPMOTUBBEValue             Unsigned32,
                               stmnCrntPMOTUBBETimeStamp         DateAndTime,
                               stmnCrntPMOTUBBEValidity          PMValidity,
                               stmnCrntPMOTUESValue              Unsigned32,
                               stmnCrntPMOTUESTimeStamp          DateAndTime,
                               stmnCrntPMOTUESValidity           PMValidity,
                               stmnCrntPMOTUSESValue             Unsigned32,
                               stmnCrntPMOTUSESTimeStamp         DateAndTime,
                               stmnCrntPMOTUSESValidity          PMValidity,
                               stmnCrntPMOTUOFSValue             Unsigned32,
                               stmnCrntPMOTUOFSTimeStamp         DateAndTime,
                               stmnCrntPMOTUOFSValidity          PMValidity,
                               stmnCrntPMNBITCRValue             Unsigned32,
                               stmnCrntPMNBITCRTimeStamp         DateAndTime,
                               stmnCrntPMNBITCRValidity          PMValidity,
                               stmnCrntPMNBYTCRValue             Unsigned32,
                               stmnCrntPMNBYTCRTimeStamp         DateAndTime,
                               stmnCrntPMNBYTCRValidity          PMValidity,
                               stmnCrntPMUNCRCDWValue            Unsigned32,
                               stmnCrntPMUNCRCDWTimeStamp        DateAndTime,
                               stmnCrntPMUNCRCDWValidity         PMValidity,
                               stmnCrntPMRSEBInitialize          InitializeCmd,
                               stmnCrntPMRSBBEInitialize         InitializeCmd,
                               stmnCrntPMRSESInitialize          InitializeCmd,
                               stmnCrntPMRSSESInitialize         InitializeCmd,
                               stmnCrntPMRSOFSInitialize         InitializeCmd,
                               stmnCrntPMMSEBInitialize          InitializeCmd,
                               stmnCrntPMMSBBEInitialize         InitializeCmd,
                               stmnCrntPMMSESInitialize          InitializeCmd,
                               stmnCrntPMMSSESInitialize         InitializeCmd,
                               stmnCrntPMMSUASInitialize         InitializeCmd,
                               stmnCrntPMOTUEBInitialize         InitializeCmd,
                               stmnCrntPMOTUBBEInitialize        InitializeCmd,
                               stmnCrntPMOTUESInitialize         InitializeCmd,
                               stmnCrntPMOTUSESInitialize        InitializeCmd,
                               stmnCrntPMOTUOFSInitialize        InitializeCmd,
                               stmnCrntPMNBITCRInitialize        InitializeCmd,
                               stmnCrntPMNBYTCRInitialize        InitializeCmd,
                               stmnCrntPMUNCRCDWInitialize       InitializeCmd,
                               stmnCrntPMOTNBERValue             DisplayString,
                               stmnCrntPMOTNBERTimeStamp         DateAndTime,
                               stmnCrntPMOTNBERValidity          PMValidity,
                               stmnCrntPMOTNBERInitialize        InitializeCmd,
                               stmnCrntPMOTNAVGBERValue          DisplayString,
                               stmnCrntPMOTNAVGBERTimeStamp      DateAndTime,
                               stmnCrntPMOTNAVGBERValidity       PMValidity,
                               stmnCrntPMOTNAVGBERInitialize     InitializeCmd,
                               stmnCrntPMNBITCR64BitValue        Unsigned64,
                               stmnCrntPMNBITCR64BitTimeStamp    DateAndTime,
                               stmnCrntPMNBITCR64BitValidity     PMValidity,
                               stmnCrntPMNBITCR64BitInitialize   InitializeCmd,
                               stmnCrntPMNBYTCR64BitValue        Unsigned64,
                               stmnCrntPMNBYTCR64BitTimeStamp    DateAndTime,
                               stmnCrntPMNBYTCR64BitValidity     PMValidity,
                               stmnCrntPMNBYTCR64BitInitialize   InitializeCmd,
                               stmnCrntPMRSUASValue              Unsigned32,
                               stmnCrntPMRSUASTimeStamp          DateAndTime,
                               stmnCrntPMRSUASValidity           PMValidity,
                               stmnCrntPMRSUASInitialize         InitializeCmd,
                               stmnCrntPMOTUUASValue             Unsigned32,
                               stmnCrntPMOTUUASTimeStamp         DateAndTime,
                               stmnCrntPMOTUUASValidity          PMValidity,
                               stmnCrntPMOTUUASInitialize        InitializeCmd,
                               stmnCrntPMOPRMinValue             FixedX10,
                               stmnCrntPMOPRMinTimeStamp         DateAndTime,
                               stmnCrntPMOPRMinValidity          PMValidity,
                               stmnCrntPMOPRMinInitialize        InitializeCmd,
                               stmnCrntPMOPRMaxValue             FixedX10,
                               stmnCrntPMOPRMaxTimeStamp         DateAndTime,
                               stmnCrntPMOPRMaxValidity          PMValidity,
                               stmnCrntPMOPRMaxInitialize        InitializeCmd,
                               stmnCrntPMOPRAvgValue             FixedX10,
                               stmnCrntPMOPRAvgTimeStamp         DateAndTime,
                               stmnCrntPMOPRAvgValidity          PMValidity,
                               stmnCrntPMOPRAvgInitialize        InitializeCmd,
                               stmnCrntPMOPTMinValue             FixedX10,
                               stmnCrntPMOPTMinTimeStamp         DateAndTime,
                               stmnCrntPMOPTMinValidity          PMValidity,
                               stmnCrntPMOPTMinInitialize        InitializeCmd,
                               stmnCrntPMOPTMaxValue             FixedX10,
                               stmnCrntPMOPTMaxTimeStamp         DateAndTime,
                               stmnCrntPMOPTMaxValidity          PMValidity,
                               stmnCrntPMOPTMaxInitialize        InitializeCmd,
                               stmnCrntPMOPTAvgValue             FixedX10,
                               stmnCrntPMOPTAvgTimeStamp         DateAndTime,
                               stmnCrntPMOPTAvgValidity          PMValidity,
                               stmnCrntPMOPTAvgInitialize        InitializeCmd }


stmnCrntPMTypeIdx OBJECT-TYPE
    SYNTAX       StmnType
    MAX-ACCESS   not-accessible
    STATUS       current
    DESCRIPTION  "The type of STM-N facility targeted for PMs."
    ::= { stmnCrntPMEntry 1 }


stmnCrntPMShelfIdx OBJECT-TYPE
    SYNTAX       INTEGER (1|11|21|31)
    MAX-ACCESS   not-accessible
    STATUS       current
    DESCRIPTION  "The number of the shelf on which the STM-N facility targeted
                  for PMs is provisioned."
    ::= { stmnCrntPMEntry 2 }


stmnCrntPMSlotIdx OBJECT-TYPE
    SYNTAX       INTEGER (1..20)
    MAX-ACCESS   not-accessible
    STATUS       current
    DESCRIPTION  "The number of the slot within which the STM-N facility
                  targeted for PMs is provisioned."
    ::= { stmnCrntPMEntry 3 }


stmnCrntPMPortIdx OBJECT-TYPE
    SYNTAX       INTEGER (1..6)
    MAX-ACCESS   not-accessible
    STATUS       current
    DESCRIPTION  "The number of the port on the circuit pack on which the STM-N
                  facility targeted for PMs is provisioned."
    ::= { stmnCrntPMEntry 4 }


stmnCrntPMIntervalTypeIdx OBJECT-TYPE
    SYNTAX       PMIntervalType
    MAX-ACCESS   not-accessible
    STATUS       current
    DESCRIPTION  "The type of PM bin according to interval length."
    ::= { stmnCrntPMEntry 5 }


stmnCrntPMOPRValue OBJECT-TYPE
    SYNTAX       FixedX10
    UNITS        "dBm/10"
    MAX-ACCESS   read-only
    STATUS       current
    DESCRIPTION  "The optical power received on the input of the OC-N facility
                  port."
    ::= { stmnCrntPMEntry 6 }


stmnCrntPMOPRTimeStamp OBJECT-TYPE
    SYNTAX       DateAndTime
    MAX-ACCESS   read-only
    STATUS       current
    DESCRIPTION  "The date and time stamp of the optical power received value."
    ::= { stmnCrntPMEntry 7 }


stmnCrntPMOPRValidity OBJECT-TYPE
    SYNTAX       PMValidity
    MAX-ACCESS   read-only
    STATUS       current
    DESCRIPTION  "Indicates the validity of the provided optical power received
                  value."
    ::= { stmnCrntPMEntry 8 }


stmnCrntPMOPTValue OBJECT-TYPE
    SYNTAX       FixedX10
    UNITS        "dBm/10"
    MAX-ACCESS   read-only
    STATUS       current
    DESCRIPTION  "The optical power transmitted at the output of the STM-N
                  facility port."
    ::= { stmnCrntPMEntry 9 }


stmnCrntPMOPTTimeStamp OBJECT-TYPE
    SYNTAX       DateAndTime
    MAX-ACCESS   read-only
    STATUS       current
    DESCRIPTION  "The date and time stamp of the optical power transmitted
                  value."
    ::= { stmnCrntPMEntry 10 }


stmnCrntPMOPTValidity OBJECT-TYPE
    SYNTAX       PMValidity
    MAX-ACCESS   read-only
    STATUS       current
    DESCRIPTION  "Indicates the validity of the provided optical power
                  transmitted value."
    ::= { stmnCrntPMEntry 11 }


stmnCrntPMTempValue OBJECT-TYPE
    SYNTAX       INTEGER (-32768..32767)
    UNITS        "degrees Celsius"
    MAX-ACCESS   read-only
    STATUS       current
    DESCRIPTION  "The temperature measured on the STM-N facility port."
    ::= { stmnCrntPMEntry 12 }


stmnCrntPMTempTimeStamp OBJECT-TYPE
    SYNTAX       DateAndTime
    MAX-ACCESS   read-only
    STATUS       current
    DESCRIPTION  "The date and time stamp of the temperature value."
    ::= { stmnCrntPMEntry 13 }


stmnCrntPMTempValidity OBJECT-TYPE
    SYNTAX       PMValidity
    MAX-ACCESS   read-only
    STATUS       current
    DESCRIPTION  "Indicates the validity of the provided temperature value."
    ::= { stmnCrntPMEntry 14 }


stmnCrntPMSupplyVoltageValue OBJECT-TYPE
    SYNTAX       FixedX10
    UNITS        "mVolts/10"
    MAX-ACCESS   read-only
    STATUS       current
    DESCRIPTION  "The supply voltage measured on the STM-N facility port."
    ::= { stmnCrntPMEntry 15 }


stmnCrntPMSupplyVoltageTimeStamp OBJECT-TYPE
    SYNTAX       DateAndTime
    MAX-ACCESS   read-only
    STATUS       current
    DESCRIPTION  "The date and time stamp of the supply voltage value."
    ::= { stmnCrntPMEntry 16 }


stmnCrntPMSupplyVoltageValidity OBJECT-TYPE
    SYNTAX       PMValidity
    MAX-ACCESS   read-only
    STATUS       current
    DESCRIPTION  "Indicates the validity of the provided supply voltage value."
    ::= { stmnCrntPMEntry 17 }


stmnCrntPMLBCValue OBJECT-TYPE
    SYNTAX       INTEGER (-32768..32767)
    UNITS        "mAmp"
    MAX-ACCESS   read-only
    STATUS       current
    DESCRIPTION  "The laser bias current measured on the STM-N facility port."
    ::= { stmnCrntPMEntry 18 }


stmnCrntPMLBCTimeStamp OBJECT-TYPE
    SYNTAX       DateAndTime
    MAX-ACCESS   read-only
    STATUS       current
    DESCRIPTION  "The date and time stamp of the laser bias current value."
    ::= { stmnCrntPMEntry 19 }


stmnCrntPMLBCValidity OBJECT-TYPE
    SYNTAX       PMValidity
    MAX-ACCESS   read-only
    STATUS       current
    DESCRIPTION  "Indicates the validity of the provided laser bias current
                  value."
    ::= { stmnCrntPMEntry 20 }


stmnCrntPMRSEBValue OBJECT-TYPE
    SYNTAX       Unsigned32
    MAX-ACCESS   read-write
    STATUS       current
    DESCRIPTION  "The count of regenerator section errored blocks."
    ::= { stmnCrntPMEntry 21 }


stmnCrntPMRSEBTimeStamp OBJECT-TYPE
    SYNTAX       DateAndTime
    MAX-ACCESS   read-only
    STATUS       current
    DESCRIPTION  "The date and time stamp of the regenerator section errored
                  blocks value."
    ::= { stmnCrntPMEntry 22 }


stmnCrntPMRSEBValidity OBJECT-TYPE
    SYNTAX       PMValidity
    MAX-ACCESS   read-only
    STATUS       current
    DESCRIPTION  "Indicates the validity of the provided regenerator section
                  errored blocks value."
    ::= { stmnCrntPMEntry 23 }


stmnCrntPMRSBBEValue OBJECT-TYPE
    SYNTAX       Unsigned32
    MAX-ACCESS   read-write
    STATUS       current
    DESCRIPTION  "The count of regenerator section background block errors."
    ::= { stmnCrntPMEntry 24 }


stmnCrntPMRSBBETimeStamp OBJECT-TYPE
    SYNTAX       DateAndTime
    MAX-ACCESS   read-only
    STATUS       current
    DESCRIPTION  "The date and time stamp of the regenerator section background
                  block errors value."
    ::= { stmnCrntPMEntry 25 }


stmnCrntPMRSBBEValidity OBJECT-TYPE
    SYNTAX       PMValidity
    MAX-ACCESS   read-only
    STATUS       current
    DESCRIPTION  "Indicates the validity of the provided regenerator section
                  background block errors value."
    ::= { stmnCrntPMEntry 26 }


stmnCrntPMRSESValue OBJECT-TYPE
    SYNTAX       Unsigned32
    MAX-ACCESS   read-write
    STATUS       current
    DESCRIPTION  "The count of regenerator section errored seconds."
    ::= { stmnCrntPMEntry 27 }


stmnCrntPMRSESTimeStamp OBJECT-TYPE
    SYNTAX       DateAndTime
    MAX-ACCESS   read-only
    STATUS       current
    DESCRIPTION  "The date and time stamp of the regenerator section errored
                  seconds value."
    ::= { stmnCrntPMEntry 28 }


stmnCrntPMRSESValidity OBJECT-TYPE
    SYNTAX       PMValidity
    MAX-ACCESS   read-only
    STATUS       current
    DESCRIPTION  "Indicates the validity of the provided regenerator section
                  errored seconds value."
    ::= { stmnCrntPMEntry 29 }


stmnCrntPMRSSESValue OBJECT-TYPE
    SYNTAX       Unsigned32
    MAX-ACCESS   read-write
    STATUS       current
    DESCRIPTION  "The count of regenerator section severely errored seconds."
    ::= { stmnCrntPMEntry 30 }


stmnCrntPMRSSESTimeStamp OBJECT-TYPE
    SYNTAX       DateAndTime
    MAX-ACCESS   read-only
    STATUS       current
    DESCRIPTION  "The date and time stamp of the regenerator section severely
                  errored seconds value."
    ::= { stmnCrntPMEntry 31 }


stmnCrntPMRSSESValidity OBJECT-TYPE
    SYNTAX       PMValidity
    MAX-ACCESS   read-only
    STATUS       current
    DESCRIPTION  "Indicates the validity of the provided regenerator section
                  severely errored seconds value."
    ::= { stmnCrntPMEntry 32 }


stmnCrntPMRSOFSValue OBJECT-TYPE
    SYNTAX       Unsigned32
    MAX-ACCESS   read-write
    STATUS       current
    DESCRIPTION  "The count of regenerator section out-of-frame seconds."
    ::= { stmnCrntPMEntry 33 }


stmnCrntPMRSOFSTimeStamp OBJECT-TYPE
    SYNTAX       DateAndTime
    MAX-ACCESS   read-only
    STATUS       current
    DESCRIPTION  "The date and time stamp of the regenerator section
                  out-of-frame seconds value."
    ::= { stmnCrntPMEntry 34 }


stmnCrntPMRSOFSValidity OBJECT-TYPE
    SYNTAX       PMValidity
    MAX-ACCESS   read-only
    STATUS       current
    DESCRIPTION  "Indicates the validity of the provided regenerator section
                  out-of-frame seconds value."
    ::= { stmnCrntPMEntry 35 }


stmnCrntPMSupplyVoltage2Value OBJECT-TYPE
    SYNTAX       FixedX10
    UNITS        "mVolts/10"
    MAX-ACCESS   read-only
    STATUS       current
    DESCRIPTION  "The value of the second supply voltage source measured on the
                  STM-N facility port transceiver."
    ::= { stmnCrntPMEntry 36 }


stmnCrntPMSupplyVoltage2TimeStamp OBJECT-TYPE
    SYNTAX       DateAndTime
    MAX-ACCESS   read-only
    STATUS       current
    DESCRIPTION  "The date and time stamp of the second supply voltage value."
    ::= { stmnCrntPMEntry 37 }


stmnCrntPMSupplyVoltage2Validity OBJECT-TYPE
    SYNTAX       PMValidity
    MAX-ACCESS   read-only
    STATUS       current
    DESCRIPTION  "Indicates the validity of the provided second supply voltage
                  value."
    ::= { stmnCrntPMEntry 38 }


stmnCrntPMMSEBValue OBJECT-TYPE
    SYNTAX       Unsigned32
    MAX-ACCESS   read-write
    STATUS       current
    DESCRIPTION  "The count of multiplex section errored blocks."
    ::= { stmnCrntPMEntry 39 }


stmnCrntPMMSEBTimeStamp OBJECT-TYPE
    SYNTAX       DateAndTime
    MAX-ACCESS   read-only
    STATUS       current
    DESCRIPTION  "The date and time stamp of the multiplex section errored
                  blocks value."
    ::= { stmnCrntPMEntry 40 }


stmnCrntPMMSEBValidity OBJECT-TYPE
    SYNTAX       PMValidity
    MAX-ACCESS   read-only
    STATUS       current
    DESCRIPTION  "Indicates the validity of the provided multiplex section
                  errored blocks value."
    ::= { stmnCrntPMEntry 41 }


stmnCrntPMMSBBEValue OBJECT-TYPE
    SYNTAX       Unsigned32
    MAX-ACCESS   read-write
    STATUS       current
    DESCRIPTION  "The count of multiplex section background block errors."
    ::= { stmnCrntPMEntry 42 }


stmnCrntPMMSBBETimeStamp OBJECT-TYPE
    SYNTAX       DateAndTime
    MAX-ACCESS   read-only
    STATUS       current
    DESCRIPTION  "The date and time stamp of the multiplex section background
                  block errors value."
    ::= { stmnCrntPMEntry 43 }


stmnCrntPMMSBBEValidity OBJECT-TYPE
    SYNTAX       PMValidity
    MAX-ACCESS   read-only
    STATUS       current
    DESCRIPTION  "Indicates the validity of the provided multiplex section
                  background block errors value."
    ::= { stmnCrntPMEntry 44 }


stmnCrntPMMSESValue OBJECT-TYPE
    SYNTAX       Unsigned32
    MAX-ACCESS   read-write
    STATUS       current
    DESCRIPTION  "The count of multiplex section errored seconds."
    ::= { stmnCrntPMEntry 45 }


stmnCrntPMMSESTimeStamp OBJECT-TYPE
    SYNTAX       DateAndTime
    MAX-ACCESS   read-only
    STATUS       current
    DESCRIPTION  "The date and time stamp of the multiplex section errored
                  seconds value."
    ::= { stmnCrntPMEntry 46 }


stmnCrntPMMSESValidity OBJECT-TYPE
    SYNTAX       PMValidity
    MAX-ACCESS   read-only
    STATUS       current
    DESCRIPTION  "Indicates the validity of the provided multiplex section
                  errored seconds value."
    ::= { stmnCrntPMEntry 47 }


stmnCrntPMMSSESValue OBJECT-TYPE
    SYNTAX       Unsigned32
    MAX-ACCESS   read-write
    STATUS       current
    DESCRIPTION  "The count of multiplex section severely errored seconds."
    ::= { stmnCrntPMEntry 48 }


stmnCrntPMMSSESTimeStamp OBJECT-TYPE
    SYNTAX       DateAndTime
    MAX-ACCESS   read-only
    STATUS       current
    DESCRIPTION  "The date and time stamp of the multiplex section severely
                  errored seconds value."
    ::= { stmnCrntPMEntry 49 }


stmnCrntPMMSSESValidity OBJECT-TYPE
    SYNTAX       PMValidity
    MAX-ACCESS   read-only
    STATUS       current
    DESCRIPTION  "Indicates the validity of the provided multiplex section
                  severely errored seconds value."
    ::= { stmnCrntPMEntry 50 }


stmnCrntPMMSUASValue OBJECT-TYPE
    SYNTAX       Unsigned32
    MAX-ACCESS   read-write
    STATUS       current
    DESCRIPTION  "The count of multiplex section unavailable seconds."
    ::= { stmnCrntPMEntry 51 }


stmnCrntPMMSUASTimeStamp OBJECT-TYPE
    SYNTAX       DateAndTime
    MAX-ACCESS   read-only
    STATUS       current
    DESCRIPTION  "The date and time stamp of the multiplex section unavailable
                  seconds value."
    ::= { stmnCrntPMEntry 52 }


stmnCrntPMMSUASValidity OBJECT-TYPE
    SYNTAX       PMValidity
    MAX-ACCESS   read-only
    STATUS       current
    DESCRIPTION  "Indicates the validity of the provided multiplex section
                  unavailable seconds value."
    ::= { stmnCrntPMEntry 53 }


stmnCrntPMOTUEBValue OBJECT-TYPE
    SYNTAX       Unsigned32 
    MAX-ACCESS   read-write
    STATUS       current
    DESCRIPTION  "The count of OTU digital wrapper layer errored blocks."
    ::= { stmnCrntPMEntry 54 }


stmnCrntPMOTUEBTimeStamp OBJECT-TYPE
    SYNTAX       DateAndTime
    MAX-ACCESS   read-only
    STATUS       current
    DESCRIPTION  "The date and time stamp of the OTU digital wrapper layer
                  errored blocks value."
    ::= { stmnCrntPMEntry 55 }


stmnCrntPMOTUEBValidity OBJECT-TYPE
    SYNTAX       PMValidity
    MAX-ACCESS   read-only
    STATUS       current
    DESCRIPTION  "Indicates the validity of the provided OTU digital wrapper
                  layer errored blocks value."
    ::= { stmnCrntPMEntry 56 }


stmnCrntPMOTUBBEValue OBJECT-TYPE
    SYNTAX       Unsigned32 
    MAX-ACCESS   read-write
    STATUS       current
    DESCRIPTION  "The count of OTU digital wrapper layer background block
                  errors."
    ::= { stmnCrntPMEntry 57 }


stmnCrntPMOTUBBETimeStamp OBJECT-TYPE
    SYNTAX       DateAndTime
    MAX-ACCESS   read-only
    STATUS       current
    DESCRIPTION  "The date and time stamp of the OTU digital wrapper layer
                  background block errors value."
    ::= { stmnCrntPMEntry 58 }


stmnCrntPMOTUBBEValidity OBJECT-TYPE
    SYNTAX       PMValidity
    MAX-ACCESS   read-only
    STATUS       current
    DESCRIPTION  "Indicates the validity of the provided OTU digital wrapper
                  layer background block errors value."
    ::= { stmnCrntPMEntry 59 }


stmnCrntPMOTUESValue OBJECT-TYPE
    SYNTAX       Unsigned32
    MAX-ACCESS   read-write
    STATUS       current
    DESCRIPTION  "The count of OTU digital wrapper layer errored seconds."
    ::= { stmnCrntPMEntry 60 }


stmnCrntPMOTUESTimeStamp OBJECT-TYPE
    SYNTAX       DateAndTime
    MAX-ACCESS   read-only
    STATUS       current
    DESCRIPTION  "The date and time stamp of the OTU digital wrapper layer
                  errored seconds value."
    ::= { stmnCrntPMEntry 61 }


stmnCrntPMOTUESValidity OBJECT-TYPE
    SYNTAX       PMValidity
    MAX-ACCESS   read-only
    STATUS       current
    DESCRIPTION  "Indicates the validity of the provided OTU digital wrapper
                  layer errored seconds value."
    ::= { stmnCrntPMEntry 62 }


stmnCrntPMOTUSESValue OBJECT-TYPE
    SYNTAX       Unsigned32
    MAX-ACCESS   read-write
    STATUS       current
    DESCRIPTION  "The count of OTU digital wrapper layer severely errored
                  seconds."
    ::= { stmnCrntPMEntry 63 }


stmnCrntPMOTUSESTimeStamp OBJECT-TYPE
    SYNTAX       DateAndTime
    MAX-ACCESS   read-only
    STATUS       current
    DESCRIPTION  "The date and time stamp of the OTU digital wrapper layer
                  severely errored seconds value."
    ::= { stmnCrntPMEntry 64 }


stmnCrntPMOTUSESValidity OBJECT-TYPE
    SYNTAX       PMValidity
    MAX-ACCESS   read-only
    STATUS       current
    DESCRIPTION  "Indicates the validity of the provided OTU digital wrapper
                  layer severely errored seconds value."
    ::= { stmnCrntPMEntry 65 }


stmnCrntPMOTUOFSValue OBJECT-TYPE
    SYNTAX       Unsigned32
    MAX-ACCESS   read-write
    STATUS       current
    DESCRIPTION  "The count of OTU digital wrapper layer out-of-frame seconds."
    ::= { stmnCrntPMEntry 66 }


stmnCrntPMOTUOFSTimeStamp OBJECT-TYPE
    SYNTAX       DateAndTime
    MAX-ACCESS   read-only
    STATUS       current
    DESCRIPTION  "The date and time stamp of the OTU digital wrapper layer
                  out-of-frame seconds value."
    ::= { stmnCrntPMEntry 67 }


stmnCrntPMOTUOFSValidity OBJECT-TYPE
    SYNTAX       PMValidity
    MAX-ACCESS   read-only
    STATUS       current
    DESCRIPTION  "Indicates the validity of the provided OTU digital wrapper
                  layer severely errored framing seconds value."
    ::= { stmnCrntPMEntry 68 }


stmnCrntPMNBITCRValue OBJECT-TYPE
    SYNTAX       Unsigned32
    MAX-ACCESS   read-write
    STATUS       current
    DESCRIPTION  "The count of the number of bits corrected. This object applies
                  only to STM-64 line port provisioned for OTN line mapping."
    ::= { stmnCrntPMEntry 69 }


stmnCrntPMNBITCRTimeStamp OBJECT-TYPE
    SYNTAX       DateAndTime
    MAX-ACCESS   read-only
    STATUS       current
    DESCRIPTION  "The date and time stamp of the number of bits corrected
                  value."
    ::= { stmnCrntPMEntry 70 }


stmnCrntPMNBITCRValidity OBJECT-TYPE
    SYNTAX       PMValidity
    MAX-ACCESS   read-only
    STATUS       current
    DESCRIPTION  "Indicates the validity of the provided number of bits
                  corrected value."
    ::= { stmnCrntPMEntry 71 }


stmnCrntPMNBYTCRValue OBJECT-TYPE
    SYNTAX       Unsigned32
    MAX-ACCESS   read-write
    STATUS       current
    DESCRIPTION  "The count of the number of bytes corrected. This object
                  applies only to STM-64 line port provisioned for OTN line
                  mapping."
    ::= { stmnCrntPMEntry 72 }


stmnCrntPMNBYTCRTimeStamp OBJECT-TYPE
    SYNTAX       DateAndTime
    MAX-ACCESS   read-only
    STATUS       current
    DESCRIPTION  "The date and time stamp of the number of bytes corrected
                  value."
    ::= { stmnCrntPMEntry 73 }


stmnCrntPMNBYTCRValidity OBJECT-TYPE
    SYNTAX       PMValidity
    MAX-ACCESS   read-only
    STATUS       current
    DESCRIPTION  "Indicates the validity of the provided number of bytes
                  corrected value."
    ::= { stmnCrntPMEntry 74 }


stmnCrntPMUNCRCDWValue OBJECT-TYPE
    SYNTAX       Unsigned32
    MAX-ACCESS   read-write
    STATUS       current
    DESCRIPTION  "The count of uncorrectable codewords. This object applies only
                  to STM-64 line port provisioned for OTN line mapping."
    ::= { stmnCrntPMEntry 75 }


stmnCrntPMUNCRCDWTimeStamp OBJECT-TYPE
    SYNTAX       DateAndTime
    MAX-ACCESS   read-only
    STATUS       current
    DESCRIPTION  "The date and time stamp of the uncorrectable codewords value."
    ::= { stmnCrntPMEntry 76 }


stmnCrntPMUNCRCDWValidity OBJECT-TYPE
    SYNTAX       PMValidity
    MAX-ACCESS   read-only
    STATUS       current
    DESCRIPTION  "Indicates the validity of the provided uncorrectable codewords
                  value."
    ::= { stmnCrntPMEntry 77 }


stmnCrntPMRSEBInitialize OBJECT-TYPE
    SYNTAX       InitializeCmd
    MAX-ACCESS   read-write
    STATUS       current
    DESCRIPTION  "Used to initialize the value of the stmnCrntPMRSEBValue object
                  to 0."
    ::= { stmnCrntPMEntry 78 }


stmnCrntPMRSBBEInitialize OBJECT-TYPE
    SYNTAX       InitializeCmd
    MAX-ACCESS   read-write
    STATUS       current
    DESCRIPTION  "Used to initialize the value of the stmnCrntPMRSBBEValue
                  object to 0."
    ::= { stmnCrntPMEntry 79 }


stmnCrntPMRSESInitialize OBJECT-TYPE
    SYNTAX       InitializeCmd
    MAX-ACCESS   read-write
    STATUS       current
    DESCRIPTION  "Used to initialize the value of the stmnCrntPMRSESValue object
                  to 0."
    ::= { stmnCrntPMEntry 80 }


stmnCrntPMRSSESInitialize OBJECT-TYPE
    SYNTAX       InitializeCmd
    MAX-ACCESS   read-write
    STATUS       current
    DESCRIPTION  "Used to initialize the value of the stmnCrntPMRSSESValue
                  object to 0."
    ::= { stmnCrntPMEntry 81 }


stmnCrntPMRSOFSInitialize OBJECT-TYPE
    SYNTAX       InitializeCmd
    MAX-ACCESS   read-write
    STATUS       current
    DESCRIPTION  "Used to initialize the value of the stmnCrntPMRSOFSValue
                  object to 0."
    ::= { stmnCrntPMEntry 82 }


stmnCrntPMMSEBInitialize OBJECT-TYPE
    SYNTAX       InitializeCmd
    MAX-ACCESS   read-write
    STATUS       current
    DESCRIPTION  "Used to initialize the value of the stmnCrntPMMSEBValue object
                  to 0."
    ::= { stmnCrntPMEntry 83 }


stmnCrntPMMSBBEInitialize OBJECT-TYPE
    SYNTAX       InitializeCmd
    MAX-ACCESS   read-write
    STATUS       current
    DESCRIPTION  "Used to initialize the value of the stmnCrntPMMSBBEValue
                  object to 0."
    ::= { stmnCrntPMEntry 84 }


stmnCrntPMMSESInitialize OBJECT-TYPE
    SYNTAX       InitializeCmd
    MAX-ACCESS   read-write
    STATUS       current
    DESCRIPTION  "Used to initialize the value of the stmnCrntPMMSESValue object
                  to 0."
    ::= { stmnCrntPMEntry 85 }


stmnCrntPMMSSESInitialize OBJECT-TYPE
    SYNTAX       InitializeCmd
    MAX-ACCESS   read-write
    STATUS       current
    DESCRIPTION  "Used to initialize the value of the stmnCrntPMMSSESValue
                  object to 0."
    ::= { stmnCrntPMEntry 86 }


stmnCrntPMMSUASInitialize OBJECT-TYPE
    SYNTAX       InitializeCmd
    MAX-ACCESS   read-write
    STATUS       current
    DESCRIPTION  "Used to initialize the value of the stmnCrntPMMSUASValue
                  object to 0."
    ::= { stmnCrntPMEntry 87 }


stmnCrntPMOTUEBInitialize OBJECT-TYPE
    SYNTAX       InitializeCmd
    MAX-ACCESS   read-write
    STATUS       current
    DESCRIPTION  "Used to initialize the value of the stmnCrntPMOTUEBValue
                  object to 0."
    ::= { stmnCrntPMEntry 88 }


stmnCrntPMOTUBBEInitialize OBJECT-TYPE
    SYNTAX       InitializeCmd
    MAX-ACCESS   read-write
    STATUS       current
    DESCRIPTION  "Used to initialize the value of the stmnCrntPMOTUBBEValue
                  object to 0."
    ::= { stmnCrntPMEntry 89 }


stmnCrntPMOTUESInitialize OBJECT-TYPE
    SYNTAX       InitializeCmd
    MAX-ACCESS   read-write
    STATUS       current
    DESCRIPTION  "Used to initialize the value of the stmnCrntPMOTUESValue
                  object to 0."
    ::= { stmnCrntPMEntry 90 }


stmnCrntPMOTUSESInitialize OBJECT-TYPE
    SYNTAX       InitializeCmd
    MAX-ACCESS   read-write
    STATUS       current
    DESCRIPTION  "Used to initialize the value of the stmnCrntPMOTUSESValue
                  object to 0."
    ::= { stmnCrntPMEntry 91 }


stmnCrntPMOTUOFSInitialize OBJECT-TYPE
    SYNTAX       InitializeCmd
    MAX-ACCESS   read-write
    STATUS       current
    DESCRIPTION  "Used to initialize the value of the stmnCrntPMOTUOFSValue
                  object to 0."
    ::= { stmnCrntPMEntry 92 }


stmnCrntPMNBITCRInitialize OBJECT-TYPE
    SYNTAX       InitializeCmd
    MAX-ACCESS   read-write
    STATUS       current
    DESCRIPTION  "Used to initialize the value of the stmnCrntPMNBITCRValue
                  object to 0."
    ::= { stmnCrntPMEntry 93 }


stmnCrntPMNBYTCRInitialize OBJECT-TYPE
    SYNTAX       InitializeCmd
    MAX-ACCESS   read-write
    STATUS       current
    DESCRIPTION  "Used to initialize the value of the stmnCrntPMNBYTCRValue
                  object to 0."
    ::= { stmnCrntPMEntry 94 }


stmnCrntPMUNCRCDWInitialize OBJECT-TYPE
    SYNTAX       InitializeCmd
    MAX-ACCESS   read-write
    STATUS       current
    DESCRIPTION  "Used to initialize the value of the stmnCrntPMUNCRCDWValue
                  object to 0."
    ::= { stmnCrntPMEntry 95 }


stmnCrntPMOTNBERValue OBJECT-TYPE
    SYNTAX       DisplayString
    MAX-ACCESS   read-only
    STATUS       current
    DESCRIPTION  "The instantaneous BER of STM-64 line port provisioned for OTN line mapping."
    ::= { stmnCrntPMEntry 96 }


stmnCrntPMOTNBERTimeStamp OBJECT-TYPE
    SYNTAX       DateAndTime
    MAX-ACCESS   read-only
    STATUS       current
    DESCRIPTION  "The date and time stamp of the instantaneous BER."
    ::= { stmnCrntPMEntry 97 }


stmnCrntPMOTNBERValidity OBJECT-TYPE
    SYNTAX       PMValidity
    MAX-ACCESS   read-only
    STATUS       current
    DESCRIPTION  "Indicates the validity of the provided instantaneous BER."
    ::= { stmnCrntPMEntry 98 }

stmnCrntPMOTNBERInitialize OBJECT-TYPE
    SYNTAX       InitializeCmd
    MAX-ACCESS   read-write
    STATUS       current
    DESCRIPTION  "Used to initialize the value of the stmnCrntPMOTNBERValue
                  object to 0."
    ::= { stmnCrntPMEntry 99 }


stmnCrntPMOTNAVGBERValue OBJECT-TYPE
    SYNTAX       DisplayString
    MAX-ACCESS   read-only
    STATUS       current
    DESCRIPTION  "The interval/average BER of STM-64 line port provisioned for OTN line mapping."
    ::= { stmnCrntPMEntry 100 }


stmnCrntPMOTNAVGBERTimeStamp OBJECT-TYPE
    SYNTAX       DateAndTime
    MAX-ACCESS   read-only
    STATUS       current
    DESCRIPTION  "The date and time stamp of the interval/average BER."
    ::= { stmnCrntPMEntry 101 }


stmnCrntPMOTNAVGBERValidity OBJECT-TYPE
    SYNTAX       PMValidity
    MAX-ACCESS   read-only
    STATUS       current
    DESCRIPTION  "Indicates the validity of the provided interval/average BER."
    ::= { stmnCrntPMEntry 102 }


stmnCrntPMOTNAVGBERInitialize OBJECT-TYPE
    SYNTAX       InitializeCmd
    MAX-ACCESS   read-write
    STATUS       current
    DESCRIPTION  "Used to initialize the value of the stmnCrntPMOTNAVGBERValue
                  object to 0."
    ::= { stmnCrntPMEntry 103 }


stmnCrntPMNBITCR64BitValue OBJECT-TYPE
    SYNTAX       Unsigned64
    MAX-ACCESS   read-only
    STATUS       current
    DESCRIPTION  "The 64-bit count of the number of bits corrected. This object applies
                  only to STM-64 line port provisioned for OTN line mapping."
    ::= { stmnCrntPMEntry 104 }


stmnCrntPMNBITCR64BitTimeStamp OBJECT-TYPE
    SYNTAX       DateAndTime
    MAX-ACCESS   read-only
    STATUS       current
    DESCRIPTION  "The date and time stamp of the 64-bit number of bits corrected
                  value."
    ::= { stmnCrntPMEntry 105 }


stmnCrntPMNBITCR64BitValidity OBJECT-TYPE
    SYNTAX       PMValidity
    MAX-ACCESS   read-only
    STATUS       current
    DESCRIPTION  "Indicates the validity of the provided 64-bit number of bits
                  corrected value."
    ::= { stmnCrntPMEntry 106 }


stmnCrntPMNBITCR64BitInitialize OBJECT-TYPE
    SYNTAX       InitializeCmd
    MAX-ACCESS   read-write
    STATUS       current
    DESCRIPTION  "Used to initialize the value of the stmnCrntPMNBITCR64BitValue
                  object to 0."
    ::= { stmnCrntPMEntry 107 }


stmnCrntPMNBYTCR64BitValue OBJECT-TYPE
    SYNTAX       Unsigned64
    MAX-ACCESS   read-only
    STATUS       current
    DESCRIPTION  "The 64-bit count of the number of bytes corrected. This object
                  applies only to STM-64 line port provisioned for OTN line
                  mapping."
    ::= { stmnCrntPMEntry 108 }


stmnCrntPMNBYTCR64BitTimeStamp OBJECT-TYPE
    SYNTAX       DateAndTime
    MAX-ACCESS   read-only
    STATUS       current
    DESCRIPTION  "The date and time stamp of the 64-bit number of bytes corrected
                  value."
    ::= { stmnCrntPMEntry 109 }


stmnCrntPMNBYTCR64BitValidity OBJECT-TYPE
    SYNTAX       PMValidity
    MAX-ACCESS   read-only
    STATUS       current
    DESCRIPTION  "Indicates the validity of the provided 64-bit number of bytes
                  corrected value."
    ::= { stmnCrntPMEntry 110 }


stmnCrntPMNBYTCR64BitInitialize OBJECT-TYPE
    SYNTAX       InitializeCmd
    MAX-ACCESS   read-write
    STATUS       current
    DESCRIPTION  "Used to initialize the value of the stmnCrntPMNBYTCR64BitValue
                  object to 0."
    ::= { stmnCrntPMEntry 111 }


stmnCrntPMRSUASValue OBJECT-TYPE
    SYNTAX       Unsigned32
    MAX-ACCESS   read-write
    STATUS       current
    DESCRIPTION  "The count of regenerator section unavailable seconds.
                  This object applies only to STM-64 line port provisioned
                  for OTN line mapping."
    ::= { stmnCrntPMEntry 112 }

stmnCrntPMRSUASTimeStamp OBJECT-TYPE
    SYNTAX       DateAndTime
    MAX-ACCESS   read-only
    STATUS       current
    DESCRIPTION  "The date and time stamp of the regenerator section
                  unavailable seconds value."
    ::= { stmnCrntPMEntry 113 }


stmnCrntPMRSUASValidity OBJECT-TYPE
    SYNTAX       PMValidity
    MAX-ACCESS   read-only
    STATUS       current
    DESCRIPTION  "Indicates the validity of the provided regenerator section
                  unavailable seconds value."
    ::= { stmnCrntPMEntry 114 }


stmnCrntPMRSUASInitialize OBJECT-TYPE
    SYNTAX       InitializeCmd
    MAX-ACCESS   read-write
    STATUS       current
    DESCRIPTION  "Used to initialize the value of the stmnCrntPMRSUASValue
                  object to 0."
    ::= { stmnCrntPMEntry 115 }

stmnCrntPMOTUUASValue OBJECT-TYPE
    SYNTAX       Unsigned32
    MAX-ACCESS   read-write
    STATUS       current
    DESCRIPTION  "The count of OTU digital wrapper layer unavailable seconds."
    ::= { stmnCrntPMEntry 116 }


stmnCrntPMOTUUASTimeStamp OBJECT-TYPE
    SYNTAX       DateAndTime
    MAX-ACCESS   read-only
    STATUS       current
    DESCRIPTION  "The date and time stamp of the OTU digital wrapper layer
                  unavailable seconds value."
    ::= { stmnCrntPMEntry 117 }


stmnCrntPMOTUUASValidity OBJECT-TYPE
    SYNTAX       PMValidity
    MAX-ACCESS   read-only
    STATUS       current
    DESCRIPTION  "Indicates the validity of the provided OTU digital wrapper
                  layer unavailable seconds value."
    ::= { stmnCrntPMEntry 118 }

stmnCrntPMOTUUASInitialize OBJECT-TYPE
    SYNTAX       InitializeCmd
    MAX-ACCESS   read-write
    STATUS       current
    DESCRIPTION  "Used to initialize the value of the stmnCrntPMOTUUASValue
                  object to 0."
    ::= { stmnCrntPMEntry 119 }

stmnCrntPMOPRMinValue OBJECT-TYPE
    SYNTAX       FixedX10
    UNITS        "dBm/10"
    MAX-ACCESS   read-only
    STATUS       current
    DESCRIPTION  "The minimum optical power received on the input of the transceiver."
    ::= { stmnCrntPMEntry 120 }


stmnCrntPMOPRMinTimeStamp OBJECT-TYPE
    SYNTAX       DateAndTime
    MAX-ACCESS   read-only
    STATUS       current
    DESCRIPTION  "The date and time stamp of the minimum optical power received value."
    ::= { stmnCrntPMEntry 121 }


stmnCrntPMOPRMinValidity OBJECT-TYPE
    SYNTAX       PMValidity
    MAX-ACCESS   read-only
    STATUS       current
    DESCRIPTION  "Indicates the validity of the provided minimum optical power received
                  value."
    ::= { stmnCrntPMEntry 122 }

stmnCrntPMOPRMinInitialize OBJECT-TYPE
    SYNTAX       InitializeCmd
    MAX-ACCESS   read-write
    STATUS       current
    DESCRIPTION  "Used to initialize the value of the stmnCrntPMOPRMinValue
                  object to 0."
    ::= { stmnCrntPMEntry 123 }

stmnCrntPMOPRMaxValue OBJECT-TYPE
    SYNTAX       FixedX10
    UNITS        "dBm/10"
    MAX-ACCESS   read-only
    STATUS       current
    DESCRIPTION  "The maximum optical power received on the input of the transceiver."
    ::= { stmnCrntPMEntry 124 }


stmnCrntPMOPRMaxTimeStamp OBJECT-TYPE
    SYNTAX       DateAndTime
    MAX-ACCESS   read-only
    STATUS       current
    DESCRIPTION  "The date and time stamp of the maximum optical power received value."
    ::= { stmnCrntPMEntry 125 }


stmnCrntPMOPRMaxValidity OBJECT-TYPE
    SYNTAX       PMValidity
    MAX-ACCESS   read-only
    STATUS       current
    DESCRIPTION  "Indicates the validity of the provided maximum optical power received
                  value."
    ::= { stmnCrntPMEntry 126 }

stmnCrntPMOPRMaxInitialize OBJECT-TYPE
    SYNTAX       InitializeCmd
    MAX-ACCESS   read-write
    STATUS       current
    DESCRIPTION  "Used to initialize the value of the stmnCrntPMOPRMaxValue
                  object to 0."
    ::= { stmnCrntPMEntry 127 }

stmnCrntPMOPRAvgValue OBJECT-TYPE
    SYNTAX       FixedX10
    UNITS        "dBm/10"
    MAX-ACCESS   read-only
    STATUS       current
    DESCRIPTION  "The average optical power received on the input of the transceiver."
    ::= { stmnCrntPMEntry 128 }


stmnCrntPMOPRAvgTimeStamp OBJECT-TYPE
    SYNTAX       DateAndTime
    MAX-ACCESS   read-only
    STATUS       current
    DESCRIPTION  "The date and time stamp of the average optical power received value."
    ::= { stmnCrntPMEntry 129 }


stmnCrntPMOPRAvgValidity OBJECT-TYPE
    SYNTAX       PMValidity
    MAX-ACCESS   read-only
    STATUS       current
    DESCRIPTION  "Indicates the validity of the provided average optical power received
                  value."
    ::= { stmnCrntPMEntry 130 }

stmnCrntPMOPRAvgInitialize OBJECT-TYPE
    SYNTAX       InitializeCmd
    MAX-ACCESS   read-write
    STATUS       current
    DESCRIPTION  "Used to initialize the value of the stmnCrntPMOPRAvgValue
                  object to 0."
    ::= { stmnCrntPMEntry 131 }

stmnCrntPMOPTMinValue OBJECT-TYPE
    SYNTAX       FixedX10
    UNITS        "dBm/10"
    MAX-ACCESS   read-only
    STATUS       current
    DESCRIPTION  "The minimum optical power transmitted at the output of the
                  transceiver."
    ::= { stmnCrntPMEntry 132 }

stmnCrntPMOPTMinTimeStamp OBJECT-TYPE
    SYNTAX       DateAndTime
    MAX-ACCESS   read-only
    STATUS       current
    DESCRIPTION  "The date and time stamp of the minimum optical power transmitted
                  value."
    ::= { stmnCrntPMEntry 133 }


stmnCrntPMOPTMinValidity OBJECT-TYPE
    SYNTAX       PMValidity
    MAX-ACCESS   read-only
    STATUS       current
    DESCRIPTION  "Indicates the validity of the provided minimum optical power
                  transmitted value."
    ::= { stmnCrntPMEntry 134 }

stmnCrntPMOPTMinInitialize OBJECT-TYPE
    SYNTAX       InitializeCmd
    MAX-ACCESS   read-write
    STATUS       current
    DESCRIPTION  "Used to initialize the value of the stmnCrntPMOPTMinValue
                  object to 0."
    ::= { stmnCrntPMEntry 135 }

stmnCrntPMOPTMaxValue OBJECT-TYPE
    SYNTAX       FixedX10
    UNITS        "dBm/10"
    MAX-ACCESS   read-only
    STATUS       current
    DESCRIPTION  "The maximum optical power transmitted at the output of the
                  transceiver."
    ::= { stmnCrntPMEntry 136 }


stmnCrntPMOPTMaxTimeStamp OBJECT-TYPE
    SYNTAX       DateAndTime
    MAX-ACCESS   read-only
    STATUS       current
    DESCRIPTION  "The date and time stamp of the maximum optical power transmitted
                  value."
    ::= { stmnCrntPMEntry 137 }


stmnCrntPMOPTMaxValidity OBJECT-TYPE
    SYNTAX       PMValidity
    MAX-ACCESS   read-only
    STATUS       current
    DESCRIPTION  "Indicates the validity of the provided maximum optical power
                  transmitted value."
    ::= { stmnCrntPMEntry 138 }

stmnCrntPMOPTMaxInitialize OBJECT-TYPE
    SYNTAX       InitializeCmd
    MAX-ACCESS   read-write
    STATUS       current
    DESCRIPTION  "Used to initialize the value of the stmnCrntPMOPTMaxValue
                  object to 0."
    ::= { stmnCrntPMEntry 139 }

stmnCrntPMOPTAvgValue OBJECT-TYPE
    SYNTAX       FixedX10
    UNITS        "dBm/10"
    MAX-ACCESS   read-only
    STATUS       current
    DESCRIPTION  "The average optical power transmitted at the output of the
                  transceiver."
    ::= { stmnCrntPMEntry 140 }


stmnCrntPMOPTAvgTimeStamp OBJECT-TYPE
    SYNTAX       DateAndTime
    MAX-ACCESS   read-only
    STATUS       current
    DESCRIPTION  "The date and time stamp of the average optical power transmitted
                  value."
    ::= { stmnCrntPMEntry 141 }

stmnCrntPMOPTAvgValidity OBJECT-TYPE
    SYNTAX       PMValidity
    MAX-ACCESS   read-only
    STATUS       current
    DESCRIPTION  "Indicates the validity of the provided average optical power
                  transmitted value."
    ::= { stmnCrntPMEntry 142 }

stmnCrntPMOPTAvgInitialize OBJECT-TYPE
    SYNTAX       InitializeCmd
    MAX-ACCESS   read-write
    STATUS       current
    DESCRIPTION  "Used to initialize the value of the stmnCrntPMOPTAvgValue
                  object to 0."
    ::= { stmnCrntPMEntry 143 }

-----------------------------------------------------------------------
-- Objects used to retrieve historical SDH STM-N
-- Performance Monitoring statistics
-- 
-- A listing of historical SDH STM-N PM values is contained in the
-- StmnHistPMEntry of the BTI 7000 Series MIB. When retrieved, this 
-- table provides one row for set of each historical SDH STM-N PM data.
-- 
-- The following table lists the objects in each entry of the 
-- StmnHistPMEntry.
-----------------------------------------------------------------------


stmnHistPMTable OBJECT-TYPE
    SYNTAX       SEQUENCE OF StmnHistPMEntry
    MAX-ACCESS   not-accessible
    STATUS       current
    DESCRIPTION  "A table of historical performance monitoring statistics
                  collected for the SDH STM-N facilities on the NE."
    ::= { performance 15 }


stmnHistPMEntry OBJECT-TYPE
    SYNTAX       StmnHistPMEntry
    MAX-ACCESS   not-accessible
    STATUS       current
    DESCRIPTION  "The row entry object of the SDH STM-N historical performance
                  monitoring table. Each row of this table contains a full set
                  of PM statistics and related data for a historical measurement
                  interval for a given STM-N facility."
    INDEX        { stmnHistPMTypeIdx,
                   stmnHistPMShelfIdx,
                   stmnHistPMSlotIdx,
                   stmnHistPMPortIdx,
                   stmnHistPMIntervalTypeIdx,
                   stmnHistPMIntervalIdx }
    ::= { stmnHistPMTable 1 }


StmnHistPMEntry ::= SEQUENCE { stmnHistPMTypeIdx                 StmnType,
                               stmnHistPMShelfIdx                INTEGER,
                               stmnHistPMSlotIdx                 INTEGER,
                               stmnHistPMPortIdx                 INTEGER,
                               stmnHistPMIntervalTypeIdx         PMIntervalType,
                               stmnHistPMIntervalIdx             INTEGER,
                               stmnHistPMOPRValue                FixedX10,
                               stmnHistPMOPRTimeStamp            DateAndTime,
                               stmnHistPMOPRValidity             PMValidity,
                               stmnHistPMOPTValue                FixedX10,
                               stmnHistPMOPTTimeStamp            DateAndTime,
                               stmnHistPMOPTValidity             PMValidity,
                               stmnHistPMTempValue               INTEGER,
                               stmnHistPMTempTimeStamp           DateAndTime,
                               stmnHistPMTempValidity            PMValidity,
                               stmnHistPMSupplyVoltageValue      FixedX10,
                               stmnHistPMSupplyVoltageTimeStamp  DateAndTime,
                               stmnHistPMSupplyVoltageValidity   PMValidity,
                               stmnHistPMLBCValue                INTEGER,
                               stmnHistPMLBCTimeStamp            DateAndTime,
                               stmnHistPMLBCValidity             PMValidity,
                               stmnHistPMRSEBValue               Unsigned32,
                               stmnHistPMRSEBTimeStamp           DateAndTime,
                               stmnHistPMRSEBValidity            PMValidity,
                               stmnHistPMRSBBEValue              Unsigned32,
                               stmnHistPMRSBBETimeStamp          DateAndTime,
                               stmnHistPMRSBBEValidity           PMValidity,
                               stmnHistPMRSESValue               Unsigned32,
                               stmnHistPMRSESTimeStamp           DateAndTime,
                               stmnHistPMRSESValidity            PMValidity,
                               stmnHistPMRSSESValue              Unsigned32,
                               stmnHistPMRSSESTimeStamp          DateAndTime,
                               stmnHistPMRSSESValidity           PMValidity,
                               stmnHistPMRSOFSValue              Unsigned32,
                               stmnHistPMRSOFSTimeStamp          DateAndTime,
                               stmnHistPMRSOFSValidity           PMValidity,
                               stmnHistPMSupplyVoltage2Value     FixedX10,
                               stmnHistPMSupplyVoltage2TimeStamp DateAndTime,
                               stmnHistPMSupplyVoltage2Validity  PMValidity,
                               stmnHistPMMSEBValue               Unsigned32,
                               stmnHistPMMSEBTimeStamp           DateAndTime,
                               stmnHistPMMSEBValidity            PMValidity,
                               stmnHistPMMSBBEValue              Unsigned32,
                               stmnHistPMMSBBETimeStamp          DateAndTime,
                               stmnHistPMMSBBEValidity           PMValidity,
                               stmnHistPMMSESValue               Unsigned32,
                               stmnHistPMMSESTimeStamp           DateAndTime,
                               stmnHistPMMSESValidity            PMValidity,
                               stmnHistPMMSSESValue              Unsigned32,
                               stmnHistPMMSSESTimeStamp          DateAndTime,
                               stmnHistPMMSSESValidity           PMValidity,
                               stmnHistPMMSUASValue              Unsigned32,
                               stmnHistPMMSUASTimeStamp          DateAndTime,
                               stmnHistPMMSUASValidity           PMValidity,
                               stmnHistPMOTUEBValue              Unsigned32,
                               stmnHistPMOTUEBTimeStamp          DateAndTime,
                               stmnHistPMOTUEBValidity           PMValidity,
                               stmnHistPMOTUBBEValue             Unsigned32,
                               stmnHistPMOTUBBETimeStamp         DateAndTime,
                               stmnHistPMOTUBBEValidity          PMValidity,
                               stmnHistPMOTUESValue              Unsigned32,
                               stmnHistPMOTUESTimeStamp          DateAndTime,
                               stmnHistPMOTUESValidity           PMValidity,
                               stmnHistPMOTUSESValue             Unsigned32,
                               stmnHistPMOTUSESTimeStamp         DateAndTime,
                               stmnHistPMOTUSESValidity          PMValidity,
                               stmnHistPMOTUOFSValue             Unsigned32,
                               stmnHistPMOTUOFSTimeStamp         DateAndTime,
                               stmnHistPMOTUOFSValidity          PMValidity,
                               stmnHistPMNBITCRValue             Unsigned32,
                               stmnHistPMNBITCRTimeStamp         DateAndTime,
                               stmnHistPMNBITCRValidity          PMValidity,
                               stmnHistPMNBYTCRValue             Unsigned32,
                               stmnHistPMNBYTCRTimeStamp         DateAndTime,
                               stmnHistPMNBYTCRValidity          PMValidity,
                               stmnHistPMUNCRCDWValue            Unsigned32,
                               stmnHistPMUNCRCDWTimeStamp        DateAndTime,
                               stmnHistPMUNCRCDWValidity         PMValidity,
                               stmnHistPMRSEBInitialize          InitializeCmd,
                               stmnHistPMRSBBEInitialize         InitializeCmd,
                               stmnHistPMRSESInitialize          InitializeCmd,
                               stmnHistPMRSSESInitialize         InitializeCmd,
                               stmnHistPMRSOFSInitialize         InitializeCmd,
                               stmnHistPMMSEBInitialize          InitializeCmd,
                               stmnHistPMMSBBEInitialize         InitializeCmd,
                               stmnHistPMMSESInitialize          InitializeCmd,
                               stmnHistPMMSSESInitialize         InitializeCmd,
                               stmnHistPMMSUASInitialize         InitializeCmd,
                               stmnHistPMOTUEBInitialize         InitializeCmd,
                               stmnHistPMOTUBBEInitialize        InitializeCmd,
                               stmnHistPMOTUESInitialize         InitializeCmd,
                               stmnHistPMOTUSESInitialize        InitializeCmd,
                               stmnHistPMOTUOFSInitialize        InitializeCmd,
                               stmnHistPMNBITCRInitialize        InitializeCmd,
                               stmnHistPMNBYTCRInitialize        InitializeCmd,
                               stmnHistPMUNCRCDWInitialize       InitializeCmd,
                               stmnHistPMOTNBERValue             DisplayString,
                               stmnHistPMOTNBERTimeStamp         DateAndTime,
                               stmnHistPMOTNBERValidity          PMValidity,
                               stmnHistPMOTNBERInitialize        InitializeCmd,
                               stmnHistPMOTNAVGBERValue          DisplayString,
                               stmnHistPMOTNAVGBERTimeStamp      DateAndTime,
                               stmnHistPMOTNAVGBERValidity       PMValidity,
                               stmnHistPMOTNAVGBERInitialize     InitializeCmd,
                               stmnHistPMNBITCR64BitValue        Unsigned64,
                               stmnHistPMNBITCR64BitTimeStamp    DateAndTime,
                               stmnHistPMNBITCR64BitValidity     PMValidity,
                               stmnHistPMNBITCR64BitInitialize   InitializeCmd,
                               stmnHistPMNBYTCR64BitValue        Unsigned64,
                               stmnHistPMNBYTCR64BitTimeStamp    DateAndTime,
                               stmnHistPMNBYTCR64BitValidity     PMValidity,
                               stmnHistPMNBYTCR64BitInitialize   InitializeCmd,
                               stmnHistPMRSUASValue              Unsigned32,
                               stmnHistPMRSUASTimeStamp          DateAndTime,
                               stmnHistPMRSUASValidity           PMValidity,
                               stmnHistPMRSUASInitialize         InitializeCmd,
                               stmnHistPMOTUUASValue             Unsigned32,
                               stmnHistPMOTUUASTimeStamp         DateAndTime,
                               stmnHistPMOTUUASValidity          PMValidity,
                               stmnHistPMOTUUASInitialize        InitializeCmd,
                               stmnHistPMOPRMinValue             FixedX10,
                               stmnHistPMOPRMinTimeStamp         DateAndTime,
                               stmnHistPMOPRMinValidity          PMValidity,
                               stmnHistPMOPRMinInitialize        InitializeCmd,
                               stmnHistPMOPRMaxValue             FixedX10,
                               stmnHistPMOPRMaxTimeStamp         DateAndTime,
                               stmnHistPMOPRMaxValidity          PMValidity,
                               stmnHistPMOPRMaxInitialize        InitializeCmd,
                               stmnHistPMOPRAvgValue             FixedX10,
                               stmnHistPMOPRAvgTimeStamp         DateAndTime,
                               stmnHistPMOPRAvgValidity          PMValidity,
                               stmnHistPMOPRAvgInitialize        InitializeCmd,
                               stmnHistPMOPTMinValue             FixedX10,
                               stmnHistPMOPTMinTimeStamp         DateAndTime,
                               stmnHistPMOPTMinValidity          PMValidity,
                               stmnHistPMOPTMinInitialize        InitializeCmd,
                               stmnHistPMOPTMaxValue             FixedX10,
                               stmnHistPMOPTMaxTimeStamp         DateAndTime,
                               stmnHistPMOPTMaxValidity          PMValidity,
                               stmnHistPMOPTMaxInitialize        InitializeCmd,
                               stmnHistPMOPTAvgValue             FixedX10,
                               stmnHistPMOPTAvgTimeStamp         DateAndTime,
                               stmnHistPMOPTAvgValidity          PMValidity,
                               stmnHistPMOPTAvgInitialize        InitializeCmd }


stmnHistPMTypeIdx OBJECT-TYPE
    SYNTAX       StmnType
    MAX-ACCESS   not-accessible
    STATUS       current
    DESCRIPTION  "The type of the STM-N facility targeted for PMs."
    ::= { stmnHistPMEntry 1 }


stmnHistPMShelfIdx OBJECT-TYPE
    SYNTAX       INTEGER (1|11|21|31)
    MAX-ACCESS   not-accessible
    STATUS       current
    DESCRIPTION  "The number of the shelf on which the STM-N facility targeted
                  for PMs is provisioned."
    ::= { stmnHistPMEntry 2 }


stmnHistPMSlotIdx OBJECT-TYPE
    SYNTAX       INTEGER (1..20)
    MAX-ACCESS   not-accessible
    STATUS       current
    DESCRIPTION  "The number of the slot within which the STM-N facility
                  targeted for PMs is provisioned."
    ::= { stmnHistPMEntry 3 }


stmnHistPMPortIdx OBJECT-TYPE
    SYNTAX       INTEGER (1..6)
    MAX-ACCESS   not-accessible
    STATUS       current
    DESCRIPTION  "The number of the port on the circuit pack on which the STM-N
                  facility targeted for PMs is provisioned."
    ::= { stmnHistPMEntry 4 }


stmnHistPMIntervalTypeIdx OBJECT-TYPE
    SYNTAX       PMIntervalType
    MAX-ACCESS   not-accessible
    STATUS       current
    DESCRIPTION  "The type of PM bin according to interval length."
    ::= { stmnHistPMEntry 5 }


stmnHistPMIntervalIdx OBJECT-TYPE
    SYNTAX       INTEGER (1..96)
    MAX-ACCESS   not-accessible
    STATUS       current
    DESCRIPTION  "The specific PM bin number. The range is 1 to 96 for the
                  15-minute historical bins. For the 1-day historical bin, the
                  value is 1."
    ::= { stmnHistPMEntry 6 }


stmnHistPMOPRValue OBJECT-TYPE
    SYNTAX       FixedX10
    UNITS        "dBm/10"
    MAX-ACCESS   read-only
    STATUS       current
    DESCRIPTION  "The optical power received on the input of the STM-N
                  facility."
    ::= { stmnHistPMEntry 7 }


stmnHistPMOPRTimeStamp OBJECT-TYPE
    SYNTAX       DateAndTime
    MAX-ACCESS   read-only
    STATUS       current
    DESCRIPTION  "The date and time stamp of the optical power received value."
    ::= { stmnHistPMEntry 8 }


stmnHistPMOPRValidity OBJECT-TYPE
    SYNTAX       PMValidity
    MAX-ACCESS   read-only
    STATUS       current
    DESCRIPTION  "Indicates the validity of the provided optical power received
                  value."
    ::= { stmnHistPMEntry 9 }


stmnHistPMOPTValue OBJECT-TYPE
    SYNTAX       FixedX10
    UNITS        "dBm/10"
    MAX-ACCESS   read-only
    STATUS       current
    DESCRIPTION  "The optical power transmitted at the output of the STM-N
                  facility."
    ::= { stmnHistPMEntry 10 }


stmnHistPMOPTTimeStamp OBJECT-TYPE
    SYNTAX       DateAndTime
    MAX-ACCESS   read-only
    STATUS       current
    DESCRIPTION  "The date and time stamp of the optical power transmitted
                  value."
    ::= { stmnHistPMEntry 11 }


stmnHistPMOPTValidity OBJECT-TYPE
    SYNTAX       PMValidity
    MAX-ACCESS   read-only
    STATUS       current
    DESCRIPTION  "Indicates the validity of the provided optical power
                  transmitted value."
    ::= { stmnHistPMEntry 12 }


stmnHistPMTempValue OBJECT-TYPE
    SYNTAX       INTEGER (-32768..32767)
    UNITS        "degrees Celsius"
    MAX-ACCESS   read-only
    STATUS       current
    DESCRIPTION  "The temperature measured on the STM-N facility port."
    ::= { stmnHistPMEntry 13 }


stmnHistPMTempTimeStamp OBJECT-TYPE
    SYNTAX       DateAndTime
    MAX-ACCESS   read-only
    STATUS       current
    DESCRIPTION  "The date and time stamp of the temperature value."
    ::= { stmnHistPMEntry 14 }


stmnHistPMTempValidity OBJECT-TYPE
    SYNTAX       PMValidity
    MAX-ACCESS   read-only
    STATUS       current
    DESCRIPTION  "Indicates the validity of the provided temperature value."
    ::= { stmnHistPMEntry 15 }


stmnHistPMSupplyVoltageValue OBJECT-TYPE
    SYNTAX       FixedX10
    UNITS        "mVolts/10"
    MAX-ACCESS   read-only
    STATUS       current
    DESCRIPTION  "The supply voltage measured on the STM-N facility port."
    ::= { stmnHistPMEntry 16 }


stmnHistPMSupplyVoltageTimeStamp OBJECT-TYPE
    SYNTAX       DateAndTime
    MAX-ACCESS   read-only
    STATUS       current
    DESCRIPTION  "The date and time stamp of the supply voltage value."
    ::= { stmnHistPMEntry 17 }


stmnHistPMSupplyVoltageValidity OBJECT-TYPE
    SYNTAX       PMValidity
    MAX-ACCESS   read-only
    STATUS       current
    DESCRIPTION  "Indicates the validity of the provided supply voltage value."
    ::= { stmnHistPMEntry 18 }


stmnHistPMLBCValue OBJECT-TYPE
    SYNTAX       INTEGER (-32768..32767)
    UNITS        "mAmp"
    MAX-ACCESS   read-only
    STATUS       current
    DESCRIPTION  "The laser bias current measured on the STM-N facility port."
    ::= { stmnHistPMEntry 19 }


stmnHistPMLBCTimeStamp OBJECT-TYPE
    SYNTAX       DateAndTime
    MAX-ACCESS   read-only
    STATUS       current
    DESCRIPTION  "The date and time stamp of the laser bias current value."
    ::= { stmnHistPMEntry 20 }


stmnHistPMLBCValidity OBJECT-TYPE
    SYNTAX       PMValidity
    MAX-ACCESS   read-only
    STATUS       current
    DESCRIPTION  "Indicates the validity of the provided laser bias current
                  value."
    ::= { stmnHistPMEntry 21 }


stmnHistPMRSEBValue OBJECT-TYPE
    SYNTAX       Unsigned32
    MAX-ACCESS   read-write
    STATUS       current
    DESCRIPTION  "The count of regenerator section errored blocks."
    ::= { stmnHistPMEntry 22 }


stmnHistPMRSEBTimeStamp OBJECT-TYPE
    SYNTAX       DateAndTime
    MAX-ACCESS   read-only
    STATUS       current
    DESCRIPTION  "The date and time stamp of the regenerator section errored
                  blocks value."
    ::= { stmnHistPMEntry 23 }


stmnHistPMRSEBValidity OBJECT-TYPE
    SYNTAX       PMValidity
    MAX-ACCESS   read-only
    STATUS       current
    DESCRIPTION  "Indicates the validity of the provided regenerator section
                  errored blocks value."
    ::= { stmnHistPMEntry 24 }


stmnHistPMRSBBEValue OBJECT-TYPE
    SYNTAX       Unsigned32
    MAX-ACCESS   read-write
    STATUS       current
    DESCRIPTION  "The count of regenerator section background block errors."
    ::= { stmnHistPMEntry 25 }


stmnHistPMRSBBETimeStamp OBJECT-TYPE
    SYNTAX       DateAndTime
    MAX-ACCESS   read-only
    STATUS       current
    DESCRIPTION  "The date and time stamp of the regenerator section background
                  block errors value."
    ::= { stmnHistPMEntry 26 }


stmnHistPMRSBBEValidity OBJECT-TYPE
    SYNTAX       PMValidity
    MAX-ACCESS   read-only
    STATUS       current
    DESCRIPTION  "Indicates the validity of the provided regenerator section
                  background block errors value."
    ::= { stmnHistPMEntry 27 }


stmnHistPMRSESValue OBJECT-TYPE
    SYNTAX       Unsigned32
    MAX-ACCESS   read-write
    STATUS       current
    DESCRIPTION  "The count of regenerator section errored seconds."
    ::= { stmnHistPMEntry 28 }


stmnHistPMRSESTimeStamp OBJECT-TYPE
    SYNTAX       DateAndTime
    MAX-ACCESS   read-only
    STATUS       current
    DESCRIPTION  "The date and time stamp of the regenerator section errored
                  seconds value."
    ::= { stmnHistPMEntry 29 }


stmnHistPMRSESValidity OBJECT-TYPE
    SYNTAX       PMValidity
    MAX-ACCESS   read-only
    STATUS       current
    DESCRIPTION  "Indicates the validity of the provided regenerator section
                  errored seconds value."
    ::= { stmnHistPMEntry 30 }


stmnHistPMRSSESValue OBJECT-TYPE
    SYNTAX       Unsigned32
    MAX-ACCESS   read-write
    STATUS       current
    DESCRIPTION  "The count of regenerator section severely errored seconds."
    ::= { stmnHistPMEntry 31 }


stmnHistPMRSSESTimeStamp OBJECT-TYPE
    SYNTAX       DateAndTime
    MAX-ACCESS   read-only
    STATUS       current
    DESCRIPTION  "The date and time stamp of the regenerator section severely
                  errored seconds value."
    ::= { stmnHistPMEntry 32 }


stmnHistPMRSSESValidity OBJECT-TYPE
    SYNTAX       PMValidity
    MAX-ACCESS   read-only
    STATUS       current
    DESCRIPTION  "Indicates the validity of the provided regenerator section
                  severely errored seconds value."
    ::= { stmnHistPMEntry 33 }


stmnHistPMRSOFSValue OBJECT-TYPE
    SYNTAX       Unsigned32
    MAX-ACCESS   read-write
    STATUS       current
    DESCRIPTION  "The count of regenerator section out-of-frame seconds."
    ::= { stmnHistPMEntry 34 }


stmnHistPMRSOFSTimeStamp OBJECT-TYPE
    SYNTAX       DateAndTime
    MAX-ACCESS   read-only
    STATUS       current
    DESCRIPTION  "The date and time stamp of the regenerator section
                  out-of-frame seconds value."
    ::= { stmnHistPMEntry 35 }


stmnHistPMRSOFSValidity OBJECT-TYPE
    SYNTAX       PMValidity
    MAX-ACCESS   read-only
    STATUS       current
    DESCRIPTION  "Indicates the validity of the provided regenerator section
                  out-of-frame seconds value."
    ::= { stmnHistPMEntry 36 }


stmnHistPMSupplyVoltage2Value OBJECT-TYPE
    SYNTAX       FixedX10
    UNITS        "mVolts/10"
    MAX-ACCESS   read-only
    STATUS       current
    DESCRIPTION  "The value of the second supply voltage source measured on the
                  STM-N facility port transceiver."
    ::= { stmnHistPMEntry 37 }


stmnHistPMSupplyVoltage2TimeStamp OBJECT-TYPE
    SYNTAX       DateAndTime
    MAX-ACCESS   read-only
    STATUS       current
    DESCRIPTION  "The date and time stamp of the second supply voltage value."
    ::= { stmnHistPMEntry 38 }


stmnHistPMSupplyVoltage2Validity OBJECT-TYPE
    SYNTAX       PMValidity
    MAX-ACCESS   read-only
    STATUS       current
    DESCRIPTION  "Indicates the validity of the provided second supply voltage
                  value."
    ::= { stmnHistPMEntry 39 }


stmnHistPMMSEBValue OBJECT-TYPE
    SYNTAX       Unsigned32
    MAX-ACCESS   read-write
    STATUS       current
    DESCRIPTION  "The count of multiplex section errored blocks."
    ::= { stmnHistPMEntry 40 }


stmnHistPMMSEBTimeStamp OBJECT-TYPE
    SYNTAX       DateAndTime
    MAX-ACCESS   read-only
    STATUS       current
    DESCRIPTION  "The date and time stamp of the multiplex section errored
                  blocks value."
    ::= { stmnHistPMEntry 41 }


stmnHistPMMSEBValidity OBJECT-TYPE
    SYNTAX       PMValidity
    MAX-ACCESS   read-only
    STATUS       current
    DESCRIPTION  "Indicates the validity of the provided multiplex section
                  errored blocks value."
    ::= { stmnHistPMEntry 42 }


stmnHistPMMSBBEValue OBJECT-TYPE
    SYNTAX       Unsigned32
    MAX-ACCESS   read-write
    STATUS       current
    DESCRIPTION  "The count of multiplex section background block errors."
    ::= { stmnHistPMEntry 43 }


stmnHistPMMSBBETimeStamp OBJECT-TYPE
    SYNTAX       DateAndTime
    MAX-ACCESS   read-only
    STATUS       current
    DESCRIPTION  "The date and time stamp of the multiplex section background
                  block errors value."
    ::= { stmnHistPMEntry 44 }


stmnHistPMMSBBEValidity OBJECT-TYPE
    SYNTAX       PMValidity
    MAX-ACCESS   read-only
    STATUS       current
    DESCRIPTION  "Indicates the validity of the provided multiplex section
                  background block errors value."
    ::= { stmnHistPMEntry 45 }


stmnHistPMMSESValue OBJECT-TYPE
    SYNTAX       Unsigned32
    MAX-ACCESS   read-write
    STATUS       current
    DESCRIPTION  "The count of multiplex section errored seconds."
    ::= { stmnHistPMEntry 46 }


stmnHistPMMSESTimeStamp OBJECT-TYPE
    SYNTAX       DateAndTime
    MAX-ACCESS   read-only
    STATUS       current
    DESCRIPTION  "The date and time stamp of the multiplex section errored
                  seconds value."
    ::= { stmnHistPMEntry 47 }


stmnHistPMMSESValidity OBJECT-TYPE
    SYNTAX       PMValidity
    MAX-ACCESS   read-only
    STATUS       current
    DESCRIPTION  "Indicates the validity of the provided multiplex section
                  errored seconds value."
    ::= { stmnHistPMEntry 48 }


stmnHistPMMSSESValue OBJECT-TYPE
    SYNTAX       Unsigned32
    MAX-ACCESS   read-write
    STATUS       current
    DESCRIPTION  "The count of multiplex section severely errored seconds."
    ::= { stmnHistPMEntry 49 }


stmnHistPMMSSESTimeStamp OBJECT-TYPE
    SYNTAX       DateAndTime
    MAX-ACCESS   read-only
    STATUS       current
    DESCRIPTION  "The date and time stamp of the multiplex section severely
                  errored seconds value."
    ::= { stmnHistPMEntry 50 }


stmnHistPMMSSESValidity OBJECT-TYPE
    SYNTAX       PMValidity
    MAX-ACCESS   read-only
    STATUS       current
    DESCRIPTION  "Indicates the validity of the provided multiplex section
                  severely errored seconds value."
    ::= { stmnHistPMEntry 51 }


stmnHistPMMSUASValue OBJECT-TYPE
    SYNTAX       Unsigned32
    MAX-ACCESS   read-write
    STATUS       current
    DESCRIPTION  "The count of multiplex section unavailable seconds."
    ::= { stmnHistPMEntry 52 }


stmnHistPMMSUASTimeStamp OBJECT-TYPE
    SYNTAX       DateAndTime
    MAX-ACCESS   read-only
    STATUS       current
    DESCRIPTION  "The date and time stamp of the multiplex section unavailable
                  seconds value."
    ::= { stmnHistPMEntry 53 }


stmnHistPMMSUASValidity OBJECT-TYPE
    SYNTAX       PMValidity
    MAX-ACCESS   read-only
    STATUS       current
    DESCRIPTION  "Indicates the validity of the provided multiplex section
                  unavailable seconds value."
    ::= { stmnHistPMEntry 54 }


stmnHistPMOTUEBValue OBJECT-TYPE
    SYNTAX       Unsigned32 
    MAX-ACCESS   read-write
    STATUS       current
    DESCRIPTION  "The count of OTU digital wrapper layer errored blocks."
    ::= { stmnHistPMEntry 55 }


stmnHistPMOTUEBTimeStamp OBJECT-TYPE
    SYNTAX       DateAndTime
    MAX-ACCESS   read-only
    STATUS       current
    DESCRIPTION  "The date and time stamp of the OTU digital wrapper layer
                  errored blocks value."
    ::= { stmnHistPMEntry 56 }


stmnHistPMOTUEBValidity OBJECT-TYPE
    SYNTAX       PMValidity
    MAX-ACCESS   read-only
    STATUS       current
    DESCRIPTION  "Indicates the validity of the provided OTU digital wrapper
                  layer errored blocks value."
    ::= { stmnHistPMEntry 57 }


stmnHistPMOTUBBEValue OBJECT-TYPE
    SYNTAX       Unsigned32 
    MAX-ACCESS   read-write
    STATUS       current
    DESCRIPTION  "The count of OTU digital wrapper layer background block
                  errors."
    ::= { stmnHistPMEntry 58 }


stmnHistPMOTUBBETimeStamp OBJECT-TYPE
    SYNTAX       DateAndTime
    MAX-ACCESS   read-only
    STATUS       current
    DESCRIPTION  "The date and time stamp of the OTU digital wrapper layer
                  background block errors value."
    ::= { stmnHistPMEntry 59 }


stmnHistPMOTUBBEValidity OBJECT-TYPE
    SYNTAX       PMValidity
    MAX-ACCESS   read-only
    STATUS       current
    DESCRIPTION  "Indicates the validity of the provided OTU digital wrapper
                  layer background block errors value."
    ::= { stmnHistPMEntry 60 }


stmnHistPMOTUESValue OBJECT-TYPE
    SYNTAX       Unsigned32
    MAX-ACCESS   read-write
    STATUS       current
    DESCRIPTION  "The count of OTU digital wrapper layer errored seconds."
    ::= { stmnHistPMEntry 61 }


stmnHistPMOTUESTimeStamp OBJECT-TYPE
    SYNTAX       DateAndTime
    MAX-ACCESS   read-only
    STATUS       current
    DESCRIPTION  "The date and time stamp of the OTU digital wrapper layer
                  errored seconds value."
    ::= { stmnHistPMEntry 62 }


stmnHistPMOTUESValidity OBJECT-TYPE
    SYNTAX       PMValidity
    MAX-ACCESS   read-only
    STATUS       current
    DESCRIPTION  "Indicates the validity of the provided OTU digital wrapper
                  layer errored seconds value."
    ::= { stmnHistPMEntry 63 }


stmnHistPMOTUSESValue OBJECT-TYPE
    SYNTAX       Unsigned32
    MAX-ACCESS   read-write
    STATUS       current
    DESCRIPTION  "The count of OTU digital wrapper layer severely errored
                  seconds."
    ::= { stmnHistPMEntry 64 }


stmnHistPMOTUSESTimeStamp OBJECT-TYPE
    SYNTAX       DateAndTime
    MAX-ACCESS   read-only
    STATUS       current
    DESCRIPTION  "The date and time stamp of the OTU digital wrapper layer
                  severely errored seconds value."
    ::= { stmnHistPMEntry 65 }


stmnHistPMOTUSESValidity OBJECT-TYPE
    SYNTAX       PMValidity
    MAX-ACCESS   read-only
    STATUS       current
    DESCRIPTION  "Indicates the validity of the provided OTU digital wrapper
                  layer severely errored seconds value."
    ::= { stmnHistPMEntry 66 }


stmnHistPMOTUOFSValue OBJECT-TYPE
    SYNTAX       Unsigned32
    MAX-ACCESS   read-write
    STATUS       current
    DESCRIPTION  "The count of OTU digital wrapper layer out-of-frame seconds."
    ::= { stmnHistPMEntry 67 }


stmnHistPMOTUOFSTimeStamp OBJECT-TYPE
    SYNTAX       DateAndTime
    MAX-ACCESS   read-only
    STATUS       current
    DESCRIPTION  "The date and time stamp of the OTU digital wrapper layer
                  out-of-frame seconds value."
    ::= { stmnHistPMEntry 68 }


stmnHistPMOTUOFSValidity OBJECT-TYPE
    SYNTAX       PMValidity
    MAX-ACCESS   read-only
    STATUS       current
    DESCRIPTION  "Indicates the validity of the provided OTU digital wrapper
                  layer severely errored framing seconds value."
    ::= { stmnHistPMEntry 69 }


stmnHistPMNBITCRValue OBJECT-TYPE
    SYNTAX       Unsigned32
    MAX-ACCESS   read-write
    STATUS       current
    DESCRIPTION  "The count of the number of bits corrected. This object applies
                  only to STM-64 line port provisioned for OTN line mapping."
    ::= { stmnHistPMEntry 70 }


stmnHistPMNBITCRTimeStamp OBJECT-TYPE
    SYNTAX       DateAndTime
    MAX-ACCESS   read-only
    STATUS       current
    DESCRIPTION  "The date and time stamp of the number of bits corrected
                  value."
    ::= { stmnHistPMEntry 71 }


stmnHistPMNBITCRValidity OBJECT-TYPE
    SYNTAX       PMValidity
    MAX-ACCESS   read-only
    STATUS       current
    DESCRIPTION  "Indicates the validity of the provided number of bits
                  corrected value."
    ::= { stmnHistPMEntry 72 }


stmnHistPMNBYTCRValue OBJECT-TYPE
    SYNTAX       Unsigned32
    MAX-ACCESS   read-write
    STATUS       current
    DESCRIPTION  "The count of the number of bytes corrected. This object
                  applies only to STM-64 line port provisioned for OTN line
                  mapping."
    ::= { stmnHistPMEntry 73 }


stmnHistPMNBYTCRTimeStamp OBJECT-TYPE
    SYNTAX       DateAndTime
    MAX-ACCESS   read-only
    STATUS       current
    DESCRIPTION  "The date and time stamp of the number of bytes corrected
                  value."
    ::= { stmnHistPMEntry 74 }


stmnHistPMNBYTCRValidity OBJECT-TYPE
    SYNTAX       PMValidity
    MAX-ACCESS   read-only
    STATUS       current
    DESCRIPTION  "Indicates the validity of the provided number of bytes
                  corrected value."
    ::= { stmnHistPMEntry 75 }


stmnHistPMUNCRCDWValue OBJECT-TYPE
    SYNTAX       Unsigned32
    MAX-ACCESS   read-write
    STATUS       current
    DESCRIPTION  "The count of uncorrectable codewords. This object applies only
                  to STM-64 line port provisioned for OTN line mapping."
    ::= { stmnHistPMEntry 76 }


stmnHistPMUNCRCDWTimeStamp OBJECT-TYPE
    SYNTAX       DateAndTime
    MAX-ACCESS   read-only
    STATUS       current
    DESCRIPTION  "The date and time stamp of the uncorrectable codewords value."
    ::= { stmnHistPMEntry 77 }


stmnHistPMUNCRCDWValidity OBJECT-TYPE
    SYNTAX       PMValidity
    MAX-ACCESS   read-only
    STATUS       current
    DESCRIPTION  "Indicates the validity of the provided uncorrectable codewords
                  value."
    ::= { stmnHistPMEntry 78 }


stmnHistPMRSEBInitialize OBJECT-TYPE
    SYNTAX       InitializeCmd
    MAX-ACCESS   read-write
    STATUS       current
    DESCRIPTION  "Used to initialize the value of the stmnHistPMRSEBValue object
                  to 0."
    ::= { stmnHistPMEntry 79 }


stmnHistPMRSBBEInitialize OBJECT-TYPE
    SYNTAX       InitializeCmd
    MAX-ACCESS   read-write
    STATUS       current
    DESCRIPTION  "Used to initialize the value of the stmnHistPMRSBBEValue
                  object to 0."
    ::= { stmnHistPMEntry 80 }


stmnHistPMRSESInitialize OBJECT-TYPE
    SYNTAX       InitializeCmd
    MAX-ACCESS   read-write
    STATUS       current
    DESCRIPTION  "Used to initialize the value of the stmnHistPMRSESValue object
                  to 0."
    ::= { stmnHistPMEntry 81 }


stmnHistPMRSSESInitialize OBJECT-TYPE
    SYNTAX       InitializeCmd
    MAX-ACCESS   read-write
    STATUS       current
    DESCRIPTION  "Used to initialize the value of the stmnHistPMRSSESValue
                  object to 0."
    ::= { stmnHistPMEntry 82 }


stmnHistPMRSOFSInitialize OBJECT-TYPE
    SYNTAX       InitializeCmd
    MAX-ACCESS   read-write
    STATUS       current
    DESCRIPTION  "Used to initialize the value of the stmnHistPMRSOFSValue
                  object to 0."
    ::= { stmnHistPMEntry 83 }


stmnHistPMMSEBInitialize OBJECT-TYPE
    SYNTAX       InitializeCmd
    MAX-ACCESS   read-write
    STATUS       current
    DESCRIPTION  "Used to initialize the value of the stmnHistPMMSEBValue object
                  to 0."
    ::= { stmnHistPMEntry 84 }


stmnHistPMMSBBEInitialize OBJECT-TYPE
    SYNTAX       InitializeCmd
    MAX-ACCESS   read-write
    STATUS       current
    DESCRIPTION  "Used to initialize the value of the stmnHistPMMSBBEValue
                  object to 0."
    ::= { stmnHistPMEntry 85 }


stmnHistPMMSESInitialize OBJECT-TYPE
    SYNTAX       InitializeCmd
    MAX-ACCESS   read-write
    STATUS       current
    DESCRIPTION  "Used to initialize the value of the stmnHistPMMSESValue object
                  to 0."
    ::= { stmnHistPMEntry 86 }


stmnHistPMMSSESInitialize OBJECT-TYPE
    SYNTAX       InitializeCmd
    MAX-ACCESS   read-write
    STATUS       current
    DESCRIPTION  "Used to initialize the value of the stmnHistPMMSSESValue
                  object to 0."
    ::= { stmnHistPMEntry 87 }


stmnHistPMMSUASInitialize OBJECT-TYPE
    SYNTAX       InitializeCmd
    MAX-ACCESS   read-write
    STATUS       current
    DESCRIPTION  "Used to initialize the value of the stmnHistPMMSUASValue
                  object to 0."
    ::= { stmnHistPMEntry 88 }


stmnHistPMOTUEBInitialize OBJECT-TYPE
    SYNTAX       InitializeCmd
    MAX-ACCESS   read-write
    STATUS       current
    DESCRIPTION  "Used to initialize the value of the stmnHistPMOTUEBValue
                  object to 0."
    ::= { stmnHistPMEntry 89 }


stmnHistPMOTUBBEInitialize OBJECT-TYPE
    SYNTAX       InitializeCmd
    MAX-ACCESS   read-write
    STATUS       current
    DESCRIPTION  "Used to initialize the value of the stmnHistPMOTUBBEValue
                  object to 0."
    ::= { stmnHistPMEntry 90 }


stmnHistPMOTUESInitialize OBJECT-TYPE
    SYNTAX       InitializeCmd
    MAX-ACCESS   read-write
    STATUS       current
    DESCRIPTION  "Used to initialize the value of the stmnHistPMOTUESValue
                  object to 0."
    ::= { stmnHistPMEntry 91 }


stmnHistPMOTUSESInitialize OBJECT-TYPE
    SYNTAX       InitializeCmd
    MAX-ACCESS   read-write
    STATUS       current
    DESCRIPTION  "Used to initialize the value of the stmnHistPMOTUSESValue
                  object to 0."
    ::= { stmnHistPMEntry 92 }


stmnHistPMOTUOFSInitialize OBJECT-TYPE
    SYNTAX       InitializeCmd
    MAX-ACCESS   read-write
    STATUS       current
    DESCRIPTION  "Used to initialize the value of the stmnHistPMOTUOFSValue
                  object to 0."
    ::= { stmnHistPMEntry 93 }


stmnHistPMNBITCRInitialize OBJECT-TYPE
    SYNTAX       InitializeCmd
    MAX-ACCESS   read-write
    STATUS       current
    DESCRIPTION  "Used to initialize the value of the stmnHistPMNBITCRValue
                  object to 0."
    ::= { stmnHistPMEntry 94 }


stmnHistPMNBYTCRInitialize OBJECT-TYPE
    SYNTAX       InitializeCmd
    MAX-ACCESS   read-write
    STATUS       current
    DESCRIPTION  "Used to initialize the value of the stmnHistPMNBYTCRValue
                  object to 0."
    ::= { stmnHistPMEntry 95 }


stmnHistPMUNCRCDWInitialize OBJECT-TYPE
    SYNTAX       InitializeCmd
    MAX-ACCESS   read-write
    STATUS       current
    DESCRIPTION  "Used to initialize the value of the stmnHistPMUNCRCDWValue
                  object to 0."
    ::= { stmnHistPMEntry 96 }


stmnHistPMOTNBERValue OBJECT-TYPE
    SYNTAX       DisplayString
    MAX-ACCESS   read-only
    STATUS       current
    DESCRIPTION  "The instantaneous BER of STM-64 line port provisioned for OTN line mapping."
    ::= { stmnHistPMEntry 97 }


stmnHistPMOTNBERTimeStamp OBJECT-TYPE
    SYNTAX       DateAndTime
    MAX-ACCESS   read-only
    STATUS       current
    DESCRIPTION  "The date and time stamp of the instantaneous BER."
    ::= { stmnHistPMEntry 98 }


stmnHistPMOTNBERValidity OBJECT-TYPE
    SYNTAX       PMValidity
    MAX-ACCESS   read-only
    STATUS       current
    DESCRIPTION  "Indicates the validity of the provided instantaneous BER."
    ::= { stmnHistPMEntry 99 }


stmnHistPMOTNBERInitialize OBJECT-TYPE
    SYNTAX       InitializeCmd
    MAX-ACCESS   read-write
    STATUS       current
    DESCRIPTION  "Used to initialize the value of the stmnHistPMOTNBERValue
                  object to 0."
    ::= { stmnHistPMEntry 100 }


stmnHistPMOTNAVGBERValue OBJECT-TYPE
    SYNTAX       DisplayString
    MAX-ACCESS   read-only
    STATUS       current
    DESCRIPTION  "The interval/average BER of STM-64 line port provisioned for OTN line mapping."
    ::= { stmnHistPMEntry 101 }


stmnHistPMOTNAVGBERTimeStamp OBJECT-TYPE
    SYNTAX       DateAndTime
    MAX-ACCESS   read-only
    STATUS       current
    DESCRIPTION  "The date and time stamp of the interval/average BER."
    ::= { stmnHistPMEntry 102 }


stmnHistPMOTNAVGBERValidity OBJECT-TYPE
    SYNTAX       PMValidity
    MAX-ACCESS   read-only
    STATUS       current
    DESCRIPTION  "Indicates the validity of the provided interval/average BER."
    ::= { stmnHistPMEntry 103 }

stmnHistPMOTNAVGBERInitialize OBJECT-TYPE
    SYNTAX       InitializeCmd
    MAX-ACCESS   read-write
    STATUS       current
    DESCRIPTION  "Used to initialize the value of the stmnHistPMOTNAVGBERValue
                  object to 0."
    ::= { stmnHistPMEntry 104 }


stmnHistPMNBITCR64BitValue OBJECT-TYPE
    SYNTAX       Unsigned64
    MAX-ACCESS   read-only
    STATUS       current
    DESCRIPTION  "The 64-bit count of the number of bits corrected. This object applies
                  only to STM-64 line port provisioned for OTN line mapping."
    ::= { stmnHistPMEntry 105 }


stmnHistPMNBITCR64BitTimeStamp OBJECT-TYPE
    SYNTAX       DateAndTime
    MAX-ACCESS   read-only
    STATUS       current
    DESCRIPTION  "The date and time stamp of the 64-bit number of bits corrected
                  value."
    ::= { stmnHistPMEntry 106 }


stmnHistPMNBITCR64BitValidity OBJECT-TYPE
    SYNTAX       PMValidity
    MAX-ACCESS   read-only
    STATUS       current
    DESCRIPTION  "Indicates the validity of the provided 64-bit number of bits
                  corrected value."
    ::= { stmnHistPMEntry 107 }


stmnHistPMNBITCR64BitInitialize OBJECT-TYPE
    SYNTAX       InitializeCmd
    MAX-ACCESS   read-write
    STATUS       current
    DESCRIPTION  "Used to initialize the value of the stmnCrntPMNBITCR64BitValue
                  object to 0."
    ::= { stmnHistPMEntry 108 }


stmnHistPMNBYTCR64BitValue OBJECT-TYPE
    SYNTAX       Unsigned64
    MAX-ACCESS   read-only
    STATUS       current
    DESCRIPTION  "The 64-bit count of the number of bytes corrected. This object
                  applies only to STM-64 line port provisioned for OTN line
                  mapping."
    ::= { stmnHistPMEntry 109 }


stmnHistPMNBYTCR64BitTimeStamp OBJECT-TYPE
    SYNTAX       DateAndTime
    MAX-ACCESS   read-only
    STATUS       current
    DESCRIPTION  "The date and time stamp of the 64-bit number of bytes corrected
                  value."
    ::= { stmnHistPMEntry 110 }


stmnHistPMNBYTCR64BitValidity OBJECT-TYPE
    SYNTAX       PMValidity
    MAX-ACCESS   read-only
    STATUS       current
    DESCRIPTION  "Indicates the validity of the provided 64-bit number of bytes
                  corrected value."
    ::= { stmnHistPMEntry 111 }


stmnHistPMNBYTCR64BitInitialize OBJECT-TYPE
    SYNTAX       InitializeCmd
    MAX-ACCESS   read-write
    STATUS       current
    DESCRIPTION  "Used to initialize the value of the stmnCrntPMNBYTCR64BitValue
                  object to 0."
    ::= { stmnHistPMEntry 112 }


stmnHistPMRSUASValue OBJECT-TYPE
    SYNTAX       Unsigned32
    MAX-ACCESS   read-write
    STATUS       current
    DESCRIPTION  "The count of regenerator section unavailable seconds.
                  This object applies only to STM-64 line port provisioned
                  for OTN line mapping."
    ::= { stmnHistPMEntry 113 }

stmnHistPMRSUASTimeStamp OBJECT-TYPE
    SYNTAX       DateAndTime
    MAX-ACCESS   read-only
    STATUS       current
    DESCRIPTION  "The date and time stamp of the regenerator section
                  unavailable seconds value."
    ::= { stmnHistPMEntry 114 }


stmnHistPMRSUASValidity OBJECT-TYPE
    SYNTAX       PMValidity
    MAX-ACCESS   read-only
    STATUS       current
    DESCRIPTION  "Indicates the validity of the provided regenerator section
                  unavailable seconds value."
    ::= { stmnHistPMEntry 115 }


stmnHistPMRSUASInitialize OBJECT-TYPE
    SYNTAX       InitializeCmd
    MAX-ACCESS   read-write
    STATUS       current
    DESCRIPTION  "Used to initialize the value of the stmnHistPMRSUASValue
                  object to 0."
    ::= { stmnHistPMEntry 116 }

stmnHistPMOTUUASValue OBJECT-TYPE
    SYNTAX       Unsigned32
    MAX-ACCESS   read-write
    STATUS       current
    DESCRIPTION  "The count of OTU digital wrapper layer unavailable seconds."
    ::= { stmnHistPMEntry 117 }


stmnHistPMOTUUASTimeStamp OBJECT-TYPE
    SYNTAX       DateAndTime
    MAX-ACCESS   read-only
    STATUS       current
    DESCRIPTION  "The date and time stamp of the OTU digital wrapper layer
                  unavailable seconds value."
    ::= { stmnHistPMEntry 118 }


stmnHistPMOTUUASValidity OBJECT-TYPE
    SYNTAX       PMValidity
    MAX-ACCESS   read-only
    STATUS       current
    DESCRIPTION  "Indicates the validity of the provided OTU digital wrapper
                  layer unavailable seconds value."
    ::= { stmnHistPMEntry 119 }

stmnHistPMOTUUASInitialize OBJECT-TYPE
    SYNTAX       InitializeCmd
    MAX-ACCESS   read-write
    STATUS       current
    DESCRIPTION  "Used to initialize the value of the stmnHistPMOTUUASValue
                  object to 0."
    ::= { stmnHistPMEntry 120 }

stmnHistPMOPRMinValue OBJECT-TYPE
    SYNTAX       FixedX10
    UNITS        "dBm/10"
    MAX-ACCESS   read-only
    STATUS       current
    DESCRIPTION  "The minimum optical power received on the input of the transceiver."
    ::= { stmnHistPMEntry 121 }


stmnHistPMOPRMinTimeStamp OBJECT-TYPE
    SYNTAX       DateAndTime
    MAX-ACCESS   read-only
    STATUS       current
    DESCRIPTION  "The date and time stamp of the minimum optical power received value."
    ::= { stmnHistPMEntry 122 }


stmnHistPMOPRMinValidity OBJECT-TYPE
    SYNTAX       PMValidity
    MAX-ACCESS   read-only
    STATUS       current
    DESCRIPTION  "Indicates the validity of the provided minimum optical power received
                  value."
    ::= { stmnHistPMEntry 123 }

stmnHistPMOPRMinInitialize OBJECT-TYPE
    SYNTAX       InitializeCmd
    MAX-ACCESS   read-write
    STATUS       current
    DESCRIPTION  "Used to initialize the value of the stmnHistPMOPRMinValue
                  object to 0."
    ::= { stmnHistPMEntry 124 }

stmnHistPMOPRMaxValue OBJECT-TYPE
    SYNTAX       FixedX10
    UNITS        "dBm/10"
    MAX-ACCESS   read-only
    STATUS       current
    DESCRIPTION  "The maximum optical power received on the input of the transceiver."
    ::= { stmnHistPMEntry 125 }


stmnHistPMOPRMaxTimeStamp OBJECT-TYPE
    SYNTAX       DateAndTime
    MAX-ACCESS   read-only
    STATUS       current
    DESCRIPTION  "The date and time stamp of the maximum optical power received value."
    ::= { stmnHistPMEntry 126 }


stmnHistPMOPRMaxValidity OBJECT-TYPE
    SYNTAX       PMValidity
    MAX-ACCESS   read-only
    STATUS       current
    DESCRIPTION  "Indicates the validity of the provided maximum optical power received
                  value."
    ::= { stmnHistPMEntry 127 }

stmnHistPMOPRMaxInitialize OBJECT-TYPE
    SYNTAX       InitializeCmd
    MAX-ACCESS   read-write
    STATUS       current
    DESCRIPTION  "Used to initialize the value of the stmnHistPMOPRMaxValue
                  object to 0."
    ::= { stmnHistPMEntry 128 }

stmnHistPMOPRAvgValue OBJECT-TYPE
    SYNTAX       FixedX10
    UNITS        "dBm/10"
    MAX-ACCESS   read-only
    STATUS       current
    DESCRIPTION  "The average optical power received on the input of the transceiver."
    ::= { stmnHistPMEntry 129 }


stmnHistPMOPRAvgTimeStamp OBJECT-TYPE
    SYNTAX       DateAndTime
    MAX-ACCESS   read-only
    STATUS       current
    DESCRIPTION  "The date and time stamp of the average optical power received value."
    ::= { stmnHistPMEntry 130 }


stmnHistPMOPRAvgValidity OBJECT-TYPE
    SYNTAX       PMValidity
    MAX-ACCESS   read-only
    STATUS       current
    DESCRIPTION  "Indicates the validity of the provided average optical power received
                  value."
    ::= { stmnHistPMEntry 131 }

stmnHistPMOPRAvgInitialize OBJECT-TYPE
    SYNTAX       InitializeCmd
    MAX-ACCESS   read-write
    STATUS       current
    DESCRIPTION  "Used to initialize the value of the stmnHistPMOPRAvgValue
                  object to 0."
    ::= { stmnHistPMEntry 132 }

stmnHistPMOPTMinValue OBJECT-TYPE
    SYNTAX       FixedX10
    UNITS        "dBm/10"
    MAX-ACCESS   read-only
    STATUS       current
    DESCRIPTION  "The minimum optical power transmitted at the output of the
                  transceiver."
    ::= { stmnHistPMEntry 133 }

stmnHistPMOPTMinTimeStamp OBJECT-TYPE
    SYNTAX       DateAndTime
    MAX-ACCESS   read-only
    STATUS       current
    DESCRIPTION  "The date and time stamp of the minimum optical power transmitted
                  value."
    ::= { stmnHistPMEntry 134 }


stmnHistPMOPTMinValidity OBJECT-TYPE
    SYNTAX       PMValidity
    MAX-ACCESS   read-only
    STATUS       current
    DESCRIPTION  "Indicates the validity of the provided minimum optical power
                  transmitted value."
    ::= { stmnHistPMEntry 135 }

stmnHistPMOPTMinInitialize OBJECT-TYPE
    SYNTAX       InitializeCmd
    MAX-ACCESS   read-write
    STATUS       current
    DESCRIPTION  "Used to initialize the value of the stmnHistPMOPTMinValue
                  object to 0."
    ::= { stmnHistPMEntry 136 }

stmnHistPMOPTMaxValue OBJECT-TYPE
    SYNTAX       FixedX10
    UNITS        "dBm/10"
    MAX-ACCESS   read-only
    STATUS       current
    DESCRIPTION  "The maximum optical power transmitted at the output of the
                  transceiver."
    ::= { stmnHistPMEntry 137 }


stmnHistPMOPTMaxTimeStamp OBJECT-TYPE
    SYNTAX       DateAndTime
    MAX-ACCESS   read-only
    STATUS       current
    DESCRIPTION  "The date and time stamp of the maximum optical power transmitted
                  value."
    ::= { stmnHistPMEntry 138 }


stmnHistPMOPTMaxValidity OBJECT-TYPE
    SYNTAX       PMValidity
    MAX-ACCESS   read-only
    STATUS       current
    DESCRIPTION  "Indicates the validity of the provided maximum optical power
                  transmitted value."
    ::= { stmnHistPMEntry 139 }

stmnHistPMOPTMaxInitialize OBJECT-TYPE
    SYNTAX       InitializeCmd
    MAX-ACCESS   read-write
    STATUS       current
    DESCRIPTION  "Used to initialize the value of the stmnHistPMOPTMaxValue
                  object to 0."
    ::= { stmnHistPMEntry 140 }

stmnHistPMOPTAvgValue OBJECT-TYPE
    SYNTAX       FixedX10
    UNITS        "dBm/10"
    MAX-ACCESS   read-only
    STATUS       current
    DESCRIPTION  "The average optical power transmitted at the output of the
                  transceiver."
    ::= { stmnHistPMEntry 141 }


stmnHistPMOPTAvgTimeStamp OBJECT-TYPE
    SYNTAX       DateAndTime
    MAX-ACCESS   read-only
    STATUS       current
    DESCRIPTION  "The date and time stamp of the average optical power transmitted
                  value."
    ::= { stmnHistPMEntry 142 }

stmnHistPMOPTAvgValidity OBJECT-TYPE
    SYNTAX       PMValidity
    MAX-ACCESS   read-only
    STATUS       current
    DESCRIPTION  "Indicates the validity of the provided average optical power
                  transmitted value."
    ::= { stmnHistPMEntry 143 }

stmnHistPMOPTAvgInitialize OBJECT-TYPE
    SYNTAX       InitializeCmd
    MAX-ACCESS   read-write
    STATUS       current
    DESCRIPTION  "Used to initialize the value of the stmnHistPMOPTAvgValue
                  object to 0."
    ::= { stmnHistPMEntry 144 }

-----------------------------------------------------------------------
-- Objects used to manage SDH STM-N 
-- Monitoring Threshold Levels
-- 
-- A listing of SDH STM-N PM threshold levels is contained in the
-- stsmPMThresholdTable of the BTI-7000-MIB. When retrieved, this 
-- table provides one row for each set of SDH STM-N PM threshold data.
-- 
-- The following table lists the objects in each entry of the 
-- stsmPMThresholdTable.
-----------------------------------------------------------------------


stmnPMThresholdTable OBJECT-TYPE
    SYNTAX       SEQUENCE OF StmnPMThresholdEntry
    MAX-ACCESS   not-accessible
    STATUS       current
    DESCRIPTION  "A table of threshold levels for performance monitoring counter
                  values on SDH STM-N facilities, that are used in the
                  generation of threshold crossing alerts."
    ::= { performance 16 }


stmnPMThresholdEntry OBJECT-TYPE
    SYNTAX       StmnPMThresholdEntry
    MAX-ACCESS   not-accessible
    STATUS       current
    DESCRIPTION  "The row entry object of the SDH STM-N performance monitoring
                  threshold table. Each row of this table contains a set of PM
                  thresholds for a given interval type that applies to an
                  individual STM-N facility."
    INDEX        { stmnPMThresholdTypeIdx,
                   stmnPMThresholdShelfIdx,
                   stmnPMThresholdSlotIdx,
                   stmnPMThresholdPortIdx,
                   stmnPMThresholdIntervalTypeIdx }
    ::= { stmnPMThresholdTable 1 }


StmnPMThresholdEntry ::= SEQUENCE { stmnPMThresholdTypeIdx          StmnType,
                                    stmnPMThresholdShelfIdx         INTEGER,
                                    stmnPMThresholdSlotIdx          INTEGER,
                                    stmnPMThresholdPortIdx          INTEGER,
                                    stmnPMThresholdIntervalTypeIdx  PMIntervalType,
                                    stmnPMThresholdRSEBValue        Unsigned32,
                                    stmnPMThresholdRSBBEValue       Unsigned32,
                                    stmnPMThresholdRSESValue        Unsigned32,
                                    stmnPMThresholdRSSESValue       Unsigned32,
                                    stmnPMThresholdRSOFSValue       Unsigned32,
                                    stmnPMThresholdMSEBValue        Unsigned32,
                                    stmnPMThresholdMSBBEValue       Unsigned32,
                                    stmnPMThresholdMSESValue        Unsigned32,
                                    stmnPMThresholdMSSESValue       Unsigned32,
                                    stmnPMThresholdMSUASValue       Unsigned32,
                                    stmnPMThresholdOTUEBValue       Unsigned32,
                                    stmnPMThresholdOTUBBEValue      Unsigned32,
                                    stmnPMThresholdOTUESValue       Unsigned32,
                                    stmnPMThresholdOTUSESValue      Unsigned32,
                                    stmnPMThresholdOTUOFSValue      Unsigned32,
                                    stmnPMThresholdUNCRCDWValue     Unsigned32,
                                    stmnPMThresholdRSUASValue       Unsigned32,
                                    stmnPMThresholdOTUUASValue      Unsigned32 }


stmnPMThresholdTypeIdx OBJECT-TYPE
    SYNTAX       StmnType
    MAX-ACCESS   not-accessible
    STATUS       current
    DESCRIPTION  "The type of the STM-N facility targeted for PM thresholds."
    ::= { stmnPMThresholdEntry 1 }


stmnPMThresholdShelfIdx OBJECT-TYPE
    SYNTAX       INTEGER (1|11|21|31)
    MAX-ACCESS   not-accessible
    STATUS       current
    DESCRIPTION  "The shelf number on which the STM-N facility targeted for PM
                  thresholds is provisioned."
    ::= { stmnPMThresholdEntry 2 }


stmnPMThresholdSlotIdx OBJECT-TYPE
    SYNTAX       INTEGER (1..20)
    MAX-ACCESS   not-accessible
    STATUS       current
    DESCRIPTION  "The slot number on which the STM-N facility targeted for PM
                  thresholds is provisioned."
    ::= { stmnPMThresholdEntry 3 }


stmnPMThresholdPortIdx OBJECT-TYPE
    SYNTAX       INTEGER (1..6)
    MAX-ACCESS   not-accessible
    STATUS       current
    DESCRIPTION  "The number of the port on the circuit pack on which the STM-N
                  facility targeted for PM thresholds is provisioned."
    ::= { stmnPMThresholdEntry 4 }


stmnPMThresholdIntervalTypeIdx OBJECT-TYPE
    SYNTAX       PMIntervalType 
    MAX-ACCESS   not-accessible
    STATUS       current
    DESCRIPTION  "The type of PM bin according to interval length. Thresholds
                  are supported for the 15-minute and 1-day PM bins only."
    ::= { stmnPMThresholdEntry 5 }


stmnPMThresholdRSEBValue OBJECT-TYPE
    SYNTAX       Unsigned32
    MAX-ACCESS   read-write
    STATUS       current
    DESCRIPTION  "The threshold for the count of regenerator section errored
                  blocks."
    ::= { stmnPMThresholdEntry 6 }


stmnPMThresholdRSBBEValue OBJECT-TYPE
    SYNTAX       Unsigned32
    MAX-ACCESS   read-write
    STATUS       current
    DESCRIPTION  "The threshold for the count of regenerator section background
                  block errors."
    ::= { stmnPMThresholdEntry 7 }


stmnPMThresholdRSESValue OBJECT-TYPE
    SYNTAX       Unsigned32
    MAX-ACCESS   read-write
    STATUS       current
    DESCRIPTION  "The threshold for the count of regenerator section errored
                  seconds."
    ::= { stmnPMThresholdEntry 8 }


stmnPMThresholdRSSESValue OBJECT-TYPE
    SYNTAX       Unsigned32
    MAX-ACCESS   read-write
    STATUS       current
    DESCRIPTION  "The threshold for the count of regenerator section severely
                  errored seconds."
    ::= { stmnPMThresholdEntry 9 }


stmnPMThresholdRSOFSValue OBJECT-TYPE
    SYNTAX       Unsigned32
    MAX-ACCESS   read-write
    STATUS       current
    DESCRIPTION  "The threshold for the count of regenerator section
                  out-of-frame seconds."
    ::= { stmnPMThresholdEntry 10 }


stmnPMThresholdMSEBValue OBJECT-TYPE
    SYNTAX       Unsigned32
    MAX-ACCESS   read-write
    STATUS       current
    DESCRIPTION  "The threshold for the count of multiplex section errored
                  blocks."
    ::= { stmnPMThresholdEntry 11 }


stmnPMThresholdMSBBEValue OBJECT-TYPE
    SYNTAX       Unsigned32
    MAX-ACCESS   read-write
    STATUS       current
    DESCRIPTION  "The threshold for the count of multiplex section background
                  block errors."
    ::= { stmnPMThresholdEntry 12 }


stmnPMThresholdMSESValue OBJECT-TYPE
    SYNTAX       Unsigned32
    MAX-ACCESS   read-write
    STATUS       current
    DESCRIPTION  "The threshold for the count of multiplex section errored
                  seconds."
    ::= { stmnPMThresholdEntry 13 }


stmnPMThresholdMSSESValue OBJECT-TYPE
    SYNTAX       Unsigned32
    MAX-ACCESS   read-write
    STATUS       current
    DESCRIPTION  "The threshold for the count of multiplex section severely
                  errored seconds."
    ::= { stmnPMThresholdEntry 14 }


stmnPMThresholdMSUASValue OBJECT-TYPE
    SYNTAX       Unsigned32
    MAX-ACCESS   read-write
    STATUS       current
    DESCRIPTION  "The threshold for the count of multiplex section unavailable
                  seconds."
    ::= { stmnPMThresholdEntry 15 }


stmnPMThresholdOTUEBValue OBJECT-TYPE
    SYNTAX       Unsigned32
    MAX-ACCESS   read-write
    STATUS       current
    DESCRIPTION  "The threshold for the count of OTU digital wrapper layer
                  errored blocks."
    ::= { stmnPMThresholdEntry 16 }


stmnPMThresholdOTUBBEValue OBJECT-TYPE
    SYNTAX       Unsigned32
    MAX-ACCESS   read-write
    STATUS       current
    DESCRIPTION  "The threshold for the count of OTU digital wrapper layer
                  background block errors."
    ::= { stmnPMThresholdEntry 17 }


stmnPMThresholdOTUESValue OBJECT-TYPE
    SYNTAX       Unsigned32
    MAX-ACCESS   read-write
    STATUS       current
    DESCRIPTION  "The threshold for the count of OTU digital wrapper layer
                  errored seconds."
    ::= { stmnPMThresholdEntry 18 }


stmnPMThresholdOTUSESValue OBJECT-TYPE
    SYNTAX       Unsigned32
    MAX-ACCESS   read-write
    STATUS       current
    DESCRIPTION  "The threshold for the count of OTU digital wrapper layer
                  severely errored seconds."
    ::= { stmnPMThresholdEntry 19 }


stmnPMThresholdOTUOFSValue OBJECT-TYPE
    SYNTAX       Unsigned32
    MAX-ACCESS   read-write
    STATUS       current
    DESCRIPTION  "The threshold for the count of OTU digital wrapper layer
                  out-of-frame seconds."
    ::= { stmnPMThresholdEntry 20 }


stmnPMThresholdUNCRCDWValue OBJECT-TYPE
    SYNTAX       Unsigned32
    MAX-ACCESS   read-write
    STATUS       current
    DESCRIPTION  "The threshold for the count of uncorrectable codewords."
    ::= { stmnPMThresholdEntry 23 }

stmnPMThresholdRSUASValue OBJECT-TYPE
    SYNTAX       Unsigned32
    MAX-ACCESS   read-write
    STATUS       current
    DESCRIPTION  "The threshold for the count of regenerator section
                  unavailable seconds."
    ::= { stmnPMThresholdEntry 24 }

stmnPMThresholdOTUUASValue OBJECT-TYPE
    SYNTAX       Unsigned32
    MAX-ACCESS   read-write
    STATUS       current
    DESCRIPTION  "The threshold for the count of OTU digital wrapper layer
                  unavailable seconds."
    ::= { stmnPMThresholdEntry 25 }

-----------------------------------------------------------------------
-- Objects used to retrieve current SDH VC-N
-- Performance Monitoring statistics
-- 
-- A listing of current SDH VC-N PM values is contained in the 
-- vcnCrntPMTable of the BTI 7000 Series MIB. When retrieved, this 
-- table provides one row for each set of current SDH VC-N PM data.
-- 
-- The following table lists the objects in each entry of the 
-- vcnCrntPMTable.
-----------------------------------------------------------------------


vcnCrntPMTable OBJECT-TYPE
    SYNTAX       SEQUENCE OF VcnCrntPMEntry
    MAX-ACCESS   not-accessible
    STATUS       current
    DESCRIPTION  "A table of current performance monitoring statistics collected
                  for the SDH VC-N facilities on the NE."
    ::= { performance 17 }


vcnCrntPMEntry OBJECT-TYPE
    SYNTAX       VcnCrntPMEntry
    MAX-ACCESS   not-accessible
    STATUS       current
    DESCRIPTION  "The row entry object of the SDH VC-N current performance
                  monitoring table. Each row of this table contains a full set
                  of PM statistics and related data for a current measurement
                  interval for a given VC-N facility."
    INDEX        { vcnCrntPMTypeIdx,
                   vcnCrntPMShelfIdx,
                   vcnCrntPMSlotIdx,
                   vcnCrntPMPortIdx,
                   vcnCrntPMIdx,
                   vcnCrntPMIntervalTypeIdx }
    ::= { vcnCrntPMTable 1 }


VcnCrntPMEntry ::= SEQUENCE { vcnCrntPMTypeIdx          VcnType,
                              vcnCrntPMShelfIdx         INTEGER,
                              vcnCrntPMSlotIdx          INTEGER,
                              vcnCrntPMPortIdx          INTEGER,
                              vcnCrntPMIdx              INTEGER,
                              vcnCrntPMIntervalTypeIdx  PMIntervalType,
                              vcnCrntPMHPEBValue        Unsigned32,
                              vcnCrntPMHPEBTimeStamp    DateAndTime,
                              vcnCrntPMHPEBValidity     PMValidity,
                              vcnCrntPMHPBBEValue       Unsigned32,
                              vcnCrntPMHPBBETimeStamp   DateAndTime,
                              vcnCrntPMHPBBEValidity    PMValidity,
                              vcnCrntPMHPESValue        Unsigned32,
                              vcnCrntPMHPESTimeStamp    DateAndTime,
                              vcnCrntPMHPESValidity     PMValidity,
                              vcnCrntPMHPSESValue       Unsigned32,
                              vcnCrntPMHPSESTimeStamp   DateAndTime,
                              vcnCrntPMHPSESValidity    PMValidity,
                              vcnCrntPMHPUASValue       Unsigned32,
                              vcnCrntPMHPUASTimeStamp   DateAndTime,
                              vcnCrntPMHPUASValidity    PMValidity,
                              vcnCrntPMHPEBInitialize   InitializeCmd,
                              vcnCrntPMHPBBEInitialize  InitializeCmd,
                              vcnCrntPMHPESInitialize   InitializeCmd,
                              vcnCrntPMHPSESInitialize  InitializeCmd,
                              vcnCrntPMHPUASInitialize  InitializeCmd }


vcnCrntPMTypeIdx OBJECT-TYPE
    SYNTAX       VcnType
    MAX-ACCESS   not-accessible
    STATUS       current
    DESCRIPTION  "The type of VC-N facility targeted for PMs."
    ::= { vcnCrntPMEntry 1 }


vcnCrntPMShelfIdx OBJECT-TYPE
    SYNTAX       INTEGER (1|11|21|31)
    MAX-ACCESS   not-accessible
    STATUS       current
    DESCRIPTION  "The number of the shelf of the VC-N facility targeted for
                  PMs."
    ::= { vcnCrntPMEntry 2 }


vcnCrntPMSlotIdx OBJECT-TYPE
    SYNTAX       INTEGER (1..20)
    MAX-ACCESS   not-accessible
    STATUS       current
    DESCRIPTION  "The number of the slot of the VC-N facility targeted for PMs."
    ::= { vcnCrntPMEntry 3 }


vcnCrntPMPortIdx OBJECT-TYPE
    SYNTAX       INTEGER (1..2)
    MAX-ACCESS   not-accessible
    STATUS       current
    DESCRIPTION  "The number of the port on the circuit pack of the VC-N
                  facility targeted for PMs."
    ::= { vcnCrntPMEntry 4 }


vcnCrntPMIdx OBJECT-TYPE
    SYNTAX       INTEGER (1..64)
    MAX-ACCESS   not-accessible
    STATUS       current
    DESCRIPTION  "The channel number of the VC-N facility targeted for PMs."
    ::= { vcnCrntPMEntry 5 }


vcnCrntPMIntervalTypeIdx OBJECT-TYPE
    SYNTAX       PMIntervalType
    MAX-ACCESS   not-accessible
    STATUS       current
    DESCRIPTION  "The type of PM bin according to interval length."
    ::= { vcnCrntPMEntry 6 }


vcnCrntPMHPEBValue OBJECT-TYPE
    SYNTAX       Unsigned32 
    MAX-ACCESS   read-write
    STATUS       current
    DESCRIPTION  "The count of high order path errored blocks."
    ::= { vcnCrntPMEntry 7 }


vcnCrntPMHPEBTimeStamp OBJECT-TYPE
    SYNTAX       DateAndTime
    MAX-ACCESS   read-only
    STATUS       current
    DESCRIPTION  "The date and time stamp of the high order path errored blocks
                  value."
    ::= { vcnCrntPMEntry 8 }


vcnCrntPMHPEBValidity OBJECT-TYPE
    SYNTAX       PMValidity
    MAX-ACCESS   read-only
    STATUS       current
    DESCRIPTION  "Indicates the validity of the provided high order path errored
                  blocks value."
    ::= { vcnCrntPMEntry 9 }


vcnCrntPMHPBBEValue OBJECT-TYPE
    SYNTAX       Unsigned32 
    MAX-ACCESS   read-write
    STATUS       current
    DESCRIPTION  "The count of high order path background block errors."
    ::= { vcnCrntPMEntry 10 }


vcnCrntPMHPBBETimeStamp OBJECT-TYPE
    SYNTAX       DateAndTime
    MAX-ACCESS   read-only
    STATUS       current
    DESCRIPTION  "The date and time stamp of the high order path background
                  block errors value."
    ::= { vcnCrntPMEntry 11 }


vcnCrntPMHPBBEValidity OBJECT-TYPE
    SYNTAX       PMValidity
    MAX-ACCESS   read-only
    STATUS       current
    DESCRIPTION  "Indicates the validity of the provided high order path
                  background block errors value."
    ::= { vcnCrntPMEntry 12 }


vcnCrntPMHPESValue OBJECT-TYPE
    SYNTAX       Unsigned32
    MAX-ACCESS   read-write
    STATUS       current
    DESCRIPTION  "The count of high order path errored seconds."
    ::= { vcnCrntPMEntry 13 }


vcnCrntPMHPESTimeStamp OBJECT-TYPE
    SYNTAX       DateAndTime
    MAX-ACCESS   read-only
    STATUS       current
    DESCRIPTION  "The date and time stamp of the high order path errored seconds
                  value."
    ::= { vcnCrntPMEntry 14 }


vcnCrntPMHPESValidity OBJECT-TYPE
    SYNTAX       PMValidity
    MAX-ACCESS   read-only
    STATUS       current
    DESCRIPTION  "Indicates the validity of the provided high order path errored
                  seconds value."
    ::= { vcnCrntPMEntry 15 }


vcnCrntPMHPSESValue OBJECT-TYPE
    SYNTAX       Unsigned32
    MAX-ACCESS   read-write
    STATUS       current
    DESCRIPTION  "The count of high order path severely errored seconds."
    ::= { vcnCrntPMEntry 16 }


vcnCrntPMHPSESTimeStamp OBJECT-TYPE
    SYNTAX       DateAndTime
    MAX-ACCESS   read-only
    STATUS       current
    DESCRIPTION  "The date and time stamp of the high order path severely
                  errored seconds value."
    ::= { vcnCrntPMEntry 17 }


vcnCrntPMHPSESValidity OBJECT-TYPE
    SYNTAX       PMValidity
    MAX-ACCESS   read-only
    STATUS       current
    DESCRIPTION  "Indicates the validity of the provided high order path
                  severely errored seconds value."
    ::= { vcnCrntPMEntry 18 }


vcnCrntPMHPUASValue OBJECT-TYPE
    SYNTAX       Unsigned32
    MAX-ACCESS   read-write
    STATUS       current
    DESCRIPTION  "The count of high order path unavailable seconds."
    ::= { vcnCrntPMEntry 19 }


vcnCrntPMHPUASTimeStamp OBJECT-TYPE
    SYNTAX       DateAndTime
    MAX-ACCESS   read-only
    STATUS       current
    DESCRIPTION  "The date and time stamp of the high order path unavailable
                  seconds value."
    ::= { vcnCrntPMEntry 20 }


vcnCrntPMHPUASValidity OBJECT-TYPE
    SYNTAX       PMValidity
    MAX-ACCESS   read-only
    STATUS       current
    DESCRIPTION  "Indicates the validity of the provided high order path
                  unavailable seconds value."
    ::= { vcnCrntPMEntry 21 }


vcnCrntPMHPEBInitialize OBJECT-TYPE
    SYNTAX       InitializeCmd
    MAX-ACCESS   read-write
    STATUS       current
    DESCRIPTION  "Used to initialize the value of the vcnCrntPMHPEBValue object
                  to 0."
    ::= { vcnCrntPMEntry 22 }


vcnCrntPMHPBBEInitialize OBJECT-TYPE
    SYNTAX       InitializeCmd
    MAX-ACCESS   read-write
    STATUS       current
    DESCRIPTION  "Used to initialize the value of the vcnCrntPMHPBBEValue object
                  to 0."
    ::= { vcnCrntPMEntry 23 }


vcnCrntPMHPESInitialize OBJECT-TYPE
    SYNTAX       InitializeCmd
    MAX-ACCESS   read-write
    STATUS       current
    DESCRIPTION  "Used to initialize the value of the vcnCrntPMHPESValue object
                  to 0."
    ::= { vcnCrntPMEntry 24 }


vcnCrntPMHPSESInitialize OBJECT-TYPE
    SYNTAX       InitializeCmd
    MAX-ACCESS   read-write
    STATUS       current
    DESCRIPTION  "Used to initialize the value of the vcnCrntPMHPSESValue object
                  to 0."
    ::= { vcnCrntPMEntry 25 }


vcnCrntPMHPUASInitialize OBJECT-TYPE
    SYNTAX       InitializeCmd
    MAX-ACCESS   read-write
    STATUS       current
    DESCRIPTION  "Used to initialize the value of the vcnCrntPMHPUASValue object
                  to 0."
    ::= { vcnCrntPMEntry 26 }



-----------------------------------------------------------------------
-- Objects used to retrieve historical SDH VC-N
-- Performance Monitoring statistics
-- 
-- A listing of historical SDH VC-N PM values is contained in the 
-- vcnHistPMTable of the BTI 7000 Series MIB. When retrieved, this 
-- table provides one row for each set of historical SDH VC-N PM data.
-- 
-- The following table lists the objects in each entry of the 
-- vcnHistPMTable.
-----------------------------------------------------------------------


vcnHistPMTable OBJECT-TYPE
    SYNTAX       SEQUENCE OF VcnHistPMEntry
    MAX-ACCESS   not-accessible
    STATUS       current
    DESCRIPTION  "A table of historical performance monitoring statistics
                  collected for the SDH VC-N facilities on the NE."
    ::= { performance 18 }


vcnHistPMEntry OBJECT-TYPE
    SYNTAX       VcnHistPMEntry
    MAX-ACCESS   not-accessible
    STATUS       current
    DESCRIPTION  "The row entry object of the SDH VC-N historical performance
                  monitoring table. Each row of this table contains a full set
                  of PM statistics and related data for a historical measurement
                  interval for a given VC-N facility."
    INDEX        { vcnHistPMTypeIdx,
                   vcnHistPMShelfIdx,
                   vcnHistPMSlotIdx,
                   vcnHistPMPortIdx,
                   vcnHistPMIdx,
                   vcnHistPMIntervalTypeIdx,
                   vcnHistPMIntervalIdx }
    ::= { vcnHistPMTable 1 }


VcnHistPMEntry ::= SEQUENCE { vcnHistPMTypeIdx          VcnType,
                              vcnHistPMShelfIdx         INTEGER,
                              vcnHistPMSlotIdx          INTEGER,
                              vcnHistPMPortIdx          INTEGER,
                              vcnHistPMIdx              INTEGER,
                              vcnHistPMIntervalTypeIdx  PMIntervalType,
                              vcnHistPMIntervalIdx      INTEGER,
                              vcnHistPMHPEBValue        Unsigned32,
                              vcnHistPMHPEBTimeStamp    DateAndTime,
                              vcnHistPMHPEBValidity     PMValidity,
                              vcnHistPMHPBBEValue       Unsigned32,
                              vcnHistPMHPBBETimeStamp   DateAndTime,
                              vcnHistPMHPBBEValidity    PMValidity,
                              vcnHistPMHPESValue        Unsigned32,
                              vcnHistPMHPESTimeStamp    DateAndTime,
                              vcnHistPMHPESValidity     PMValidity,
                              vcnHistPMHPSESValue       Unsigned32,
                              vcnHistPMHPSESTimeStamp   DateAndTime,
                              vcnHistPMHPSESValidity    PMValidity,
                              vcnHistPMHPUASValue       Unsigned32,
                              vcnHistPMHPUASTimeStamp   DateAndTime,
                              vcnHistPMHPUASValidity    PMValidity,
                              vcnHistPMHPEBInitialize   InitializeCmd,
                              vcnHistPMHPBBEInitialize  InitializeCmd,
                              vcnHistPMHPESInitialize   InitializeCmd,
                              vcnHistPMHPSESInitialize  InitializeCmd,
                              vcnHistPMHPUASInitialize  InitializeCmd }


vcnHistPMTypeIdx OBJECT-TYPE
    SYNTAX       VcnType
    MAX-ACCESS   not-accessible
    STATUS       current
    DESCRIPTION  "The type of the VC-N facility targeted for PMs."
    ::= { vcnHistPMEntry 1 }


vcnHistPMShelfIdx OBJECT-TYPE
    SYNTAX       INTEGER (1|11|21|31)
    MAX-ACCESS   not-accessible
    STATUS       current
    DESCRIPTION  "The number of the shelf of the VC-N facility targeted for
                  PMs."
    ::= { vcnHistPMEntry 2 }


vcnHistPMSlotIdx OBJECT-TYPE
    SYNTAX       INTEGER (1..20)
    MAX-ACCESS   not-accessible
    STATUS       current
    DESCRIPTION  "The number of the slot of the VC-N facility targeted for PMs."
    ::= { vcnHistPMEntry 3 }


vcnHistPMPortIdx OBJECT-TYPE
    SYNTAX       INTEGER (1..2)
    MAX-ACCESS   not-accessible
    STATUS       current
    DESCRIPTION  "The number of the port on the circuit pack of the VC-N
                  facility targeted for PMs."
    ::= { vcnHistPMEntry 4 }


vcnHistPMIdx OBJECT-TYPE
    SYNTAX       INTEGER (1..64)
    MAX-ACCESS   not-accessible
    STATUS       current
    DESCRIPTION  "The channel number of the VC-N facility targeted for PMs."
    ::= { vcnHistPMEntry 5 }


vcnHistPMIntervalTypeIdx OBJECT-TYPE
    SYNTAX       PMIntervalType
    MAX-ACCESS   not-accessible
    STATUS       current
    DESCRIPTION  "The type of PM bin according to interval length."
    ::= { vcnHistPMEntry 6 }


vcnHistPMIntervalIdx OBJECT-TYPE
    SYNTAX       INTEGER (1..96)
    MAX-ACCESS   not-accessible
    STATUS       current
    DESCRIPTION  "The specific PM bin number. The range is 1 to 96 for the
                  15-minute historical bins. For the 1-day historical bin, the
                  value is 1."
    ::= { vcnHistPMEntry 7 }


vcnHistPMHPEBValue OBJECT-TYPE
    SYNTAX       Unsigned32
    MAX-ACCESS   read-write
    STATUS       current
    DESCRIPTION  "The count of high order path errored blocks."
    ::= { vcnHistPMEntry 8 }


vcnHistPMHPEBTimeStamp OBJECT-TYPE
    SYNTAX       DateAndTime
    MAX-ACCESS   read-only
    STATUS       current
    DESCRIPTION  "The date and time stamp of the high order path errored blocks
                  value."
    ::= { vcnHistPMEntry 9 }


vcnHistPMHPEBValidity OBJECT-TYPE
    SYNTAX       PMValidity
    MAX-ACCESS   read-only
    STATUS       current
    DESCRIPTION  "Indicates the validity of the provided high order path errored
                  blocks value."
    ::= { vcnHistPMEntry 10 }


vcnHistPMHPBBEValue OBJECT-TYPE
    SYNTAX       Unsigned32
    MAX-ACCESS   read-write
    STATUS       current
    DESCRIPTION  "The count of high order path background block errors."
    ::= { vcnHistPMEntry 11 }


vcnHistPMHPBBETimeStamp OBJECT-TYPE
    SYNTAX       DateAndTime
    MAX-ACCESS   read-only
    STATUS       current
    DESCRIPTION  "The date and time stamp of the high order path background
                  block errors value."
    ::= { vcnHistPMEntry 12 }


vcnHistPMHPBBEValidity OBJECT-TYPE
    SYNTAX       PMValidity
    MAX-ACCESS   read-only
    STATUS       current
    DESCRIPTION  "Indicates the validity of the provided high order path
                  background block errors value."
    ::= { vcnHistPMEntry 13 }


vcnHistPMHPESValue OBJECT-TYPE
    SYNTAX       Unsigned32
    MAX-ACCESS   read-write
    STATUS       current
    DESCRIPTION  "The count of high order path errored seconds."
    ::= { vcnHistPMEntry 14 }


vcnHistPMHPESTimeStamp OBJECT-TYPE
    SYNTAX       DateAndTime
    MAX-ACCESS   read-only
    STATUS       current
    DESCRIPTION  "The date and time stamp of the high order path errored seconds
                  value."
    ::= { vcnHistPMEntry 15 }


vcnHistPMHPESValidity OBJECT-TYPE
    SYNTAX       PMValidity
    MAX-ACCESS   read-only
    STATUS       current
    DESCRIPTION  "Indicates the validity of the high order path errored seconds
                  value."
    ::= { vcnHistPMEntry 16 }


vcnHistPMHPSESValue OBJECT-TYPE
    SYNTAX       Unsigned32
    MAX-ACCESS   read-write
    STATUS       current
    DESCRIPTION  "The count of high order path severely errored seconds."
    ::= { vcnHistPMEntry 17 }


vcnHistPMHPSESTimeStamp OBJECT-TYPE
    SYNTAX       DateAndTime
    MAX-ACCESS   read-only
    STATUS       current
    DESCRIPTION  "The date and time stamp of the high order path severely
                  errored seconds value."
    ::= { vcnHistPMEntry 18 }


vcnHistPMHPSESValidity OBJECT-TYPE
    SYNTAX       PMValidity
    MAX-ACCESS   read-only
    STATUS       current
    DESCRIPTION  "Indicates the validity of the provided high order path
                  severely errored seconds value."
    ::= { vcnHistPMEntry 19 }


vcnHistPMHPUASValue OBJECT-TYPE
    SYNTAX       Unsigned32
    MAX-ACCESS   read-write
    STATUS       current
    DESCRIPTION  "The count of high order path unavailable seconds."
    ::= { vcnHistPMEntry 20 }


vcnHistPMHPUASTimeStamp OBJECT-TYPE
    SYNTAX       DateAndTime
    MAX-ACCESS   read-only
    STATUS       current
    DESCRIPTION  "The date and time stamp of the high order path unavailable
                  seconds value."
    ::= { vcnHistPMEntry 21 }


vcnHistPMHPUASValidity OBJECT-TYPE
    SYNTAX       PMValidity
    MAX-ACCESS   read-only
    STATUS       current
    DESCRIPTION  "Indicates the validity of the provided high order path
                  unavailable seconds value."
    ::= { vcnHistPMEntry 22 }


vcnHistPMHPEBInitialize OBJECT-TYPE
    SYNTAX       InitializeCmd
    MAX-ACCESS   read-write
    STATUS       current
    DESCRIPTION  "Used to initialize the value of the vcnHistPMHPEBValue object
                  to 0."
    ::= { vcnHistPMEntry 23 }


vcnHistPMHPBBEInitialize OBJECT-TYPE
    SYNTAX       InitializeCmd
    MAX-ACCESS   read-write
    STATUS       current
    DESCRIPTION  "Used to initialize the value of the vcnHistPMHPBBEValue object
                  to 0."
    ::= { vcnHistPMEntry 24 }


vcnHistPMHPESInitialize OBJECT-TYPE
    SYNTAX       InitializeCmd
    MAX-ACCESS   read-write
    STATUS       current
    DESCRIPTION  "Used to initialize the value of the vcnHistPMHPESValue object
                  to 0."
    ::= { vcnHistPMEntry 25 }


vcnHistPMHPSESInitialize OBJECT-TYPE
    SYNTAX       InitializeCmd
    MAX-ACCESS   read-write
    STATUS       current
    DESCRIPTION  "Used to initialize the value of the vcnHistPMHPSESValue object
                  to 0."
    ::= { vcnHistPMEntry 26 }


vcnHistPMHPUASInitialize OBJECT-TYPE
    SYNTAX       InitializeCmd
    MAX-ACCESS   read-write
    STATUS       current
    DESCRIPTION  "Used to initialize the value of the vcnHistPMHPUASValue object
                  to 0."
    ::= { vcnHistPMEntry 27 }



-----------------------------------------------------------------------
-- Objects used to manage SDH VC-N Performance
-- Monitoring Threshold Levels
-- 
-- A listing of SDH VC-N PM threshold levels is contained in the
-- VcnPMThresholdByPortEntry of the BTI-7000-MIB. When retrieved, this 
-- table provides one row for each set of SDH VC-N PM threshold data.
-- 
-- The following table lists the objects in each entry of the 
-- VcnPMThresholdByPortEntry.
-----------------------------------------------------------------------


vcnPMThresholdByPortTable OBJECT-TYPE
    SYNTAX       SEQUENCE OF VcnPMThresholdByPortEntry
    MAX-ACCESS   not-accessible
    STATUS       current
    DESCRIPTION  "A table of threshold levels for performance monitoring counter
                  values on SDH VC-N facilities, that are used in the generation
                  of threshold crossing alerts. The VC-N threshold settings will
                  be the same for all channels on a given STM-N facility port."
    ::= { performance 19 }


vcnPMThresholdByPortEntry OBJECT-TYPE
    SYNTAX       VcnPMThresholdByPortEntry
    MAX-ACCESS   not-accessible
    STATUS       current
    DESCRIPTION  "The row entry object of the SDH STM-N performance monitoring
                  threshold by port table. Each row of this table contains a set
                  of PM thresholds for a given interval type that applies to all
                  the VC-N channels on an STM-N facility port."
    INDEX        { vcnPMThresholdByPortTypeIdx,
                   vcnPMThresholdByPortShelfIdx,
                   vcnPMThresholdByPortSlotIdx,
                   vcnPMThresholdByPortIdx,
                   vcnPMThresholdByPortIntervalTypeIdx }
    ::= { vcnPMThresholdByPortTable 1 }


VcnPMThresholdByPortEntry ::= SEQUENCE { vcnPMThresholdByPortTypeIdx          VcnType,
                                         vcnPMThresholdByPortShelfIdx         INTEGER,
                                         vcnPMThresholdByPortSlotIdx          INTEGER,
                                         vcnPMThresholdByPortIdx              INTEGER,
                                         vcnPMThresholdByPortIntervalTypeIdx  PMIntervalType,
                                         vcnPMThresholdByPortHPEBValue        Unsigned32,
                                         vcnPMThresholdByPortHPBBEValue       Unsigned32,
                                         vcnPMThresholdByPortHPESValue        Unsigned32,
                                         vcnPMThresholdByPortHPSESValue       Unsigned32,
                                         vcnPMThresholdByPortHPUASValue       Unsigned32 }
      

vcnPMThresholdByPortTypeIdx OBJECT-TYPE
    SYNTAX       VcnType
    MAX-ACCESS   not-accessible
    STATUS       current
    DESCRIPTION  "The type of the VC-N facility targeted for PM thresholds."
    ::= { vcnPMThresholdByPortEntry 1 }


vcnPMThresholdByPortShelfIdx OBJECT-TYPE
    SYNTAX       INTEGER (1|11|21|31)
    MAX-ACCESS   not-accessible
    STATUS       current
    DESCRIPTION  "The shelf number of the VC-N facilities targeted for PM
                  thresholds."
    ::= { vcnPMThresholdByPortEntry 2 }


vcnPMThresholdByPortSlotIdx OBJECT-TYPE
    SYNTAX       INTEGER (1..20)
    MAX-ACCESS   not-accessible
    STATUS       current
    DESCRIPTION  "The slot number of the VC-N facilities targeted for PM
                  thresholds."
    ::= { vcnPMThresholdByPortEntry 3 }


vcnPMThresholdByPortIdx OBJECT-TYPE
    SYNTAX       INTEGER (1..2)
    MAX-ACCESS   not-accessible
    STATUS       current
    DESCRIPTION  "The number of the port on the circuit pack of the VC-N
                  facilities targeted for PM thresholds."
    ::= { vcnPMThresholdByPortEntry 4 }


vcnPMThresholdByPortIntervalTypeIdx OBJECT-TYPE
    SYNTAX       PMIntervalType 
    MAX-ACCESS   not-accessible
    STATUS       current
    DESCRIPTION  "The type of PM bin according to interval length. Thresholds
                  are supported for the 15-minute and 1-day PM bins only."
    ::= { vcnPMThresholdByPortEntry 5 }


vcnPMThresholdByPortHPEBValue OBJECT-TYPE
    SYNTAX       Unsigned32
    MAX-ACCESS   read-write
    STATUS       current
    DESCRIPTION  "The threshold for the count of high order path errored
                  blocks."
    ::= { vcnPMThresholdByPortEntry 6 }


vcnPMThresholdByPortHPBBEValue OBJECT-TYPE
    SYNTAX       Unsigned32
    MAX-ACCESS   read-write
    STATUS       current
    DESCRIPTION  "The threshold for the count of high order path background
                  block errors."
    ::= { vcnPMThresholdByPortEntry 7 }


vcnPMThresholdByPortHPESValue OBJECT-TYPE
    SYNTAX       Unsigned32
    MAX-ACCESS   read-write
    STATUS       current
    DESCRIPTION  "The threshold for the count of high order path errored
                  seconds."
    ::= { vcnPMThresholdByPortEntry 8 }


vcnPMThresholdByPortHPSESValue OBJECT-TYPE
    SYNTAX       Unsigned32
    MAX-ACCESS   read-write
    STATUS       current
    DESCRIPTION  "The threshold for the count of high order path severely
                  errored seconds."
    ::= { vcnPMThresholdByPortEntry 9 }


vcnPMThresholdByPortHPUASValue OBJECT-TYPE
    SYNTAX       Unsigned32
    MAX-ACCESS   read-write
    STATUS       current
    DESCRIPTION  "The threshold for the count of high order path unavailable
                  seconds."
    ::= { vcnPMThresholdByPortEntry 10 }



-----------------------------------------------------------------------
-- Objects used to retrieve current Gigabit Ethernet
-- Performance Monitoring statistics
-- 
-- A listing of current Gigabit Ethernet PM values is contained in the 
-- geCrntPMTable of the BTI 7000 Series MIB. When retrieved, this 
-- table provides one row for each set of current Gigabit Ethernet 
-- PM data.
-- 
-- The following table lists the objects in each entry of the 
-- geCrntPMTable.
-----------------------------------------------------------------------


geCrntPMTable OBJECT-TYPE
    SYNTAX       SEQUENCE OF GeCrntPMEntry
    MAX-ACCESS   not-accessible
    STATUS       current
    DESCRIPTION  "A table of current performance monitoring statistics collected
                  for the Gigabit Ethernet facilities on the NE."
    ::= { performance 20 }


geCrntPMEntry OBJECT-TYPE
    SYNTAX       GeCrntPMEntry
    MAX-ACCESS   not-accessible
    STATUS       current
    DESCRIPTION  "The row entry object of the Gigabit Ethernet current
                  performance monitoring table. Each row of this table contains
                  a full set of PM statistics and related data for a current
                  measurement interval for a given Gigabit Ethernet facility."
    INDEX        { geCrntPMShelfIdx,
                   geCrntPMSlotIdx,
                   geCrntPMPortIdx,
                   geCrntPMIntervalTypeIdx }
    ::= { geCrntPMTable 1 }


GeCrntPMEntry ::= SEQUENCE { geCrntPMShelfIdx                  INTEGER,
                             geCrntPMSlotIdx                   INTEGER,
                             geCrntPMPortIdx                   INTEGER,
                             geCrntPMIntervalTypeIdx           PMIntervalType,
                             geCrntPMOPRValue                  FixedX10,
                             geCrntPMOPRTimeStamp              DateAndTime,
                             geCrntPMOPRValidity               PMValidity,
                             geCrntPMOPTValue                  FixedX10,
                             geCrntPMOPTTimeStamp              DateAndTime,
                             geCrntPMOPTValidity               PMValidity,
                             geCrntPMTempValue                 INTEGER,
                             geCrntPMTempTimeStamp             DateAndTime,
                             geCrntPMTempValidity              PMValidity,
                             geCrntPMSupplyVoltageValue        FixedX10,
                             geCrntPMSupplyVoltageTimeStamp    DateAndTime,
                             geCrntPMSupplyVoltageValidity     PMValidity,
                             geCrntPMLBCValue                  INTEGER,
                             geCrntPMLBCTimeStamp              DateAndTime,
                             geCrntPMLBCValidity               PMValidity,
                             geCrntPMCVValue                   Unsigned32,
                             geCrntPMCVTimeStamp               DateAndTime,
                             geCrntPMCVValidity                PMValidity,
                             geCrntPMESValue                   Unsigned32,
                             geCrntPMESTimeStamp               DateAndTime,
                             geCrntPMESValidity                PMValidity,
                             geCrntPMSESValue                  Unsigned32,
                             geCrntPMSESTimeStamp              DateAndTime,
                             geCrntPMSESValidity               PMValidity,
                             geCrntPMTFRCRXValue               Unsigned64,
                             geCrntPMTFRCRXTimeStamp           DateAndTime,
                             geCrntPMTFRCRXValidity            PMValidity,
                             geCrntPMTFRCRXInitialize          InitializeCmd,
                             geCrntPMTFRCTXValue               Unsigned64,
                             geCrntPMTFRCTXTimeStamp           DateAndTime,
                             geCrntPMTFRCTXValidity            PMValidity,
                             geCrntPMTFRCTXInitialize          InitializeCmd,
                             geCrntPMFRDRValue                 Unsigned32,
                             geCrntPMFRDRTimeStamp             DateAndTime,
                             geCrntPMFRDRValidity              PMValidity,
                             geCrntPMFCSEValue                 Unsigned32,
                             geCrntPMFCSETimeStamp             DateAndTime,
                             geCrntPMFCSEValidity              PMValidity,
                             geCrntPMTBYCRXValue               Unsigned64,
                             geCrntPMTBYCRXTimeStamp           DateAndTime,
                             geCrntPMTBYCRXValidity            PMValidity,
                             geCrntPMTBYCRXInitialize          InitializeCmd,
                             geCrntPMTBYCTXValue               Unsigned64,
                             geCrntPMTBYCTXTimeStamp           DateAndTime,
                             geCrntPMTBYCTXValidity            PMValidity,
                             geCrntPMTBYCTXInitialize          InitializeCmd,
                             geCrntPMBCSTValue                 Unsigned64,
                             geCrntPMBCSTTimeStamp             DateAndTime,
                             geCrntPMBCSTValidity              PMValidity,
                             geCrntPMBCSTInitialize            InitializeCmd,
                             geCrntPMMCSTValue                 Unsigned64,
                             geCrntPMMCSTTimeStamp             DateAndTime,
                             geCrntPMMCSTValidity              PMValidity,
                             geCrntPMMCSTInitialize            InitializeCmd,
                             geCrntPMSIZE64Value               Unsigned64,
                             geCrntPMSIZE64TimeStamp           DateAndTime,
                             geCrntPMSIZE64Validity            PMValidity,
                             geCrntPMSIZE64Initialize          InitializeCmd,
                             geCrntPMSIZE65To127Value          Unsigned64,
                             geCrntPMSIZE65To127TimeStamp      DateAndTime,
                             geCrntPMSIZE65To127Validity       PMValidity,
                             geCrntPMSIZE65To127Initialize     InitializeCmd,
                             geCrntPMSIZE128To255Value         Unsigned64,
                             geCrntPMSIZE128To255TimeStamp     DateAndTime,
                             geCrntPMSIZE128To255Validity      PMValidity,
                             geCrntPMSIZE128To255Initialize    InitializeCmd,
                             geCrntPMSIZE256To511Value         Unsigned64,
                             geCrntPMSIZE256To511TimeStamp     DateAndTime,
                             geCrntPMSIZE256To511Validity      PMValidity,
                             geCrntPMSIZE256To511Initialize    InitializeCmd,
                             geCrntPMSIZE512To1023Value        Unsigned64,
                             geCrntPMSIZE512To1023TimeStamp    DateAndTime,
                             geCrntPMSIZE512To1023Validity     PMValidity,
                             geCrntPMSIZE512To1023Initialize   InitializeCmd,
                             geCrntPMSIZE1024To1518Value       Unsigned64,
                             geCrntPMSIZE1024To1518TimeStamp   DateAndTime,
                             geCrntPMSIZE1024To1518Validity    PMValidity,
                             geCrntPMSIZE1024To1518Initialize  InitializeCmd,
                             geCrntPMSIZEOver1518Value         Unsigned64,
                             geCrntPMSIZEOver1518TimeStamp     DateAndTime,
                             geCrntPMSIZEOver1518Validity      PMValidity,
                             geCrntPMSIZEOver1518Initialize    InitializeCmd,
                             geCrntPMTPFCRXValue               Unsigned64,
                             geCrntPMTPFCRXTimeStamp           DateAndTime,
                             geCrntPMTPFCRXValidity            PMValidity,
                             geCrntPMTPFCRXInitialize          InitializeCmd,
                             geCrntPMTPFCTXValue               Unsigned64,
                             geCrntPMTPFCTXTimeStamp           DateAndTime,
                             geCrntPMTPFCTXValidity            PMValidity,
                             geCrntPMTPFCTXInitialize          InitializeCmd,
                             geCrntPMUSIZEValue                Unsigned32,
                             geCrntPMUSIZETimeStamp            DateAndTime,
                             geCrntPMUSIZEValidity             PMValidity,
                             geCrntPMOSIZEValue                Unsigned32,
                             geCrntPMOSIZETimeStamp            DateAndTime,
                             geCrntPMOSIZEValidity             PMValidity,
                             geCrntPMFRGTValue                 Unsigned32,
                             geCrntPMFRGTTimeStamp             DateAndTime,
                             geCrntPMFRGTValidity              PMValidity,
                             geCrntPMJABRValue                 Unsigned32,
                             geCrntPMJABRTimeStamp             DateAndTime,
                             geCrntPMJABRValidity              PMValidity,
                             geCrntPMCVInitialize              InitializeCmd,
                             geCrntPMESInitialize              InitializeCmd,
                             geCrntPMSESInitialize             InitializeCmd,
                             geCrntPMFCSEInitialize            InitializeCmd,
                             geCrntPMFRDRInitialize            InitializeCmd,
                             geCrntPMUSIZEInitialize           InitializeCmd,
                             geCrntPMOSIZEInitialize           InitializeCmd,
                             geCrntPMFRGTInitialize            InitializeCmd,
                             geCrntPMJABRInitialize            InitializeCmd,
                             geCrntPMUASValue                  Unsigned32,
                             geCrntPMUASTimeStamp              DateAndTime,
                             geCrntPMUASValidity               PMValidity,
                             geCrntPMUASInitialize             InitializeCmd,
                             geCrntPMOPRMinValue               FixedX10,
                             geCrntPMOPRMinTimeStamp           DateAndTime,
                             geCrntPMOPRMinValidity            PMValidity,
                             geCrntPMOPRMinInitialize          InitializeCmd,
                             geCrntPMOPRMaxValue               FixedX10,
                             geCrntPMOPRMaxTimeStamp           DateAndTime,
                             geCrntPMOPRMaxValidity            PMValidity,
                             geCrntPMOPRMaxInitialize          InitializeCmd,
                             geCrntPMOPRAvgValue               FixedX10,
                             geCrntPMOPRAvgTimeStamp           DateAndTime,
                             geCrntPMOPRAvgValidity            PMValidity,
                             geCrntPMOPRAvgInitialize          InitializeCmd,
                             geCrntPMOPTMinValue               FixedX10,
                             geCrntPMOPTMinTimeStamp           DateAndTime,
                             geCrntPMOPTMinValidity            PMValidity,
                             geCrntPMOPTMinInitialize          InitializeCmd,
                             geCrntPMOPTMaxValue               FixedX10,
                             geCrntPMOPTMaxTimeStamp           DateAndTime,
                             geCrntPMOPTMaxValidity            PMValidity,
                             geCrntPMOPTMaxInitialize          InitializeCmd,
                             geCrntPMOPTAvgValue               FixedX10,
                             geCrntPMOPTAvgTimeStamp           DateAndTime,
                             geCrntPMOPTAvgValidity            PMValidity,
                             geCrntPMOPTAvgInitialize          InitializeCmd }


geCrntPMShelfIdx OBJECT-TYPE
    SYNTAX       INTEGER (1|11|21|31)
    MAX-ACCESS   not-accessible
    STATUS       current
    DESCRIPTION  "The number of the shelf on which the GE facility targeted for
                  PMs is provisioned."
    ::= { geCrntPMEntry 1 }


geCrntPMSlotIdx OBJECT-TYPE
    SYNTAX       INTEGER (1..20)
    MAX-ACCESS   not-accessible
    STATUS       current
    DESCRIPTION  "The number of the slot within which the GE facility targeted
                  for PMs is provisioned."
    ::= { geCrntPMEntry 2 }


geCrntPMPortIdx OBJECT-TYPE
    SYNTAX       INTEGER (3..12)
    MAX-ACCESS   not-accessible
    STATUS       current
    DESCRIPTION  "The number of the port on the circuit pack on which the GE
                  facility targeted for PMs is provisioned."
    ::= { geCrntPMEntry 3 }


geCrntPMIntervalTypeIdx OBJECT-TYPE
    SYNTAX       PMIntervalType
    MAX-ACCESS   not-accessible
    STATUS       current
    DESCRIPTION  "The type of PM bin according to interval length."
    ::= { geCrntPMEntry 4 }


geCrntPMOPRValue OBJECT-TYPE
    SYNTAX       FixedX10
    UNITS        "dBm/10"
    MAX-ACCESS   read-only
    STATUS       current
    DESCRIPTION  "The optical power received on the input of the GE facility
                  port."
    ::= { geCrntPMEntry 5 }


geCrntPMOPRTimeStamp OBJECT-TYPE
    SYNTAX       DateAndTime
    MAX-ACCESS   read-only
    STATUS       current
    DESCRIPTION  "The date and time stamp of the optical power received value."
    ::= { geCrntPMEntry 6 }


geCrntPMOPRValidity OBJECT-TYPE
    SYNTAX       PMValidity
    MAX-ACCESS   read-only
    STATUS       current
    DESCRIPTION  "Indicates the validity of the provided optical power received
                  value."
    ::= { geCrntPMEntry 7 }


geCrntPMOPTValue OBJECT-TYPE
    SYNTAX       FixedX10
    UNITS        "dBm/10"
    MAX-ACCESS   read-only
    STATUS       current
    DESCRIPTION  "The optical power transmitted at the output of the GE facility
                  port."
    ::= { geCrntPMEntry 8 }


geCrntPMOPTTimeStamp OBJECT-TYPE
    SYNTAX       DateAndTime
    MAX-ACCESS   read-only
    STATUS       current
    DESCRIPTION  "The date and time stamp of the optical power transmitted
                  value."
    ::= { geCrntPMEntry 9 }


geCrntPMOPTValidity OBJECT-TYPE
    SYNTAX       PMValidity
    MAX-ACCESS   read-only
    STATUS       current
    DESCRIPTION  "Indicates the validity of the provided optical power
                  transmitted value."
    ::= { geCrntPMEntry 10 }


geCrntPMTempValue OBJECT-TYPE
    SYNTAX       INTEGER (-32768..32767)
    UNITS        "degrees Celsius"
    MAX-ACCESS   read-only
    STATUS       current
    DESCRIPTION  "The temperature measured on the GE facility port."
    ::= { geCrntPMEntry 11 }


geCrntPMTempTimeStamp OBJECT-TYPE
    SYNTAX       DateAndTime
    MAX-ACCESS   read-only
    STATUS       current
    DESCRIPTION  "The date and time stamp of the temperature value."
    ::= { geCrntPMEntry 12 }


geCrntPMTempValidity OBJECT-TYPE
    SYNTAX       PMValidity
    MAX-ACCESS   read-only
    STATUS       current
    DESCRIPTION  "Indicates the validity of the provided temperature value."
    ::= { geCrntPMEntry 13 }


geCrntPMSupplyVoltageValue OBJECT-TYPE
    SYNTAX       FixedX10
    UNITS        "mVolts/10"
    MAX-ACCESS   read-only
    STATUS       current
    DESCRIPTION  "The supply voltage measured on the GE facility port."
    ::= { geCrntPMEntry 14 }


geCrntPMSupplyVoltageTimeStamp OBJECT-TYPE
    SYNTAX       DateAndTime
    MAX-ACCESS   read-only
    STATUS       current
    DESCRIPTION  "The date and time stamp of the supply voltage value."
    ::= { geCrntPMEntry 15 }


geCrntPMSupplyVoltageValidity OBJECT-TYPE
    SYNTAX       PMValidity
    MAX-ACCESS   read-only
    STATUS       current
    DESCRIPTION  "Indicates the validity of the provided supply voltage value."
    ::= { geCrntPMEntry 16 }


geCrntPMLBCValue OBJECT-TYPE
    SYNTAX       INTEGER (-32768..32767)
    UNITS        "mAmp"
    MAX-ACCESS   read-only
    STATUS       current
    DESCRIPTION  "The laser bias current measured on the GE facility port."
    ::= { geCrntPMEntry 17 }


geCrntPMLBCTimeStamp OBJECT-TYPE
    SYNTAX       DateAndTime
    MAX-ACCESS   read-only
    STATUS       current
    DESCRIPTION  "The date and time stamp of the laser bias current value."
    ::= { geCrntPMEntry 18 }


geCrntPMLBCValidity OBJECT-TYPE
    SYNTAX       PMValidity
    MAX-ACCESS   read-only
    STATUS       current
    DESCRIPTION  "Indicates the validity of the provided laser bias current
                  value."
    ::= { geCrntPMEntry 19 }


geCrntPMCVValue OBJECT-TYPE
    SYNTAX       Unsigned32 
    MAX-ACCESS   read-write
    STATUS       current
    DESCRIPTION  "The count of Gigabit Ethernet 8B/10B coding violations."
    ::= { geCrntPMEntry 20 }


geCrntPMCVTimeStamp OBJECT-TYPE
    SYNTAX       DateAndTime
    MAX-ACCESS   read-only
    STATUS       current
    DESCRIPTION  "The date and time stamp of the GE coding violations value."
    ::= { geCrntPMEntry 21 }


geCrntPMCVValidity OBJECT-TYPE
    SYNTAX       PMValidity
    MAX-ACCESS   read-only
    STATUS       current
    DESCRIPTION  "Indicates the validity of the provided GE coding violations
                  value."
    ::= { geCrntPMEntry 22 }


geCrntPMESValue OBJECT-TYPE
    SYNTAX       Unsigned32
    MAX-ACCESS   read-write
    STATUS       current
    DESCRIPTION  "The count of GE errored seconds."
    ::= { geCrntPMEntry 23 }


geCrntPMESTimeStamp OBJECT-TYPE
    SYNTAX       DateAndTime
    MAX-ACCESS   read-only
    STATUS       current
    DESCRIPTION  "The date and time stamp of the GE errored seconds value."
    ::= { geCrntPMEntry 24 }


geCrntPMESValidity OBJECT-TYPE
    SYNTAX       PMValidity
    MAX-ACCESS   read-only
    STATUS       current
    DESCRIPTION  "Indicates the validity of the provided GE errored seconds
                  value."
    ::= { geCrntPMEntry 25 }


geCrntPMSESValue OBJECT-TYPE
    SYNTAX       Unsigned32
    MAX-ACCESS   read-write
    STATUS       current
    DESCRIPTION  "The count of GE severely errored seconds."
    ::= { geCrntPMEntry 26 }


geCrntPMSESTimeStamp OBJECT-TYPE
    SYNTAX       DateAndTime
    MAX-ACCESS   read-only
    STATUS       current
    DESCRIPTION  "The date and time stamp of the GE severely errored seconds
                  value."
    ::= { geCrntPMEntry 27 }


geCrntPMSESValidity OBJECT-TYPE
    SYNTAX       PMValidity
    MAX-ACCESS   read-only
    STATUS       current
    DESCRIPTION  "Indicates the validity of the provided GE severely errored
                  seconds value."
    ::= { geCrntPMEntry 28 }


geCrntPMTFRCRXValue OBJECT-TYPE
    SYNTAX       Unsigned64
    MAX-ACCESS   read-only
    STATUS       current
    DESCRIPTION  "The Gigabit Ethernet total received frame count."
    ::= { geCrntPMEntry 29 }


geCrntPMTFRCRXTimeStamp OBJECT-TYPE
    SYNTAX       DateAndTime
    MAX-ACCESS   read-only
    STATUS       current
    DESCRIPTION  "The date and time stamp of the GE total received frame count
                  value."
    ::= { geCrntPMEntry 30 }


geCrntPMTFRCRXValidity OBJECT-TYPE
    SYNTAX       PMValidity
    MAX-ACCESS   read-only
    STATUS       current
    DESCRIPTION  "Indicates the validity of the provided GE total received frame
                  count value."
    ::= { geCrntPMEntry 31 }


geCrntPMTFRCRXInitialize OBJECT-TYPE
    SYNTAX       InitializeCmd
    MAX-ACCESS   read-write
    STATUS       current
    DESCRIPTION  "Used to initialize the value of the geCrntPMTFRCRXValue object
                  to 0."
    ::= { geCrntPMEntry 32 }


geCrntPMTFRCTXValue OBJECT-TYPE
    SYNTAX       Unsigned64
    MAX-ACCESS   read-only
    STATUS       current
    DESCRIPTION  "The Gigabit Ethernet total transmitted frame count."
    ::= { geCrntPMEntry 33 }


geCrntPMTFRCTXTimeStamp OBJECT-TYPE
    SYNTAX       DateAndTime
    MAX-ACCESS   read-only
    STATUS       current
    DESCRIPTION  "The date and time stamp of the GE total transmitted frame
                  count value."
    ::= { geCrntPMEntry 34 }


geCrntPMTFRCTXValidity OBJECT-TYPE
    SYNTAX       PMValidity
    MAX-ACCESS   read-only
    STATUS       current
    DESCRIPTION  "Indicates the validity of the provided GE total transmitted
                  frame count value."
    ::= { geCrntPMEntry 35 }


geCrntPMTFRCTXInitialize OBJECT-TYPE
    SYNTAX       InitializeCmd
    MAX-ACCESS   read-write
    STATUS       current
    DESCRIPTION  "Used to initialize the value of the geCrntPMTFRCTXValue object
                  to 0."
    ::= { geCrntPMEntry 36 }


geCrntPMFRDRValue OBJECT-TYPE
    SYNTAX       Unsigned32
    MAX-ACCESS   read-write
    STATUS       current
    DESCRIPTION  "The count of Gigabit Ethernet discarded frames."
    ::= { geCrntPMEntry 37 }


geCrntPMFRDRTimeStamp OBJECT-TYPE
    SYNTAX       DateAndTime
    MAX-ACCESS   read-only
    STATUS       current
    DESCRIPTION  "The date and time stamp of the GE discarded frames value."
    ::= { geCrntPMEntry 38 }


geCrntPMFRDRValidity OBJECT-TYPE
    SYNTAX       PMValidity
    MAX-ACCESS   read-only
    STATUS       current
    DESCRIPTION  "Indicates the validity of the provided GE discarded frames
                  value."
    ::= { geCrntPMEntry 39 }


geCrntPMFCSEValue OBJECT-TYPE
    SYNTAX       Unsigned32
    MAX-ACCESS   read-write
    STATUS       current
    DESCRIPTION  "The count of Gigabit Ethernet frame checksum errors."
    ::= { geCrntPMEntry 40 }


geCrntPMFCSETimeStamp OBJECT-TYPE
    SYNTAX       DateAndTime
    MAX-ACCESS   read-only
    STATUS       current
    DESCRIPTION  "The date and time stamp of the GE frame checksum errors
                  value."
    ::= { geCrntPMEntry 41 }


geCrntPMFCSEValidity OBJECT-TYPE
    SYNTAX       PMValidity
    MAX-ACCESS   read-only
    STATUS       current
    DESCRIPTION  "Indicates the validity of the provided GE frame checksum
                  errors value."
    ::= { geCrntPMEntry 42 }


geCrntPMTBYCRXValue OBJECT-TYPE
    SYNTAX       Unsigned64
    MAX-ACCESS   read-only
    STATUS       current
    DESCRIPTION  "The Gigabit Ethernet total received byte count."
    ::= { geCrntPMEntry 43 }


geCrntPMTBYCRXTimeStamp OBJECT-TYPE
    SYNTAX       DateAndTime
    MAX-ACCESS   read-only
    STATUS       current
    DESCRIPTION  "The date and time stamp of the GE total received byte count
                  value."
    ::= { geCrntPMEntry 44 }


geCrntPMTBYCRXValidity OBJECT-TYPE
    SYNTAX       PMValidity
    MAX-ACCESS   read-only
    STATUS       current
    DESCRIPTION  "Indicates the validity of the provided GE total received byte
                  count value."
    ::= { geCrntPMEntry 45 }


geCrntPMTBYCRXInitialize OBJECT-TYPE
    SYNTAX       InitializeCmd
    MAX-ACCESS   read-write
    STATUS       current
    DESCRIPTION  "Used to initialize the value of the geCrntPMTBYCRXValue object
                  to 0."
    ::= { geCrntPMEntry 46 }


geCrntPMTBYCTXValue OBJECT-TYPE
    SYNTAX       Unsigned64
    MAX-ACCESS   read-only
    STATUS       current
    DESCRIPTION  "The Gigabit Ethernet total transmitted byte count."
    ::= { geCrntPMEntry 47 }


geCrntPMTBYCTXTimeStamp OBJECT-TYPE
    SYNTAX       DateAndTime
    MAX-ACCESS   read-only
    STATUS       current
    DESCRIPTION  "The date and time stamp of the GE total transmitted byte count
                  value."
    ::= { geCrntPMEntry 48 }


geCrntPMTBYCTXValidity OBJECT-TYPE
    SYNTAX       PMValidity
    MAX-ACCESS   read-only
    STATUS       current
    DESCRIPTION  "Indicates the validity of the provided GE total transmitted
                  byte count value."
    ::= { geCrntPMEntry 49 }


geCrntPMTBYCTXInitialize OBJECT-TYPE
    SYNTAX       InitializeCmd
    MAX-ACCESS   read-write
    STATUS       current
    DESCRIPTION  "Used to initialize the value of the geCrntPMTBYCTXValue object
                  to 0."
    ::= { geCrntPMEntry 50 }


geCrntPMBCSTValue OBJECT-TYPE
    SYNTAX       Unsigned64
    MAX-ACCESS   read-only
    STATUS       current
    DESCRIPTION  "The total number of good frames received that were directed to
                  the broadcast address. Note that this does not include
                  multicast frames."
    ::= { geCrntPMEntry 51 }


geCrntPMBCSTTimeStamp OBJECT-TYPE
    SYNTAX       DateAndTime
    MAX-ACCESS   read-only
    STATUS       current
    DESCRIPTION  "The date and time stamp of the broadcast packets received
                  count value."
    ::= { geCrntPMEntry 52 }


geCrntPMBCSTValidity OBJECT-TYPE
    SYNTAX       PMValidity
    MAX-ACCESS   read-only
    STATUS       current
    DESCRIPTION  "Indicates the validity of the provided broadcast packets
                  received count value."
    ::= { geCrntPMEntry 53 }


geCrntPMBCSTInitialize OBJECT-TYPE
    SYNTAX       InitializeCmd
    MAX-ACCESS   read-write
    STATUS       current
    DESCRIPTION  "Used to initialize the value of the geCrntPMBCSTValue object
                  to 0."
    ::= { geCrntPMEntry 54 }


geCrntPMMCSTValue OBJECT-TYPE
    SYNTAX       Unsigned64
    MAX-ACCESS   read-only
    STATUS       current
    DESCRIPTION  "The total number of good frames received that were directed to
                  a multicast address. Note that this number does not include
                  frames directed to the broadcast address."
    ::= { geCrntPMEntry 55 }


geCrntPMMCSTTimeStamp OBJECT-TYPE
    SYNTAX       DateAndTime
    MAX-ACCESS   read-only
    STATUS       current
    DESCRIPTION  "The date and time stamp of the multicast packets received
                  count value."
    ::= { geCrntPMEntry 56 }


geCrntPMMCSTValidity OBJECT-TYPE
    SYNTAX       PMValidity
    MAX-ACCESS   read-only
    STATUS       current
    DESCRIPTION  "Indicates the validity of the provided multicast packets
                  received count value."
    ::= { geCrntPMEntry 57 }


geCrntPMMCSTInitialize OBJECT-TYPE
    SYNTAX       InitializeCmd
    MAX-ACCESS   read-write
    STATUS       current
    DESCRIPTION  "Used to initialize the value of the geCrntPMMCSTValue object
                  to 0."
    ::= { geCrntPMEntry 58 }


geCrntPMSIZE64Value OBJECT-TYPE
    SYNTAX       Unsigned64
    MAX-ACCESS   read-only
    STATUS       current
    DESCRIPTION  "The total number of 64 byte frames received (excluding framing
                  bits but including FCS octets)."
    ::= { geCrntPMEntry 59 }


geCrntPMSIZE64TimeStamp OBJECT-TYPE
    SYNTAX       DateAndTime
    MAX-ACCESS   read-only
    STATUS       current
    DESCRIPTION  "The date and time stamp of the count of 64-byte packets
                  received."
    ::= { geCrntPMEntry 60 }


geCrntPMSIZE64Validity OBJECT-TYPE
    SYNTAX       PMValidity
    MAX-ACCESS   read-only
    STATUS       current
    DESCRIPTION  "Indicates the validity of the provided count of 64-byte
                  packets packets received."
    ::= { geCrntPMEntry 61 }


geCrntPMSIZE64Initialize OBJECT-TYPE
    SYNTAX       InitializeCmd
    MAX-ACCESS   read-write
    STATUS       current
    DESCRIPTION  "Used to initialize the value of the geCrntPMSIZE64Value object
                  to 0."
    ::= { geCrntPMEntry 62 }


geCrntPMSIZE65To127Value OBJECT-TYPE
    SYNTAX       Unsigned64
    MAX-ACCESS   read-only
    STATUS       current
    DESCRIPTION  "The total number of frames received that are 65 to 127 bytes
                  inclusive in length (excluding framing bits but including FCS
                  octets)."
    ::= { geCrntPMEntry 63 }


geCrntPMSIZE65To127TimeStamp OBJECT-TYPE
    SYNTAX       DateAndTime
    MAX-ACCESS   read-only
    STATUS       current
    DESCRIPTION  "The date and time stamp of the count of packets between 65 and
                  127 bytes."
    ::= { geCrntPMEntry 64 }


geCrntPMSIZE65To127Validity OBJECT-TYPE
    SYNTAX       PMValidity
    MAX-ACCESS   read-only
    STATUS       current
    DESCRIPTION  "Indicates the validity of the provided count of packets
                  between 65 and 127 bytes."
    ::= { geCrntPMEntry 65 }


geCrntPMSIZE65To127Initialize OBJECT-TYPE
    SYNTAX       InitializeCmd
    MAX-ACCESS   read-write
    STATUS       current
    DESCRIPTION  "Used to initialize the value of the geCrntPMSIZE65To127Value
                  object to 0."
    ::= { geCrntPMEntry 66 }


geCrntPMSIZE128To255Value OBJECT-TYPE
    SYNTAX       Unsigned64
    MAX-ACCESS   read-only
    STATUS       current
    DESCRIPTION  "The total number of frames received that are 128 to 255 bytes
                  inclusive in length (excluding framing bits but including FCS
                  octets)."
    ::= { geCrntPMEntry 67 }


geCrntPMSIZE128To255TimeStamp OBJECT-TYPE
    SYNTAX       DateAndTime
    MAX-ACCESS   read-only
    STATUS       current
    DESCRIPTION  "The date and time stamp of the count of packets between 128
                  and 255 bytes."
    ::= { geCrntPMEntry 68 }


geCrntPMSIZE128To255Validity OBJECT-TYPE
    SYNTAX       PMValidity
    MAX-ACCESS   read-only
    STATUS       current
    DESCRIPTION  "Indicates the validity of the provided count of packets
                  between 128 and 255 bytes."
    ::= { geCrntPMEntry 69 }


geCrntPMSIZE128To255Initialize OBJECT-TYPE
    SYNTAX       InitializeCmd
    MAX-ACCESS   read-write
    STATUS       current
    DESCRIPTION  "Used to initialize the value of the geCrntPMSIZE128To255Value
                  object to 0."
    ::= { geCrntPMEntry 70 }


geCrntPMSIZE256To511Value OBJECT-TYPE
    SYNTAX       Unsigned64
    MAX-ACCESS   read-only
    STATUS       current
    DESCRIPTION  "The total number of frames received that are 256 to 511 bytes
                  inclusive in length (excluding framing bits but including FCS
                  octets)."
    ::= { geCrntPMEntry 71 }


geCrntPMSIZE256To511TimeStamp OBJECT-TYPE
    SYNTAX       DateAndTime
    MAX-ACCESS   read-only
    STATUS       current
    DESCRIPTION  "The date and time stamp of the count of packets between 256
                  and 511 bytes."
    ::= { geCrntPMEntry 72 }


geCrntPMSIZE256To511Validity OBJECT-TYPE
    SYNTAX       PMValidity
    MAX-ACCESS   read-only
    STATUS       current
    DESCRIPTION  "Indicates the validity of the provided count of packets
                  between 256 and 511 bytes."
    ::= { geCrntPMEntry 73 }


geCrntPMSIZE256To511Initialize OBJECT-TYPE
    SYNTAX       InitializeCmd
    MAX-ACCESS   read-write
    STATUS       current
    DESCRIPTION  "Used to initialize the value of the geCrntPMSIZE256To511Value
                  object to 0."
    ::= { geCrntPMEntry 74 }


geCrntPMSIZE512To1023Value OBJECT-TYPE
    SYNTAX       Unsigned64
    MAX-ACCESS   read-only
    STATUS       current
    DESCRIPTION  "The total number of frames received that are 512 to 1023 bytes
                  inclusive in length (excluding framing bits but including FCS
                  octets)."
    ::= { geCrntPMEntry 75 }


geCrntPMSIZE512To1023TimeStamp OBJECT-TYPE
    SYNTAX       DateAndTime
    MAX-ACCESS   read-only
    STATUS       current
    DESCRIPTION  "The date and time stamp of the count of packets between 512
                  and 1023 bytes."
    ::= { geCrntPMEntry 76 }


geCrntPMSIZE512To1023Validity OBJECT-TYPE
    SYNTAX       PMValidity
    MAX-ACCESS   read-only
    STATUS       current
    DESCRIPTION  "Indicates the validity of the provided count of packets
                  between 512 and 1023 bytes."
    ::= { geCrntPMEntry 77 }


geCrntPMSIZE512To1023Initialize OBJECT-TYPE
    SYNTAX       InitializeCmd
    MAX-ACCESS   read-write
    STATUS       current
    DESCRIPTION  "Used to initialize the value of the geCrntPMSIZE512To1023Value
                  object to 0."
    ::= { geCrntPMEntry 78 }


geCrntPMSIZE1024To1518Value OBJECT-TYPE
    SYNTAX       Unsigned64
    MAX-ACCESS   read-only
    STATUS       current
    DESCRIPTION  "The total number of frames received that are 1024 to 1518
                  bytes inclusive in length (excluding framing bits but
                  including FCS octets)."
    ::= { geCrntPMEntry 79 }


geCrntPMSIZE1024To1518TimeStamp OBJECT-TYPE
    SYNTAX       DateAndTime
    MAX-ACCESS   read-only
    STATUS       current
    DESCRIPTION  "The date and time stamp of the count of packets between 1024
                  and 1518 bytes."
    ::= { geCrntPMEntry 80 }


geCrntPMSIZE1024To1518Validity OBJECT-TYPE
    SYNTAX       PMValidity
    MAX-ACCESS   read-only
    STATUS       current
    DESCRIPTION  "Indicates the validity of the provided count of packets
                  between 1024 and 1518 bytes."
    ::= { geCrntPMEntry 81 }


geCrntPMSIZE1024To1518Initialize OBJECT-TYPE
    SYNTAX       InitializeCmd
    MAX-ACCESS   read-write
    STATUS       current
    DESCRIPTION  "Used to initialize the value of the
                  geCrntPMSIZE1024To1518Value object to 0."
    ::= { geCrntPMEntry 82 }


geCrntPMSIZEOver1518Value OBJECT-TYPE
    SYNTAX       Unsigned64
    MAX-ACCESS   read-only
    STATUS       current
    DESCRIPTION  "The total number of frames received that are greater than or
                  equal to 1519 bytes in length (excluding framing bits but
                  including FCS octets)."
    ::= { geCrntPMEntry 83 }


geCrntPMSIZEOver1518TimeStamp OBJECT-TYPE
    SYNTAX       DateAndTime
    MAX-ACCESS   read-only
    STATUS       current
    DESCRIPTION  "The date and time stamp of the count of packets over 1518
                  bytes."
    ::= { geCrntPMEntry 84 }


geCrntPMSIZEOver1518Validity OBJECT-TYPE
    SYNTAX       PMValidity
    MAX-ACCESS   read-only
    STATUS       current
    DESCRIPTION  "Indicates the validity of the provided count of packets over
                  1518 bytes."
    ::= { geCrntPMEntry 85 }


geCrntPMSIZEOver1518Initialize OBJECT-TYPE
    SYNTAX       InitializeCmd
    MAX-ACCESS   read-write
    STATUS       current
    DESCRIPTION  "Used to initialize the value of the geCrntPMSIZEOver1518Value
                  object to 0."
    ::= { geCrntPMEntry 86 }


geCrntPMTPFCRXValue OBJECT-TYPE
    SYNTAX       Unsigned64
    MAX-ACCESS   read-only
    STATUS       current
    DESCRIPTION  "The Gigabit Ethernet total received pause frame count."
    ::= { geCrntPMEntry 87 }


geCrntPMTPFCRXTimeStamp OBJECT-TYPE
    SYNTAX       DateAndTime
    MAX-ACCESS   read-only
    STATUS       current
    DESCRIPTION  "The date and time stamp of the GE total received pause frame
                  count value."
    ::= { geCrntPMEntry 88 }


geCrntPMTPFCRXValidity OBJECT-TYPE
    SYNTAX       PMValidity
    MAX-ACCESS   read-only
    STATUS       current
    DESCRIPTION  "Indicates the validity of the provided GE total received pause
                  frame count value."
    ::= { geCrntPMEntry 89 }


geCrntPMTPFCRXInitialize OBJECT-TYPE
    SYNTAX       InitializeCmd
    MAX-ACCESS   read-write
    STATUS       current
    DESCRIPTION  "Used to initialize the value of the geCrntPMTPFCRXValue object
                  to 0."
    ::= { geCrntPMEntry 90 }


geCrntPMTPFCTXValue OBJECT-TYPE
    SYNTAX       Unsigned64
    MAX-ACCESS   read-only
    STATUS       current
    DESCRIPTION  "The Gigabit Ethernet total transmitted pause frame count."
    ::= { geCrntPMEntry 91 }


geCrntPMTPFCTXTimeStamp OBJECT-TYPE
    SYNTAX       DateAndTime
    MAX-ACCESS   read-only
    STATUS       current
    DESCRIPTION  "The date and time stamp of the GE total transmitted pause
                  frame count value."
    ::= { geCrntPMEntry 92 }


geCrntPMTPFCTXValidity OBJECT-TYPE
    SYNTAX       PMValidity
    MAX-ACCESS   read-only
    STATUS       current
    DESCRIPTION  "Indicates the validity of the provided GE total transmitted
                  pause frame count value."
    ::= { geCrntPMEntry 93 }


geCrntPMTPFCTXInitialize OBJECT-TYPE
    SYNTAX       InitializeCmd
    MAX-ACCESS   read-write
    STATUS       current
    DESCRIPTION  "Used to initialize the value of the geCrntPMTPFCTXValue object
                  to 0."
    ::= { geCrntPMEntry 94 }


geCrntPMUSIZEValue OBJECT-TYPE
    SYNTAX       Unsigned32
    MAX-ACCESS   read-write
    STATUS       current
    DESCRIPTION  "The total number of frames received that were less than 64
                  octets long (excluding framing bits, but including FCS octets)
                  and were otherwise well formed."
    ::= { geCrntPMEntry 95 }


geCrntPMUSIZETimeStamp OBJECT-TYPE
    SYNTAX       DateAndTime
    MAX-ACCESS   read-only
    STATUS       current
    DESCRIPTION  "The date and time stamp of the count of undersized packets."
    ::= { geCrntPMEntry 96 }


geCrntPMUSIZEValidity OBJECT-TYPE
    SYNTAX       PMValidity
    MAX-ACCESS   read-only
    STATUS       current
    DESCRIPTION  "Indicates the validity of the provided count of undersized
                  packets."
    ::= { geCrntPMEntry 97 }


geCrntPMOSIZEValue OBJECT-TYPE
    SYNTAX       Unsigned32
    MAX-ACCESS   read-write
    STATUS       current
    DESCRIPTION  "The total number of frames received that were longer than 9600
                  octets (excluding framing bits, but including FCS octets) and
                  were otherwise well formed."
    ::= { geCrntPMEntry 98 }


geCrntPMOSIZETimeStamp OBJECT-TYPE
    SYNTAX       DateAndTime
    MAX-ACCESS   read-only
    STATUS       current
    DESCRIPTION  "The date and time stamp of the count of oversized packets."
    ::= { geCrntPMEntry 99 }


geCrntPMOSIZEValidity OBJECT-TYPE
    SYNTAX       PMValidity
    MAX-ACCESS   read-only
    STATUS       current
    DESCRIPTION  "Indicates the validity of the provided count of oversized
                  packets."
    ::= { geCrntPMEntry 100 }


geCrntPMFRGTValue OBJECT-TYPE
    SYNTAX       Unsigned32
    MAX-ACCESS   read-write
    STATUS       current
    DESCRIPTION  "The total number of frames received that were less than 64
                  octets in length (excluding framing bits but including FCS
                  octets) and had either a bad Frame Check Sequence (FCS) with
                  an integral number of octets (FCS Error) or a bad FCS with a
                  non-integral number of octets (Alignment Error)."
    ::= { geCrntPMEntry 101 }


geCrntPMFRGTTimeStamp OBJECT-TYPE
    SYNTAX       DateAndTime
    MAX-ACCESS   read-only
    STATUS       current
    DESCRIPTION  "The date and time stamp of the count of received packet
                  fragments."
    ::= { geCrntPMEntry 102 }


geCrntPMFRGTValidity OBJECT-TYPE
    SYNTAX       PMValidity
    MAX-ACCESS   read-only
    STATUS       current
    DESCRIPTION  "Indicates the validity of the provided count of received
                  packet fragments."
    ::= { geCrntPMEntry 103 }


geCrntPMJABRValue OBJECT-TYPE
    SYNTAX       Unsigned32
    MAX-ACCESS   read-write
    STATUS       current
    DESCRIPTION  "The total number of frames received that were longer than
                  14336 9600 octets (excluding framing bits, but including FCS
                  octets), and had either a bad Frame Check Sequence (FCS) with
                  an integral number of octets (FCS Error) or a bad FCS with
                  non-integral number of octets (Alignment Error)."
    ::= { geCrntPMEntry 104 }


geCrntPMJABRTimeStamp OBJECT-TYPE
    SYNTAX       DateAndTime
    MAX-ACCESS   read-only
    STATUS       current
    DESCRIPTION  "The date and time stamp of the count of received jabbers."
    ::= { geCrntPMEntry 105 }


geCrntPMJABRValidity OBJECT-TYPE
    SYNTAX       PMValidity
    MAX-ACCESS   read-only
    STATUS       current
    DESCRIPTION  "Indicates the validity of the provided count of received
                  jabbers."
    ::= { geCrntPMEntry 106 }


geCrntPMCVInitialize OBJECT-TYPE
    SYNTAX       InitializeCmd
    MAX-ACCESS   read-write
    STATUS       current
    DESCRIPTION  "Used to initialize the value of the geCrntPMCVValue object to
                  0."
    ::= { geCrntPMEntry 107 }


geCrntPMESInitialize OBJECT-TYPE
    SYNTAX       InitializeCmd
    MAX-ACCESS   read-write
    STATUS       current
    DESCRIPTION  "Used to initialize the value of the geCrntPMESValue object to
                  0."
    ::= { geCrntPMEntry 108 }


geCrntPMSESInitialize OBJECT-TYPE
    SYNTAX       InitializeCmd
    MAX-ACCESS   read-write
    STATUS       current
    DESCRIPTION  "Used to initialize the value of the geCrntPMSESValue object to
                  0."
    ::= { geCrntPMEntry 109 }


geCrntPMFCSEInitialize OBJECT-TYPE
    SYNTAX       InitializeCmd
    MAX-ACCESS   read-write
    STATUS       current
    DESCRIPTION  "Used to initialize the value of the geCrntPMFCSEValue object
                  to 0."
    ::= { geCrntPMEntry 110 }


geCrntPMFRDRInitialize OBJECT-TYPE
    SYNTAX       InitializeCmd
    MAX-ACCESS   read-write
    STATUS       current
    DESCRIPTION  "Used to initialize the value of the geCrntPMFRDRValue object
                  to 0."
    ::= { geCrntPMEntry 111 }


geCrntPMUSIZEInitialize OBJECT-TYPE
    SYNTAX       InitializeCmd
    MAX-ACCESS   read-write
    STATUS       current
    DESCRIPTION  "Used to initialize the value of the geCrntPMUSIZEValue object
                  to 0."
    ::= { geCrntPMEntry 112 }


geCrntPMOSIZEInitialize OBJECT-TYPE
    SYNTAX       InitializeCmd
    MAX-ACCESS   read-write
    STATUS       current
    DESCRIPTION  "Used to initialize the value of the geCrntPMOSIZEValue object
                  to 0."
    ::= { geCrntPMEntry 113 }


geCrntPMFRGTInitialize OBJECT-TYPE
    SYNTAX       InitializeCmd
    MAX-ACCESS   read-write
    STATUS       current
    DESCRIPTION  "Used to initialize the value of the geCrntPMFRGTValue object
                  to 0."
    ::= { geCrntPMEntry 114 }


geCrntPMJABRInitialize OBJECT-TYPE
    SYNTAX       InitializeCmd
    MAX-ACCESS   read-write
    STATUS       current
    DESCRIPTION  "Used to initialize the value of the geCrntPMJABRValue object
                  to 0."
    ::= { geCrntPMEntry 115 }

geCrntPMUASValue OBJECT-TYPE
    SYNTAX       Unsigned32
    MAX-ACCESS   read-write
    STATUS       current
    DESCRIPTION  "The count of unavailable seconds. This object applies
                  only to transciever ports provisioned for the gigabit ethernet
                  protocol."
    ::= { geCrntPMEntry 116 }

geCrntPMUASTimeStamp OBJECT-TYPE
    SYNTAX       DateAndTime
    MAX-ACCESS   read-only
    STATUS       current
    DESCRIPTION  "The date and time stamp of the unavailable seconds
                  value."
    ::= { geCrntPMEntry 117 }


geCrntPMUASValidity OBJECT-TYPE
    SYNTAX       PMValidity
    MAX-ACCESS   read-only
    STATUS       current
    DESCRIPTION  "Indicates the validity of the provided unavailable
                  seconds value."
    ::= { geCrntPMEntry 118 }


geCrntPMUASInitialize OBJECT-TYPE
    SYNTAX       InitializeCmd
    MAX-ACCESS   read-write
    STATUS       current
    DESCRIPTION  "Used to initialize the value of the geCrntPMUASValue
                  object to 0."
    ::= { geCrntPMEntry 119 }

geCrntPMOPRMinValue OBJECT-TYPE
    SYNTAX       FixedX10
    UNITS        "dBm/10"
    MAX-ACCESS   read-only
    STATUS       current
    DESCRIPTION  "The minimum optical power received on the input of the transceiver."
    ::= { geCrntPMEntry 120 }


geCrntPMOPRMinTimeStamp OBJECT-TYPE
    SYNTAX       DateAndTime
    MAX-ACCESS   read-only
    STATUS       current
    DESCRIPTION  "The date and time stamp of the minimum optical power received value."
    ::= { geCrntPMEntry 121 }


geCrntPMOPRMinValidity OBJECT-TYPE
    SYNTAX       PMValidity
    MAX-ACCESS   read-only
    STATUS       current
    DESCRIPTION  "Indicates the validity of the provided minimum optical power received
                  value."
    ::= { geCrntPMEntry 122 }

geCrntPMOPRMinInitialize OBJECT-TYPE
    SYNTAX       InitializeCmd
    MAX-ACCESS   read-write
    STATUS       current
    DESCRIPTION  "Used to initialize the value of the geCrntPMOPRMinValue
                  object to 0."
    ::= { geCrntPMEntry 123 }

geCrntPMOPRMaxValue OBJECT-TYPE
    SYNTAX       FixedX10
    UNITS        "dBm/10"
    MAX-ACCESS   read-only
    STATUS       current
    DESCRIPTION  "The maximum optical power received on the input of the transceiver."
    ::= { geCrntPMEntry 124 }


geCrntPMOPRMaxTimeStamp OBJECT-TYPE
    SYNTAX       DateAndTime
    MAX-ACCESS   read-only
    STATUS       current
    DESCRIPTION  "The date and time stamp of the maximum optical power received value."
    ::= { geCrntPMEntry 125 }


geCrntPMOPRMaxValidity OBJECT-TYPE
    SYNTAX       PMValidity
    MAX-ACCESS   read-only
    STATUS       current
    DESCRIPTION  "Indicates the validity of the provided maximum optical power received
                  value."
    ::= { geCrntPMEntry 126 }

geCrntPMOPRMaxInitialize OBJECT-TYPE
    SYNTAX       InitializeCmd
    MAX-ACCESS   read-write
    STATUS       current
    DESCRIPTION  "Used to initialize the value of the geCrntPMOPRMaxValue
                  object to 0."
    ::= { geCrntPMEntry 127 }

geCrntPMOPRAvgValue OBJECT-TYPE
    SYNTAX       FixedX10
    UNITS        "dBm/10"
    MAX-ACCESS   read-only
    STATUS       current
    DESCRIPTION  "The average optical power received on the input of the transceiver."
    ::= { geCrntPMEntry 128 }


geCrntPMOPRAvgTimeStamp OBJECT-TYPE
    SYNTAX       DateAndTime
    MAX-ACCESS   read-only
    STATUS       current
    DESCRIPTION  "The date and time stamp of the average optical power received value."
    ::= { geCrntPMEntry 129 }


geCrntPMOPRAvgValidity OBJECT-TYPE
    SYNTAX       PMValidity
    MAX-ACCESS   read-only
    STATUS       current
    DESCRIPTION  "Indicates the validity of the provided average optical power received
                  value."
    ::= { geCrntPMEntry 130 }

geCrntPMOPRAvgInitialize OBJECT-TYPE
    SYNTAX       InitializeCmd
    MAX-ACCESS   read-write
    STATUS       current
    DESCRIPTION  "Used to initialize the value of the geCrntPMOPRAvgValue
                  object to 0."
    ::= { geCrntPMEntry 131 }

geCrntPMOPTMinValue OBJECT-TYPE
    SYNTAX       FixedX10
    UNITS        "dBm/10"
    MAX-ACCESS   read-only
    STATUS       current
    DESCRIPTION  "The minimum optical power transmitted at the output of the
                  transceiver."
    ::= { geCrntPMEntry 132 }

geCrntPMOPTMinTimeStamp OBJECT-TYPE
    SYNTAX       DateAndTime
    MAX-ACCESS   read-only
    STATUS       current
    DESCRIPTION  "The date and time stamp of the minimum optical power transmitted
                  value."
    ::= { geCrntPMEntry 133 }


geCrntPMOPTMinValidity OBJECT-TYPE
    SYNTAX       PMValidity
    MAX-ACCESS   read-only
    STATUS       current
    DESCRIPTION  "Indicates the validity of the provided minimum optical power
                  transmitted value."
    ::= { geCrntPMEntry 134 }

geCrntPMOPTMinInitialize OBJECT-TYPE
    SYNTAX       InitializeCmd
    MAX-ACCESS   read-write
    STATUS       current
    DESCRIPTION  "Used to initialize the value of the geCrntPMOPTMinValue
                  object to 0."
    ::= { geCrntPMEntry 135 }

geCrntPMOPTMaxValue OBJECT-TYPE
    SYNTAX       FixedX10
    UNITS        "dBm/10"
    MAX-ACCESS   read-only
    STATUS       current
    DESCRIPTION  "The maximum optical power transmitted at the output of the
                  transceiver."
    ::= { geCrntPMEntry 136 }


geCrntPMOPTMaxTimeStamp OBJECT-TYPE
    SYNTAX       DateAndTime
    MAX-ACCESS   read-only
    STATUS       current
    DESCRIPTION  "The date and time stamp of the maximum optical power transmitted
                  value."
    ::= { geCrntPMEntry 137 }


geCrntPMOPTMaxValidity OBJECT-TYPE
    SYNTAX       PMValidity
    MAX-ACCESS   read-only
    STATUS       current
    DESCRIPTION  "Indicates the validity of the provided maximum optical power
                  transmitted value."
    ::= { geCrntPMEntry 138 }

geCrntPMOPTMaxInitialize OBJECT-TYPE
    SYNTAX       InitializeCmd
    MAX-ACCESS   read-write
    STATUS       current
    DESCRIPTION  "Used to initialize the value of the geCrntPMOPTMaxValue
                  object to 0."
    ::= { geCrntPMEntry 139 }

geCrntPMOPTAvgValue OBJECT-TYPE
    SYNTAX       FixedX10
    UNITS        "dBm/10"
    MAX-ACCESS   read-only
    STATUS       current
    DESCRIPTION  "The average optical power transmitted at the output of the
                  transceiver."
    ::= { geCrntPMEntry 140 }


geCrntPMOPTAvgTimeStamp OBJECT-TYPE
    SYNTAX       DateAndTime
    MAX-ACCESS   read-only
    STATUS       current
    DESCRIPTION  "The date and time stamp of the average optical power transmitted
                  value."
    ::= { geCrntPMEntry 141 }

geCrntPMOPTAvgValidity OBJECT-TYPE
    SYNTAX       PMValidity
    MAX-ACCESS   read-only
    STATUS       current
    DESCRIPTION  "Indicates the validity of the provided average optical power
                  transmitted value."
    ::= { geCrntPMEntry 142 }

geCrntPMOPTAvgInitialize OBJECT-TYPE
    SYNTAX       InitializeCmd
    MAX-ACCESS   read-write
    STATUS       current
    DESCRIPTION  "Used to initialize the value of the geCrntPMOPTAvgValue
                  object to 0."
    ::= { geCrntPMEntry 143 }


-----------------------------------------------------------------------
-- Objects used to retrieve historical Gigabit Ethernet
-- Performance Monitoring statistics
-- 
-- A listing of historical Gigabit Ethernet PM values is contained in 
-- the geHistPMTable of the BTI 7000 Series MIB. When retrieved, this 
-- table provides one row for each set of historical Gigabit Ethernet 
-- PM data.
-- 
-- The following table lists the objects in each entry of the geHistPMTable.
-----------------------------------------------------------------------


geHistPMTable OBJECT-TYPE
    SYNTAX       SEQUENCE OF GeHistPMEntry
    MAX-ACCESS   not-accessible
    STATUS       current
    DESCRIPTION  "A table of historical performance monitoring statistics
                  collected for the Gigabit Ethernet facilities on the NE."
    ::= { performance 21 }


geHistPMEntry OBJECT-TYPE
    SYNTAX       GeHistPMEntry
    MAX-ACCESS   not-accessible
    STATUS       current
    DESCRIPTION  "The row entry object of the Gigabit Ethernet historical
                  performance monitoring table. Each row of this table contains
                  a full set of PM statistics and related data for a historical
                  measurement interval for a given Gigabit Ethernet facility."
    INDEX        { geHistPMShelfIdx,
                   geHistPMSlotIdx,
                   geHistPMPortIdx,
                   geHistPMIntervalTypeIdx,
                   geHistPMIntervalIdx }
    ::= { geHistPMTable 1 }


GeHistPMEntry ::= SEQUENCE { geHistPMShelfIdx                  INTEGER,
                             geHistPMSlotIdx                   INTEGER,
                             geHistPMPortIdx                   INTEGER,
                             geHistPMIntervalTypeIdx           PMIntervalType,
                             geHistPMIntervalIdx               INTEGER,
                             geHistPMOPRValue                  FixedX10,
                             geHistPMOPRTimeStamp              DateAndTime,
                             geHistPMOPRValidity               PMValidity,
                             geHistPMOPTValue                  FixedX10,
                             geHistPMOPTTimeStamp              DateAndTime,
                             geHistPMOPTValidity               PMValidity,
                             geHistPMTempValue                 INTEGER,
                             geHistPMTempTimeStamp             DateAndTime,
                             geHistPMTempValidity              PMValidity,
                             geHistPMSupplyVoltageValue        FixedX10,
                             geHistPMSupplyVoltageTimeStamp    DateAndTime,
                             geHistPMSupplyVoltageValidity     PMValidity,
                             geHistPMLBCValue                  INTEGER,
                             geHistPMLBCTimeStamp              DateAndTime,
                             geHistPMLBCValidity               PMValidity,
                             geHistPMCVValue                   Unsigned32,
                             geHistPMCVTimeStamp               DateAndTime,
                             geHistPMCVValidity                PMValidity,
                             geHistPMESValue                   Unsigned32,
                             geHistPMESTimeStamp               DateAndTime,
                             geHistPMESValidity                PMValidity,
                             geHistPMSESValue                  Unsigned32,
                             geHistPMSESTimeStamp              DateAndTime,
                             geHistPMSESValidity               PMValidity,
                             geHistPMTFRCRXValue               Unsigned64,
                             geHistPMTFRCRXTimeStamp           DateAndTime,
                             geHistPMTFRCRXValidity            PMValidity,
                             geHistPMTFRCRXInitialize          InitializeCmd,
                             geHistPMTFRCTXValue               Unsigned64,
                             geHistPMTFRCTXTimeStamp           DateAndTime,
                             geHistPMTFRCTXValidity            PMValidity,
                             geHistPMTFRCTXInitialize          InitializeCmd,
                             geHistPMFRDRValue                 Unsigned32,
                             geHistPMFRDRTimeStamp             DateAndTime,
                             geHistPMFRDRValidity              PMValidity,
                             geHistPMFCSEValue                 Unsigned32,
                             geHistPMFCSETimeStamp             DateAndTime,
                             geHistPMFCSEValidity              PMValidity,
                             geHistPMTBYCRXValue               Unsigned64,
                             geHistPMTBYCRXTimeStamp           DateAndTime,
                             geHistPMTBYCRXValidity            PMValidity,
                             geHistPMTBYCRXInitialize          InitializeCmd,
                             geHistPMTBYCTXValue               Unsigned64,
                             geHistPMTBYCTXTimeStamp           DateAndTime,
                             geHistPMTBYCTXValidity            PMValidity,
                             geHistPMTBYCTXInitialize          InitializeCmd,
                             geHistPMBCSTValue                 Unsigned64,
                             geHistPMBCSTTimeStamp             DateAndTime,
                             geHistPMBCSTValidity              PMValidity,
                             geHistPMBCSTInitialize            InitializeCmd,
                             geHistPMMCSTValue                 Unsigned64,
                             geHistPMMCSTTimeStamp             DateAndTime,
                             geHistPMMCSTValidity              PMValidity,
                             geHistPMMCSTInitialize            InitializeCmd,
                             geHistPMSIZE64Value               Unsigned64,
                             geHistPMSIZE64TimeStamp           DateAndTime,
                             geHistPMSIZE64Validity            PMValidity,
                             geHistPMSIZE64Initialize          InitializeCmd,
                             geHistPMSIZE65To127Value          Unsigned64,
                             geHistPMSIZE65To127TimeStamp      DateAndTime,
                             geHistPMSIZE65To127Validity       PMValidity,
                             geHistPMSIZE65To127Initialize     InitializeCmd,
                             geHistPMSIZE128To255Value         Unsigned64,
                             geHistPMSIZE128To255TimeStamp     DateAndTime,
                             geHistPMSIZE128To255Validity      PMValidity,
                             geHistPMSIZE128To255Initialize    InitializeCmd,
                             geHistPMSIZE256To511Value         Unsigned64,
                             geHistPMSIZE256To511TimeStamp     DateAndTime,
                             geHistPMSIZE256To511Validity      PMValidity,
                             geHistPMSIZE256To511Initialize    InitializeCmd,
                             geHistPMSIZE512To1023Value        Unsigned64,
                             geHistPMSIZE512To1023TimeStamp    DateAndTime,
                             geHistPMSIZE512To1023Validity     PMValidity,
                             geHistPMSIZE512To1023Initialize   InitializeCmd,
                             geHistPMSIZE1024To1518Value       Unsigned64,
                             geHistPMSIZE1024To1518TimeStamp   DateAndTime,
                             geHistPMSIZE1024To1518Validity    PMValidity,
                             geHistPMSIZE1024To1518Initialize  InitializeCmd,
                             geHistPMSIZEOver1518Value         Unsigned64,
                             geHistPMSIZEOver1518TimeStamp     DateAndTime,
                             geHistPMSIZEOver1518Validity      PMValidity,
                             geHistPMSIZEOver1518Initialize    InitializeCmd,
                             geHistPMTPFCRXValue               Unsigned64,
                             geHistPMTPFCRXTimeStamp           DateAndTime,
                             geHistPMTPFCRXValidity            PMValidity,
                             geHistPMTPFCRXInitialize          InitializeCmd,
                             geHistPMTPFCTXValue               Unsigned64,
                             geHistPMTPFCTXTimeStamp           DateAndTime,
                             geHistPMTPFCTXValidity            PMValidity,
                             geHistPMTPFCTXInitialize          InitializeCmd,
                             geHistPMUSIZEValue                Unsigned32,
                             geHistPMUSIZETimeStamp            DateAndTime,
                             geHistPMUSIZEValidity             PMValidity,
                             geHistPMOSIZEValue                Unsigned32,
                             geHistPMOSIZETimeStamp            DateAndTime,
                             geHistPMOSIZEValidity             PMValidity,
                             geHistPMFRGTValue                 Unsigned32,
                             geHistPMFRGTTimeStamp             DateAndTime,
                             geHistPMFRGTValidity              PMValidity,
                             geHistPMJABRValue                 Unsigned32,
                             geHistPMJABRTimeStamp             DateAndTime,
                             geHistPMJABRValidity              PMValidity,
                             geHistPMCVInitialize              InitializeCmd,
                             geHistPMESInitialize              InitializeCmd,
                             geHistPMSESInitialize             InitializeCmd,
                             geHistPMFCSEInitialize            InitializeCmd,
                             geHistPMFRDRInitialize            InitializeCmd,
                             geHistPMUSIZEInitialize           InitializeCmd,
                             geHistPMOSIZEInitialize           InitializeCmd,
                             geHistPMFRGTInitialize            InitializeCmd,
                             geHistPMJABRInitialize            InitializeCmd,
                             geHistPMUASValue                  Unsigned32,
                             geHistPMUASTimeStamp              DateAndTime,
                             geHistPMUASValidity               PMValidity,
                             geHistPMUASInitialize             InitializeCmd,
                             geHistPMOPRMinValue               FixedX10,
                             geHistPMOPRMinTimeStamp           DateAndTime,
                             geHistPMOPRMinValidity            PMValidity,
                             geHistPMOPRMinInitialize          InitializeCmd,
                             geHistPMOPRMaxValue               FixedX10,
                             geHistPMOPRMaxTimeStamp           DateAndTime,
                             geHistPMOPRMaxValidity            PMValidity,
                             geHistPMOPRMaxInitialize          InitializeCmd,
                             geHistPMOPRAvgValue               FixedX10,
                             geHistPMOPRAvgTimeStamp           DateAndTime,
                             geHistPMOPRAvgValidity            PMValidity,
                             geHistPMOPRAvgInitialize          InitializeCmd,
                             geHistPMOPTMinValue               FixedX10,
                             geHistPMOPTMinTimeStamp           DateAndTime,
                             geHistPMOPTMinValidity            PMValidity,
                             geHistPMOPTMinInitialize          InitializeCmd,
                             geHistPMOPTMaxValue               FixedX10,
                             geHistPMOPTMaxTimeStamp           DateAndTime,
                             geHistPMOPTMaxValidity            PMValidity,
                             geHistPMOPTMaxInitialize          InitializeCmd,
                             geHistPMOPTAvgValue               FixedX10,
                             geHistPMOPTAvgTimeStamp           DateAndTime,
                             geHistPMOPTAvgValidity            PMValidity,
                             geHistPMOPTAvgInitialize          InitializeCmd}


geHistPMShelfIdx OBJECT-TYPE
    SYNTAX       INTEGER (1|11|21|31)
    MAX-ACCESS   not-accessible
    STATUS       current
    DESCRIPTION  "The number of the shelf on which the GE facility targeted for
                  PMs is provisioned."
    ::= { geHistPMEntry 1 }


geHistPMSlotIdx OBJECT-TYPE
    SYNTAX       INTEGER (1..20)
    MAX-ACCESS   not-accessible
    STATUS       current
    DESCRIPTION  "The number of the slot within which the GE facility targeted
                  for PMs is provisioned."
    ::= { geHistPMEntry 2 }


geHistPMPortIdx OBJECT-TYPE
    SYNTAX       INTEGER (3..12)
    MAX-ACCESS   not-accessible
    STATUS       current
    DESCRIPTION  "The number of the port on the circuit pack on which the GE
                  facility targeted for PMs is provisioned."
    ::= { geHistPMEntry 3 }


geHistPMIntervalTypeIdx OBJECT-TYPE
    SYNTAX       PMIntervalType
    MAX-ACCESS   not-accessible
    STATUS       current
    DESCRIPTION  "The type of PM bin according to interval length."
    ::= { geHistPMEntry 4 }


geHistPMIntervalIdx OBJECT-TYPE
    SYNTAX       INTEGER (1..96)
    MAX-ACCESS   not-accessible
    STATUS       current
    DESCRIPTION  "The specific PM bin number. The range is 1 to 96 for the
                  15-minute historical bins. For the 1-day historical bin, the
                  value is 1."
    ::= { geHistPMEntry 5 }


geHistPMOPRValue OBJECT-TYPE
    SYNTAX       FixedX10
    UNITS        "dBm/10"
    MAX-ACCESS   read-only
    STATUS       current
    DESCRIPTION  "The optical power received on the input of the GE facility
                  port."
    ::= { geHistPMEntry 6 }


geHistPMOPRTimeStamp OBJECT-TYPE
    SYNTAX       DateAndTime
    MAX-ACCESS   read-only
    STATUS       current
    DESCRIPTION  "The date and time stamp of the optical power received value."
    ::= { geHistPMEntry 7 }


geHistPMOPRValidity OBJECT-TYPE
    SYNTAX       PMValidity
    MAX-ACCESS   read-only
    STATUS       current
    DESCRIPTION  "Indicates the validity of the provided optical power received
                  value."
    ::= { geHistPMEntry 8 }


geHistPMOPTValue OBJECT-TYPE
    SYNTAX       FixedX10
    UNITS        "dBm/10"
    MAX-ACCESS   read-only
    STATUS       current
    DESCRIPTION  "The optical power transmitted at the output of the GE facility
                  port."
    ::= { geHistPMEntry 9 }


geHistPMOPTTimeStamp OBJECT-TYPE
    SYNTAX       DateAndTime
    MAX-ACCESS   read-only
    STATUS       current
    DESCRIPTION  "The date and time stamp of the optical power transmitted
                  value."
    ::= { geHistPMEntry 10 }


geHistPMOPTValidity OBJECT-TYPE
    SYNTAX       PMValidity
    MAX-ACCESS   read-only
    STATUS       current
    DESCRIPTION  "Indicates the validity of the provided optical power
                  transmitted value."
    ::= { geHistPMEntry 11 }


geHistPMTempValue OBJECT-TYPE
    SYNTAX       INTEGER (-32768..32767)
    UNITS        "degrees Celsius"
    MAX-ACCESS   read-only
    STATUS       current
    DESCRIPTION  "The temperature measured on the GE facility port."
    ::= { geHistPMEntry 12 }


geHistPMTempTimeStamp OBJECT-TYPE
    SYNTAX       DateAndTime
    MAX-ACCESS   read-only
    STATUS       current
    DESCRIPTION  "The date and time stamp of the temperature value."
    ::= { geHistPMEntry 13 }


geHistPMTempValidity OBJECT-TYPE
    SYNTAX       PMValidity
    MAX-ACCESS   read-only
    STATUS       current
    DESCRIPTION  "Indicates the validity of the provided temperature value."
    ::= { geHistPMEntry 14 }


geHistPMSupplyVoltageValue OBJECT-TYPE
    SYNTAX       FixedX10
    UNITS        "mVolts/10"
    MAX-ACCESS   read-only
    STATUS       current
    DESCRIPTION  "The supply voltage measured on the GE facility port."
    ::= { geHistPMEntry 15 }


geHistPMSupplyVoltageTimeStamp OBJECT-TYPE
    SYNTAX       DateAndTime
    MAX-ACCESS   read-only
    STATUS       current
    DESCRIPTION  "The date and time stamp of the supply voltage value."
    ::= { geHistPMEntry 16 }


geHistPMSupplyVoltageValidity OBJECT-TYPE
    SYNTAX       PMValidity
    MAX-ACCESS   read-only
    STATUS       current
    DESCRIPTION  "Indicates the validity of the provided supply voltage value."
    ::= { geHistPMEntry 17 }


geHistPMLBCValue OBJECT-TYPE
    SYNTAX       INTEGER (-32768..32767)
    UNITS        "mAmp"
    MAX-ACCESS   read-only
    STATUS       current
    DESCRIPTION  "The laser bias current measured on the GE facility port."
    ::= { geHistPMEntry 18 }


geHistPMLBCTimeStamp OBJECT-TYPE
    SYNTAX       DateAndTime
    MAX-ACCESS   read-only
    STATUS       current
    DESCRIPTION  "The date and time stamp of the laser bias current value."
    ::= { geHistPMEntry 19 }


geHistPMLBCValidity OBJECT-TYPE
    SYNTAX       PMValidity
    MAX-ACCESS   read-only
    STATUS       current
    DESCRIPTION  "Indicates the validity of the provided laser bias current
                  value."
    ::= { geHistPMEntry 20 }


geHistPMCVValue OBJECT-TYPE
    SYNTAX       Unsigned32 
    MAX-ACCESS   read-write
    STATUS       current
    DESCRIPTION  "The count of Gigabit Ethernet 8B/10B coding violations."
    ::= { geHistPMEntry 21 }


geHistPMCVTimeStamp OBJECT-TYPE
    SYNTAX       DateAndTime
    MAX-ACCESS   read-only
    STATUS       current
    DESCRIPTION  "The date and time stamp of the GE coding violations value."
    ::= { geHistPMEntry 22 }


geHistPMCVValidity OBJECT-TYPE
    SYNTAX       PMValidity
    MAX-ACCESS   read-only
    STATUS       current
    DESCRIPTION  "Indicates the validity of the provided GE coding violations
                  value."
    ::= { geHistPMEntry 23 }


geHistPMESValue OBJECT-TYPE
    SYNTAX       Unsigned32
    MAX-ACCESS   read-write
    STATUS       current
    DESCRIPTION  "The count of GE errored seconds."
    ::= { geHistPMEntry 24 }


geHistPMESTimeStamp OBJECT-TYPE
    SYNTAX       DateAndTime
    MAX-ACCESS   read-only
    STATUS       current
    DESCRIPTION  "The date and time stamp of the GE errored seconds value."
    ::= { geHistPMEntry 25 }


geHistPMESValidity OBJECT-TYPE
    SYNTAX       PMValidity
    MAX-ACCESS   read-only
    STATUS       current
    DESCRIPTION  "Indicates the validity of the provided GE errored seconds
                  value."
    ::= { geHistPMEntry 26 }


geHistPMSESValue OBJECT-TYPE
    SYNTAX       Unsigned32
    MAX-ACCESS   read-write
    STATUS       current
    DESCRIPTION  "The count of GE severely errored seconds."
    ::= { geHistPMEntry 27 }


geHistPMSESTimeStamp OBJECT-TYPE
    SYNTAX       DateAndTime
    MAX-ACCESS   read-only
    STATUS       current
    DESCRIPTION  "The date and time stamp of the GE severely errored seconds
                  value."
    ::= { geHistPMEntry 28 }


geHistPMSESValidity OBJECT-TYPE
    SYNTAX       PMValidity
    MAX-ACCESS   read-only
    STATUS       current
    DESCRIPTION  "Indicates the validity of the provided GE severely errored
                  seconds value."
    ::= { geHistPMEntry 29 }


geHistPMTFRCRXValue OBJECT-TYPE
    SYNTAX       Unsigned64
    MAX-ACCESS   read-only
    STATUS       current
    DESCRIPTION  "The Gigabit Ethernet total received byte count."
    ::= { geHistPMEntry 30 }


geHistPMTFRCRXTimeStamp OBJECT-TYPE
    SYNTAX       DateAndTime
    MAX-ACCESS   read-only
    STATUS       current
    DESCRIPTION  "The date and time stamp of the GE total received byte count
                  value."
    ::= { geHistPMEntry 31 }


geHistPMTFRCRXValidity OBJECT-TYPE
    SYNTAX       PMValidity
    MAX-ACCESS   read-only
    STATUS       current
    DESCRIPTION  "Indicates the validity of the provided GE total received byte
                  count value."
    ::= { geHistPMEntry 32 }


geHistPMTFRCRXInitialize OBJECT-TYPE
    SYNTAX       InitializeCmd
    MAX-ACCESS   read-write
    STATUS       current
    DESCRIPTION  "Used to initialize the value of the geHistPMTBYCRXValue object
                  to 0."
    ::= { geHistPMEntry 33 }


geHistPMTFRCTXValue OBJECT-TYPE
    SYNTAX       Unsigned64
    MAX-ACCESS   read-only
    STATUS       current
    DESCRIPTION  "The Gigabit Ethernet total transmitted frame count."
    ::= { geHistPMEntry 34 }


geHistPMTFRCTXTimeStamp OBJECT-TYPE
    SYNTAX       DateAndTime
    MAX-ACCESS   read-only
    STATUS       current
    DESCRIPTION  "The date and time stamp of the GE total transmitted frame
                  count value."
    ::= { geHistPMEntry 35 }


geHistPMTFRCTXValidity OBJECT-TYPE
    SYNTAX       PMValidity
    MAX-ACCESS   read-only
    STATUS       current
    DESCRIPTION  "Indicates the validity of the provided GE total transmitted
                  frame count value."
    ::= { geHistPMEntry 36 }


geHistPMTFRCTXInitialize OBJECT-TYPE
    SYNTAX       InitializeCmd
    MAX-ACCESS   read-write
    STATUS       current
    DESCRIPTION  "Used to initialize the value of the geHistPMTFRCTXValue object
                  to 0."
    ::= { geHistPMEntry 37 }


geHistPMFRDRValue OBJECT-TYPE
    SYNTAX       Unsigned32
    MAX-ACCESS   read-write
    STATUS       current
    DESCRIPTION  "The count of Gigabit Ethernet discarded frames."
    ::= { geHistPMEntry 38 }


geHistPMFRDRTimeStamp OBJECT-TYPE
    SYNTAX       DateAndTime
    MAX-ACCESS   read-only
    STATUS       current
    DESCRIPTION  "The date and time stamp of the GE discarded frames value."
    ::= { geHistPMEntry 39 }


geHistPMFRDRValidity OBJECT-TYPE
    SYNTAX       PMValidity
    MAX-ACCESS   read-only
    STATUS       current
    DESCRIPTION  "Indicates the validity of the provided GE discarded frames
                  value."
    ::= { geHistPMEntry 40 }


geHistPMFCSEValue OBJECT-TYPE
    SYNTAX       Unsigned32
    MAX-ACCESS   read-write
    STATUS       current
    DESCRIPTION  "The count of Gigabit Ethernet frame checksum errors."
    ::= { geHistPMEntry 41 }


geHistPMFCSETimeStamp OBJECT-TYPE
    SYNTAX       DateAndTime
    MAX-ACCESS   read-only
    STATUS       current
    DESCRIPTION  "The date and time stamp of the GE frame checksum errors
                  value."
    ::= { geHistPMEntry 42 }


geHistPMFCSEValidity OBJECT-TYPE
    SYNTAX       PMValidity
    MAX-ACCESS   read-only
    STATUS       current
    DESCRIPTION  "Indicates the validity of the provided GE frame checksum
                  errors value."
    ::= { geHistPMEntry 43 }


geHistPMTBYCRXValue OBJECT-TYPE
    SYNTAX       Unsigned64
    MAX-ACCESS   read-only
    STATUS       current
    DESCRIPTION  "The Gigabit Ethernet total received byte count."
    ::= { geHistPMEntry 44 }


geHistPMTBYCRXTimeStamp OBJECT-TYPE
    SYNTAX       DateAndTime
    MAX-ACCESS   read-only
    STATUS       current
    DESCRIPTION  "The date and time stamp of the GE total received byte count
                  value."
    ::= { geHistPMEntry 45 }


geHistPMTBYCRXValidity OBJECT-TYPE
    SYNTAX       PMValidity
    MAX-ACCESS   read-only
    STATUS       current
    DESCRIPTION  "Indicates the validity of the provided GE total received byte
                  count value."
    ::= { geHistPMEntry 46 }


geHistPMTBYCRXInitialize OBJECT-TYPE
    SYNTAX       InitializeCmd
    MAX-ACCESS   read-write
    STATUS       current
    DESCRIPTION  "Used to initialize the value of the geHistPMTBYCRXValue object
                  to 0."
    ::= { geHistPMEntry 47 }


geHistPMTBYCTXValue OBJECT-TYPE
    SYNTAX       Unsigned64
    MAX-ACCESS   read-only
    STATUS       current
    DESCRIPTION  "The Gigabit Ethernet total transmitted byte count."
    ::= { geHistPMEntry 48 }


geHistPMTBYCTXTimeStamp OBJECT-TYPE
    SYNTAX       DateAndTime
    MAX-ACCESS   read-only
    STATUS       current
    DESCRIPTION  "The date and time stamp of the GE total transmitted byte count
                  value."
    ::= { geHistPMEntry 49 }


geHistPMTBYCTXValidity OBJECT-TYPE
    SYNTAX       PMValidity
    MAX-ACCESS   read-only
    STATUS       current
    DESCRIPTION  "Indicates the validity of the provided GE total transmitted
                  byte count value."
    ::= { geHistPMEntry 50 }


geHistPMTBYCTXInitialize OBJECT-TYPE
    SYNTAX       InitializeCmd
    MAX-ACCESS   read-write
    STATUS       current
    DESCRIPTION  "Used to initialize the value of the geHistPMTBYCTXValue object
                  to 0."
    ::= { geHistPMEntry 51 }


geHistPMBCSTValue OBJECT-TYPE
    SYNTAX       Unsigned64
    MAX-ACCESS   read-only
    STATUS       current
    DESCRIPTION  "The total number of good frames received that were directed to
                  the broadcast address. Note that this does not include
                  multicast frames."
    ::= { geHistPMEntry 52 }


geHistPMBCSTTimeStamp OBJECT-TYPE
    SYNTAX       DateAndTime
    MAX-ACCESS   read-only
    STATUS       current
    DESCRIPTION  "The date and time stamp of the broadcast packets received
                  count value."
    ::= { geHistPMEntry 53 }


geHistPMBCSTValidity OBJECT-TYPE
    SYNTAX       PMValidity
    MAX-ACCESS   read-only
    STATUS       current
    DESCRIPTION  "Indicates the validity of the provided broadcast packets
                  received count value."
    ::= { geHistPMEntry 54 }


geHistPMBCSTInitialize OBJECT-TYPE
    SYNTAX       InitializeCmd
    MAX-ACCESS   read-write
    STATUS       current
    DESCRIPTION  "Used to initialize the value of the geHistPMBCSTValue object
                  to 0."
    ::= { geHistPMEntry 55 }


geHistPMMCSTValue OBJECT-TYPE
    SYNTAX       Unsigned64
    MAX-ACCESS   read-only
    STATUS       current
    DESCRIPTION  "The total number of good frames received that were directed to
                  a multicast address. Note that this number does not include
                  frames directed to the broadcast address."
    ::= { geHistPMEntry 56 }


geHistPMMCSTTimeStamp OBJECT-TYPE
    SYNTAX       DateAndTime
    MAX-ACCESS   read-only
    STATUS       current
    DESCRIPTION  "The date and time stamp of the multicast packets received
                  count value."
    ::= { geHistPMEntry 57 }


geHistPMMCSTValidity OBJECT-TYPE
    SYNTAX       PMValidity
    MAX-ACCESS   read-only
    STATUS       current
    DESCRIPTION  "Indicates the validity of the provided multicast packets
                  received count value."
    ::= { geHistPMEntry 58 }


geHistPMMCSTInitialize OBJECT-TYPE
    SYNTAX       InitializeCmd
    MAX-ACCESS   read-write
    STATUS       current
    DESCRIPTION  "Used to initialize the value of the geHistPMMCSTValue object
                  to 0."
    ::= { geHistPMEntry 59 }


geHistPMSIZE64Value OBJECT-TYPE
    SYNTAX       Unsigned64
    MAX-ACCESS   read-only
    STATUS       current
    DESCRIPTION  "The total number of 64 byte frames received (excluding framing
                  bits but including FCS octets)."
    ::= { geHistPMEntry 60 }


geHistPMSIZE64TimeStamp OBJECT-TYPE
    SYNTAX       DateAndTime
    MAX-ACCESS   read-only
    STATUS       current
    DESCRIPTION  "The date and time stamp of the count of 64-byte packets
                  received."
    ::= { geHistPMEntry 61 }


geHistPMSIZE64Validity OBJECT-TYPE
    SYNTAX       PMValidity
    MAX-ACCESS   read-only
    STATUS       current
    DESCRIPTION  "Indicates the validity of the provided count of 64-byte
                  packets packets received."
    ::= { geHistPMEntry 62 }


geHistPMSIZE64Initialize OBJECT-TYPE
    SYNTAX       InitializeCmd
    MAX-ACCESS   read-write
    STATUS       current
    DESCRIPTION  "Used to initialize the value of the geHistPMSIZE64Value object
                  to 0."
    ::= { geHistPMEntry 63 }


geHistPMSIZE65To127Value OBJECT-TYPE
    SYNTAX       Unsigned64
    MAX-ACCESS   read-only
    STATUS       current
    DESCRIPTION  "The total number of frames received that are 65 to 127 bytes
                  inclusive in length (excluding framing bits but including FCS
                  octets)."
    ::= { geHistPMEntry 64 }


geHistPMSIZE65To127TimeStamp OBJECT-TYPE
    SYNTAX       DateAndTime
    MAX-ACCESS   read-only
    STATUS       current
    DESCRIPTION  "The date and time stamp of the count of packets between 65 and
                  127 bytes."
    ::= { geHistPMEntry 65 }


geHistPMSIZE65To127Validity OBJECT-TYPE
    SYNTAX       PMValidity
    MAX-ACCESS   read-only
    STATUS       current
    DESCRIPTION  "Indicates the validity of the provided count of packets
                  between 65 and 127 bytes."
    ::= { geHistPMEntry 66 }


geHistPMSIZE65To127Initialize OBJECT-TYPE
    SYNTAX       InitializeCmd
    MAX-ACCESS   read-write
    STATUS       current
    DESCRIPTION  "Used to initialize the value of the geHistPMSIZE65To127Value
                  object to 0."
    ::= { geHistPMEntry 67 }


geHistPMSIZE128To255Value OBJECT-TYPE
    SYNTAX       Unsigned64
    MAX-ACCESS   read-only
    STATUS       current
    DESCRIPTION  "The total number of frames received that are 128 to 255 bytes
                  inclusive in length (excluding framing bits but including FCS
                  octets)."
    ::= { geHistPMEntry 68 }


geHistPMSIZE128To255TimeStamp OBJECT-TYPE
    SYNTAX       DateAndTime
    MAX-ACCESS   read-only
    STATUS       current
    DESCRIPTION  "The date and time stamp of the count of packets between 128
                  and 255 bytes."
    ::= { geHistPMEntry 69 }


geHistPMSIZE128To255Validity OBJECT-TYPE
    SYNTAX       PMValidity
    MAX-ACCESS   read-only
    STATUS       current
    DESCRIPTION  "Indicates the validity of the provided count of packets
                  between 128 and 255 bytes."
    ::= { geHistPMEntry 70 }


geHistPMSIZE128To255Initialize OBJECT-TYPE
    SYNTAX       InitializeCmd
    MAX-ACCESS   read-write
    STATUS       current
    DESCRIPTION  "Used to initialize the value of the geHistPMSIZE128To255Value
                  object to 0."
    ::= { geHistPMEntry 71 }


geHistPMSIZE256To511Value OBJECT-TYPE
    SYNTAX       Unsigned64
    MAX-ACCESS   read-only
    STATUS       current
    DESCRIPTION  "The total number of frames received that are 256 to 511 bytes
                  inclusive in length (excluding framing bits but including FCS
                  octets)."
    ::= { geHistPMEntry 72 }


geHistPMSIZE256To511TimeStamp OBJECT-TYPE
    SYNTAX       DateAndTime
    MAX-ACCESS   read-only
    STATUS       current
    DESCRIPTION  "The date and time stamp of the count of packets between 256
                  and 511 bytes."
    ::= { geHistPMEntry 73 }


geHistPMSIZE256To511Validity OBJECT-TYPE
    SYNTAX       PMValidity
    MAX-ACCESS   read-only
    STATUS       current
    DESCRIPTION  "Indicates the validity of the provided count of packets
                  between 256 and 511 bytes."
    ::= { geHistPMEntry 74 }


geHistPMSIZE256To511Initialize OBJECT-TYPE
    SYNTAX       InitializeCmd
    MAX-ACCESS   read-write
    STATUS       current
    DESCRIPTION  "Used to initialize the value of the geHistPMSIZE256To511Value
                  object to 0."
    ::= { geHistPMEntry 75 }


geHistPMSIZE512To1023Value OBJECT-TYPE
    SYNTAX       Unsigned64
    MAX-ACCESS   read-only
    STATUS       current
    DESCRIPTION  "The total number of frames received that are 512 to 1023 bytes
                  inclusive in length (excluding framing bits but including FCS
                  octets)."
    ::= { geHistPMEntry 76 }


geHistPMSIZE512To1023TimeStamp OBJECT-TYPE
    SYNTAX       DateAndTime
    MAX-ACCESS   read-only
    STATUS       current
    DESCRIPTION  "The date and time stamp of the count of packets between 512
                  and 1023 bytes."
    ::= { geHistPMEntry 77 }


geHistPMSIZE512To1023Validity OBJECT-TYPE
    SYNTAX       PMValidity
    MAX-ACCESS   read-only
    STATUS       current
    DESCRIPTION  "Indicates the validity of the provided count of packets
                  between 512 and 1023 bytes."
    ::= { geHistPMEntry 78 }


geHistPMSIZE512To1023Initialize OBJECT-TYPE
    SYNTAX       InitializeCmd
    MAX-ACCESS   read-write
    STATUS       current
    DESCRIPTION  "Used to initialize the value of the geHistPMSIZE512To1023Value
                  object to 0."
    ::= { geHistPMEntry 79 }


geHistPMSIZE1024To1518Value OBJECT-TYPE
    SYNTAX       Unsigned64
    MAX-ACCESS   read-only
    STATUS       current
    DESCRIPTION  "The total number of frames received that are 1024 to 1518
                  bytes inclusive in length (excluding framing bits but
                  including FCS octets)."
    ::= { geHistPMEntry 80 }


geHistPMSIZE1024To1518TimeStamp OBJECT-TYPE
    SYNTAX       DateAndTime
    MAX-ACCESS   read-only
    STATUS       current
    DESCRIPTION  "The date and time stamp of the count of packets between 1024
                  and 1518 bytes."
    ::= { geHistPMEntry 81 }


geHistPMSIZE1024To1518Validity OBJECT-TYPE
    SYNTAX       PMValidity
    MAX-ACCESS   read-only
    STATUS       current
    DESCRIPTION  "Indicates the validity of the provided count of packets
                  between 1024 and 1518 bytes."
    ::= { geHistPMEntry 82 }


geHistPMSIZE1024To1518Initialize OBJECT-TYPE
    SYNTAX       InitializeCmd
    MAX-ACCESS   read-write
    STATUS       current
    DESCRIPTION  "Used to initialize the value of the
                  geHistPMSIZE1024To1518Value object to 0."
    ::= { geHistPMEntry 83 }


geHistPMSIZEOver1518Value OBJECT-TYPE
    SYNTAX       Unsigned64
    MAX-ACCESS   read-only
    STATUS       current
    DESCRIPTION  "The total number of frames received that are greater than or
                  equal to 1519 bytes in length (excluding framing bits but
                  including FCS octets)."
    ::= { geHistPMEntry 84 }


geHistPMSIZEOver1518TimeStamp OBJECT-TYPE
    SYNTAX       DateAndTime
    MAX-ACCESS   read-only
    STATUS       current
    DESCRIPTION  "The date and time stamp of the count of packets over 1518
                  bytes."
    ::= { geHistPMEntry 85 }


geHistPMSIZEOver1518Validity OBJECT-TYPE
    SYNTAX       PMValidity
    MAX-ACCESS   read-only
    STATUS       current
    DESCRIPTION  "Indicates the validity of the provided count of packets over
                  1518 bytes."
    ::= { geHistPMEntry 86 }


geHistPMSIZEOver1518Initialize OBJECT-TYPE
    SYNTAX       InitializeCmd
    MAX-ACCESS   read-write
    STATUS       current
    DESCRIPTION  "Used to initialize the value of the geHistPMSIZEOver1518Value
                  object to 0."
    ::= { geHistPMEntry 87 }


geHistPMTPFCRXValue OBJECT-TYPE
    SYNTAX       Unsigned64
    MAX-ACCESS   read-only
    STATUS       current
    DESCRIPTION  "The Gigabit Ethernet total received pause frame count."
    ::= { geHistPMEntry 88 }


geHistPMTPFCRXTimeStamp OBJECT-TYPE
    SYNTAX       DateAndTime
    MAX-ACCESS   read-only
    STATUS       current
    DESCRIPTION  "The date and time stamp of the GE total received pause frame
                  count value."
    ::= { geHistPMEntry 89 }


geHistPMTPFCRXValidity OBJECT-TYPE
    SYNTAX       PMValidity
    MAX-ACCESS   read-only
    STATUS       current
    DESCRIPTION  "Indicates the validity of the provided GE total received pause
                  frame count value."
    ::= { geHistPMEntry 90 }


geHistPMTPFCRXInitialize OBJECT-TYPE
    SYNTAX       InitializeCmd
    MAX-ACCESS   read-write
    STATUS       current
    DESCRIPTION  "Used to initialize the value of the geHistPMTPFCRXValue object
                  to 0."
    ::= { geHistPMEntry 91 }


geHistPMTPFCTXValue OBJECT-TYPE
    SYNTAX       Unsigned64
    MAX-ACCESS   read-only
    STATUS       current
    DESCRIPTION  "The Gigabit Ethernet total transmitted pause frame count."
    ::= { geHistPMEntry 92 }


geHistPMTPFCTXTimeStamp OBJECT-TYPE
    SYNTAX       DateAndTime
    MAX-ACCESS   read-only
    STATUS       current
    DESCRIPTION  "The date and time stamp of the GE total transmitted pause
                  frame count value."
    ::= { geHistPMEntry 93 }


geHistPMTPFCTXValidity OBJECT-TYPE
    SYNTAX       PMValidity
    MAX-ACCESS   read-only
    STATUS       current
    DESCRIPTION  "Indicates the validity of the provided GE total transmitted
                  pause frame count value."
    ::= { geHistPMEntry 94 }


geHistPMTPFCTXInitialize OBJECT-TYPE
    SYNTAX       InitializeCmd
    MAX-ACCESS   read-write
    STATUS       current
    DESCRIPTION  "Used to initialize the value of the geHistPMTPFCTXValue object
                  to 0."
    ::= { geHistPMEntry 95 }


geHistPMUSIZEValue OBJECT-TYPE
    SYNTAX       Unsigned32
    MAX-ACCESS   read-write
    STATUS       current
    DESCRIPTION  "The total number of frames received that were less than 64
                  octets long (excluding framing bits, but including FCS octets)
                  and were otherwise well formed."
    ::= { geHistPMEntry 96 }


geHistPMUSIZETimeStamp OBJECT-TYPE
    SYNTAX       DateAndTime
    MAX-ACCESS   read-only
    STATUS       current
    DESCRIPTION  "The date and time stamp of the count of undersized packets."
    ::= { geHistPMEntry 97 }


geHistPMUSIZEValidity OBJECT-TYPE
    SYNTAX       PMValidity
    MAX-ACCESS   read-only
    STATUS       current
    DESCRIPTION  "Indicates the validity of the provided count of undersized
                  packets."
    ::= { geHistPMEntry 98 }


geHistPMOSIZEValue OBJECT-TYPE
    SYNTAX       Unsigned32
    MAX-ACCESS   read-write
    STATUS       current
    DESCRIPTION  "The total number of frames received that were longer than 9600
                  octets (excluding framing bits, but including FCS octets) and
                  were otherwise well formed."
    ::= { geHistPMEntry 99 }


geHistPMOSIZETimeStamp OBJECT-TYPE
    SYNTAX       DateAndTime
    MAX-ACCESS   read-only
    STATUS       current
    DESCRIPTION  "The date and time stamp of the count of oversized packets."
    ::= { geHistPMEntry 100 }


geHistPMOSIZEValidity OBJECT-TYPE
    SYNTAX       PMValidity
    MAX-ACCESS   read-only
    STATUS       current
    DESCRIPTION  "Indicates the validity of the provided count of oversized
                  packets."
    ::= { geHistPMEntry 101 }


geHistPMFRGTValue OBJECT-TYPE
    SYNTAX       Unsigned32
    MAX-ACCESS   read-write
    STATUS       current
    DESCRIPTION  "The total number of frames received that were less than 64
                  octets in length (excluding framing bits but including FCS
                  octets) and had either a bad Frame Check Sequence (FCS) with
                  an integral number of octets (FCS Error) or a bad FCS with a
                  non-integral number of octets (Alignment Error)."
    ::= { geHistPMEntry 102 }


geHistPMFRGTTimeStamp OBJECT-TYPE
    SYNTAX       DateAndTime
    MAX-ACCESS   read-only
    STATUS       current
    DESCRIPTION  "The date and time stamp of the count of received packet
                  fragments."
    ::= { geHistPMEntry 103 }


geHistPMFRGTValidity OBJECT-TYPE
    SYNTAX       PMValidity
    MAX-ACCESS   read-only
    STATUS       current
    DESCRIPTION  "Indicates the validity of the provided count of received
                  packet fragments."
    ::= { geHistPMEntry 104 }


geHistPMJABRValue OBJECT-TYPE
    SYNTAX       Unsigned32
    MAX-ACCESS   read-write
    STATUS       current
    DESCRIPTION  "The total number of frames received that were longer than
                  14336 9600 octets (excluding framing bits, but including FCS
                  octets), and had either a bad Frame Check Sequence (FCS) with
                  an integral number of octets (FCS Error) or a bad FCS with
                  non-integral number of octets (Alignment Error)."
    ::= { geHistPMEntry 105 }


geHistPMJABRTimeStamp OBJECT-TYPE
    SYNTAX       DateAndTime
    MAX-ACCESS   read-only
    STATUS       current
    DESCRIPTION  "The date and time stamp of the count of received jabbers."
    ::= { geHistPMEntry 106 }


geHistPMJABRValidity OBJECT-TYPE
    SYNTAX       PMValidity
    MAX-ACCESS   read-only
    STATUS       current
    DESCRIPTION  "Indicates the validity of the provided count of received
                  jabbers."
    ::= { geHistPMEntry 107 }


geHistPMCVInitialize OBJECT-TYPE
    SYNTAX       InitializeCmd
    MAX-ACCESS   read-write
    STATUS       current
    DESCRIPTION  "Used to initialize the value of the geHistPMCVValue object to
                  0."
    ::= { geHistPMEntry 108 }


geHistPMESInitialize OBJECT-TYPE
    SYNTAX       InitializeCmd
    MAX-ACCESS   read-write
    STATUS       current
    DESCRIPTION  "Used to initialize the value of the geHistPMESValue object to
                  0."
    ::= { geHistPMEntry 109 }


geHistPMSESInitialize OBJECT-TYPE
    SYNTAX       InitializeCmd
    MAX-ACCESS   read-write
    STATUS       current
    DESCRIPTION  "Used to initialize the value of the geHistPMSESValue object to
                  0."
    ::= { geHistPMEntry 110 }


geHistPMFCSEInitialize OBJECT-TYPE
    SYNTAX       InitializeCmd
    MAX-ACCESS   read-write
    STATUS       current
    DESCRIPTION  "Used to initialize the value of the geHistPMFCSEValue object
                  to 0."
    ::= { geHistPMEntry 111 }


geHistPMFRDRInitialize OBJECT-TYPE
    SYNTAX       InitializeCmd
    MAX-ACCESS   read-write
    STATUS       current
    DESCRIPTION  "Used to initialize the value of the geHistPMFRDRValue object
                  to 0."
    ::= { geHistPMEntry 112 }


geHistPMUSIZEInitialize OBJECT-TYPE
    SYNTAX       InitializeCmd
    MAX-ACCESS   read-write
    STATUS       current
    DESCRIPTION  "Used to initialize the value of the geHistPMUSIZEValue object
                  to 0."
    ::= { geHistPMEntry 113 }


geHistPMOSIZEInitialize OBJECT-TYPE
    SYNTAX       InitializeCmd
    MAX-ACCESS   read-write
    STATUS       current
    DESCRIPTION  "Used to initialize the value of the geHistPMOSIZEValue object
                  to 0."
    ::= { geHistPMEntry 114 }


geHistPMFRGTInitialize OBJECT-TYPE
    SYNTAX       InitializeCmd
    MAX-ACCESS   read-write
    STATUS       current
    DESCRIPTION  "Used to initialize the value of the geHistPMFRGTValue object
                  to 0."
    ::= { geHistPMEntry 115 }


geHistPMJABRInitialize OBJECT-TYPE
    SYNTAX       InitializeCmd
    MAX-ACCESS   read-write
    STATUS       current
    DESCRIPTION  "Used to initialize the value of the geHistPMJABRValue object
                  to 0."
    ::= { geHistPMEntry 116 }

geHistPMUASValue OBJECT-TYPE
    SYNTAX       Unsigned32
    MAX-ACCESS   read-write
    STATUS       current
    DESCRIPTION  "The count of unavailable seconds. This object applies
                  only to transciever ports provisioned for the gigabit ethernet
                  protocol."
    ::= { geHistPMEntry 117 }

geHistPMUASTimeStamp OBJECT-TYPE
    SYNTAX       DateAndTime
    MAX-ACCESS   read-only
    STATUS       current
    DESCRIPTION  "The date and time stamp of the unavailable seconds
                  value."
    ::= { geHistPMEntry 118 }


geHistPMUASValidity OBJECT-TYPE
    SYNTAX       PMValidity
    MAX-ACCESS   read-only
    STATUS       current
    DESCRIPTION  "Indicates the validity of the provided unavailable
                  seconds value."
    ::= { geHistPMEntry 119 }


geHistPMUASInitialize OBJECT-TYPE
    SYNTAX       InitializeCmd
    MAX-ACCESS   read-write
    STATUS       current
    DESCRIPTION  "Used to initialize the value of the geHistPMUASValue
                  object to 0."
    ::= { geHistPMEntry 120 }

geHistPMOPRMinValue OBJECT-TYPE
    SYNTAX       FixedX10
    UNITS        "dBm/10"
    MAX-ACCESS   read-only
    STATUS       current
    DESCRIPTION  "The minimum optical power received on the input of the transceiver."
    ::= { geHistPMEntry 121 }


geHistPMOPRMinTimeStamp OBJECT-TYPE
    SYNTAX       DateAndTime
    MAX-ACCESS   read-only
    STATUS       current
    DESCRIPTION  "The date and time stamp of the minimum optical power received value."
    ::= { geHistPMEntry 122 }


geHistPMOPRMinValidity OBJECT-TYPE
    SYNTAX       PMValidity
    MAX-ACCESS   read-only
    STATUS       current
    DESCRIPTION  "Indicates the validity of the provided minimum optical power received
                  value."
    ::= { geHistPMEntry 123 }

geHistPMOPRMinInitialize OBJECT-TYPE
    SYNTAX       InitializeCmd
    MAX-ACCESS   read-write
    STATUS       current
    DESCRIPTION  "Used to initialize the value of the geHistPMOPRMinValue
                  object to 0."
    ::= { geHistPMEntry 124 }

geHistPMOPRMaxValue OBJECT-TYPE
    SYNTAX       FixedX10
    UNITS        "dBm/10"
    MAX-ACCESS   read-only
    STATUS       current
    DESCRIPTION  "The maximum optical power received on the input of the transceiver."
    ::= { geHistPMEntry 125 }


geHistPMOPRMaxTimeStamp OBJECT-TYPE
    SYNTAX       DateAndTime
    MAX-ACCESS   read-only
    STATUS       current
    DESCRIPTION  "The date and time stamp of the maximum optical power received value."
    ::= { geHistPMEntry 126 }


geHistPMOPRMaxValidity OBJECT-TYPE
    SYNTAX       PMValidity
    MAX-ACCESS   read-only
    STATUS       current
    DESCRIPTION  "Indicates the validity of the provided maximum optical power received
                  value."
    ::= { geHistPMEntry 127 }

geHistPMOPRMaxInitialize OBJECT-TYPE
    SYNTAX       InitializeCmd
    MAX-ACCESS   read-write
    STATUS       current
    DESCRIPTION  "Used to initialize the value of the geHistPMOPRMaxValue
                  object to 0."
    ::= { geHistPMEntry 128 }

geHistPMOPRAvgValue OBJECT-TYPE
    SYNTAX       FixedX10
    UNITS        "dBm/10"
    MAX-ACCESS   read-only
    STATUS       current
    DESCRIPTION  "The average optical power received on the input of the transceiver."
    ::= { geHistPMEntry 129 }


geHistPMOPRAvgTimeStamp OBJECT-TYPE
    SYNTAX       DateAndTime
    MAX-ACCESS   read-only
    STATUS       current
    DESCRIPTION  "The date and time stamp of the average optical power received value."
    ::= { geHistPMEntry 130 }


geHistPMOPRAvgValidity OBJECT-TYPE
    SYNTAX       PMValidity
    MAX-ACCESS   read-only
    STATUS       current
    DESCRIPTION  "Indicates the validity of the provided average optical power received
                  value."
    ::= { geHistPMEntry 131 }

geHistPMOPRAvgInitialize OBJECT-TYPE
    SYNTAX       InitializeCmd
    MAX-ACCESS   read-write
    STATUS       current
    DESCRIPTION  "Used to initialize the value of the geHistPMOPRAvgValue
                  object to 0."
    ::= { geHistPMEntry 132 }

geHistPMOPTMinValue OBJECT-TYPE
    SYNTAX       FixedX10
    UNITS        "dBm/10"
    MAX-ACCESS   read-only
    STATUS       current
    DESCRIPTION  "The minimum optical power transmitted at the output of the
                  transceiver."
    ::= { geHistPMEntry 133 }

geHistPMOPTMinTimeStamp OBJECT-TYPE
    SYNTAX       DateAndTime
    MAX-ACCESS   read-only
    STATUS       current
    DESCRIPTION  "The date and time stamp of the minimum optical power transmitted
                  value."
    ::= { geHistPMEntry 134 }


geHistPMOPTMinValidity OBJECT-TYPE
    SYNTAX       PMValidity
    MAX-ACCESS   read-only
    STATUS       current
    DESCRIPTION  "Indicates the validity of the provided minimum optical power
                  transmitted value."
    ::= { geHistPMEntry 135 }

geHistPMOPTMinInitialize OBJECT-TYPE
    SYNTAX       InitializeCmd
    MAX-ACCESS   read-write
    STATUS       current
    DESCRIPTION  "Used to initialize the value of the geHistPMOPTMinValue
                  object to 0."
    ::= { geHistPMEntry 136 }

geHistPMOPTMaxValue OBJECT-TYPE
    SYNTAX       FixedX10
    UNITS        "dBm/10"
    MAX-ACCESS   read-only
    STATUS       current
    DESCRIPTION  "The maximum optical power transmitted at the output of the
                  transceiver."
    ::= { geHistPMEntry 137 }


geHistPMOPTMaxTimeStamp OBJECT-TYPE
    SYNTAX       DateAndTime
    MAX-ACCESS   read-only
    STATUS       current
    DESCRIPTION  "The date and time stamp of the maximum optical power transmitted
                  value."
    ::= { geHistPMEntry 138 }


geHistPMOPTMaxValidity OBJECT-TYPE
    SYNTAX       PMValidity
    MAX-ACCESS   read-only
    STATUS       current
    DESCRIPTION  "Indicates the validity of the provided maximum optical power
                  transmitted value."
    ::= { geHistPMEntry 139 }

geHistPMOPTMaxInitialize OBJECT-TYPE
    SYNTAX       InitializeCmd
    MAX-ACCESS   read-write
    STATUS       current
    DESCRIPTION  "Used to initialize the value of the geHistPMOPTMaxValue
                  object to 0."
    ::= { geHistPMEntry 140 }

geHistPMOPTAvgValue OBJECT-TYPE
    SYNTAX       FixedX10
    UNITS        "dBm/10"
    MAX-ACCESS   read-only
    STATUS       current
    DESCRIPTION  "The average optical power transmitted at the output of the
                  transceiver."
    ::= { geHistPMEntry 141 }


geHistPMOPTAvgTimeStamp OBJECT-TYPE
    SYNTAX       DateAndTime
    MAX-ACCESS   read-only
    STATUS       current
    DESCRIPTION  "The date and time stamp of the average optical power transmitted
                  value."
    ::= { geHistPMEntry 142 }

geHistPMOPTAvgValidity OBJECT-TYPE
    SYNTAX       PMValidity
    MAX-ACCESS   read-only
    STATUS       current
    DESCRIPTION  "Indicates the validity of the provided average optical power
                  transmitted value."
    ::= { geHistPMEntry 143 }

geHistPMOPTAvgInitialize OBJECT-TYPE
    SYNTAX       InitializeCmd
    MAX-ACCESS   read-write
    STATUS       current
    DESCRIPTION  "Used to initialize the value of the geHistPMOPTAvgValue
                  object to 0."
    ::= { geHistPMEntry 144 }


-----------------------------------------------------------------------
-- Objects used to manage Gigabit Ethernet Performance
-- Monitoring Threshold Levels
-- 
-- A listing of Gigabit Ethernet PM threshold levels is contained in 
-- the gePMThresholdTable of the BTI-7000-MIB. When retrieved, this 
-- table provides one row for each set of Gigabit Ethernet PM threshold 
-- data. 
-- 
-- The following table lists the objects in each entry of the 
-- gePMThresholdTable.
-----------------------------------------------------------------------


gePMThresholdTable OBJECT-TYPE
    SYNTAX       SEQUENCE OF GePMThresholdEntry
    MAX-ACCESS   not-accessible
    STATUS       current
    DESCRIPTION  "A table of threshold levels for performance monitoring counter
                  values on Gigabit Ethernet facilities, that are used in the
                  generation of threshold crossing alerts."
    ::= { performance 22 }


gePMThresholdEntry OBJECT-TYPE
    SYNTAX       GePMThresholdEntry
    MAX-ACCESS   not-accessible
    STATUS       current
    DESCRIPTION  "The row entry object of the Gigabit Ethernet performance
                  monitoring threshold table. Each row of this table contains a
                  set of PM thresholds for a given interval type that applies to
                  an individual GE facility."
    INDEX        { gePMThresholdShelfIdx,
                   gePMThresholdSlotIdx,
                   gePMThresholdPortIdx,
                   gePMThresholdIntervalTypeIdx }
    ::= { gePMThresholdTable 1 }


GePMThresholdEntry ::= SEQUENCE { gePMThresholdShelfIdx         INTEGER,
                                  gePMThresholdSlotIdx          INTEGER,
                                  gePMThresholdPortIdx          INTEGER,
                                  gePMThresholdIntervalTypeIdx  PMIntervalType,
                                  gePMThresholdCVValue          Unsigned32,
                                  gePMThresholdESValue          Unsigned32,
                                  gePMThresholdSESValue         Unsigned32,
                                  gePMThresholdFRDRValue        Unsigned32,
                                  gePMThresholdFCSEValue        Unsigned32,
                                  gePMThresholdUSIZEValue       Unsigned32,
                                  gePMThresholdOSIZEValue       Unsigned32,
                                  gePMThresholdFRGTValue        Unsigned32,
                                  gePMThresholdJABRValue        Unsigned32,
                                  gePMThresholdUASValue         Unsigned32}
      

gePMThresholdShelfIdx OBJECT-TYPE
    SYNTAX       INTEGER (1|11|21|31)
    MAX-ACCESS   not-accessible
    STATUS       current
    DESCRIPTION  "The shelf number on which the Gigabit Ethernet facility
                  targeted for PM thresholds is provisioned."
    ::= { gePMThresholdEntry 1 }


gePMThresholdSlotIdx OBJECT-TYPE
    SYNTAX       INTEGER (1..20)
    MAX-ACCESS   not-accessible
    STATUS       current
    DESCRIPTION  "The slot number on which the Gigabit Ethernet facility
                  targeted for PM thresholds is provisioned."
    ::= { gePMThresholdEntry 2 }


gePMThresholdPortIdx OBJECT-TYPE
    SYNTAX       INTEGER (3..12)
    MAX-ACCESS   not-accessible
    STATUS       current
    DESCRIPTION  "The number of the port on the circuit pack on which the
                  Gigabit Ethernet facility targeted for PM thresholds is
                  provisioned."
    ::= { gePMThresholdEntry 3 }


gePMThresholdIntervalTypeIdx OBJECT-TYPE
    SYNTAX       PMIntervalType 
    MAX-ACCESS   not-accessible
    STATUS       current
    DESCRIPTION  "The type of PM bin according to interval length. Thresholds
                  are supported for the 15-minute and 1-day PM bins only."
    ::= { gePMThresholdEntry 4 }


gePMThresholdCVValue OBJECT-TYPE
    SYNTAX       Unsigned32
    MAX-ACCESS   read-write
    STATUS       current
    DESCRIPTION  "The threshold for the count of Gigabit Ethernet 8B/10B coding
                  violations."
    ::= { gePMThresholdEntry 5 }


gePMThresholdESValue OBJECT-TYPE
    SYNTAX       Unsigned32
    MAX-ACCESS   read-write
    STATUS       current
    DESCRIPTION  "The threshold for the count of Gigabit Ethernet errored
                  seconds."
    ::= { gePMThresholdEntry 6 }


gePMThresholdSESValue OBJECT-TYPE
    SYNTAX       Unsigned32
    MAX-ACCESS   read-write
    STATUS       current
    DESCRIPTION  "The threshold for the count of Gigabit Ethernet severely
                  errored seconds."
    ::= { gePMThresholdEntry 7 }


gePMThresholdFRDRValue OBJECT-TYPE
    SYNTAX       Unsigned32
    MAX-ACCESS   read-write
    STATUS       current
    DESCRIPTION  "The threshold for the count of Gigabit Ethernet discarded
                  frames."
    ::= { gePMThresholdEntry 8 }


gePMThresholdFCSEValue OBJECT-TYPE
    SYNTAX       Unsigned32
    MAX-ACCESS   read-write
    STATUS       current
    DESCRIPTION  "The threshold for the count of Gigabit Ethernet frame check
                  sum errors."
    ::= { gePMThresholdEntry 9 }


gePMThresholdUSIZEValue OBJECT-TYPE
    SYNTAX       Unsigned32
    MAX-ACCESS   read-write
    STATUS       current
    DESCRIPTION  "The threshold for the count of Gigabit Ethernet undersized
                  frames."
    ::= { gePMThresholdEntry 10 }


gePMThresholdOSIZEValue OBJECT-TYPE
    SYNTAX       Unsigned32
    MAX-ACCESS   read-write
    STATUS       current
    DESCRIPTION  "The threshold for the count of Gigabit Ethernet oversized
                  frames."
    ::= { gePMThresholdEntry 11 }


gePMThresholdFRGTValue OBJECT-TYPE
    SYNTAX       Unsigned32
    MAX-ACCESS   read-write
    STATUS       current
    DESCRIPTION  "The threshold for the count of Gigabit Ethernet frame
                  fragments."
    ::= { gePMThresholdEntry 12 }


gePMThresholdJABRValue OBJECT-TYPE
    SYNTAX       Unsigned32
    MAX-ACCESS   read-write
    STATUS       current
    DESCRIPTION  "The threshold for the count of Gigabit Ethernet jabbers."
    ::= { gePMThresholdEntry 13 }

gePMThresholdUASValue OBJECT-TYPE
    SYNTAX       Unsigned32
    MAX-ACCESS   read-write
    STATUS       current
    DESCRIPTION  "The threshold for the count of Gigabit Ethernet unavailable seconds."
    ::= { gePMThresholdEntry 14 }

-----------------------------------------------------------------------
-- Objects used to retrieve current Fiber Channel
-- Performance Monitoring statistics
-----------------------------------------------------------------------


fcCrntPMTable OBJECT-TYPE
    SYNTAX       SEQUENCE OF FcCrntPMEntry
    MAX-ACCESS   not-accessible
    STATUS       current
    DESCRIPTION  "A table of current performance monitoring statistics collected
                  for the Fiber Channel facilities on the NE."
    ::= { performance 23 }


fcCrntPMEntry OBJECT-TYPE
    SYNTAX       FcCrntPMEntry
    MAX-ACCESS   not-accessible
    STATUS       current
    DESCRIPTION  "The row entry object of the Fiber Channel current performance
                  monitoring table. Each row of this table contains a full set
                  of PM statistics and related data for a current measurement
                  interval for a given Fiber Channel facility."
    INDEX        { fcCrntPMShelfIdx,
                   fcCrntPMSlotIdx,
                   fcCrntPMPortIdx,
                   fcCrntPMIntervalTypeIdx }
    ::= { fcCrntPMTable 1 }


FcCrntPMEntry ::= SEQUENCE { fcCrntPMShelfIdx                  INTEGER,
                             fcCrntPMSlotIdx                   INTEGER,
                             fcCrntPMPortIdx                   INTEGER,
                             fcCrntPMIntervalTypeIdx           PMIntervalType,
                             fcCrntPMOPRValue                  FixedX10,
                             fcCrntPMOPRTimeStamp              DateAndTime,
                             fcCrntPMOPRValidity               PMValidity,
                             fcCrntPMOPTValue                  FixedX10,
                             fcCrntPMOPTTimeStamp              DateAndTime,
                             fcCrntPMOPTValidity               PMValidity,
                             fcCrntPMTempValue                 INTEGER,
                             fcCrntPMTempTimeStamp             DateAndTime,
                             fcCrntPMTempValidity              PMValidity,
                             fcCrntPMSupplyVoltageValue        FixedX10,
                             fcCrntPMSupplyVoltageTimeStamp    DateAndTime,
                             fcCrntPMSupplyVoltageValidity     PMValidity,
                             fcCrntPMLBCValue                  INTEGER,
                             fcCrntPMLBCTimeStamp              DateAndTime,
                             fcCrntPMLBCValidity               PMValidity,
                             fcCrntPMCVValue                   Unsigned32,
                             fcCrntPMCVTimeStamp               DateAndTime,
                             fcCrntPMCVValidity                PMValidity,
                             fcCrntPMESValue                   Unsigned32,
                             fcCrntPMESTimeStamp               DateAndTime,
                             fcCrntPMESValidity                PMValidity,
                             fcCrntPMSESValue                  Unsigned32,
                             fcCrntPMSESTimeStamp              DateAndTime,
                             fcCrntPMSESValidity               PMValidity,
                             fcCrntPMCVInitialize              InitializeCmd,
                             fcCrntPMESInitialize              InitializeCmd,
                             fcCrntPMSESInitialize             InitializeCmd,
                             fcCrntPMUASValue                  Unsigned32,
			     fcCrntPMUASTimeStamp              DateAndTime,
			     fcCrntPMUASValidity               PMValidity,
			     fcCrntPMUASInitialize             InitializeCmd,
                             fcCrntPMOPRMinValue               FixedX10,
                             fcCrntPMOPRMinTimeStamp           DateAndTime,
                             fcCrntPMOPRMinValidity            PMValidity,
                             fcCrntPMOPRMinInitialize          InitializeCmd,
                             fcCrntPMOPRMaxValue               FixedX10,
                             fcCrntPMOPRMaxTimeStamp           DateAndTime,
                             fcCrntPMOPRMaxValidity            PMValidity,
                             fcCrntPMOPRMaxInitialize          InitializeCmd,
                             fcCrntPMOPRAvgValue               FixedX10,
                             fcCrntPMOPRAvgTimeStamp           DateAndTime,
                             fcCrntPMOPRAvgValidity            PMValidity,
                             fcCrntPMOPRAvgInitialize          InitializeCmd,
                             fcCrntPMOPTMinValue               FixedX10,
                             fcCrntPMOPTMinTimeStamp           DateAndTime,
                             fcCrntPMOPTMinValidity            PMValidity,
                             fcCrntPMOPTMinInitialize          InitializeCmd,
                             fcCrntPMOPTMaxValue               FixedX10,
                             fcCrntPMOPTMaxTimeStamp           DateAndTime,
                             fcCrntPMOPTMaxValidity            PMValidity,
                             fcCrntPMOPTMaxInitialize          InitializeCmd,
                             fcCrntPMOPTAvgValue               FixedX10,
                             fcCrntPMOPTAvgTimeStamp           DateAndTime,
                             fcCrntPMOPTAvgValidity            PMValidity,
                             fcCrntPMOPTAvgInitialize          InitializeCmd }


fcCrntPMShelfIdx OBJECT-TYPE
    SYNTAX       INTEGER (1|11|21|31)
    MAX-ACCESS   not-accessible
    STATUS       current
    DESCRIPTION  "The number of the shelf on which the FC facility targeted for
                  PMs is provisioned."
    ::= { fcCrntPMEntry 1 }


fcCrntPMSlotIdx OBJECT-TYPE
    SYNTAX       INTEGER (1|3|5|7|9|11|13|15|17|19)
    MAX-ACCESS   not-accessible
    STATUS       current
    DESCRIPTION  "The number of the slot within which the FC facility targeted
                  for PMs is provisioned."
    ::= { fcCrntPMEntry 2 }


fcCrntPMPortIdx OBJECT-TYPE
    SYNTAX       INTEGER (3..12)
    MAX-ACCESS   not-accessible
    STATUS       current
    DESCRIPTION  "The number of the port on the circuit pack on which the FC
                  facility targeted for PMs is provisioned."
    ::= { fcCrntPMEntry 3 }


fcCrntPMIntervalTypeIdx OBJECT-TYPE
    SYNTAX       PMIntervalType
    MAX-ACCESS   not-accessible
    STATUS       current
    DESCRIPTION  "The type of PM bin according to interval length."
    ::= { fcCrntPMEntry 4 }


fcCrntPMOPRValue OBJECT-TYPE
    SYNTAX       FixedX10
    UNITS        "dBm/10"
    MAX-ACCESS   read-only
    STATUS       current
    DESCRIPTION  "The optical power received on the input of the FC facility
                  port."
    ::= { fcCrntPMEntry 5 }


fcCrntPMOPRTimeStamp OBJECT-TYPE
    SYNTAX       DateAndTime
    MAX-ACCESS   read-only
    STATUS       current
    DESCRIPTION  "The date and time stamp of the optical power received value."
    ::= { fcCrntPMEntry 6 }


fcCrntPMOPRValidity OBJECT-TYPE
    SYNTAX       PMValidity
    MAX-ACCESS   read-only
    STATUS       current
    DESCRIPTION  "Indicates the validity of the provided optical power received
                  value."
    ::= { fcCrntPMEntry 7 }


fcCrntPMOPTValue OBJECT-TYPE
    SYNTAX       FixedX10
    UNITS        "dBm/10"
    MAX-ACCESS   read-only
    STATUS       current
    DESCRIPTION  "The optical power transmitted at the output of the FC facility
                  port."
    ::= { fcCrntPMEntry 8 }


fcCrntPMOPTTimeStamp OBJECT-TYPE
    SYNTAX       DateAndTime
    MAX-ACCESS   read-only
    STATUS       current
    DESCRIPTION  "The date and time stamp of the optical power transmitted
                  value."
    ::= { fcCrntPMEntry 9 }


fcCrntPMOPTValidity OBJECT-TYPE
    SYNTAX       PMValidity
    MAX-ACCESS   read-only
    STATUS       current
    DESCRIPTION  "Indicates the validity of the provided optical power
                  transmitted value."
    ::= { fcCrntPMEntry 10 }


fcCrntPMTempValue OBJECT-TYPE
    SYNTAX       INTEGER (-32768..32767)
    UNITS        "degrees Celsius"
    MAX-ACCESS   read-only
    STATUS       current
    DESCRIPTION  "The temperature measured on the FC facility port."
    ::= { fcCrntPMEntry 11 }


fcCrntPMTempTimeStamp OBJECT-TYPE
    SYNTAX       DateAndTime
    MAX-ACCESS   read-only
    STATUS       current
    DESCRIPTION  "The date and time stamp of the temperature value."
    ::= { fcCrntPMEntry 12 }


fcCrntPMTempValidity OBJECT-TYPE
    SYNTAX       PMValidity
    MAX-ACCESS   read-only
    STATUS       current
    DESCRIPTION  "Indicates the validity of the provided temperature value."
    ::= { fcCrntPMEntry 13 }


fcCrntPMSupplyVoltageValue OBJECT-TYPE
    SYNTAX       FixedX10
    UNITS        "mVolts/10"
    MAX-ACCESS   read-only
    STATUS       current
    DESCRIPTION  "The supply voltage measured on the FC facility port."
    ::= { fcCrntPMEntry 14 }


fcCrntPMSupplyVoltageTimeStamp OBJECT-TYPE
    SYNTAX       DateAndTime
    MAX-ACCESS   read-only
    STATUS       current
    DESCRIPTION  "The date and time stamp of the supply voltage value."
    ::= { fcCrntPMEntry 15 }


fcCrntPMSupplyVoltageValidity OBJECT-TYPE
    SYNTAX       PMValidity
    MAX-ACCESS   read-only
    STATUS       current
    DESCRIPTION  "Indicates the validity of the provided supply voltage value."
    ::= { fcCrntPMEntry 16 }


fcCrntPMLBCValue OBJECT-TYPE
    SYNTAX       INTEGER (-32768..32767)
    UNITS        "mAmp"
    MAX-ACCESS   read-only
    STATUS       current
    DESCRIPTION  "The laser bias current measured on the FC facility port."
    ::= { fcCrntPMEntry 17 }


fcCrntPMLBCTimeStamp OBJECT-TYPE
    SYNTAX       DateAndTime
    MAX-ACCESS   read-only
    STATUS       current
    DESCRIPTION  "The date and time stamp of the laser bias current value."
    ::= { fcCrntPMEntry 18 }


fcCrntPMLBCValidity OBJECT-TYPE
    SYNTAX       PMValidity
    MAX-ACCESS   read-only
    STATUS       current
    DESCRIPTION  "Indicates the validity of the provided laser bias current
                  value."
    ::= { fcCrntPMEntry 19 }


fcCrntPMCVValue OBJECT-TYPE
    SYNTAX       Unsigned32 
    MAX-ACCESS   read-write
    STATUS       current
    DESCRIPTION  "The count of Fiber Channel coding violations."
    ::= { fcCrntPMEntry 20 }


fcCrntPMCVTimeStamp OBJECT-TYPE
    SYNTAX       DateAndTime
    MAX-ACCESS   read-only
    STATUS       current
    DESCRIPTION  "The date and time stamp of the FC coding violations value."
    ::= { fcCrntPMEntry 21 }


fcCrntPMCVValidity OBJECT-TYPE
    SYNTAX       PMValidity
    MAX-ACCESS   read-only
    STATUS       current
    DESCRIPTION  "Indicates the validity of the provided FC coding violations
                  value."
    ::= { fcCrntPMEntry 22 }


fcCrntPMESValue OBJECT-TYPE
    SYNTAX       Unsigned32
    MAX-ACCESS   read-write
    STATUS       current
    DESCRIPTION  "The count of FC errored seconds."
    ::= { fcCrntPMEntry 23 }


fcCrntPMESTimeStamp OBJECT-TYPE
    SYNTAX       DateAndTime
    MAX-ACCESS   read-only
    STATUS       current
    DESCRIPTION  "The date and time stamp of the FC errored seconds value."
    ::= { fcCrntPMEntry 24 }


fcCrntPMESValidity OBJECT-TYPE
    SYNTAX       PMValidity
    MAX-ACCESS   read-only
    STATUS       current
    DESCRIPTION  "Indicates the validity of the provided FC errored seconds
                  value."
    ::= { fcCrntPMEntry 25 }


fcCrntPMSESValue OBJECT-TYPE
    SYNTAX       Unsigned32
    MAX-ACCESS   read-write
    STATUS       current
    DESCRIPTION  "The count of FC severely errored seconds."
    ::= { fcCrntPMEntry 26 }


fcCrntPMSESTimeStamp OBJECT-TYPE
    SYNTAX       DateAndTime
    MAX-ACCESS   read-only
    STATUS       current
    DESCRIPTION  "The date and time stamp of the FC severely errored seconds
                  value."
    ::= { fcCrntPMEntry 27 }


fcCrntPMSESValidity OBJECT-TYPE
    SYNTAX       PMValidity
    MAX-ACCESS   read-only
    STATUS       current
    DESCRIPTION  "Indicates the validity of the provided FC severely errored
                  seconds value."
    ::= { fcCrntPMEntry 28 }


fcCrntPMCVInitialize OBJECT-TYPE
    SYNTAX       InitializeCmd
    MAX-ACCESS   read-write
    STATUS       current
    DESCRIPTION  "Used to initialize the value of the fcCrntPMCVValue object to
                  0."
    ::= { fcCrntPMEntry 29 }


fcCrntPMESInitialize OBJECT-TYPE
    SYNTAX       InitializeCmd
    MAX-ACCESS   read-write
    STATUS       current
    DESCRIPTION  "Used to initialize the value of the fcCrntPMESValue object to
                  0."
    ::= { fcCrntPMEntry 30 }


fcCrntPMSESInitialize OBJECT-TYPE
    SYNTAX       InitializeCmd
    MAX-ACCESS   read-write
    STATUS       current
    DESCRIPTION  "Used to initialize the value of the fcCrntPMSESValue object to
                  0."
    ::= { fcCrntPMEntry 31 }

fcCrntPMUASValue OBJECT-TYPE
    SYNTAX       Unsigned32
    MAX-ACCESS   read-write
    STATUS       current
    DESCRIPTION  "The count of unavailable seconds. This object applies
                  only to transciever ports provisioned for the fiber
                  channel protocol."
    ::= { fcCrntPMEntry 32 }

fcCrntPMUASTimeStamp OBJECT-TYPE
    SYNTAX       DateAndTime
    MAX-ACCESS   read-only
    STATUS       current
    DESCRIPTION  "The date and time stamp of the unavailable seconds
                  value."
    ::= { fcCrntPMEntry 33 }


fcCrntPMUASValidity OBJECT-TYPE
    SYNTAX       PMValidity
    MAX-ACCESS   read-only
    STATUS       current
    DESCRIPTION  "Indicates the validity of the provided unavailable
                  seconds value."
    ::= { fcCrntPMEntry 34 }


fcCrntPMUASInitialize OBJECT-TYPE
    SYNTAX       InitializeCmd
    MAX-ACCESS   read-write
    STATUS       current
    DESCRIPTION  "Used to initialize the value of the fcCrntPMUASValue
                  object to 0."
    ::= { fcCrntPMEntry 35 }

fcCrntPMOPRMinValue OBJECT-TYPE
    SYNTAX       FixedX10
    UNITS        "dBm/10"
    MAX-ACCESS   read-only
    STATUS       current
    DESCRIPTION  "The minimum optical power received on the input of the transceiver."
    ::= { fcCrntPMEntry 36 }


fcCrntPMOPRMinTimeStamp OBJECT-TYPE
    SYNTAX       DateAndTime
    MAX-ACCESS   read-only
    STATUS       current
    DESCRIPTION  "The date and time stamp of the minimum optical power received value."
    ::= { fcCrntPMEntry 37 }


fcCrntPMOPRMinValidity OBJECT-TYPE
    SYNTAX       PMValidity
    MAX-ACCESS   read-only
    STATUS       current
    DESCRIPTION  "Indicates the validity of the provided minimum optical power received
                  value."
    ::= { fcCrntPMEntry 38 }

fcCrntPMOPRMinInitialize OBJECT-TYPE
    SYNTAX       InitializeCmd
    MAX-ACCESS   read-write
    STATUS       current
    DESCRIPTION  "Used to initialize the value of the fcCrntPMOPRMinValue
                  object to 0."
    ::= { fcCrntPMEntry 39 }

fcCrntPMOPRMaxValue OBJECT-TYPE
    SYNTAX       FixedX10
    UNITS        "dBm/10"
    MAX-ACCESS   read-only
    STATUS       current
    DESCRIPTION  "The maximum optical power received on the input of the transceiver."
    ::= { fcCrntPMEntry 40 }


fcCrntPMOPRMaxTimeStamp OBJECT-TYPE
    SYNTAX       DateAndTime
    MAX-ACCESS   read-only
    STATUS       current
    DESCRIPTION  "The date and time stamp of the maximum optical power received value."
    ::= { fcCrntPMEntry 41 }


fcCrntPMOPRMaxValidity OBJECT-TYPE
    SYNTAX       PMValidity
    MAX-ACCESS   read-only
    STATUS       current
    DESCRIPTION  "Indicates the validity of the provided maximum optical power received
                  value."
    ::= { fcCrntPMEntry 42 }

fcCrntPMOPRMaxInitialize OBJECT-TYPE
    SYNTAX       InitializeCmd
    MAX-ACCESS   read-write
    STATUS       current
    DESCRIPTION  "Used to initialize the value of the fcCrntPMOPRMaxValue
                  object to 0."
    ::= { fcCrntPMEntry 43 }

fcCrntPMOPRAvgValue OBJECT-TYPE
    SYNTAX       FixedX10
    UNITS        "dBm/10"
    MAX-ACCESS   read-only
    STATUS       current
    DESCRIPTION  "The average optical power received on the input of the transceiver."
    ::= { fcCrntPMEntry 44 }


fcCrntPMOPRAvgTimeStamp OBJECT-TYPE
    SYNTAX       DateAndTime
    MAX-ACCESS   read-only
    STATUS       current
    DESCRIPTION  "The date and time stamp of the average optical power received value."
    ::= { fcCrntPMEntry 45 }


fcCrntPMOPRAvgValidity OBJECT-TYPE
    SYNTAX       PMValidity
    MAX-ACCESS   read-only
    STATUS       current
    DESCRIPTION  "Indicates the validity of the provided average optical power received
                  value."
    ::= { fcCrntPMEntry 46 }

fcCrntPMOPRAvgInitialize OBJECT-TYPE
    SYNTAX       InitializeCmd
    MAX-ACCESS   read-write
    STATUS       current
    DESCRIPTION  "Used to initialize the value of the fcCrntPMOPRAvgValue
                  object to 0."
    ::= { fcCrntPMEntry 47 }

fcCrntPMOPTMinValue OBJECT-TYPE
    SYNTAX       FixedX10
    UNITS        "dBm/10"
    MAX-ACCESS   read-only
    STATUS       current
    DESCRIPTION  "The minimum optical power transmitted at the output of the
                  transceiver."
    ::= { fcCrntPMEntry 48 }

fcCrntPMOPTMinTimeStamp OBJECT-TYPE
    SYNTAX       DateAndTime
    MAX-ACCESS   read-only
    STATUS       current
    DESCRIPTION  "The date and time stamp of the minimum optical power transmitted
                  value."
    ::= { fcCrntPMEntry 49 }


fcCrntPMOPTMinValidity OBJECT-TYPE
    SYNTAX       PMValidity
    MAX-ACCESS   read-only
    STATUS       current
    DESCRIPTION  "Indicates the validity of the provided minimum optical power
                  transmitted value."
    ::= { fcCrntPMEntry 50 }

fcCrntPMOPTMinInitialize OBJECT-TYPE
    SYNTAX       InitializeCmd
    MAX-ACCESS   read-write
    STATUS       current
    DESCRIPTION  "Used to initialize the value of the fcCrntPMOPTMinValue
                  object to 0."
    ::= { fcCrntPMEntry 51 }

fcCrntPMOPTMaxValue OBJECT-TYPE
    SYNTAX       FixedX10
    UNITS        "dBm/10"
    MAX-ACCESS   read-only
    STATUS       current
    DESCRIPTION  "The maximum optical power transmitted at the output of the
                  transceiver."
    ::= { fcCrntPMEntry 52 }


fcCrntPMOPTMaxTimeStamp OBJECT-TYPE
    SYNTAX       DateAndTime
    MAX-ACCESS   read-only
    STATUS       current
    DESCRIPTION  "The date and time stamp of the maximum optical power transmitted
                  value."
    ::= { fcCrntPMEntry 53 }


fcCrntPMOPTMaxValidity OBJECT-TYPE
    SYNTAX       PMValidity
    MAX-ACCESS   read-only
    STATUS       current
    DESCRIPTION  "Indicates the validity of the provided maximum optical power
                  transmitted value."
    ::= { fcCrntPMEntry 54 }

fcCrntPMOPTMaxInitialize OBJECT-TYPE
    SYNTAX       InitializeCmd
    MAX-ACCESS   read-write
    STATUS       current
    DESCRIPTION  "Used to initialize the value of the fcCrntPMOPTMaxValue
                  object to 0."
    ::= { fcCrntPMEntry 55 }

fcCrntPMOPTAvgValue OBJECT-TYPE
    SYNTAX       FixedX10
    UNITS        "dBm/10"
    MAX-ACCESS   read-only
    STATUS       current
    DESCRIPTION  "The average optical power transmitted at the output of the
                  transceiver."
    ::= { fcCrntPMEntry 56 }


fcCrntPMOPTAvgTimeStamp OBJECT-TYPE
    SYNTAX       DateAndTime
    MAX-ACCESS   read-only
    STATUS       current
    DESCRIPTION  "The date and time stamp of the average optical power transmitted
                  value."
    ::= { fcCrntPMEntry 57 }

fcCrntPMOPTAvgValidity OBJECT-TYPE
    SYNTAX       PMValidity
    MAX-ACCESS   read-only
    STATUS       current
    DESCRIPTION  "Indicates the validity of the provided average optical power
                  transmitted value."
    ::= { fcCrntPMEntry 58 }

fcCrntPMOPTAvgInitialize OBJECT-TYPE
    SYNTAX       InitializeCmd
    MAX-ACCESS   read-write
    STATUS       current
    DESCRIPTION  "Used to initialize the value of the fcCrntPMOPTAvgValue
                  object to 0."
    ::= { fcCrntPMEntry 59 }


-----------------------------------------------------------------------
-- Objects used to retrieve historical Fiber Channel
-- Performance Monitoring statistics
-----------------------------------------------------------------------


fcHistPMTable OBJECT-TYPE
    SYNTAX       SEQUENCE OF FcHistPMEntry
    MAX-ACCESS   not-accessible
    STATUS       current
    DESCRIPTION  "A table of historical performance monitoring statistics
                  collected for the Fiber Channel facilities on the NE."
    ::= { performance 24 }


fcHistPMEntry OBJECT-TYPE
    SYNTAX       FcHistPMEntry
    MAX-ACCESS   not-accessible
    STATUS       current
    DESCRIPTION  "The row entry object of the Fiber Channel historical
                  performance monitoring table. Each row of this table contains
                  a full set of PM statistics and related data for a historical
                  measurement interval for a given Fiber Channel facility."
    INDEX        { fcHistPMShelfIdx,
                   fcHistPMSlotIdx,
                   fcHistPMPortIdx,
                   fcHistPMIntervalTypeIdx,
                   fcHistPMIntervalIdx }
    ::= { fcHistPMTable 1 }


FcHistPMEntry ::= SEQUENCE { fcHistPMShelfIdx                  INTEGER,
                             fcHistPMSlotIdx                   INTEGER,
                             fcHistPMPortIdx                   INTEGER,
                             fcHistPMIntervalTypeIdx           PMIntervalType,
                             fcHistPMIntervalIdx               INTEGER,
                             fcHistPMOPRValue                  FixedX10,
                             fcHistPMOPRTimeStamp              DateAndTime,
                             fcHistPMOPRValidity               PMValidity,
                             fcHistPMOPTValue                  FixedX10,
                             fcHistPMOPTTimeStamp              DateAndTime,
                             fcHistPMOPTValidity               PMValidity,
                             fcHistPMTempValue                 INTEGER,
                             fcHistPMTempTimeStamp             DateAndTime,
                             fcHistPMTempValidity              PMValidity,
                             fcHistPMSupplyVoltageValue        FixedX10,
                             fcHistPMSupplyVoltageTimeStamp    DateAndTime,
                             fcHistPMSupplyVoltageValidity     PMValidity,
                             fcHistPMLBCValue                  INTEGER,
                             fcHistPMLBCTimeStamp              DateAndTime,
                             fcHistPMLBCValidity               PMValidity,
                             fcHistPMCVValue                   Unsigned32,
                             fcHistPMCVTimeStamp               DateAndTime,
                             fcHistPMCVValidity                PMValidity,
                             fcHistPMESValue                   Unsigned32,
                             fcHistPMESTimeStamp               DateAndTime,
                             fcHistPMESValidity                PMValidity,
                             fcHistPMSESValue                  Unsigned32,
                             fcHistPMSESTimeStamp              DateAndTime,
                             fcHistPMSESValidity               PMValidity,
                             fcHistPMCVInitialize              InitializeCmd,
                             fcHistPMESInitialize              InitializeCmd,
                             fcHistPMSESInitialize             InitializeCmd,
                             fcHistPMUASValue                  Unsigned32,
			     fcHistPMUASTimeStamp              DateAndTime,
			     fcHistPMUASValidity               PMValidity,
			     fcHistPMUASInitialize             InitializeCmd,
                             fcHistPMOPRMinValue               FixedX10,
                             fcHistPMOPRMinTimeStamp           DateAndTime,
                             fcHistPMOPRMinValidity            PMValidity,
                             fcHistPMOPRMinInitialize          InitializeCmd,
                             fcHistPMOPRMaxValue               FixedX10,
                             fcHistPMOPRMaxTimeStamp           DateAndTime,
                             fcHistPMOPRMaxValidity            PMValidity,
                             fcHistPMOPRMaxInitialize          InitializeCmd,
                             fcHistPMOPRAvgValue               FixedX10,
                             fcHistPMOPRAvgTimeStamp           DateAndTime,
                             fcHistPMOPRAvgValidity            PMValidity,
                             fcHistPMOPRAvgInitialize          InitializeCmd,
                             fcHistPMOPTMinValue               FixedX10,
                             fcHistPMOPTMinTimeStamp           DateAndTime,
                             fcHistPMOPTMinValidity            PMValidity,
                             fcHistPMOPTMinInitialize          InitializeCmd,
                             fcHistPMOPTMaxValue               FixedX10,
                             fcHistPMOPTMaxTimeStamp           DateAndTime,
                             fcHistPMOPTMaxValidity            PMValidity,
                             fcHistPMOPTMaxInitialize          InitializeCmd,
                             fcHistPMOPTAvgValue               FixedX10,
                             fcHistPMOPTAvgTimeStamp           DateAndTime,
                             fcHistPMOPTAvgValidity            PMValidity,
                             fcHistPMOPTAvgInitialize          InitializeCmd }


fcHistPMShelfIdx OBJECT-TYPE
    SYNTAX       INTEGER (1|11|21|31)
    MAX-ACCESS   not-accessible
    STATUS       current
    DESCRIPTION  "The number of the shelf on which the FC facility targeted for
                  PMs is provisioned."
    ::= { fcHistPMEntry 1 }


fcHistPMSlotIdx OBJECT-TYPE
    SYNTAX       INTEGER (1|3|5|7|9|11|13|15|17|19)
    MAX-ACCESS   not-accessible
    STATUS       current
    DESCRIPTION  "The number of the slot within which the FC facility targeted
                  for PMs is provisioned."
    ::= { fcHistPMEntry 2 }


fcHistPMPortIdx OBJECT-TYPE
    SYNTAX       INTEGER (3..12)
    MAX-ACCESS   not-accessible
    STATUS       current
    DESCRIPTION  "The number of the port on the circuit pack on which the FC
                  facility targeted for PMs is provisioned."
    ::= { fcHistPMEntry 3 }


fcHistPMIntervalTypeIdx OBJECT-TYPE
    SYNTAX       PMIntervalType
    MAX-ACCESS   not-accessible
    STATUS       current
    DESCRIPTION  "The type of PM bin according to interval length."
    ::= { fcHistPMEntry 4 }


fcHistPMIntervalIdx OBJECT-TYPE
    SYNTAX       INTEGER (1..96)
    MAX-ACCESS   not-accessible
    STATUS       current
    DESCRIPTION  "The specific PM bin number. The range is 1 to 96 for the
                  15-minute historical bins. For the 1-day historical bin, the
                  value is 1."
    ::= { fcHistPMEntry 5 }


fcHistPMOPRValue OBJECT-TYPE
    SYNTAX       FixedX10
    UNITS        "dBm/10"
    MAX-ACCESS   read-only
    STATUS       current
    DESCRIPTION  "The optical power received on the input of the FC facility
                  port."
    ::= { fcHistPMEntry 6 }


fcHistPMOPRTimeStamp OBJECT-TYPE
    SYNTAX       DateAndTime
    MAX-ACCESS   read-only
    STATUS       current
    DESCRIPTION  "The date and time stamp of the optical power received value."
    ::= { fcHistPMEntry 7 }


fcHistPMOPRValidity OBJECT-TYPE
    SYNTAX       PMValidity
    MAX-ACCESS   read-only
    STATUS       current
    DESCRIPTION  "Indicates the validity of the provided optical power received
                  value."
    ::= { fcHistPMEntry 8 }


fcHistPMOPTValue OBJECT-TYPE
    SYNTAX       FixedX10
    UNITS        "dBm/10"
    MAX-ACCESS   read-only
    STATUS       current
    DESCRIPTION  "The optical power transmitted at the output of the FC facility
                  port."
    ::= { fcHistPMEntry 9 }


fcHistPMOPTTimeStamp OBJECT-TYPE
    SYNTAX       DateAndTime
    MAX-ACCESS   read-only
    STATUS       current
    DESCRIPTION  "The date and time stamp of the optical power transmitted
                  value."
    ::= { fcHistPMEntry 10 }


fcHistPMOPTValidity OBJECT-TYPE
    SYNTAX       PMValidity
    MAX-ACCESS   read-only
    STATUS       current
    DESCRIPTION  "Indicates the validity of the provided optical power
                  transmitted value."
    ::= { fcHistPMEntry 11 }


fcHistPMTempValue OBJECT-TYPE
    SYNTAX       INTEGER (-32768..32767)
    UNITS        "degrees Celsius"
    MAX-ACCESS   read-only
    STATUS       current
    DESCRIPTION  "The temperature measured on the FC facility port."
    ::= { fcHistPMEntry 12 }


fcHistPMTempTimeStamp OBJECT-TYPE
    SYNTAX       DateAndTime
    MAX-ACCESS   read-only
    STATUS       current
    DESCRIPTION  "The date and time stamp of the temperature value."
    ::= { fcHistPMEntry 13 }


fcHistPMTempValidity OBJECT-TYPE
    SYNTAX       PMValidity
    MAX-ACCESS   read-only
    STATUS       current
    DESCRIPTION  "Indicates the validity of the provided temperature value."
    ::= { fcHistPMEntry 14 }


fcHistPMSupplyVoltageValue OBJECT-TYPE
    SYNTAX       FixedX10
    UNITS        "mVolts/10"
    MAX-ACCESS   read-only
    STATUS       current
    DESCRIPTION  "The supply voltage measured on the FC facility port."
    ::= { fcHistPMEntry 15 }


fcHistPMSupplyVoltageTimeStamp OBJECT-TYPE
    SYNTAX       DateAndTime
    MAX-ACCESS   read-only
    STATUS       current
    DESCRIPTION  "The date and time stamp of the supply voltage value."
    ::= { fcHistPMEntry 16 }


fcHistPMSupplyVoltageValidity OBJECT-TYPE
    SYNTAX       PMValidity
    MAX-ACCESS   read-only
    STATUS       current
    DESCRIPTION  "Indicates the validity of the provided supply voltage value."
    ::= { fcHistPMEntry 17 }


fcHistPMLBCValue OBJECT-TYPE
    SYNTAX       INTEGER (-32768..32767)
    UNITS        "mAmp"
    MAX-ACCESS   read-only
    STATUS       current
    DESCRIPTION  "The laser bias current measured on the FC facility port."
    ::= { fcHistPMEntry 18 }


fcHistPMLBCTimeStamp OBJECT-TYPE
    SYNTAX       DateAndTime
    MAX-ACCESS   read-only
    STATUS       current
    DESCRIPTION  "The date and time stamp of the laser bias current value."
    ::= { fcHistPMEntry 19 }


fcHistPMLBCValidity OBJECT-TYPE
    SYNTAX       PMValidity
    MAX-ACCESS   read-only
    STATUS       current
    DESCRIPTION  "Indicates the validity of the provided laser bias current
                  value."
    ::= { fcHistPMEntry 20 }


fcHistPMCVValue OBJECT-TYPE
    SYNTAX       Unsigned32 
    MAX-ACCESS   read-write
    STATUS       current
    DESCRIPTION  "The count of Fiber Channel coding violations."
    ::= { fcHistPMEntry 21 }


fcHistPMCVTimeStamp OBJECT-TYPE
    SYNTAX       DateAndTime
    MAX-ACCESS   read-only
    STATUS       current
    DESCRIPTION  "The date and time stamp of the FC coding violations value."
    ::= { fcHistPMEntry 22 }


fcHistPMCVValidity OBJECT-TYPE
    SYNTAX       PMValidity
    MAX-ACCESS   read-only
    STATUS       current
    DESCRIPTION  "Indicates the validity of the provided FC coding violations
                  value."
    ::= { fcHistPMEntry 23 }


fcHistPMESValue OBJECT-TYPE
    SYNTAX       Unsigned32
    MAX-ACCESS   read-write
    STATUS       current
    DESCRIPTION  "The count of FC errored seconds."
    ::= { fcHistPMEntry 24 }


fcHistPMESTimeStamp OBJECT-TYPE
    SYNTAX       DateAndTime
    MAX-ACCESS   read-only
    STATUS       current
    DESCRIPTION  "The date and time stamp of the FC errored seconds value."
    ::= { fcHistPMEntry 25 }


fcHistPMESValidity OBJECT-TYPE
    SYNTAX       PMValidity
    MAX-ACCESS   read-only
    STATUS       current
    DESCRIPTION  "Indicates the validity of the provided FC errored seconds
                  value."
    ::= { fcHistPMEntry 26 }


fcHistPMSESValue OBJECT-TYPE
    SYNTAX       Unsigned32
    MAX-ACCESS   read-write
    STATUS       current
    DESCRIPTION  "The count of FC severely errored seconds."
    ::= { fcHistPMEntry 27 }


fcHistPMSESTimeStamp OBJECT-TYPE
    SYNTAX       DateAndTime
    MAX-ACCESS   read-only
    STATUS       current
    DESCRIPTION  "The date and time stamp of the FC severely errored seconds
                  value."
    ::= { fcHistPMEntry 28 }


fcHistPMSESValidity OBJECT-TYPE
    SYNTAX       PMValidity
    MAX-ACCESS   read-only
    STATUS       current
    DESCRIPTION  "Indicates the validity of the provided FC severely errored
                  seconds value."
    ::= { fcHistPMEntry 29 }


fcHistPMCVInitialize OBJECT-TYPE
    SYNTAX       InitializeCmd
    MAX-ACCESS   read-write
    STATUS       current
    DESCRIPTION  "Used to initialize the value of the fcHistPMCVValue object to
                  0."
    ::= { fcHistPMEntry 30 }


fcHistPMESInitialize OBJECT-TYPE
    SYNTAX       InitializeCmd
    MAX-ACCESS   read-write
    STATUS       current
    DESCRIPTION  "Used to initialize the value of the fcHistPMESValue object to
                  0."
    ::= { fcHistPMEntry 31 }


fcHistPMSESInitialize OBJECT-TYPE
    SYNTAX       InitializeCmd
    MAX-ACCESS   read-write
    STATUS       current
    DESCRIPTION  "Used to initialize the value of the fcHistPMSESValue object to
                  0."
    ::= { fcHistPMEntry 32 }

fcHistPMUASValue OBJECT-TYPE
    SYNTAX       Unsigned32
    MAX-ACCESS   read-write
    STATUS       current
    DESCRIPTION  "The count of unavailable seconds. This object applies
                  only to transciever ports provisioned for the fiber
                  channel protocol."
    ::= { fcHistPMEntry 33 }

fcHistPMUASTimeStamp OBJECT-TYPE
    SYNTAX       DateAndTime
    MAX-ACCESS   read-only
    STATUS       current
    DESCRIPTION  "The date and time stamp of the unavailable seconds
                  value."
    ::= { fcHistPMEntry 34 }


fcHistPMUASValidity OBJECT-TYPE
    SYNTAX       PMValidity
    MAX-ACCESS   read-only
    STATUS       current
    DESCRIPTION  "Indicates the validity of the provided unavailable
                  seconds value."
    ::= { fcHistPMEntry 35 }


fcHistPMUASInitialize OBJECT-TYPE
    SYNTAX       InitializeCmd
    MAX-ACCESS   read-write
    STATUS       current
    DESCRIPTION  "Used to initialize the value of the fcHistPMUASValue
                  object to 0."
    ::= { fcHistPMEntry 36 }

fcHistPMOPRMinValue OBJECT-TYPE
    SYNTAX       FixedX10
    UNITS        "dBm/10"
    MAX-ACCESS   read-only
    STATUS       current
    DESCRIPTION  "The minimum optical power received on the input of the transceiver."
    ::= { fcHistPMEntry 37 }


fcHistPMOPRMinTimeStamp OBJECT-TYPE
    SYNTAX       DateAndTime
    MAX-ACCESS   read-only
    STATUS       current
    DESCRIPTION  "The date and time stamp of the minimum optical power received value."
    ::= { fcHistPMEntry 38 }


fcHistPMOPRMinValidity OBJECT-TYPE
    SYNTAX       PMValidity
    MAX-ACCESS   read-only
    STATUS       current
    DESCRIPTION  "Indicates the validity of the provided minimum optical power received
                  value."
    ::= { fcHistPMEntry 39 }

fcHistPMOPRMinInitialize OBJECT-TYPE
    SYNTAX       InitializeCmd
    MAX-ACCESS   read-write
    STATUS       current
    DESCRIPTION  "Used to initialize the value of the fcHistPMOPRMinValue
                  object to 0."
    ::= { fcHistPMEntry 40 }

fcHistPMOPRMaxValue OBJECT-TYPE
    SYNTAX       FixedX10
    UNITS        "dBm/10"
    MAX-ACCESS   read-only
    STATUS       current
    DESCRIPTION  "The maximum optical power received on the input of the transceiver."
    ::= { fcHistPMEntry 41 }


fcHistPMOPRMaxTimeStamp OBJECT-TYPE
    SYNTAX       DateAndTime
    MAX-ACCESS   read-only
    STATUS       current
    DESCRIPTION  "The date and time stamp of the maximum optical power received value."
    ::= { fcHistPMEntry 42 }


fcHistPMOPRMaxValidity OBJECT-TYPE
    SYNTAX       PMValidity
    MAX-ACCESS   read-only
    STATUS       current
    DESCRIPTION  "Indicates the validity of the provided maximum optical power received
                  value."
    ::= { fcHistPMEntry 43 }

fcHistPMOPRMaxInitialize OBJECT-TYPE
    SYNTAX       InitializeCmd
    MAX-ACCESS   read-write
    STATUS       current
    DESCRIPTION  "Used to initialize the value of the fcHistPMOPRMaxValue
                  object to 0."
    ::= { fcHistPMEntry 44 }

fcHistPMOPRAvgValue OBJECT-TYPE
    SYNTAX       FixedX10
    UNITS        "dBm/10"
    MAX-ACCESS   read-only
    STATUS       current
    DESCRIPTION  "The average optical power received on the input of the transceiver."
    ::= { fcHistPMEntry 45 }


fcHistPMOPRAvgTimeStamp OBJECT-TYPE
    SYNTAX       DateAndTime
    MAX-ACCESS   read-only
    STATUS       current
    DESCRIPTION  "The date and time stamp of the average optical power received value."
    ::= { fcHistPMEntry 46 }


fcHistPMOPRAvgValidity OBJECT-TYPE
    SYNTAX       PMValidity
    MAX-ACCESS   read-only
    STATUS       current
    DESCRIPTION  "Indicates the validity of the provided average optical power received
                  value."
    ::= { fcHistPMEntry 47 }

fcHistPMOPRAvgInitialize OBJECT-TYPE
    SYNTAX       InitializeCmd
    MAX-ACCESS   read-write
    STATUS       current
    DESCRIPTION  "Used to initialize the value of the fcHistPMOPRAvgValue
                  object to 0."
    ::= { fcHistPMEntry 48 }

fcHistPMOPTMinValue OBJECT-TYPE
    SYNTAX       FixedX10
    UNITS        "dBm/10"
    MAX-ACCESS   read-only
    STATUS       current
    DESCRIPTION  "The minimum optical power transmitted at the output of the
                  transceiver."
    ::= { fcHistPMEntry 49 }

fcHistPMOPTMinTimeStamp OBJECT-TYPE
    SYNTAX       DateAndTime
    MAX-ACCESS   read-only
    STATUS       current
    DESCRIPTION  "The date and time stamp of the minimum optical power transmitted
                  value."
    ::= { fcHistPMEntry 50 }


fcHistPMOPTMinValidity OBJECT-TYPE
    SYNTAX       PMValidity
    MAX-ACCESS   read-only
    STATUS       current
    DESCRIPTION  "Indicates the validity of the provided minimum optical power
                  transmitted value."
    ::= { fcHistPMEntry 51 }

fcHistPMOPTMinInitialize OBJECT-TYPE
    SYNTAX       InitializeCmd
    MAX-ACCESS   read-write
    STATUS       current
    DESCRIPTION  "Used to initialize the value of the fcHistPMOPTMinValue
                  object to 0."
    ::= { fcHistPMEntry 52 }

fcHistPMOPTMaxValue OBJECT-TYPE
    SYNTAX       FixedX10
    UNITS        "dBm/10"
    MAX-ACCESS   read-only
    STATUS       current
    DESCRIPTION  "The maximum optical power transmitted at the output of the
                  transceiver."
    ::= { fcHistPMEntry 53 }


fcHistPMOPTMaxTimeStamp OBJECT-TYPE
    SYNTAX       DateAndTime
    MAX-ACCESS   read-only
    STATUS       current
    DESCRIPTION  "The date and time stamp of the maximum optical power transmitted
                  value."
    ::= { fcHistPMEntry 54 }


fcHistPMOPTMaxValidity OBJECT-TYPE
    SYNTAX       PMValidity
    MAX-ACCESS   read-only
    STATUS       current
    DESCRIPTION  "Indicates the validity of the provided maximum optical power
                  transmitted value."
    ::= { fcHistPMEntry 55 }

fcHistPMOPTMaxInitialize OBJECT-TYPE
    SYNTAX       InitializeCmd
    MAX-ACCESS   read-write
    STATUS       current
    DESCRIPTION  "Used to initialize the value of the fcHistPMOPTMaxValue
                  object to 0."
    ::= { fcHistPMEntry 56 }

fcHistPMOPTAvgValue OBJECT-TYPE
    SYNTAX       FixedX10
    UNITS        "dBm/10"
    MAX-ACCESS   read-only
    STATUS       current
    DESCRIPTION  "The average optical power transmitted at the output of the
                  transceiver."
    ::= { fcHistPMEntry 57 }


fcHistPMOPTAvgTimeStamp OBJECT-TYPE
    SYNTAX       DateAndTime
    MAX-ACCESS   read-only
    STATUS       current
    DESCRIPTION  "The date and time stamp of the average optical power transmitted
                  value."
    ::= { fcHistPMEntry 58 }

fcHistPMOPTAvgValidity OBJECT-TYPE
    SYNTAX       PMValidity
    MAX-ACCESS   read-only
    STATUS       current
    DESCRIPTION  "Indicates the validity of the provided average optical power
                  transmitted value."
    ::= { fcHistPMEntry 59 }

fcHistPMOPTAvgInitialize OBJECT-TYPE
    SYNTAX       InitializeCmd
    MAX-ACCESS   read-write
    STATUS       current
    DESCRIPTION  "Used to initialize the value of the fcHistPMOPTAvgValue
                  object to 0."
    ::= { fcHistPMEntry 60 }


-----------------------------------------------------------------------
-- Objects used to manage Fiber Channel Performance
-- Monitoring Threshold Levels
-----------------------------------------------------------------------


fcPMThresholdTable OBJECT-TYPE
    SYNTAX       SEQUENCE OF FcPMThresholdEntry
    MAX-ACCESS   not-accessible
    STATUS       current
    DESCRIPTION  "A table of threshold levels for performance monitoring counter
                  values on Fiber Channel facilities, that are used in the
                  generation of threshold crossing alerts."
    ::= { performance 25 }


fcPMThresholdEntry OBJECT-TYPE
    SYNTAX       FcPMThresholdEntry
    MAX-ACCESS   not-accessible
    STATUS       current
    DESCRIPTION  "The row entry object of the Fiber Channel performance
                  monitoring threshold table. Each row of this table contains a
                  set of PM thresholds for a given interval type that applies to
                  an individual FC facility."
    INDEX        { fcPMThresholdShelfIdx,
                   fcPMThresholdSlotIdx,
                   fcPMThresholdPortIdx,
                   fcPMThresholdIntervalTypeIdx }
    ::= { fcPMThresholdTable 1 }


FcPMThresholdEntry ::= SEQUENCE { fcPMThresholdShelfIdx         INTEGER,
                                  fcPMThresholdSlotIdx          INTEGER,
                                  fcPMThresholdPortIdx          INTEGER,
                                  fcPMThresholdIntervalTypeIdx  PMIntervalType,
                                  fcPMThresholdCVValue          Unsigned32,
                                  fcPMThresholdESValue          Unsigned32,
                                  fcPMThresholdSESValue         Unsigned32,
                                  fcPMThresholdUASValue         Unsigned32 }
      

fcPMThresholdShelfIdx OBJECT-TYPE
    SYNTAX       INTEGER (1|11|21|31)
    MAX-ACCESS   not-accessible
    STATUS       current
    DESCRIPTION  "The shelf number on which the Fiber Channel facility targeted
                  for PM thresholds is provisioned."
    ::= { fcPMThresholdEntry 1 }


fcPMThresholdSlotIdx OBJECT-TYPE
    SYNTAX       INTEGER (1|3|5|7|9|11|13|15|17|19)
    MAX-ACCESS   not-accessible
    STATUS       current
    DESCRIPTION  "The slot number on which the Fiber Channel facility targeted
                  for PM thresholds is provisioned."
    ::= { fcPMThresholdEntry 2 }


fcPMThresholdPortIdx OBJECT-TYPE
    SYNTAX       INTEGER (3..12)
    MAX-ACCESS   not-accessible
    STATUS       current
    DESCRIPTION  "The number of the port on the circuit pack on which the Fiber
                  Channel facility targeted for PM thresholds is provisioned."
    ::= { fcPMThresholdEntry 3 }


fcPMThresholdIntervalTypeIdx OBJECT-TYPE
    SYNTAX       PMIntervalType 
    MAX-ACCESS   not-accessible
    STATUS       current
    DESCRIPTION  "The type of PM bin according to interval length. Thresholds
                  are supported for the 15-minute and 1-day PM bins only."
    ::= { fcPMThresholdEntry 4 }


fcPMThresholdCVValue OBJECT-TYPE
    SYNTAX       Unsigned32
    MAX-ACCESS   read-write
    STATUS       current
    DESCRIPTION  "The threshold for the count of Fiber Channel coding
                  violations."
    ::= { fcPMThresholdEntry 5 }


fcPMThresholdESValue OBJECT-TYPE
    SYNTAX       Unsigned32
    MAX-ACCESS   read-write
    STATUS       current
    DESCRIPTION  "The threshold for the count of Fiber Channel errored seconds."
    ::= { fcPMThresholdEntry 6 }


fcPMThresholdSESValue OBJECT-TYPE
    SYNTAX       Unsigned32
    MAX-ACCESS   read-write
    STATUS       current
    DESCRIPTION  "The threshold for the count of Fiber Channel severely errored
                  seconds."
    ::= { fcPMThresholdEntry 7 }

fcPMThresholdUASValue OBJECT-TYPE
    SYNTAX       Unsigned32
    MAX-ACCESS   read-write
    STATUS       current
    DESCRIPTION  "The threshold for the count of Fiber Channel unavailable seconds."
    ::= { fcPMThresholdEntry 8 }

-----------------------------------------------------------------------
-- Objects used to retrieve current Ethernet Layer 1 Interface
-- Performance Monitoring statistics
-----------------------------------------------------------------------


ethL1IFCrntPMTable OBJECT-TYPE
    SYNTAX       SEQUENCE OF EthL1IFCrntPMEntry
    MAX-ACCESS   not-accessible
    STATUS       current
    DESCRIPTION  "A table of current performance monitoring statistics collected
                  for the Ethernet Layer 1 Interface facilities on the NE."
    ::= { performance 26 }


ethL1IFCrntPMEntry OBJECT-TYPE
    SYNTAX       EthL1IFCrntPMEntry
    MAX-ACCESS   not-accessible
    STATUS       current
    DESCRIPTION  "The row entry object of the Ethernet Layer 1 Interface current
                  performance monitoring table. Each row of this table contains
                  a full set of PM statistics and related data for a current
                  measurement interval for a given Ethernet Layer 1 Interface facility."
    INDEX        { ethL1IFCrntPMShelfIdx,
                   ethL1IFCrntPMSlotIdx,
                   ethL1IFCrntPMPortTypeIdx,
                   ethL1IFCrntPMPortIdx,
                   ethL1IFCrntPMIntervalTypeIdx }
    ::= { ethL1IFCrntPMTable 1 }


EthL1IFCrntPMEntry ::= SEQUENCE { ethL1IFCrntPMShelfIdx                  INTEGER,
                                  ethL1IFCrntPMSlotIdx                   INTEGER,
                                  ethL1IFCrntPMPortTypeIdx               PvxL1PortType,
				  ethL1IFCrntPMPortIdx                   INTEGER,
                                  ethL1IFCrntPMIntervalTypeIdx           PMIntervalType,
                                  ethL1IFCrntPMOPRValue                  FixedX10,
                                  ethL1IFCrntPMOPRTimeStamp              DateAndTime,
                                  ethL1IFCrntPMOPRValidity               PMValidity,
                                  ethL1IFCrntPMOPTValue                  FixedX10,
                                  ethL1IFCrntPMOPTTimeStamp              DateAndTime,
                                  ethL1IFCrntPMOPTValidity               PMValidity,
                                  ethL1IFCrntPMTempValue                 INTEGER,
                                  ethL1IFCrntPMTempTimeStamp             DateAndTime,
                                  ethL1IFCrntPMTempValidity              PMValidity,
                                  ethL1IFCrntPMSupplyVoltageValue        FixedX10,
                                  ethL1IFCrntPMSupplyVoltageTimeStamp    DateAndTime,
                                  ethL1IFCrntPMSupplyVoltageValidity     PMValidity,
                                  ethL1IFCrntPMSupplyVoltage2Value       FixedX10,
                                  ethL1IFCrntPMSupplyVoltage2TimeStamp   DateAndTime,
                                  ethL1IFCrntPMSupplyVoltage2Validity    PMValidity,
                                  ethL1IFCrntPMLBCValue                  INTEGER,
                                  ethL1IFCrntPMLBCTimeStamp              DateAndTime,
                                  ethL1IFCrntPMLBCValidity               PMValidity,
                                  ethL1IFCrntPMCVValue                   Unsigned32,
                                  ethL1IFCrntPMCVTimeStamp               DateAndTime,
                                  ethL1IFCrntPMCVValidity                PMValidity,
                                  ethL1IFCrntPMCVInitialize              InitializeCmd,
                                  ethL1IFCrntPMINVBLKValue               Unsigned32,
                                  ethL1IFCrntPMINVBLKTimeStamp           DateAndTime,
                                  ethL1IFCrntPMINVBLKValidity            PMValidity,
                                  ethL1IFCrntPMINVBLKInitialize          InitializeCmd,
                                  ethL1IFCrntPMESValue                   Unsigned32,
                                  ethL1IFCrntPMESTimeStamp               DateAndTime,
                                  ethL1IFCrntPMESValidity                PMValidity,
                                  ethL1IFCrntPMESInitialize              InitializeCmd,
                                  ethL1IFCrntPMSESValue                  Unsigned32,
                                  ethL1IFCrntPMSESTimeStamp              DateAndTime,
                                  ethL1IFCrntPMSESValidity               PMValidity,
                                  ethL1IFCrntPMSESInitialize             InitializeCmd,
                                  ethL1IFCrntPMOTUEBValue                Unsigned32,
                                  ethL1IFCrntPMOTUEBTimeStamp            DateAndTime,
                                  ethL1IFCrntPMOTUEBValidity             PMValidity,
                                  ethL1IFCrntPMOTUEBInitialize           InitializeCmd,
                                  ethL1IFCrntPMOTUBBEValue               Unsigned32,
                                  ethL1IFCrntPMOTUBBETimeStamp           DateAndTime,
                                  ethL1IFCrntPMOTUBBEValidity            PMValidity,
                                  ethL1IFCrntPMOTUBBEInitialize          InitializeCmd,
                                  ethL1IFCrntPMOTUESValue                Unsigned32,
                                  ethL1IFCrntPMOTUESTimeStamp            DateAndTime,
                                  ethL1IFCrntPMOTUESValidity             PMValidity,
                                  ethL1IFCrntPMOTUESInitialize           InitializeCmd,
                                  ethL1IFCrntPMOTUSESValue               Unsigned32,
                                  ethL1IFCrntPMOTUSESTimeStamp           DateAndTime,
                                  ethL1IFCrntPMOTUSESValidity            PMValidity,
                                  ethL1IFCrntPMOTUSESInitialize          InitializeCmd,
                                  ethL1IFCrntPMOTUOFSValue               Unsigned32,
                                  ethL1IFCrntPMOTUOFSTimeStamp           DateAndTime,
                                  ethL1IFCrntPMOTUOFSValidity            PMValidity,
                                  ethL1IFCrntPMOTUOFSInitialize          InitializeCmd,
                                  ethL1IFCrntPMNBITCRValue               Unsigned32,
                                  ethL1IFCrntPMNBITCRTimeStamp           DateAndTime,
                                  ethL1IFCrntPMNBITCRValidity            PMValidity,
                                  ethL1IFCrntPMNBITCRInitialize          InitializeCmd,
                                  ethL1IFCrntPMNBYTCRValue               Unsigned32,
                                  ethL1IFCrntPMNBYTCRTimeStamp           DateAndTime,
                                  ethL1IFCrntPMNBYTCRValidity            PMValidity,
                                  ethL1IFCrntPMNBYTCRInitialize          InitializeCmd,
                                  ethL1IFCrntPMUNCRCDWValue              Unsigned32,
                                  ethL1IFCrntPMUNCRCDWTimeStamp          DateAndTime,
                                  ethL1IFCrntPMUNCRCDWValidity           PMValidity,
                                  ethL1IFCrntPMUNCRCDWInitialize         InitializeCmd,
                                  ethL1IFCrntPMOTNBERValue               DisplayString,
                                  ethL1IFCrntPMOTNBERTimeStamp           DateAndTime,
                                  ethL1IFCrntPMOTNBERValidity            PMValidity,
                                  ethL1IFCrntPMOTNBERInitialize          InitializeCmd,
                                  ethL1IFCrntPMOTNAVGBERValue            DisplayString,
                                  ethL1IFCrntPMOTNAVGBERTimeStamp        DateAndTime,
                                  ethL1IFCrntPMOTNAVGBERValidity         PMValidity,
                                  ethL1IFCrntPMOTNAVGBERInitialize       InitializeCmd,
                                  ethL1IFCrntPMNBITCR64BitValue          Unsigned64,
                                  ethL1IFCrntPMNBITCR64BitTimeStamp      DateAndTime,
                                  ethL1IFCrntPMNBITCR64BitValidity       PMValidity,
                                  ethL1IFCrntPMNBITCR64BitInitialize     InitializeCmd,
                                  ethL1IFCrntPMNBYTCR64BitValue          Unsigned64,
                                  ethL1IFCrntPMNBYTCR64BitTimeStamp      DateAndTime,
                                  ethL1IFCrntPMNBYTCR64BitValidity       PMValidity,
                                  ethL1IFCrntPMNBYTCR64BitInitialize     InitializeCmd,
                                  ethL1IFCrntPMUASValue                  Unsigned32,
			          ethL1IFCrntPMUASTimeStamp              DateAndTime,
			          ethL1IFCrntPMUASValidity               PMValidity,
			          ethL1IFCrntPMUASInitialize             InitializeCmd,
                                  ethL1IFCrntPMOTUUASValue               Unsigned32,
                                  ethL1IFCrntPMOTUUASTimeStamp           DateAndTime,
                                  ethL1IFCrntPMOTUUASValidity            PMValidity,
                                  ethL1IFCrntPMOTUUASInitialize          InitializeCmd,
                                  ethL1IFCrntPMOPRMinValue               FixedX10,
                                  ethL1IFCrntPMOPRMinTimeStamp           DateAndTime,
                                  ethL1IFCrntPMOPRMinValidity            PMValidity,
                                  ethL1IFCrntPMOPRMinInitialize          InitializeCmd,
                                  ethL1IFCrntPMOPRMaxValue               FixedX10,
                                  ethL1IFCrntPMOPRMaxTimeStamp           DateAndTime,
                                  ethL1IFCrntPMOPRMaxValidity            PMValidity,
                                  ethL1IFCrntPMOPRMaxInitialize          InitializeCmd,
                                  ethL1IFCrntPMOPRAvgValue               FixedX10,
                                  ethL1IFCrntPMOPRAvgTimeStamp           DateAndTime,
                                  ethL1IFCrntPMOPRAvgValidity            PMValidity,
                                  ethL1IFCrntPMOPRAvgInitialize          InitializeCmd,
                                  ethL1IFCrntPMOPTMinValue               FixedX10,
                                  ethL1IFCrntPMOPTMinTimeStamp           DateAndTime,
                                  ethL1IFCrntPMOPTMinValidity            PMValidity,
                                  ethL1IFCrntPMOPTMinInitialize          InitializeCmd,
                                  ethL1IFCrntPMOPTMaxValue               FixedX10,
                                  ethL1IFCrntPMOPTMaxTimeStamp           DateAndTime,
                                  ethL1IFCrntPMOPTMaxValidity            PMValidity,
                                  ethL1IFCrntPMOPTMaxInitialize          InitializeCmd,
                                  ethL1IFCrntPMOPTAvgValue               FixedX10,
                                  ethL1IFCrntPMOPTAvgTimeStamp           DateAndTime,
                                  ethL1IFCrntPMOPTAvgValidity            PMValidity,
                                  ethL1IFCrntPMOPTAvgInitialize          InitializeCmd }


ethL1IFCrntPMShelfIdx OBJECT-TYPE
    SYNTAX       INTEGER (1|11|21|31)
    MAX-ACCESS   not-accessible
    STATUS       current
    DESCRIPTION  "The number of the shelf on which the Ethernet Layer 1 facility targeted for
                  PMs is provisioned."
    ::= { ethL1IFCrntPMEntry 1 }


ethL1IFCrntPMSlotIdx OBJECT-TYPE
    SYNTAX       INTEGER (1|3|5|7|9|11|13|15|17|19)
    MAX-ACCESS   not-accessible
    STATUS       current
    DESCRIPTION  "The number of the slot within which the Ethernet Layer 1 facility targeted
                  for PMs is provisioned."
    ::= { ethL1IFCrntPMEntry 2 }


ethL1IFCrntPMPortTypeIdx OBJECT-TYPE
    SYNTAX       PvxL1PortType
    MAX-ACCESS   not-accessible
    STATUS       current
    DESCRIPTION  "The type of Ethernet Layer 1 port
				  targeted for PMs."
    ::= { ethL1IFCrntPMEntry 3 }


ethL1IFCrntPMPortIdx OBJECT-TYPE
    SYNTAX       INTEGER (1..24)
    MAX-ACCESS   not-accessible
    STATUS       current
    DESCRIPTION  "The number of the port of the identified type 
				   targeted for PMs."
    ::= { ethL1IFCrntPMEntry 4 }


ethL1IFCrntPMIntervalTypeIdx OBJECT-TYPE
    SYNTAX       PMIntervalType
    MAX-ACCESS   not-accessible
    STATUS       current
    DESCRIPTION  "The type of PM bin according to interval length."
    ::= { ethL1IFCrntPMEntry 5 }


ethL1IFCrntPMOPRValue OBJECT-TYPE
    SYNTAX       FixedX10
    UNITS        "dBm/10"
    MAX-ACCESS   read-only
    STATUS       current
    DESCRIPTION  "The optical power received on the input of the Ethernet Layer 1 facility
                  port."
    ::= { ethL1IFCrntPMEntry 6 }


ethL1IFCrntPMOPRTimeStamp OBJECT-TYPE
    SYNTAX       DateAndTime
    MAX-ACCESS   read-only
    STATUS       current
    DESCRIPTION  "The date and time stamp of the optical power received value."
    ::= { ethL1IFCrntPMEntry 7 }


ethL1IFCrntPMOPRValidity OBJECT-TYPE
    SYNTAX       PMValidity
    MAX-ACCESS   read-only
    STATUS       current
    DESCRIPTION  "Indicates the validity of the provided optical power received
                  value."
    ::= { ethL1IFCrntPMEntry 8 }


ethL1IFCrntPMOPTValue OBJECT-TYPE
    SYNTAX       FixedX10
    UNITS        "dBm/10"
    MAX-ACCESS   read-only
    STATUS       current
    DESCRIPTION  "The optical power transmitted at the output of the Ethernet Layer 1 facility
                  port."
    ::= { ethL1IFCrntPMEntry 9 }


ethL1IFCrntPMOPTTimeStamp OBJECT-TYPE
    SYNTAX       DateAndTime
    MAX-ACCESS   read-only
    STATUS       current
    DESCRIPTION  "The date and time stamp of the optical power transmitted
                  value."
    ::= { ethL1IFCrntPMEntry 10 }


ethL1IFCrntPMOPTValidity OBJECT-TYPE
    SYNTAX       PMValidity
    MAX-ACCESS   read-only
    STATUS       current
    DESCRIPTION  "Indicates the validity of the provided optical power
                  transmitted value."
    ::= { ethL1IFCrntPMEntry 11 }


ethL1IFCrntPMTempValue OBJECT-TYPE
    SYNTAX       INTEGER (-32768..32767)
    UNITS        "degrees Celsius"
    MAX-ACCESS   read-only
    STATUS       current
    DESCRIPTION  "The temperature measured on the Ethernet Layer 1 facility port."
    ::= { ethL1IFCrntPMEntry 12 }


ethL1IFCrntPMTempTimeStamp OBJECT-TYPE
    SYNTAX       DateAndTime
    MAX-ACCESS   read-only
    STATUS       current
    DESCRIPTION  "The date and time stamp of the temperature value."
    ::= { ethL1IFCrntPMEntry 13 }


ethL1IFCrntPMTempValidity OBJECT-TYPE
    SYNTAX       PMValidity
    MAX-ACCESS   read-only
    STATUS       current
    DESCRIPTION  "Indicates the validity of the provided temperature value."
    ::= { ethL1IFCrntPMEntry 14 }


ethL1IFCrntPMSupplyVoltageValue OBJECT-TYPE
    SYNTAX       FixedX10
    UNITS        "mVolts/10"
    MAX-ACCESS   read-only
    STATUS       current

    DESCRIPTION  "The supply voltage measured on the Ethernet Layer 1 facility port."
    ::= { ethL1IFCrntPMEntry 15 }


ethL1IFCrntPMSupplyVoltageTimeStamp OBJECT-TYPE
    SYNTAX       DateAndTime
    MAX-ACCESS   read-only
    STATUS       current
    DESCRIPTION  "The date and time stamp of the supply voltage value."
    ::= { ethL1IFCrntPMEntry 16 }


ethL1IFCrntPMSupplyVoltageValidity OBJECT-TYPE
    SYNTAX       PMValidity
    MAX-ACCESS   read-only
    STATUS       current
    DESCRIPTION  "Indicates the validity of the provided supply voltage value."
    ::= { ethL1IFCrntPMEntry 17 }


ethL1IFCrntPMSupplyVoltage2Value OBJECT-TYPE
    SYNTAX       FixedX10
    UNITS        "mVolts/10"
    MAX-ACCESS   read-only
    STATUS       current
    DESCRIPTION  "A second supply voltage value measured on the Ethernet Layer 1 facility port.
    			  This object is available only for XFP-equipped Ethernet Interface ports."
    ::= { ethL1IFCrntPMEntry 18 }


ethL1IFCrntPMSupplyVoltage2TimeStamp OBJECT-TYPE
    SYNTAX       DateAndTime
    MAX-ACCESS   read-only
    STATUS       current
    DESCRIPTION  "The date and time stamp of the second supply voltage value."
    ::= { ethL1IFCrntPMEntry 19 }


ethL1IFCrntPMSupplyVoltage2Validity OBJECT-TYPE
    SYNTAX       PMValidity
    MAX-ACCESS   read-only
    STATUS       current
    DESCRIPTION  "Indicates the validity of the provided second supply voltage value."
    ::= { ethL1IFCrntPMEntry 20 }


ethL1IFCrntPMLBCValue OBJECT-TYPE
    SYNTAX       INTEGER (-32768..32767)
    UNITS        "mAmp"
    MAX-ACCESS   read-only
    STATUS       current
    DESCRIPTION  "The laser bias current measured on the Ethernet Layer 1 facility port."
    ::= { ethL1IFCrntPMEntry 21 }


ethL1IFCrntPMLBCTimeStamp OBJECT-TYPE
    SYNTAX       DateAndTime
    MAX-ACCESS   read-only
    STATUS       current
    DESCRIPTION  "The date and time stamp of the laser bias current value."
    ::= { ethL1IFCrntPMEntry 22 }


ethL1IFCrntPMLBCValidity OBJECT-TYPE
    SYNTAX       PMValidity
    MAX-ACCESS   read-only
    STATUS       current
    DESCRIPTION  "Indicates the validity of the provided laser bias current
                  value."
    ::= { ethL1IFCrntPMEntry 23 }


ethL1IFCrntPMCVValue OBJECT-TYPE
    SYNTAX       Unsigned32 
    MAX-ACCESS   read-write
    STATUS       current
    DESCRIPTION  "The count of 8B/10B coding violations. This object is only available
    			  on Gigabit Ethernet ports."
    ::= { ethL1IFCrntPMEntry 24 }


ethL1IFCrntPMCVTimeStamp OBJECT-TYPE
    SYNTAX       DateAndTime
    MAX-ACCESS   read-only
    STATUS       current
    DESCRIPTION  "The date and time stamp of the coding violations value."
    ::= { ethL1IFCrntPMEntry 25 }


ethL1IFCrntPMCVValidity OBJECT-TYPE
    SYNTAX       PMValidity
    MAX-ACCESS   read-only
    STATUS       current
    DESCRIPTION  "Indicates the validity of the provided coding violations
                  value."
    ::= { ethL1IFCrntPMEntry 26 }


ethL1IFCrntPMCVInitialize OBJECT-TYPE
    SYNTAX       InitializeCmd
    MAX-ACCESS   read-write
    STATUS       current
    DESCRIPTION  "Used to initialize the value of the ethL1IFCrntPMCVValue object
                  to 0."
    ::= { ethL1IFCrntPMEntry 27 }


ethL1IFCrntPMINVBLKValue OBJECT-TYPE
    SYNTAX       Unsigned32 
    MAX-ACCESS   read-write
    STATUS       current
    DESCRIPTION  "The count of invalid blocks. This object is only available
    			  on 10 Gigabit Ethernet ports."
    ::= { ethL1IFCrntPMEntry 28 }


ethL1IFCrntPMINVBLKTimeStamp OBJECT-TYPE
    SYNTAX       DateAndTime
    MAX-ACCESS   read-only
    STATUS       current
    DESCRIPTION  "The date and time stamp of the invalid blocks value."
    ::= { ethL1IFCrntPMEntry 29 }


ethL1IFCrntPMINVBLKValidity OBJECT-TYPE
    SYNTAX       PMValidity
    MAX-ACCESS   read-only
    STATUS       current
    DESCRIPTION  "Indicates the validity of the provided invalid blocks
                  value."
    ::= { ethL1IFCrntPMEntry 30 }


ethL1IFCrntPMINVBLKInitialize OBJECT-TYPE
    SYNTAX       InitializeCmd
    MAX-ACCESS   read-write
    STATUS       current
    DESCRIPTION  "Used to initialize the value of the ethL1IFCrntPMINVBLKValue object
                  to 0."
    ::= { ethL1IFCrntPMEntry 31 }


ethL1IFCrntPMESValue OBJECT-TYPE
    SYNTAX       Unsigned32
    MAX-ACCESS   read-write
    STATUS       current
    DESCRIPTION  "The count of Ethernet Layer 1 errored seconds."
    ::= { ethL1IFCrntPMEntry 32 }


ethL1IFCrntPMESTimeStamp OBJECT-TYPE
    SYNTAX       DateAndTime
    MAX-ACCESS   read-only
    STATUS       current
    DESCRIPTION  "The date and time stamp of the Ethernet Layer 1 errored seconds value."
    ::= { ethL1IFCrntPMEntry 33 }


ethL1IFCrntPMESValidity OBJECT-TYPE
    SYNTAX       PMValidity
    MAX-ACCESS   read-only
    STATUS       current
    DESCRIPTION  "Indicates the validity of the provided Ethernet Layer 1 errored seconds
                  value."
    ::= { ethL1IFCrntPMEntry 34 }


ethL1IFCrntPMESInitialize OBJECT-TYPE
    SYNTAX       InitializeCmd
    MAX-ACCESS   read-write
    STATUS       current
    DESCRIPTION  "Used to initialize the value of the ethL1IFCrntPMESValue object
                  to 0."
    ::= { ethL1IFCrntPMEntry 35 }


ethL1IFCrntPMSESValue OBJECT-TYPE
    SYNTAX       Unsigned32
    MAX-ACCESS   read-write
    STATUS       current
    DESCRIPTION  "The count of Ethernet Layer 1 severely errored seconds."
    ::= { ethL1IFCrntPMEntry 36 }


ethL1IFCrntPMSESTimeStamp OBJECT-TYPE
    SYNTAX       DateAndTime
    MAX-ACCESS   read-only
    STATUS       current
    DESCRIPTION  "The date and time stamp of the Ethernet Layer 1 severely errored seconds
                  value."
    ::= { ethL1IFCrntPMEntry 37 }


ethL1IFCrntPMSESValidity OBJECT-TYPE
    SYNTAX       PMValidity
    MAX-ACCESS   read-only
    STATUS       current
    DESCRIPTION  "Indicates the validity of the provided Ethernet Layer 1 severely errored
                  seconds value."
    ::= { ethL1IFCrntPMEntry 38 }


ethL1IFCrntPMSESInitialize OBJECT-TYPE
    SYNTAX       InitializeCmd
    MAX-ACCESS   read-write
    STATUS       current
    DESCRIPTION  "Used to initialize the value of the ethL1IFCrntPMSESValue object
                  to 0."
    ::= { ethL1IFCrntPMEntry 39 }


ethL1IFCrntPMOTUEBValue OBJECT-TYPE
    SYNTAX       Unsigned32 
    MAX-ACCESS   read-write
    STATUS       current
    DESCRIPTION  "The count of OTU digital wrapper layer errored blocks."
    ::= { ethL1IFCrntPMEntry 40 }


ethL1IFCrntPMOTUEBTimeStamp OBJECT-TYPE
    SYNTAX       DateAndTime
    MAX-ACCESS   read-only
    STATUS       current
    DESCRIPTION  "The date and time stamp of the OTU digital wrapper layer
                  errored blocks value."
    ::= { ethL1IFCrntPMEntry 41 }


ethL1IFCrntPMOTUEBValidity OBJECT-TYPE
    SYNTAX       PMValidity
    MAX-ACCESS   read-only
    STATUS       current
    DESCRIPTION  "Indicates the validity of the provided OTU digital wrapper
                  layer errored blocks value."
    ::= { ethL1IFCrntPMEntry 42 }


ethL1IFCrntPMOTUEBInitialize OBJECT-TYPE
    SYNTAX       InitializeCmd
    MAX-ACCESS   read-write
    STATUS       current
    DESCRIPTION  "Used to initialize the value of the ethL1IFCrntPMOTUEBValue object
                  to 0."
    ::= { ethL1IFCrntPMEntry 43 }


ethL1IFCrntPMOTUBBEValue OBJECT-TYPE
    SYNTAX       Unsigned32 
    MAX-ACCESS   read-write
    STATUS       current
    DESCRIPTION  "The count of OTU digital wrapper layer background block
                  errors."
    ::= { ethL1IFCrntPMEntry 44 }


ethL1IFCrntPMOTUBBETimeStamp OBJECT-TYPE
    SYNTAX       DateAndTime
    MAX-ACCESS   read-only
    STATUS       current
    DESCRIPTION  "The date and time stamp of the OTU digital wrapper layer
                  background block errors value."
    ::= { ethL1IFCrntPMEntry 45 }


ethL1IFCrntPMOTUBBEValidity OBJECT-TYPE
    SYNTAX       PMValidity
    MAX-ACCESS   read-only
    STATUS       current
    DESCRIPTION  "Indicates the validity of the provided OTU digital wrapper
                  layer background block errors value."
    ::= { ethL1IFCrntPMEntry 46 }


ethL1IFCrntPMOTUBBEInitialize OBJECT-TYPE
    SYNTAX       InitializeCmd
    MAX-ACCESS   read-write
    STATUS       current
    DESCRIPTION  "Used to initialize the value of the ethL1IFCrntPMOTUBBEValue object
                  to 0."
    ::= { ethL1IFCrntPMEntry 47 }


ethL1IFCrntPMOTUESValue OBJECT-TYPE
    SYNTAX       Unsigned32
    MAX-ACCESS   read-write
    STATUS       current
    DESCRIPTION  "The count of OTU digital wrapper layer errored seconds."
    ::= { ethL1IFCrntPMEntry 48 }


ethL1IFCrntPMOTUESTimeStamp OBJECT-TYPE
    SYNTAX       DateAndTime
    MAX-ACCESS   read-only
    STATUS       current
    DESCRIPTION  "The date and time stamp of the OTU digital wrapper layer
                  errored seconds value."
    ::= { ethL1IFCrntPMEntry 49 }


ethL1IFCrntPMOTUESValidity OBJECT-TYPE
    SYNTAX       PMValidity
    MAX-ACCESS   read-only
    STATUS       current
    DESCRIPTION  "Indicates the validity of the provided OTU digital wrapper
                  layer errored seconds value."
    ::= { ethL1IFCrntPMEntry 50 }


ethL1IFCrntPMOTUESInitialize OBJECT-TYPE
    SYNTAX       InitializeCmd
    MAX-ACCESS   read-write
    STATUS       current
    DESCRIPTION  "Used to initialize the value of the ethL1IFCrntPMOTUESValue object
                  to 0."
    ::= { ethL1IFCrntPMEntry 51 }


ethL1IFCrntPMOTUSESValue OBJECT-TYPE
    SYNTAX       Unsigned32
    MAX-ACCESS   read-write
    STATUS       current
    DESCRIPTION  "The count of OTU digital wrapper layer severely errored
                  seconds."
    ::= { ethL1IFCrntPMEntry 52 }


ethL1IFCrntPMOTUSESTimeStamp OBJECT-TYPE
    SYNTAX       DateAndTime
    MAX-ACCESS   read-only
    STATUS       current
    DESCRIPTION  "The date and time stamp of the OTU digital wrapper layer
                  severely errored seconds value."
    ::= { ethL1IFCrntPMEntry 53 }


ethL1IFCrntPMOTUSESValidity OBJECT-TYPE
    SYNTAX       PMValidity
    MAX-ACCESS   read-only
    STATUS       current
    DESCRIPTION  "Indicates the validity of the provided OTU digital wrapper
                  layer severely errored seconds value."
    ::= { ethL1IFCrntPMEntry 54 }


ethL1IFCrntPMOTUSESInitialize OBJECT-TYPE
    SYNTAX       InitializeCmd
    MAX-ACCESS   read-write
    STATUS       current
    DESCRIPTION  "Used to initialize the value of the ethL1IFCrntPMOTUSESValue object
                  to 0."
    ::= { ethL1IFCrntPMEntry 55 }


ethL1IFCrntPMOTUOFSValue OBJECT-TYPE
    SYNTAX       Unsigned32
    MAX-ACCESS   read-write
    STATUS       current
    DESCRIPTION  "The count of OTU digital wrapper layer out-of-frame seconds."
    ::= { ethL1IFCrntPMEntry 56 }


ethL1IFCrntPMOTUOFSTimeStamp OBJECT-TYPE
    SYNTAX       DateAndTime
    MAX-ACCESS   read-only
    STATUS       current
    DESCRIPTION  "The date and time stamp of the OTU digital wrapper layer
                  out-of-frame seconds value."
    ::= { ethL1IFCrntPMEntry 57 }


ethL1IFCrntPMOTUOFSValidity OBJECT-TYPE
    SYNTAX       PMValidity
    MAX-ACCESS   read-only
    STATUS       current
    DESCRIPTION  "Indicates the validity of the provided OTU digital wrapper
                  layer out-of-frame seconds value."
    ::= { ethL1IFCrntPMEntry 58 }


ethL1IFCrntPMOTUOFSInitialize OBJECT-TYPE
    SYNTAX       InitializeCmd
    MAX-ACCESS   read-write
    STATUS       current
    DESCRIPTION  "Used to initialize the value of the ethL1IFCrntPMOTUOFSValue object
                  to 0."
    ::= { ethL1IFCrntPMEntry 59 }


ethL1IFCrntPMNBITCRValue OBJECT-TYPE
    SYNTAX       Unsigned32
    MAX-ACCESS   read-write
    STATUS       current
    DESCRIPTION  "The count of the number of bits corrected. This object
                  applies only to xGigE line ports provisioned for OTN line
                  mapping with Forward Eror Correction (FEC)."
    ::= { ethL1IFCrntPMEntry 60 }


ethL1IFCrntPMNBITCRTimeStamp OBJECT-TYPE
    SYNTAX       DateAndTime
    MAX-ACCESS   read-only
    STATUS       current
    DESCRIPTION  "The date and time stamp of the number of bits corrected
                  value."
    ::= { ethL1IFCrntPMEntry 61 }


ethL1IFCrntPMNBITCRValidity OBJECT-TYPE
    SYNTAX       PMValidity
    MAX-ACCESS   read-only
    STATUS       current
    DESCRIPTION  "Indicates the validity of the provided number of bits
                  corrected value."
    ::= { ethL1IFCrntPMEntry 62 }


ethL1IFCrntPMNBITCRInitialize OBJECT-TYPE
    SYNTAX       InitializeCmd
    MAX-ACCESS   read-write
    STATUS       current
    DESCRIPTION  "Used to initialize the value of the ethL1IFCrntPMNBITCRValue object
                  to 0."
    ::= { ethL1IFCrntPMEntry 63 }


ethL1IFCrntPMNBYTCRValue OBJECT-TYPE
    SYNTAX       Unsigned32
    MAX-ACCESS   read-write
    STATUS       current
    DESCRIPTION  "The count of the number of bytes corrected. This object
                  applies only to xGigE line ports provisioned for OTN line
                  mapping with Forward Eror Correction (FEC)."
    ::= { ethL1IFCrntPMEntry 64 }


ethL1IFCrntPMNBYTCRTimeStamp OBJECT-TYPE
    SYNTAX       DateAndTime
    MAX-ACCESS   read-only
    STATUS       current
    DESCRIPTION  "The date and time stamp of the number of bytes corrected
                  value."
    ::= { ethL1IFCrntPMEntry 65 }


ethL1IFCrntPMNBYTCRValidity OBJECT-TYPE
    SYNTAX       PMValidity
    MAX-ACCESS   read-only
    STATUS       current
    DESCRIPTION  "Indicates the validity of the provided number of bytes
                  corrected value."
    ::= { ethL1IFCrntPMEntry 66 }


ethL1IFCrntPMNBYTCRInitialize OBJECT-TYPE
    SYNTAX       InitializeCmd
    MAX-ACCESS   read-write
    STATUS       current
    DESCRIPTION  "Used to initialize the value of the ethL1IFCrntPMNBYTCRValue object
                  to 0."
    ::= { ethL1IFCrntPMEntry 67 }


ethL1IFCrntPMUNCRCDWValue OBJECT-TYPE
    SYNTAX       Unsigned32
    MAX-ACCESS   read-write
    STATUS       current
    DESCRIPTION  "The count of uncorrectable codewords. This object
                  applies only to xGigE line ports provisioned for OTN line
                  mapping with Forward Eror Correction (FEC)."
    ::= { ethL1IFCrntPMEntry 68 }


ethL1IFCrntPMUNCRCDWTimeStamp OBJECT-TYPE
    SYNTAX       DateAndTime
    MAX-ACCESS   read-only
    STATUS       current
    DESCRIPTION  "The date and time stamp of the uncorrectable codewords value."
    ::= { ethL1IFCrntPMEntry 69 }


ethL1IFCrntPMUNCRCDWValidity OBJECT-TYPE
    SYNTAX       PMValidity
    MAX-ACCESS   read-only
    STATUS       current
    DESCRIPTION  "Indicates the validity of the provided uncorrectable codewords
                  value."
    ::= { ethL1IFCrntPMEntry 70 }


ethL1IFCrntPMUNCRCDWInitialize OBJECT-TYPE
    SYNTAX       InitializeCmd
    MAX-ACCESS   read-write
    STATUS       current
    DESCRIPTION  "Used to initialize the value of the ethL1IFCrntPMUNCRCDWValue object
                  to 0."
    ::= { ethL1IFCrntPMEntry 71 }

ethL1IFCrntPMOTNBERValue OBJECT-TYPE
    SYNTAX       DisplayString
    MAX-ACCESS   read-only
    STATUS       current
    DESCRIPTION  "The instantaneous BER of the line port."
    ::= { ethL1IFCrntPMEntry 72 }


ethL1IFCrntPMOTNBERTimeStamp OBJECT-TYPE
    SYNTAX       DateAndTime
    MAX-ACCESS   read-only
    STATUS       current
    DESCRIPTION  "The date and time stamp of the instantaneous BER."
    ::= { ethL1IFCrntPMEntry 73 }


ethL1IFCrntPMOTNBERValidity OBJECT-TYPE
    SYNTAX       PMValidity
    MAX-ACCESS   read-only
    STATUS       current
    DESCRIPTION  "Indicates the validity of the provided instantaneous BER."
    ::= { ethL1IFCrntPMEntry 74 }


ethL1IFCrntPMOTNBERInitialize OBJECT-TYPE
    SYNTAX       InitializeCmd
    MAX-ACCESS   read-write
    STATUS       current
    DESCRIPTION  "Used to initialize the value of the ethL1IFCrntPMOTNBERValue object
                  to 0."
    ::= { ethL1IFCrntPMEntry 75 }


ethL1IFCrntPMOTNAVGBERValue OBJECT-TYPE
    SYNTAX       DisplayString
    MAX-ACCESS   read-only
    STATUS       current
    DESCRIPTION  "The interval/average BER of the line port."
    ::= { ethL1IFCrntPMEntry 76 }


ethL1IFCrntPMOTNAVGBERTimeStamp OBJECT-TYPE
    SYNTAX       DateAndTime
    MAX-ACCESS   read-only
    STATUS       current
    DESCRIPTION  "The date and time stamp of the interval/average BER."
    ::= { ethL1IFCrntPMEntry 77 }


ethL1IFCrntPMOTNAVGBERValidity OBJECT-TYPE
    SYNTAX       PMValidity
    MAX-ACCESS   read-only
    STATUS       current
    DESCRIPTION  "Indicates the validity of the provided interval/average BER."
    ::= { ethL1IFCrntPMEntry 78 }


ethL1IFCrntPMOTNAVGBERInitialize OBJECT-TYPE
    SYNTAX       InitializeCmd
    MAX-ACCESS   read-write
    STATUS       current
    DESCRIPTION  "Used to initialize the value of the ethL1IFCrntPMOTNAVGBERValue object
                  to 0."
    ::= { ethL1IFCrntPMEntry 79 }


ethL1IFCrntPMNBITCR64BitValue OBJECT-TYPE
    SYNTAX       Unsigned64
    MAX-ACCESS   read-only
    STATUS       current
    DESCRIPTION  "The 64-bit count of the number of bits corrected. This object
                  applies only to xGigE line ports provisioned for OTN line
                  mapping with Forward Eror Correction (FEC)."
    ::= { ethL1IFCrntPMEntry 80 }


ethL1IFCrntPMNBITCR64BitTimeStamp OBJECT-TYPE
    SYNTAX       DateAndTime
    MAX-ACCESS   read-only
    STATUS       current
    DESCRIPTION  "The date and time stamp of the 64-bit number of bits corrected
                  value."
    ::= { ethL1IFCrntPMEntry 81 }


ethL1IFCrntPMNBITCR64BitValidity OBJECT-TYPE
    SYNTAX       PMValidity
    MAX-ACCESS   read-only
    STATUS       current
    DESCRIPTION  "Indicates the validity of the provided 64-bit number of bits
                  corrected value."
    ::= { ethL1IFCrntPMEntry 82 }


ethL1IFCrntPMNBITCR64BitInitialize OBJECT-TYPE
    SYNTAX       InitializeCmd
    MAX-ACCESS   read-write
    STATUS       current
    DESCRIPTION  "Used to initialize the value of the ethL1IFCrntPMNBITCR64BitValue
                  object to 0."
    ::= { ethL1IFCrntPMEntry 83 }


ethL1IFCrntPMNBYTCR64BitValue OBJECT-TYPE
    SYNTAX       Unsigned64
    MAX-ACCESS   read-only
    STATUS       current
    DESCRIPTION  "The 64-bit count of the number of bytes corrected. This object
                  applies only to xGigE line ports provisioned for OTN line
                  mapping with Forward Eror Correction (FEC)."
    ::= { ethL1IFCrntPMEntry 84 }


ethL1IFCrntPMNBYTCR64BitTimeStamp OBJECT-TYPE
    SYNTAX       DateAndTime
    MAX-ACCESS   read-only
    STATUS       current
    DESCRIPTION  "The date and time stamp of the 64-bit number of bytes corrected
                  value."
    ::= { ethL1IFCrntPMEntry 85 }


ethL1IFCrntPMNBYTCR64BitValidity OBJECT-TYPE
    SYNTAX       PMValidity
    MAX-ACCESS   read-only
    STATUS       current
    DESCRIPTION  "Indicates the validity of the provided 64-bit number of bytes
                  corrected value."
    ::= { ethL1IFCrntPMEntry 86 }


ethL1IFCrntPMNBYTCR64BitInitialize OBJECT-TYPE
    SYNTAX       InitializeCmd
    MAX-ACCESS   read-write
    STATUS       current
    DESCRIPTION  "Used to initialize the value of the ethL1IFCrntPMNBYTCR64BitValue
                  object to 0."
    ::= { ethL1IFCrntPMEntry 87 }


ethL1IFCrntPMUASValue OBJECT-TYPE
    SYNTAX       Unsigned32
    MAX-ACCESS   read-write
    STATUS       current
    DESCRIPTION  "The count of unavailable seconds. This object is only available
                  on Gigabit Ethernet ports."
    ::= { ethL1IFCrntPMEntry 88 }

ethL1IFCrntPMUASTimeStamp OBJECT-TYPE
    SYNTAX       DateAndTime
    MAX-ACCESS   read-only
    STATUS       current
    DESCRIPTION  "The date and time stamp of the unavailable seconds
                  value."
    ::= { ethL1IFCrntPMEntry 89 }


ethL1IFCrntPMUASValidity OBJECT-TYPE
    SYNTAX       PMValidity
    MAX-ACCESS   read-only
    STATUS       current
    DESCRIPTION  "Indicates the validity of the provided unavailable
                  seconds value."
    ::= { ethL1IFCrntPMEntry 90 }


ethL1IFCrntPMUASInitialize OBJECT-TYPE
    SYNTAX       InitializeCmd
    MAX-ACCESS   read-write
    STATUS       current
    DESCRIPTION  "Used to initialize the value of the ethL1IFCrntPMUASValue
                  object to 0."
    ::= { ethL1IFCrntPMEntry 91 }


ethL1IFCrntPMOTUUASValue OBJECT-TYPE
    SYNTAX       Unsigned32
    MAX-ACCESS   read-write
    STATUS       current
    DESCRIPTION  "The count of OTU digital wrapper layer unavailable seconds."
    ::= { ethL1IFCrntPMEntry 92 }


ethL1IFCrntPMOTUUASTimeStamp OBJECT-TYPE
    SYNTAX       DateAndTime
    MAX-ACCESS   read-only
    STATUS       current
    DESCRIPTION  "The date and time stamp of the OTU digital wrapper layer
                  unavailable seconds value."
    ::= { ethL1IFCrntPMEntry 93 }


ethL1IFCrntPMOTUUASValidity OBJECT-TYPE
    SYNTAX       PMValidity
    MAX-ACCESS   read-only
    STATUS       current
    DESCRIPTION  "Indicates the validity of the provided OTU digital wrapper
                  layer unavailable seconds value."
    ::= { ethL1IFCrntPMEntry 94 }


ethL1IFCrntPMOTUUASInitialize OBJECT-TYPE
    SYNTAX       InitializeCmd
    MAX-ACCESS   read-write
    STATUS       current
    DESCRIPTION  "Used to initialize the value of the ethL1IFCrntPMOTUUASValue object
                  to 0."
    ::= { ethL1IFCrntPMEntry 95 }

ethL1IFCrntPMOPRMinValue OBJECT-TYPE
    SYNTAX       FixedX10
    UNITS        "dBm/10"
    MAX-ACCESS   read-only
    STATUS       current
    DESCRIPTION  "The minimum optical power received on the input of the transceiver."
    ::= { ethL1IFCrntPMEntry 96 }


ethL1IFCrntPMOPRMinTimeStamp OBJECT-TYPE
    SYNTAX       DateAndTime
    MAX-ACCESS   read-only
    STATUS       current
    DESCRIPTION  "The date and time stamp of the minimum optical power received value."
    ::= { ethL1IFCrntPMEntry 97 }


ethL1IFCrntPMOPRMinValidity OBJECT-TYPE
    SYNTAX       PMValidity
    MAX-ACCESS   read-only
    STATUS       current
    DESCRIPTION  "Indicates the validity of the provided minimum optical power received
                  value."
    ::= { ethL1IFCrntPMEntry 98 }

ethL1IFCrntPMOPRMinInitialize OBJECT-TYPE
    SYNTAX       InitializeCmd
    MAX-ACCESS   read-write
    STATUS       current
    DESCRIPTION  "Used to initialize the value of the ethL1IFCrntPMOPRMinValue
                  object to 0."
    ::= { ethL1IFCrntPMEntry 99 }

ethL1IFCrntPMOPRMaxValue OBJECT-TYPE
    SYNTAX       FixedX10
    UNITS        "dBm/10"
    MAX-ACCESS   read-only
    STATUS       current
    DESCRIPTION  "The maximum optical power received on the input of the transceiver."
    ::= { ethL1IFCrntPMEntry 100 }


ethL1IFCrntPMOPRMaxTimeStamp OBJECT-TYPE
    SYNTAX       DateAndTime
    MAX-ACCESS   read-only
    STATUS       current
    DESCRIPTION  "The date and time stamp of the maximum optical power received value."
    ::= { ethL1IFCrntPMEntry 101 }


ethL1IFCrntPMOPRMaxValidity OBJECT-TYPE
    SYNTAX       PMValidity
    MAX-ACCESS   read-only
    STATUS       current
    DESCRIPTION  "Indicates the validity of the provided maximum optical power received
                  value."
    ::= { ethL1IFCrntPMEntry 102 }

ethL1IFCrntPMOPRMaxInitialize OBJECT-TYPE
    SYNTAX       InitializeCmd
    MAX-ACCESS   read-write
    STATUS       current
    DESCRIPTION  "Used to initialize the value of the ethL1IFCrntPMOPRMaxValue
                  object to 0."
    ::= { ethL1IFCrntPMEntry 103 }

ethL1IFCrntPMOPRAvgValue OBJECT-TYPE
    SYNTAX       FixedX10
    UNITS        "dBm/10"
    MAX-ACCESS   read-only
    STATUS       current
    DESCRIPTION  "The average optical power received on the input of the transceiver."
    ::= { ethL1IFCrntPMEntry 104 }


ethL1IFCrntPMOPRAvgTimeStamp OBJECT-TYPE
    SYNTAX       DateAndTime
    MAX-ACCESS   read-only
    STATUS       current
    DESCRIPTION  "The date and time stamp of the average optical power received value."
    ::= { ethL1IFCrntPMEntry 105 }


ethL1IFCrntPMOPRAvgValidity OBJECT-TYPE
    SYNTAX       PMValidity
    MAX-ACCESS   read-only
    STATUS       current
    DESCRIPTION  "Indicates the validity of the provided average optical power received
                  value."
    ::= { ethL1IFCrntPMEntry 106 }

ethL1IFCrntPMOPRAvgInitialize OBJECT-TYPE
    SYNTAX       InitializeCmd
    MAX-ACCESS   read-write
    STATUS       current
    DESCRIPTION  "Used to initialize the value of the ethL1IFCrntPMOPRAvgValue
                  object to 0."
    ::= { ethL1IFCrntPMEntry 107 }

ethL1IFCrntPMOPTMinValue OBJECT-TYPE
    SYNTAX       FixedX10
    UNITS        "dBm/10"
    MAX-ACCESS   read-only
    STATUS       current
    DESCRIPTION  "The minimum optical power transmitted at the output of the
                  transceiver."
    ::= { ethL1IFCrntPMEntry 108 }

ethL1IFCrntPMOPTMinTimeStamp OBJECT-TYPE
    SYNTAX       DateAndTime
    MAX-ACCESS   read-only
    STATUS       current
    DESCRIPTION  "The date and time stamp of the minimum optical power transmitted
                  value."
    ::= { ethL1IFCrntPMEntry 109 }


ethL1IFCrntPMOPTMinValidity OBJECT-TYPE
    SYNTAX       PMValidity
    MAX-ACCESS   read-only
    STATUS       current
    DESCRIPTION  "Indicates the validity of the provided minimum optical power
                  transmitted value."
    ::= { ethL1IFCrntPMEntry 110 }

ethL1IFCrntPMOPTMinInitialize OBJECT-TYPE
    SYNTAX       InitializeCmd
    MAX-ACCESS   read-write
    STATUS       current
    DESCRIPTION  "Used to initialize the value of the ethL1IFCrntPMOPTMinValue
                  object to 0."
    ::= { ethL1IFCrntPMEntry 111 }

ethL1IFCrntPMOPTMaxValue OBJECT-TYPE
    SYNTAX       FixedX10
    UNITS        "dBm/10"
    MAX-ACCESS   read-only
    STATUS       current
    DESCRIPTION  "The maximum optical power transmitted at the output of the
                  transceiver."
    ::= { ethL1IFCrntPMEntry 112 }


ethL1IFCrntPMOPTMaxTimeStamp OBJECT-TYPE
    SYNTAX       DateAndTime
    MAX-ACCESS   read-only
    STATUS       current
    DESCRIPTION  "The date and time stamp of the maximum optical power transmitted
                  value."
    ::= { ethL1IFCrntPMEntry 113 }


ethL1IFCrntPMOPTMaxValidity OBJECT-TYPE
    SYNTAX       PMValidity
    MAX-ACCESS   read-only
    STATUS       current
    DESCRIPTION  "Indicates the validity of the provided maximum optical power
                  transmitted value."
    ::= { ethL1IFCrntPMEntry 114 }

ethL1IFCrntPMOPTMaxInitialize OBJECT-TYPE
    SYNTAX       InitializeCmd
    MAX-ACCESS   read-write
    STATUS       current
    DESCRIPTION  "Used to initialize the value of the ethL1IFCrntPMOPTMaxValue
                  object to 0."
    ::= { ethL1IFCrntPMEntry 115 }

ethL1IFCrntPMOPTAvgValue OBJECT-TYPE
    SYNTAX       FixedX10
    UNITS        "dBm/10"
    MAX-ACCESS   read-only
    STATUS       current
    DESCRIPTION  "The average optical power transmitted at the output of the
                  transceiver."
    ::= { ethL1IFCrntPMEntry 116 }


ethL1IFCrntPMOPTAvgTimeStamp OBJECT-TYPE
    SYNTAX       DateAndTime
    MAX-ACCESS   read-only
    STATUS       current
    DESCRIPTION  "The date and time stamp of the average optical power transmitted
                  value."
    ::= { ethL1IFCrntPMEntry 117 }

ethL1IFCrntPMOPTAvgValidity OBJECT-TYPE
    SYNTAX       PMValidity
    MAX-ACCESS   read-only
    STATUS       current
    DESCRIPTION  "Indicates the validity of the provided average optical power
                  transmitted value."
    ::= { ethL1IFCrntPMEntry 118 }

ethL1IFCrntPMOPTAvgInitialize OBJECT-TYPE
    SYNTAX       InitializeCmd
    MAX-ACCESS   read-write
    STATUS       current
    DESCRIPTION  "Used to initialize the value of the ethL1IFCrntPMOPTAvgValue
                  object to 0."
    ::= { ethL1IFCrntPMEntry 119 }


-----------------------------------------------------------------------
-- Objects used to retrieve historical Ethernet Layer 1 Interface
-- Performance Monitoring statistics
-----------------------------------------------------------------------


ethL1IFHistPMTable OBJECT-TYPE
    SYNTAX       SEQUENCE OF EthL1IFHistPMEntry
    MAX-ACCESS   not-accessible
    STATUS       current
    DESCRIPTION  "A table of historical performance monitoring statistics collected
                  for the Ethernet Layer 1 Interface facilities on the NE."
    ::= { performance 27 }


ethL1IFHistPMEntry OBJECT-TYPE
    SYNTAX       EthL1IFHistPMEntry
    MAX-ACCESS   not-accessible
    STATUS       current
    DESCRIPTION  "The row entry object of the Ethernet Layer 1 Interface historical
                  performance monitoring table. Each row of this table contains
                  a full set of PM statistics and related data for a historical
                  measurement interval for a given Ethernet Layer 1 Interface facility."
     INDEX        { ethL1IFHistPMShelfIdx,
                    ethL1IFHistPMSlotIdx,
                    ethL1IFHistPMPortTypeIdx,
                    ethL1IFHistPMPortIdx,
                    ethL1IFHistPMIntervalTypeIdx,
                    ethL1IFHistPMIntervalIdx }
    ::= { ethL1IFHistPMTable 1 }


EthL1IFHistPMEntry ::= SEQUENCE { ethL1IFHistPMShelfIdx                  INTEGER,
                                  ethL1IFHistPMSlotIdx                   INTEGER,
                                  ethL1IFHistPMPortTypeIdx               PvxL1PortType,
				  ethL1IFHistPMPortIdx                   INTEGER,
                                  ethL1IFHistPMIntervalTypeIdx           PMIntervalType,
                                  ethL1IFHistPMIntervalIdx               INTEGER,
                                  ethL1IFHistPMOPRValue                  FixedX10,
                                  ethL1IFHistPMOPRTimeStamp              DateAndTime,
                                  ethL1IFHistPMOPRValidity               PMValidity,
                                  ethL1IFHistPMOPTValue                  FixedX10,
                                  ethL1IFHistPMOPTTimeStamp              DateAndTime,
                                  ethL1IFHistPMOPTValidity               PMValidity,
                                  ethL1IFHistPMTempValue                 INTEGER,
                                  ethL1IFHistPMTempTimeStamp             DateAndTime,
                                  ethL1IFHistPMTempValidity              PMValidity,
                                  ethL1IFHistPMSupplyVoltageValue        FixedX10,
                                  ethL1IFHistPMSupplyVoltageTimeStamp    DateAndTime,
                                  ethL1IFHistPMSupplyVoltageValidity     PMValidity,
                                  ethL1IFHistPMSupplyVoltage2Value       FixedX10,
                                  ethL1IFHistPMSupplyVoltage2TimeStamp   DateAndTime,
                                  ethL1IFHistPMSupplyVoltage2Validity    PMValidity,
                                  ethL1IFHistPMLBCValue                  INTEGER,
                                  ethL1IFHistPMLBCTimeStamp              DateAndTime,
                                  ethL1IFHistPMLBCValidity               PMValidity,
                                  ethL1IFHistPMCVValue                   Unsigned32,
                                  ethL1IFHistPMCVTimeStamp               DateAndTime,
                                  ethL1IFHistPMCVValidity                PMValidity,
                                  ethL1IFHistPMCVInitialize              InitializeCmd,
                                  ethL1IFHistPMINVBLKValue               Unsigned32,
                                  ethL1IFHistPMINVBLKTimeStamp           DateAndTime,
                                  ethL1IFHistPMINVBLKValidity            PMValidity,
                                  ethL1IFHistPMINVBLKInitialize          InitializeCmd,
                                  ethL1IFHistPMESValue                   Unsigned32,
                                  ethL1IFHistPMESTimeStamp               DateAndTime,
                                  ethL1IFHistPMESValidity                PMValidity,
                                  ethL1IFHistPMESInitialize              InitializeCmd,
                                  ethL1IFHistPMSESValue                  Unsigned32,
                                  ethL1IFHistPMSESTimeStamp              DateAndTime,
                                  ethL1IFHistPMSESValidity               PMValidity,
                                  ethL1IFHistPMSESInitialize             InitializeCmd,
                                  ethL1IFHistPMOTUEBValue                Unsigned32,
                                  ethL1IFHistPMOTUEBTimeStamp            DateAndTime,
                                  ethL1IFHistPMOTUEBValidity             PMValidity,
                                  ethL1IFHistPMOTUEBInitialize           InitializeCmd,
                                  ethL1IFHistPMOTUBBEValue               Unsigned32,
                                  ethL1IFHistPMOTUBBETimeStamp           DateAndTime,
                                  ethL1IFHistPMOTUBBEValidity            PMValidity,
                                  ethL1IFHistPMOTUBBEInitialize          InitializeCmd,
                                  ethL1IFHistPMOTUESValue                Unsigned32,
                                  ethL1IFHistPMOTUESTimeStamp            DateAndTime,
                                  ethL1IFHistPMOTUESValidity             PMValidity,
                                  ethL1IFHistPMOTUESInitialize           InitializeCmd,
                                  ethL1IFHistPMOTUSESValue               Unsigned32,
                                  ethL1IFHistPMOTUSESTimeStamp           DateAndTime,
                                  ethL1IFHistPMOTUSESValidity            PMValidity,
                                  ethL1IFHistPMOTUSESInitialize          InitializeCmd,
                                  ethL1IFHistPMOTUOFSValue               Unsigned32,
                                  ethL1IFHistPMOTUOFSTimeStamp           DateAndTime,
                                  ethL1IFHistPMOTUOFSValidity            PMValidity,
                                  ethL1IFHistPMOTUOFSInitialize          InitializeCmd,
                                  ethL1IFHistPMNBITCRValue               Unsigned32,
                                  ethL1IFHistPMNBITCRTimeStamp           DateAndTime,
                                  ethL1IFHistPMNBITCRValidity            PMValidity,
                                  ethL1IFHistPMNBITCRInitialize          InitializeCmd,
                                  ethL1IFHistPMNBYTCRValue               Unsigned32,
                                  ethL1IFHistPMNBYTCRTimeStamp           DateAndTime,
                                  ethL1IFHistPMNBYTCRValidity            PMValidity,
                                  ethL1IFHistPMNBYTCRInitialize          InitializeCmd,
                                  ethL1IFHistPMUNCRCDWValue              Unsigned32,
                                  ethL1IFHistPMUNCRCDWTimeStamp          DateAndTime,
                                  ethL1IFHistPMUNCRCDWValidity           PMValidity,
                                  ethL1IFHistPMUNCRCDWInitialize         InitializeCmd,
                                  ethL1IFHistPMOTNBERValue               DisplayString,
                                  ethL1IFHistPMOTNBERTimeStamp           DateAndTime,
                                  ethL1IFHistPMOTNBERValidity            PMValidity,
                                  ethL1IFHistPMOTNBERInitialize          InitializeCmd,
                                  ethL1IFHistPMOTNAVGBERValue            DisplayString,
                                  ethL1IFHistPMOTNAVGBERTimeStamp        DateAndTime,
                                  ethL1IFHistPMOTNAVGBERValidity         PMValidity,
                                  ethL1IFHistPMOTNAVGBERInitialize       InitializeCmd,
                                  ethL1IFHistPMNBITCR64BitValue          Unsigned64,
                                  ethL1IFHistPMNBITCR64BitTimeStamp      DateAndTime,
                                  ethL1IFHistPMNBITCR64BitValidity       PMValidity,
                                  ethL1IFHistPMNBITCR64BitInitialize     InitializeCmd,
                                  ethL1IFHistPMNBYTCR64BitValue          Unsigned64,
                                  ethL1IFHistPMNBYTCR64BitTimeStamp      DateAndTime,
                                  ethL1IFHistPMNBYTCR64BitValidity       PMValidity,
                                  ethL1IFHistPMNBYTCR64BitInitialize     InitializeCmd,
                                  ethL1IFHistPMUASValue                  Unsigned32,
			          ethL1IFHistPMUASTimeStamp              DateAndTime,
			          ethL1IFHistPMUASValidity               PMValidity,
			          ethL1IFHistPMUASInitialize             InitializeCmd,
                                  ethL1IFHistPMOTUUASValue               Unsigned32,
                                  ethL1IFHistPMOTUUASTimeStamp           DateAndTime,
                                  ethL1IFHistPMOTUUASValidity            PMValidity,
                                  ethL1IFHistPMOTUUASInitialize          InitializeCmd,
                                  ethL1IFHistPMOPRMinValue               FixedX10,
                                  ethL1IFHistPMOPRMinTimeStamp           DateAndTime,
                                  ethL1IFHistPMOPRMinValidity            PMValidity,
                                  ethL1IFHistPMOPRMinInitialize          InitializeCmd,
                                  ethL1IFHistPMOPRMaxValue               FixedX10,
                                  ethL1IFHistPMOPRMaxTimeStamp           DateAndTime,
                                  ethL1IFHistPMOPRMaxValidity            PMValidity,
                                  ethL1IFHistPMOPRMaxInitialize          InitializeCmd,
                                  ethL1IFHistPMOPRAvgValue               FixedX10,
                                  ethL1IFHistPMOPRAvgTimeStamp           DateAndTime,
                                  ethL1IFHistPMOPRAvgValidity            PMValidity,
                                  ethL1IFHistPMOPRAvgInitialize          InitializeCmd,
                                  ethL1IFHistPMOPTMinValue               FixedX10,
                                  ethL1IFHistPMOPTMinTimeStamp           DateAndTime,
                                  ethL1IFHistPMOPTMinValidity            PMValidity,
                                  ethL1IFHistPMOPTMinInitialize          InitializeCmd,
                                  ethL1IFHistPMOPTMaxValue               FixedX10,
                                  ethL1IFHistPMOPTMaxTimeStamp           DateAndTime,
                                  ethL1IFHistPMOPTMaxValidity            PMValidity,
                                  ethL1IFHistPMOPTMaxInitialize          InitializeCmd,
                                  ethL1IFHistPMOPTAvgValue               FixedX10,
                                  ethL1IFHistPMOPTAvgTimeStamp           DateAndTime,
                                  ethL1IFHistPMOPTAvgValidity            PMValidity,
                                  ethL1IFHistPMOPTAvgInitialize          InitializeCmd }


ethL1IFHistPMShelfIdx OBJECT-TYPE
    SYNTAX       INTEGER (1|11|21|31)
    MAX-ACCESS   not-accessible
    STATUS       current
    DESCRIPTION  "The number of the shelf on which the Ethernet Layer 1 facility targeted for
                  PMs is provisioned."
    ::= { ethL1IFHistPMEntry 1 }


ethL1IFHistPMSlotIdx OBJECT-TYPE
    SYNTAX       INTEGER (1|3|5|7|9|11|13|15|17|19)
    MAX-ACCESS   not-accessible
    STATUS       current
    DESCRIPTION  "The number of the slot within which the Ethernet Layer 1 facility targeted
                  for PMs is provisioned."
    ::= { ethL1IFHistPMEntry 2 }


ethL1IFHistPMPortTypeIdx OBJECT-TYPE
    SYNTAX       PvxL1PortType
    MAX-ACCESS   not-accessible
    STATUS       current
    DESCRIPTION  "The type of Ethernet Layer 1 port
				  targeted for PMs."
    ::= { ethL1IFHistPMEntry 3 }


ethL1IFHistPMPortIdx OBJECT-TYPE
    SYNTAX       INTEGER (1..24)
    MAX-ACCESS   not-accessible
    STATUS       current
    DESCRIPTION  "The number of the port of the identified type 
				   targeted for PMs."
    ::= { ethL1IFHistPMEntry 4 }


ethL1IFHistPMIntervalTypeIdx OBJECT-TYPE
    SYNTAX       PMIntervalType
    MAX-ACCESS   not-accessible
    STATUS       current
    DESCRIPTION  "The type of PM bin according to interval length."
    ::= { ethL1IFHistPMEntry 5 }


ethL1IFHistPMIntervalIdx OBJECT-TYPE
    SYNTAX       INTEGER (1..96)
    MAX-ACCESS   not-accessible
    STATUS       current
    DESCRIPTION  "The specific PM bin number. The range is 1..96 for 15-minute
                  bins, and for 1-day historical bins, the value is 1."
    ::= { ethL1IFHistPMEntry 6 }


ethL1IFHistPMOPRValue OBJECT-TYPE
    SYNTAX       FixedX10
    UNITS        "dBm/10"
    MAX-ACCESS   read-only
    STATUS       current
    DESCRIPTION  "The optical power received on the input of the Ethernet Layer 1 facility
                  port."
    ::= { ethL1IFHistPMEntry 7 }


ethL1IFHistPMOPRTimeStamp OBJECT-TYPE
    SYNTAX       DateAndTime
    MAX-ACCESS   read-only
    STATUS       current
    DESCRIPTION  "The date and time stamp of the optical power received value."
    ::= { ethL1IFHistPMEntry 8 }


ethL1IFHistPMOPRValidity OBJECT-TYPE
    SYNTAX       PMValidity
    MAX-ACCESS   read-only
    STATUS       current
    DESCRIPTION  "Indicates the validity of the provided optical power received
                  value."
    ::= { ethL1IFHistPMEntry 9 }


ethL1IFHistPMOPTValue OBJECT-TYPE
    SYNTAX       FixedX10
    UNITS        "dBm/10"
    MAX-ACCESS   read-only
    STATUS       current
    DESCRIPTION  "The optical power transmitted at the output of the Ethernet Layer 1 facility
                  port."
    ::= { ethL1IFHistPMEntry 10 }


ethL1IFHistPMOPTTimeStamp OBJECT-TYPE
    SYNTAX       DateAndTime
    MAX-ACCESS   read-only
    STATUS       current
    DESCRIPTION  "The date and time stamp of the optical power transmitted
                  value."
    ::= { ethL1IFHistPMEntry 11 }


ethL1IFHistPMOPTValidity OBJECT-TYPE
    SYNTAX       PMValidity
    MAX-ACCESS   read-only
    STATUS       current
    DESCRIPTION  "Indicates the validity of the provided optical power
                  transmitted value."
    ::= { ethL1IFHistPMEntry 12 }


ethL1IFHistPMTempValue OBJECT-TYPE
    SYNTAX       INTEGER (-32768..32767)
    UNITS        "degrees Celsius"
    MAX-ACCESS   read-only
    STATUS       current
    DESCRIPTION  "The temperature measured on the Ethernet Layer 1 facility port."
    ::= { ethL1IFHistPMEntry 13 }


ethL1IFHistPMTempTimeStamp OBJECT-TYPE
    SYNTAX       DateAndTime
    MAX-ACCESS   read-only
    STATUS       current
    DESCRIPTION  "The date and time stamp of the temperature value."
    ::= { ethL1IFHistPMEntry 14 }


ethL1IFHistPMTempValidity OBJECT-TYPE
    SYNTAX       PMValidity
    MAX-ACCESS   read-only
    STATUS       current
    DESCRIPTION  "Indicates the validity of the provided temperature value."
    ::= { ethL1IFHistPMEntry 15 }


ethL1IFHistPMSupplyVoltageValue OBJECT-TYPE
    SYNTAX       FixedX10
    UNITS        "mVolts/10"
    MAX-ACCESS   read-only
    STATUS       current
    DESCRIPTION  "The supply voltage measured on the Ethernet Layer 1 facility port."
    ::= { ethL1IFHistPMEntry 16 }


ethL1IFHistPMSupplyVoltageTimeStamp OBJECT-TYPE
    SYNTAX       DateAndTime
    MAX-ACCESS   read-only
    STATUS       current
    DESCRIPTION  "The date and time stamp of the supply voltage value."
    ::= { ethL1IFHistPMEntry 17 }


ethL1IFHistPMSupplyVoltageValidity OBJECT-TYPE
    SYNTAX       PMValidity
    MAX-ACCESS   read-only
    STATUS       current
    DESCRIPTION  "Indicates the validity of the provided supply voltage value."
    ::= { ethL1IFHistPMEntry 18 }


ethL1IFHistPMSupplyVoltage2Value OBJECT-TYPE
    SYNTAX       FixedX10
    UNITS        "mVolts/10"
    MAX-ACCESS   read-only
    STATUS       current
    DESCRIPTION  "A second supply voltage value measured on the Ethernet Layer 1 facility port.
    			  This object is available only for XFP-equipped Ethernet Interface ports."
    ::= { ethL1IFHistPMEntry 19 }


ethL1IFHistPMSupplyVoltage2TimeStamp OBJECT-TYPE
    SYNTAX       DateAndTime
    MAX-ACCESS   read-only
    STATUS       current
    DESCRIPTION  "The date and time stamp of the second supply voltage value."
    ::= { ethL1IFHistPMEntry 20 }


ethL1IFHistPMSupplyVoltage2Validity OBJECT-TYPE
    SYNTAX       PMValidity
    MAX-ACCESS   read-only
    STATUS       current
    DESCRIPTION  "Indicates the validity of the provided second supply voltage value."
    ::= { ethL1IFHistPMEntry 21 }


ethL1IFHistPMLBCValue OBJECT-TYPE
    SYNTAX       INTEGER (-32768..32767)
    UNITS        "mAmp"
    MAX-ACCESS   read-only
    STATUS       current
    DESCRIPTION  "The laser bias current measured on the Ethernet Layer 1 facility port."
    ::= { ethL1IFHistPMEntry 22 }


ethL1IFHistPMLBCTimeStamp OBJECT-TYPE
    SYNTAX       DateAndTime
    MAX-ACCESS   read-only
    STATUS       current
    DESCRIPTION  "The date and time stamp of the laser bias current value."
    ::= { ethL1IFHistPMEntry 23 }


ethL1IFHistPMLBCValidity OBJECT-TYPE
    SYNTAX       PMValidity
    MAX-ACCESS   read-only
    STATUS       current
    DESCRIPTION  "Indicates the validity of the provided laser bias current
                  value."
    ::= { ethL1IFHistPMEntry 24 }


ethL1IFHistPMCVValue OBJECT-TYPE
    SYNTAX       Unsigned32 
    MAX-ACCESS   read-write
    STATUS       current
    DESCRIPTION  "The count of 8B/10B coding violations. This object is only available
    			  on Gigabit Ethernet ports."
    ::= { ethL1IFHistPMEntry 25 }


ethL1IFHistPMCVTimeStamp OBJECT-TYPE
    SYNTAX       DateAndTime
    MAX-ACCESS   read-only
    STATUS       current
    DESCRIPTION  "The date and time stamp of the coding violations value."
    ::= { ethL1IFHistPMEntry 26 }


ethL1IFHistPMCVValidity OBJECT-TYPE
    SYNTAX       PMValidity
    MAX-ACCESS   read-only
    STATUS       current
    DESCRIPTION  "Indicates the validity of the provided coding violations
                  value."
    ::= { ethL1IFHistPMEntry 27 }


ethL1IFHistPMCVInitialize OBJECT-TYPE
    SYNTAX       InitializeCmd
    MAX-ACCESS   read-write
    STATUS       current
    DESCRIPTION  "Used to initialize the value of the ethL1IFHistPMCVValue object
                  to 0."
    ::= { ethL1IFHistPMEntry 28 }


ethL1IFHistPMINVBLKValue OBJECT-TYPE
    SYNTAX       Unsigned32 
    MAX-ACCESS   read-write
    STATUS       current
    DESCRIPTION  "The count of invalid blocks. This object is only available
    			  on 10 Gigabit Ethernet ports."
    ::= { ethL1IFHistPMEntry 29 }


ethL1IFHistPMINVBLKTimeStamp OBJECT-TYPE
    SYNTAX       DateAndTime
    MAX-ACCESS   read-only
    STATUS       current
    DESCRIPTION  "The date and time stamp of the invalid blocks value."
    ::= { ethL1IFHistPMEntry 30 }


ethL1IFHistPMINVBLKValidity OBJECT-TYPE
    SYNTAX       PMValidity
    MAX-ACCESS   read-only
    STATUS       current
    DESCRIPTION  "Indicates the validity of the provided invalid blocks
                  value."
    ::= { ethL1IFHistPMEntry 31 }


ethL1IFHistPMINVBLKInitialize OBJECT-TYPE
    SYNTAX       InitializeCmd
    MAX-ACCESS   read-write
    STATUS       current
    DESCRIPTION  "Used to initialize the value of the ethL1IFHistPMINVBLKValue object
                  to 0."
    ::= { ethL1IFHistPMEntry 32 }


ethL1IFHistPMESValue OBJECT-TYPE
    SYNTAX       Unsigned32
    MAX-ACCESS   read-write
    STATUS       current
    DESCRIPTION  "The count of Ethernet Layer 1 errored seconds."
    ::= { ethL1IFHistPMEntry 33 }


ethL1IFHistPMESTimeStamp OBJECT-TYPE
    SYNTAX       DateAndTime
    MAX-ACCESS   read-only
    STATUS       current
    DESCRIPTION  "The date and time stamp of the Ethernet Layer 1 errored seconds value."
    ::= { ethL1IFHistPMEntry 34 }


ethL1IFHistPMESValidity OBJECT-TYPE
    SYNTAX       PMValidity
    MAX-ACCESS   read-only
    STATUS       current
    DESCRIPTION  "Indicates the validity of the provided Ethernet Layer 1 errored seconds
                  value."
    ::= { ethL1IFHistPMEntry 35 }


ethL1IFHistPMESInitialize OBJECT-TYPE
    SYNTAX       InitializeCmd
    MAX-ACCESS   read-write
    STATUS       current
    DESCRIPTION  "Used to initialize the value of the ethL1IFHistPMESValue object
                  to 0."
    ::= { ethL1IFHistPMEntry 36 }


ethL1IFHistPMSESValue OBJECT-TYPE
    SYNTAX       Unsigned32
    MAX-ACCESS   read-write
    STATUS       current
    DESCRIPTION  "The count of Ethernet Layer 1 severely errored seconds."
    ::= { ethL1IFHistPMEntry 37 }


ethL1IFHistPMSESTimeStamp OBJECT-TYPE
    SYNTAX       DateAndTime
    MAX-ACCESS   read-only
    STATUS       current
    DESCRIPTION  "The date and time stamp of the Ethernet Layer 1 severely errored seconds
                  value."
    ::= { ethL1IFHistPMEntry 38 }


ethL1IFHistPMSESValidity OBJECT-TYPE
    SYNTAX       PMValidity
    MAX-ACCESS   read-only
    STATUS       current
    DESCRIPTION  "Indicates the validity of the provided Ethernet Layer 1 severely errored
                  seconds value."
    ::= { ethL1IFHistPMEntry 39 }


ethL1IFHistPMSESInitialize OBJECT-TYPE
    SYNTAX       InitializeCmd
    MAX-ACCESS   read-write
    STATUS       current
    DESCRIPTION  "Used to initialize the value of the ethL1IFHistPMSESValue object
                  to 0."
    ::= { ethL1IFHistPMEntry 40 }


ethL1IFHistPMOTUEBValue OBJECT-TYPE
    SYNTAX       Unsigned32 
    MAX-ACCESS   read-write
    STATUS       current
    DESCRIPTION  "The count of OTU digital wrapper layer errored blocks."
    ::= { ethL1IFHistPMEntry 41 }


ethL1IFHistPMOTUEBTimeStamp OBJECT-TYPE
    SYNTAX       DateAndTime
    MAX-ACCESS   read-only
    STATUS       current
    DESCRIPTION  "The date and time stamp of the OTU digital wrapper layer
                  errored blocks value."
    ::= { ethL1IFHistPMEntry 42 }


ethL1IFHistPMOTUEBValidity OBJECT-TYPE
    SYNTAX       PMValidity
    MAX-ACCESS   read-only
    STATUS       current
    DESCRIPTION  "Indicates the validity of the provided OTU digital wrapper
                  layer errored blocks value."
    ::= { ethL1IFHistPMEntry 43 }


ethL1IFHistPMOTUEBInitialize OBJECT-TYPE
    SYNTAX       InitializeCmd
    MAX-ACCESS   read-write
    STATUS       current
    DESCRIPTION  "Used to initialize the value of the ethL1IFHistPMOTUEBValue object
                  to 0."
    ::= { ethL1IFHistPMEntry 44 }


ethL1IFHistPMOTUBBEValue OBJECT-TYPE
    SYNTAX       Unsigned32 
    MAX-ACCESS   read-write
    STATUS       current
    DESCRIPTION  "The count of OTU digital wrapper layer background block
                  errors."
    ::= { ethL1IFHistPMEntry 45 }


ethL1IFHistPMOTUBBETimeStamp OBJECT-TYPE
    SYNTAX       DateAndTime
    MAX-ACCESS   read-only
    STATUS       current
    DESCRIPTION  "The date and time stamp of the OTU digital wrapper layer
                  background block errors value."
    ::= { ethL1IFHistPMEntry 46 }


ethL1IFHistPMOTUBBEValidity OBJECT-TYPE
    SYNTAX       PMValidity
    MAX-ACCESS   read-only
    STATUS       current
    DESCRIPTION  "Indicates the validity of the provided OTU digital wrapper
                  layer background block errors value."
    ::= { ethL1IFHistPMEntry 47 }


ethL1IFHistPMOTUBBEInitialize OBJECT-TYPE
    SYNTAX       InitializeCmd
    MAX-ACCESS   read-write
    STATUS       current
    DESCRIPTION  "Used to initialize the value of the ethL1IFHistPMOTUBBEValue object
                  to 0."
    ::= { ethL1IFHistPMEntry 48 }


ethL1IFHistPMOTUESValue OBJECT-TYPE
    SYNTAX       Unsigned32
    MAX-ACCESS   read-write
    STATUS       current
    DESCRIPTION  "The count of OTU digital wrapper layer errored seconds."
    ::= { ethL1IFHistPMEntry 49 }


ethL1IFHistPMOTUESTimeStamp OBJECT-TYPE
    SYNTAX       DateAndTime
    MAX-ACCESS   read-only
    STATUS       current
    DESCRIPTION  "The date and time stamp of the OTU digital wrapper layer
                  errored seconds value."
    ::= { ethL1IFHistPMEntry 50 }


ethL1IFHistPMOTUESValidity OBJECT-TYPE
    SYNTAX       PMValidity
    MAX-ACCESS   read-only
    STATUS       current
    DESCRIPTION  "Indicates the validity of the provided OTU digital wrapper
                  layer errored seconds value."
    ::= { ethL1IFHistPMEntry 51 }


ethL1IFHistPMOTUESInitialize OBJECT-TYPE
    SYNTAX       InitializeCmd
    MAX-ACCESS   read-write
    STATUS       current
    DESCRIPTION  "Used to initialize the value of the ethL1IFHistPMOTUESValue object
                  to 0."
    ::= { ethL1IFHistPMEntry 52 }


ethL1IFHistPMOTUSESValue OBJECT-TYPE
    SYNTAX       Unsigned32
    MAX-ACCESS   read-write
    STATUS       current
    DESCRIPTION  "The count of OTU digital wrapper layer severely errored
                  seconds."
    ::= { ethL1IFHistPMEntry 53 }


ethL1IFHistPMOTUSESTimeStamp OBJECT-TYPE
    SYNTAX       DateAndTime
    MAX-ACCESS   read-only
    STATUS       current
    DESCRIPTION  "The date and time stamp of the OTU digital wrapper layer
                  severely errored seconds value."
    ::= { ethL1IFHistPMEntry 54 }


ethL1IFHistPMOTUSESValidity OBJECT-TYPE
    SYNTAX       PMValidity
    MAX-ACCESS   read-only
    STATUS       current
    DESCRIPTION  "Indicates the validity of the provided OTU digital wrapper
                  layer severely errored seconds value."
    ::= { ethL1IFHistPMEntry 55 }


ethL1IFHistPMOTUSESInitialize OBJECT-TYPE
    SYNTAX       InitializeCmd
    MAX-ACCESS   read-write
    STATUS       current
    DESCRIPTION  "Used to initialize the value of the ethL1IFHistPMOTUSESValue object
                  to 0."
    ::= { ethL1IFHistPMEntry 56 }


ethL1IFHistPMOTUOFSValue OBJECT-TYPE
    SYNTAX       Unsigned32
    MAX-ACCESS   read-write
    STATUS       current
    DESCRIPTION  "The count of OTU digital wrapper layer out-of-frame seconds."
    ::= { ethL1IFHistPMEntry 57 }


ethL1IFHistPMOTUOFSTimeStamp OBJECT-TYPE
    SYNTAX       DateAndTime
    MAX-ACCESS   read-only
    STATUS       current
    DESCRIPTION  "The date and time stamp of the OTU digital wrapper layer
                  out-of-frame seconds value."
    ::= { ethL1IFHistPMEntry 58 }


ethL1IFHistPMOTUOFSValidity OBJECT-TYPE
    SYNTAX       PMValidity
    MAX-ACCESS   read-only
    STATUS       current
    DESCRIPTION  "Indicates the validity of the provided OTU digital wrapper
                  layer out-of-frame seconds value."
    ::= { ethL1IFHistPMEntry 59 }


ethL1IFHistPMOTUOFSInitialize OBJECT-TYPE
    SYNTAX       InitializeCmd
    MAX-ACCESS   read-write
    STATUS       current
    DESCRIPTION  "Used to initialize the value of the ethL1IFHistPMOTUOFSValue object
                  to 0."
    ::= { ethL1IFHistPMEntry 60 }


ethL1IFHistPMNBITCRValue OBJECT-TYPE
    SYNTAX       Unsigned32
    MAX-ACCESS   read-write
    STATUS       current
    DESCRIPTION  "The count of the number of bits corrected."
    ::= { ethL1IFHistPMEntry 61 }


ethL1IFHistPMNBITCRTimeStamp OBJECT-TYPE
    SYNTAX       DateAndTime
    MAX-ACCESS   read-only
    STATUS       current
    DESCRIPTION  "The date and time stamp of the number of bits corrected
                  value."
    ::= { ethL1IFHistPMEntry 62 }


ethL1IFHistPMNBITCRValidity OBJECT-TYPE
    SYNTAX       PMValidity
    MAX-ACCESS   read-only
    STATUS       current
    DESCRIPTION  "Indicates the validity of the provided number of bits
                  corrected value."
    ::= { ethL1IFHistPMEntry 63 }


ethL1IFHistPMNBITCRInitialize OBJECT-TYPE
    SYNTAX       InitializeCmd
    MAX-ACCESS   read-write
    STATUS       current
    DESCRIPTION  "Used to initialize the value of the ethL1IFHistPMNBITCRValue object
                  to 0."
    ::= { ethL1IFHistPMEntry 64 }


ethL1IFHistPMNBYTCRValue OBJECT-TYPE
    SYNTAX       Unsigned32
    MAX-ACCESS   read-write
    STATUS       current
    DESCRIPTION  "The count of the number of bytes corrected. This object
                  applies only to OC-192 line port provisioned for OTN line
                  mapping."
    ::= { ethL1IFHistPMEntry 65 }


ethL1IFHistPMNBYTCRTimeStamp OBJECT-TYPE
    SYNTAX       DateAndTime
    MAX-ACCESS   read-only
    STATUS       current
    DESCRIPTION  "The date and time stamp of the number of bytes corrected
                  value."
    ::= { ethL1IFHistPMEntry 66 }


ethL1IFHistPMNBYTCRValidity OBJECT-TYPE
    SYNTAX       PMValidity
    MAX-ACCESS   read-only
    STATUS       current
    DESCRIPTION  "Indicates the validity of the provided number of bytes
                  corrected value."
    ::= { ethL1IFHistPMEntry 67 }


ethL1IFHistPMNBYTCRInitialize OBJECT-TYPE
    SYNTAX       InitializeCmd
    MAX-ACCESS   read-write
    STATUS       current
    DESCRIPTION  "Used to initialize the value of the ethL1IFHistPMNBYTCRValue object
                  to 0."
    ::= { ethL1IFHistPMEntry 68 }


ethL1IFHistPMUNCRCDWValue OBJECT-TYPE
    SYNTAX       Unsigned32
    MAX-ACCESS   read-write
    STATUS       current
    DESCRIPTION  "The count of uncorrectable codewords. This object applies only
                  to OC-192 line port provisioned for OTN line mapping."
    ::= { ethL1IFHistPMEntry 69 }


ethL1IFHistPMUNCRCDWTimeStamp OBJECT-TYPE
    SYNTAX       DateAndTime
    MAX-ACCESS   read-only
    STATUS       current
    DESCRIPTION  "The date and time stamp of the uncorrectable codewords value."
    ::= { ethL1IFHistPMEntry 70 }


ethL1IFHistPMUNCRCDWValidity OBJECT-TYPE
    SYNTAX       PMValidity
    MAX-ACCESS   read-only
    STATUS       current
    DESCRIPTION  "Indicates the validity of the provided uncorrectable codewords
                  value."
    ::= { ethL1IFHistPMEntry 71 }


ethL1IFHistPMUNCRCDWInitialize OBJECT-TYPE
    SYNTAX       InitializeCmd
    MAX-ACCESS   read-write
    STATUS       current
    DESCRIPTION  "Used to initialize the value of the ethL1IFHistPMUNCRCDWValue object
                  to 0."
    ::= { ethL1IFHistPMEntry 72 }


ethL1IFHistPMOTNBERValue OBJECT-TYPE
    SYNTAX       DisplayString
    MAX-ACCESS   read-only
    STATUS       current
    DESCRIPTION  "The instantaneous BER of the line port."
    ::= { ethL1IFHistPMEntry 73 }


ethL1IFHistPMOTNBERTimeStamp OBJECT-TYPE
    SYNTAX       DateAndTime
    MAX-ACCESS   read-only
    STATUS       current
    DESCRIPTION  "The date and time stamp of the instantaneous BER."
    ::= { ethL1IFHistPMEntry 74 }


ethL1IFHistPMOTNBERValidity OBJECT-TYPE
    SYNTAX       PMValidity
    MAX-ACCESS   read-only
    STATUS       current
    DESCRIPTION  "Indicates the validity of the provided instantaneous BER."
    ::= { ethL1IFHistPMEntry 75 }


ethL1IFHistPMOTNBERInitialize OBJECT-TYPE
    SYNTAX       InitializeCmd
    MAX-ACCESS   read-write
    STATUS       current
    DESCRIPTION  "Used to initialize the value of the ethL1IFHistPMOTNBERValue object
                  to 0."
    ::= { ethL1IFHistPMEntry 76 }


ethL1IFHistPMOTNAVGBERValue OBJECT-TYPE
    SYNTAX       DisplayString
    MAX-ACCESS   read-only
    STATUS       current
    DESCRIPTION  "The interval/average BER of the line port."
    ::= { ethL1IFHistPMEntry 77 }


ethL1IFHistPMOTNAVGBERTimeStamp OBJECT-TYPE
    SYNTAX       DateAndTime
    MAX-ACCESS   read-only
    STATUS       current
    DESCRIPTION  "The date and time stamp of the interval/average BER."
    ::= { ethL1IFHistPMEntry 78 }


ethL1IFHistPMOTNAVGBERValidity OBJECT-TYPE
    SYNTAX       PMValidity
    MAX-ACCESS   read-only
    STATUS       current
    DESCRIPTION  "Indicates the validity of the provided interval/average BER."
    ::= { ethL1IFHistPMEntry 79 }


ethL1IFHistPMOTNAVGBERInitialize OBJECT-TYPE
    SYNTAX       InitializeCmd
    MAX-ACCESS   read-write
    STATUS       current
    DESCRIPTION  "Used to initialize the value of the ethL1IFHistPMOTNAVGBERValue object
                  to 0."
    ::= { ethL1IFHistPMEntry 80 }


ethL1IFHistPMNBITCR64BitValue OBJECT-TYPE
    SYNTAX       Unsigned64
    MAX-ACCESS   read-only
    STATUS       current
    DESCRIPTION  "The 64-bit count of the number of bits corrected. This object
                  applies only to xGigE line ports provisioned for OTN line
                  mapping with Forward Eror Correction (FEC)."
    ::= { ethL1IFHistPMEntry 81 }


ethL1IFHistPMNBITCR64BitTimeStamp OBJECT-TYPE
    SYNTAX       DateAndTime
    MAX-ACCESS   read-only
    STATUS       current
    DESCRIPTION  "The date and time stamp of the 64-bit number of bits corrected
                  value."
    ::= { ethL1IFHistPMEntry 82 }


ethL1IFHistPMNBITCR64BitValidity OBJECT-TYPE
    SYNTAX       PMValidity
    MAX-ACCESS   read-only
    STATUS       current
    DESCRIPTION  "Indicates the validity of the provided 64-bit number of bits
                  corrected value."
    ::= { ethL1IFHistPMEntry 83 }


ethL1IFHistPMNBITCR64BitInitialize OBJECT-TYPE
    SYNTAX       InitializeCmd
    MAX-ACCESS   read-write
    STATUS       current
    DESCRIPTION  "Used to initialize the value of the ethL1IFHistPMNBITCR64BitValue
                  object to 0."
    ::= { ethL1IFHistPMEntry 84 }


ethL1IFHistPMNBYTCR64BitValue OBJECT-TYPE
    SYNTAX       Unsigned64
    MAX-ACCESS   read-only
    STATUS       current
    DESCRIPTION  "The 64-bit count of the number of bytes corrected. This object
                  applies only to xGigE line ports provisioned for OTN line
                  mapping with Forward Eror Correction (FEC)."
    ::= { ethL1IFHistPMEntry 85 }


ethL1IFHistPMNBYTCR64BitTimeStamp OBJECT-TYPE
    SYNTAX       DateAndTime
    MAX-ACCESS   read-only
    STATUS       current
    DESCRIPTION  "The date and time stamp of the 64-bit number of bytes corrected
                  value."
    ::= { ethL1IFHistPMEntry 86 }


ethL1IFHistPMNBYTCR64BitValidity OBJECT-TYPE
    SYNTAX       PMValidity
    MAX-ACCESS   read-only
    STATUS       current
    DESCRIPTION  "Indicates the validity of the provided 64-bit number of bytes
                  corrected value."
    ::= { ethL1IFHistPMEntry 87 }


ethL1IFHistPMNBYTCR64BitInitialize OBJECT-TYPE
    SYNTAX       InitializeCmd
    MAX-ACCESS   read-write
    STATUS       current
    DESCRIPTION  "Used to initialize the value of the ethL1IFHistPMNBYTCR64BitValue
                  object to 0."
    ::= { ethL1IFHistPMEntry 88 }


ethL1IFHistPMUASValue OBJECT-TYPE
    SYNTAX       Unsigned32
    MAX-ACCESS   read-write
    STATUS       current
    DESCRIPTION  "The count of unavailable seconds. This object is only available
                  on Gigabit Ethernet ports."
    ::= { ethL1IFHistPMEntry 89 }

ethL1IFHistPMUASTimeStamp OBJECT-TYPE
    SYNTAX       DateAndTime
    MAX-ACCESS   read-only
    STATUS       current
    DESCRIPTION  "The date and time stamp of the unavailable seconds
                  value."
    ::= { ethL1IFHistPMEntry 90 }


ethL1IFHistPMUASValidity OBJECT-TYPE
    SYNTAX       PMValidity
    MAX-ACCESS   read-only
    STATUS       current
    DESCRIPTION  "Indicates the validity of the provided unavailable
                  seconds value."
    ::= { ethL1IFHistPMEntry 91 }


ethL1IFHistPMUASInitialize OBJECT-TYPE
    SYNTAX       InitializeCmd
    MAX-ACCESS   read-write
    STATUS       current
    DESCRIPTION  "Used to initialize the value of the ethL1IFHistPMUASValue
                  object to 0."
    ::= { ethL1IFHistPMEntry 92 }

ethL1IFHistPMOTUUASValue OBJECT-TYPE
    SYNTAX       Unsigned32
    MAX-ACCESS   read-write
    STATUS       current
    DESCRIPTION  "The count of OTU digital wrapper layer unavailable seconds."
    ::= { ethL1IFHistPMEntry 93 }


ethL1IFHistPMOTUUASTimeStamp OBJECT-TYPE
    SYNTAX       DateAndTime
    MAX-ACCESS   read-only
    STATUS       current
    DESCRIPTION  "The date and time stamp of the OTU digital wrapper layer
                  unavailable seconds value."
    ::= { ethL1IFHistPMEntry 94 }


ethL1IFHistPMOTUUASValidity OBJECT-TYPE
    SYNTAX       PMValidity
    MAX-ACCESS   read-only
    STATUS       current
    DESCRIPTION  "Indicates the validity of the provided OTU digital wrapper
                  layer unavailable seconds value."
    ::= { ethL1IFHistPMEntry 95 }


ethL1IFHistPMOTUUASInitialize OBJECT-TYPE
    SYNTAX       InitializeCmd
    MAX-ACCESS   read-write
    STATUS       current
    DESCRIPTION  "Used to initialize the value of the ethL1IFHistPMOTUUASValue object
                  to 0."
    ::= { ethL1IFHistPMEntry 96 }

ethL1IFHistPMOPRMinValue OBJECT-TYPE
    SYNTAX       FixedX10
    UNITS        "dBm/10"
    MAX-ACCESS   read-only
    STATUS       current
    DESCRIPTION  "The minimum optical power received on the input of the transceiver."
    ::= { ethL1IFHistPMEntry 97 }


ethL1IFHistPMOPRMinTimeStamp OBJECT-TYPE
    SYNTAX       DateAndTime
    MAX-ACCESS   read-only
    STATUS       current
    DESCRIPTION  "The date and time stamp of the minimum optical power received value."
    ::= { ethL1IFHistPMEntry 98 }


ethL1IFHistPMOPRMinValidity OBJECT-TYPE
    SYNTAX       PMValidity
    MAX-ACCESS   read-only
    STATUS       current
    DESCRIPTION  "Indicates the validity of the provided minimum optical power received
                  value."
    ::= { ethL1IFHistPMEntry 99 }

ethL1IFHistPMOPRMinInitialize OBJECT-TYPE
    SYNTAX       InitializeCmd
    MAX-ACCESS   read-write
    STATUS       current
    DESCRIPTION  "Used to initialize the value of the ethL1IFHistPMOPRMinValue
                  object to 0."
    ::= { ethL1IFHistPMEntry 100 }

ethL1IFHistPMOPRMaxValue OBJECT-TYPE
    SYNTAX       FixedX10
    UNITS        "dBm/10"
    MAX-ACCESS   read-only
    STATUS       current
    DESCRIPTION  "The maximum optical power received on the input of the transceiver."
    ::= { ethL1IFHistPMEntry 101 }


ethL1IFHistPMOPRMaxTimeStamp OBJECT-TYPE
    SYNTAX       DateAndTime
    MAX-ACCESS   read-only
    STATUS       current
    DESCRIPTION  "The date and time stamp of the maximum optical power received value."
    ::= { ethL1IFHistPMEntry 102 }


ethL1IFHistPMOPRMaxValidity OBJECT-TYPE
    SYNTAX       PMValidity
    MAX-ACCESS   read-only
    STATUS       current
    DESCRIPTION  "Indicates the validity of the provided maximum optical power received
                  value."
    ::= { ethL1IFHistPMEntry 103 }

ethL1IFHistPMOPRMaxInitialize OBJECT-TYPE
    SYNTAX       InitializeCmd
    MAX-ACCESS   read-write
    STATUS       current
    DESCRIPTION  "Used to initialize the value of the ethL1IFHistPMOPRMaxValue
                  object to 0."
    ::= { ethL1IFHistPMEntry 104 }

ethL1IFHistPMOPRAvgValue OBJECT-TYPE
    SYNTAX       FixedX10
    UNITS        "dBm/10"
    MAX-ACCESS   read-only
    STATUS       current
    DESCRIPTION  "The average optical power received on the input of the transceiver."
    ::= { ethL1IFHistPMEntry 105 }


ethL1IFHistPMOPRAvgTimeStamp OBJECT-TYPE
    SYNTAX       DateAndTime
    MAX-ACCESS   read-only
    STATUS       current
    DESCRIPTION  "The date and time stamp of the average optical power received value."
    ::= { ethL1IFHistPMEntry 106 }


ethL1IFHistPMOPRAvgValidity OBJECT-TYPE
    SYNTAX       PMValidity
    MAX-ACCESS   read-only
    STATUS       current
    DESCRIPTION  "Indicates the validity of the provided average optical power received
                  value."
    ::= { ethL1IFHistPMEntry 107 }

ethL1IFHistPMOPRAvgInitialize OBJECT-TYPE
    SYNTAX       InitializeCmd
    MAX-ACCESS   read-write
    STATUS       current
    DESCRIPTION  "Used to initialize the value of the ethL1IFHistPMOPRAvgValue
                  object to 0."
    ::= { ethL1IFHistPMEntry 108 }

ethL1IFHistPMOPTMinValue OBJECT-TYPE
    SYNTAX       FixedX10
    UNITS        "dBm/10"
    MAX-ACCESS   read-only
    STATUS       current
    DESCRIPTION  "The minimum optical power transmitted at the output of the
                  transceiver."
    ::= { ethL1IFHistPMEntry 109 }

ethL1IFHistPMOPTMinTimeStamp OBJECT-TYPE
    SYNTAX       DateAndTime
    MAX-ACCESS   read-only
    STATUS       current
    DESCRIPTION  "The date and time stamp of the minimum optical power transmitted
                  value."
    ::= { ethL1IFHistPMEntry 110 }


ethL1IFHistPMOPTMinValidity OBJECT-TYPE
    SYNTAX       PMValidity
    MAX-ACCESS   read-only
    STATUS       current
    DESCRIPTION  "Indicates the validity of the provided minimum optical power
                  transmitted value."
    ::= { ethL1IFHistPMEntry 111 }

ethL1IFHistPMOPTMinInitialize OBJECT-TYPE
    SYNTAX       InitializeCmd
    MAX-ACCESS   read-write
    STATUS       current
    DESCRIPTION  "Used to initialize the value of the ethL1IFHistPMOPTMinValue
                  object to 0."
    ::= { ethL1IFHistPMEntry 112 }

ethL1IFHistPMOPTMaxValue OBJECT-TYPE
    SYNTAX       FixedX10
    UNITS        "dBm/10"
    MAX-ACCESS   read-only
    STATUS       current
    DESCRIPTION  "The maximum optical power transmitted at the output of the
                  transceiver."
    ::= { ethL1IFHistPMEntry 113 }


ethL1IFHistPMOPTMaxTimeStamp OBJECT-TYPE
    SYNTAX       DateAndTime
    MAX-ACCESS   read-only
    STATUS       current
    DESCRIPTION  "The date and time stamp of the maximum optical power transmitted
                  value."
    ::= { ethL1IFHistPMEntry 114 }


ethL1IFHistPMOPTMaxValidity OBJECT-TYPE
    SYNTAX       PMValidity
    MAX-ACCESS   read-only
    STATUS       current
    DESCRIPTION  "Indicates the validity of the provided maximum optical power
                  transmitted value."
    ::= { ethL1IFHistPMEntry 115 }

ethL1IFHistPMOPTMaxInitialize OBJECT-TYPE
    SYNTAX       InitializeCmd
    MAX-ACCESS   read-write
    STATUS       current
    DESCRIPTION  "Used to initialize the value of the ethL1IFHistPMOPTMaxValue
                  object to 0."
    ::= { ethL1IFHistPMEntry 116 }

ethL1IFHistPMOPTAvgValue OBJECT-TYPE
    SYNTAX       FixedX10
    UNITS        "dBm/10"
    MAX-ACCESS   read-only
    STATUS       current
    DESCRIPTION  "The average optical power transmitted at the output of the
                  transceiver."
    ::= { ethL1IFHistPMEntry 117 }


ethL1IFHistPMOPTAvgTimeStamp OBJECT-TYPE
    SYNTAX       DateAndTime
    MAX-ACCESS   read-only
    STATUS       current
    DESCRIPTION  "The date and time stamp of the average optical power transmitted
                  value."
    ::= { ethL1IFHistPMEntry 118 }

ethL1IFHistPMOPTAvgValidity OBJECT-TYPE
    SYNTAX       PMValidity
    MAX-ACCESS   read-only
    STATUS       current
    DESCRIPTION  "Indicates the validity of the provided average optical power
                  transmitted value."
    ::= { ethL1IFHistPMEntry 119 }

ethL1IFHistPMOPTAvgInitialize OBJECT-TYPE
    SYNTAX       InitializeCmd
    MAX-ACCESS   read-write
    STATUS       current
    DESCRIPTION  "Used to initialize the value of the ethL1IFHistPMOPTAvgValue
                  object to 0."
    ::= { ethL1IFHistPMEntry 120 }


-----------------------------------------------------------------------
-- Objects used to manage Ethernet Layer 1 Interface Performance
-- Monitoring Threshold Levels
-----------------------------------------------------------------------


ethL1IFPMThresholdTable OBJECT-TYPE
    SYNTAX       SEQUENCE OF EthL1IFPMThresholdEntry
    MAX-ACCESS   not-accessible
    STATUS       current
    DESCRIPTION  "A table of threshold levels for performance monitoring counter
                  values on Ethernet Layer 1 facilities, that are used in the
                  generation of threshold crossing alerts."
    ::= { performance 28 }


ethL1IFPMThresholdEntry OBJECT-TYPE
    SYNTAX       EthL1IFPMThresholdEntry
    MAX-ACCESS   not-accessible
    STATUS       current
    DESCRIPTION  "The row entry object of the Ethernet Layer 1 performance
                  monitoring threshold table. Each row of this table contains a
                  set of PM thresholds for a given interval type that applies to
                  an individual Ethernet Layer 1 facility."
    INDEX        { ethL1IFPMThresholdShelfIdx,
                   ethL1IFPMThresholdSlotIdx,
                   ethL1IFPMThresholdPortTypeIdx,
                   ethL1IFPMThresholdPortIdx,
                   ethL1IFPMThresholdIntervalTypeIdx }
    ::= { ethL1IFPMThresholdTable 1 }


EthL1IFPMThresholdEntry ::= SEQUENCE { ethL1IFPMThresholdShelfIdx         INTEGER,
                                       ethL1IFPMThresholdSlotIdx          INTEGER,
                                       ethL1IFPMThresholdPortTypeIdx      PvxL1PortType,
                                       ethL1IFPMThresholdPortIdx          INTEGER,
                                       ethL1IFPMThresholdIntervalTypeIdx  PMIntervalType,
                                       ethL1IFPMThresholdCVValue          Unsigned32,
                                       ethL1IFPMThresholdINVBLKValue      Unsigned32,
                                       ethL1IFPMThresholdESValue          Unsigned32,
                                       ethL1IFPMThresholdSESValue         Unsigned32,
                                       ethL1IFPMThresholdOTUEBValue       Unsigned32,
                                       ethL1IFPMThresholdOTUBBEValue      Unsigned32,
                                       ethL1IFPMThresholdOTUESValue       Unsigned32,
                                       ethL1IFPMThresholdOTUSESValue      Unsigned32,
                                       ethL1IFPMThresholdOTUOFSValue      Unsigned32,
                                       ethL1IFPMThresholdUNCRCDWValue     Unsigned32,
                                       ethL1IFPMThresholdUASValue         Unsigned32,
                                       ethL1IFPMThresholdOTUUASValue      Unsigned32 }
                                       
      

ethL1IFPMThresholdShelfIdx OBJECT-TYPE
    SYNTAX       INTEGER (1|11|21|31)
    MAX-ACCESS   not-accessible
    STATUS       current
    DESCRIPTION  "The shelf number on which the Ethernet Layer 1 facility
                  targeted for PM thresholds is provisioned."
    ::= { ethL1IFPMThresholdEntry 1 }


ethL1IFPMThresholdSlotIdx OBJECT-TYPE
    SYNTAX       INTEGER (1|3|5|7|9|11|13|15|17|19)
    MAX-ACCESS   not-accessible
    STATUS       current
    DESCRIPTION  "The slot number on which the Ethernet Layer 1 facility
                  targeted for PM thresholds is provisioned."
    ::= { ethL1IFPMThresholdEntry 2 }


ethL1IFPMThresholdPortTypeIdx OBJECT-TYPE
    SYNTAX       PvxL1PortType
    MAX-ACCESS   not-accessible
    STATUS       current
    DESCRIPTION  "The type of Ethernet Layer 1 port
				  targeted for PM thresholds."
    ::= { ethL1IFPMThresholdEntry 3 }


ethL1IFPMThresholdPortIdx OBJECT-TYPE
    SYNTAX       INTEGER (1..24)
    MAX-ACCESS   not-accessible
    STATUS       current
    DESCRIPTION  "The number of the port of the identified type
    			  targeted for PM thresholds."
    ::= { ethL1IFPMThresholdEntry 4 }


ethL1IFPMThresholdIntervalTypeIdx OBJECT-TYPE
    SYNTAX       PMIntervalType 
    MAX-ACCESS   not-accessible
    STATUS       current
    DESCRIPTION  "The type of PM bin according to interval length. Thresholds
                  are supported for the 15-minute and 1-day PM bins only."
    ::= { ethL1IFPMThresholdEntry 5 }


ethL1IFPMThresholdCVValue OBJECT-TYPE
    SYNTAX       Unsigned32
    MAX-ACCESS   read-write
    STATUS       current
    DESCRIPTION  "The threshold for the count of 8B/10B coding
                  violations. This object is only available
    			  on Gigabit Ethernet ports."
    ::= { ethL1IFPMThresholdEntry 6 }


ethL1IFPMThresholdINVBLKValue OBJECT-TYPE
    SYNTAX       Unsigned32
    MAX-ACCESS   read-write
    STATUS       current
    DESCRIPTION  "The threshold for the count of invalid blocks. 
                  This object is only available
    			  on 10 Gigabit Ethernet ports."
    ::= { ethL1IFPMThresholdEntry 7 }


ethL1IFPMThresholdESValue OBJECT-TYPE
    SYNTAX       Unsigned32
    MAX-ACCESS   read-write
    STATUS       current
    DESCRIPTION  "The threshold for the count of errored
                  seconds."
    ::= { ethL1IFPMThresholdEntry 8 }


ethL1IFPMThresholdSESValue OBJECT-TYPE
    SYNTAX       Unsigned32
    MAX-ACCESS   read-write
    STATUS       current
    DESCRIPTION  "The threshold for the count of severely
                  errored seconds."
    ::= { ethL1IFPMThresholdEntry 9 }


ethL1IFPMThresholdOTUEBValue OBJECT-TYPE
    SYNTAX       Unsigned32
    MAX-ACCESS   read-write
    STATUS       current
    DESCRIPTION  "The threshold for the count of errored blocks at the OTU
                  digital wrapper layer."
    ::= { ethL1IFPMThresholdEntry 10 }


ethL1IFPMThresholdOTUBBEValue OBJECT-TYPE
    SYNTAX       Unsigned32
    MAX-ACCESS   read-write
    STATUS       current
    DESCRIPTION  "The threshold for the count of background block errors at the
                  OTU digital wrapper layer."
    ::= { ethL1IFPMThresholdEntry 11 }


ethL1IFPMThresholdOTUESValue OBJECT-TYPE
    SYNTAX       Unsigned32
    MAX-ACCESS   read-write
    STATUS       current
    DESCRIPTION  "The threshold for the count of errored seconds at the OTU
                  digital wrapper layer."
    ::= { ethL1IFPMThresholdEntry 12 }


ethL1IFPMThresholdOTUSESValue OBJECT-TYPE
    SYNTAX       Unsigned32
    MAX-ACCESS   read-write
    STATUS       current
    DESCRIPTION  "The threshold for the count of severely errored seconds at the
                  OTU digital wrapper layer."
    ::= { ethL1IFPMThresholdEntry 13 }


ethL1IFPMThresholdOTUOFSValue OBJECT-TYPE
    SYNTAX       Unsigned32
    MAX-ACCESS   read-write
    STATUS       current
    DESCRIPTION  "The threshold for the count of out-of-frame seconds at the OTU
                  digital wrapper layer."
    ::= { ethL1IFPMThresholdEntry 14 }


ethL1IFPMThresholdUNCRCDWValue OBJECT-TYPE
    SYNTAX       Unsigned32
    MAX-ACCESS   read-write
    STATUS       current
    DESCRIPTION  "The threshold for the count of uncorrectable codewords."
    ::= { ethL1IFPMThresholdEntry 15 }


ethL1IFPMThresholdUASValue OBJECT-TYPE
    SYNTAX       Unsigned32
    MAX-ACCESS   read-write
    STATUS       current
    DESCRIPTION  "The threshold for the count of unavailable seconds."
    ::= { ethL1IFPMThresholdEntry 16 }


ethL1IFPMThresholdOTUUASValue OBJECT-TYPE
    SYNTAX       Unsigned32
    MAX-ACCESS   read-write
    STATUS       current
    DESCRIPTION  "The threshold for the count of unavailable seconds at the
                  OTU digital wrapper layer."
    ::= { ethL1IFPMThresholdEntry 17 }


-----------------------------------------------------------------------
-- Objects used to retrieve current Ethernet Layer 2
-- Performance Monitoring statistics for PacketVX Interfaces
-----------------------------------------------------------------------


pvxL2IFCrntPMTable OBJECT-TYPE
    SYNTAX       SEQUENCE OF PvxL2IFCrntPMEntry
    MAX-ACCESS   not-accessible
    STATUS       current
    DESCRIPTION  "A table of current performance monitoring statistics collected
                  for the PacketVX Layer2 interfaces on the NE."
    ::= { performance 29 }


pvxL2IFCrntPMEntry OBJECT-TYPE
    SYNTAX       PvxL2IFCrntPMEntry
    MAX-ACCESS   not-accessible
    STATUS       current
    DESCRIPTION  "The row entry object of the PacketVX Layer 2 current
                  performance monitoring table. Each row of this table contains
                  a full set of PM statistics and related data for a current
                  measurement interval for a given PVX Layer 2 interface facility."
    INDEX        { pvxL2IFCrntPMSwitchIdx,
			       pvxL2IFCrntPMShelfIdx,
                   pvxL2IFCrntPMSlotIdx,
                   pvxL2IFCrntPMPortTypeIdx,
                   pvxL2IFCrntPMPortIdx,
                   pvxL2IFCrntPMIntervalTypeIdx }
    ::= { pvxL2IFCrntPMTable 1 }


PvxL2IFCrntPMEntry ::= SEQUENCE { pvxL2IFCrntPMSwitchIdx                 INTEGER,
					     		  pvxL2IFCrntPMShelfIdx                  INTEGER,
                                  pvxL2IFCrntPMSlotIdx                   INTEGER,
                                  pvxL2IFCrntPMPortTypeIdx               PvxPortType,
                                  pvxL2IFCrntPMPortIdx                   INTEGER,
                                  pvxL2IFCrntPMIntervalTypeIdx           PMIntervalType,
                                  pvxL2IFCrntPMTFRCRXValue               Unsigned64,
                                  pvxL2IFCrntPMTFRCRXTimeStamp           DateAndTime,
                                  pvxL2IFCrntPMTFRCRXValidity            PMValidity,
                                  pvxL2IFCrntPMTFRCRXInitialize          InitializeCmd,
                                  pvxL2IFCrntPMTFRCTXValue               Unsigned64,
                                  pvxL2IFCrntPMTFRCTXTimeStamp           DateAndTime,
                                  pvxL2IFCrntPMTFRCTXValidity            PMValidity,
                                  pvxL2IFCrntPMTFRCTXInitialize          InitializeCmd,
                                  pvxL2IFCrntPMFRDRValue                 Unsigned32,
                                  pvxL2IFCrntPMFRDRTimeStamp             DateAndTime,
                                  pvxL2IFCrntPMFRDRValidity              PMValidity,
                                  pvxL2IFCrntPMFRDRInitialize            InitializeCmd,
                                  pvxL2IFCrntPMFCSEValue                 Unsigned32,
                                  pvxL2IFCrntPMFCSETimeStamp             DateAndTime,
                                  pvxL2IFCrntPMFCSEValidity              PMValidity,
                                  pvxL2IFCrntPMFCSEInitialize            InitializeCmd,
                                  pvxL2IFCrntPMTBYCRXValue               Unsigned64,
                                  pvxL2IFCrntPMTBYCRXTimeStamp           DateAndTime,
                                  pvxL2IFCrntPMTBYCRXValidity            PMValidity,
                                  pvxL2IFCrntPMTBYCRXInitialize          InitializeCmd,
                                  pvxL2IFCrntPMTBYCTXValue               Unsigned64,
                                  pvxL2IFCrntPMTBYCTXTimeStamp           DateAndTime,
                                  pvxL2IFCrntPMTBYCTXValidity            PMValidity,
                                  pvxL2IFCrntPMTBYCTXInitialize          InitializeCmd,
                                  pvxL2IFCrntPMBCSTValue                 Unsigned64,
                                  pvxL2IFCrntPMBCSTTimeStamp             DateAndTime,
                                  pvxL2IFCrntPMBCSTValidity              PMValidity,
                                  pvxL2IFCrntPMBCSTInitialize            InitializeCmd,
                                  pvxL2IFCrntPMMCSTValue                 Unsigned64,
                                  pvxL2IFCrntPMMCSTTimeStamp             DateAndTime,
                                  pvxL2IFCrntPMMCSTValidity              PMValidity,
                                  pvxL2IFCrntPMMCSTInitialize            InitializeCmd,
                                  pvxL2IFCrntPMSIZE64Value               Unsigned64,
                                  pvxL2IFCrntPMSIZE64TimeStamp           DateAndTime,
                                  pvxL2IFCrntPMSIZE64Validity            PMValidity,
                                  pvxL2IFCrntPMSIZE64Initialize          InitializeCmd,
                                  pvxL2IFCrntPMSIZE65To127Value          Unsigned64,
                                  pvxL2IFCrntPMSIZE65To127TimeStamp      DateAndTime,
                                  pvxL2IFCrntPMSIZE65To127Validity       PMValidity,
                                  pvxL2IFCrntPMSIZE65To127Initialize     InitializeCmd,
                                  pvxL2IFCrntPMSIZE128To255Value         Unsigned64,
                                  pvxL2IFCrntPMSIZE128To255TimeStamp     DateAndTime,
                                  pvxL2IFCrntPMSIZE128To255Validity      PMValidity,
                                  pvxL2IFCrntPMSIZE128To255Initialize    InitializeCmd,
                                  pvxL2IFCrntPMSIZE256To511Value         Unsigned64,
                                  pvxL2IFCrntPMSIZE256To511TimeStamp     DateAndTime,
                                  pvxL2IFCrntPMSIZE256To511Validity      PMValidity,
                                  pvxL2IFCrntPMSIZE256To511Initialize    InitializeCmd,
                                  pvxL2IFCrntPMSIZE512To1023Value        Unsigned64,
                                  pvxL2IFCrntPMSIZE512To1023TimeStamp    DateAndTime,
                                  pvxL2IFCrntPMSIZE512To1023Validity     PMValidity,
                                  pvxL2IFCrntPMSIZE512To1023Initialize   InitializeCmd,
                                  pvxL2IFCrntPMSIZE1024To1518Value       Unsigned64,
                                  pvxL2IFCrntPMSIZE1024To1518TimeStamp   DateAndTime,
                                  pvxL2IFCrntPMSIZE1024To1518Validity    PMValidity,
                                  pvxL2IFCrntPMSIZE1024To1518Initialize  InitializeCmd,
                                  pvxL2IFCrntPMSIZEOver1518Value         Unsigned64,
                                  pvxL2IFCrntPMSIZEOver1518TimeStamp     DateAndTime,
                                  pvxL2IFCrntPMSIZEOver1518Validity      PMValidity,
                                  pvxL2IFCrntPMSIZEOver1518Initialize    InitializeCmd,
                                  pvxL2IFCrntPMTPFCRXValue               Unsigned64,
                                  pvxL2IFCrntPMTPFCRXTimeStamp           DateAndTime,
                                  pvxL2IFCrntPMTPFCRXValidity            PMValidity,
                                  pvxL2IFCrntPMTPFCRXInitialize          InitializeCmd,
                                  pvxL2IFCrntPMTPFCTXValue               Unsigned64,
                                  pvxL2IFCrntPMTPFCTXTimeStamp           DateAndTime,
                                  pvxL2IFCrntPMTPFCTXValidity            PMValidity,
                                  pvxL2IFCrntPMTPFCTXInitialize          InitializeCmd,
                                  pvxL2IFCrntPMUSIZEValue                Unsigned32,
                                  pvxL2IFCrntPMUSIZETimeStamp            DateAndTime,
                                  pvxL2IFCrntPMUSIZEValidity             PMValidity,
                                  pvxL2IFCrntPMUSIZEInitialize           InitializeCmd,
                                  pvxL2IFCrntPMOSIZEValue                Unsigned32,
                                  pvxL2IFCrntPMOSIZETimeStamp            DateAndTime,
                                  pvxL2IFCrntPMOSIZEValidity             PMValidity,
                                  pvxL2IFCrntPMOSIZEInitialize           InitializeCmd,
                                  pvxL2IFCrntPMFRGTValue                 Unsigned32,
                                  pvxL2IFCrntPMFRGTTimeStamp             DateAndTime,
                                  pvxL2IFCrntPMFRGTValidity              PMValidity,
                                  pvxL2IFCrntPMFRGTInitialize            InitializeCmd}


pvxL2IFCrntPMSwitchIdx OBJECT-TYPE
    SYNTAX       INTEGER(1..11) 
    MAX-ACCESS   not-accessible
    STATUS       current
    DESCRIPTION  "The identifier of the ethernet switch instance on which
			the Layer 2 Interface facilitiy is provisioned."
    ::= {pvxL2IFCrntPMEntry 1 }


pvxL2IFCrntPMShelfIdx OBJECT-TYPE
    SYNTAX       INTEGER (0|1|11|21|31)
    MAX-ACCESS   not-accessible
    STATUS       current
    DESCRIPTION  "The number of the shelf on which the PVX Layer2 IF targeted for
                  PMs is provisioned. For LAG entities, the shelf number is 0."
    ::= { pvxL2IFCrntPMEntry 2 }


pvxL2IFCrntPMSlotIdx OBJECT-TYPE
    SYNTAX       INTEGER (0|1|3|5|7|9|11|13|15|17|19)
    MAX-ACCESS   not-accessible
    STATUS       current
    DESCRIPTION  "The number of the slot within which the PVX Layer2 IF targeted
                  for PMs is provisioned. For LAG entities, the slot number is 0."
    ::= { pvxL2IFCrntPMEntry 3 }


pvxL2IFCrntPMPortTypeIdx OBJECT-TYPE
    SYNTAX       PvxPortType 
    MAX-ACCESS   not-accessible
    STATUS       current
    DESCRIPTION  "The type of PacketVX port on which the Layer 2 Interface facility
			is provisioned."
    ::= { pvxL2IFCrntPMEntry 4 }


pvxL2IFCrntPMPortIdx OBJECT-TYPE
    SYNTAX       INTEGER (1..24)
    MAX-ACCESS   not-accessible
    STATUS       current
    DESCRIPTION  "The number of the port of the identified type on which the PVX Layer 2 IF
                  facility targeted for PMs is provisioned."
    ::= { pvxL2IFCrntPMEntry 5 }


pvxL2IFCrntPMIntervalTypeIdx OBJECT-TYPE
    SYNTAX       PMIntervalType
    MAX-ACCESS   not-accessible
    STATUS       current
    DESCRIPTION  "The type of PM bin according to interval length."
    ::= { pvxL2IFCrntPMEntry 6 }


pvxL2IFCrntPMTFRCRXValue OBJECT-TYPE
    SYNTAX       Unsigned64
    MAX-ACCESS   read-only
    STATUS       current
    DESCRIPTION  "The total received frame count receieved on the interface."
    ::= { pvxL2IFCrntPMEntry 7 }


pvxL2IFCrntPMTFRCRXTimeStamp OBJECT-TYPE
    SYNTAX       DateAndTime
    MAX-ACCESS   read-only
    STATUS       current
    DESCRIPTION  "The date and time stamp of the total received frame count
                  value."
    ::= { pvxL2IFCrntPMEntry 8 }


pvxL2IFCrntPMTFRCRXValidity OBJECT-TYPE
    SYNTAX       PMValidity
    MAX-ACCESS   read-only
    STATUS       current
    DESCRIPTION  "Indicates the validity of the provided total received frame
                  count value."
    ::= { pvxL2IFCrntPMEntry 9 }


pvxL2IFCrntPMTFRCRXInitialize OBJECT-TYPE
    SYNTAX       InitializeCmd
    MAX-ACCESS   read-write
    STATUS       current
    DESCRIPTION  "Used to initialize the value of the pvxL2IFCrntPMTFRCRXValue object
                  to 0."
    ::= { pvxL2IFCrntPMEntry 10 }


pvxL2IFCrntPMTFRCTXValue OBJECT-TYPE
    SYNTAX       Unsigned64
    MAX-ACCESS   read-only
    STATUS       current
    DESCRIPTION  "The total transmitted frame count on the interface."
    ::= { pvxL2IFCrntPMEntry 11 }


pvxL2IFCrntPMTFRCTXTimeStamp OBJECT-TYPE
    SYNTAX       DateAndTime
    MAX-ACCESS   read-only
    STATUS       current
    DESCRIPTION  "The date and time stamp of the total transmitted frame
                  count value."
    ::= { pvxL2IFCrntPMEntry 12 }


pvxL2IFCrntPMTFRCTXValidity OBJECT-TYPE
    SYNTAX       PMValidity
    MAX-ACCESS   read-only
    STATUS       current
    DESCRIPTION  "Indicates the validity of the provided total transmitted
                  frame count value."
    ::= { pvxL2IFCrntPMEntry 13 }


pvxL2IFCrntPMTFRCTXInitialize OBJECT-TYPE
    SYNTAX       InitializeCmd
    MAX-ACCESS   read-write
    STATUS       current
    DESCRIPTION  "Used to initialize the value of the pvxL2IFCrntPMTFRCTXValue object
                  to 0."
    ::= { pvxL2IFCrntPMEntry 14 }


pvxL2IFCrntPMFRDRValue OBJECT-TYPE
    SYNTAX       Unsigned32
    MAX-ACCESS   read-write
    STATUS       current
    DESCRIPTION  "The count of discarded frames on the interface."
    ::= { pvxL2IFCrntPMEntry 15 }


pvxL2IFCrntPMFRDRTimeStamp OBJECT-TYPE
    SYNTAX       DateAndTime
    MAX-ACCESS   read-only
    STATUS       current
    DESCRIPTION  "The date and time stamp of the discarded frames value."
    ::= { pvxL2IFCrntPMEntry 16 }


pvxL2IFCrntPMFRDRValidity OBJECT-TYPE
    SYNTAX       PMValidity
    MAX-ACCESS   read-only
    STATUS       current
    DESCRIPTION  "Indicates the validity of the provided discarded frames
                  value."
    ::= { pvxL2IFCrntPMEntry 17 }


pvxL2IFCrntPMFRDRInitialize OBJECT-TYPE
    SYNTAX       InitializeCmd
    MAX-ACCESS   read-write
    STATUS       current
    DESCRIPTION  "Used to initialize the value of the pvxL2IFCrntPMFRDRValue object
                  to 0."
    ::= { pvxL2IFCrntPMEntry 18 }


pvxL2IFCrntPMFCSEValue OBJECT-TYPE
    SYNTAX       Unsigned32
    MAX-ACCESS   read-write
    STATUS       current
    DESCRIPTION  "The count of frame checksum errors on the interface."
    ::= { pvxL2IFCrntPMEntry 19 }


pvxL2IFCrntPMFCSETimeStamp OBJECT-TYPE
    SYNTAX       DateAndTime
    MAX-ACCESS   read-only
    STATUS       current
    DESCRIPTION  "The date and time stamp of the frame checksum errors value."
    ::= { pvxL2IFCrntPMEntry 20 }


pvxL2IFCrntPMFCSEValidity OBJECT-TYPE
    SYNTAX       PMValidity
    MAX-ACCESS   read-only
    STATUS       current
    DESCRIPTION  "Indicates the validity of the provided frame checksum errors
                  value."
    ::= { pvxL2IFCrntPMEntry 21 }


pvxL2IFCrntPMFCSEInitialize OBJECT-TYPE
    SYNTAX       InitializeCmd
    MAX-ACCESS   read-write
    STATUS       current
    DESCRIPTION  "Used to initialize the value of the pvxL2IFCrntPMFCSEValue
                  object to 0."
    ::= { pvxL2IFCrntPMEntry 22 }


pvxL2IFCrntPMTBYCRXValue OBJECT-TYPE
    SYNTAX       Unsigned64
    MAX-ACCESS   read-only
    STATUS       current
    DESCRIPTION  "The total received byte count on the interface."
    ::= { pvxL2IFCrntPMEntry 23 }


pvxL2IFCrntPMTBYCRXTimeStamp OBJECT-TYPE
    SYNTAX       DateAndTime
    MAX-ACCESS   read-only
    STATUS       current
    DESCRIPTION  "The date and time stamp of the total received byte count
                  value."
    ::= { pvxL2IFCrntPMEntry 24 }


pvxL2IFCrntPMTBYCRXValidity OBJECT-TYPE
    SYNTAX       PMValidity
    MAX-ACCESS   read-only
    STATUS       current
    DESCRIPTION  "Indicates the validity of the provided total received byte
                  count value."
    ::= { pvxL2IFCrntPMEntry 25 }


pvxL2IFCrntPMTBYCRXInitialize OBJECT-TYPE
    SYNTAX       InitializeCmd
    MAX-ACCESS   read-write
    STATUS       current
    DESCRIPTION  "Used to initialize the value of the pvxL2IFCrntPMTBYCRXValue
                  object to 0."
    ::= { pvxL2IFCrntPMEntry 26 }


pvxL2IFCrntPMTBYCTXValue OBJECT-TYPE
    SYNTAX       Unsigned64
    MAX-ACCESS   read-only
    STATUS       current
    DESCRIPTION  "The total transmitted byte count on the interface."
    ::= { pvxL2IFCrntPMEntry 27 }


pvxL2IFCrntPMTBYCTXTimeStamp OBJECT-TYPE
    SYNTAX       DateAndTime
    MAX-ACCESS   read-only
    STATUS       current
    DESCRIPTION  "The date and time stamp of the total transmitted byte count
                  value."
    ::= { pvxL2IFCrntPMEntry 28 }


pvxL2IFCrntPMTBYCTXValidity OBJECT-TYPE
    SYNTAX       PMValidity
    MAX-ACCESS   read-only
    STATUS       current
    DESCRIPTION  "Indicates the validity of the provided Ftotal transmitted byte
                  count value."
    ::= { pvxL2IFCrntPMEntry 29 }


pvxL2IFCrntPMTBYCTXInitialize OBJECT-TYPE
    SYNTAX       InitializeCmd
    MAX-ACCESS   read-write
    STATUS       current
    DESCRIPTION  "Used to initialize the value of the pvxL2IFCrntPMTBYCTXValue
                  object to 0."
    ::= { pvxL2IFCrntPMEntry 30 }


pvxL2IFCrntPMBCSTValue OBJECT-TYPE
    SYNTAX       Unsigned64
    MAX-ACCESS   read-only
    STATUS       current
    DESCRIPTION  "The total number of good frames received that were directed to
                  the broadcast address. Note that this does not include
                  multicast frames."
    ::= { pvxL2IFCrntPMEntry 31 }


pvxL2IFCrntPMBCSTTimeStamp OBJECT-TYPE
    SYNTAX       DateAndTime
    MAX-ACCESS   read-only
    STATUS       current
    DESCRIPTION  "The date and time stamp of the broadcast packets received
                  count value."
    ::= { pvxL2IFCrntPMEntry 32 }


pvxL2IFCrntPMBCSTValidity OBJECT-TYPE
    SYNTAX       PMValidity
    MAX-ACCESS   read-only
    STATUS       current
    DESCRIPTION  "Indicates the validity of the provided broadcast packets
                  received count value."
    ::= { pvxL2IFCrntPMEntry 33 }


pvxL2IFCrntPMBCSTInitialize OBJECT-TYPE
    SYNTAX       InitializeCmd
    MAX-ACCESS   read-write
    STATUS       current
    DESCRIPTION  "Used to initialize the value of the pvxL2IFCrntPMBCSTValue
                  object to 0."
    ::= { pvxL2IFCrntPMEntry 34 }


pvxL2IFCrntPMMCSTValue OBJECT-TYPE
    SYNTAX       Unsigned64
    MAX-ACCESS   read-only
    STATUS       current
    DESCRIPTION  "The total number of good frames received that were directed to
                  a multicast address. Note that this number does not include
                  frames directed to the broadcast address."
    ::= { pvxL2IFCrntPMEntry 35 }


pvxL2IFCrntPMMCSTTimeStamp OBJECT-TYPE
    SYNTAX       DateAndTime
    MAX-ACCESS   read-only
    STATUS       current
    DESCRIPTION  "The date and time stamp of the multicast packets received
                  count value."
    ::= { pvxL2IFCrntPMEntry 36 }


pvxL2IFCrntPMMCSTValidity OBJECT-TYPE
    SYNTAX       PMValidity
    MAX-ACCESS   read-only
    STATUS       current
    DESCRIPTION  "Indicates the validity of the provided multicast packets
                  received count value."
    ::= { pvxL2IFCrntPMEntry 37 }


pvxL2IFCrntPMMCSTInitialize OBJECT-TYPE
    SYNTAX       InitializeCmd
    MAX-ACCESS   read-write
    STATUS       current
    DESCRIPTION  "Used to initialize the value of the pvxL2IFCrntPMMCSTValue
                  object to 0."
    ::= { pvxL2IFCrntPMEntry 38 }


pvxL2IFCrntPMSIZE64Value OBJECT-TYPE
    SYNTAX       Unsigned64
    MAX-ACCESS   read-only
    STATUS       current
    DESCRIPTION  "The total number of 64 byte frames received (excluding framing
                  bits but including FCS octets)."
    ::= { pvxL2IFCrntPMEntry 39 }


pvxL2IFCrntPMSIZE64TimeStamp OBJECT-TYPE
    SYNTAX       DateAndTime
    MAX-ACCESS   read-only
    STATUS       current
    DESCRIPTION  "The date and time stamp of the count of 64-byte packets
                  received."
    ::= { pvxL2IFCrntPMEntry 40 }


pvxL2IFCrntPMSIZE64Validity OBJECT-TYPE
    SYNTAX       PMValidity
    MAX-ACCESS   read-only
    STATUS       current
    DESCRIPTION  "Indicates the validity of the provided count of 64-byte
                  packets packets received."
    ::= { pvxL2IFCrntPMEntry 41 }


pvxL2IFCrntPMSIZE64Initialize OBJECT-TYPE
    SYNTAX       InitializeCmd
    MAX-ACCESS   read-write
    STATUS       current
    DESCRIPTION  "Used to initialize the value of the pvxL2IFCrntPMSIZE64Value
                  object to 0."
    ::= { pvxL2IFCrntPMEntry 42 }


pvxL2IFCrntPMSIZE65To127Value OBJECT-TYPE
    SYNTAX       Unsigned64
    MAX-ACCESS   read-only
    STATUS       current
    DESCRIPTION  "The total number of frames received that are 65 to 127 bytes
                  inclusive in length (excluding framing bits but including FCS
                  octets)."
    ::= { pvxL2IFCrntPMEntry 43 }


pvxL2IFCrntPMSIZE65To127TimeStamp OBJECT-TYPE
    SYNTAX       DateAndTime
    MAX-ACCESS   read-only
    STATUS       current
    DESCRIPTION  "The date and time stamp of the count of packets between 65 and
                  127 bytes."
    ::= { pvxL2IFCrntPMEntry 44 }


pvxL2IFCrntPMSIZE65To127Validity OBJECT-TYPE
    SYNTAX       PMValidity
    MAX-ACCESS   read-only
    STATUS       current
    DESCRIPTION  "Indicates the validity of the provided count of packets
                  between 65 and 127 bytes."
    ::= { pvxL2IFCrntPMEntry 45 }


pvxL2IFCrntPMSIZE65To127Initialize OBJECT-TYPE
    SYNTAX       InitializeCmd
    MAX-ACCESS   read-write
    STATUS       current
    DESCRIPTION  "Used to initialize the value of the
                  pvxL2IFCrntPMSIZE65To127Value object to 0."
    ::= { pvxL2IFCrntPMEntry 46 }


pvxL2IFCrntPMSIZE128To255Value OBJECT-TYPE
    SYNTAX       Unsigned64
    MAX-ACCESS   read-only
    STATUS       current
    DESCRIPTION  "The total number of frames received that are 128 to 255 bytes
                  inclusive in length (excluding framing bits but including FCS
                  octets)."
    ::= { pvxL2IFCrntPMEntry 47 }


pvxL2IFCrntPMSIZE128To255TimeStamp OBJECT-TYPE
    SYNTAX       DateAndTime
    MAX-ACCESS   read-only
    STATUS       current
    DESCRIPTION  "The date and time stamp of the count of packets between 128
                  and 255 bytes."
    ::= { pvxL2IFCrntPMEntry 48 }


pvxL2IFCrntPMSIZE128To255Validity OBJECT-TYPE
    SYNTAX       PMValidity
    MAX-ACCESS   read-only
    STATUS       current
    DESCRIPTION  "Indicates the validity of the provided count of packets
                  between 128 and 255 bytes."
    ::= { pvxL2IFCrntPMEntry 49 }


pvxL2IFCrntPMSIZE128To255Initialize OBJECT-TYPE
    SYNTAX       InitializeCmd
    MAX-ACCESS   read-write
    STATUS       current
    DESCRIPTION  "Used to initialize the value of the
                  pvxL2IFCrntPMSIZE128To255Value object to 0."
    ::= { pvxL2IFCrntPMEntry 50 }


pvxL2IFCrntPMSIZE256To511Value OBJECT-TYPE
    SYNTAX       Unsigned64
    MAX-ACCESS   read-only
    STATUS       current
    DESCRIPTION  "The total number of frames received that are 256 to 511 bytes
                  inclusive in length (excluding framing bits but including FCS
                  octets)."
    ::= { pvxL2IFCrntPMEntry 51 }


pvxL2IFCrntPMSIZE256To511TimeStamp OBJECT-TYPE
    SYNTAX       DateAndTime
    MAX-ACCESS   read-only
    STATUS       current
    DESCRIPTION  "The date and time stamp of the count of packets between 256
                  and 511 bytes."
    ::= { pvxL2IFCrntPMEntry 52 }


pvxL2IFCrntPMSIZE256To511Validity OBJECT-TYPE
    SYNTAX       PMValidity
    MAX-ACCESS   read-only
    STATUS       current
    DESCRIPTION  "Indicates the validity of the provided count of packets
                  between 256 and 511 bytes."
    ::= { pvxL2IFCrntPMEntry 53 }


pvxL2IFCrntPMSIZE256To511Initialize OBJECT-TYPE
    SYNTAX       InitializeCmd
    MAX-ACCESS   read-write
    STATUS       current
    DESCRIPTION  "Used to initialize the value of the
                  pvxL2IFCrntPMSIZE256To511Value object to 0."
    ::= { pvxL2IFCrntPMEntry 54 }


pvxL2IFCrntPMSIZE512To1023Value OBJECT-TYPE
    SYNTAX       Unsigned64
    MAX-ACCESS   read-only
    STATUS       current
    DESCRIPTION  "The total number of frames received that are 512 to 1023 bytes
                  inclusive in length (excluding framing bits but including FCS
                  octets)."
    ::= { pvxL2IFCrntPMEntry 55 }


pvxL2IFCrntPMSIZE512To1023TimeStamp OBJECT-TYPE
    SYNTAX       DateAndTime
    MAX-ACCESS   read-only
    STATUS       current
    DESCRIPTION  "The date and time stamp of the count of packets between 512
                  and 1023 bytes."
    ::= { pvxL2IFCrntPMEntry 56 }


pvxL2IFCrntPMSIZE512To1023Validity OBJECT-TYPE
    SYNTAX       PMValidity
    MAX-ACCESS   read-only
    STATUS       current
    DESCRIPTION  "Indicates the validity of the provided count of packets
                  between 512 and 1023 bytes."
    ::= { pvxL2IFCrntPMEntry 57 }


pvxL2IFCrntPMSIZE512To1023Initialize OBJECT-TYPE
    SYNTAX       InitializeCmd
    MAX-ACCESS   read-write
    STATUS       current
    DESCRIPTION  "Used to initialize the value of the
                  pvxL2IFCrntPMSIZE512To1023Value object to 0."
    ::= { pvxL2IFCrntPMEntry 58 }


pvxL2IFCrntPMSIZE1024To1518Value OBJECT-TYPE
    SYNTAX       Unsigned64
    MAX-ACCESS   read-only
    STATUS       current
    DESCRIPTION  "The total number of frames received that are 1024 to 1518
                  bytes inclusive in length (excluding framing bits but
                  including FCS octets)."
    ::= { pvxL2IFCrntPMEntry 59 }


pvxL2IFCrntPMSIZE1024To1518TimeStamp OBJECT-TYPE
    SYNTAX       DateAndTime
    MAX-ACCESS   read-only
    STATUS       current
    DESCRIPTION  "The date and time stamp of the count of packets between 1024
                  and 1518 bytes."
    ::= { pvxL2IFCrntPMEntry 60 }


pvxL2IFCrntPMSIZE1024To1518Validity OBJECT-TYPE
    SYNTAX       PMValidity
    MAX-ACCESS   read-only
    STATUS       current
    DESCRIPTION  "Indicates the validity of the provided count of packets
                  between 1024 and 1518 bytes."
    ::= { pvxL2IFCrntPMEntry 61 }


pvxL2IFCrntPMSIZE1024To1518Initialize OBJECT-TYPE
    SYNTAX       InitializeCmd
    MAX-ACCESS   read-write
    STATUS       current
    DESCRIPTION  "Used to initialize the value of the
                  pvxL2IFCrntPMSIZE1024To1518Value object to 0."
    ::= { pvxL2IFCrntPMEntry 62 }


pvxL2IFCrntPMSIZEOver1518Value OBJECT-TYPE
    SYNTAX       Unsigned64
    MAX-ACCESS   read-only
    STATUS       current
    DESCRIPTION  "The total number of frames received that are greater than or
                  equal to 1519 bytes in length (excluding framing bits but
                  including FCS octets)."
    ::= { pvxL2IFCrntPMEntry 63 }


pvxL2IFCrntPMSIZEOver1518TimeStamp OBJECT-TYPE
    SYNTAX       DateAndTime
    MAX-ACCESS   read-only
    STATUS       current
    DESCRIPTION  "The date and time stamp of the count of packets over 1518
                  bytes."
    ::= { pvxL2IFCrntPMEntry 64 }


pvxL2IFCrntPMSIZEOver1518Validity OBJECT-TYPE
    SYNTAX       PMValidity
    MAX-ACCESS   read-only
    STATUS       current
    DESCRIPTION  "Indicates the validity of the provided count of packets over
                  1518 bytes."
    ::= { pvxL2IFCrntPMEntry 65 }


pvxL2IFCrntPMSIZEOver1518Initialize OBJECT-TYPE
    SYNTAX       InitializeCmd
    MAX-ACCESS   read-write
    STATUS       current
    DESCRIPTION  "Used to initialize the value of the
                  pvxL2IFCrntPMSIZEOver1518Value object to 0."
    ::= { pvxL2IFCrntPMEntry 66 }


pvxL2IFCrntPMTPFCRXValue OBJECT-TYPE
    SYNTAX       Unsigned64
    MAX-ACCESS   read-only
    STATUS       current
    DESCRIPTION  "The total received pause frame count on the interface."
    ::= { pvxL2IFCrntPMEntry 67 }


pvxL2IFCrntPMTPFCRXTimeStamp OBJECT-TYPE
    SYNTAX       DateAndTime
    MAX-ACCESS   read-only
    STATUS       current
    DESCRIPTION  "The date and time stamp of the total received pause frame
                  count value."
    ::= { pvxL2IFCrntPMEntry 68 }


pvxL2IFCrntPMTPFCRXValidity OBJECT-TYPE
    SYNTAX       PMValidity
    MAX-ACCESS   read-only
    STATUS       current
    DESCRIPTION  "Indicates the validity of the provided total received pause
                  frame count value."
    ::= { pvxL2IFCrntPMEntry 69 }


pvxL2IFCrntPMTPFCRXInitialize OBJECT-TYPE
    SYNTAX       InitializeCmd
    MAX-ACCESS   read-write
    STATUS       current
    DESCRIPTION  "Used to initialize the value of the pvxL2IFCrntPMTPFCRXValue
                  object to 0."
    ::= { pvxL2IFCrntPMEntry 70 }


pvxL2IFCrntPMTPFCTXValue OBJECT-TYPE
    SYNTAX       Unsigned64
    MAX-ACCESS   read-only
    STATUS       current
    DESCRIPTION  "The total transmitted pause frame count on the interface."
    ::= { pvxL2IFCrntPMEntry 71 }


pvxL2IFCrntPMTPFCTXTimeStamp OBJECT-TYPE
    SYNTAX       DateAndTime
    MAX-ACCESS   read-only
    STATUS       current
    DESCRIPTION  "The date and time stamp of the total transmitted pause frame
                  count value."
    ::= { pvxL2IFCrntPMEntry 72 }


pvxL2IFCrntPMTPFCTXValidity OBJECT-TYPE
    SYNTAX       PMValidity
    MAX-ACCESS   read-only
    STATUS       current
    DESCRIPTION  "Indicates the validity of the provided total transmitted pause
                  frame count value."
    ::= { pvxL2IFCrntPMEntry 73 }


pvxL2IFCrntPMTPFCTXInitialize OBJECT-TYPE
    SYNTAX       InitializeCmd
    MAX-ACCESS   read-write
    STATUS       current
    DESCRIPTION  "Used to initialize the value of the pvxL2IFCrntPMTPFCTXValue
                  object to 0."
    ::= { pvxL2IFCrntPMEntry 74 }


pvxL2IFCrntPMUSIZEValue OBJECT-TYPE
    SYNTAX       Unsigned32
    MAX-ACCESS   read-write
    STATUS       current
    DESCRIPTION  "The total number of frames received that were less than 64
                  octets long (excluding framing bits, but including FCS octets)
                  and were otherwise well formed."
    ::= { pvxL2IFCrntPMEntry 75 }


pvxL2IFCrntPMUSIZETimeStamp OBJECT-TYPE
    SYNTAX       DateAndTime
    MAX-ACCESS   read-only
    STATUS       current
    DESCRIPTION  "The date and time stamp of the count of undersized packets."
    ::= { pvxL2IFCrntPMEntry 76 }


pvxL2IFCrntPMUSIZEValidity OBJECT-TYPE
    SYNTAX       PMValidity
    MAX-ACCESS   read-only
    STATUS       current
    DESCRIPTION  "Indicates the validity of the provided count of undersized
                  packets."
    ::= { pvxL2IFCrntPMEntry 77 }


pvxL2IFCrntPMUSIZEInitialize OBJECT-TYPE
    SYNTAX       InitializeCmd
    MAX-ACCESS   read-write
    STATUS       current
    DESCRIPTION  "Used to initialize the value of the pvxL2IFCrntPMUSIZEValue
                  object to 0."
    ::= { pvxL2IFCrntPMEntry 78 }


pvxL2IFCrntPMOSIZEValue OBJECT-TYPE
    SYNTAX       Unsigned32
    MAX-ACCESS   read-write
    STATUS       current
    DESCRIPTION  "The total number of frames received that were longer than 9600
                  octets (excluding framing bits, but including FCS octets) and
                  were otherwise well formed."
    ::= { pvxL2IFCrntPMEntry 79 }


pvxL2IFCrntPMOSIZETimeStamp OBJECT-TYPE
    SYNTAX       DateAndTime
    MAX-ACCESS   read-only
    STATUS       current
    DESCRIPTION  "The date and time stamp of the count of oversized packets."
    ::= { pvxL2IFCrntPMEntry 80 }


pvxL2IFCrntPMOSIZEValidity OBJECT-TYPE
    SYNTAX       PMValidity
    MAX-ACCESS   read-only
    STATUS       current
    DESCRIPTION  "Indicates the validity of the provided count of oversized
                  packets."
    ::= { pvxL2IFCrntPMEntry 81 }


pvxL2IFCrntPMOSIZEInitialize OBJECT-TYPE
    SYNTAX       InitializeCmd
    MAX-ACCESS   read-write
    STATUS       current
    DESCRIPTION  "Used to initialize the value of the pvxL2IFCrntPMOSIZEValue
                  object to 0."
    ::= { pvxL2IFCrntPMEntry 82 }


pvxL2IFCrntPMFRGTValue OBJECT-TYPE
    SYNTAX       Unsigned32
    MAX-ACCESS   read-write
    STATUS       current
    DESCRIPTION  "The total number of frames received that were less than 64
                  octets in length (excluding framing bits but including FCS
                  octets) and had either a bad Frame Check Sequence (FCS) with
                  an integral number of octets (FCS Error) or a bad FCS with a
                  non-integral number of octets (Alignment Error)."
    ::= { pvxL2IFCrntPMEntry 83 }


pvxL2IFCrntPMFRGTTimeStamp OBJECT-TYPE
    SYNTAX       DateAndTime
    MAX-ACCESS   read-only
    STATUS       current
    DESCRIPTION  "The date and time stamp of the count of received packet
                  fragments."
    ::= { pvxL2IFCrntPMEntry 84 }


pvxL2IFCrntPMFRGTValidity OBJECT-TYPE
    SYNTAX       PMValidity
    MAX-ACCESS   read-only
    STATUS       current
    DESCRIPTION  "Indicates the validity of the provided count of received
                  packet fragments."
    ::= { pvxL2IFCrntPMEntry 85 }


pvxL2IFCrntPMFRGTInitialize OBJECT-TYPE
    SYNTAX       InitializeCmd
    MAX-ACCESS   read-write
    STATUS       current
    DESCRIPTION  "Used to initialize the value of the pvxL2IFCrntPMFRGTValue
                  object to 0."
    ::= { pvxL2IFCrntPMEntry 86 }

-- { pvxL2IFCrntPMEntry 87 } DELETED

-- { pvxL2IFCrntPMEntry 88 } DELETED

-- { pvxL2IFCrntPMEntry 89 } DELETED

-- { pvxL2IFCrntPMEntry 90 } DELETED


-----------------------------------------------------------------------
-- Objects used to retrieve historical Ethernet Layer 2
-- Performance Monitoring statistics for PacketVX Interfaces
-----------------------------------------------------------------------


pvxL2IFHistPMTable OBJECT-TYPE
    SYNTAX       SEQUENCE OF PvxL2IFHistPMEntry
    MAX-ACCESS   not-accessible
    STATUS       current
    DESCRIPTION  "A table of historical performance monitoring statistics
                  collected for the PacketVX Layer2 interfaces on the NE."
    ::= { performance 30 }


pvxL2IFHistPMEntry OBJECT-TYPE
    SYNTAX       PvxL2IFHistPMEntry
    MAX-ACCESS   not-accessible
    STATUS       current
    DESCRIPTION  "The row entry object of the PacketVX Layer 2 historical
                  performance monitoring table. Each row of this table contains
                  a full set of PM statistics and related data for a historical
                  measurement interval for a given PVX Layer 2 interface
                  facility."
    INDEX        { pvxL2IFHistPMSwitchIdx,
			       pvxL2IFHistPMShelfIdx,
                   pvxL2IFHistPMSlotIdx,
                   pvxL2IFHistPMPortTypeIdx,
                   pvxL2IFHistPMPortIdx,
                   pvxL2IFHistPMIntervalTypeIdx,
                   pvxL2IFHistPMIntervalIdx }
    ::= { pvxL2IFHistPMTable 1 }


PvxL2IFHistPMEntry ::= SEQUENCE { pvxL2IFHistPMSwitchIdx                 INTEGER,
					    		  pvxL2IFHistPMShelfIdx                  INTEGER,
                                  pvxL2IFHistPMSlotIdx                   INTEGER,
                                  pvxL2IFHistPMPortTypeIdx               PvxPortType,
                                  pvxL2IFHistPMPortIdx                   INTEGER,
                                  pvxL2IFHistPMIntervalTypeIdx           PMIntervalType,
                             	  pvxL2IFHistPMIntervalIdx               INTEGER,
                                  pvxL2IFHistPMTFRCRXValue               Unsigned64,
                                  pvxL2IFHistPMTFRCRXTimeStamp           DateAndTime,
                                  pvxL2IFHistPMTFRCRXValidity            PMValidity,
                                  pvxL2IFHistPMTFRCRXInitialize          InitializeCmd,
                                  pvxL2IFHistPMTFRCTXValue               Unsigned64,
                                  pvxL2IFHistPMTFRCTXTimeStamp           DateAndTime,
                                  pvxL2IFHistPMTFRCTXValidity            PMValidity,
                                  pvxL2IFHistPMTFRCTXInitialize          InitializeCmd,
                                  pvxL2IFHistPMFRDRValue                 Unsigned32,
                                  pvxL2IFHistPMFRDRTimeStamp             DateAndTime,
                                  pvxL2IFHistPMFRDRValidity              PMValidity,
                                  pvxL2IFHistPMFRDRInitialize            InitializeCmd,
                                  pvxL2IFHistPMFCSEValue                 Unsigned32,
                                  pvxL2IFHistPMFCSETimeStamp             DateAndTime,
                                  pvxL2IFHistPMFCSEValidity              PMValidity,
                                  pvxL2IFHistPMFCSEInitialize            InitializeCmd,
                                  pvxL2IFHistPMTBYCRXValue               Unsigned64,
                                  pvxL2IFHistPMTBYCRXTimeStamp           DateAndTime,
                                  pvxL2IFHistPMTBYCRXValidity            PMValidity,
                                  pvxL2IFHistPMTBYCRXInitialize          InitializeCmd,
                                  pvxL2IFHistPMTBYCTXValue               Unsigned64,
                                  pvxL2IFHistPMTBYCTXTimeStamp           DateAndTime,
                                  pvxL2IFHistPMTBYCTXValidity            PMValidity,
                                  pvxL2IFHistPMTBYCTXInitialize          InitializeCmd,
                                  pvxL2IFHistPMBCSTValue                 Unsigned64,
                                  pvxL2IFHistPMBCSTTimeStamp             DateAndTime,
                                  pvxL2IFHistPMBCSTValidity              PMValidity,
                                  pvxL2IFHistPMBCSTInitialize            InitializeCmd,
                                  pvxL2IFHistPMMCSTValue                 Unsigned64,
                                  pvxL2IFHistPMMCSTTimeStamp             DateAndTime,
                                  pvxL2IFHistPMMCSTValidity              PMValidity,
                                  pvxL2IFHistPMMCSTInitialize            InitializeCmd,
                                  pvxL2IFHistPMSIZE64Value               Unsigned64,
                                  pvxL2IFHistPMSIZE64TimeStamp           DateAndTime,
                                  pvxL2IFHistPMSIZE64Validity            PMValidity,
                                  pvxL2IFHistPMSIZE64Initialize          InitializeCmd,
                                  pvxL2IFHistPMSIZE65To127Value          Unsigned64,
                                  pvxL2IFHistPMSIZE65To127TimeStamp      DateAndTime,
                                  pvxL2IFHistPMSIZE65To127Validity       PMValidity,
                                  pvxL2IFHistPMSIZE65To127Initialize     InitializeCmd,
                                  pvxL2IFHistPMSIZE128To255Value         Unsigned64,
                                  pvxL2IFHistPMSIZE128To255TimeStamp     DateAndTime,
                                  pvxL2IFHistPMSIZE128To255Validity      PMValidity,
                                  pvxL2IFHistPMSIZE128To255Initialize    InitializeCmd,
                                  pvxL2IFHistPMSIZE256To511Value         Unsigned64,
                                  pvxL2IFHistPMSIZE256To511TimeStamp     DateAndTime,
                                  pvxL2IFHistPMSIZE256To511Validity      PMValidity,
                                  pvxL2IFHistPMSIZE256To511Initialize    InitializeCmd,
                                  pvxL2IFHistPMSIZE512To1023Value        Unsigned64,
                                  pvxL2IFHistPMSIZE512To1023TimeStamp    DateAndTime,
                                  pvxL2IFHistPMSIZE512To1023Validity     PMValidity,
                                  pvxL2IFHistPMSIZE512To1023Initialize   InitializeCmd,
                                  pvxL2IFHistPMSIZE1024To1518Value       Unsigned64,
                                  pvxL2IFHistPMSIZE1024To1518TimeStamp   DateAndTime,
                                  pvxL2IFHistPMSIZE1024To1518Validity    PMValidity,
                                  pvxL2IFHistPMSIZE1024To1518Initialize  InitializeCmd,
                                  pvxL2IFHistPMSIZEOver1518Value         Unsigned64,
                                  pvxL2IFHistPMSIZEOver1518TimeStamp     DateAndTime,
                                  pvxL2IFHistPMSIZEOver1518Validity      PMValidity,
                                  pvxL2IFHistPMSIZEOver1518Initialize    InitializeCmd,
                                  pvxL2IFHistPMTPFCRXValue               Unsigned64,
                                  pvxL2IFHistPMTPFCRXTimeStamp           DateAndTime,
                                  pvxL2IFHistPMTPFCRXValidity            PMValidity,
                                  pvxL2IFHistPMTPFCRXInitialize          InitializeCmd,
                                  pvxL2IFHistPMTPFCTXValue               Unsigned64,
                                  pvxL2IFHistPMTPFCTXTimeStamp           DateAndTime,
                                  pvxL2IFHistPMTPFCTXValidity            PMValidity,
                                  pvxL2IFHistPMTPFCTXInitialize          InitializeCmd,
                                  pvxL2IFHistPMUSIZEValue                Unsigned32,
                                  pvxL2IFHistPMUSIZETimeStamp            DateAndTime,
                                  pvxL2IFHistPMUSIZEValidity             PMValidity,
                                  pvxL2IFHistPMUSIZEInitialize           InitializeCmd,
                                  pvxL2IFHistPMOSIZEValue                Unsigned32,
                                  pvxL2IFHistPMOSIZETimeStamp            DateAndTime,
                                  pvxL2IFHistPMOSIZEValidity             PMValidity,
                                  pvxL2IFHistPMOSIZEInitialize           InitializeCmd,
                                  pvxL2IFHistPMFRGTValue                 Unsigned32,
                                  pvxL2IFHistPMFRGTTimeStamp             DateAndTime,
                                  pvxL2IFHistPMFRGTValidity              PMValidity,
                                  pvxL2IFHistPMFRGTInitialize            InitializeCmd}


pvxL2IFHistPMSwitchIdx OBJECT-TYPE
    SYNTAX       INTEGER(1..11) 
    MAX-ACCESS   not-accessible
    STATUS       current
    DESCRIPTION  "The identifier of the ethernet switch instance on which the
                  Layer 2 Interface facilitiy is provisioned."
    ::= {pvxL2IFHistPMEntry 1 }


pvxL2IFHistPMShelfIdx OBJECT-TYPE
    SYNTAX       INTEGER (0|1|11|21|31)
    MAX-ACCESS   not-accessible
    STATUS       current
    DESCRIPTION  "The number of the shelf on which the PVX Layer2 IF targeted
                  for PMs is provisioned. For LAG entities, the shelf number is 0."
    ::= { pvxL2IFHistPMEntry 2 }


pvxL2IFHistPMSlotIdx OBJECT-TYPE
    SYNTAX       INTEGER (0|1|3|5|7|9|11|13|15|17|19)
    MAX-ACCESS   not-accessible
    STATUS       current
    DESCRIPTION  "The number of the slot within which the PVX Layer2 IF targeted
                  for PMs is provisioned. For LAG entities, the slot number is 0."
    ::= { pvxL2IFHistPMEntry 3 }


pvxL2IFHistPMPortTypeIdx OBJECT-TYPE
    SYNTAX       PvxPortType 
    MAX-ACCESS   not-accessible
    STATUS       current
    DESCRIPTION  "The type of PacketVX port on which the Layer 2 Interface
                  facility is provisioned."
    ::= { pvxL2IFHistPMEntry 4 }


pvxL2IFHistPMPortIdx OBJECT-TYPE
    SYNTAX       INTEGER (1..24)
    MAX-ACCESS   not-accessible
    STATUS       current
    DESCRIPTION  "The number of the port of the identified type on which the PVX
                  Layer 2 IF facility targeted for PMs is provisioned."
    ::= { pvxL2IFHistPMEntry 5 }


pvxL2IFHistPMIntervalTypeIdx OBJECT-TYPE
    SYNTAX       PMIntervalType
    MAX-ACCESS   not-accessible
    STATUS       current
    DESCRIPTION  "The type of PM bin according to interval length."
    ::= { pvxL2IFHistPMEntry 6 }


pvxL2IFHistPMIntervalIdx OBJECT-TYPE
    SYNTAX       INTEGER (1..96)
    MAX-ACCESS   not-accessible
    STATUS       current
    DESCRIPTION  "The specific PM bin number. The range is 1 to 96 for the
                  15-minute historical bins. For the 1-day historical bin, the
                  value is 1."
    ::= { pvxL2IFHistPMEntry 7 }


pvxL2IFHistPMTFRCRXValue OBJECT-TYPE
    SYNTAX       Unsigned64
    MAX-ACCESS   read-only
    STATUS       current
    DESCRIPTION  "The total received frame count receieved on the interface."
    ::= { pvxL2IFHistPMEntry 8 }


pvxL2IFHistPMTFRCRXTimeStamp OBJECT-TYPE
    SYNTAX       DateAndTime
    MAX-ACCESS   read-only
    STATUS       current
    DESCRIPTION  "The date and time stamp of the total received frame count
                  value."
    ::= { pvxL2IFHistPMEntry 9 }


pvxL2IFHistPMTFRCRXValidity OBJECT-TYPE
    SYNTAX       PMValidity
    MAX-ACCESS   read-only
    STATUS       current
    DESCRIPTION  "Indicates the validity of the provided total received frame
                  count value."
    ::= { pvxL2IFHistPMEntry 10 }


pvxL2IFHistPMTFRCRXInitialize OBJECT-TYPE
    SYNTAX       InitializeCmd
    MAX-ACCESS   read-write
    STATUS       current
    DESCRIPTION  "Used to initialize the value of the pvxL2IFHistPMTFRCRXValue
                  object to 0."
    ::= { pvxL2IFHistPMEntry 11 }


pvxL2IFHistPMTFRCTXValue OBJECT-TYPE
    SYNTAX       Unsigned64
    MAX-ACCESS   read-only
    STATUS       current
    DESCRIPTION  "The total transmitted frame count on the interface."
    ::= { pvxL2IFHistPMEntry 12 }


pvxL2IFHistPMTFRCTXTimeStamp OBJECT-TYPE
    SYNTAX       DateAndTime
    MAX-ACCESS   read-only
    STATUS       current
    DESCRIPTION  "The date and time stamp of the total transmitted frame count
                  value."
    ::= { pvxL2IFHistPMEntry 13 }


pvxL2IFHistPMTFRCTXValidity OBJECT-TYPE
    SYNTAX       PMValidity
    MAX-ACCESS   read-only
    STATUS       current
    DESCRIPTION  "Indicates the validity of the provided total transmitted frame
                  count value."
    ::= { pvxL2IFHistPMEntry 14 }


pvxL2IFHistPMTFRCTXInitialize OBJECT-TYPE
    SYNTAX       InitializeCmd
    MAX-ACCESS   read-write
    STATUS       current
    DESCRIPTION  "Used to initialize the value of the pvxL2IFHistPMTFRCTXValue
                  object to 0."
    ::= { pvxL2IFHistPMEntry 15 }


pvxL2IFHistPMFRDRValue OBJECT-TYPE
    SYNTAX       Unsigned32
    MAX-ACCESS   read-write
    STATUS       current
    DESCRIPTION  "The count of discarded frames on the interface."
    ::= { pvxL2IFHistPMEntry 16 }


pvxL2IFHistPMFRDRTimeStamp OBJECT-TYPE
    SYNTAX       DateAndTime
    MAX-ACCESS   read-only
    STATUS       current
    DESCRIPTION  "The date and time stamp of the discarded frames value."
    ::= { pvxL2IFHistPMEntry 17 }


pvxL2IFHistPMFRDRValidity OBJECT-TYPE
    SYNTAX       PMValidity
    MAX-ACCESS   read-only
    STATUS       current
    DESCRIPTION  "Indicates the validity of the provided discarded frames
                  value."
    ::= { pvxL2IFHistPMEntry 18 }


pvxL2IFHistPMFRDRInitialize OBJECT-TYPE
    SYNTAX       InitializeCmd
    MAX-ACCESS   read-write
    STATUS       current
    DESCRIPTION  "Used to initialize the value of the pvxL2IFHistPMFRDRValue
                  object to 0."
    ::= { pvxL2IFHistPMEntry 19 }


pvxL2IFHistPMFCSEValue OBJECT-TYPE
    SYNTAX       Unsigned32
    MAX-ACCESS   read-write
    STATUS       current
    DESCRIPTION  "The count of frame checksum errors on the interface."
    ::= { pvxL2IFHistPMEntry 20 }


pvxL2IFHistPMFCSETimeStamp OBJECT-TYPE
    SYNTAX       DateAndTime
    MAX-ACCESS   read-only
    STATUS       current
    DESCRIPTION  "The date and time stamp of the frame checksum errors value."
    ::= { pvxL2IFHistPMEntry 21 }


pvxL2IFHistPMFCSEValidity OBJECT-TYPE
    SYNTAX       PMValidity
    MAX-ACCESS   read-only
    STATUS       current
    DESCRIPTION  "Indicates the validity of the provided frame checksum errors
                  value."
    ::= { pvxL2IFHistPMEntry 22 }


pvxL2IFHistPMFCSEInitialize OBJECT-TYPE
    SYNTAX       InitializeCmd
    MAX-ACCESS   read-write
    STATUS       current
    DESCRIPTION  "Used to initialize the value of the pvxL2IFHistPMFCSEValue
                  object to 0."
    ::= { pvxL2IFHistPMEntry 23 }


pvxL2IFHistPMTBYCRXValue OBJECT-TYPE
    SYNTAX       Unsigned64
    MAX-ACCESS   read-only
    STATUS       current
    DESCRIPTION  "The total received byte count on the interface."
    ::= { pvxL2IFHistPMEntry 24 }


pvxL2IFHistPMTBYCRXTimeStamp OBJECT-TYPE
    SYNTAX       DateAndTime
    MAX-ACCESS   read-only
    STATUS       current
    DESCRIPTION  "The date and time stamp of the total received byte count
                  value."
    ::= { pvxL2IFHistPMEntry 25 }


pvxL2IFHistPMTBYCRXValidity OBJECT-TYPE
    SYNTAX       PMValidity
    MAX-ACCESS   read-only
    STATUS       current
    DESCRIPTION  "Indicates the validity of the provided total received byte
                  count value."
    ::= { pvxL2IFHistPMEntry 26 }


pvxL2IFHistPMTBYCRXInitialize OBJECT-TYPE
    SYNTAX       InitializeCmd
    MAX-ACCESS   read-write
    STATUS       current
    DESCRIPTION  "Used to initialize the value of the pvxL2IFHistPMTBYCRXValue
                  object to 0."
    ::= { pvxL2IFHistPMEntry 27 }


pvxL2IFHistPMTBYCTXValue OBJECT-TYPE
    SYNTAX       Unsigned64
    MAX-ACCESS   read-only
    STATUS       current
    DESCRIPTION  "The total transmitted byte count on the interface."
    ::= { pvxL2IFHistPMEntry 28 }


pvxL2IFHistPMTBYCTXTimeStamp OBJECT-TYPE
    SYNTAX       DateAndTime
    MAX-ACCESS   read-only
    STATUS       current
    DESCRIPTION  "The date and time stamp of the total transmitted byte count
                  value."
    ::= { pvxL2IFHistPMEntry 29 }


pvxL2IFHistPMTBYCTXValidity OBJECT-TYPE
    SYNTAX       PMValidity
    MAX-ACCESS   read-only
    STATUS       current
    DESCRIPTION  "Indicates the validity of the provided Ftotal transmitted byte
                  count value."
    ::= { pvxL2IFHistPMEntry 30 }


pvxL2IFHistPMTBYCTXInitialize OBJECT-TYPE
    SYNTAX       InitializeCmd
    MAX-ACCESS   read-write
    STATUS       current
    DESCRIPTION  "Used to initialize the value of the pvxL2IFHistPMTBYCTXValue
                  object to 0."
    ::= { pvxL2IFHistPMEntry 31 }


pvxL2IFHistPMBCSTValue OBJECT-TYPE
    SYNTAX       Unsigned64
    MAX-ACCESS   read-only
    STATUS       current
    DESCRIPTION  "The total number of good frames received that were directed to
                  the broadcast address. Note that this does not include
                  multicast frames."
    ::= { pvxL2IFHistPMEntry 32 }


pvxL2IFHistPMBCSTTimeStamp OBJECT-TYPE
    SYNTAX       DateAndTime
    MAX-ACCESS   read-only
    STATUS       current
    DESCRIPTION  "The date and time stamp of the broadcast packets received
                  count value."
    ::= { pvxL2IFHistPMEntry 33 }


pvxL2IFHistPMBCSTValidity OBJECT-TYPE
    SYNTAX       PMValidity
    MAX-ACCESS   read-only
    STATUS       current
    DESCRIPTION  "Indicates the validity of the provided broadcast packets
                  received count value."
    ::= { pvxL2IFHistPMEntry 34 }


pvxL2IFHistPMBCSTInitialize OBJECT-TYPE
    SYNTAX       InitializeCmd
    MAX-ACCESS   read-write
    STATUS       current
    DESCRIPTION  "Used to initialize the value of the pvxL2IFHistPMBCSTValue
                  object to 0."
    ::= { pvxL2IFHistPMEntry 35 }


pvxL2IFHistPMMCSTValue OBJECT-TYPE
    SYNTAX       Unsigned64
    MAX-ACCESS   read-only
    STATUS       current
    DESCRIPTION  "The total number of good frames received that were directed to
                  a multicast address. Note that this number does not include
                  frames directed to the broadcast address."
    ::= { pvxL2IFHistPMEntry 36 }


pvxL2IFHistPMMCSTTimeStamp OBJECT-TYPE
    SYNTAX       DateAndTime
    MAX-ACCESS   read-only
    STATUS       current
    DESCRIPTION  "The date and time stamp of the multicast packets received
                  count value."
    ::= { pvxL2IFHistPMEntry 37 }


pvxL2IFHistPMMCSTValidity OBJECT-TYPE
    SYNTAX       PMValidity
    MAX-ACCESS   read-only
    STATUS       current
    DESCRIPTION  "Indicates the validity of the provided multicast packets
                  received count value."
    ::= { pvxL2IFHistPMEntry 38 }


pvxL2IFHistPMMCSTInitialize OBJECT-TYPE
    SYNTAX       InitializeCmd
    MAX-ACCESS   read-write
    STATUS       current
    DESCRIPTION  "Used to initialize the value of the pvxL2IFHistPMMCSTValue
                  object to 0."
    ::= { pvxL2IFHistPMEntry 39 }


pvxL2IFHistPMSIZE64Value OBJECT-TYPE
    SYNTAX       Unsigned64
    MAX-ACCESS   read-only
    STATUS       current
    DESCRIPTION  "The total number of 64 byte frames received (excluding framing
                  bits but including FCS octets)."
    ::= { pvxL2IFHistPMEntry 40 }


pvxL2IFHistPMSIZE64TimeStamp OBJECT-TYPE
    SYNTAX       DateAndTime
    MAX-ACCESS   read-only
    STATUS       current
    DESCRIPTION  "The date and time stamp of the count of 64-byte packets
                  received."
    ::= { pvxL2IFHistPMEntry 41 }


pvxL2IFHistPMSIZE64Validity OBJECT-TYPE
    SYNTAX       PMValidity
    MAX-ACCESS   read-only
    STATUS       current
    DESCRIPTION  "Indicates the validity of the provided count of 64-byte
                  packets packets received."
    ::= { pvxL2IFHistPMEntry 42 }


pvxL2IFHistPMSIZE64Initialize OBJECT-TYPE
    SYNTAX       InitializeCmd
    MAX-ACCESS   read-write
    STATUS       current
    DESCRIPTION  "Used to initialize the value of the pvxL2IFHistPMSIZE64Value
                  object to 0."
    ::= { pvxL2IFHistPMEntry 43 }


pvxL2IFHistPMSIZE65To127Value OBJECT-TYPE
    SYNTAX       Unsigned64
    MAX-ACCESS   read-only
    STATUS       current
    DESCRIPTION  "The total number of frames received that are 65 to 127 bytes
                  inclusive in length (excluding framing bits but including FCS
                  octets)."
    ::= { pvxL2IFHistPMEntry 44 }


pvxL2IFHistPMSIZE65To127TimeStamp OBJECT-TYPE
    SYNTAX       DateAndTime
    MAX-ACCESS   read-only
    STATUS       current
    DESCRIPTION  "The date and time stamp of the count of packets between 65 and
                  127 bytes."
    ::= { pvxL2IFHistPMEntry 45 }


pvxL2IFHistPMSIZE65To127Validity OBJECT-TYPE
    SYNTAX       PMValidity
    MAX-ACCESS   read-only
    STATUS       current
    DESCRIPTION  "Indicates the validity of the provided count of packets
                  between 65 and 127 bytes."
    ::= { pvxL2IFHistPMEntry 46 }


pvxL2IFHistPMSIZE65To127Initialize OBJECT-TYPE
    SYNTAX       InitializeCmd
    MAX-ACCESS   read-write
    STATUS       current
    DESCRIPTION  "Used to initialize the value of the
                  pvxL2IFHistPMSIZE65To127Value object to 0."
    ::= { pvxL2IFHistPMEntry 47 }


pvxL2IFHistPMSIZE128To255Value OBJECT-TYPE
    SYNTAX       Unsigned64
    MAX-ACCESS   read-only
    STATUS       current
    DESCRIPTION  "The total number of frames received that are 128 to 255 bytes
                  inclusive in length (excluding framing bits but including FCS
                  octets)."
    ::= { pvxL2IFHistPMEntry 48 }


pvxL2IFHistPMSIZE128To255TimeStamp OBJECT-TYPE
    SYNTAX       DateAndTime
    MAX-ACCESS   read-only
    STATUS       current
    DESCRIPTION  "The date and time stamp of the count of packets between 128
                  and 255 bytes."
    ::= { pvxL2IFHistPMEntry 49 }


pvxL2IFHistPMSIZE128To255Validity OBJECT-TYPE
    SYNTAX       PMValidity
    MAX-ACCESS   read-only
    STATUS       current
    DESCRIPTION  "Indicates the validity of the provided count of packets
                  between 128 and 255 bytes."
    ::= { pvxL2IFHistPMEntry 50 }


pvxL2IFHistPMSIZE128To255Initialize OBJECT-TYPE
    SYNTAX       InitializeCmd
    MAX-ACCESS   read-write
    STATUS       current
    DESCRIPTION  "Used to initialize the value of the
                  pvxL2IFHistPMSIZE128To255Value object to 0."
    ::= { pvxL2IFHistPMEntry 51 }


pvxL2IFHistPMSIZE256To511Value OBJECT-TYPE
    SYNTAX       Unsigned64
    MAX-ACCESS   read-only
    STATUS       current
    DESCRIPTION  "The total number of frames received that are 256 to 511 bytes
                  inclusive in length (excluding framing bits but including FCS
                  octets)."
    ::= { pvxL2IFHistPMEntry 52 }


pvxL2IFHistPMSIZE256To511TimeStamp OBJECT-TYPE
    SYNTAX       DateAndTime
    MAX-ACCESS   read-only
    STATUS       current
    DESCRIPTION  "The date and time stamp of the count of packets between 256
                  and 511 bytes."
    ::= { pvxL2IFHistPMEntry 53 }


pvxL2IFHistPMSIZE256To511Validity OBJECT-TYPE
    SYNTAX       PMValidity
    MAX-ACCESS   read-only
    STATUS       current
    DESCRIPTION  "Indicates the validity of the provided count of packets
                  between 256 and 511 bytes."
    ::= { pvxL2IFHistPMEntry 54 }


pvxL2IFHistPMSIZE256To511Initialize OBJECT-TYPE
    SYNTAX       InitializeCmd
    MAX-ACCESS   read-write
    STATUS       current
    DESCRIPTION  "Used to initialize the value of the
                  pvxL2IFHistPMSIZE256To511Value object to 0."
    ::= { pvxL2IFHistPMEntry 55 }


pvxL2IFHistPMSIZE512To1023Value OBJECT-TYPE
    SYNTAX       Unsigned64
    MAX-ACCESS   read-only
    STATUS       current
    DESCRIPTION  "The total number of frames received that are 512 to 1023 bytes
                  inclusive in length (excluding framing bits but including FCS
                  octets)."
    ::= { pvxL2IFHistPMEntry 56 }


pvxL2IFHistPMSIZE512To1023TimeStamp OBJECT-TYPE
    SYNTAX       DateAndTime
    MAX-ACCESS   read-only
    STATUS       current
    DESCRIPTION  "The date and time stamp of the count of packets between 512
                  and 1023 bytes."
    ::= { pvxL2IFHistPMEntry 57 }


pvxL2IFHistPMSIZE512To1023Validity OBJECT-TYPE
    SYNTAX       PMValidity
    MAX-ACCESS   read-only
    STATUS       current
    DESCRIPTION  "Indicates the validity of the provided count of packets
                  between 512 and 1023 bytes."
    ::= { pvxL2IFHistPMEntry 58 }


pvxL2IFHistPMSIZE512To1023Initialize OBJECT-TYPE
    SYNTAX       InitializeCmd
    MAX-ACCESS   read-write
    STATUS       current
    DESCRIPTION  "Used to initialize the value of the
                  pvxL2IFHistPMSIZE512To1023Value object to 0."
    ::= { pvxL2IFHistPMEntry 59 }


pvxL2IFHistPMSIZE1024To1518Value OBJECT-TYPE
    SYNTAX       Unsigned64
    MAX-ACCESS   read-only
    STATUS       current
    DESCRIPTION  "The total number of frames received that are 1024 to 1518
                  bytes inclusive in length (excluding framing bits but
                  including FCS octets)."
    ::= { pvxL2IFHistPMEntry 60 }


pvxL2IFHistPMSIZE1024To1518TimeStamp OBJECT-TYPE
    SYNTAX       DateAndTime
    MAX-ACCESS   read-only
    STATUS       current
    DESCRIPTION  "The date and time stamp of the count of packets between 1024
                  and 1518 bytes."
    ::= { pvxL2IFHistPMEntry 61 }


pvxL2IFHistPMSIZE1024To1518Validity OBJECT-TYPE
    SYNTAX       PMValidity
    MAX-ACCESS   read-only
    STATUS       current
    DESCRIPTION  "Indicates the validity of the provided count of packets
                  between 1024 and 1518 bytes."
    ::= { pvxL2IFHistPMEntry 62 }


pvxL2IFHistPMSIZE1024To1518Initialize OBJECT-TYPE
    SYNTAX       InitializeCmd
    MAX-ACCESS   read-write
    STATUS       current
    DESCRIPTION  "Used to initialize the value of the
                  pvxL2IFHistPMSIZE1024To1518Value object to 0."
    ::= { pvxL2IFHistPMEntry 63 }


pvxL2IFHistPMSIZEOver1518Value OBJECT-TYPE
    SYNTAX       Unsigned64
    MAX-ACCESS   read-only
    STATUS       current
    DESCRIPTION  "The total number of frames received that are greater than or
                  equal to 1519 bytes in length (excluding framing bits but
                  including FCS octets)."
    ::= { pvxL2IFHistPMEntry 64 }


pvxL2IFHistPMSIZEOver1518TimeStamp OBJECT-TYPE
    SYNTAX       DateAndTime
    MAX-ACCESS   read-only
    STATUS       current
    DESCRIPTION  "The date and time stamp of the count of packets over 1518
                  bytes."
    ::= { pvxL2IFHistPMEntry 65 }


pvxL2IFHistPMSIZEOver1518Validity OBJECT-TYPE
    SYNTAX       PMValidity
    MAX-ACCESS   read-only
    STATUS       current
    DESCRIPTION  "Indicates the validity of the provided count of packets over
                  1518 bytes."
    ::= { pvxL2IFHistPMEntry 66 }


pvxL2IFHistPMSIZEOver1518Initialize OBJECT-TYPE
    SYNTAX       InitializeCmd
    MAX-ACCESS   read-write
    STATUS       current
    DESCRIPTION  "Used to initialize the value of the
                  pvxL2IFHistPMSIZEOver1518Value object to 0."
    ::= { pvxL2IFHistPMEntry 67 }


pvxL2IFHistPMTPFCRXValue OBJECT-TYPE
    SYNTAX       Unsigned64
    MAX-ACCESS   read-only
    STATUS       current
    DESCRIPTION  "The total received pause frame count on the interface."
    ::= { pvxL2IFHistPMEntry 68 }


pvxL2IFHistPMTPFCRXTimeStamp OBJECT-TYPE
    SYNTAX       DateAndTime
    MAX-ACCESS   read-only
    STATUS       current
    DESCRIPTION  "The date and time stamp of the total received pause frame
                  count value."
    ::= { pvxL2IFHistPMEntry 69 }


pvxL2IFHistPMTPFCRXValidity OBJECT-TYPE
    SYNTAX       PMValidity
    MAX-ACCESS   read-only
    STATUS       current
    DESCRIPTION  "Indicates the validity of the provided total received pause
                  frame count value."
    ::= { pvxL2IFHistPMEntry 70 }


pvxL2IFHistPMTPFCRXInitialize OBJECT-TYPE
    SYNTAX       InitializeCmd
    MAX-ACCESS   read-write
    STATUS       current
    DESCRIPTION  "Used to initialize the value of the pvxL2IFHistPMTPFCRXValue
                  object to 0."
    ::= { pvxL2IFHistPMEntry 71 }


pvxL2IFHistPMTPFCTXValue OBJECT-TYPE
    SYNTAX       Unsigned64
    MAX-ACCESS   read-only
    STATUS       current
    DESCRIPTION  "The total transmitted pause frame count on the interface."
    ::= { pvxL2IFHistPMEntry 72 }


pvxL2IFHistPMTPFCTXTimeStamp OBJECT-TYPE
    SYNTAX       DateAndTime
    MAX-ACCESS   read-only
    STATUS       current
    DESCRIPTION  "The date and time stamp of the total transmitted pause frame
                  count value."
    ::= { pvxL2IFHistPMEntry 73 }


pvxL2IFHistPMTPFCTXValidity OBJECT-TYPE
    SYNTAX       PMValidity
    MAX-ACCESS   read-only
    STATUS       current
    DESCRIPTION  "Indicates the validity of the provided total transmitted pause
                  frame count value."
    ::= { pvxL2IFHistPMEntry 74 }


pvxL2IFHistPMTPFCTXInitialize OBJECT-TYPE
    SYNTAX       InitializeCmd
    MAX-ACCESS   read-write
    STATUS       current
    DESCRIPTION  "Used to initialize the value of the pvxL2IFHistPMTPFCTXValue
                  object to 0."
    ::= { pvxL2IFHistPMEntry 75 }


pvxL2IFHistPMUSIZEValue OBJECT-TYPE
    SYNTAX       Unsigned32
    MAX-ACCESS   read-write
    STATUS       current
    DESCRIPTION  "The total number of frames received that were less than 64
                  octets long (excluding framing bits, but including FCS octets)
                  and were otherwise well formed."
    ::= { pvxL2IFHistPMEntry 76 }


pvxL2IFHistPMUSIZETimeStamp OBJECT-TYPE
    SYNTAX       DateAndTime
    MAX-ACCESS   read-only
    STATUS       current
    DESCRIPTION  "The date and time stamp of the count of undersized packets."
    ::= { pvxL2IFHistPMEntry 77 }


pvxL2IFHistPMUSIZEValidity OBJECT-TYPE
    SYNTAX       PMValidity
    MAX-ACCESS   read-only
    STATUS       current
    DESCRIPTION  "Indicates the validity of the provided count of undersized
                  packets."
    ::= { pvxL2IFHistPMEntry 78 }


pvxL2IFHistPMUSIZEInitialize OBJECT-TYPE
    SYNTAX       InitializeCmd
    MAX-ACCESS   read-write
    STATUS       current
    DESCRIPTION  "Used to initialize the value of the pvxL2IFHistPMUSIZEValue
                  object to 0."
    ::= { pvxL2IFHistPMEntry 79 }


pvxL2IFHistPMOSIZEValue OBJECT-TYPE
    SYNTAX       Unsigned32
    MAX-ACCESS   read-write
    STATUS       current
    DESCRIPTION  "The total number of frames received that were longer than 9600
                  octets (excluding framing bits, but including FCS octets) and
                  were otherwise well formed."
    ::= { pvxL2IFHistPMEntry 80 }


pvxL2IFHistPMOSIZETimeStamp OBJECT-TYPE
    SYNTAX       DateAndTime
    MAX-ACCESS   read-only
    STATUS       current
    DESCRIPTION  "The date and time stamp of the count of oversized packets."
    ::= { pvxL2IFHistPMEntry 81 }


pvxL2IFHistPMOSIZEValidity OBJECT-TYPE
    SYNTAX       PMValidity
    MAX-ACCESS   read-only
    STATUS       current
    DESCRIPTION  "Indicates the validity of the provided count of oversized
                  packets."
    ::= { pvxL2IFHistPMEntry 82 }


pvxL2IFHistPMOSIZEInitialize OBJECT-TYPE
    SYNTAX       InitializeCmd
    MAX-ACCESS   read-write
    STATUS       current
    DESCRIPTION  "Used to initialize the value of the pvxL2IFHistPMOSIZEValue
                  object to 0."
    ::= { pvxL2IFHistPMEntry 83 }


pvxL2IFHistPMFRGTValue OBJECT-TYPE
    SYNTAX       Unsigned32
    MAX-ACCESS   read-write
    STATUS       current
    DESCRIPTION  "The total number of frames received that were less than 64
                  octets in length (excluding framing bits but including FCS
                  octets) and had either a bad Frame Check Sequence (FCS) with
                  an integral number of octets (FCS Error) or a bad FCS with a
                  non-integral number of octets (Alignment Error)."
    ::= { pvxL2IFHistPMEntry 84 }


pvxL2IFHistPMFRGTTimeStamp OBJECT-TYPE
    SYNTAX       DateAndTime
    MAX-ACCESS   read-only
    STATUS       current
    DESCRIPTION  "The date and time stamp of the count of received packet
                  fragments."
    ::= { pvxL2IFHistPMEntry 85 }


pvxL2IFHistPMFRGTValidity OBJECT-TYPE
    SYNTAX       PMValidity
    MAX-ACCESS   read-only
    STATUS       current
    DESCRIPTION  "Indicates the validity of the provided count of received
                  packet fragments."
    ::= { pvxL2IFHistPMEntry 86 }


pvxL2IFHistPMFRGTInitialize OBJECT-TYPE
    SYNTAX       InitializeCmd
    MAX-ACCESS   read-write
    STATUS       current
    DESCRIPTION  "Used to initialize the value of the pvxL2IFHistPMFRGTValue
                  object to 0."
    ::= { pvxL2IFHistPMEntry 87 }

-- { pvxL2IFHistPMEntry 88 } DELETED

-- { pvxL2IFHistPMEntry 89 } DELETED

-- { pvxL2IFHistPMEntry 90 } DELETED

-- { pvxL2IFHistPMEntry 91 } DELETED


-----------------------------------------------------------------------
-- Objects used to manage configured Ethernet Layer 2
-- Performance Monitoring thresholds levels on PacketVX Interfaces
-----------------------------------------------------------------------


pvxL2IFPMThresholdTable OBJECT-TYPE
    SYNTAX       SEQUENCE OF PvxL2IFPMThresholdEntry
    MAX-ACCESS   not-accessible
    STATUS       current
    DESCRIPTION  "A table of threshold levels for performance monitoring counter
                  values on PVX Layer 2 IF facilities, that are used in the
                  generation of threshold crossing alerts."
    ::= { performance 31 }


pvxL2IFPMThresholdEntry OBJECT-TYPE
    SYNTAX       PvxL2IFPMThresholdEntry
    MAX-ACCESS   not-accessible
    STATUS       current
    DESCRIPTION  "The row entry object of the PacketVX Layer 2 Interface
                  performance monitoring threshold table. Each row of this table
                  contains a set of PM thresholds for a given interval type that
                  applies to an individual PVX Layer 2 IF facility."
    INDEX        { pvxL2IFPMThresholdSwitchIdx,
			 pvxL2IFPMThresholdShelfIdx,
                   pvxL2IFPMThresholdSlotIdx,
                   pvxL2IFPMThresholdPortTypeIdx,
                   pvxL2IFPMThresholdPortIdx,
                   pvxL2IFPMThresholdIntervalTypeIdx }
    ::= { pvxL2IFPMThresholdTable 1 }


PvxL2IFPMThresholdEntry ::= SEQUENCE { pvxL2IFPMThresholdSwitchIdx            INTEGER,
					                   pvxL2IFPMThresholdShelfIdx             INTEGER,
                                       pvxL2IFPMThresholdSlotIdx              INTEGER,
                                       pvxL2IFPMThresholdPortTypeIdx          PvxPortType,
                                       pvxL2IFPMThresholdPortIdx              INTEGER,
                                       pvxL2IFPMThresholdIntervalTypeIdx      PMIntervalType,
                                       pvxL2IFPMThresholdFRDRValue            Unsigned32,
                                       pvxL2IFPMThresholdFCSEValue            Unsigned32,
                                       pvxL2IFPMThresholdUSIZEValue           Unsigned32,
                                       pvxL2IFPMThresholdOSIZEValue           Unsigned32,
                                       pvxL2IFPMThresholdFRGTValue            Unsigned32}


pvxL2IFPMThresholdSwitchIdx OBJECT-TYPE
    SYNTAX       INTEGER(1..11) 
    MAX-ACCESS   not-accessible
    STATUS       current
    DESCRIPTION  "The identifier of the ethernet switch instance on which the
                  Layer 2 Interface facilitiy is provisioned."
    ::= {pvxL2IFPMThresholdEntry 1 }


pvxL2IFPMThresholdShelfIdx OBJECT-TYPE
    SYNTAX       INTEGER (0|1|11|21|31)
    MAX-ACCESS   not-accessible
    STATUS       current
    DESCRIPTION  "The number of the shelf on which the PVX Layer2 IF targeted
                  for PM thresholds is provisioned. For LAG entities, the shelf number is 0."
    ::= { pvxL2IFPMThresholdEntry 2 }


pvxL2IFPMThresholdSlotIdx OBJECT-TYPE
    SYNTAX       INTEGER (0|1|3|5|7|9|11|13|15|17|19)
    MAX-ACCESS   not-accessible
    STATUS       current
    DESCRIPTION  "The number of the slot within which the PVX Layer2 IF targeted
                  for PM thresholds is provisioned. For LAG entities, the slot number is 0."
    ::= { pvxL2IFPMThresholdEntry 3 }


pvxL2IFPMThresholdPortTypeIdx OBJECT-TYPE
    SYNTAX       PvxPortType 
    MAX-ACCESS   not-accessible
    STATUS       current
    DESCRIPTION  "The type of PacketVX port on which the Layer 2 Interface
                  facility is provisioned."
    ::= { pvxL2IFPMThresholdEntry 4 }


pvxL2IFPMThresholdPortIdx OBJECT-TYPE
    SYNTAX       INTEGER (1..24)
    MAX-ACCESS   not-accessible
    STATUS       current
    DESCRIPTION  "The number of the port of the identified type on which the PVX
                  Layer 2 IF facility targeted for PM thresholds is
                  provisioned."
    ::= { pvxL2IFPMThresholdEntry 5 }


pvxL2IFPMThresholdIntervalTypeIdx OBJECT-TYPE
    SYNTAX       PMIntervalType
    MAX-ACCESS   not-accessible
    STATUS       current
    DESCRIPTION  "The type of PM bin according to interval length."
    ::= { pvxL2IFPMThresholdEntry 6 }


pvxL2IFPMThresholdFRDRValue OBJECT-TYPE
    SYNTAX       Unsigned32
    MAX-ACCESS   read-write
    STATUS       current
    DESCRIPTION  "The threshold for the count of discarded frames on the
                  interface."
    ::= { pvxL2IFPMThresholdEntry 7 }


pvxL2IFPMThresholdFCSEValue OBJECT-TYPE
    SYNTAX       Unsigned32
    MAX-ACCESS   read-write
    STATUS       current
    DESCRIPTION  "The threshold for the count of frame checksum errors on the
                  interface."
    ::= { pvxL2IFPMThresholdEntry 8 }


pvxL2IFPMThresholdUSIZEValue OBJECT-TYPE
    SYNTAX       Unsigned32
    MAX-ACCESS   read-write
    STATUS       current
    DESCRIPTION  "The threshold for the count of undersized frames."
    ::= { pvxL2IFPMThresholdEntry 9 }


pvxL2IFPMThresholdOSIZEValue OBJECT-TYPE
    SYNTAX       Unsigned32
    MAX-ACCESS   read-write
    STATUS       current
    DESCRIPTION  "The threshold for the count of oversized frames."
    ::= { pvxL2IFPMThresholdEntry 10 }


pvxL2IFPMThresholdFRGTValue OBJECT-TYPE
    SYNTAX       Unsigned32
    MAX-ACCESS   read-write
    STATUS       current
    DESCRIPTION  "The threshold for the count of fragmented frames."
    ::= { pvxL2IFPMThresholdEntry 11 }

-- { pvxL2IFPMThresholdEntry 12 } DELETED


-----------------------------------------------------------------------
-- Objects used to retrieve current Bit Rate Independent (BRI) port
-- Performance Monitoring statistics
-----------------------------------------------------------------------


briCrntPMTable OBJECT-TYPE
    SYNTAX       SEQUENCE OF BriCrntPMEntry
    MAX-ACCESS   not-accessible
    STATUS       current
    DESCRIPTION  "A table of current performance monitoring statistics collected
                  for the Bit Rate Independent (BRI) facilities on the NE."
    ::= { performance 38 }


briCrntPMEntry OBJECT-TYPE
    SYNTAX       BriCrntPMEntry
    MAX-ACCESS   not-accessible
    STATUS       current
    DESCRIPTION  "The row entry object of the BRI current performance
                  monitoring table. Each row of this table contains a full set
                  of PM statistics and related data for a current measurement
                  interval for a given BRI facility."
    INDEX        { briCrntPMShelfIdx,
                   briCrntPMSlotIdx,
                   briCrntPMPortIdx,
                   briCrntPMIntervalTypeIdx }
    ::= { briCrntPMTable 1 }


BriCrntPMEntry ::= SEQUENCE { briCrntPMShelfIdx                  INTEGER,
                              briCrntPMSlotIdx                   INTEGER,
                              briCrntPMPortIdx                   INTEGER,
                              briCrntPMIntervalTypeIdx           PMIntervalType,
                              briCrntPMOPRValue                  FixedX10,
                              briCrntPMOPRTimeStamp              DateAndTime,
                              briCrntPMOPRValidity               PMValidity,
                              briCrntPMOPTValue                  FixedX10,
                              briCrntPMOPTTimeStamp              DateAndTime,
                              briCrntPMOPTValidity               PMValidity,
                              briCrntPMTempValue                 INTEGER,
                              briCrntPMTempTimeStamp             DateAndTime,
                              briCrntPMTempValidity              PMValidity,
                              briCrntPMSupplyVoltageValue        FixedX10,
                              briCrntPMSupplyVoltageTimeStamp    DateAndTime,
                              briCrntPMSupplyVoltageValidity     PMValidity,
                              briCrntPMLBCValue                  INTEGER,
                              briCrntPMLBCTimeStamp              DateAndTime,
                              briCrntPMLBCValidity               PMValidity,
                              briCrntPMOPRMinValue               FixedX10,
                              briCrntPMOPRMinTimeStamp           DateAndTime,
                              briCrntPMOPRMinValidity            PMValidity,
                              briCrntPMOPRMinInitialize          InitializeCmd,
                              briCrntPMOPRMaxValue               FixedX10,
                              briCrntPMOPRMaxTimeStamp           DateAndTime,
                              briCrntPMOPRMaxValidity            PMValidity,
                              briCrntPMOPRMaxInitialize          InitializeCmd,
                              briCrntPMOPRAvgValue               FixedX10,
                              briCrntPMOPRAvgTimeStamp           DateAndTime,
                              briCrntPMOPRAvgValidity            PMValidity,
                              briCrntPMOPRAvgInitialize          InitializeCmd,
                              briCrntPMOPTMinValue               FixedX10,
                              briCrntPMOPTMinTimeStamp           DateAndTime,
                              briCrntPMOPTMinValidity            PMValidity,
                              briCrntPMOPTMinInitialize          InitializeCmd,
                              briCrntPMOPTMaxValue               FixedX10,
                              briCrntPMOPTMaxTimeStamp           DateAndTime,
                              briCrntPMOPTMaxValidity            PMValidity,
                              briCrntPMOPTMaxInitialize          InitializeCmd,
                              briCrntPMOPTAvgValue               FixedX10,
                              briCrntPMOPTAvgTimeStamp           DateAndTime,
                              briCrntPMOPTAvgValidity            PMValidity,
                              briCrntPMOPTAvgInitialize          InitializeCmd }


briCrntPMShelfIdx OBJECT-TYPE
    SYNTAX       INTEGER (1|11|21|31)
    MAX-ACCESS   not-accessible
    STATUS       current
    DESCRIPTION  "The number of the shelf on which the BRI facility targeted for
                  PMs is provisioned."
    ::= { briCrntPMEntry 1 }


briCrntPMSlotIdx OBJECT-TYPE
    SYNTAX       INTEGER (1|3|5|7|9|11|13|15|17|19)
    MAX-ACCESS   not-accessible
    STATUS       current
    DESCRIPTION  "The number of the slot within which the BRI facility targeted
                  for PMs is provisioned."
    ::= { briCrntPMEntry 2 }


briCrntPMPortIdx OBJECT-TYPE
    SYNTAX       INTEGER (3..12)
    MAX-ACCESS   not-accessible
    STATUS       current
    DESCRIPTION  "The number of the port on the circuit pack on which the BRI
                  facility targeted for PMs is provisioned."
    ::= { briCrntPMEntry 3 }


briCrntPMIntervalTypeIdx OBJECT-TYPE
    SYNTAX       PMIntervalType
    MAX-ACCESS   not-accessible
    STATUS       current
    DESCRIPTION  "The type of BRI bin according to interval length."
    ::= { briCrntPMEntry 4 }


briCrntPMOPRValue OBJECT-TYPE
    SYNTAX       FixedX10
    UNITS        "dBm/10"
    MAX-ACCESS   read-only
    STATUS       current
    DESCRIPTION  "The optical power received on the input of the BRI facility
                  port."
    ::= { briCrntPMEntry 5 }


briCrntPMOPRTimeStamp OBJECT-TYPE
    SYNTAX       DateAndTime
    MAX-ACCESS   read-only
    STATUS       current
    DESCRIPTION  "The date and time stamp of the optical power received value."
    ::= { briCrntPMEntry 6 }


briCrntPMOPRValidity OBJECT-TYPE
    SYNTAX       PMValidity
    MAX-ACCESS   read-only
    STATUS       current
    DESCRIPTION  "Indicates the validity of the provided optical power received
                  value."
    ::= { briCrntPMEntry 7 }


briCrntPMOPTValue OBJECT-TYPE
    SYNTAX       FixedX10
    UNITS        "dBm/10"
    MAX-ACCESS   read-only
    STATUS       current
    DESCRIPTION  "The optical power transmitted at the output of the BRI facility
                  port."
    ::= { briCrntPMEntry 8 }


briCrntPMOPTTimeStamp OBJECT-TYPE
    SYNTAX       DateAndTime
    MAX-ACCESS   read-only
    STATUS       current
    DESCRIPTION  "The date and time stamp of the optical power transmitted
                  value."
    ::= { briCrntPMEntry 9 }


briCrntPMOPTValidity OBJECT-TYPE
    SYNTAX       PMValidity
    MAX-ACCESS   read-only
    STATUS       current
    DESCRIPTION  "Indicates the validity of the provided optical power
                  transmitted value."
    ::= { briCrntPMEntry 10 }


briCrntPMTempValue OBJECT-TYPE
    SYNTAX       INTEGER (-32768..32767)
    UNITS        "degrees Celsius"
    MAX-ACCESS   read-only
    STATUS       current
    DESCRIPTION  "The temperature measured on the BRI facility port."
    ::= { briCrntPMEntry 11 }


briCrntPMTempTimeStamp OBJECT-TYPE
    SYNTAX       DateAndTime
    MAX-ACCESS   read-only
    STATUS       current
    DESCRIPTION  "The date and time stamp of the temperature value."
    ::= { briCrntPMEntry 12 }


briCrntPMTempValidity OBJECT-TYPE
    SYNTAX       PMValidity
    MAX-ACCESS   read-only
    STATUS       current
    DESCRIPTION  "Indicates the validity of the provided temperature value."
    ::= { briCrntPMEntry 13 }


briCrntPMSupplyVoltageValue OBJECT-TYPE
    SYNTAX       FixedX10
    UNITS        "mVolts/10"
    MAX-ACCESS   read-only
    STATUS       current
    DESCRIPTION  "The supply voltage measured on the BRI facility port."
    ::= { briCrntPMEntry 14 }


briCrntPMSupplyVoltageTimeStamp OBJECT-TYPE
    SYNTAX       DateAndTime
    MAX-ACCESS   read-only
    STATUS       current
    DESCRIPTION  "The date and time stamp of the supply voltage value."
    ::= { briCrntPMEntry 15 }


briCrntPMSupplyVoltageValidity OBJECT-TYPE
    SYNTAX       PMValidity
    MAX-ACCESS   read-only
    STATUS       current
    DESCRIPTION  "Indicates the validity of the provided supply voltage value."
    ::= { briCrntPMEntry 16 }


briCrntPMLBCValue OBJECT-TYPE
    SYNTAX       INTEGER (-32768..32767)
    UNITS        "mAmp"
    MAX-ACCESS   read-only
    STATUS       current
    DESCRIPTION  "The laser bias current measured on the BRI facility port."
    ::= { briCrntPMEntry 17 }


briCrntPMLBCTimeStamp OBJECT-TYPE
    SYNTAX       DateAndTime
    MAX-ACCESS   read-only
    STATUS       current
    DESCRIPTION  "The date and time stamp of the laser bias current value."
    ::= { briCrntPMEntry 18 }


briCrntPMLBCValidity OBJECT-TYPE
    SYNTAX       PMValidity
    MAX-ACCESS   read-only
    STATUS       current
    DESCRIPTION  "Indicates the validity of the provided laser bias current
                  value."
    ::= { briCrntPMEntry 19 }

briCrntPMOPRMinValue OBJECT-TYPE
    SYNTAX       FixedX10
    UNITS        "dBm/10"
    MAX-ACCESS   read-only
    STATUS       current
    DESCRIPTION  "The minimum optical power received on the input of the transceiver."
    ::= { briCrntPMEntry 20 }


briCrntPMOPRMinTimeStamp OBJECT-TYPE
    SYNTAX       DateAndTime
    MAX-ACCESS   read-only
    STATUS       current
    DESCRIPTION  "The date and time stamp of the minimum optical power received value."
    ::= { briCrntPMEntry 21 }


briCrntPMOPRMinValidity OBJECT-TYPE
    SYNTAX       PMValidity
    MAX-ACCESS   read-only
    STATUS       current
    DESCRIPTION  "Indicates the validity of the provided minimum optical power received
                  value."
    ::= { briCrntPMEntry 22 }

briCrntPMOPRMinInitialize OBJECT-TYPE
    SYNTAX       InitializeCmd
    MAX-ACCESS   read-write
    STATUS       current
    DESCRIPTION  "Used to initialize the value of the briCrntPMOPRMinValue
                  object to 0."
    ::= { briCrntPMEntry 23 }

briCrntPMOPRMaxValue OBJECT-TYPE
    SYNTAX       FixedX10
    UNITS        "dBm/10"
    MAX-ACCESS   read-only
    STATUS       current
    DESCRIPTION  "The maximum optical power received on the input of the transceiver."
    ::= { briCrntPMEntry 24 }


briCrntPMOPRMaxTimeStamp OBJECT-TYPE
    SYNTAX       DateAndTime
    MAX-ACCESS   read-only
    STATUS       current
    DESCRIPTION  "The date and time stamp of the maximum optical power received value."
    ::= { briCrntPMEntry 25 }


briCrntPMOPRMaxValidity OBJECT-TYPE
    SYNTAX       PMValidity
    MAX-ACCESS   read-only
    STATUS       current
    DESCRIPTION  "Indicates the validity of the provided maximum optical power received
                  value."
    ::= { briCrntPMEntry 26 }

briCrntPMOPRMaxInitialize OBJECT-TYPE
    SYNTAX       InitializeCmd
    MAX-ACCESS   read-write
    STATUS       current
    DESCRIPTION  "Used to initialize the value of the briCrntPMOPRMaxValue
                  object to 0."
    ::= { briCrntPMEntry 27 }

briCrntPMOPRAvgValue OBJECT-TYPE
    SYNTAX       FixedX10
    UNITS        "dBm/10"
    MAX-ACCESS   read-only
    STATUS       current
    DESCRIPTION  "The average optical power received on the input of the transceiver."
    ::= { briCrntPMEntry 28 }


briCrntPMOPRAvgTimeStamp OBJECT-TYPE
    SYNTAX       DateAndTime
    MAX-ACCESS   read-only
    STATUS       current
    DESCRIPTION  "The date and time stamp of the average optical power received value."
    ::= { briCrntPMEntry 29 }


briCrntPMOPRAvgValidity OBJECT-TYPE
    SYNTAX       PMValidity
    MAX-ACCESS   read-only
    STATUS       current
    DESCRIPTION  "Indicates the validity of the provided average optical power received
                  value."
    ::= { briCrntPMEntry 30 }

briCrntPMOPRAvgInitialize OBJECT-TYPE
    SYNTAX       InitializeCmd
    MAX-ACCESS   read-write
    STATUS       current
    DESCRIPTION  "Used to initialize the value of the briCrntPMOPRAvgValue
                  object to 0."
    ::= { briCrntPMEntry 31 }

briCrntPMOPTMinValue OBJECT-TYPE
    SYNTAX       FixedX10
    UNITS        "dBm/10"
    MAX-ACCESS   read-only
    STATUS       current
    DESCRIPTION  "The minimum optical power transmitted at the output of the
                  transceiver."
    ::= { briCrntPMEntry 32 }

briCrntPMOPTMinTimeStamp OBJECT-TYPE
    SYNTAX       DateAndTime
    MAX-ACCESS   read-only
    STATUS       current
    DESCRIPTION  "The date and time stamp of the minimum optical power transmitted
                  value."
    ::= { briCrntPMEntry 33 }


briCrntPMOPTMinValidity OBJECT-TYPE
    SYNTAX       PMValidity
    MAX-ACCESS   read-only
    STATUS       current
    DESCRIPTION  "Indicates the validity of the provided minimum optical power
                  transmitted value."
    ::= { briCrntPMEntry 34 }

briCrntPMOPTMinInitialize OBJECT-TYPE
    SYNTAX       InitializeCmd
    MAX-ACCESS   read-write
    STATUS       current
    DESCRIPTION  "Used to initialize the value of the briCrntPMOPTMinValue
                  object to 0."
    ::= { briCrntPMEntry 35 }

briCrntPMOPTMaxValue OBJECT-TYPE
    SYNTAX       FixedX10
    UNITS        "dBm/10"
    MAX-ACCESS   read-only
    STATUS       current
    DESCRIPTION  "The maximum optical power transmitted at the output of the
                  transceiver."
    ::= { briCrntPMEntry 36 }


briCrntPMOPTMaxTimeStamp OBJECT-TYPE
    SYNTAX       DateAndTime
    MAX-ACCESS   read-only
    STATUS       current
    DESCRIPTION  "The date and time stamp of the maximum optical power transmitted
                  value."
    ::= { briCrntPMEntry 37 }


briCrntPMOPTMaxValidity OBJECT-TYPE
    SYNTAX       PMValidity
    MAX-ACCESS   read-only
    STATUS       current
    DESCRIPTION  "Indicates the validity of the provided maximum optical power
                  transmitted value."
    ::= { briCrntPMEntry 38 }

briCrntPMOPTMaxInitialize OBJECT-TYPE
    SYNTAX       InitializeCmd
    MAX-ACCESS   read-write
    STATUS       current
    DESCRIPTION  "Used to initialize the value of the briCrntPMOPTMaxValue
                  object to 0."
    ::= { briCrntPMEntry 39 }

briCrntPMOPTAvgValue OBJECT-TYPE
    SYNTAX       FixedX10
    UNITS        "dBm/10"
    MAX-ACCESS   read-only
    STATUS       current
    DESCRIPTION  "The average optical power transmitted at the output of the
                  transceiver."
    ::= { briCrntPMEntry 40 }


briCrntPMOPTAvgTimeStamp OBJECT-TYPE
    SYNTAX       DateAndTime
    MAX-ACCESS   read-only
    STATUS       current
    DESCRIPTION  "The date and time stamp of the average optical power transmitted
                  value."
    ::= { briCrntPMEntry 41 }

briCrntPMOPTAvgValidity OBJECT-TYPE
    SYNTAX       PMValidity
    MAX-ACCESS   read-only
    STATUS       current
    DESCRIPTION  "Indicates the validity of the provided average optical power
                  transmitted value."
    ::= { briCrntPMEntry 42 }

briCrntPMOPTAvgInitialize OBJECT-TYPE
    SYNTAX       InitializeCmd
    MAX-ACCESS   read-write
    STATUS       current
    DESCRIPTION  "Used to initialize the value of the briCrntPMOPTAvgValue
                  object to 0."
    ::= { briCrntPMEntry 43 }


-----------------------------------------------------------------------
-- Objects used to retrieve historical Bit Rate Independent (BRI) port
-- Performance Monitoring statistics
-----------------------------------------------------------------------


briHistPMTable OBJECT-TYPE
    SYNTAX       SEQUENCE OF BriHistPMEntry
    MAX-ACCESS   not-accessible
    STATUS       current
    DESCRIPTION  "A table of historical performance monitoring statistics
                  collected for the Bit Rate Independent (BRI) facilities 
                  on the NE."
    ::= { performance 39 }


briHistPMEntry OBJECT-TYPE
    SYNTAX       BriHistPMEntry
    MAX-ACCESS   not-accessible
    STATUS       current
    DESCRIPTION  "The row entry object of the BRI historical
                  performance monitoring table. Each row of this table contains
                  a full set of PM statistics and related data for a historical
                  measurement interval for a given BRI facility."
    INDEX        { briHistPMShelfIdx,
                   briHistPMSlotIdx,
                   briHistPMPortIdx,
                   briHistPMIntervalTypeIdx,
                   briHistPMIntervalIdx }
    ::= { briHistPMTable 1 }


BriHistPMEntry ::= SEQUENCE { briHistPMShelfIdx                  INTEGER,
                              briHistPMSlotIdx                   INTEGER,
                              briHistPMPortIdx                   INTEGER,
                              briHistPMIntervalTypeIdx           PMIntervalType,
                              briHistPMIntervalIdx               INTEGER,
                              briHistPMOPRValue                  FixedX10,
                              briHistPMOPRTimeStamp              DateAndTime,
                              briHistPMOPRValidity               PMValidity,
                              briHistPMOPTValue                  FixedX10,
                              briHistPMOPTTimeStamp              DateAndTime,
                              briHistPMOPTValidity               PMValidity,
                              briHistPMTempValue                 INTEGER,
                              briHistPMTempTimeStamp             DateAndTime,
                              briHistPMTempValidity              PMValidity,
                              briHistPMSupplyVoltageValue        FixedX10,
                              briHistPMSupplyVoltageTimeStamp    DateAndTime,
                              briHistPMSupplyVoltageValidity     PMValidity,
                              briHistPMLBCValue                  INTEGER,
                              briHistPMLBCTimeStamp              DateAndTime,
                              briHistPMLBCValidity               PMValidity,
                              briHistPMOPRMinValue               FixedX10,
                              briHistPMOPRMinTimeStamp           DateAndTime,
                              briHistPMOPRMinValidity            PMValidity,
                              briHistPMOPRMinInitialize          InitializeCmd,
                              briHistPMOPRMaxValue               FixedX10,
                              briHistPMOPRMaxTimeStamp           DateAndTime,
                              briHistPMOPRMaxValidity            PMValidity,
                              briHistPMOPRMaxInitialize          InitializeCmd,
                              briHistPMOPRAvgValue               FixedX10,
                              briHistPMOPRAvgTimeStamp           DateAndTime,
                              briHistPMOPRAvgValidity            PMValidity,
                              briHistPMOPRAvgInitialize          InitializeCmd,
                              briHistPMOPTMinValue               FixedX10,
                              briHistPMOPTMinTimeStamp           DateAndTime,
                              briHistPMOPTMinValidity            PMValidity,
                              briHistPMOPTMinInitialize          InitializeCmd,
                              briHistPMOPTMaxValue               FixedX10,
                              briHistPMOPTMaxTimeStamp           DateAndTime,
                              briHistPMOPTMaxValidity            PMValidity,
                              briHistPMOPTMaxInitialize          InitializeCmd,
                              briHistPMOPTAvgValue               FixedX10,
                              briHistPMOPTAvgTimeStamp           DateAndTime,
                              briHistPMOPTAvgValidity            PMValidity,
                              briHistPMOPTAvgInitialize          InitializeCmd }


briHistPMShelfIdx OBJECT-TYPE
    SYNTAX       INTEGER (1|11|21|31)
    MAX-ACCESS   not-accessible
    STATUS       current
    DESCRIPTION  "The number of the shelf on which the BRI facility targeted for
                  PMs is provisioned."
    ::= { briHistPMEntry 1 }


briHistPMSlotIdx OBJECT-TYPE
    SYNTAX       INTEGER (1|3|5|7|9|11|13|15|17|19)
    MAX-ACCESS   not-accessible
    STATUS       current
    DESCRIPTION  "The number of the slot within which the BRI facility targeted
                  for PMs is provisioned."
    ::= { briHistPMEntry 2 }


briHistPMPortIdx OBJECT-TYPE
    SYNTAX       INTEGER (3..12)
    MAX-ACCESS   not-accessible
    STATUS       current
    DESCRIPTION  "The number of the port on the circuit pack on which the BRI
                  facility targeted for PMs is provisioned."
    ::= { briHistPMEntry 3 }


briHistPMIntervalTypeIdx OBJECT-TYPE
    SYNTAX       PMIntervalType
    MAX-ACCESS   not-accessible
    STATUS       current
    DESCRIPTION  "The type of PM bin according to interval length."
    ::= { briHistPMEntry 4 }


briHistPMIntervalIdx OBJECT-TYPE
    SYNTAX       INTEGER (1..96)
    MAX-ACCESS   not-accessible
    STATUS       current
    DESCRIPTION  "The specific PM bin number. The range is 1 to 96 for the
                  15-minute historical bins. For the 1-day historical bin, the
                  value is 1."
    ::= { briHistPMEntry 5 }


briHistPMOPRValue OBJECT-TYPE
    SYNTAX       FixedX10
    UNITS        "dBm/10"
    MAX-ACCESS   read-only
    STATUS       current
    DESCRIPTION  "The optical power received on the input of the BRI facility
                  port."
    ::= { briHistPMEntry 6 }


briHistPMOPRTimeStamp OBJECT-TYPE
    SYNTAX       DateAndTime
    MAX-ACCESS   read-only
    STATUS       current
    DESCRIPTION  "The date and time stamp of the optical power received value."
    ::= { briHistPMEntry 7 }


briHistPMOPRValidity OBJECT-TYPE
    SYNTAX       PMValidity
    MAX-ACCESS   read-only
    STATUS       current
    DESCRIPTION  "Indicates the validity of the provided optical power received
                  value."
    ::= { briHistPMEntry 8 }


briHistPMOPTValue OBJECT-TYPE
    SYNTAX       FixedX10
    UNITS        "dBm/10"
    MAX-ACCESS   read-only
    STATUS       current
    DESCRIPTION  "The optical power transmitted at the output of the BRI facility
                  port."
    ::= { briHistPMEntry 9 }


briHistPMOPTTimeStamp OBJECT-TYPE
    SYNTAX       DateAndTime
    MAX-ACCESS   read-only
    STATUS       current
    DESCRIPTION  "The date and time stamp of the optical power transmitted
                  value."
    ::= { briHistPMEntry 10 }


briHistPMOPTValidity OBJECT-TYPE
    SYNTAX       PMValidity
    MAX-ACCESS   read-only
    STATUS       current
    DESCRIPTION  "Indicates the validity of the provided optical power
                  transmitted value."
    ::= { briHistPMEntry 11 }


briHistPMTempValue OBJECT-TYPE
    SYNTAX       INTEGER (-32768..32767)
    UNITS        "degrees Celsius"
    MAX-ACCESS   read-only
    STATUS       current
    DESCRIPTION  "The temperature measured on the BRI facility port."
    ::= { briHistPMEntry 12 }


briHistPMTempTimeStamp OBJECT-TYPE
    SYNTAX       DateAndTime
    MAX-ACCESS   read-only
    STATUS       current
    DESCRIPTION  "The date and time stamp of the temperature value."
    ::= { briHistPMEntry 13 }


briHistPMTempValidity OBJECT-TYPE
    SYNTAX       PMValidity
    MAX-ACCESS   read-only
    STATUS       current
    DESCRIPTION  "Indicates the validity of the provided temperature value."
    ::= { briHistPMEntry 14 }


briHistPMSupplyVoltageValue OBJECT-TYPE
    SYNTAX       FixedX10
    UNITS        "mVolts/10"
    MAX-ACCESS   read-only
    STATUS       current
    DESCRIPTION  "The supply voltage measured on the BRI facility port."
    ::= { briHistPMEntry 15 }


briHistPMSupplyVoltageTimeStamp OBJECT-TYPE
    SYNTAX       DateAndTime
    MAX-ACCESS   read-only
    STATUS       current
    DESCRIPTION  "The date and time stamp of the supply voltage value."
    ::= { briHistPMEntry 16 }


briHistPMSupplyVoltageValidity OBJECT-TYPE
    SYNTAX       PMValidity
    MAX-ACCESS   read-only
    STATUS       current
    DESCRIPTION  "Indicates the validity of the provided supply voltage value."
    ::= { briHistPMEntry 17 }


briHistPMLBCValue OBJECT-TYPE
    SYNTAX       INTEGER (-32768..32767)
    UNITS        "mAmp"
    MAX-ACCESS   read-only
    STATUS       current
    DESCRIPTION  "The laser bias current measured on the BRI facility port."
    ::= { briHistPMEntry 18 }


briHistPMLBCTimeStamp OBJECT-TYPE
    SYNTAX       DateAndTime
    MAX-ACCESS   read-only
    STATUS       current
    DESCRIPTION  "The date and time stamp of the laser bias current value."
    ::= { briHistPMEntry 19 }


briHistPMLBCValidity OBJECT-TYPE
    SYNTAX       PMValidity
    MAX-ACCESS   read-only
    STATUS       current
    DESCRIPTION  "Indicates the validity of the provided laser bias current
                  value."
    ::= { briHistPMEntry 20 }

briHistPMOPRMinValue OBJECT-TYPE
    SYNTAX       FixedX10
    UNITS        "dBm/10"
    MAX-ACCESS   read-only
    STATUS       current
    DESCRIPTION  "The minimum optical power received on the input of the transceiver."
    ::= { briHistPMEntry 21 }


briHistPMOPRMinTimeStamp OBJECT-TYPE
    SYNTAX       DateAndTime
    MAX-ACCESS   read-only
    STATUS       current
    DESCRIPTION  "The date and time stamp of the minimum optical power received value."
    ::= { briHistPMEntry 22 }


briHistPMOPRMinValidity OBJECT-TYPE
    SYNTAX       PMValidity
    MAX-ACCESS   read-only
    STATUS       current
    DESCRIPTION  "Indicates the validity of the provided minimum optical power received
                  value."
    ::= { briHistPMEntry 23 }

briHistPMOPRMinInitialize OBJECT-TYPE
    SYNTAX       InitializeCmd
    MAX-ACCESS   read-write
    STATUS       current
    DESCRIPTION  "Used to initialize the value of the briHistPMOPRMinValue
                  object to 0."
    ::= { briHistPMEntry 24 }

briHistPMOPRMaxValue OBJECT-TYPE
    SYNTAX       FixedX10
    UNITS        "dBm/10"
    MAX-ACCESS   read-only
    STATUS       current
    DESCRIPTION  "The maximum optical power received on the input of the transceiver."
    ::= { briHistPMEntry 25 }


briHistPMOPRMaxTimeStamp OBJECT-TYPE
    SYNTAX       DateAndTime
    MAX-ACCESS   read-only
    STATUS       current
    DESCRIPTION  "The date and time stamp of the maximum optical power received value."
    ::= { briHistPMEntry 26 }


briHistPMOPRMaxValidity OBJECT-TYPE
    SYNTAX       PMValidity
    MAX-ACCESS   read-only
    STATUS       current
    DESCRIPTION  "Indicates the validity of the provided maximum optical power received
                  value."
    ::= { briHistPMEntry 27 }

briHistPMOPRMaxInitialize OBJECT-TYPE
    SYNTAX       InitializeCmd
    MAX-ACCESS   read-write
    STATUS       current
    DESCRIPTION  "Used to initialize the value of the briHistPMOPRMaxValue
                  object to 0."
    ::= { briHistPMEntry 28 }

briHistPMOPRAvgValue OBJECT-TYPE
    SYNTAX       FixedX10
    UNITS        "dBm/10"
    MAX-ACCESS   read-only
    STATUS       current
    DESCRIPTION  "The average optical power received on the input of the transceiver."
    ::= { briHistPMEntry 29 }


briHistPMOPRAvgTimeStamp OBJECT-TYPE
    SYNTAX       DateAndTime
    MAX-ACCESS   read-only
    STATUS       current
    DESCRIPTION  "The date and time stamp of the average optical power received value."
    ::= { briHistPMEntry 30 }


briHistPMOPRAvgValidity OBJECT-TYPE
    SYNTAX       PMValidity
    MAX-ACCESS   read-only
    STATUS       current
    DESCRIPTION  "Indicates the validity of the provided average optical power received
                  value."
    ::= { briHistPMEntry 31 }

briHistPMOPRAvgInitialize OBJECT-TYPE
    SYNTAX       InitializeCmd
    MAX-ACCESS   read-write
    STATUS       current
    DESCRIPTION  "Used to initialize the value of the briHistPMOPRAvgValue
                  object to 0."
    ::= { briHistPMEntry 32 }

briHistPMOPTMinValue OBJECT-TYPE
    SYNTAX       FixedX10
    UNITS        "dBm/10"
    MAX-ACCESS   read-only
    STATUS       current
    DESCRIPTION  "The minimum optical power transmitted at the output of the
                  transceiver."
    ::= { briHistPMEntry 33 }

briHistPMOPTMinTimeStamp OBJECT-TYPE
    SYNTAX       DateAndTime
    MAX-ACCESS   read-only
    STATUS       current
    DESCRIPTION  "The date and time stamp of the minimum optical power transmitted
                  value."
    ::= { briHistPMEntry 34 }


briHistPMOPTMinValidity OBJECT-TYPE
    SYNTAX       PMValidity
    MAX-ACCESS   read-only
    STATUS       current
    DESCRIPTION  "Indicates the validity of the provided minimum optical power
                  transmitted value."
    ::= { briHistPMEntry 35 }

briHistPMOPTMinInitialize OBJECT-TYPE
    SYNTAX       InitializeCmd
    MAX-ACCESS   read-write
    STATUS       current
    DESCRIPTION  "Used to initialize the value of the briHistPMOPTMinValue
                  object to 0."
    ::= { briHistPMEntry 36 }

briHistPMOPTMaxValue OBJECT-TYPE
    SYNTAX       FixedX10
    UNITS        "dBm/10"
    MAX-ACCESS   read-only
    STATUS       current
    DESCRIPTION  "The maximum optical power transmitted at the output of the
                  transceiver."
    ::= { briHistPMEntry 37 }


briHistPMOPTMaxTimeStamp OBJECT-TYPE
    SYNTAX       DateAndTime
    MAX-ACCESS   read-only
    STATUS       current
    DESCRIPTION  "The date and time stamp of the maximum optical power transmitted
                  value."
    ::= { briHistPMEntry 38 }


briHistPMOPTMaxValidity OBJECT-TYPE
    SYNTAX       PMValidity
    MAX-ACCESS   read-only
    STATUS       current
    DESCRIPTION  "Indicates the validity of the provided maximum optical power
                  transmitted value."
    ::= { briHistPMEntry 39 }

briHistPMOPTMaxInitialize OBJECT-TYPE
    SYNTAX       InitializeCmd
    MAX-ACCESS   read-write
    STATUS       current
    DESCRIPTION  "Used to initialize the value of the briHistPMOPTMaxValue
                  object to 0."
    ::= { briHistPMEntry 40 }

briHistPMOPTAvgValue OBJECT-TYPE
    SYNTAX       FixedX10
    UNITS        "dBm/10"
    MAX-ACCESS   read-only
    STATUS       current
    DESCRIPTION  "The average optical power transmitted at the output of the
                  transceiver."
    ::= { briHistPMEntry 41 }


briHistPMOPTAvgTimeStamp OBJECT-TYPE
    SYNTAX       DateAndTime
    MAX-ACCESS   read-only
    STATUS       current
    DESCRIPTION  "The date and time stamp of the average optical power transmitted
                  value."
    ::= { briHistPMEntry 42 }

briHistPMOPTAvgValidity OBJECT-TYPE
    SYNTAX       PMValidity
    MAX-ACCESS   read-only
    STATUS       current
    DESCRIPTION  "Indicates the validity of the provided average optical power
                  transmitted value."
    ::= { briHistPMEntry 43 }

briHistPMOPTAvgInitialize OBJECT-TYPE
    SYNTAX       InitializeCmd
    MAX-ACCESS   read-write
    STATUS       current
    DESCRIPTION  "Used to initialize the value of the briHistPMOPTAvgValue
                  object to 0."
    ::= { briHistPMEntry 44 }


-----------------------------------------------------------------------
-- Objects used to retrieve current provisioned circuit pack
-- Performance Monitoring statistics
-----------------------------------------------------------------------


cpCrntPMTable OBJECT-TYPE
    SYNTAX       SEQUENCE OF CpCrntPMEntry
    MAX-ACCESS   not-accessible
    STATUS       current
    DESCRIPTION  "A table of current performance monitoring statistics collected
                  for the circuit packs on the NE."
    ::= { performance 49 }


cpCrntPMEntry OBJECT-TYPE
    SYNTAX       CpCrntPMEntry
    MAX-ACCESS   not-accessible
    STATUS       current
    DESCRIPTION  "The row entry object of the equipment current
                  performance monitoring table. Each row of this table contains
                  a full set of PM statistics and related data for a current
                  measurement interval for a given circuit pack."
    INDEX        { cpCrntPMCpTypeIdx,
                   cpCrntPMShelfIdx,
                   cpCrntPMSlotIdx,
                   cpCrntPMIntervalTypeIdx }
    ::= { cpCrntPMTable 1 }


CpCrntPMEntry ::= SEQUENCE { cpCrntPMCpTypeIdx               CpType,
                             cpCrntPMShelfIdx                INTEGER,
                             cpCrntPMSlotIdx                 INTEGER,
                             cpCrntPMIntervalTypeIdx         PMIntervalType,
                             cpCrntPMTempValue               INTEGER,
                             cpCrntPMTempTimeStamp           DateAndTime,
                             cpCrntPMTempValidity            PMValidity }


cpCrntPMCpTypeIdx OBJECT-TYPE
    SYNTAX       CpType
    MAX-ACCESS   not-accessible
    STATUS       current
    DESCRIPTION  "The type of the circuit pack targeted for PM retrieval."
    ::= { cpCrntPMEntry 1 }


cpCrntPMShelfIdx OBJECT-TYPE
    SYNTAX       INTEGER (1|11|21|31)
    MAX-ACCESS   not-accessible
    STATUS       current
    DESCRIPTION  "The number of the shelf on which the circuit pack targeted for
                  PMs is provisioned."
    ::= { cpCrntPMEntry 2 }

cpCrntPMSlotIdx OBJECT-TYPE
    SYNTAX       INTEGER (1..20)
    MAX-ACCESS   not-accessible
    STATUS       current
    DESCRIPTION  "The number of the slot within which the circuit pack
                  targeted for PMs is provisioned."
    ::= { cpCrntPMEntry 3 }


cpCrntPMIntervalTypeIdx OBJECT-TYPE
    SYNTAX       PMIntervalType
    MAX-ACCESS   not-accessible
    STATUS       current
    DESCRIPTION  "The type of PM bin according to interval length."
    ::= { cpCrntPMEntry 4 }


cpCrntPMTempValue OBJECT-TYPE
    SYNTAX       INTEGER (-32768..32767)
    UNITS        "degrees Celsius"
    MAX-ACCESS   read-only
    STATUS       current
    DESCRIPTION  "The circuit pack temperature."
    ::= { cpCrntPMEntry 5 }


cpCrntPMTempTimeStamp OBJECT-TYPE
    SYNTAX       DateAndTime
    MAX-ACCESS   read-only
    STATUS       current
    DESCRIPTION  "The date and time stamp of the temperature value."
    ::= { cpCrntPMEntry 6 }


cpCrntPMTempValidity OBJECT-TYPE
    SYNTAX       PMValidity
    MAX-ACCESS   read-only
    STATUS       current
    DESCRIPTION  "Indicates the validity of the provided temperature
                  value."
    ::= { cpCrntPMEntry 7 }


-----------------------------------------------------------------------
-- Objects used to retrieve historical provisioned circuit pack
-- Performance Monitoring statistics
-----------------------------------------------------------------------


cpHistPMTable OBJECT-TYPE
    SYNTAX       SEQUENCE OF CpHistPMEntry
    MAX-ACCESS   not-accessible
    STATUS       current
    DESCRIPTION  "A table of historical performance monitoring statistics
                  collected for the circuit packs on the NE."
    ::= { performance 50 }


cpHistPMEntry OBJECT-TYPE
    SYNTAX       CpHistPMEntry
    MAX-ACCESS   not-accessible
    STATUS       current
    DESCRIPTION  "The row entry object of the circuit pack historical
                  performance monitoring table. Each row of this table contains
                  a full set of PM statistics and related data for a historical
                  measurement interval for a given circuit pack."
    INDEX        { cpHistPMCpTypeIdx,
                   cpHistPMShelfIdx,
                   cpHistPMSlotIdx,
                   cpHistPMIntervalTypeIdx,
                   cpHistPMIntervalIdx }
    ::= { cpHistPMTable 1 }


CpHistPMEntry ::= SEQUENCE { cpHistPMCpTypeIdx             CpType,
                             cpHistPMShelfIdx              INTEGER,
                             cpHistPMSlotIdx               INTEGER,
                             cpHistPMIntervalTypeIdx       PMIntervalType,
                             cpHistPMIntervalIdx           INTEGER,
                             cpHistPMTempValue             INTEGER,
                             cpHistPMTempTimeStamp         DateAndTime,
                             cpHistPMTempValidity          PMValidity }


cpHistPMCpTypeIdx OBJECT-TYPE
    SYNTAX       CpType
    MAX-ACCESS   not-accessible
    STATUS       current
    DESCRIPTION  "The type of the circuit pack targeted for PM retrieval."
    ::= { cpHistPMEntry 1 }


cpHistPMShelfIdx OBJECT-TYPE
    SYNTAX       INTEGER (1|11|21|31)
    MAX-ACCESS   not-accessible
    STATUS       current
    DESCRIPTION  "The number of the shelf on which the circuit pack targeted for
                  PMs is provisioned."
    ::= { cpHistPMEntry 2 }


cpHistPMSlotIdx OBJECT-TYPE
    SYNTAX       INTEGER (1..20)
    MAX-ACCESS   not-accessible
    STATUS       current
    DESCRIPTION  "The number of the slot within which the circuit pack
                  targeted for PMs is provisioned."
    ::= { cpHistPMEntry 3 }


cpHistPMIntervalTypeIdx OBJECT-TYPE
    SYNTAX       PMIntervalType
    MAX-ACCESS   not-accessible
    STATUS       current
    DESCRIPTION  "The type of PM bin according to interval length."
    ::= { cpHistPMEntry 4 }


cpHistPMIntervalIdx OBJECT-TYPE
    SYNTAX       INTEGER (1..96)
    MAX-ACCESS   not-accessible
    STATUS       current
    DESCRIPTION  "The specific PM bin number. The range is 1..96 for 15-minute
                  bins, and for 1-day historical bins, the value is 1."
    ::= { cpHistPMEntry 5 }


cpHistPMTempValue OBJECT-TYPE
    SYNTAX       INTEGER (-32768..32767)
    UNITS        "degrees Celsius"
    MAX-ACCESS   read-only
    STATUS       current
    DESCRIPTION  "The circuit pack temperature."
    ::= { cpHistPMEntry 6 }


cpHistPMTempTimeStamp OBJECT-TYPE
    SYNTAX       DateAndTime
    MAX-ACCESS   read-only
    STATUS       current
    DESCRIPTION  "The date and time stamp of the temperature value."
    ::= { cpHistPMEntry 7 }


cpHistPMTempValidity OBJECT-TYPE
    SYNTAX       PMValidity
    MAX-ACCESS   read-only
    STATUS       current
    DESCRIPTION  "Indicates the validity of the provided temperature
                  value."
    ::= { cpHistPMEntry 8 }


-----------------------------------------------------------------------
-- Objects related to GCC0 
------------------------------------------------------------------------

gcc0ConfigTable OBJECT-TYPE
  SYNTAX        SEQUENCE OF Gcc0ConfigEntry
  MAX-ACCESS    not-accessible
  STATUS        current
  DESCRIPTION  "A table of GCC0 configuration information.
                This table contains one row for every provisioned GCC0."
  ::= { dataComms 4 }


gcc0ConfigEntry OBJECT-TYPE
  SYNTAX      Gcc0ConfigEntry
  MAX-ACCESS  not-accessible
  STATUS      current
  DESCRIPTION "A conceptual row that contains GCC0 configuration
               information of an interface.  Each instance must
               correspond to an instance of an OTN Port
               capable of supporting GCC.
               Instances of this conceptual row persist across
               agent restarts."
  INDEX  { gcc0ConfigCpTypeIdx,
           gcc0ConfigShelfIdx, 
           gcc0ConfigSlotIdx, 
           gcc0ConfigPortIdx }
  ::= { gcc0ConfigTable 1 }

Gcc0ConfigEntry ::= SEQUENCE {  gcc0ConfigCpTypeIdx          CpType,
                                gcc0ConfigShelfIdx           INTEGER,
                                gcc0ConfigSlotIdx            INTEGER,
                                gcc0ConfigPortIdx            INTEGER,
                                gcc0ConfigMode               INTEGER,
                                gcc0ConfigAdminStatus        AdminStatus,
                                gcc0ConfigOperStatus         OperStatus,
                                gcc0ConfigOperStatQlfr       OperStatQlfr,
                                gcc0ConfigRowStatus          RowStatus }

gcc0ConfigCpTypeIdx OBJECT-TYPE
    SYNTAX       CpType
    MAX-ACCESS   not-accessible
    STATUS       current
    DESCRIPTION  "The specific type of circuit pack provisioned."
    ::= { gcc0ConfigEntry 1 }

gcc0ConfigShelfIdx OBJECT-TYPE
   SYNTAX       INTEGER (1|11|21|31)
    MAX-ACCESS   not-accessible
    STATUS       current
    DESCRIPTION  "The number of the shelf on which the gcc0 is provisioned."
    ::= { gcc0ConfigEntry 2 }

gcc0ConfigSlotIdx OBJECT-TYPE
    SYNTAX       INTEGER (1..20)
    MAX-ACCESS   not-accessible
    STATUS       current
    DESCRIPTION  "The number of the slot in which the gcc0 is provisioned."
    ::= { gcc0ConfigEntry 3 }

gcc0ConfigPortIdx OBJECT-TYPE
    SYNTAX       INTEGER (1..4)
   MAX-ACCESS   not-accessible
    STATUS       current
    DESCRIPTION  "The number of the port on the circuit pack on which the
                  gcc0 provisioned."
    ::= { gcc0ConfigEntry 4 }

gcc0ConfigMode OBJECT-TYPE
    SYNTAX       INTEGER { fullRate  (1),
                           lowRate   (2) }
    MAX-ACCESS   read-create
    STATUS       current
    DESCRIPTION  "The desired mode to which the gcc0 is to be provisioned."
    DEFVAL       { fullRate }
    ::= { gcc0ConfigEntry 5 }

gcc0ConfigAdminStatus OBJECT-TYPE
    SYNTAX       AdminStatus
    MAX-ACCESS   read-create
    STATUS       current
    DESCRIPTION  "The administrative status of the gcc."
    DEFVAL       { enabled }
    ::= { gcc0ConfigEntry 6 }


gcc0ConfigOperStatus OBJECT-TYPE
    SYNTAX       OperStatus
    MAX-ACCESS   read-only
    STATUS       current
    DESCRIPTION  "The reported operational status of the gcc."
    ::= { gcc0ConfigEntry 7 }


gcc0ConfigOperStatQlfr OBJECT-TYPE
    SYNTAX       OperStatQlfr
    MAX-ACCESS   read-only
    STATUS       current
    DESCRIPTION  "A textual list of qualifiers of the reported operational
                  status of the gcc."
    ::= { gcc0ConfigEntry 8 }


gcc0ConfigRowStatus OBJECT-TYPE
  SYNTAX  RowStatus
  MAX-ACCESS  read-create
  STATUS  current
  DESCRIPTION "This columnar object is used for creating and deleting a
               conceptual row of the gcc0 config table."
  ::= { gcc0ConfigEntry  9 }




-----------------------------------------------------------------------
-- IPExtInterface_Table
-----------------------------------------------------------------------

ipExtInterfaceTable OBJECT-TYPE
    SYNTAX       SEQUENCE OF IPExtInterfaceTableEntry
    MAX-ACCESS   not-accessible
    STATUS       current
    DESCRIPTION  ""
    ::= { dataComms 5 }


ipExtInterfaceTableEntry OBJECT-TYPE
    SYNTAX       IPExtInterfaceTableEntry
    MAX-ACCESS   not-accessible
    STATUS       current
    DESCRIPTION  ""
    INDEX        {
                 pvxL2IntfSwitchIdx,
                 pvxL2IntfShelfIdx,
                 pvxL2IntfSlotIdx,
                 pvxL2IntfPortTypeIdx,
                 pvxL2IntfPortIdx,
                 pvxL2IntfSubPortNumber
                 }
    ::= { ipExtInterfaceTable 1 }


IPExtInterfaceTableEntry ::= SEQUENCE {
        pvxL2IntfSubPortNumber      Integer32,
        ipExtIntfPrimaryState       OperStatus,
        ipExtIntfSecondaryState     OperStatQlfr,
        ipExtIntfCmdPrimaryState    OperStatus,
        ipExtIntfNumberedStatus     TruthValue,
        ipExtIntfAddressType        InetAddressType,
        ipExtIntfAddress            InetAddress,
        ipExtIntfSubnetMask         InetAddress,
        ipExtIntfProxyARPStatus     TruthValue,
        ipExtIntfDescription        DisplayString,
        ipExtIntfMACAddr            MacAddress,
        ipExtIntfOperStatus         OperStatus,
        ipExtIntfType               INTEGER,
        ipExtIntfBroadcastAddress   InetAddress,
        ipExtIntfSpeed              Gauge32,
        ipExtIntfMode               DuplexModeType,
        ipExtIntfMTUSize            Integer32,
        ipExtIntfLastChange         Integer32,
        ipExtIntfGateway            InetAddress,
        ipExtIntfRowStatus          RowStatus }


pvxL2IntfSubPortNumber OBJECT-TYPE
    SYNTAX       Integer32
    MAX-ACCESS   not-accessible
    STATUS       current
    DESCRIPTION  "A number indentifying a entity smaller than and contained
                  in a port. At this time, this value is unused and must be
                  zero."
    ::= { ipExtInterfaceTableEntry 1 }


ipExtIntfPrimaryState OBJECT-TYPE
    SYNTAX       OperStatus
    MAX-ACCESS   read-only
    STATUS       current
    DESCRIPTION  "The reported operational status of the IP Interface."
    ::= { ipExtInterfaceTableEntry 2 }


ipExtIntfSecondaryState OBJECT-TYPE
    SYNTAX       OperStatQlfr
    MAX-ACCESS   read-only
    STATUS       current
    DESCRIPTION  "A textual list of qualifiers for the reported operational
                  status of the IP Interface"
    ::= { ipExtInterfaceTableEntry 3 }


ipExtIntfCmdPrimaryState OBJECT-TYPE
    SYNTAX       OperStatus
    MAX-ACCESS   read-only
    STATUS       current
    DESCRIPTION  ""
    ::= { ipExtInterfaceTableEntry 4 }


ipExtIntfNumberedStatus OBJECT-TYPE
    SYNTAX       TruthValue
    MAX-ACCESS   read-create
    STATUS       current
    DESCRIPTION  "Set to true if this is a numbered interface and false
                  if it is unnumbered."
    ::= { ipExtInterfaceTableEntry 5 }


ipExtIntfAddressType OBJECT-TYPE
    SYNTAX       InetAddressType
    MAX-ACCESS   read-only
    STATUS       current
    DESCRIPTION  "The type of addresses (v4/v6) used in this row of
                  this MIB. Currently only ipv4 is allowed in this table."
    ::= { ipExtInterfaceTableEntry 6 }


ipExtIntfAddress OBJECT-TYPE
    SYNTAX       InetAddress
    MAX-ACCESS   read-only
    STATUS       current
    DESCRIPTION  "The IP Address associated with the interface."
    ::= { ipExtInterfaceTableEntry 7 }


ipExtIntfSubnetMask OBJECT-TYPE
    SYNTAX       InetAddress
    MAX-ACCESS   read-only
    STATUS       current
    DESCRIPTION  "The sub-net mask associated with the interface."
    ::= { ipExtInterfaceTableEntry 8 }


ipExtIntfProxyARPStatus OBJECT-TYPE
    SYNTAX       TruthValue
    MAX-ACCESS   read-only
    STATUS       current
    DESCRIPTION  "Not currently implemented."
    ::= { ipExtInterfaceTableEntry 9 }


ipExtIntfDescription OBJECT-TYPE
    SYNTAX       DisplayString (SIZE (0..255))
    MAX-ACCESS   read-only
    STATUS       current
    DESCRIPTION  "A string describing the interface."
    ::= { ipExtInterfaceTableEntry 10 }


ipExtIntfMACAddr OBJECT-TYPE
    SYNTAX       MacAddress
    MAX-ACCESS   read-only
    STATUS       current
    DESCRIPTION  "The MAC address associated with the interface, if
                  applicable. All zeros for a non-MAC interface."
    ::= { ipExtInterfaceTableEntry 11 }


ipExtIntfOperStatus OBJECT-TYPE
    SYNTAX       OperStatus
    MAX-ACCESS   read-only
    STATUS       current
    DESCRIPTION  ""
    ::= { ipExtInterfaceTableEntry 12 }


ipExtIntfType OBJECT-TYPE
    SYNTAX       INTEGER { optical    (1),
                           electrical (2),
                           logical    (3) }
    MAX-ACCESS   read-only
    STATUS       current
    DESCRIPTION  "A value describing the type of interface."
    ::= { ipExtInterfaceTableEntry 13 }


ipExtIntfBroadcastAddress OBJECT-TYPE
    SYNTAX       InetAddress
    MAX-ACCESS   read-only
    STATUS       current
    DESCRIPTION  "The broadcast address associated with the interface."
    ::= { ipExtInterfaceTableEntry 14 }


ipExtIntfSpeed OBJECT-TYPE
    SYNTAX       Gauge32
    MAX-ACCESS   read-only
    STATUS       current
    DESCRIPTION  ""
    ::= { ipExtInterfaceTableEntry 15 }


ipExtIntfMode OBJECT-TYPE
    SYNTAX       DuplexModeType
    MAX-ACCESS   read-only
    STATUS       current
    DESCRIPTION  "Is the interface full or half-duplex?"
    ::= { ipExtInterfaceTableEntry 16 }


ipExtIntfMTUSize OBJECT-TYPE
    SYNTAX       Integer32
    MAX-ACCESS   read-only
    STATUS       current
    DESCRIPTION  "The Maximum Transmission Unit for the interface."
    ::= { ipExtInterfaceTableEntry 17 }


ipExtIntfLastChange OBJECT-TYPE
    SYNTAX       Integer32
    MAX-ACCESS   read-only
    STATUS       current
    DESCRIPTION  ""
    ::= { ipExtInterfaceTableEntry 18 }


ipExtIntfGateway OBJECT-TYPE
    SYNTAX       InetAddress
    MAX-ACCESS   read-only
    STATUS       current
    DESCRIPTION  "The gateway IP address associated with the interface."
    ::= { ipExtInterfaceTableEntry 19 }

ipExtIntfRowStatus OBJECT-TYPE
    SYNTAX       RowStatus
    MAX-ACCESS   read-only
    STATUS       current
    DESCRIPTION  "This columnar object is used for creating and deleting a
                  conceptual row of the ipExtIntf table."
  ::= { ipExtInterfaceTableEntry 100 }



-----------------------------------------------------------------------
-- Scalar objects used to contain data transfered in
-- Trap OBJECTS
-----------------------------------------------------------------------


notifObjects  OBJECT IDENTIFIER ::= { conditions 1 }

condDateAndTime OBJECT-TYPE
    SYNTAX       DateAndTime
    MAX-ACCESS   accessible-for-notify
    STATUS       current
    DESCRIPTION  "This object is used in Trap messages to indicate the date and
                  time at which the condition or alarm reported in the Trap
                  message occurred."
    ::= { notifObjects 1 }


condReportType OBJECT-TYPE
    SYNTAX       CondReportType
    MAX-ACCESS   accessible-for-notify   
    STATUS       current
    DESCRIPTION  "Indicates if this is a condition (non-alarmed) or an alarm.
                  This object is used solely for reporting the condition report
                  type in Trap messages."
    ::= { notifObjects 2 }


condSeverity OBJECT-TYPE
    SYNTAX       CondSeverity
    MAX-ACCESS   accessible-for-notify
    STATUS       current
    DESCRIPTION  "Indicates the severity of the condition or alarm. This object
                  is used solely for reporting the condition severity in Trap
                  messages."
    ::= { notifObjects 3 }


condServiceAffecting OBJECT-TYPE
    SYNTAX       CondServiceAffecting
    MAX-ACCESS   accessible-for-notify
    STATUS       current
    DESCRIPTION  "Indicates if the presence of this active condition or alarm
                  impacts the ability of the equipment to provide service as
                  expected. This object is used solely for reporting whether or
                  not a condition is service affecting in Trap messages."
    ::= { notifObjects 4 }


condDescription OBJECT-TYPE
    SYNTAX       DisplayString
    MAX-ACCESS   accessible-for-notify
    STATUS       current
    DESCRIPTION  "A textual decription of the condition or alarm. This object is
                  used solely for reporting the condition description in Trap
                  messages."
    ::= { notifObjects 5 }


condObjectType OBJECT-TYPE
    SYNTAX       NotifObjectType
    MAX-ACCESS   accessible-for-notify
    STATUS       current
    DESCRIPTION  "Identifies the type of managed object against which the
                  condition or alarm is raised."
    ::= { notifObjects 6 }


condCodeType OBJECT-TYPE
    SYNTAX       NotifCodeType
    MAX-ACCESS   accessible-for-notify
    STATUS       current
    DESCRIPTION  "This object value uniquely identifies the type of condition
                  or alarm that is raised."
    ::= { notifObjects 7 }



-----------------------------------------------------------------------
-- Information on standing conditions and alarms that are active on
-- the network element.
-----------------------------------------------------------------------


actCondTable OBJECT-TYPE
    SYNTAX       SEQUENCE OF ActCondEntry
    MAX-ACCESS   not-accessible
    STATUS       current
    DESCRIPTION  "This table lists all active conditions and alarms raised on
                  the system."
    ::= { conditions 2 }


actCondEntry OBJECT-TYPE
    SYNTAX       ActCondEntry
    MAX-ACCESS   not-accessible
    STATUS       current
    DESCRIPTION  "Contains identifying and descriptive attributes for a single
                  active condition or alarm raised on the network element."
    INDEX        { actCondNotifIdx,
                   actCondTableEntryIdx,
                   actCondInstanceIdx }
    ::= { actCondTable 1 }


ActCondEntry ::= SEQUENCE { actCondNotifIdx           OBJECT IDENTIFIER,
                            actCondTableEntryIdx      OBJECT IDENTIFIER,
                            actCondInstanceIdx        DisplayString,
                            actCondReportType         CondReportType,
                            actCondDateAndTime        DateAndTime,
                            actCondSeverity           CondSeverity,
                            actCondServiceAffecting   CondServiceAffecting,
                            actCondDescription        DisplayString,
                            actCondObjectType		  NotifObjectType,
                            actCondCodeType			  NotifCodeType }


actCondNotifIdx OBJECT-TYPE
    SYNTAX       OBJECT IDENTIFIER
    MAX-ACCESS   not-accessible
    STATUS       current
    DESCRIPTION  "Identifies the type of condition or alarm that is active by
                  pointing to the NOTIFICATION-TYPE object that corresponds to
                  the raising event of the condition or alarm."
    ::= { actCondEntry 1 }


actCondTableEntryIdx OBJECT-TYPE
    SYNTAX       OBJECT IDENTIFIER
    MAX-ACCESS   not-accessible
    STATUS       current
    DESCRIPTION  "Identifies the type of resource that is alarmed by pointing to
                  the corresponding table entry object."
    ::= { actCondEntry 2 }


actCondInstanceIdx OBJECT-TYPE
    SYNTAX       DisplayString (SIZE (1..32))
    MAX-ACCESS   not-accessible
    STATUS       current
    DESCRIPTION  "Identifies the specific instance of the idenitifed resource
                  type that is alarmed by providing instance data that applies
                  to an instance of the table entry object type identified by
                  actCondTableEntryIdx. The instance data portion of the OID is
                  mapped to an OCTET string."
    ::= { actCondEntry 3 }


actCondReportType OBJECT-TYPE
    SYNTAX       CondReportType
    MAX-ACCESS   read-only
    STATUS       current
    DESCRIPTION  "Indicates if the table entry is a condition (non-alarmed) or
                  an alarm."
    ::= { actCondEntry 4 }


actCondDateAndTime OBJECT-TYPE
    SYNTAX       DateAndTime
    MAX-ACCESS   read-only
    STATUS       current
    DESCRIPTION  "The date and time that the condition or alarm reported in the
                  trap message was raised."
    ::= { actCondEntry 5 }


actCondSeverity OBJECT-TYPE
    SYNTAX       CondSeverity
    MAX-ACCESS   read-only
    STATUS       current
    DESCRIPTION  "Indicates how severe the condition or alarm is."
    ::= { actCondEntry 6 }


actCondServiceAffecting OBJECT-TYPE
    SYNTAX       CondServiceAffecting
    MAX-ACCESS   read-only
    STATUS       current
    DESCRIPTION  "Indicates if the presence of this active condition or alarm
                  impacts the ability of the equipment to provide service as
                  expected."
    ::= { actCondEntry 7 }


actCondDescription OBJECT-TYPE
    SYNTAX       DisplayString
    MAX-ACCESS   read-only
    STATUS       current
    DESCRIPTION  "A textual decription of the condition or alarm."
    ::= { actCondEntry 8 }


actCondObjectType OBJECT-TYPE
    SYNTAX       NotifObjectType
    MAX-ACCESS   read-only
    STATUS       current
    DESCRIPTION  "Identifies the type of managed object against which the
                  condition or alarm is raised."
    ::= { actCondEntry 9 }


actCondCodeType OBJECT-TYPE
    SYNTAX       NotifCodeType
    MAX-ACCESS   read-only
    STATUS       current
    DESCRIPTION  "This object value uniquely identifies the type of condition
                  or alarm that is raised."
    ::= { actCondEntry 10 }


actCondSummary OBJECT-TYPE
    SYNTAX       INTEGER { noActiveConditions         (1),
                           nonAlarmedConditionsActive (2),
                           minorAlarmsActive          (3),
                           majorAlarmsActive          (4),
                           criticalAlarmsActive       (5) }
    MAX-ACCESS   read-only
    STATUS       current
    DESCRIPTION  "This object summarizes the active alarm/condition status of
                  the network element. The value of the object returned
                  indicates the following status data:
                  - noActiveConditions: there are no active alarms or conditions
                  on the network element
                  - nonAlarmedConditionsActive: there is one or more active
                  conditions on the network element, but none are of alarmable
                  severity
                  - minorAlarmsActive: there is one or more active conditions
                  and/or alarms on the network element, and the highest severity
                  level alarm is minor
                  - majorAlarmsActive: there is one or more active conditions
                  and/or alarms on the network element, and the highest severity
                  level alarm is major
                  - criticalAlarmsActive: there is one or more active conditions
                  and/or alarms on the network element, and the highest severity
                  level alarm is critical"
    ::= { conditions 3 }



-----------------------------------------------------------------------
-- Information on alarms that are active on
-- the network element.
-----------------------------------------------------------------------

actAlarmTable OBJECT-TYPE
    SYNTAX       SEQUENCE OF ActAlarmEntry
    MAX-ACCESS   not-accessible
    STATUS       current
    DESCRIPTION  "This table lists all active alarms raised on the system."
    ::= { conditions 4 }


actAlarmEntry OBJECT-TYPE
    SYNTAX       ActAlarmEntry
    MAX-ACCESS   not-accessible
    STATUS       current
    DESCRIPTION  "Contains identifying and descriptive attributes for a single
                  active alarm raised on the system."
    INDEX        { actAlarmNotifIdx,
                   actAlarmTableEntryIdx,
                   actAlarmInstanceIdx }
    ::= { actAlarmTable 1 }


ActAlarmEntry ::= SEQUENCE { actAlarmNotifIdx           OBJECT IDENTIFIER,
                             actAlarmTableEntryIdx      OBJECT IDENTIFIER,
                             actAlarmInstanceIdx        DisplayString,
                             actAlarmReportType         CondReportType,
                             actAlarmDateAndTime        DateAndTime,
                             actAlarmSeverity           CondSeverity,
                             actAlarmServiceAffecting   CondServiceAffecting,
                             actAlarmDescription        DisplayString,
                             actAlarmObjectType		    NotifObjectType,
                             actAlarmCodeType			NotifCodeType }


actAlarmNotifIdx OBJECT-TYPE
    SYNTAX       OBJECT IDENTIFIER
    MAX-ACCESS   not-accessible
    STATUS       current
    DESCRIPTION  "Identifies the type of alarm that is active by pointing to the
                  NOTIFICATION-TYPE object that corresponds to the raising event
                  of the condition or alarm."
    ::= { actAlarmEntry 1 }


actAlarmTableEntryIdx OBJECT-TYPE
    SYNTAX       OBJECT IDENTIFIER
    MAX-ACCESS   not-accessible
    STATUS       current
    DESCRIPTION  "Identifies the type of resource that is alarmed by pointing to
                  the corresponding table entry object."
    ::= { actAlarmEntry 2 }


actAlarmInstanceIdx OBJECT-TYPE
    SYNTAX       DisplayString (SIZE (1..32))
    MAX-ACCESS   not-accessible
    STATUS       current
    DESCRIPTION  "Identifies the specific instance of the idenitifed resource
                  type that is alarmed by providing instance data that applies
                  to an instance of the table entry object type identified by
                  actAlarmTableEntryIdx. The instance data portion of the OID is
                  mapped to an OCTET string."
    ::= { actAlarmEntry 3 }


actAlarmReportType OBJECT-TYPE
    SYNTAX       CondReportType
    MAX-ACCESS   read-only
    STATUS       current
    DESCRIPTION  "Indicates if the table entry is an alarm."
    ::= { actAlarmEntry 4 }


actAlarmDateAndTime OBJECT-TYPE
    SYNTAX       DateAndTime
    MAX-ACCESS   read-only
    STATUS       current
    DESCRIPTION  "The date and time that the alarm reported in the trap message
                  was raised."
    ::= { actAlarmEntry 5 }


actAlarmSeverity OBJECT-TYPE
    SYNTAX       CondSeverity
    MAX-ACCESS   read-only
    STATUS       current
    DESCRIPTION  "Indicates how severe the alarm is."
    ::= { actAlarmEntry 6 }


actAlarmServiceAffecting OBJECT-TYPE
    SYNTAX       CondServiceAffecting
    MAX-ACCESS   read-only
    STATUS       current
    DESCRIPTION  "Indicates if the presence of this active alarm impacts the
                  ability of the equipment to provide service as expected."
    ::= { actAlarmEntry 7 }


actAlarmDescription OBJECT-TYPE
    SYNTAX       DisplayString
    MAX-ACCESS   read-only
    STATUS       current
    DESCRIPTION  "A textual decription of the alarm."
    ::= { actAlarmEntry 8 }


actAlarmObjectType OBJECT-TYPE
    SYNTAX       NotifObjectType
    MAX-ACCESS   read-only
    STATUS       current
    DESCRIPTION  "Identifies the type of managed object against which the
                  alarm is raised."
    ::= { actAlarmEntry 9 }


actAlarmCodeType OBJECT-TYPE
    SYNTAX       NotifCodeType
    MAX-ACCESS   read-only
    STATUS       current
    DESCRIPTION  "This object value uniquely identifies the type of
                  alarm that is raised."
    ::= { actAlarmEntry 10 }



-----------------------------------------------------------------------
-- Objects related to managing the TL1 Users
-- configured on the system.
-----------------------------------------------------------------------


tl1UserTable OBJECT-TYPE
    SYNTAX       SEQUENCE OF Tl1UserEntry
    MAX-ACCESS   not-accessible
    STATUS       current
    DESCRIPTION  "This table contains one row for every provisioned user that
                  can operate the TL1 management interface on the NE. Each row
                  contains a list of attributes that pertain to a provisioned
                  TL1 user."
    ::= { administration 1 }


tl1UserEntry OBJECT-TYPE
    SYNTAX       Tl1UserEntry
    MAX-ACCESS   not-accessible
    STATUS       current
    DESCRIPTION  "The conceptual row object of the TL1 user table."
    INDEX        { tl1UserIdx }
    ::= { tl1UserTable 1 }


Tl1UserEntry ::= SEQUENCE { tl1UserIdx  DisplayString }


tl1UserIdx OBJECT-TYPE
    SYNTAX       DisplayString (SIZE (1..32))
    MAX-ACCESS   accessible-for-notify
    STATUS       current
    DESCRIPTION  "This is the unique user identifier, or UID, that is used for
                  TL1 access."
    ::= { tl1UserEntry 1 }


tl1IpLockoutAddr OBJECT-TYPE
    SYNTAX       DisplayString (SIZE (1..15))
    MAX-ACCESS   accessible-for-notify
    STATUS       current
    DESCRIPTION  "This is an IP address from which TL1 user login attempts have
                  been temporarily disabled due to an excessive number of failed
                  user login attempts."
    ::= { administration 2 }


-----------------------------------------------------------------------
-- Objects related to retrieval of system logs generated by the TL1
-- management interface.
-----------------------------------------------------------------------


tl1LogTable OBJECT-TYPE
    SYNTAX       SEQUENCE OF Tl1LogEntry
    MAX-ACCESS   not-accessible
    STATUS       current
    DESCRIPTION  "This table lists all the log entries generated by the TL1
                  interface on the BTI 7000 system."
    ::= { administration 3 }


tl1LogEntry OBJECT-TYPE
    SYNTAX       Tl1LogEntry
    MAX-ACCESS   not-accessible
    STATUS       current
    DESCRIPTION  "The conceptual row object of the TL1 log table."
    INDEX        { tl1LogIdx }
    ::= { tl1LogTable 1 }


Tl1LogEntry ::= SEQUENCE { tl1LogIdx                    Unsigned32,
                           tl1LogSysName                DisplayString,
                           tl1LogType                   INTEGER,
                           tl1LogTypeSpecificLogNum     Unsigned32,
                           tl1LogMsgCode                DisplayString,
                           tl1LogDateAndTime            DateAndTime,
                           tl1LogMessage                DisplayString }


tl1LogIdx OBJECT-TYPE
    SYNTAX       Unsigned32
    MAX-ACCESS   not-accessible
    STATUS       current
    DESCRIPTION  "The unique identifier for this log entry. It is the global Log
                  Id of the entry when viewed through the TL1 interface."
    ::= { tl1LogEntry 1 }


tl1LogSysName OBJECT-TYPE
    SYNTAX       DisplayString (SIZE (1..20))
    MAX-ACCESS   read-only
    STATUS       current
    DESCRIPTION  "The name of the BTI 7000 system at the time that the log was
                  recorded."
    ::= { tl1LogEntry 2 }


tl1LogType OBJECT-TYPE
    SYNTAX       INTEGER { alarm    (1),
                           event    (2),
                           dbChange (3),
                           security (4),
                           command  (5),
                           rtrvcmd  (6) }
    MAX-ACCESS   read-only
    STATUS       current
    DESCRIPTION  "The type of log entry."
    ::= { tl1LogEntry 3 }


tl1LogTypeSpecificLogNum OBJECT-TYPE
    SYNTAX       Unsigned32
    MAX-ACCESS   read-only
    STATUS       current
    DESCRIPTION  "The type-specific number for this log."
    ::= { tl1LogEntry 4 }


tl1LogMsgCode OBJECT-TYPE
    SYNTAX       DisplayString (SIZE (1..32))
    MAX-ACCESS   read-only
    STATUS       current
    DESCRIPTION  "The message code that was issued for this log entry. This
                  field is relevant to log entries for TL1 autonomous
                  notifications. For example, the message code may be 'REPT ALM
                  OC48'. A message code is reported for all log entries of type
                  alarm, event and dbChange. For logs of type security or
                  command, the message code is an empty string."
    ::= { tl1LogEntry 5 }


tl1LogDateAndTime OBJECT-TYPE
    SYNTAX       DateAndTime
    MAX-ACCESS   read-only
    STATUS       current
    DESCRIPTION  "The timestamp of the log entry."
    ::= { tl1LogEntry 6 }


tl1LogMessage OBJECT-TYPE
    SYNTAX       DisplayString
    MAX-ACCESS   read-only
    STATUS       current
    DESCRIPTION  "This is the main log entry contents. The log entry is enclosed
                  in double quotations."
    ::= { tl1LogEntry 7 }



latestTl1LogNum OBJECT-TYPE
    SYNTAX       Unsigned32
    MAX-ACCESS   read-only
    STATUS       current
    DESCRIPTION  "Identifies the value of the tl1LogIdx object for the most recently
                  added entry in the tl1LogTable."
    ::= { administration 4 }



-----------------------------------------------------------------------
-- Objects related to managing the configured recipients of trap or
-- inform messages generated by the system's SNMP agent.
-----------------------------------------------------------------------


snmpTrapRcvTable OBJECT-TYPE
    SYNTAX       SEQUENCE OF SnmpTrapRcvEntry
    MAX-ACCESS   not-accessible
    STATUS       current
    DESCRIPTION  "This table contains one row for every configured SNMP
                  trap receiver. Each row contains a list of attributes
                  that pertain to a provisioned trap receiver. All access to
                  this table, whether for read, write, or create requests
                  are restricted to SNMP requests issued with a valid
                  community string configured with read-write access."
    ::= { administration 5 }


snmpTrapRcvEntry OBJECT-TYPE
    SYNTAX       SnmpTrapRcvEntry
    MAX-ACCESS   not-accessible
    STATUS       current
    DESCRIPTION  "The conceptual row object of the SNMP trap receiver table."
    INDEX        { snmpTrapRcvIdx }
    ::= { snmpTrapRcvTable 1 }


SnmpTrapRcvEntry ::= SEQUENCE { snmpTrapRcvIdx        DisplayString,
                                snmpTrapRcvIPAddr     IpAddress,
                                snmpTrapRcvPort       INTEGER,
                                snmpTrapRcvNotifType  INTEGER,
                                snmpTrapRcvVersion    INTEGER,
                                snmpTrapRcvCommunity  DisplayString,
                                snmpTrapRcvTTL        HoursAndMinutes,
                                snmpTrapRcvRowStatus  RowStatus }


snmpTrapRcvIdx OBJECT-TYPE
    SYNTAX       DisplayString (SIZE (1..32))
    MAX-ACCESS   read-create
    STATUS       current
    DESCRIPTION  "This string serves as a unique trap receiver Id and is
                  used to index the table."
    ::= { snmpTrapRcvEntry 1 }


snmpTrapRcvIPAddr OBJECT-TYPE
    SYNTAX       IpAddress
    MAX-ACCESS   read-create
    STATUS       current
    DESCRIPTION  "The IP address of the trap receiver. The setting of this
                  object is mandatory when creating a new row."
    ::= { snmpTrapRcvEntry 2 }


snmpTrapRcvPort OBJECT-TYPE
    SYNTAX       INTEGER (1..65535)
    MAX-ACCESS   read-create
    STATUS       current
    DESCRIPTION  "The port on the specified IP address of the trap receiver."
    DEFVAL       { 162 }
    ::= { snmpTrapRcvEntry 3 }


snmpTrapRcvNotifType OBJECT-TYPE
    SYNTAX       INTEGER { trap   (1),
                           inform (2) }
    MAX-ACCESS   read-create
    STATUS       current
    DESCRIPTION  "The type of notification service to be provided to the
                  trap receiver. The notification type can be configured
                  as inform only if the message version specified for the
                  snmpTrapRcvVersion object is snmpv2c."
    DEFVAL       { trap }
    ::= { snmpTrapRcvEntry 4 }


snmpTrapRcvVersion OBJECT-TYPE
    SYNTAX       INTEGER { snmpV1  (1),
                           snmpV2c (2),
                           snmpV3  (3) }
    MAX-ACCESS   read-create
    STATUS       current
    DESCRIPTION  "The type of notification service to be provided to the
                  trap receiver. The notification type can be configured
                  as inform only if the message version specified for the
                  snmpTrapRcvVersion object is snmpv2c. The setting of this
                  object is mandatory when creating a new row."
    ::= { snmpTrapRcvEntry 5 }


snmpTrapRcvCommunity OBJECT-TYPE
    SYNTAX       DisplayString (SIZE (1..20))
    MAX-ACCESS   read-create
    STATUS       current
    DESCRIPTION  "The community string inserted into the trap messages
                  generated for this trap receiver. The setting of this
                  object is mandatory when creating a new row."
    ::= { snmpTrapRcvEntry 6 }


snmpTrapRcvTTL OBJECT-TYPE
    SYNTAX       HoursAndMinutes
    MAX-ACCESS   read-create
    STATUS       current
    DESCRIPTION  "The time-to-live for the trap receiver. When the trap
                  receiver is created or this object is set, this object
                  specifies how long the trap receiver is to be configured.
                  When read, the value returned is the length of time
                  remaining before the trap receiver is automatically
                  deleted. The valid range for this object is 000-00 to
                  099-99. If this object is set to a value of 000-00,
                  the trap receiver will never auto-delete."
    DEFVAL       { "000-00" }
    ::= { snmpTrapRcvEntry 7 }


snmpTrapRcvRowStatus OBJECT-TYPE
    SYNTAX       RowStatus
    MAX-ACCESS   read-create
    STATUS       current
    DESCRIPTION  "Used to control the addition and deletion of entries
                  in the SNMP trap receiver table."
    ::= { snmpTrapRcvEntry 100 }



-----------------------------------------------------------------------
-- Objects related to cross connections between optical transceiver
-- facilities on wavelength conversion circuit packs
-- 
-- A listing of provisioned optical transceiver cross connects is
-- contained in the xcvrXCTable of the BTI 7000 Series MIB. When
-- retrieved, this table provides one row for each provisioned optical
-- transceiver cross connect between two transceiver end ports.
-- 
-- To create a cross connect, a new row of the xcvrXCTable must be
-- created. To delete a cross connect, the corresponding row of the
-- table must be destroyed.
-----------------------------------------------------------------------


xcvrXCTable OBJECT-TYPE
    SYNTAX       SEQUENCE OF XcvrXCEntry
    MAX-ACCESS   not-accessible
    STATUS       current
    DESCRIPTION  "This table contains one row for every provisioned cross
                  connection between optical transceiver facilities on
                  wavelength translator, regenerator and manager circuit packs."
    ::= { connections 1 }


xcvrXCEntry OBJECT-TYPE
    SYNTAX       XcvrXCEntry
    MAX-ACCESS   not-accessible
    STATUS       current
    DESCRIPTION  "The conceptual row object of the optical transceiver cross
                  connection table."
    INDEX        { xcvrXCSrcTypeIdx,
                   xcvrXCSrcShelfIdx,
                   xcvrXCSrcSlotIdx,
                   xcvrXCSrcIdx,
                   xcvrXCDestTypeIdx,
                   xcvrXCDestShelfIdx,
                   xcvrXCDestSlotIdx,
                   xcvrXCDestIdx }
    ::= { xcvrXCTable 1 }


XcvrXCEntry ::= SEQUENCE { xcvrXCSrcTypeIdx    XcvrType,
                           xcvrXCSrcShelfIdx   INTEGER,
                           xcvrXCSrcSlotIdx    INTEGER,
                           xcvrXCSrcIdx        INTEGER,
                           xcvrXCDestTypeIdx   XcvrType,
                           xcvrXCDestShelfIdx  INTEGER,
                           xcvrXCDestSlotIdx   INTEGER,
                           xcvrXCDestIdx       INTEGER,
                           xcvrXCType          XCType,
                           xcvrXCRowStatus     RowStatus }


xcvrXCSrcTypeIdx OBJECT-TYPE
    SYNTAX       XcvrType
    MAX-ACCESS   not-accessible
    STATUS       current
    DESCRIPTION  "The specific type of wavelength conversion function of the
                  transceiver port that serves as the source port for the cross
                  connection."
    ::= { xcvrXCEntry 1 }


xcvrXCSrcShelfIdx OBJECT-TYPE
    SYNTAX       INTEGER (1|11|21|31)
    MAX-ACCESS   not-accessible
    STATUS       current
    DESCRIPTION  "The number of the shelf of the transceiver port that serves as
                  the source port for the cross connection."
    ::= { xcvrXCEntry 2 }


xcvrXCSrcSlotIdx OBJECT-TYPE
    SYNTAX       INTEGER (1..20)
    MAX-ACCESS   not-accessible
    STATUS       current
    DESCRIPTION  "The number of the slot of the transceiver port that serves as
                  the source port for the cross connection."
    ::= { xcvrXCEntry 3 }


xcvrXCSrcIdx OBJECT-TYPE
    SYNTAX       INTEGER (1..4)
    MAX-ACCESS   not-accessible
    STATUS       current
    DESCRIPTION  "The number of the port of the transceiver port that serves as
                  the source port for the cross connection."
    ::= { xcvrXCEntry 4 }


xcvrXCDestTypeIdx OBJECT-TYPE
    SYNTAX       XcvrType
    MAX-ACCESS   not-accessible
    STATUS       current
    DESCRIPTION  "The specific type of wavelength conversion function of the
                  transceiver port that serves as the destination port for the
                  cross connection."
    ::= { xcvrXCEntry 5 }


xcvrXCDestShelfIdx OBJECT-TYPE
    SYNTAX       INTEGER (1|11|21|31)
    MAX-ACCESS   not-accessible
    STATUS       current
    DESCRIPTION  "The number of the shelf of the transceiver port that serves as
                  the destination port for the cross connection."
    ::= { xcvrXCEntry 6 }


xcvrXCDestSlotIdx OBJECT-TYPE
    SYNTAX       INTEGER (1..20)
    MAX-ACCESS   not-accessible
    STATUS       current
    DESCRIPTION  "The number of the slot of the transceiver port that serves as
                  the destination port for the cross connection."
    ::= { xcvrXCEntry 7 }


xcvrXCDestIdx OBJECT-TYPE
    SYNTAX       INTEGER (1..4)
    MAX-ACCESS   not-accessible
    STATUS       current
    DESCRIPTION  "The number of the port of the transceiver port that serves as
                  the destination port for the cross connection."
    ::= { xcvrXCEntry 8 }


xcvrXCType OBJECT-TYPE
    SYNTAX       XCType
    MAX-ACCESS   read-create
    STATUS       current
    DESCRIPTION  "The type of cross connection between the identified source and
                  destination transceiver ports. This is a mandatory object when
                  a row of the transceiver cross connect table is created. Only
                  1-way and 2-way cross-connections are supported on optical
                  transceiver ports"
    ::= { xcvrXCEntry 9 }


xcvrXCRowStatus OBJECT-TYPE
    SYNTAX       RowStatus
    MAX-ACCESS   read-create
    STATUS       current
    DESCRIPTION  "Used to control the addition and deletion of entries in the
                  transceiver cross connection table, which in turn controls the
                  provisioning and de-provisioning of transceiver cross
                  connections."
    ::= { xcvrXCEntry 100 }



-----------------------------------------------------------------------
-- Objects related to cross connections between Virtual Concatenation
-- Group (VCG) entities on Muxponder circuit packs
-- 
-- A listing of provisioned virtual concatenation group (VCG) cross
-- connects is contained in the vcgXCTable of the BTI 7000 Series MIB. 
-- VCG entities are created on the muxponder circuit pack to facilitate 
-- the mapping of client facilities into line facility time slots. The 
-- client facilities are transported over line facility time slots when 
-- the required VCG cross-connects are created. When retrieved, this
-- table provides one row for each provisioned VCG cross connect.
-- 
-- To create a cross connect, a new row of the vcgXCTable must be 
-- created. To delete a cross connect, the corresponding row of the
-- table must be destroyed.
-----------------------------------------------------------------------


vcgXCTable OBJECT-TYPE
    SYNTAX       SEQUENCE OF VcgXCEntry
    MAX-ACCESS   not-accessible
    STATUS       current
    DESCRIPTION  "This table contains one row for every provisioned cross
                  connection between VCGs on Muxponder circuit packs."
    ::= { connections 2 }


vcgXCEntry OBJECT-TYPE
    SYNTAX       VcgXCEntry
    MAX-ACCESS   not-accessible
    STATUS       current
    DESCRIPTION  "The conceptual row object of the VCG cross connection table."
    INDEX        { vcgXCSrcShelfIdx,
                   vcgXCSrcSlotIdx,
                   vcgXCSrcPortIdx,
                   vcgXCSrcIdx,
                   vcgXCDestShelfIdx,
                   vcgXCDestSlotIdx,
                   vcgXCDestPortIdx,
                   vcgXCDestIdx }
    ::= { vcgXCTable 1 }


VcgXCEntry ::= SEQUENCE { vcgXCSrcShelfIdx   INTEGER,
                          vcgXCSrcSlotIdx    INTEGER,
                          vcgXCSrcPortIdx    INTEGER,
                          vcgXCSrcIdx        INTEGER,
                          vcgXCDestShelfIdx  INTEGER,
                          vcgXCDestSlotIdx   INTEGER,
                          vcgXCDestPortIdx   INTEGER,
                          vcgXCDestIdx       INTEGER,
                          vcgXCType          XCType,
                          vcgXCProtShelfNum  INTEGER,
                          vcgXCProtSlotNum   INTEGER,
                          vcgXCProtPortNum   INTEGER,
                          vcgXCProtNum       INTEGER,
                          vcgXCRowStatus     RowStatus }


vcgXCSrcShelfIdx OBJECT-TYPE
    SYNTAX       INTEGER (1|11|21|31)
    MAX-ACCESS   not-accessible
    STATUS       current
    DESCRIPTION  "The number of the shelf of the VCG entity that serves as the
                  source port for the cross connection."
    ::= { vcgXCEntry 1 }


vcgXCSrcSlotIdx OBJECT-TYPE
    SYNTAX       INTEGER (1..20)
    MAX-ACCESS   not-accessible
    STATUS       current
    DESCRIPTION  "The number of the slot of the VCG entity that serves as the
                  source port for the cross connection."
    ::= { vcgXCEntry 2 }


vcgXCSrcPortIdx OBJECT-TYPE
    SYNTAX       INTEGER (1..2)
    MAX-ACCESS   not-accessible
    STATUS       current
    DESCRIPTION  "The number of the port of the VCG entity that serves as the
                  source port for the cross connection."
    ::= { vcgXCEntry 3 }


vcgXCSrcIdx OBJECT-TYPE
    SYNTAX       INTEGER (1..255)
    MAX-ACCESS   not-accessible
    STATUS       current
    DESCRIPTION  "The number of the VCG within the identified port that serves
                  as the source port for the cross connection."
    ::= { vcgXCEntry 4 }


vcgXCDestShelfIdx OBJECT-TYPE
    SYNTAX       INTEGER (1|11|21|31)
    MAX-ACCESS   not-accessible
    STATUS       current
    DESCRIPTION  "The number of the shelf of the VCG entity that serves as the
                  destination port for the cross connection."
    ::= { vcgXCEntry 5 }


vcgXCDestSlotIdx OBJECT-TYPE
    SYNTAX       INTEGER (1..20)
    MAX-ACCESS   not-accessible
    STATUS       current
    DESCRIPTION  "The number of the slot of the VCG entity that serves as the
                  destination port for the cross connection."
    ::= { vcgXCEntry 6 }


vcgXCDestPortIdx OBJECT-TYPE
    SYNTAX       INTEGER (1..12)
    MAX-ACCESS   not-accessible
    STATUS       current
    DESCRIPTION  "The number of the port of the VCG entity that serves as the
                  destination port for the cross connection."
    ::= { vcgXCEntry 7 }


vcgXCDestIdx OBJECT-TYPE
    SYNTAX       INTEGER (1..255)
    MAX-ACCESS   not-accessible
    STATUS       current
    DESCRIPTION  "The number of the VCG within the identified port that serves
                  as the destination port for the cross connection."
    ::= { vcgXCEntry 8 }


vcgXCType OBJECT-TYPE
    SYNTAX       XCType
    MAX-ACCESS   read-create
    STATUS       current
    DESCRIPTION  "The type of cross connection between the identified source and
                  destination VCG entities. This is a mandatory object when a
                  row of the VCG cross connect table is created. Only 2-way and
                  2-way protected cross-connections are supported between VCGs."
    ::= { vcgXCEntry 9 }


vcgXCProtShelfNum OBJECT-TYPE
    SYNTAX       INTEGER (1|11|21|31)
    MAX-ACCESS   read-create
    STATUS       current
    DESCRIPTION  "The number of the shelf of the VCG entity that serves as the
                  protection port for the cross connection."
    ::= { vcgXCEntry 10 }


vcgXCProtSlotNum OBJECT-TYPE
    SYNTAX       INTEGER (1..20)
    MAX-ACCESS   read-create
    STATUS       current
    DESCRIPTION  "The number of the slot of the VCG entity that serves as the
                  protection port for the cross connection."
    ::= { vcgXCEntry 11 }


vcgXCProtPortNum OBJECT-TYPE
    SYNTAX       INTEGER (1..2)
    MAX-ACCESS   read-create
    STATUS       current
    DESCRIPTION  "The number of the port of the VCG entity that serves as the
                  protection port for the cross connection."
    ::= { vcgXCEntry 12 }


vcgXCProtNum OBJECT-TYPE
    SYNTAX       INTEGER (1..255)
    MAX-ACCESS   read-create
    STATUS       current
    DESCRIPTION  "The number of the VCG within the identified port that serves
                  as the protection port for the cross connection."
    ::= { vcgXCEntry 13 }


vcgXCRowStatus OBJECT-TYPE
    SYNTAX       RowStatus
    MAX-ACCESS   read-create
    STATUS       current
    DESCRIPTION  "Used to control the addition and deletion of entries in the
                  VCG cross connection table, which in turn controls the
                  provisioning and de-provisioning of VCG cross connections."
    ::= { vcgXCEntry 100 }



-----------------------------------------------------------------------
-- Objects related to cross connections of SONET STS-N facilities
-- on Muxponder circuit packs
-----------------------------------------------------------------------


stsnXCTable OBJECT-TYPE
    SYNTAX       SEQUENCE OF StsnXCEntry
    MAX-ACCESS   not-accessible
    STATUS       current
    DESCRIPTION  "This table contains one row for every provisioned cross
                  connection between SONET STS-N facilities on Muxponder circuit
                  packs."
    ::= { connections 3 }


stsnXCEntry OBJECT-TYPE
    SYNTAX       StsnXCEntry
    MAX-ACCESS   not-accessible
    STATUS       current
    DESCRIPTION  "The conceptual row object of the STS-N cross connection
                  table."
    INDEX        { stsnXCStsnTypeIdx,
                   stsnXCSrcShelfIdx,
                   stsnXCSrcSlotIdx,
                   stsnXCSrcPortIdx,
                   stsnXCSrcIdx,
                   stsnXCDestShelfIdx,
                   stsnXCDestSlotIdx,
                   stsnXCDestPortIdx,
                   stsnXCDestIdx }
    ::= { stsnXCTable 1 }


StsnXCEntry ::= SEQUENCE { stsnXCStsnTypeIdx   StsnType,
                           stsnXCSrcShelfIdx   INTEGER,
                           stsnXCSrcSlotIdx    INTEGER,
                           stsnXCSrcPortIdx    INTEGER,
                           stsnXCSrcIdx        INTEGER,
                           stsnXCDestShelfIdx  INTEGER,
                           stsnXCDestSlotIdx   INTEGER,
                           stsnXCDestPortIdx   INTEGER,
                           stsnXCDestIdx       INTEGER,
                           stsnXCType          XCType,
                           stsnXCProtTypeNum   StsnType,
                           stsnXCProtShelfNum  INTEGER,
                           stsnXCProtSlotNum   INTEGER,
                           stsnXCProtPortNum   INTEGER,
                           stsnXCProtNum       INTEGER,
                           stsnXCRowStatus     RowStatus }


stsnXCStsnTypeIdx OBJECT-TYPE
    SYNTAX       StsnType
    MAX-ACCESS   not-accessible
    STATUS       current
    DESCRIPTION  "The specific STS-N rate of the cross-connection."
    ::= { stsnXCEntry 1 }


stsnXCSrcShelfIdx OBJECT-TYPE
    SYNTAX       INTEGER (1|11|21|31)
    MAX-ACCESS   not-accessible
    STATUS       current
    DESCRIPTION  "The number of the shelf of the STS-N facility that serves as
                  the source end-point for the cross connection."
    ::= { stsnXCEntry 2 }


stsnXCSrcSlotIdx OBJECT-TYPE
    SYNTAX       INTEGER (1|3|5|7|9|11|13|15|17|19)
    MAX-ACCESS   not-accessible
    STATUS       current
    DESCRIPTION  "The number of the slot of the STS-N facility that serves as
                  the source end-point for the cross connection."
    ::= { stsnXCEntry 3 }


stsnXCSrcPortIdx OBJECT-TYPE
    SYNTAX       INTEGER (1..2)
    MAX-ACCESS   not-accessible
    STATUS       current
    DESCRIPTION  "The number of the port of the STS-N facility that serves as
                  the source end-point for the cross connection."
    ::= { stsnXCEntry 4 }


stsnXCSrcIdx OBJECT-TYPE
    SYNTAX       INTEGER (1..192)
    MAX-ACCESS   not-accessible
    STATUS       current
    DESCRIPTION  "The number of the STS-N within the identified port that serves
                  as the source end-point for the cross connection."
    ::= { stsnXCEntry 5 }


stsnXCDestShelfIdx OBJECT-TYPE
    SYNTAX       INTEGER (1|11|21|31)
    MAX-ACCESS   not-accessible
    STATUS       current
    DESCRIPTION  "The number of the shelf of the STS-N facility that serves as
                  the destination end-point for the cross connection."
    ::= { stsnXCEntry 6 }


stsnXCDestSlotIdx OBJECT-TYPE
    SYNTAX       INTEGER (1|3|5|7|9|11|13|15|17|19)
    MAX-ACCESS   not-accessible
    STATUS       current
    DESCRIPTION  "The number of the slot of the STS-N entity that serves as the
                  destination end-point for the cross connection."
    ::= { stsnXCEntry 7 }


stsnXCDestPortIdx OBJECT-TYPE
    SYNTAX       INTEGER (1..12)
    MAX-ACCESS   not-accessible
    STATUS       current
    DESCRIPTION  "The number of the port of the STS-N entity that serves as the
                  destination end-point for the cross connection."
    ::= { stsnXCEntry 8 }


stsnXCDestIdx OBJECT-TYPE
    SYNTAX       INTEGER (1..192)
    MAX-ACCESS   not-accessible
    STATUS       current
    DESCRIPTION  "The number of the STS-N within the identified port that serves
                  as the destination end-point for the cross connection."
    ::= { stsnXCEntry 9 }


stsnXCType OBJECT-TYPE
    SYNTAX       XCType
    MAX-ACCESS   read-create
    STATUS       current
    DESCRIPTION  "The type of cross connection between the identified source and
                  destination STS-N facilities. This is a mandatory object when
                  a row of the STS-N cross connect table is created. Only 2-way
                  cross-connections are supported between STS-Ns."
    ::= { stsnXCEntry 10 }


stsnXCProtTypeNum OBJECT-TYPE
    SYNTAX       StsnType
    MAX-ACCESS   read-create
    STATUS       current
    DESCRIPTION  "The rate of the STS-N facility that serves as the protection
                  end-point for the cross connection."
    ::= { stsnXCEntry 11 }


stsnXCProtShelfNum OBJECT-TYPE
    SYNTAX       INTEGER (1|11|21|31)
    MAX-ACCESS   read-create
    STATUS       current
    DESCRIPTION  "The number of the shelf of the STS-N entity that serves as the
                  protection end-point for the cross connection."
    ::= { stsnXCEntry 12 }


stsnXCProtSlotNum OBJECT-TYPE
    SYNTAX       INTEGER (1|3|5|7|9|11|13|15|17|19)
    MAX-ACCESS   read-create
    STATUS       current
    DESCRIPTION  "The number of the slot of the STS-N entity that serves as the
                  protection end-point for the cross connection."
    ::= { stsnXCEntry 13 }


stsnXCProtPortNum OBJECT-TYPE
    SYNTAX       INTEGER (1..2)
    MAX-ACCESS   read-create
    STATUS       current
    DESCRIPTION  "The number of the port of the STS-N entity that serves as the
                  protection end-point for the cross connection."
    ::= { stsnXCEntry 14 }


stsnXCProtNum OBJECT-TYPE
    SYNTAX       INTEGER (1..192)
    MAX-ACCESS   read-create
    STATUS       current
    DESCRIPTION  "The number of the STS-N within the identified port that serves
                  as the protection end-point for the cross connection."
    ::= { stsnXCEntry 15 }


stsnXCRowStatus OBJECT-TYPE
    SYNTAX       RowStatus
    MAX-ACCESS   read-create
    STATUS       current
    DESCRIPTION  "Used to control the addition and deletion of entries in the
                  STS-N cross connection table, which in turn controls the
                  provisioning and de-provisioning of STS-N cross connections."
    ::= { stsnXCEntry 100 }



-----------------------------------------------------------------------
-- Objects related to cross connections of SDH VC-N facilities
-- on Muxponder circuit packs
-----------------------------------------------------------------------


vcnXCTable OBJECT-TYPE
    SYNTAX       SEQUENCE OF VcnXCEntry
    MAX-ACCESS   not-accessible
    STATUS       current
    DESCRIPTION  "This table contains one row for every provisioned cross
                  connection between SDH VC-N facilities on Muxponder circuit
                  packs."
    ::= { connections 4 }


vcnXCEntry OBJECT-TYPE
    SYNTAX       VcnXCEntry
    MAX-ACCESS   not-accessible
    STATUS       current
    DESCRIPTION  "The conceptual row object of the VC-N cross connection table."
    INDEX        { vcnXCVcnTypeIdx,
                   vcnXCSrcShelfIdx,
                   vcnXCSrcSlotIdx,
                   vcnXCSrcPortIdx,
                   vcnXCSrcIdx,
                   vcnXCDestShelfIdx,
                   vcnXCDestSlotIdx,
                   vcnXCDestPortIdx,
                   vcnXCDestIdx }
    ::= { vcnXCTable 1 }


VcnXCEntry ::= SEQUENCE { vcnXCVcnTypeIdx    VcnType,
                          vcnXCSrcShelfIdx   INTEGER,
                          vcnXCSrcSlotIdx    INTEGER,
                          vcnXCSrcPortIdx    INTEGER,
                          vcnXCSrcIdx        INTEGER,
                          vcnXCDestShelfIdx  INTEGER,
                          vcnXCDestSlotIdx   INTEGER,
                          vcnXCDestPortIdx   INTEGER,
                          vcnXCDestIdx       INTEGER,
                          vcnXCType          XCType,
                          vcnXCProtTypeNum   VcnType,
                          vcnXCProtShelfNum  INTEGER,
                          vcnXCProtSlotNum   INTEGER,
                          vcnXCProtPortNum   INTEGER,
                          vcnXCProtNum       INTEGER,
                          vcnXCRowStatus     RowStatus }


vcnXCVcnTypeIdx OBJECT-TYPE
    SYNTAX       VcnType
    MAX-ACCESS   not-accessible
    STATUS       current
    DESCRIPTION  "The specific rate of the VC-N cross-connection."
    ::= { vcnXCEntry 1 }


vcnXCSrcShelfIdx OBJECT-TYPE
    SYNTAX       INTEGER (1|11|21|31)
    MAX-ACCESS   not-accessible
    STATUS       current
    DESCRIPTION  "The number of the shelf of the VC-N facility that serves as
                  the source end-point for the cross connection."
    ::= { vcnXCEntry 2 }


vcnXCSrcSlotIdx OBJECT-TYPE
    SYNTAX       INTEGER (1|3|5|7|9|11|13|15|17|19)
    MAX-ACCESS   not-accessible
    STATUS       current
    DESCRIPTION  "The number of the slot of the VC-N facility that serves as the
                  source end-point for the cross connection."
    ::= { vcnXCEntry 3 }


vcnXCSrcPortIdx OBJECT-TYPE
    SYNTAX       INTEGER (1..2)
    MAX-ACCESS   not-accessible
    STATUS       current
    DESCRIPTION  "The number of the port of the VC-N facility that serves as the
                  source end-point for the cross connection."
    ::= { vcnXCEntry 4 }


vcnXCSrcIdx OBJECT-TYPE
    SYNTAX       INTEGER (1..64)
    MAX-ACCESS   not-accessible
    STATUS       current
    DESCRIPTION  "The number of the VC-N within the identified port that serves
                  as the source end-point for the cross connection."
    ::= { vcnXCEntry 5 }


vcnXCDestShelfIdx OBJECT-TYPE
    SYNTAX       INTEGER (1|11|21|31)
    MAX-ACCESS   not-accessible
    STATUS       current
    DESCRIPTION  "The number of the shelf of the VC-N facility that serves as
                  the destination end-point for the cross connection."
    ::= { vcnXCEntry 6 }


vcnXCDestSlotIdx OBJECT-TYPE
    SYNTAX       INTEGER (1|3|5|7|9|11|13|15|17|19)
    MAX-ACCESS   not-accessible
    STATUS       current
    DESCRIPTION  "The number of the slot of the VC-N entity that serves as the
                  destination end-point for the cross connection."
    ::= { vcnXCEntry 7 }


vcnXCDestPortIdx OBJECT-TYPE
    SYNTAX       INTEGER (1..12)
    MAX-ACCESS   not-accessible
    STATUS       current
    DESCRIPTION  "The number of the port of the VC-N entity that serves as the
                  destination end-point for the cross connection."
    ::= { vcnXCEntry 8 }


vcnXCDestIdx OBJECT-TYPE
    SYNTAX       INTEGER (1..64)
    MAX-ACCESS   not-accessible
    STATUS       current
    DESCRIPTION  "The number of the VC-N within the identified port that serves
                  as the destination end-point for the cross connection."
    ::= { vcnXCEntry 9 }


vcnXCType OBJECT-TYPE
    SYNTAX       XCType
    MAX-ACCESS   read-create
    STATUS       current
    DESCRIPTION  "The type of cross connection between the identified source and
                  destination VC-N facilities. This is a mandatory object when a
                  row of the VC-N cross connect table is created. Only 2-way
                  cross-connections are supported between VC-Ns."
    ::= { vcnXCEntry 10 }


vcnXCProtTypeNum OBJECT-TYPE
    SYNTAX       VcnType
    MAX-ACCESS   read-create
    STATUS       current
    DESCRIPTION  "The rate of the VC-N facility that serves as the protection
                  end-point for the cross connection."
    ::= { vcnXCEntry 11 }


vcnXCProtShelfNum OBJECT-TYPE
    SYNTAX       INTEGER (1|11|21|31)
    MAX-ACCESS   read-create
    STATUS       current
    DESCRIPTION  "The number of the shelf of the VC-N entity that serves as the
                  protection end-point for the cross connection."
    ::= { vcnXCEntry 12 }


vcnXCProtSlotNum OBJECT-TYPE
    SYNTAX       INTEGER (1|3|5|7|9|11|13|15|17|19)
    MAX-ACCESS   read-create
    STATUS       current
    DESCRIPTION  "The number of the slot of the VC-N entity that serves as the
                  protection end-point for the cross connection."
    ::= { vcnXCEntry 13 }


vcnXCProtPortNum OBJECT-TYPE
    SYNTAX       INTEGER (1..2)
    MAX-ACCESS   read-create
    STATUS       current
    DESCRIPTION  "The number of the port of the VC-N entity that serves as the
                  protection end-point for the cross connection."
    ::= { vcnXCEntry 14 }


vcnXCProtNum OBJECT-TYPE
    SYNTAX       INTEGER (1..64)
    MAX-ACCESS   read-create
    STATUS       current
    DESCRIPTION  "The number of the VC-N within the identified port that serves
                  as the protection end-point for the cross connection."
    ::= { vcnXCEntry 15 }


vcnXCRowStatus OBJECT-TYPE
    SYNTAX       RowStatus
    MAX-ACCESS   read-create
    STATUS       current
    DESCRIPTION  "Used to control the addition and deletion of entries in the
                  VC-N cross connection table, which in turn controls the
                  provisioning and de-provisioning of VC-N cross connections."
    ::= { vcnXCEntry 100 }



-----------------------------------------------------------------------
-- Objects related to cross connections of OTN ODU-N facilities
-- on Muxponder circuit packs
-----------------------------------------------------------------------


odunXCTable OBJECT-TYPE
    SYNTAX       SEQUENCE OF OdunXCEntry
    MAX-ACCESS   not-accessible
    STATUS       current
    DESCRIPTION  "This table contains one row for every provisioned cross
                  connection between OTN ODU-N facilities on Muxponder circuit
                  packs."
    ::= { connections 5 }


odunXCEntry OBJECT-TYPE
    SYNTAX       OdunXCEntry
    MAX-ACCESS   not-accessible
    STATUS       current
    DESCRIPTION  "The conceptual row object of the ODU-N cross connection
                  table."
    INDEX        { odunXCOdunTypeIdx,
                   odunXCSrcShelfIdx,
                   odunXCSrcSlotIdx,
                   odunXCSrcPortIdx,
                   odunXCSrcIdx,
                   odunXCDestShelfIdx,
                   odunXCDestSlotIdx,
                   odunXCDestPortIdx,
                   odunXCDestIdx }
    ::= { odunXCTable 1 }


OdunXCEntry ::= SEQUENCE { odunXCOdunTypeIdx   OdunType,
                           odunXCSrcShelfIdx   INTEGER,
                           odunXCSrcSlotIdx    INTEGER,
                           odunXCSrcPortIdx    INTEGER,
                           odunXCSrcIdx        INTEGER,
                           odunXCDestShelfIdx  INTEGER,
                           odunXCDestSlotIdx   INTEGER,
                           odunXCDestPortIdx   INTEGER,
                           odunXCDestIdx       INTEGER,
                           odunXCType          XCType,
                           odunXCProtTypeNum   OdunType,
                           odunXCProtShelfNum  INTEGER,
                           odunXCProtSlotNum   INTEGER,
                           odunXCProtPortNum   INTEGER,
                           odunXCProtNum       INTEGER,
                           odunXCRowStatus     RowStatus }


odunXCOdunTypeIdx OBJECT-TYPE
    SYNTAX       OdunType
    MAX-ACCESS   not-accessible
    STATUS       current
    DESCRIPTION  "The specific rate of the ODU-N cross-connection."
    ::= { odunXCEntry 1 }


odunXCSrcShelfIdx OBJECT-TYPE
    SYNTAX       INTEGER (1|11|21|31)
    MAX-ACCESS   not-accessible
    STATUS       current
    DESCRIPTION  "The number of the shelf of the ODU-N facility that serves as
                  the source end-point for the cross connection."
    ::= { odunXCEntry 2 }


odunXCSrcSlotIdx OBJECT-TYPE
    SYNTAX       INTEGER (1|3|5|7|9|11|13|15|17|19)
    MAX-ACCESS   not-accessible
    STATUS       current
    DESCRIPTION  "The number of the slot of the ODU-N facility that serves as
                  the source end-point for the cross connection."
    ::= { odunXCEntry 3 }


odunXCSrcPortIdx OBJECT-TYPE
    SYNTAX       INTEGER (1..2)
    MAX-ACCESS   not-accessible
    STATUS       current
    DESCRIPTION  "The number of the port of the ODU-N facility that serves as
                  the source end-point for the cross connection."
    ::= { odunXCEntry 4 }


odunXCSrcIdx OBJECT-TYPE
    SYNTAX       INTEGER (1..4)
    MAX-ACCESS   not-accessible
    STATUS       current
    DESCRIPTION  "The number of the ODU-N within the identified port that serves
                  as the source end-point for the cross connection."
    ::= { odunXCEntry 5 }


odunXCDestShelfIdx OBJECT-TYPE
    SYNTAX       INTEGER (1|11|21|31)
    MAX-ACCESS   not-accessible
    STATUS       current
    DESCRIPTION  "The number of the shelf of the ODU-N facility that serves as
                  the destination end-point for the cross connection."
    ::= { odunXCEntry 6 }


odunXCDestSlotIdx OBJECT-TYPE
    SYNTAX       INTEGER (1|3|5|7|9|11|13|15|17|19)
    MAX-ACCESS   not-accessible
    STATUS       current
    DESCRIPTION  "The number of the slot of the ODU-N entity that serves as the
                  destination end-point for the cross connection."
    ::= { odunXCEntry 7 }


odunXCDestPortIdx OBJECT-TYPE
    SYNTAX       INTEGER (1..12)
    MAX-ACCESS   not-accessible
    STATUS       current
    DESCRIPTION  "The number of the port of the ODU-N entity that serves as the
                  destination end-point for the cross connection."
    ::= { odunXCEntry 8 }


odunXCDestIdx OBJECT-TYPE
    SYNTAX       INTEGER (1..1)
    MAX-ACCESS   not-accessible
    STATUS       current
    DESCRIPTION  "The number of the ODU-N within the identified port that serves
                  as the destination end-point for the cross connection."
    ::= { odunXCEntry 9 }


odunXCType OBJECT-TYPE
    SYNTAX       XCType
    MAX-ACCESS   read-create
    STATUS       current
    DESCRIPTION  "The type of cross connection between the identified source and
                  destination ODU-N facilities. This is a mandatory object when
                  a row of the ODU-N cross connect table is created. Only 2-way
                  cross-connections are supported between ODU-Ns."
    ::= { odunXCEntry 10 }


odunXCProtTypeNum OBJECT-TYPE
    SYNTAX       OdunType
    MAX-ACCESS   read-create
    STATUS       current
    DESCRIPTION  "The rate of the ODU-N facility that serves as the protection
                  end-point for the cross connection."
    ::= { odunXCEntry 11 }


odunXCProtShelfNum OBJECT-TYPE
    SYNTAX       INTEGER (1|11|21|31)
    MAX-ACCESS   read-create
    STATUS       current
    DESCRIPTION  "The number of the shelf of the ODU-N entity that serves as the
                  protection end-point for the cross connection."
    ::= { odunXCEntry 12 }


odunXCProtSlotNum OBJECT-TYPE
    SYNTAX       INTEGER (1|3|5|7|9|11|13|15|17|19)
    MAX-ACCESS   read-create
    STATUS       current
    DESCRIPTION  "The number of the slot of the ODU-N entity that serves as the
                  protection end-point for the cross connection."
    ::= { odunXCEntry 13 }


odunXCProtPortNum OBJECT-TYPE
    SYNTAX       INTEGER (1..2)
    MAX-ACCESS   read-create
    STATUS       current
    DESCRIPTION  "The number of the port of the ODU-N entity that serves as the
                  protection end-point for the cross connection."
    ::= { odunXCEntry 14 }


odunXCProtNum OBJECT-TYPE
    SYNTAX       INTEGER (1..4)
    MAX-ACCESS   read-create
    STATUS       current
    DESCRIPTION  "The number of the ODU-N within the identified port that serves
                  as the protection end-point for the cross connection."
    ::= { odunXCEntry 15 }


odunXCRowStatus OBJECT-TYPE
    SYNTAX       RowStatus
    MAX-ACCESS   read-create
    STATUS       current
    DESCRIPTION  "Used to control the addition and deletion of entries in the
                  ODU-N cross connection table, which in turn controls the
                  provisioning and de-provisioning of ODU-N cross connections."
    ::= { odunXCEntry 100 }



-----------------------------------------------------------------------
-- Objects related to protection group pairings between optical
-- transceiver facilities on wavelength conversion circuit packs
-- 
-- A listing of provisioned protection group pairs is contained in
-- the xcvrProtGrpTable of the BTI 7000 Series MIB. When retrieved,
-- this table provides one row for each transceiver port protection
-- group pair provisioned on the BTI 7000 Series.
-- 
-- To create a protection group, a new row of the xcvrProtGrpTable must
-- be created. To delete a protection group, the corresponding row of
-- the table must be destroyed.
-- 
-- The following table lists the objects in each entry of the
-- xcvrProtGrpTable.
-----------------------------------------------------------------------


xcvrProtGrpTable OBJECT-TYPE
    SYNTAX       SEQUENCE OF XcvrProtGrpEntry
    MAX-ACCESS   not-accessible
    STATUS       current
    DESCRIPTION  "This table contains one row for every provisioned protection
                  group pairing between optical transceiver facilities on the
                  wavelength translator, regenerator and manager cards."
    ::= { protection 1 }


xcvrProtGrpEntry OBJECT-TYPE
    SYNTAX       XcvrProtGrpEntry
    MAX-ACCESS   not-accessible
    STATUS       current
    DESCRIPTION  "The conceptual row object of the optical transceiver
                  protection group table."
    INDEX        { xcvrProtGrpWorkTypeIdx,
                   xcvrProtGrpWorkShelfIdx,
                   xcvrProtGrpWorkSlotIdx,
                   xcvrProtGrpWorkIdx,
                   xcvrProtGrpProtTypeIdx,
                   xcvrProtGrpProtShelfIdx,
                   xcvrProtGrpProtSlotIdx,
                   xcvrProtGrpProtIdx }
    ::= { xcvrProtGrpTable 1 }


XcvrProtGrpEntry ::= SEQUENCE { xcvrProtGrpWorkTypeIdx   XcvrType,
                                xcvrProtGrpWorkShelfIdx  INTEGER,
                                xcvrProtGrpWorkSlotIdx   INTEGER,
                                xcvrProtGrpWorkIdx       INTEGER,
                                xcvrProtGrpProtTypeIdx   XcvrType,
                                xcvrProtGrpProtShelfIdx  INTEGER,
                                xcvrProtGrpProtSlotIdx   INTEGER,
                                xcvrProtGrpProtIdx       INTEGER,
                                xcvrProtGrpId            DisplayString,
                                xcvrProtGrpRowStatus     RowStatus }


xcvrProtGrpWorkTypeIdx OBJECT-TYPE
    SYNTAX       XcvrType
    MAX-ACCESS   not-accessible
    STATUS       current
    DESCRIPTION  "The specific type of wavelength conversion function of the
                  transceiver port that serves as the working port for the
                  protection group."
    ::= { xcvrProtGrpEntry 1 }


xcvrProtGrpWorkShelfIdx OBJECT-TYPE
    SYNTAX       INTEGER (1|11|21|31)
    MAX-ACCESS   not-accessible
    STATUS       current
    DESCRIPTION  "The number of the shelf of the transceiver port that serves as
                  the working port for the protection group."
    ::= { xcvrProtGrpEntry 2 }


xcvrProtGrpWorkSlotIdx OBJECT-TYPE
    SYNTAX       INTEGER (1..20)
    MAX-ACCESS   not-accessible
    STATUS       current
    DESCRIPTION  "The number of the slot of the transceiver port that serves as
                  the working port for the protection group."
    ::= { xcvrProtGrpEntry 3 }


xcvrProtGrpWorkIdx OBJECT-TYPE
    SYNTAX       INTEGER (1..4)
    MAX-ACCESS   not-accessible
    STATUS       current
    DESCRIPTION  "The number of the port of the transceiver port that serves as
                  the working port for the protection group."
    ::= { xcvrProtGrpEntry 4 }


xcvrProtGrpProtTypeIdx OBJECT-TYPE
    SYNTAX       XcvrType
    MAX-ACCESS   not-accessible
    STATUS       current
    DESCRIPTION  "The specific type of wavelength conversion function of the
                  transceiver port that serves as the protection port for the
                  protection group."
    ::= { xcvrProtGrpEntry 5 }


xcvrProtGrpProtShelfIdx OBJECT-TYPE
    SYNTAX       INTEGER (1|11|21|31)
    MAX-ACCESS   not-accessible
    STATUS       current
    DESCRIPTION  "The number of the shelf of the transceiver port that serves as
                  the protection port for the protection group."
    ::= { xcvrProtGrpEntry 6 }


xcvrProtGrpProtSlotIdx OBJECT-TYPE
    SYNTAX       INTEGER (1..20)
    MAX-ACCESS   not-accessible
    STATUS       current
    DESCRIPTION  "The number of the slot of the transceiver port that serves as
                  the protection port for the protection group."
    ::= { xcvrProtGrpEntry 7 }


xcvrProtGrpProtIdx OBJECT-TYPE
    SYNTAX       INTEGER (1..4)
    MAX-ACCESS   not-accessible
    STATUS       current
    DESCRIPTION  "The number of the port of the transceiver port that serves as
                  the protection port for the protection group."
    ::= { xcvrProtGrpEntry 8 }


xcvrProtGrpId OBJECT-TYPE
    SYNTAX       DisplayString (SIZE (0..32))
    MAX-ACCESS   read-create
    STATUS       current
    DESCRIPTION  "Textual data recorded by the user to describe the provisioned
                  transceiver protection group in a manner useful to the user."
    DEFVAL       { "" }
    ::= { xcvrProtGrpEntry 9 }


xcvrProtGrpRowStatus OBJECT-TYPE
    SYNTAX       RowStatus
    MAX-ACCESS   read-create
    STATUS       current
    DESCRIPTION  "Used to control the addition and deletion of entries in the
                  transceiver protection group table, which in turn controls
                  provisioning and deprovisioning of optical transceiver
                  protection groups."
    ::= { xcvrProtGrpEntry 100 }


-----------------------------------------------------------------------
-- Objects related to protection group pairings between SONET OC-N
-- facilities on Muxponder circuit packs
-----------------------------------------------------------------------


ocnProtGrpTable OBJECT-TYPE
    SYNTAX       SEQUENCE OF OcnProtGrpEntry
    MAX-ACCESS   not-accessible
    STATUS       current
    DESCRIPTION  "This table contains one row for every provisioned protection
                  group pairing between SONET OC-N facilities on Muxponder
                  circuit packs."
    ::= { protection 2 }


ocnProtGrpEntry OBJECT-TYPE
    SYNTAX       OcnProtGrpEntry
    MAX-ACCESS   not-accessible
    STATUS       current
    DESCRIPTION  "The conceptual row object of the OC-N facility protection
                  group table."
    INDEX        { ocnProtGrpWorkTypeIdx,
                   ocnProtGrpWorkShelfIdx,
                   ocnProtGrpWorkSlotIdx,
                   ocnProtGrpWorkPortIdx,
                   ocnProtGrpProtTypeIdx,
                   ocnProtGrpProtShelfIdx,
                   ocnProtGrpProtSlotIdx,
                   ocnProtGrpProtPortIdx }
    ::= { ocnProtGrpTable 1 }


OcnProtGrpEntry ::= SEQUENCE { ocnProtGrpWorkTypeIdx   OcnType,
                               ocnProtGrpWorkShelfIdx  INTEGER,
                               ocnProtGrpWorkSlotIdx   INTEGER,
                               ocnProtGrpWorkPortIdx   INTEGER,
                               ocnProtGrpProtTypeIdx   OcnType,
                               ocnProtGrpProtShelfIdx  INTEGER,
                               ocnProtGrpProtSlotIdx   INTEGER,
                               ocnProtGrpProtPortIdx   INTEGER,
                               ocnProtGrpId            DisplayString,
                               ocnProtGrpRowStatus     RowStatus }


ocnProtGrpWorkTypeIdx OBJECT-TYPE
    SYNTAX       OcnType
    MAX-ACCESS   not-accessible
    STATUS       current
    DESCRIPTION  "The specific rate of the OC-N facility that serves as the
                  working facility for the protection group. Currently, only
                  OCN-N facilities that are OTU-N mapped are supported for protection
                  grouping."
    ::= { ocnProtGrpEntry 1 }


ocnProtGrpWorkShelfIdx OBJECT-TYPE
    SYNTAX       INTEGER (1|11|21|31)
    MAX-ACCESS   not-accessible
    STATUS       current
    DESCRIPTION  "The number of the shelf of the OC-N facility that serves as
                  the working facility for the protection group."
    ::= { ocnProtGrpEntry 2 }


ocnProtGrpWorkSlotIdx OBJECT-TYPE
    SYNTAX       INTEGER (1|3|5|7|9|11|13|15|17|19)
    MAX-ACCESS   not-accessible
    STATUS       current
    DESCRIPTION  "The number of the slot of the OC-N facility that serves as
                  the working facility for the protection group."
    ::= { ocnProtGrpEntry 3 }


ocnProtGrpWorkPortIdx OBJECT-TYPE
    SYNTAX       INTEGER (1..2)
    MAX-ACCESS   not-accessible
    STATUS       current
    DESCRIPTION  "The number of the port of the OC-N facility that serves as
                  the working facility for the protection group."
    ::= { ocnProtGrpEntry 4 }


ocnProtGrpProtTypeIdx OBJECT-TYPE
    SYNTAX       OcnType
    MAX-ACCESS   not-accessible
    STATUS       current
    DESCRIPTION  "The specific rate of the OC-N facility that serves as the
                  protection facility for the protection group. Currently, only
                  OC-N facilities that are OTU-N mapped are supported for protection
                  grouping."
    ::= { ocnProtGrpEntry 5 }


ocnProtGrpProtShelfIdx OBJECT-TYPE
    SYNTAX       INTEGER (1|11|21|31)
    MAX-ACCESS   not-accessible
    STATUS       current
    DESCRIPTION  "The number of the shelf of the OC-N facility that serves as
                  the protection facility for the protection group."
    ::= { ocnProtGrpEntry 6 }


ocnProtGrpProtSlotIdx OBJECT-TYPE
    SYNTAX       INTEGER (1|3|5|7|9|11|13|15|17|19)
    MAX-ACCESS   not-accessible
    STATUS       current
    DESCRIPTION  "The number of the slot of the OC-N facility that serves as
                  the protection facility for the protection group."
    ::= { ocnProtGrpEntry 7 }


ocnProtGrpProtPortIdx OBJECT-TYPE
    SYNTAX       INTEGER (1..2)
    MAX-ACCESS   not-accessible
    STATUS       current
    DESCRIPTION  "The number of the port of the OC-N facility that serves as
                  the protection facility for the protection group."
    ::= { ocnProtGrpEntry 8 }


ocnProtGrpId OBJECT-TYPE
    SYNTAX       DisplayString (SIZE (0..32))
    MAX-ACCESS   read-create
    STATUS       current
    DESCRIPTION  "Textual data recorded by the user to describe the provisioned
                  OC-N protection group in a manner useful to the user."
    DEFVAL       { "" }
    ::= { ocnProtGrpEntry 9 }


ocnProtGrpRowStatus OBJECT-TYPE
    SYNTAX       RowStatus
    MAX-ACCESS   read-create
    STATUS       current
    DESCRIPTION  "Used to control the addition and deletion of entries in the
                  OC-N protection group table, which in turn controls
                  provisioning and deprovisioning of OC-N facility
                  protection groups."
    ::= { ocnProtGrpEntry 100 }
    


-----------------------------------------------------------------------
-- Objects related to protection group pairings between SDH STM-N
-- facilities on Muxponder circuit packs
-----------------------------------------------------------------------


stmnProtGrpTable OBJECT-TYPE
    SYNTAX       SEQUENCE OF StmnProtGrpEntry
    MAX-ACCESS   not-accessible
    STATUS       current
    DESCRIPTION  "This table contains one row for every provisioned protection
                  group pairing between SDH STM-N facilities on Muxponder
                  circuit packs."
    ::= { protection 3 }


stmnProtGrpEntry OBJECT-TYPE
    SYNTAX       StmnProtGrpEntry
    MAX-ACCESS   not-accessible
    STATUS       current
    DESCRIPTION  "The conceptual row object of the STM-N facility protection
                  group table."
    INDEX        { stmnProtGrpWorkTypeIdx,
                   stmnProtGrpWorkShelfIdx,
                   stmnProtGrpWorkSlotIdx,
                   stmnProtGrpWorkPortIdx,
                   stmnProtGrpProtTypeIdx,
                   stmnProtGrpProtShelfIdx,
                   stmnProtGrpProtSlotIdx,
                   stmnProtGrpProtPortIdx }
    ::= { stmnProtGrpTable 1 }


StmnProtGrpEntry ::= SEQUENCE { stmnProtGrpWorkTypeIdx   StmnType,
                                stmnProtGrpWorkShelfIdx  INTEGER,
                                stmnProtGrpWorkSlotIdx   INTEGER,
                                stmnProtGrpWorkPortIdx   INTEGER,
                                stmnProtGrpProtTypeIdx   StmnType,
                                stmnProtGrpProtShelfIdx  INTEGER,
                                stmnProtGrpProtSlotIdx   INTEGER,
                                stmnProtGrpProtPortIdx   INTEGER,
                                stmnProtGrpId            DisplayString,
                                stmnProtGrpRowStatus     RowStatus }


stmnProtGrpWorkTypeIdx OBJECT-TYPE
    SYNTAX       StmnType
    MAX-ACCESS   not-accessible
    STATUS       current
    DESCRIPTION  "The specific rate of the STM-N facility that serves as the
                  working facility for the protection group. Currently, only
                  STM-N facilities that are OTU-N mapped are supported for protection
                  grouping."
    ::= { stmnProtGrpEntry 1 }


stmnProtGrpWorkShelfIdx OBJECT-TYPE
    SYNTAX       INTEGER (1|11|21|31)
    MAX-ACCESS   not-accessible
    STATUS       current
    DESCRIPTION  "The number of the shelf of the STM-N facility that serves as
                  the working facility for the protection group."
    ::= { stmnProtGrpEntry 2 }


stmnProtGrpWorkSlotIdx OBJECT-TYPE
    SYNTAX       INTEGER (1|3|5|7|9|11|13|15|17|19)
    MAX-ACCESS   not-accessible
    STATUS       current
    DESCRIPTION  "The number of the slot of the STM-N facility that serves as
                  the working facility for the protection group."
    ::= { stmnProtGrpEntry 3 }


stmnProtGrpWorkPortIdx OBJECT-TYPE
    SYNTAX       INTEGER (1..2)
    MAX-ACCESS   not-accessible
    STATUS       current
    DESCRIPTION  "The number of the port of the STM-N facility that serves as
                  the working facility for the protection group."
    ::= { stmnProtGrpEntry 4 }


stmnProtGrpProtTypeIdx OBJECT-TYPE
    SYNTAX       StmnType
    MAX-ACCESS   not-accessible
    STATUS       current
    DESCRIPTION  "The specific rate of the STM-N facility that serves as the
                  protection facility for the protection group. Currently, only
                  STM-N facilities that are OTU-N mapped are supported for protection
                  grouping."
    ::= { stmnProtGrpEntry 5 }


stmnProtGrpProtShelfIdx OBJECT-TYPE
    SYNTAX       INTEGER (1|11|21|31)
    MAX-ACCESS   not-accessible
    STATUS       current
    DESCRIPTION  "The number of the shelf of the STM-N facility that serves as
                  the protection facility for the protection group."
    ::= { stmnProtGrpEntry 6 }


stmnProtGrpProtSlotIdx OBJECT-TYPE
    SYNTAX       INTEGER (1|3|5|7|9|11|13|15|17|19)
    MAX-ACCESS   not-accessible
    STATUS       current
    DESCRIPTION  "The number of the slot of the STM-N facility that serves as
                  the protection facility for the protection group."
    ::= { stmnProtGrpEntry 7 }


stmnProtGrpProtPortIdx OBJECT-TYPE
    SYNTAX       INTEGER (1..2)
    MAX-ACCESS   not-accessible
    STATUS       current
    DESCRIPTION  "The number of the port of the STM-N facility that serves as
                  the protection facility for the protection group."
    ::= { stmnProtGrpEntry 8 }


stmnProtGrpId OBJECT-TYPE
    SYNTAX       DisplayString (SIZE (0..32))
    MAX-ACCESS   read-create
    STATUS       current
    DESCRIPTION  "Textual data recorded by the user to describe the provisioned
                  STM-N protection group in a manner useful to the user."
    DEFVAL       { "" }
    ::= { stmnProtGrpEntry 9 }


stmnProtGrpRowStatus OBJECT-TYPE
    SYNTAX       RowStatus
    MAX-ACCESS   read-create
    STATUS       current
    DESCRIPTION  "Used to control the addition and deletion of entries in the
                  STM-N protection group table, which in turn controls
                  provisioning and deprovisioning of STM-N facility
                  protection groups."
    ::= { stmnProtGrpEntry 100 }



-----------------------------------------------------------------------
-- Objects used to perform operations directed at the network element
-- as a whole
-----------------------------------------------------------------------


dbBackupAndRestore      OBJECT IDENTIFIER ::= { neOperations 1 }
swUpgrade               OBJECT IDENTIFIER ::= { neOperations 2 }


DbBackupAndRestoreCmd ::= TEXTUAL-CONVENTION
    STATUS       current
    DESCRIPTION  "The MSCP maintains all provisionable data in non-volatile 
			storage so that configuration settings are retained during 
			system shutdowns and restarts. The configuration database 
			is version controlled to facilitate the detection of an
			incompatible software load and/or database.

			The BTI 7000 Series supports user-initiated backup and 
			restore operations of the configuration database through the 
			SNMP Set requests performed on the dbBackupAndRestoreCmd 
			object with a value corresponding to the required action.

			In a backup operation, the database is uploaded to a 
			user-specified network location (that is, a local PC or a 
			remote PC) using the file transfer protocol (FTP), or it is 
			stored locally on the MSCP.

			In a restore operation, the database is restored using a 
			version of the file from an FTP server or locally from the 
			MSCP. The integrity of the file is validated to ensure that 
			it matches the current software load on the BTI 7000 Series.

			The DbBackupAndRestoreCmd textual convention is the value of
                  the dbBackupAndRestoreCmd object, which is used to activate a
                  database backup operation, or the various steps of a database
                  restore operation. These operations are initiated when a set
                  request is performed on the dbBackupAndRestoreCmd object with
                  a value corresponding to the desired action, as explained
                  below. A get request on this type returns the value noOp.
                  
                  The valid values for DbBackupAndRestoreCmd that can be used in
                  a set operation are:
                  - 'invokeBackup': used to perform a database backup operation.
                  The operation may be used to perform a local database backup,
                  or to save the database backup to a remote repository.
                  - 'loadRestore': used to initiate a database restore
                  operation. The operation may be the restoration of a local
                  database backup or of a remote database backup
                  - 'invokeRestore': continues a database restore operation
                  after the loadRestore stage has completed. The database being
                  restored is made active on the SCP circuit pack at this stage.
                  - 'applyRestore':  Obsolete  this functionality is now done as
                  part of the invokeRestore.
                  - 'commitRestore': is used to complete a database restore
                  operation and can be used after the applyRestore action
                  completes
                  - 'cancelRestore': is used to cancel and back out of a
                  database restore operation in progress and can be used before
                  the commitRestore action is called.
                  
                  In order for the set request on the dbBackupAndRestoreCmd
                  object to complete successfully, the values of other objects
                  must be set in the same set request for some of the commands.
                  The additional objects required to be set along with the
                  dbBackupAndRestoreCmd object for each DbBackupAndRestoreCmd
                  value are listed below.
                  - invokeBackup: must also set dbBackupAndRestoreType. If this
                  object is set to remote, then the dbBackupAndRestoreAddress,
                  dbBackupAndRestoreFtpUser and dbBackupAndRestorePswd object
                  values must also be specified in the set request. The
                  dbBackupAndRestoreCheckAlm object may optionally be set when
                  the invokeBackup action is performed. Also when the
                  dbBackupAndRestoreType is set to remote the
                  dbBackupAndRestorePath is optional. If not specified the
                  default name is used.
                  - loadRestore: must also set dbBackupAndRestoreType. If this
                  object is set to remote, then the dbBackupAndRestoreAddress,
                  dbBackupAndRestorePath, dbBackupAndRestoreFtpUser and
                  dbBackupAndRestorePswd object values must also be specified in
                  the set request. The dbBackupAndRestoreCheckSysName object may
                  be set when the loadRestore action is performed, but is not
                  mandatory.
                  - invokeRestore: must also set
                  dbBackupAndRestoreInvokeFilename to confirm the name of the
                  backed file to be used in the restore operation. Optionally,
                  the dbBackupAndRestoreCheckAlm object may be set.
                  - applyRestore, commitRestore, cancelRestore: no additional
                  object values are required to be included for these set
                  requests"
    SYNTAX       INTEGER { noOp          (1),
                           invokeBackup  (2),
                           loadRestore   (3),
                           invokeRestore (4),
                           -- applyRestore  (5),  Obsolete as of release 7.3.0.
                           commitRestore (6),
                           cancelRestore (7) }


DbBackupAndRestoreType ::= TEXTUAL-CONVENTION
    STATUS       current
    DESCRIPTION  "Indicates the type of database backup operation to be
                  performed, or the type of database restore operation to be
                  performed. The meaning of the values are as follows.
                  - 'local': for a database backup, the backup is made on the NE
                  itself; for a database restore, the restoration is from a
                  local database backup file
                  - 'remote': for a database backup, the backup is made to an
                  external ftp server; for a database restore, the restoration
                  is from a database file located on an external ftp server
                  - 'remoteSftp': for a database backup, the backup is made to an
                  external sftp server; for a database restore, the restoration
                  is from a database file located on an external sftp server"
    SYNTAX       INTEGER { local  (1),
                           remote (2),
                           remoteSftp (3) }


dbBackupAndRestoreCmd OBJECT-TYPE
    SYNTAX       DbBackupAndRestoreCmd
    MAX-ACCESS   read-write
    STATUS       current
    DESCRIPTION  "This object is used to activate the steps of a database backup
                  or database restore operation. The description of the
                  DbBackupAndRestoreCmd textual convention explains the usage of
                  this object to perform these operations."
    ::= { dbBackupAndRestore 1 }


dbBackupAndRestoreType OBJECT-TYPE
    SYNTAX       DbBackupAndRestoreType
    MAX-ACCESS   read-write
    STATUS       current
    DESCRIPTION  "This object is used to indicate whether a local database, or a
                  remote database is involved in the backup or restore operation
                  that is being activated with the dbBackupAndRestoreCmd object,
                  as explained in the DbBackupAndRestoreType textual
                  convention."
    ::= { dbBackupAndRestore 2 }


dbBackupAndRestoreAddress OBJECT-TYPE
    SYNTAX       IpAddress
    MAX-ACCESS   read-write
    STATUS       current
    DESCRIPTION  "The IP address of an ftp server which the NE database is
                  backed up to, or restored from. This object is used when the
                  dbBackupAndRestoreType is set to remote."
    ::= { dbBackupAndRestore 3 }


dbBackupAndRestorePath OBJECT-TYPE
    SYNTAX       DisplayString (SIZE (1..64))
    MAX-ACCESS   read-write
    STATUS       current
    DESCRIPTION  "The directory path on the ftp server where where the NE
                  database backup is to be saved to, or restored from. This
                  object is used when the dbBackupAndRestoreType is set to
                  remote."
    ::= { dbBackupAndRestore 4 }


dbBackupAndRestoreFtpUser OBJECT-TYPE
    SYNTAX       DisplayString (SIZE (1..64))
    MAX-ACCESS   read-write
    STATUS       current
    DESCRIPTION  "The user identifier to be used on the ftp server where the NE
                  database backup is to be saved to, or restored from. This
                  object is used when the dbBackupAndRestoreType is set to
                  remote."
    ::= { dbBackupAndRestore 5 }


dbBackupAndRestoreFtpPswd OBJECT-TYPE
    SYNTAX       DisplayString (SIZE (1..64))
    MAX-ACCESS   read-write
    STATUS       current
    DESCRIPTION  "The password to be used on the ftp server where the NE
                  database backup is to be saved to, or restored from. This
                  object is used when the dbBackupAndRestoreType is set to
                  remote."
    ::= { dbBackupAndRestore 6 }


dbBackupAndRestoreCheckAlm OBJECT-TYPE
    SYNTAX       INTEGER { yes (1),
                           no  (2) }
    MAX-ACCESS   read-write
    STATUS       current
    DESCRIPTION  "This object is used to indicate whether or not the system is
                  to be checked for active alarms before proceding with a backup
                  or restore operation. If set to yes, the requested action will
                  not be performed if alarms are active on the system. If not
                  specified in the same set request as the dbBackupAndRestoreCmd
                  object, the value is defaulted to yes."
    ::= { dbBackupAndRestore 7 }


dbBackupAndRestoreCheckSysName OBJECT-TYPE
    SYNTAX       INTEGER { yes (1),
                           no  (2) }
    MAX-ACCESS   read-write
    STATUS       current
    DESCRIPTION  "This object is used to indicate whether or not the system name
                  of the NE targeted for a database restore operation against
                  the system name embedded in the database backup file to be
                  restored. If set to yes, the requested action will not be
                  performed if system names do not match. If not specified in
                  the same set request as the dbBackupAndRestoreCmd object, the
                  value is defaulted to yes."
    ::= { dbBackupAndRestore 8 }


dbBackupAndRestoreInvokeFilename OBJECT-TYPE
    SYNTAX       DisplayString (SIZE (1..64))
    MAX-ACCESS   read-write
    STATUS       current
    DESCRIPTION  "The name of the database backup file that is to be used in a
                  database restore operation. This object is set along with the
                  dbBackupAndRestoreCmd object when it is set to invokeRestore,
                  as a confirmation that the database that is to be restored is
                  the correct database. In order for the invokeRestore command
                  to proceed, the value set for this object must match the value
                  of the dbBackupAndRestoreFilename object."
    ::= { dbBackupAndRestore 9 }


dbBackupAndRestoreFilename OBJECT-TYPE
    SYNTAX       DisplayString (SIZE (1..64))
    MAX-ACCESS   read-only
    STATUS       current
    DESCRIPTION  "The name of the database backup file that is present and ready
                  to be restored. The value of this field is valid after the
                  completion of the loadRestore command."
    ::= { dbBackupAndRestore 10 }


dbBackupAndRestoreResult OBJECT-TYPE
    SYNTAX       INTEGER { success (1),
                           failure (2) }
    MAX-ACCESS   accessible-for-notify
    STATUS       current
    DESCRIPTION  "Indicates if the identified stage of the database backup and
                  restore process has resulted in success or failure."
    ::= { dbBackupAndRestore 11 }



SwUpgradeCmd ::= TEXTUAL-CONVENTION
    STATUS       current
    DESCRIPTION  "All BTI 7000 Series circuit packs are shipped with 
			pre-loaded software. At system commissioning, it is not 
			necessary to start the system by loading software.
			However, during the life cycle of the BTI 7000 Series, 
			it might be necessary to upgrade the system software. 
			Normally, the system software is upgraded to:

			� Support the functionality of new circuit packs
			� Provide new features for existing circuit packs
			� Add specific software improvements

			Performing a system software upgrade on the BTI 7000 Series 
			is non-service affecting. The upgrade process is designed 
			for application environments that require that the optical 
			signals passing through the BTI 7000 Series are not interrupted.

			The BTI 7000 Series supports a user-initiated software upgrade 
			operation through the SNMP Set requests performed on the 
			swUpgradeCmd object with a value corresponding to the required 
			action.
			
			The SwUpgradeCmd textual convention is the value of the
                  swUpgradeCmd object, which is used to activate the various
                  steps of the software upgrade procedure on the system. These
                  steps are initiated when a set request is performed on the
                  swUpgradeCmd object with a value corresponding to the desired
                  action, as explained below. A get request will return the
                  value noOp.
                  
                  The valid values for SwUpgradeCmd that can be used in a set
                  operation are:
                  - 'checkUpgrade': used to perform a pre-upgrade check of the
                  system to ensure that it is ready for the upgrade process, and
                  that the load files on the server are accessible.
                  - 'loadUpgrade': used to initiate a system upgrade by
                  downloading the load files from a remote server to the SCP
                  software load storage area.
                  - 'invokeUpgrade': continues a system upgrade operation after
                  the loadUpgrade stage has completed. First the upgrade load is
                  installed on all circuit packs in the system, then each card
                  is rebooted to run the upgrade load.
                  - 'commitUpgrade': is used to complete a system upgrade
                  operation and can be used after the invkUpgrade action
                  completes
                  - 'cancelUpgrade': is used to cancel and back out of a system
                  software upgrade operation in progress and can be used before
                  the cmmtUpgrade action is called.
                  - 'invokeScpUpgrade': is a special-purpose upgrade step used
                  in place of the invkUpgrade value when an upgrade is being
                  performed on an SCP pack only. Such a targeted upgrade is
                  valid only when an SCP pack is replaced and the new pack
                  requires a software upgrade to make its software version
                  consistent with the system
                  
                  In order for the set request on the swUpgradeCmd object to
                  complete successfully, the values of other objects must be set
                  in the same set request for some of the commands. The
                  additional objects required to be set along with the
                  swUpgradeCmd object for each SwUpgradeCmd value are listed
                  below.
                  - checkUpgrade, loadUpgrade: must also set swUpgradeAddress,
                  swUpgradePath, swUpgradeFtpUser, swUpgradeFtpPswd and
                  swUpgradeFileTransferType object values to indicate where 
                  the ftp or sftp server with the upgrade load files is to 
                  be found, along with access parameters.
                  - invokeUpgrade, invokeScpUpgrade: must also set the
                  swUpgradeInvokeRelNum object to confirm the software version
                  that is to be used in the upgrade. The swUpgradeCheckAlm
                  object may be set, but is not mandatory.
                  - commitUpgrade, cancelUpgrade: no additional object values
                  are required to be specified for these set requests."
    SYNTAX       INTEGER { noOp           (1),
                           checkUpgrade   (2),
                           loadUpgrade    (3),
                           invkUpgrade    (4),
                           cmmtUpgrade    (5),
                           cancUpgrade    (6),
                           invkScpUpgrade (7) }

SwUpgradeFileTransferType ::= TEXTUAL-CONVENTION
    STATUS       current
    DESCRIPTION  "Indicates the protocol of the file transfer.
                  - 'ftp': an external ftp server is the source for the load
                  to be transfered.
                  - 'sftp': an external sftp server is the source for the load
                  to be transfered."
    SYNTAX       INTEGER { ftp  (1),
                           sftp (2) }

swUpgradeCmd OBJECT-TYPE
    SYNTAX       SwUpgradeCmd
    MAX-ACCESS   read-write
    STATUS       current
    DESCRIPTION  "This object is used to activate the steps of a software
                  upgrade procedure on the system. The description of the
                  SwUpgradeCmd textual convention explains the usage of this
                  object to perform these operations."
    ::= { swUpgrade 1 }


swUpgradeAddress OBJECT-TYPE
    SYNTAX       IpAddress
    MAX-ACCESS   read-write
    STATUS       current
    DESCRIPTION  "The IP address of an ftp or sftp server from which the software
                  load files for the upgrade are to be downloaded."
    ::= { swUpgrade 2 }


swUpgradePath OBJECT-TYPE
    SYNTAX       DisplayString (SIZE (1..64))
    MAX-ACCESS   read-write
    STATUS       current
    DESCRIPTION  "The directory path on the upgrade load files ftp or sftp server 
                  where the software load files are found."
    ::= { swUpgrade 3 }


swUpgradeFtpUser OBJECT-TYPE
    SYNTAX       DisplayString (SIZE (1..64))
    MAX-ACCESS   read-write
    STATUS       current
    DESCRIPTION  "The user identifier to be used on the ftp or sftp server from
                  which the upgrade load is downloaded."
    ::= { swUpgrade 4 }


swUpgradeFtpPswd OBJECT-TYPE
    SYNTAX       DisplayString (SIZE (1..64))
    MAX-ACCESS   read-write
    STATUS       current
    DESCRIPTION  "The password to be used on the ftp or sftp server from which
                  the upgrade load is downloaded."
    ::= { swUpgrade 5 }


swUpgradeInvokeRelNum OBJECT-TYPE
    SYNTAX       DisplayString (SIZE (1..16))
    MAX-ACCESS   read-write
    STATUS       current
    DESCRIPTION  "The release number of the software upgrade load that is
                  targeted in a software upgrade invoke operation. This object
                  must be set along with the swUpgradeCmd object when it is set
                  to invokeUpgrade or invokeScpUpgrade, as a confirmation that
                  the software load to be used in the upgrade is the correct
                  load."
    ::= { swUpgrade 6 }


swUpgradeCheckAlm OBJECT-TYPE
    SYNTAX       INTEGER { yes (1),
                           no  (2) }
    MAX-ACCESS   read-write
    STATUS       current
    DESCRIPTION  "This object is used to indicate whether or not the system is
                  to be checked for active alarms before proceding with a
                  software upgrade operation. If set to yes, the requested
                  action will not be performed if alarms are active on the
                  system. If not specified in the same set request as the
                  swUpgradeCmd object, the value is defaulted to yes."
    ::= { swUpgrade 7 }


swUpgradeActiveRelNum OBJECT-TYPE
    SYNTAX       DisplayString (SIZE (1..16))
    MAX-ACCESS   read-only
    STATUS       current
    DESCRIPTION  "The release number of the software load that is installed on
                  the system and is currently active."
    ::= { swUpgrade 8 }


swUpgradeInactiveRelNum OBJECT-TYPE
    SYNTAX       DisplayString (SIZE (1..16))
    MAX-ACCESS   read-only
    STATUS       current
    DESCRIPTION  "The release number of the software load that is installed on
                  the system and is currently inactive."
    ::= { swUpgrade 9 }


swUpgradeFileTransferType OBJECT-TYPE
    SYNTAX       SwUpgradeFileTransferType
    MAX-ACCESS   read-write
    STATUS       current
    DESCRIPTION  "This object is used to define the file transfer protocol used
                  to retreive the load from a remote server. The default value is
                  ftp"
    ::= { swUpgrade 10 }


-----------------------------------------------------------------------
-- Objects related to performing operations on provisioned circuit packs
-- 
-- When a circuit pack is restarted on the BTI 7000 Series, the following events
-- occur:
-- � Provisioning information is maintained.
-- � State information is re-synchronized at start up.
-- � Logs are maintained.
-- � Historical performance metric (PM) bins are cleared if the MSCP is restarted.
-- � Current PM bins are cleared if an amplifier or wavelength conversion circuit
-- pack is restarted.
-- � Clock time is kept up to date.
-- � Uptime is reset.
-- � Traffic is maintained if a warm restart is performed. A cold restart causes the
-- traffic path to be interrupted.
-- 
-- The cpRestartOpTable is used to perform circuit pack restarts. There is one row in
-- the table for every restartable circuit pack that is provisioned on the system. The
-- circuit pack restart is performed by setting the cpRestartOpCmd for the targeted
-- circuit pack row to perform either a warmRestart or a coldRestart.
-- 
-- The following table lists the objects in each entry of the cpRestartOpTable.
-----------------------------------------------------------------------


cpRestartOpTable OBJECT-TYPE
    SYNTAX       SEQUENCE OF CpRestartOpEntry
    MAX-ACCESS   not-accessible
    STATUS       current
    DESCRIPTION  "This table contains one row for every provisioned restartable
                  circuit pack on the NE to facilitate the performing of circuit
                  pack restarts."
    ::= { cpOperations 1 }


cpRestartOpEntry OBJECT-TYPE
    SYNTAX       CpRestartOpEntry
    MAX-ACCESS   not-accessible
    STATUS       current
    DESCRIPTION  "The conceptual row object of the circuit pack restart
                  operation table."
    INDEX        { cpRestartOpTypeIdx,
                   cpRestartOpShelfIdx,
                   cpRestartOpSlotIdx }
    ::= { cpRestartOpTable 1 }


CpRestartOpEntry ::= SEQUENCE { cpRestartOpTypeIdx   CpType,
                                cpRestartOpShelfIdx  INTEGER,
                                cpRestartOpSlotIdx   INTEGER,
                                cpRestartOpCmd       INTEGER }


cpRestartOpTypeIdx OBJECT-TYPE
    SYNTAX       CpType
    MAX-ACCESS   not-accessible
    STATUS       current
    DESCRIPTION  "The specific type of circuit pack targeted for the restart
                  operation."
    ::= { cpRestartOpEntry 1 }


cpRestartOpShelfIdx OBJECT-TYPE
    SYNTAX       INTEGER (1|11|21|31)
    MAX-ACCESS   not-accessible
    STATUS       current
    DESCRIPTION  "The number of the shelf on which the circuit pack targeted for
                  the restart operation is provisioned."
    ::= { cpRestartOpEntry 2 }


cpRestartOpSlotIdx OBJECT-TYPE
    SYNTAX       INTEGER (0..20)
    MAX-ACCESS   not-accessible
    STATUS       current
    DESCRIPTION  "The number of the slot in which the circuit pack targeted for
                  the restart operation is provisioned. For ESI type circuit
                  packs, the slot will be 0. For CCM type circuit packs, the slot 
                  can only be 1 or 2."
    ::= { cpRestartOpEntry 3 }


cpRestartOpCmd OBJECT-TYPE
    SYNTAX       INTEGER { noOp        (1),
                           warmRestart (2),
                           coldRestart (3),
                           powerOn     (4)}
    MAX-ACCESS   read-write
    STATUS       current
    DESCRIPTION  "Used to perform a circuit pack restart operation as follows.
                  - warmRestart causes a restart of the main processor only;
                  traffic is not affected
                  - coldRestart causes a full circuit pack restart, including
                  data path
                  - powerOn causes a circuit pack that has been powered down
                  due to a high temperature or voltage event to power on.

                  When this object is read, the value noOp is returned."
    ::= { cpRestartOpEntry 4 }



-----------------------------------------------------------------------
-- Objects related to performing operations on optical amplifier
-- facilities
-- 
-- The oaOOBRSDOpTable is used to perform an Override Optical Back Reflection
-- Shutdown operation on an optical amplifier. There is one entry in this table for
-- every provisioned amplifier on which such an operation can be performed. To
-- perform the operation, set the oaOOBRSOOpCmd object for the targeted amplifier
-- to overrideOBRSD.
-- 
-- The following table lists the objects in each entry of the oaOOBRSDOpTable.
-----------------------------------------------------------------------


oaOOBRSDOpTable OBJECT-TYPE
    SYNTAX       SEQUENCE OF OaOOBRSDOpEntry
    MAX-ACCESS   not-accessible
    STATUS       current
    DESCRIPTION  "This table contains one row for every provisioned optical
                  amplifier on the NE that supports the Override Optical Back
                  Reflection Shutdown operation."
    ::= { oaOperations 1 }


oaOOBRSDOpEntry OBJECT-TYPE
    SYNTAX       OaOOBRSDOpEntry
    MAX-ACCESS   not-accessible
    STATUS       current
    DESCRIPTION  "The conceptual row object of the optical amplifier override
                  optical back reflection shutdown operation table."
    INDEX        { oaOOBRSDOpTypeIdx,
                   oaOOBRSDOpShelfIdx,
                   oaOOBRSDOpSlotIdx,
                   oaOOBRSDOpIdx }
    ::= { oaOOBRSDOpTable 1 }


OaOOBRSDOpEntry ::= SEQUENCE { oaOOBRSDOpTypeIdx   OaType,
                               oaOOBRSDOpShelfIdx  INTEGER,
                               oaOOBRSDOpSlotIdx   INTEGER,
                               oaOOBRSDOpIdx       INTEGER,
                               oaOOBRSDOpCmd       INTEGER,
                               oaOOBRSDOpTimer     INTEGER }


oaOOBRSDOpTypeIdx OBJECT-TYPE
    SYNTAX       OaType
    MAX-ACCESS   not-accessible
    STATUS       current
    DESCRIPTION  "The specific type of optical amplifier."
    ::= { oaOOBRSDOpEntry 1 }


oaOOBRSDOpShelfIdx OBJECT-TYPE
    SYNTAX       INTEGER (1|11|21|31)
    MAX-ACCESS   not-accessible
    STATUS       current
    DESCRIPTION  "The number of the shelf on which the optical amplifier
                  targeted for the operation is provisioned."
    ::= { oaOOBRSDOpEntry 2 }


oaOOBRSDOpSlotIdx OBJECT-TYPE
    SYNTAX       INTEGER (1..20)
    MAX-ACCESS   not-accessible
    STATUS       current
    DESCRIPTION  "The number of the slot within which the optical amplifier
                  facility targeted for the operation is provisioned."
    ::= { oaOOBRSDOpEntry 3 }


oaOOBRSDOpIdx OBJECT-TYPE
    SYNTAX       INTEGER (1..1)
    MAX-ACCESS   not-accessible
    STATUS       current
    DESCRIPTION  "The number of the port on the circuit pack on which the
                  optical amplifier facility has been provisioned."
    ::= { oaOOBRSDOpEntry 4 }


oaOOBRSDOpCmd OBJECT-TYPE
    SYNTAX       INTEGER { noOp          (1),
                           overrideOBRSD (2) }
    MAX-ACCESS   read-write
    STATUS       current
    DESCRIPTION  "Used to perform a Override Optical Back Reflection Shutdown
                  operation when this object is set to overrideOBRSD. When read,
                  this object returns noOp."
    ::= { oaOOBRSDOpEntry 5 }


oaOOBRSDOpTimer OBJECT-TYPE
    SYNTAX       INTEGER (0..600)
    MAX-ACCESS   read-write
    STATUS       current
    DESCRIPTION  "Used to specify the time duration of an override back
                  reflection shutdown operation. It is only valid to set the
                  value of this object in the same set request as for the
                  oaOOBRSDOpCmd object. Despite the indicated value range, the
                  actual supported range is 20 to 600. The value 0 is returned
                  when this object is read, even if an overrideOBRSD operation
                  is in progress."
    ::= { oaOOBRSDOpEntry 6 }



-----------------------------------------------------------------------
-- Objects related to performing operations on optical transceiver
-- facilities
-- 
-- The xcvrLpbkOpTable is used to perform loopback operations on provisioned
-- transceiver port facilities on the wavelength conversion circuit packs. There is one
-- row in the table for each provisioned transceiver port on which a loopback
-- operation can be performed. To perform the loopback operation, set the
-- xcvrLpbkOpCmd object to oprLpbk. To release the loopback, set the
-- xcvrLpbkOpCmd object to rlsLpbk.
-- 
-- Note: The loopback operation can only be performed on a transceiver port if the
-- xcvrAdminStatus for the port is set to disabled.
-- 
-- The following table lists the objects in each entry of the xcvrLpbkOpTable.
-----------------------------------------------------------------------


xcvrLpbkOpTable OBJECT-TYPE
    SYNTAX       SEQUENCE OF XcvrLpbkOpEntry
    MAX-ACCESS   not-accessible
    STATUS       current
    DESCRIPTION  "This table contains one row for every provisioned optical
                  transceiver on the NE to facilitate the performing of
                  transceiver loopback operations."
    ::= { xcvrOperations 1 }


xcvrLpbkOpEntry OBJECT-TYPE
    SYNTAX       XcvrLpbkOpEntry
    MAX-ACCESS   not-accessible
    STATUS       current
    DESCRIPTION  "The conceptual row object of the optical transceiver loopback
                  operation table."
    INDEX        { xcvrLpbkOpTypeIdx,
                   xcvrLpbkOpShelfIdx,
                   xcvrLpbkOpSlotIdx,
                   xcvrLpbkOpIdx }
    ::= { xcvrLpbkOpTable 1 }


XcvrLpbkOpEntry ::= SEQUENCE { xcvrLpbkOpTypeIdx   XcvrType,
                               xcvrLpbkOpShelfIdx  INTEGER,
                               xcvrLpbkOpSlotIdx   INTEGER,
                               xcvrLpbkOpIdx       INTEGER,
                               xcvrLpbkOpCmd       INTEGER }


xcvrLpbkOpTypeIdx OBJECT-TYPE
    SYNTAX       XcvrType
    MAX-ACCESS   not-accessible
    STATUS       current
    DESCRIPTION  "The specific type of wavelength conversion function of the
                  circuit pack of the transceiver port targeted for the loopback
                  operation."
    ::= { xcvrLpbkOpEntry 1 }


xcvrLpbkOpShelfIdx OBJECT-TYPE
    SYNTAX       INTEGER (1|11|21|31)
    MAX-ACCESS   not-accessible
    STATUS       current
    DESCRIPTION  "The number of the shelf of the transceiver targeted for the
                  loopback operation."
    ::= { xcvrLpbkOpEntry 2 }


xcvrLpbkOpSlotIdx OBJECT-TYPE
    SYNTAX       INTEGER (1..20)
    MAX-ACCESS   not-accessible
    STATUS       current
    DESCRIPTION  "The number of the slot in which the transceiver targeted for
                  the loopback operation is provisioned."
    ::= { xcvrLpbkOpEntry 3 }


xcvrLpbkOpIdx OBJECT-TYPE
    SYNTAX       INTEGER (1..4)
    MAX-ACCESS   not-accessible
    STATUS       current
    DESCRIPTION  "The number of the port on the circuit pack on which the
                  optical transceiver facility has been provisioned."
    ::= { xcvrLpbkOpEntry 4 }


xcvrLpbkOpCmd OBJECT-TYPE
    SYNTAX       INTEGER { noOp        (1),
                           oprLpbk     (2),
                           rlsLpbk     (3),
                           oprTerminalLpbk (4) }
    MAX-ACCESS   read-write
    STATUS       current
    DESCRIPTION  "Used to perform a loopback operation on a transceiver facility
                  as follows:
                  - oprLpbk: operates a loopback on the transceiver
                  - rlsLpbk: causes a previously invoked loopback to be released
                  - oprTermLpbk: operates a terminal loopback for the transceiver

                  When read, this object returns noOp."
                  
    ::= { xcvrLpbkOpEntry 5 }

	-----------------------------------------------------------------------
-- Objects related to performing protection switching operations on optical 
-- transceiver facilities
-- 
-- The xcvrProtSwOpTable is used to perform protection switching operations on
-- transceiver port facilities. This table includes a row for every transceiver port
-- provisioned as part of a transceiver protection pair. The protection switch
-- operation is performed by setting the xcvrProtSwOpCmd object to the object value
-- that corresponds to the desired protection switching operation.
-- 
-- The following table lists the objects in each entry of the xcvrProtSwOpTable.
-----------------------------------------------------------------------

xcvrProtSwOpTable OBJECT-TYPE
    SYNTAX       SEQUENCE OF XcvrProtSwOpEntry
    MAX-ACCESS   not-accessible
    STATUS       current
    DESCRIPTION  "This table contains one row for every provisioned optical
                  transceiver on the NE configured to be part of a protection
                  group pair to facilitate the performing of transceiver
                  protection switching operations."
    ::= { xcvrOperations 2 }


xcvrProtSwOpEntry OBJECT-TYPE
    SYNTAX       XcvrProtSwOpEntry
    MAX-ACCESS   not-accessible
    STATUS       current
    DESCRIPTION  "The conceptual row object of the optical transceiver
                  protection switching operation table."
    INDEX        { xcvrProtSwOpTypeIdx,
                   xcvrProtSwOpShelfIdx,
                   xcvrProtSwOpSlotIdx,
                   xcvrProtSwOpIdx }
    ::= { xcvrProtSwOpTable 1 }


XcvrProtSwOpEntry ::= SEQUENCE { xcvrProtSwOpTypeIdx   XcvrType,
                                 xcvrProtSwOpShelfIdx  INTEGER,
                                 xcvrProtSwOpSlotIdx   INTEGER,
                                 xcvrProtSwOpIdx       INTEGER,
                                 xcvrProtSwOpCmd       INTEGER }


xcvrProtSwOpTypeIdx OBJECT-TYPE
    SYNTAX       XcvrType
    MAX-ACCESS   not-accessible
    STATUS       current
    DESCRIPTION  "The specific type of wavelength conversion function of the
                  circuit pack of the transceiver port targeted for the
                  protection switching operation."
    ::= { xcvrProtSwOpEntry 1 }


xcvrProtSwOpShelfIdx OBJECT-TYPE
    SYNTAX       INTEGER (1|11|21|31)
    MAX-ACCESS   not-accessible
    STATUS       current
    DESCRIPTION  "The number of the shelf of the transceiver targeted for the
                  protection switching operation."
    ::= { xcvrProtSwOpEntry 2 }


xcvrProtSwOpSlotIdx OBJECT-TYPE
    SYNTAX       INTEGER (1..20)
    MAX-ACCESS   not-accessible
    STATUS       current
    DESCRIPTION  "The number of the slot within which the transceiver targeted
                  for the protection switching operation is provisioned."
    ::= { xcvrProtSwOpEntry 3 }


xcvrProtSwOpIdx OBJECT-TYPE
    SYNTAX       INTEGER (1..4)
    MAX-ACCESS   not-accessible
    STATUS       current
    DESCRIPTION  "The number of the port on the circuit pack on which the
                  optical transceiver facility has been provisioned."
    ::= { xcvrProtSwOpEntry 4 }


xcvrProtSwOpCmd OBJECT-TYPE
    SYNTAX       ProtSwOpCmd
    MAX-ACCESS   read-write
    STATUS       current
    DESCRIPTION  "Used to perform a protection switch on a transceiver facility
                  which is configured to be a part of a protection group, as
                  described in the ProtSwOpCmd textual convention."
    ::= { xcvrProtSwOpEntry 5 }



-----------------------------------------------------------------------
-- Objects related to performing loopback operations on SONET OC-N
-- facilities
-- 
-- The ocnLpbkOpTable is used to perform loopback operations on provisioned
-- SONET OC-N port facilities on muxponder circuit packs. There is one row in the
-- table for each provisioned SONET OC-N port on which a loopback operation can
-- be performed. To perform the loopback operation, set the ocnLpbkOpCmd object
-- to oprFacilityLpbk. To release the loopback, set the ocnLpbkOpCmd object to
-- rlsLpbk.
-- 
-- Note: The loopback operation can only be performed on an OC-N port if the
-- ocnAdminStatus for the port is set to disabled.
-- 
-- The following table lists the objects in each entry of the ocnLpbkOpTable.
-----------------------------------------------------------------------


ocnLpbkOpTable OBJECT-TYPE
    SYNTAX       SEQUENCE OF OcnLpbkOpEntry
    MAX-ACCESS   not-accessible
    STATUS       current
    DESCRIPTION  "This table contains one row for every provisioned OC-N
                  facility on the NE to facilitate the performing loopback
                  operations."
    ::= { ocnOperations 1 }


ocnLpbkOpEntry OBJECT-TYPE
    SYNTAX       OcnLpbkOpEntry
    MAX-ACCESS   not-accessible
    STATUS       current
    DESCRIPTION  "The conceptual row object of the OC-N loopback operation
                  table."
    INDEX        { ocnLpbkOpTypeIdx,
                   ocnLpbkOpShelfIdx,
                   ocnLpbkOpSlotIdx,
                   ocnLpbkOpPortIdx }
    ::= { ocnLpbkOpTable 1 }


OcnLpbkOpEntry ::= SEQUENCE { ocnLpbkOpTypeIdx   OcnType,
                              ocnLpbkOpShelfIdx  INTEGER,
                              ocnLpbkOpSlotIdx   INTEGER,
                              ocnLpbkOpPortIdx   INTEGER,
                              ocnLpbkOpCmd       INTEGER }


ocnLpbkOpTypeIdx OBJECT-TYPE
    SYNTAX       OcnType
    MAX-ACCESS   not-accessible
    STATUS       current
    DESCRIPTION  "The specific type of OC-N signal which is targeted for the
                  loopback operation."
    ::= { ocnLpbkOpEntry 1 }


ocnLpbkOpShelfIdx OBJECT-TYPE
    SYNTAX       INTEGER (1|11|21|31)
    MAX-ACCESS   not-accessible
    STATUS       current
    DESCRIPTION  "The number of the shelf of the OC-N facility targeted for the
                  loopback operation."
    ::= { ocnLpbkOpEntry 2 }


ocnLpbkOpSlotIdx OBJECT-TYPE
    SYNTAX       INTEGER (1..20)
    MAX-ACCESS   not-accessible
    STATUS       current
    DESCRIPTION  "The number of the slot in which the OC-N facility targeted for
                  the loopback operation is provisioned."
    ::= { ocnLpbkOpEntry 3 }


ocnLpbkOpPortIdx OBJECT-TYPE
    SYNTAX       INTEGER (1..6)
    MAX-ACCESS   not-accessible
    STATUS       current
    DESCRIPTION  "The number of the port on the circuit pack on which the OC-N
                  facility targeted for the loopback operation is provisioned."
    ::= { ocnLpbkOpEntry 4 }


ocnLpbkOpCmd OBJECT-TYPE
    SYNTAX       INTEGER { noOp            (1),
                           oprFacilityLpbk (2),
                           rlsLpbk         (3),
                           oprTerminalLpbk (4) }
    MAX-ACCESS   read-write
    STATUS       current
    DESCRIPTION  "Used to perform a loopback operation on a OC-N facility as
                  follows:
                  - oprFacilityLpbk: operates an OC-N facility loopback
                  - oprTerminalLpbk: operates an OC-N terminal loopback
                  - rlsLpbk: releases a previously invoked loopback
                  
                  Note that the terminal loopback can only be operated on a
                  client OC-N facility. When read, this object returns noOp."
    ::= { ocnLpbkOpEntry 5 }
    

ocnProtSwOpTable OBJECT-TYPE
    SYNTAX       SEQUENCE OF OcnProtSwOpEntry
    MAX-ACCESS   not-accessible
    STATUS       current
    DESCRIPTION  "This table contains one row for every provisioned SONET OC-N
                  facility on the NE configured to be part of a protection group
                  pair to facilitate the performing of OC-N line protection
                  switching operations."
    ::= { ocnOperations 2 }


ocnProtSwOpEntry OBJECT-TYPE
    SYNTAX       OcnProtSwOpEntry
    MAX-ACCESS   not-accessible
    STATUS       current
    DESCRIPTION  "The conceptual row object of the SONET OC-N facility
                  protection switching operation table."
    INDEX        { ocnProtSwOpTypeIdx,
                   ocnProtSwOpShelfIdx,
                   ocnProtSwOpSlotIdx,
                   ocnProtSwOpIdx }
    ::= { ocnProtSwOpTable 1 }


OcnProtSwOpEntry ::= SEQUENCE { ocnProtSwOpTypeIdx   OcnType,
                                ocnProtSwOpShelfIdx  INTEGER,
                                ocnProtSwOpSlotIdx   INTEGER,
                                ocnProtSwOpIdx       INTEGER,
                                ocnProtSwOpCmd       INTEGER }


ocnProtSwOpTypeIdx OBJECT-TYPE
    SYNTAX       OcnType
    MAX-ACCESS   not-accessible
    STATUS       current
    DESCRIPTION  "The specific rate of OC-N facility targeted for the
                  protection switching operation."
    ::= { ocnProtSwOpEntry 1 }


ocnProtSwOpShelfIdx OBJECT-TYPE
    SYNTAX       INTEGER (1|11|21|31)
    MAX-ACCESS   not-accessible
    STATUS       current
    DESCRIPTION  "The number of the shelf of the OC-N facility targeted for
                  the protection switching operation."
    ::= { ocnProtSwOpEntry 2 }


ocnProtSwOpSlotIdx OBJECT-TYPE
    SYNTAX       INTEGER (1|3|5|7|9|11|13|15|17|19)
    MAX-ACCESS   not-accessible
    STATUS       current
    DESCRIPTION  "The number of the slot within which the OC-N facility
                  targeted for the protection switching operation is
                  provisioned."
    ::= { ocnProtSwOpEntry 3 }


ocnProtSwOpIdx OBJECT-TYPE
    SYNTAX       INTEGER (1..2)
    MAX-ACCESS   not-accessible
    STATUS       current
    DESCRIPTION  "The number of the port on the circuit pack on which the OC-N
                  facility has been provisioned."
    ::= { ocnProtSwOpEntry 4 }


ocnProtSwOpCmd OBJECT-TYPE
    SYNTAX       ProtSwOpCmd
    MAX-ACCESS   read-write
    STATUS       current
    DESCRIPTION  "Used to perform a protection switch on a OC-N facility which
                  is configured to be a part of a protection group, as described
                  in the ProtSwOpCmd textual convention."
    ::= { ocnProtSwOpEntry 5 }



-----------------------------------------------------------------------
-- Objects related to performing protection switching on SDH STS-N
-- facilities
-- 
-- The stsnProtSwOpTable is used to perform protection switching operations on
-- SONET STS-N path facilities. This table includes a row for every SONET STS-N
-- path facility provisioned as part of a SONET STS-N protection pair. The
-- protection switch operation is performed by setting the stsnProtSwOpCmd object
-- to the object value that corresponds to the desired protection switching operation.
-- 
-- The following table lists the objects in each entry of the stsnProtSwOpTable.
-----------------------------------------------------------------------


stsnProtSwOpTable OBJECT-TYPE
    SYNTAX       SEQUENCE OF StsnProtSwOpEntry
    MAX-ACCESS   not-accessible
    STATUS       current
    DESCRIPTION  "This table contains one row for every created SONET STS-N
                  facility on the system which is part of a protection group
                  pairing to facilitate the performing of STS-N protection
                  switching operations."
    ::= { stsnOperations 1 }


stsnProtSwOpEntry OBJECT-TYPE
    SYNTAX       StsnProtSwOpEntry
    MAX-ACCESS   not-accessible
    STATUS       current
    DESCRIPTION  "The conceptual row object of the SONET STS-N protection
                  switching operation table."
    INDEX        { stsnProtSwOpTypeIdx,
                   stsnProtSwOpShelfIdx,
                   stsnProtSwOpSlotIdx,
                   stsnProtSwOpPortIdx,
                   stsnProtSwOpIdx }
    ::= { stsnProtSwOpTable 1 }


StsnProtSwOpEntry ::= SEQUENCE { stsnProtSwOpTypeIdx   StsnType,
                                 stsnProtSwOpShelfIdx  INTEGER,
                                 stsnProtSwOpSlotIdx   INTEGER,
                                 stsnProtSwOpPortIdx   INTEGER,
                                 stsnProtSwOpIdx       INTEGER,
                                 stsnProtSwOpCmd       INTEGER }


stsnProtSwOpTypeIdx OBJECT-TYPE
    SYNTAX       StsnType
    MAX-ACCESS   not-accessible
    STATUS       current
    DESCRIPTION  "The specific type of STS-N signal targeted for the protection
                  switching operation."
    ::= { stsnProtSwOpEntry 1 }


stsnProtSwOpShelfIdx OBJECT-TYPE
    SYNTAX       INTEGER (1|11|21|31)
    MAX-ACCESS   not-accessible
    STATUS       current
    DESCRIPTION  "The number of the shelf of the STS-N facility targeted for the
                  protection switching operation."
    ::= { stsnProtSwOpEntry 2 }


stsnProtSwOpSlotIdx OBJECT-TYPE
    SYNTAX       INTEGER (1..20)
    MAX-ACCESS   not-accessible
    STATUS       current
    DESCRIPTION  "The number of the slot of the STS-N facility targeted for the
                  protection switching operation."
    ::= { stsnProtSwOpEntry 3 }


stsnProtSwOpPortIdx OBJECT-TYPE
    SYNTAX       INTEGER (1..2)
    MAX-ACCESS   not-accessible
    STATUS       current
    DESCRIPTION  "The number of the port of the STS-N facility targeted for the
                  protection switching operation."
    ::= { stsnProtSwOpEntry 4 }


stsnProtSwOpIdx OBJECT-TYPE
    SYNTAX       INTEGER (1..192)
    MAX-ACCESS   not-accessible
    STATUS       current
    DESCRIPTION  "The sts channel number of the STS-N facility targeted for the
                  protection switching operation."
    ::= { stsnProtSwOpEntry 5 }


stsnProtSwOpCmd OBJECT-TYPE
    SYNTAX       ProtSwOpCmd
    MAX-ACCESS   read-write
    STATUS       current
    DESCRIPTION  "Used to perform a protection switch on a STS-N facility which
                  is part of a protection group pairing, as described in the
                  ProtSwOpCmd textual convention."
    ::= { stsnProtSwOpEntry 6 }


-----------------------------------------------------------------------
-- Objects related to performing loopback operations on SDH STM-N
-- facilities
-- 
-- The stmnLpbkOpTable is used to perform loopback operations on provisioned
-- SDH STM-N port facilities on muxponder circuit packs. There is one row in the
-- table for each provisioned SDH STM-N port on which a loopback operation can
-- be performed. To perform the loopback operation, set the stmnLpbkOpCmd object
-- to oprFacilityLpbk. To release the loopback, set the smtnLpbkOpCmd object to
-- rlsLpbk.
-- 
-- Note: The loopback operation can only be performed on a transceiver port if the
-- stmnAdminStatus for the port is set to disabled.
-- 
-- The following table lists the objects in each entry of the stmnLpbkOpTable.
-----------------------------------------------------------------------


stmnLpbkOpTable OBJECT-TYPE
    SYNTAX       SEQUENCE OF StmnLpbkOpEntry
    MAX-ACCESS   not-accessible
    STATUS       current
    DESCRIPTION  "This table contains one row for every provisioned STM-N
                  facility on the NE to facilitate the performing of STM-N
                  facility loopback operations."
    ::= { stmnOperations 1 }


stmnLpbkOpEntry OBJECT-TYPE
    SYNTAX       StmnLpbkOpEntry
    MAX-ACCESS   not-accessible
    STATUS       current
    DESCRIPTION  "The conceptual row object of the STM-N loopback operation
                  table."
    INDEX        { stmnLpbkOpTypeIdx,
                   stmnLpbkOpShelfIdx,
                   stmnLpbkOpSlotIdx,
                   stmnLpbkOpPortIdx }
    ::= { stmnLpbkOpTable 1 }


StmnLpbkOpEntry ::= SEQUENCE { stmnLpbkOpTypeIdx   StmnType,
                               stmnLpbkOpShelfIdx  INTEGER,
                               stmnLpbkOpSlotIdx   INTEGER,
                               stmnLpbkOpPortIdx   INTEGER,
                               stmnLpbkOpCmd       INTEGER }


stmnLpbkOpTypeIdx OBJECT-TYPE
    SYNTAX       StmnType
    MAX-ACCESS   not-accessible
    STATUS       current
    DESCRIPTION  "The specific type of STM-N signal which is targeted for the
                  loopback operation."
    ::= { stmnLpbkOpEntry 1 }


stmnLpbkOpShelfIdx OBJECT-TYPE
    SYNTAX       INTEGER (1|11|21|31)
    MAX-ACCESS   not-accessible
    STATUS       current
    DESCRIPTION  "The number of the shelf of the STM-N facility targeted for the
                  loopback operation."
    ::= { stmnLpbkOpEntry 2 }


stmnLpbkOpSlotIdx OBJECT-TYPE
    SYNTAX       INTEGER (1..20)
    MAX-ACCESS   not-accessible
    STATUS       current
    DESCRIPTION  "The number of the slot in which the STM-N facility targeted
                  for the loopback operation is provisioned."
    ::= { stmnLpbkOpEntry 3 }


stmnLpbkOpPortIdx OBJECT-TYPE
    SYNTAX       INTEGER (1..6)
    MAX-ACCESS   not-accessible
    STATUS       current
    DESCRIPTION  "The number of the port on the circuit pack on which the STM-N
                  facility targeted for the loopback operation is provisioned."
    ::= { stmnLpbkOpEntry 4 }


stmnLpbkOpCmd OBJECT-TYPE
    SYNTAX       INTEGER { noOp            (1),
                           oprFacilityLpbk (2),
                           rlsLpbk         (3),
                           oprTerminalLpbk (4) }
    MAX-ACCESS   read-write
    STATUS       current
    DESCRIPTION  "Used to perform a loopback operation on a STM-N facility as
                  follows:
                  - oprFacilityLpbk: operates an STM-N facility loopback
                  - oprTerminalLpbk: operates an STM-N terminal loopback
                  - rlsLpbk: releases a previously invoked loopback
                  
                  Note that a terminal loopback can only be operated on a client
                  STM-N facility. When read, this object returns noOp."
    ::= { stmnLpbkOpEntry 5 }


stmnProtSwOpTable OBJECT-TYPE
    SYNTAX       SEQUENCE OF StmnProtSwOpEntry
    MAX-ACCESS   not-accessible
    STATUS       current
    DESCRIPTION  "This table contains one row for every provisioned SDH STM-N
                  facility on the NE configured to be part of a protection group
                  pair to facilitate the performing of STM-N line protection
                  switching operations."
    ::= { stmnOperations 2 }


stmnProtSwOpEntry OBJECT-TYPE
    SYNTAX       StmnProtSwOpEntry
    MAX-ACCESS   not-accessible
    STATUS       current
    DESCRIPTION  "The conceptual row object of the SDH STM-N facility
                  protection switching operation table."
    INDEX        { stmnProtSwOpTypeIdx,
                   stmnProtSwOpShelfIdx,
                   stmnProtSwOpSlotIdx,
                   stmnProtSwOpIdx }
    ::= { stmnProtSwOpTable 1 }


StmnProtSwOpEntry ::= SEQUENCE { stmnProtSwOpTypeIdx   StmnType,
                                 stmnProtSwOpShelfIdx  INTEGER,
                                 stmnProtSwOpSlotIdx   INTEGER,
                                 stmnProtSwOpIdx       INTEGER,
                                 stmnProtSwOpCmd       INTEGER }


stmnProtSwOpTypeIdx OBJECT-TYPE
    SYNTAX       StmnType
    MAX-ACCESS   not-accessible
    STATUS       current
    DESCRIPTION  "The specific rate of STM-N facility targeted for the
                  protection switching operation."
    ::= { stmnProtSwOpEntry 1 }


stmnProtSwOpShelfIdx OBJECT-TYPE
    SYNTAX       INTEGER (1|11|21|31)
    MAX-ACCESS   not-accessible
    STATUS       current
    DESCRIPTION  "The number of the shelf of the STM-N faacility targeted for
                  the protection switching operation."
    ::= { stmnProtSwOpEntry 2 }


stmnProtSwOpSlotIdx OBJECT-TYPE
    SYNTAX       INTEGER (1|3|5|7|9|11|13|15|17|19)
    MAX-ACCESS   not-accessible
    STATUS       current
    DESCRIPTION  "The number of the slot within which the STM-N facility
                  targeted for the protection switching operation is
                  provisioned."
    ::= { stmnProtSwOpEntry 3 }


stmnProtSwOpIdx OBJECT-TYPE
    SYNTAX       INTEGER (1..2)
    MAX-ACCESS   not-accessible
    STATUS       current
    DESCRIPTION  "The number of the port on the circuit pack on which the STM-N
                  facility has been provisioned."
    ::= { stmnProtSwOpEntry 4 }


stmnProtSwOpCmd OBJECT-TYPE
    SYNTAX       ProtSwOpCmd
    MAX-ACCESS   read-write
    STATUS       current
    DESCRIPTION  "Used to perform a protection switch on a STM-N facility which
                  is configured to be a part of a protection group, as described
                  in the ProtSwOpCmd textual convention."
    ::= { stmnProtSwOpEntry 5 }



-----------------------------------------------------------------------
-- Objects related to performing protection switching operations on SDH VC-N
-- facilities
-- 
-- The vcnProtSwOpTable is used to perform protection switching operations on
-- SDH VC-N path facilities. This table includes a row for every SDH VC-N path
-- facility provisioned as part of a VC-N protection pair. The protection switch
-- operation is performed by setting the vcnProtSwOpCmd object to the object value
-- that corresponds to the desired protection switching operation.
-- 
-- The following table lists the objects in each entry of the vcnProtSwOpTable.
-----------------------------------------------------------------------


vcnProtSwOpTable OBJECT-TYPE
    SYNTAX       SEQUENCE OF VcnProtSwOpEntry
    MAX-ACCESS   not-accessible
    STATUS       current
    DESCRIPTION  "This table contains one row for every created SDH VC-N
                  facility on the system which is part of a protection group
                  pairing to facilitate the performing of VC-N protection
                  switching operations."
    ::= { vcnOperations 1 }


vcnProtSwOpEntry OBJECT-TYPE
    SYNTAX       VcnProtSwOpEntry
    MAX-ACCESS   not-accessible
    STATUS       current
    DESCRIPTION  "The conceptual row object of the SDH VC-N protection switching
                  operation table."
    INDEX        { vcnProtSwOpTypeIdx,
                   vcnProtSwOpShelfIdx,
                   vcnProtSwOpSlotIdx,
                   vcnProtSwOpPortIdx,
                   vcnProtSwOpIdx }
    ::= { vcnProtSwOpTable 1 }


VcnProtSwOpEntry ::= SEQUENCE { vcnProtSwOpTypeIdx   VcnType,
                                vcnProtSwOpShelfIdx  INTEGER,
                                vcnProtSwOpSlotIdx   INTEGER,
                                vcnProtSwOpPortIdx   INTEGER,
                                vcnProtSwOpIdx       INTEGER,
                                vcnProtSwOpCmd       INTEGER }


vcnProtSwOpTypeIdx OBJECT-TYPE
    SYNTAX       VcnType
    MAX-ACCESS   not-accessible
    STATUS       current
    DESCRIPTION  "The specific type of VC-N signal targeted for the protection
                  switching operation."
    ::= { vcnProtSwOpEntry 1 }


vcnProtSwOpShelfIdx OBJECT-TYPE
    SYNTAX       INTEGER (1|11|21|31)
    MAX-ACCESS   not-accessible
    STATUS       current
    DESCRIPTION  "The number of the shelf of the VC-N facility targeted for the
                  protection switching operation."
    ::= { vcnProtSwOpEntry 2 }


vcnProtSwOpSlotIdx OBJECT-TYPE
    SYNTAX       INTEGER (1..20)
    MAX-ACCESS   not-accessible
    STATUS       current
    DESCRIPTION  "The number of the slot of the VC-N facility targeted for the
                  protection switching operation."
    ::= { vcnProtSwOpEntry 3 }


vcnProtSwOpPortIdx OBJECT-TYPE
    SYNTAX       INTEGER (1..2)
    MAX-ACCESS   not-accessible
    STATUS       current
    DESCRIPTION  "The number of the port of the VC-N facility targeted for the
                  protection switching operation."
    ::= { vcnProtSwOpEntry 4 }


vcnProtSwOpIdx OBJECT-TYPE
    SYNTAX       INTEGER (1..64)
    MAX-ACCESS   not-accessible
    STATUS       current
    DESCRIPTION  "The index number of the VC-N facility targeted for the
                  protection switching operation."
    ::= { vcnProtSwOpEntry 5 }


vcnProtSwOpCmd OBJECT-TYPE
    SYNTAX       ProtSwOpCmd
    MAX-ACCESS   read-write
    STATUS       current
    DESCRIPTION  "Used to perform a protection switch on a VC-N facility which
                  is part of a protection group pairing, as described in the
                  ProtSwOpCmd textual convention."
    ::= { vcnProtSwOpEntry 6 }



-----------------------------------------------------------------------
-- Objects related to performing operations on Gigabit Ethernet
-- facilities
-- 
-- The geLpbkOpTable is used to perform loopback operations on provisioned
-- Gigabit Ethernet port facilities on muxponder circuit packs. There is one row in
-- the table for each provisioned Gigabit Ethernet port on which a loopback operation
-- can be performed. To perform the loopback operation, set the geLpbkOpCmd
-- object to either oprFacilityLpbk or oprTerminalLpbk. To release the loopback, set
-- the smtnLpbkOpCmd object to rlsLpbk.
-- 
-- Note: The loopback operation can only be performed on a transceiver port if the
-- geAdminStatus for the port is set to disabled.
-- 
-- The following table lists the objects in each entry of the geLpbkOpTable.
-----------------------------------------------------------------------


geLpbkOpTable OBJECT-TYPE
    SYNTAX       SEQUENCE OF GeLpbkOpEntry
    MAX-ACCESS   not-accessible
    STATUS       current
    DESCRIPTION  "This table contains one row for every provisioned Gigabit
                  Ethernet facility on the NE to facilitate the performing of GE
                  facility loopback operations."
    ::= { geOperations 1 }


geLpbkOpEntry OBJECT-TYPE
    SYNTAX       GeLpbkOpEntry
    MAX-ACCESS   not-accessible
    STATUS       current
    DESCRIPTION  "The conceptual row object of the Gigabit Ethernet loopback
                  operation table."
    INDEX        { geLpbkOpShelfIdx,
                   geLpbkOpSlotIdx,
                   geLpbkOpPortIdx }
    ::= { geLpbkOpTable 1 }


GeLpbkOpEntry ::= SEQUENCE { geLpbkOpShelfIdx  INTEGER,
                             geLpbkOpSlotIdx   INTEGER,
                             geLpbkOpPortIdx   INTEGER,
                             geLpbkOpCmd       INTEGER }


geLpbkOpShelfIdx OBJECT-TYPE
    SYNTAX       INTEGER (1|11|21|31)
    MAX-ACCESS   not-accessible
    STATUS       current
    DESCRIPTION  "The number of the shelf of the Gigabit Ethernet facility
                  targeted for the loopback operation."
    ::= { geLpbkOpEntry 1 }


geLpbkOpSlotIdx OBJECT-TYPE
    SYNTAX       INTEGER (1..20)
    MAX-ACCESS   not-accessible
    STATUS       current
    DESCRIPTION  "The number of the slot in which the Gigabit Ethernet facility
                  targeted for the loopback operation is provisioned."
    ::= { geLpbkOpEntry 2 }


geLpbkOpPortIdx OBJECT-TYPE
    SYNTAX       INTEGER (3..12)
    MAX-ACCESS   not-accessible
    STATUS       current
    DESCRIPTION  "The number of the port on the circuit pack on which the
                  Gigabit Ethernet facility targeted for the loopback operation
                  is provisioned."
    ::= { geLpbkOpEntry 3 }


geLpbkOpCmd OBJECT-TYPE
    SYNTAX       INTEGER { noOp            (1),
                           oprFacilityLpbk (2),
                           oprTerminalLpbk (3),
                           rlsLpbk         (4) }
    MAX-ACCESS   read-write
    STATUS       current
    DESCRIPTION  "Used to perform a loopback operation on a Gigabit Ethernet
                  facility as follows:
                  - oprFacilityLpbk: operates an GE facility loopback
                  - oprFacilityLpbk: operates an GE terminal loopback
                  - rlsLpbk: releases a previously invoked loopback
                  
                  When read, this object returns noOp."
    ::= { geLpbkOpEntry 4 }



-----------------------------------------------------------------------
-- Objects related to performing operations on Fiber Channel
-- facilities
-----------------------------------------------------------------------


fcLpbkOpTable OBJECT-TYPE
    SYNTAX       SEQUENCE OF FcLpbkOpEntry
    MAX-ACCESS   not-accessible
    STATUS       current
    DESCRIPTION  "This table contains one row for every provisioned Fiber
                  Channel facility on the NE to facilitate the performing of FC
                  facility loopback operations."
    ::= { fcOperations 1 }


fcLpbkOpEntry OBJECT-TYPE
    SYNTAX       FcLpbkOpEntry
    MAX-ACCESS   not-accessible
    STATUS       current
    DESCRIPTION  "The conceptual row object of the Fiber Channel loopback
                  operation table."
    INDEX        { fcLpbkOpShelfIdx,
                   fcLpbkOpSlotIdx,
                   fcLpbkOpPortIdx }
    ::= { fcLpbkOpTable 1 }


FcLpbkOpEntry ::= SEQUENCE { fcLpbkOpShelfIdx  INTEGER,
                             fcLpbkOpSlotIdx   INTEGER,
                             fcLpbkOpPortIdx   INTEGER,
                             fcLpbkOpCmd       INTEGER }


fcLpbkOpShelfIdx OBJECT-TYPE
    SYNTAX       INTEGER (1|11|21|31)
    MAX-ACCESS   not-accessible
    STATUS       current
    DESCRIPTION  "The number of the shelf of the Fiber Channel facility targeted
                  for the loopback operation."
    ::= { fcLpbkOpEntry 1 }


fcLpbkOpSlotIdx OBJECT-TYPE
    SYNTAX       INTEGER (1|3|5|7|9|11|13|15|17|19)
    MAX-ACCESS   not-accessible
    STATUS       current
    DESCRIPTION  "The number of the slot in which the Fiber Channel facility
                  targeted for the loopback operation is provisioned."
    ::= { fcLpbkOpEntry 2 }


fcLpbkOpPortIdx OBJECT-TYPE
    SYNTAX       INTEGER (3..12)
    MAX-ACCESS   not-accessible
    STATUS       current
    DESCRIPTION  "The number of the port on the circuit pack on which the Fiber
                  Channel facility targeted for the loopback operation is
                  provisioned."
    ::= { fcLpbkOpEntry 3 }


fcLpbkOpCmd OBJECT-TYPE
    SYNTAX       INTEGER { noOp            (1),
                           oprFacilityLpbk (2),
                           oprTerminalLpbk (3),
                           rlsLpbk         (4) }
    MAX-ACCESS   read-write
    STATUS       current
    DESCRIPTION  "Used to perform a loopback operation on a Fiber Channel
                  facility as follows:
                  - oprFacilityLpbk: operates an FC facility loopback
                  - oprFacilityLpbk: operates an FC terminal loopback
                  - rlsLpbk: releases a previously invoked loopback
                  
                  When read, this object returns noOp."
    ::= { fcLpbkOpEntry 4 }


-----------------------------------------------------------------------
-- Objects related to performing operations on Bit Rate Independent
-- (BRI) facilities
-----------------------------------------------------------------------


briLpbkOpTable OBJECT-TYPE
    SYNTAX       SEQUENCE OF BriLpbkOpEntry
    MAX-ACCESS   not-accessible
    STATUS       current
    DESCRIPTION  "This table contains one row for every provisioned 
                  Bit Rate Independent (BRI) facility on the NE to 
                  facilitate the performing of BRI facility loopback 
                  operations."
    ::= { briOperations 1 }


briLpbkOpEntry OBJECT-TYPE
    SYNTAX       BriLpbkOpEntry
    MAX-ACCESS   not-accessible
    STATUS       current
    DESCRIPTION  "The conceptual row object of the BRI loopback
                  operation table."
    INDEX        { briLpbkOpShelfIdx,
                   briLpbkOpSlotIdx,
                   briLpbkOpPortIdx }
    ::= { briLpbkOpTable 1 }


BriLpbkOpEntry ::= SEQUENCE { briLpbkOpShelfIdx  INTEGER,
                              briLpbkOpSlotIdx   INTEGER,
                              briLpbkOpPortIdx   INTEGER,
                              briLpbkOpCmd       INTEGER }


briLpbkOpShelfIdx OBJECT-TYPE
    SYNTAX       INTEGER (1|11|21|31)
    MAX-ACCESS   not-accessible
    STATUS       current
    DESCRIPTION  "The number of the shelf of the BRI facility targeted
                  for the loopback operation."
    ::= { briLpbkOpEntry 1 }


briLpbkOpSlotIdx OBJECT-TYPE
    SYNTAX       INTEGER (1|3|5|7|9|11|13|15|17|19)
    MAX-ACCESS   not-accessible
    STATUS       current
    DESCRIPTION  "The number of the slot in which the BRI facility
                  targeted for the loopback operation is provisioned."
    ::= { briLpbkOpEntry 2 }


briLpbkOpPortIdx OBJECT-TYPE
    SYNTAX       INTEGER (3..12)
    MAX-ACCESS   not-accessible
    STATUS       current
    DESCRIPTION  "The number of the port on the circuit pack on which the
                  BRI facility targeted for the loopback operation is
                  provisioned."
    ::= { briLpbkOpEntry 3 }


briLpbkOpCmd OBJECT-TYPE
    SYNTAX       INTEGER { noOp            (1),
                           oprFacilityLpbk (2),
                           oprTerminalLpbk (3),
                           rlsLpbk         (4) }
    MAX-ACCESS   read-write
    STATUS       current
    DESCRIPTION  "Used to perform a loopback operation on a BRI
                  facility as follows:
                  - oprFacilityLpbk: operates a BRI facility loopback
                  - oprFacilityLpbk: operates a BRI terminal loopback
                  - rlsLpbk: releases a previously invoked loopback
                  
                  When read, this object returns noOp."
    ::= { briLpbkOpEntry 4 }


-----------------------------------------------------------------------
-- Objects used to control management operations related to data
-- communications
-----------------------------------------------------------------------


DataCommsPingCmd ::= TEXTUAL-CONVENTION
    STATUS       current
    DESCRIPTION  "The DataCommsPingCmd textual convention is the value of the
                  dataCommsPingCmd object which is used to perform a ping
                  operation over the NE's OSC. The operation is initiated when a
                  set request is performed on the dataCommsPingCmd object with a
                  value corresponding to the ping action, as explained below.
                  
                  The valid values for DataCommsPingCmd that can be used in a
                  set operation are:
                  - 'ping', used to trigger the ping operation over the OSC
                  
                  A value of 'pingInProgress' is returned when the
                  dataCommsPingCmd object is read in a get operation if the ping
                  command entered has not yet completed, otherwise 'noOp' is
                  returned.
                  
                  In order for the set request on a DataCommsPingCmd object to
                  complete successfully, the dataCommsPingCmd object, along with
                  the dataCommdPingAddress and optionally the
                  dataCommsPingNumAttemps objects must be set in the same set
                  
                  request for a given row of the table. The purpose of these
                  objects is:
                  - dataCommsPingAddress: indicates the IP Address which is the
                  target of the ping operation
                  - dataCommsPingNumAttempts: indicates how many ping attempts
                  are to be made in the ping operation
                  
                  Once the dataCommsPingCmd operation is completed by way of the
                  set operation on the dataCommsPingCmd and associated objects,
                  the result of the operation is checked by performing a get
                  operation on the dataCommsPingNumSuccesses object. When the
                  ping operation completes, the value of this object will be set
                  to the number of the attempted ping trials that resulted in a
                  successful ping."
    SYNTAX       INTEGER { noOp           (1),
                           ping           (2),
                           pingInProgress (3) }



						   

						   
-----------------------------------------------------------------------
-- Objects used to perform ping operations
-- 
-- The dataCommsPingTable is used to perform ping operations from the MSCP
-- circuit pack over the Optical Supervisory Channel (OSC) or a network
-- management interface of the BTI 7000 Series. This table includes a row for every
-- provisioned circuit pack on the BTI 7000 Series from which an IP ping request can
-- be sent. 
-- 
-- The following table lists the objects in each entry of the dataCommsPingTable.
-----------------------------------------------------------------------
dataCommsPingTable OBJECT-TYPE
    SYNTAX       SEQUENCE OF DataCommsPingEntry
    MAX-ACCESS   not-accessible
    STATUS       current
    DESCRIPTION  "This table contains one row for every provisioned circuit pack
                  on the NE from which an IP ping request can be sent. This
                  includes all SCP and OSC type packs."
    ::= { dataCommsOperations 1 }


dataCommsPingEntry OBJECT-TYPE
    SYNTAX       DataCommsPingEntry
    MAX-ACCESS   not-accessible
    STATUS       current
    DESCRIPTION  "The conceptual row object of the data comms ping table."
    INDEX        { dataCommsPingCpTypeIdx,
                   dataCommsPingShelfIdx,
                   dataCommsPingSlotIdx }

    ::= { dataCommsPingTable 1 }


DataCommsPingEntry ::= SEQUENCE { dataCommsPingCpTypeIdx     CpType,
                                  dataCommsPingShelfIdx      INTEGER,
                                  dataCommsPingSlotIdx       INTEGER,
                                  dataCommsPingCmd           INTEGER,
                                  dataCommsPingAddress       IpAddress,
                                  dataCommsPingNumAttempts   INTEGER,
                                  dataCommsPingNumSuccesses  INTEGER }


dataCommsPingCpTypeIdx OBJECT-TYPE
    SYNTAX       CpType
    MAX-ACCESS   not-accessible
    STATUS       current
    DESCRIPTION  "This object is used to indicate the type of circuit pack from
                  which the ping operation is to be conducted using the
                  dataCommsPingCmd object."
    ::= { dataCommsPingEntry 1 }


dataCommsPingShelfIdx OBJECT-TYPE
    SYNTAX       INTEGER (1|11|21|31)
    MAX-ACCESS   not-accessible
    STATUS       current
    DESCRIPTION  "This object is used to indicate the shelf number containing
                  the circuit pack from which the ping operation is to be
                  conducted using the dataCommsPingCmd object."
    ::= { dataCommsPingEntry 2 }


dataCommsPingSlotIdx OBJECT-TYPE
    SYNTAX       INTEGER (1..20)
    MAX-ACCESS   not-accessible
    STATUS       current
    DESCRIPTION  "This object is used to indicate the slot number containing the
                  circuit pack from which the ping operation is to be conducted
                  using the dataCommsPingCmd object."
    ::= { dataCommsPingEntry 3 }


dataCommsPingCmd OBJECT-TYPE
    SYNTAX       DataCommsPingCmd
    MAX-ACCESS   read-write
    STATUS       current
    DESCRIPTION  "This object is used to trigger a ping operation from an OSC or
                  SCP circuit pack. The description of DataCommsPingCmd textual
                  convention explains the usage of this object to perform the
                  ping operation."
    ::= { dataCommsPingEntry 4 }


dataCommsPingAddress OBJECT-TYPE
    SYNTAX       IpAddress
    MAX-ACCESS   read-write
    STATUS       current
    DESCRIPTION  "This object is used to indicate the IP Address which is the
                  target of the ping operation to be conducted using the
                  dataCommsPingCmd object."
    ::= { dataCommsPingEntry 5 }


dataCommsPingNumAttempts OBJECT-TYPE
    SYNTAX       INTEGER ( 1..3 )
    MAX-ACCESS   read-write
    STATUS       current
    DESCRIPTION  "This object is used to indicate how many ping attempts are to
                  be made in the ping operation to be conducted using the
                  dataCommsPingCmd object. The default is 3."
    ::= { dataCommsPingEntry 6 }


dataCommsPingNumSuccesses OBJECT-TYPE
    SYNTAX       INTEGER ( 0..3 )
    MAX-ACCESS   read-only
    STATUS       current
    DESCRIPTION  "This object is used to indicate how many ping trials attempted
                  in the ping operation resulted in a successful ping
                  completion."
    ::= { dataCommsPingEntry 7 }



-----------------------------------------------------------------------
-- Objects related to provisioning SONET Synchronization Attributes
-----------------------------------------------------------------------


cpSynchronizationTable OBJECT-TYPE
    SYNTAX       SEQUENCE OF CpSynchronizationEntry
    MAX-ACCESS   not-accessible
    STATUS       current
    DESCRIPTION  "This table contains one row for every provisioned circuit pack
                  that supports SONET synchronization configuration."
    ::= { synchronization 1 }


cpSynchronizationEntry OBJECT-TYPE
    SYNTAX       CpSynchronizationEntry
    MAX-ACCESS   not-accessible
    STATUS       current
    DESCRIPTION  "The conceptual row object of the circuit pack synchronization
                  table."
    INDEX        { cpSynchronizationTypeIdx,
                   cpSynchronizationShelfIdx,
                   cpSynchronizationSlotIdx }
    ::= { cpSynchronizationTable 1 }


CpSynchronizationEntry ::= SEQUENCE { cpSynchronizationTypeIdx            CpType,
                                      cpSynchronizationShelfIdx           INTEGER,
                                      cpSynchronizationSlotIdx            INTEGER,
                                      cpSynchronizationTimingMode         INTEGER,
                                      cpSynchronizationPrimRefSrcPortNum  INTEGER,
                                      cpSynchronizationPrimRefProtStatus  ProtectionStatusType,
                                      cpSynchronizationPrimProtStatQlfr   OperStatQlfr,
                                      cpSynchronizationSecRefSrcPortNum   INTEGER,
                                      cpSynchronizationSecRefProtStatus   ProtectionStatusType,
                                      cpSynchronizationSecProtStatQlfr    OperStatQlfr,
                                      cpSynchronizationPrimRefBasicSSM    INTEGER,
                                      cpSynchronizationSecRefBasicSSM     INTEGER,
                                      cpSynchronizationSwEvtType          SyncSwEvtType
                                       }


cpSynchronizationTypeIdx OBJECT-TYPE
    SYNTAX       CpType
    MAX-ACCESS   not-accessible
    STATUS       current
    DESCRIPTION  "The specific type of circuit pack provisioned."
    ::= { cpSynchronizationEntry 1 }


cpSynchronizationShelfIdx OBJECT-TYPE
    SYNTAX       INTEGER (1|11|21|31)
    MAX-ACCESS   not-accessible
    STATUS       current
    DESCRIPTION  "The number of the shelf on which the circuit pack is
                  provisioned."
    ::= { cpSynchronizationEntry 2 }


cpSynchronizationSlotIdx OBJECT-TYPE
    SYNTAX       INTEGER (1..20)
    MAX-ACCESS   not-accessible
    STATUS       current
    DESCRIPTION  "The number of the slot in which the circuit pack is
                  provisioned."
    ::= { cpSynchronizationEntry 3 }


cpSynchronizationTimingMode OBJECT-TYPE
    SYNTAX       INTEGER { internal (1),
                           line     (2) }
    MAX-ACCESS   read-write
    STATUS       current
    DESCRIPTION  "The timing mode used for SONET synchronization on the pack."
    ::= { cpSynchronizationEntry 4 }


cpSynchronizationPrimRefSrcPortNum OBJECT-TYPE
    SYNTAX       INTEGER (0..4)
    MAX-ACCESS   read-write
    STATUS       current
    DESCRIPTION  "The port number of the SONET facility that serves as the
                  primary timing reference source. When the value is 0, the
                  primary reference is not configured."
    ::= { cpSynchronizationEntry 5 }


cpSynchronizationPrimRefProtStatus OBJECT-TYPE
    SYNTAX       ProtectionStatusType
    MAX-ACCESS   read-only
    STATUS       current
    DESCRIPTION  "The protection status of the primary timing reference source."
    ::= { cpSynchronizationEntry 6 }


cpSynchronizationPrimProtStatQlfr OBJECT-TYPE
    SYNTAX       OperStatQlfr
    MAX-ACCESS   read-only
    STATUS       current
    DESCRIPTION  "A textual list of qualifiers of the reported protection status
                  of the primary timing reference source."
    ::= { cpSynchronizationEntry 7 }


cpSynchronizationSecRefSrcPortNum OBJECT-TYPE
    SYNTAX       INTEGER (0..4)
    MAX-ACCESS   read-write
    STATUS       current
    DESCRIPTION  "The port number of the SONET facility that serves as the
                  secondary timing reference source. When the value is 0, the
                  secondary reference is not configured."
    ::= { cpSynchronizationEntry 8 }


cpSynchronizationSecRefProtStatus OBJECT-TYPE
    SYNTAX       ProtectionStatusType
    MAX-ACCESS   read-only
    STATUS       current
    DESCRIPTION  "The protection status of the secondary timing reference
                  source."
    ::= { cpSynchronizationEntry 9 }


cpSynchronizationSecProtStatQlfr OBJECT-TYPE
    SYNTAX       OperStatQlfr
    MAX-ACCESS   read-only
    STATUS       current
    DESCRIPTION  "A textual list of qualifiers of the reported protection status
                  of the secondary timing reference source."
    ::= { cpSynchronizationEntry 10 }
    
cpSynchronizationPrimRefBasicSSM OBJECT-TYPE
    SYNTAX       INTEGER { yes (1),
                           no  (2) }
    MAX-ACCESS   read-write
    STATUS       current
    DESCRIPTION  "Used to enable basic Synchronization Status Messaging (SSM) 
                  functionality on the primary timing reference source."
    DEFVAL       { no }
    ::= { cpSynchronizationEntry 11 }
    
cpSynchronizationSecRefBasicSSM OBJECT-TYPE
    SYNTAX       INTEGER { yes (1),
                           no  (2) }
    MAX-ACCESS   read-write
    STATUS       current
    DESCRIPTION  "Used to enable basic Synchronization Status Messaging (SSM)
                  functionality on the primary timing reference source."
    DEFVAL       { no }
    ::= { cpSynchronizationEntry 12 }
    
cpSynchronizationSwEvtType OBJECT-TYPE
    SYNTAX       SyncSwEvtType
    MAX-ACCESS   accessible-for-notify
    STATUS       current
    DESCRIPTION  "Indicates the type of timing reference switching event that
                  has occurred on the circuit pack."
    ::= { cpSynchronizationEntry 13 }



-----------------------------------------------------------------------
-- Objects related to the network topology
-- 
-- The BTI 7000 Series supports network neighbor entries through the
-- networkNeighborTable.
-- 
-- The following table lists the objects relating to the 
-- networkNeighborTable operation.
-----------------------------------------------------------------------


networkNeighborTable OBJECT-TYPE
    SYNTAX       SEQUENCE OF NetworkNeighborEntry
    MAX-ACCESS   not-accessible
    STATUS       current
    DESCRIPTION  "This table is used to store information on the network
                  neighbors of the local network element. Each row contains
                  information on a specific network neighbor."
    ::= { topology 1 }


networkNeighborEntry OBJECT-TYPE
    SYNTAX       NetworkNeighborEntry
    MAX-ACCESS   not-accessible
    STATUS       current
    DESCRIPTION  "The conceptual row object of the network neighbor table."
    INDEX        { networkNeighborIdx }
    ::= { networkNeighborTable 1 }


NetworkNeighborEntry ::= SEQUENCE { networkNeighborIdx        DisplayString,
                                    networkNeighborIPAddr     IpAddress,
                                    networkNeighborRowStatus  RowStatus }


networkNeighborIdx OBJECT-TYPE
    SYNTAX       DisplayString (SIZE (1..32))
    MAX-ACCESS   not-accessible
    STATUS       current
    DESCRIPTION  "A textual identifier of the network neighbor."
    ::= { networkNeighborEntry 1 }


networkNeighborIPAddr OBJECT-TYPE
    SYNTAX       IpAddress
    MAX-ACCESS   read-create
    STATUS       current
    DESCRIPTION  "The primary IP Address of the network neighbor."
    ::= { networkNeighborEntry 2 }


networkNeighborRowStatus OBJECT-TYPE
    SYNTAX       RowStatus
    MAX-ACCESS   read-create
    STATUS       current
    DESCRIPTION  "Used to control the addition and deletion of entries in the
                  network neighbor table."
    ::= { networkNeighborEntry 3 }


-----------------------------------------------------------------------
-- OSPF objects
-- 
-----------------------------------------------------------------------
ospfGeneralTable  OBJECT-TYPE
    SYNTAX        SEQUENCE OF OspfGeneralGroupEntry
    MAX-ACCESS    not-accessible
    STATUS        current
    DESCRIPTION   "This table contains all of general OSPF parameters
                   for the network element. The group can be created
                   and deleted but only one entry can exist in the table."
    ::= {topology 2}

ospfGeneralGroupEntry  OBJECT-TYPE
    SYNTAX        OspfGeneralGroupEntry
    MAX-ACCESS    not-accessible
    STATUS        current
    DESCRIPTION   "The list entry for the OSPF General Group parameters."
    INDEX         { ospfIdx }
    ::= {ospfGeneralTable 1}

OspfGeneralGroupEntry ::= SEQUENCE  { ospfIdx              INTEGER,
                                      ospfRouterId         IpAddress,
                                      ospfAdminStat        INTEGER,
                                      ospfVersionNumber    INTEGER,
                                      ospfAreaBdrRtrStatus TruthValue,
                                      ospfRouteRedist      INTEGER,
                                      ospfAreaId           AreaID,
                                      ospfRowStatus        RowStatus }

ospfIdx OBJECT-TYPE
       SYNTAX       INTEGER (1)
       MAX-ACCESS   not-accessible
       STATUS       current
       DESCRIPTION  "An index used to identify the OSPF instance in order to 
                     alow for creation and deletion to allow compatibility with
                     TL1 and CLI interfaces. Note the value is always 1."
        DEFVAL  { 1 }
       ::= { ospfGeneralGroupEntry 1 }

ospfRouterId OBJECT-TYPE
       SYNTAX       IpAddress
       MAX-ACCESS   read-create
       STATUS       current
       DESCRIPTION  "A 32-bit integer uniquely identifying the router.
                     By convention, to ensure uniqueness, this
                     should default to the value of one of the
                     router's IP interface addresses.
                     This object is persistent."
       ::= { ospfGeneralGroupEntry 2 }

ospfAdminStat OBJECT-TYPE
    SYNTAX       INTEGER { enabled (1), disabled (2) }
    MAX-ACCESS   read-create
    STATUS       current
    DESCRIPTION  "The administrative status of OSPF in the
                  router.  The value 'enabled' denotes that the
                  OSPF Process is active on at least one interface;
                  'disabled' disables it on all interfaces.
                  This object is persistent."
    DEFVAL       { enabled }
       ::= { ospfGeneralGroupEntry 3 }

ospfVersionNumber OBJECT-TYPE
    SYNTAX       INTEGER { version2 (2) }
    MAX-ACCESS   read-only
    STATUS       current
    DESCRIPTION  "The current version number of the OSPF protocol is 2."
    ::= { ospfGeneralGroupEntry 4 }

ospfAreaBdrRtrStatus OBJECT-TYPE
    SYNTAX       TruthValue
    MAX-ACCESS   read-only
    STATUS       current
    DESCRIPTION "A flag to note whether this router is an Area Border Router."
    ::= { ospfGeneralGroupEntry 5 }

ospfRouteRedist OBJECT-TYPE
    SYNTAX       INTEGER { none (1),
                           static (2),
                           connected (3),
                           staticAndConnected(4),
                           defOrig(5),
                           defOrigAndStatic(6),
                           defOrigAndConnected(7),
                           all(8) }
    MAX-ACCESS   read-create
    STATUS       current
    DESCRIPTION  "Indicates the extent of route redistribution.
                  Static - static routes,
                  Connected - routes connected to the node.
                  DefOrig - default routes from adjacent nodes."
    DEFVAL       { none }
    ::= { ospfGeneralGroupEntry 6 }

ospfAreaId OBJECT-TYPE
    SYNTAX       IpAddress
    MAX-ACCESS   read-create
    STATUS       current
    DESCRIPTION  "The area ID associated with this OSPF item.
                  Note that although the area ID has the format of an 
                  IP Address it is not actually an IP address."
    ::= { ospfGeneralGroupEntry 7 }

ospfRowStatus OBJECT-TYPE
    SYNTAX       RowStatus
    MAX-ACCESS   read-create
    STATUS       current
    DESCRIPTION  "Used to control the addition and deletion of the
                  ospf General Group parameters."
    ::= { ospfGeneralGroupEntry 8 }

-----------------------------------------------------------------------
--  OSPF Interface Table
-----------------------------------------------------------------------

ospfIfTable OBJECT-TYPE  
    SYNTAX       SEQUENCE OF OspfIfEntry
    MAX-ACCESS   not-accessible
    STATUS       current
    DESCRIPTION "The OSPF Interface Table describes the interfaces
                 from the viewpoint of OSPF."
       ::= { topology 3 }

ospfIfEntry OBJECT-TYPE
     SYNTAX       OspfIfEntry
     MAX-ACCESS   not-accessible
     STATUS       current
     DESCRIPTION  "The OSPF interface entry describes one interface
          from the viewpoint of OSPF.
          Information in this table is persistent and when this object
          is written the entity is saved to non-volatile
          storage."
       INDEX { ospfIfSwitchId,
               ospfIfShelfIdx,
               ospfIfSlotIdx,
               ospfIfType,
               ospfIfIdx,
               ospfIfSubIdx }
       ::= { ospfIfTable 1 }

OspfIfEntry ::=  SEQUENCE { ospfIfSwitchId               INTEGER,
                            ospfIfShelfIdx               INTEGER,
                            ospfIfSlotIdx                INTEGER,
                            ospfIfType                   PvxPortType,
                            ospfIfIdx                    INTEGER,
                            ospfIfSubIdx                 INTEGER,
                            ospfIfAreaId                 AreaID,
                            ospfIfAdminStat              INTEGER,
                            ospfIfRtrPriority            INTEGER,
                            ospfIfTransitDelay           INTEGER,
                            ospfIfRetransInterval        INTEGER,
                            ospfIfHelloInterval          INTEGER,
                            ospfIfRtrDeadInterval        INTEGER,
                            ospfIfMetricValue            INTEGER,
                            ospfIfStatus                 RowStatus         
                          }            

ospfIfSwitchId   OBJECT-TYPE
    SYNTAX       INTEGER (0..11)
    MAX-ACCESS   accessible-for-notify
    STATUS       current
    DESCRIPTION  "The number of the switch id on which the OSPF interface 
                  exists.  Set to zero if the switchId a switch Id is not 
                  applicable for identification of the OSPF interface."
    DEFVAL       {0}
    ::= { ospfIfEntry 1 }

ospfIfShelfIdx   OBJECT-TYPE
    SYNTAX       INTEGER (1|11|21|31)
    MAX-ACCESS   accessible-for-notify
    STATUS       current
    DESCRIPTION  "The number of the shelf on which the OSPF interface exists."
    ::= { ospfIfEntry 2 }

ospfIfSlotIdx    OBJECT-TYPE
    SYNTAX       INTEGER (0..6)
    MAX-ACCESS   accessible-for-notify
    STATUS       current
    DESCRIPTION  "The number of the slot within the shelf corresponding to
                  the OSPF interface."
    ::= { ospfIfEntry 3 }

ospfIfType OBJECT-TYPE
    SYNTAX       PvxPortType
    MAX-ACCESS   accessible-for-notify
    STATUS       current
    DESCRIPTION  "The type of the interface corresponding to the OSPF 
                  interface. Set to zero if the ospfIfType is not applicable 
                  for identification of the OSPF interface."
    DEFVAL       { unknown }
    ::= { ospfIfEntry 4 }

ospfIfIdx OBJECT-TYPE
    SYNTAX       INTEGER (0..255)
    MAX-ACCESS   accessible-for-notify
    STATUS       current
    DESCRIPTION  "The number of the interface within the slot corresponding
                  to the OSPF interface."
    ::= { ospfIfEntry 5 }

ospfIfSubIdx OBJECT-TYPE
    SYNTAX       INTEGER (0..255)
    MAX-ACCESS   accessible-for-notify
    STATUS       current
    DESCRIPTION  "The number of the sub-interface that the OSFP Interface 
                  corresponds to. Set to zero if the ospfIfSubIdx is not
                  applicable for identification of the OSPF interface. "
    DEFVAL        {0}
    ::= { ospfIfEntry 6 }

ospfIfAreaId OBJECT-TYPE
    SYNTAX       AreaID
    MAX-ACCESS   read-only
    STATUS       current
    DESCRIPTION  "A 32-bit integer uniquely identifying the area
        to which the interface connects.  Area ID
        0.0.0.0 is used for the OSPF backbone."
    ::= { ospfIfEntry 7 }

ospfIfAdminStat OBJECT-TYPE
    SYNTAX       INTEGER { enabled (1), disabled (2) }
    MAX-ACCESS   read-create
    STATUS       current
    DESCRIPTION  "The OSPF interface's administrative status.
        The value formed on the interface, and the interface
        will be advertised as an internal route to some area.
        The value 'disabled' denotes that the interface is
        external to OSPF."
    DEFVAL { enabled }
    ::= { ospfIfEntry 8 }

ospfIfRtrPriority OBJECT-TYPE
    SYNTAX       INTEGER (0..'FF'h)
    MAX-ACCESS   read-create
    STATUS       current
    DESCRIPTION "The priority of this interface.  Used in
       multi-access networks, this field is used in
       the designated router election algorithm.  The
       value 0 signifies that the router is not eligible
       to become the designated router on this particular
       network.  In the event of a tie in this value,
       routers will use their Router ID as a tie breaker."
    DEFVAL { 1 }
    ::= { ospfIfEntry 9 }

ospfIfTransitDelay OBJECT-TYPE
    SYNTAX       INTEGER (0..3600)
    UNITS        "seconds"
    MAX-ACCESS   read-create
    STATUS       current
    DESCRIPTION "The estimated number of seconds it takes to
        transmit a link state update packet over this
        interface.  Note that the minimal value SHOULD be
        1 second."
    DEFVAL { 1 }
        ::= { ospfIfEntry 10 }

ospfIfRetransInterval OBJECT-TYPE
    SYNTAX       INTEGER (0..3600)
    UNITS        "seconds"
    MAX-ACCESS   read-create
    STATUS       current
    DESCRIPTION  "The number of seconds between link state advertisement
       retransmissions, for adjacencies belonging to this
       interface.  This value is also used when retransmitting
       database description and Link State request packets.
       Note that minimal value SHOULD be 1 second."
    DEFVAL { 5 }
    ::= { ospfIfEntry  11 }

ospfIfHelloInterval OBJECT-TYPE
    SYNTAX       INTEGER ( 1..'FFFF'h )
    UNITS        "seconds"
    MAX-ACCESS   read-create
    STATUS       current
    DESCRIPTION  "The length of time, in seconds, between the Hello packets
       that the router sends on the interface.  This value must be
       the same for all routers attached to a common network."
    DEFVAL { 10 }
    ::= { ospfIfEntry 12 }

ospfIfRtrDeadInterval OBJECT-TYPE
    SYNTAX       INTEGER ( 0..'7FFFFFFF'h )
    UNITS        "seconds"
    MAX-ACCESS   read-create
    STATUS       current
    DESCRIPTION  "The number of seconds that a router's Hello packets have
       not been seen before its neighbors declare the router down.
       This should be some multiple of the Hello interval.  This
       value must be the same for all routers attached to a common
       network."
    DEFVAL { 40 }
    ::= { ospfIfEntry 13 }

ospfIfMetricValue OBJECT-TYPE
    SYNTAX       INTEGER (0..'FFFF'h)
    MAX-ACCESS   read-create
    STATUS       current
    DESCRIPTION  "A metric used to identify the 'cost' associated with using 
         this interface."
    DEFVAL { 10 }
    ::= { ospfIfEntry 14 }


ospfIfStatus OBJECT-TYPE
    SYNTAX       RowStatus
    MAX-ACCESS   read-create
    STATUS       current
    DESCRIPTION  "This object permits management of the table by
       facilitating actions such as row creation,
       construction, and destruction.

       The value of this object has no effect on
       whether other objects in this conceptual row can be
       modified."
    ::= { ospfIfEntry 15 }

-----------------------------------------------------------------------
--  OSPF LSDB Table
-----------------------------------------------------------------------

ospfLsdbTable OBJECT-TYPE
    SYNTAX       SEQUENCE OF OspfLsdbEntry
    MAX-ACCESS   not-accessible
    STATUS       current

    DESCRIPTION  "The OSPF Process's link state database (LSDB).
           The LSDB contains the link state advertisements
           from throughout the areas that the device is attached to."
    ::= { topology 4 }

ospfLsdbEntry OBJECT-TYPE
    SYNTAX   OspfLsdbEntry
    MAX-ACCESS   not-accessible
    STATUS   current
    DESCRIPTION "A single link state advertisement."
    INDEX { ospfLsdbAreaId, ospfLsdbType, 
            ospfLsdbLsid,   ospfLsdbRouterId }
    ::= { ospfLsdbTable 1 }

OspfLsdbEntry ::= SEQUENCE { ospfLsdbAreaId         AreaID,
                             ospfLsdbType           INTEGER,
                             ospfLsdbLsid           IpAddress,
                             ospfLsdbRouterId       IpAddress,
                             ospfLsdbSequence       Integer32,
                             ospfLsdbAge            Integer32,
                             ospfLsdbChecksum       Integer32
                           }


ospfLsdbAreaId OBJECT-TYPE
    SYNTAX       AreaID
    MAX-ACCESS   read-only 
    STATUS       current
    DESCRIPTION  "The 32-bit identifier of the area from which
                  the LSA was received."
    ::= { ospfLsdbEntry 1 }

ospfLsdbType OBJECT-TYPE
    SYNTAX       INTEGER { routerLink (1),
                           networkLink (2),
                           summaryLink (3),
                           asSummaryLink (4),
                           asExternalLink (5), -- but see ospfAsLsdbTable
                           multicastLink (6),
                           nssaExternalLink (7),
                           areaOpaqueLink (10)
                          }
     MAX-ACCESS   read-only
     STATUS       current
     DESCRIPTION "The type of the link state advertisement.
          Each link state type has a separate advertisement
          format"
     ::= { ospfLsdbEntry 2 }

ospfLsdbLsid OBJECT-TYPE
     SYNTAX       IpAddress
     MAX-ACCESS   read-only
     STATUS       current
     DESCRIPTION  "The Link State ID is an LS Type Specific field
          containing either a Router ID or an IP address;
          it identifies the piece of the routing domain
          that is being described by the advertisement."
     ::= { ospfLsdbEntry 3 }

ospfLsdbRouterId OBJECT-TYPE
     SYNTAX       IpAddress
     MAX-ACCESS   read-only
     STATUS       current
     DESCRIPTION  "The 32-bit number that uniquely identifies the
           originating router in the Autonomous System."
     ::= { ospfLsdbEntry 4 }

ospfLsdbSequence OBJECT-TYPE
     SYNTAX       Integer32
     MAX-ACCESS   read-only
     STATUS       current
     DESCRIPTION "The sequence number field is a signed 32-bit
          integer.  It starts with the value '80000001'h,
          or -'7FFFFFFF'h, and increments until '7FFFFFFF'h.
          Thus, a typical sequence number will be very negative.
          It is used to detect old and duplicate Link State
          Advertisements.  The space of sequence numbers is linearly
          ordered.  The larger the sequence number, the more recent
          the advertisement."
     ::= { ospfLsdbEntry 5 }

ospfLsdbAge OBJECT-TYPE
     SYNTAX       Integer32
     UNITS        "seconds"
     MAX-ACCESS   read-only
     STATUS       current
     DESCRIPTION  "This field is the age of the link state advertisement
                   in seconds."
     ::= { ospfLsdbEntry 6 }

ospfLsdbChecksum OBJECT-TYPE
     SYNTAX       Integer32
     MAX-ACCESS   read-only
     STATUS       current
     DESCRIPTION "This field is the checksum of the complete contents of
          the advertisement, excepting the age field.  The age field
          is excepted so that an advertisement's age can be
          incremented without updating the checksum.  The checksum
          used is the same that is used for ISO connectionless
          datagrams; it is commonly referred to as the
          Fletcher checksum."
     ::= { ospfLsdbEntry 7 }

-----------------------------------------------------------------------
--  OSPF Neighbor Table
-----------------------------------------------------------------------

ospfNbrTable OBJECT-TYPE
    SYNTAX       SEQUENCE OF OspfNbrEntry
    MAX-ACCESS   not-accessible
    STATUS       current
    DESCRIPTION  "A table describing all non-virtual neighbors
                  in the locality of the OSPF router."
    ::= { topology 5 }

ospfNbrEntry OBJECT-TYPE
    SYNTAX       OspfNbrEntry
    MAX-ACCESS   not-accessible
    STATUS       current
    DESCRIPTION  "The information regarding a single neighbor.
                  Information in this table is persistent and when this object
                  is written the entity SHOULD save the change to non-volatile
                  storage."
    INDEX { ospfNbrIpAddr, ospfNbrAddressLessIndex }
    ::= { ospfNbrTable 1 }

OspfNbrEntry ::=  SEQUENCE { ospfNbrIpAddr             IpAddress,
                             ospfNbrAddressLessIndex   Integer32,
                             ospfNbrRtrId              IpAddress,
                             ospfNbrOptions            Integer32,
                             ospfNbrPriority           DesignatedRouterPriority,
                             ospfNbrState              INTEGER
                           }

ospfNbrIpAddr OBJECT-TYPE
    SYNTAX       IpAddress
    MAX-ACCESS   read-only -- read-only since originally an
                           -- SMIv1 index
    STATUS       current
    DESCRIPTION  "The IP address this neighbor is using in its
                  IP source address.  Note that, on addressless
                  links, this will not be 0.0.0.0 but the
                  address of another of the neighbor's interfaces."
    ::= { ospfNbrEntry 1 }

ospfNbrAddressLessIndex OBJECT-TYPE
    SYNTAX       Integer32 (0..2147483647)
    MAX-ACCESS   read-only
    STATUS       current
    DESCRIPTION "On an interface having an IP address, zero.
          On addressless interfaces, the corresponding
          value of ifIndex in the Internet Standard MIB.
          On row creation, this can be derived from the
          instance."
    ::= { ospfNbrEntry 2 }

   
ospfNbrRtrId OBJECT-TYPE
    SYNTAX       IpAddress
    MAX-ACCESS   read-only
    STATUS       current
    DESCRIPTION  "A 32-bit integer (represented as a type
                  IpAddress) uniquely identifying the neighboring
                  router in the Autonomous System."
    ::= { ospfNbrEntry 3 }

ospfNbrOptions OBJECT-TYPE
    SYNTAX       Integer32
    MAX-ACCESS   read-only
    STATUS       current
    DESCRIPTION  "A bit mask corresponding to the neighbor's
                  options field.

                  Bit 0, if set, indicates that the system will
                  operate on Type of Service metrics other than
                  TOS 0.  If zero, the neighbor will ignore all
                  metrics except the TOS 0 metric.

                  Bit 1, if set, indicates that the associated
                  area accepts and operates on external
                  information; if zero, it is a stub area.

                  Bit 2, if set, indicates that the system is
                  capable of routing IP multicast datagrams, that is
                  that it implements the multicast extensions to
                  OSPF.

                  Bit 3, if set, indicates that the associated
                  area is an NSSA.  These areas are capable of
                  carrying type-7 external advertisements, which
                  are translated into type-5 external advertisements
                  at NSSA borders."
    ::= { ospfNbrEntry 4 }

ospfNbrPriority OBJECT-TYPE
    SYNTAX       DesignatedRouterPriority
    MAX-ACCESS   read-only
    STATUS       current
    DESCRIPTION   "The priority of this neighbor in the designated
                   router election algorithm.  The value 0 signifies
                   that the neighbor is not eligible to become
                   the designated router on this particular network."
   ::= { ospfNbrEntry 5 }

ospfNbrState OBJECT-TYPE
    SYNTAX       INTEGER { down (1),
                           attempt (2),
                           init (3),
                           twoWay (4),
                           exchangeStart (5),
                           exchange (6),
                           loading (7),
                           full (8)
                         }
    MAX-ACCESS   read-only
    STATUS       current
    DESCRIPTION  "The state of the relationship with this neighbor."
    ::= { ospfNbrEntry 6 }


-----------------------------------------------------------------------
-- Objects related to provisioned Ethernet facilities 
------------------------------------------------------------------------
pvxL2IntfTable OBJECT-TYPE
    SYNTAX       SEQUENCE OF PVXL2IntfEntry
    MAX-ACCESS   not-accessible
    STATUS       current
    DESCRIPTION  "This table contains one row for every provisioned Ethernet
                  facility on the system. Each row contains a list of attributes
                  that pertain to the facility."
    ::= { pvxBridge 3 }

pvxL2IntfEntry OBJECT-TYPE
    SYNTAX       PVXL2IntfEntry
    MAX-ACCESS   not-accessible
    STATUS       current
    DESCRIPTION  "The conceptual row object of the ethIntfTable table."
    INDEX        { 	pvxL2IntfSwitchIdx,
		   			pvxL2IntfShelfIdx,
		   			pvxL2IntfSlotIdx,
					pvxL2IntfPortTypeIdx,
                	pvxL2IntfPortIdx }
    ::= { pvxL2IntfTable 1 }

PVXL2IntfEntry ::= SEQUENCE {	pvxL2IntfSwitchIdx 		           INTEGER,
                                pvxL2IntfShelfIdx                  INTEGER,
                                pvxL2IntfSlotIdx                   INTEGER,
                                pvxL2IntfPortTypeIdx               PvxPortType,
                                pvxL2IntfPortIdx                   INTEGER,
                                pvxL2IntfAdminStatus               INTEGER,
                                pvxL2IntfOperStatus                OperStatus,
                                pvxL2IntfType                      INTEGER,
                                pvxL2IntfSTpid                     INTEGER,
                                pvxL2IntfPvid                      INTEGER,
                                pvxL2IntfDefaultPriority           INTEGER,
                                pvxL2IntfAllowedFrames             INTEGER,
                                pvxL2IntfIngressFiltering          TruthValue,
                                pvxL2IntfCtrlFrmProfileId          Integer32,
                                pvxL2IntfMACAddr                   MacAddress,
                                pvxL2IntfRateLimit                 Integer32,
                                pvxL2IntfCoSProfileId              Integer32,
                                pvxL2IntfIsUNI                     INTEGER,  
                                pvxL2IntfSchedProfName             DisplayString,
                                pvxL2IntfPriTCMapProfName          DisplayString,
                                pvxL2IntfPCPCodingProfName         DisplayString,
                                pvxL2IntfDscpPHBProfName           DisplayString,
                                pvxL2IntfCtrlFrmProfileName        DisplayString,
                                pvxL2IntfUseDei                    TruthValue,
                                pvxL2IntfIngressBandwidthProfile   DisplayString,
                                pvxL2IntfEgressBandwidthProfile    DisplayString,
                                pvxL2IntfTrustIncomingPCP          TruthValue,
                                pvxL2IntfTrustIncomingDscp         TruthValue,
                                pvxL2IntfBcastLimit                INTEGER,
                                pvxL2IntfMcastLimit                INTEGER,
                                pvxL2IntfDlfLimit                  INTEGER,
                            	pvxL2IntfRowStatus      	   RowStatus } 

pvxL2IntfSwitchIdx OBJECT-TYPE
    SYNTAX       INTEGER(1..11) 
    MAX-ACCESS   accessible-for-notify
    STATUS       current
    DESCRIPTION  "The number of the switch id of the provisioned ethernet
                  facility."
    ::= {pvxL2IntfEntry 1 }

pvxL2IntfShelfIdx OBJECT-TYPE
    SYNTAX    INTEGER (0|1|11|21|31)
    MAX-ACCESS   accessible-for-notify
    STATUS       current
    DESCRIPTION  "The number of the shelf id of the provisioned ethernet
                  facility."
    ::= {pvxL2IntfEntry 2 }

pvxL2IntfSlotIdx OBJECT-TYPE
    SYNTAX    INTEGER (0..20) 
    MAX-ACCESS   accessible-for-notify
    STATUS       current
    DESCRIPTION  "The number of the instance id of the provisioned ethernet
                  facility."
    ::= {pvxL2IntfEntry 3 }

pvxL2IntfPortTypeIdx OBJECT-TYPE
	SYNTAX      PvxPortType 
    MAX-ACCESS   accessible-for-notify
    STATUS       current
    DESCRIPTION  "The number of the instance id of the provisioned ethernet
                  facility."
    ::= {pvxL2IntfEntry 4 }


pvxL2IntfPortIdx OBJECT-TYPE
    SYNTAX       INTEGER (1..24)
    MAX-ACCESS   accessible-for-notify
    STATUS       current
    DESCRIPTION  "The number of the port on the circuit pack on which the
                  ethernet facility is provisioned."
    ::= {pvxL2IntfEntry 5 }

pvxL2IntfAdminStatus OBJECT-TYPE
    SYNTAX       INTEGER { enabled  (1),
                           disabled (2) }
    MAX-ACCESS   read-create
    STATUS       current
    DESCRIPTION  "The administrative status of the Ethernet facility."
    DEFVAL       { enabled }
    ::= {pvxL2IntfEntry 6 }

pvxL2IntfOperStatus OBJECT-TYPE
    SYNTAX       OperStatus
    MAX-ACCESS   read-only
    STATUS       current
    DESCRIPTION  "The reported operational status of the Ethernet facility."
    ::= {pvxL2IntfEntry 7 }

pvxL2IntfType OBJECT-TYPE
    SYNTAX       INTEGER { pnp (1),
                           cep (2),
                           cnpPortbased (3),
                           cbp (4) }
    MAX-ACCESS   read-create
    STATUS       current
    DESCRIPTION  "This object is used to configure the type of a interface."
    DEFVAL       { pnp }
    ::= {pvxL2IntfEntry 8 }

pvxL2IntfSTpid OBJECT-TYPE
    SYNTAX       INTEGER { uni8100 (1),
                           nni88a8 (2),
                           nni9100 (3) } 
    MAX-ACCESS   read-create
    STATUS       current
    DESCRIPTION  "The Ethernet type (TPID) of the S-TAG"
    DEFVAL { uni8100 }
    ::= {pvxL2IntfEntry 9 }

pvxL2IntfPvid OBJECT-TYPE
    SYNTAX       INTEGER (1..4090)
    MAX-ACCESS   read-create
    STATUS       current
    DESCRIPTION  "The PVID (port-based VLAN ID) for the port"
    ::= {pvxL2IntfEntry 10 }  

pvxL2IntfDefaultPriority OBJECT-TYPE
    SYNTAX       INTEGER (0..7)
    MAX-ACCESS   read-create
    STATUS       current
    DESCRIPTION  "This object sets the default priority of the interface."
    ::= {pvxL2IntfEntry 11 }  

pvxL2IntfAllowedFrames OBJECT-TYPE 
    SYNTAX       INTEGER { all            (1), 
                           vlanTagged     (2),
                           priorityTagged (3) }
    MAX-ACCESS   read-create
    STATUS       current
    DESCRIPTION  "TODO: Does this feild need to support OR of the options?"
    ::= {pvxL2IntfEntry 12 }

pvxL2IntfIngressFiltering OBJECT-TYPE 
    SYNTAX       TruthValue 
    MAX-ACCESS   read-create
    STATUS       deprecated
    DESCRIPTION  "When this is true(1) the device will discard incoming frames
                  for VLANs which do not include this Port in its Member set.
                  When false(2), the port will accept all incoming frames.
                  
                  This control does not affect VLAN independent BPDU frames,
                  such as GVRP and STP. It does affect VLAN dependent BPDU
                  frames, such as GMRP."
    ::= {pvxL2IntfEntry 13 }

pvxL2IntfCtrlFrmProfileId OBJECT-TYPE 
    SYNTAX       Integer32 
    MAX-ACCESS   read-create
    STATUS       deprecated
    DESCRIPTION  ""
    ::= {pvxL2IntfEntry 14 }    
    
pvxL2IntfMACAddr OBJECT-TYPE
    SYNTAX       MacAddress
    MAX-ACCESS   read-only
    STATUS       current
    DESCRIPTION  "The MAC address of the interface."
    ::= { pvxL2IntfEntry 15 }

pvxL2IntfRateLimit OBJECT-TYPE 
    SYNTAX       Integer32
    MAX-ACCESS   read-create
    STATUS       current
    DESCRIPTION  "This represents the interface rate limit in kilobits/s."
    ::= { pvxL2IntfEntry 16 }


pvxL2IntfCoSProfileId OBJECT-TYPE
    SYNTAX       Integer32
    MAX-ACCESS   read-create
    STATUS       current
    DESCRIPTION  "This represents the Class of service profile for the 
                  interface."
    ::= { pvxL2IntfEntry 17 }
    
pvxL2IntfIsUNI OBJECT-TYPE
    SYNTAX       INTEGER { neither (1),
                           uni (2),
                           nni (3)} 
    MAX-ACCESS   read-only
    STATUS       current
    DESCRIPTION  "The Switch port type. The default value set by the switch is neither."
    ::= {pvxL2IntfEntry 18 }

pvxL2IntfSchedProfName OBJECT-TYPE
    SYNTAX       DisplayString (SIZE(0..32)) 
    MAX-ACCESS   read-create
    STATUS       current
    DESCRIPTION  "The scheduler profile used by the interface."
    ::= {pvxL2IntfEntry 19 }
    
pvxL2IntfPriTCMapProfName  OBJECT-TYPE
    SYNTAX       DisplayString (SIZE(0..32)) 
    MAX-ACCESS   read-create
    STATUS       current
    DESCRIPTION  "The priority to traffic class map profile used by the interface."
    ::= {pvxL2IntfEntry 20 }

pvxL2IntfPCPCodingProfName     OBJECT-TYPE
    SYNTAX       DisplayString (SIZE(0..32)) 
    MAX-ACCESS   read-create
    STATUS       current
    DESCRIPTION  "The scheduler profile used by the interface."
    ::= {pvxL2IntfEntry 21 }

pvxL2IntfDscpPHBProfName     OBJECT-TYPE
    SYNTAX       DisplayString (SIZE(0..32)) 
    MAX-ACCESS   read-create
    STATUS       current
    DESCRIPTION  "The internal priority setting for DSCP profile used by the interface."
    ::= {pvxL2IntfEntry 22 }

pvxL2IntfCtrlFrmProfileName  OBJECT-TYPE
    SYNTAX       DisplayString (SIZE(0..32)) 
    MAX-ACCESS   read-create
    STATUS       current
    DESCRIPTION  "The L2 control frame profile used by the interface."
    ::= {pvxL2IntfEntry 23 }

pvxL2IntfUseDei   OBJECT-TYPE
	SYNTAX      TruthValue 
    MAX-ACCESS   read-create
    STATUS       current
    DESCRIPTION  "Used by PNP port. By default, it is set to false by the switch."
    ::= {pvxL2IntfEntry 24 }
 
pvxL2IntfIngressBandwidthProfile   OBJECT-TYPE
	SYNTAX       DisplayString (SIZE(0..32)) 
    MAX-ACCESS   read-create
    STATUS       current
    DESCRIPTION  "The ingress policy map profile used by the interface."
    ::= {pvxL2IntfEntry 25 }
    
pvxL2IntfEgressBandwidthProfile   OBJECT-TYPE
	SYNTAX       DisplayString (SIZE(0..32)) 
    MAX-ACCESS   read-create
    STATUS       current
    DESCRIPTION  "The egress policy map profile used by the interface."
    ::= {pvxL2IntfEntry 26 }

pvxL2IntfTrustIncomingPCP   OBJECT-TYPE
	SYNTAX      TruthValue 
    MAX-ACCESS   read-create
    STATUS       current
    DESCRIPTION  "Used by all port type. By default, it is set to true by the switch."
    ::= {pvxL2IntfEntry 27 }
    
pvxL2IntfTrustIncomingDscp   OBJECT-TYPE
	SYNTAX      TruthValue 
    MAX-ACCESS   read-create
    STATUS       current
    DESCRIPTION  "Used by all port type. By default, it is set to true by the switch."
    ::= {pvxL2IntfEntry 28 }
    
pvxL2IntfBcastLimit OBJECT-TYPE 
    SYNTAX       INTEGER (20|40|60|100)
    MAX-ACCESS   read-create
    STATUS       current
    DESCRIPTION  "Broadcast rate limit as percentage of the line rate for 
    		 the port with default value of 100 (no storm control)."
    DEFVAL       { 100 } 
    ::= { pvxL2IntfEntry 29 }

pvxL2IntfMcastLimit OBJECT-TYPE 
    SYNTAX       INTEGER (20|40|60|100)
    MAX-ACCESS   read-create
    STATUS       current
    DESCRIPTION  "Multicast rate limit as percentage of the line rate for 
    		 the port with default value of 100 (no storm control)."
    DEFVAL       { 100 }
    ::= { pvxL2IntfEntry 30 }

pvxL2IntfDlfLimit OBJECT-TYPE 
    SYNTAX       INTEGER (20|40|60|100)
    MAX-ACCESS   read-create
    STATUS       current
    DESCRIPTION  "Unicast DLF rate limit as percentage of the line rate for 
    		 the port with default value of 100 (no storm control)."
    DEFVAL       { 100 }
    ::= { pvxL2IntfEntry 31 }

pvxL2IntfRowStatus OBJECT-TYPE
    SYNTAX       RowStatus
    MAX-ACCESS   read-create
    STATUS       current
    DESCRIPTION  "Used to control the addition and deletion of entries in the
                  PVX L2 Interface table."
    ::= {pvxL2IntfEntry 100 }



-----------------------------------------------------------------------
-- Objects used to retrieve error information for failed set requests.
-- These objects can optionally be included in set requests sent to
-- the agent. When the set request fails, the returned objects will
-- contain information to explain the reason for the set failure.
------------------------------------------------------------------------

setErrorInfo   OBJECT IDENTIFIER ::= { miscellaneous 1 } 

setErrorCode OBJECT-TYPE
    SYNTAX       Integer32
    MAX-ACCESS   read-write
    STATUS       current
    DESCRIPTION  "The BTI-specific error code for the set request failure."
    ::= { setErrorInfo 1 }


setErrorDesc OBJECT-TYPE
    SYNTAX       DisplayString
    MAX-ACCESS   read-write
    STATUS       current
    DESCRIPTION  "A textual description string that explains the reason
    			  for the failed set request."
    ::= { setErrorInfo 2 }


-----------------------------------------------------------------------
-- Event Notifications Objects
-----------------------------------------------------------------------


trapSeqNum OBJECT-TYPE
    SYNTAX       Unsigned32
    MAX-ACCESS   read-only
    STATUS       current
    DESCRIPTION  "A integer value indicating the place of the trap notification
                  message within the continual sequence of all notification
                  messages issued by the system."
    ::= { notificationObjects 1 }


evtDateAndTime OBJECT-TYPE
    SYNTAX       DateAndTime
    MAX-ACCESS   accessible-for-notify
    STATUS       current
    DESCRIPTION  "The date and time at which an event notification was issued by
                  the system."
    ::= { evtNotificationObjects 1 }


tcaIntervalType OBJECT-TYPE
    SYNTAX       PMIntervalType
    MAX-ACCESS   accessible-for-notify
    STATUS       current
    DESCRIPTION  "The type of PM bin according to interval length during which a
                  performance monitoring threshold crossing occurred."
    ::= { evtNotificationObjects 2 }


tcaDateAndTime OBJECT-TYPE
    SYNTAX       DateAndTime
    MAX-ACCESS   accessible-for-notify
    STATUS       current
    DESCRIPTION  "The date and time of the performance monitoring interval for
                  which a performance monitoring threshold crossing alert is
                  generated."
    ::= { evtNotificationObjects 3 }


tcaMontype OBJECT-TYPE
    SYNTAX       PMMontype
    MAX-ACCESS   accessible-for-notify
    STATUS       current
    DESCRIPTION  "Identify the performance monitoring monitored type for which a
                  threshold crossing alert is generated."
    ::= { evtNotificationObjects 4 }


tcaValue OBJECT-TYPE
    SYNTAX       Unsigned32
    MAX-ACCESS   accessible-for-notify
    STATUS       current
    DESCRIPTION  "The measured value of the monitored type for which a
                  performance monitoring threshold crossing alert is generated."
    ::= { evtNotificationObjects 5 }


tcaThreshold OBJECT-TYPE
    SYNTAX       Unsigned32
    MAX-ACCESS   accessible-for-notify
    STATUS       current
    DESCRIPTION  "The threshold for the monitored type that was exceeded
                  resulting in the generation of a performance monnitoring
                  threshold crossing alert."
    ::= { evtNotificationObjects 6 }


evtDescription OBJECT-TYPE
    SYNTAX       DisplayString
    MAX-ACCESS   accessible-for-notify
    STATUS       current
    DESCRIPTION  "A textual decription of the event."
    ::= { evtNotificationObjects 7 }


evtObjectType OBJECT-TYPE
    SYNTAX       NotifObjectType
    MAX-ACCESS   accessible-for-notify
    STATUS       current
    DESCRIPTION  "Identifies the type of managed object against which the
                  event notification is raised."
    ::= { evtNotificationObjects 8 }


evtCodeType OBJECT-TYPE
    SYNTAX       NotifCodeType
    MAX-ACCESS   accessible-for-notify
    STATUS       current
    DESCRIPTION  "This object value uniquely identifies the type of event
    			  that has been generated."
    ::= { evtNotificationObjects 9 }



-----------------------------------------------------------------------
-- Database Change Event Notification Objects
-----------------------------------------------------------------------

dbChangeNotificationsObjects  OBJECT IDENTIFIER ::= { dbChangeNotifications 1 }


dbChangeDateAndTime OBJECT-TYPE
    SYNTAX       DateAndTime
    MAX-ACCESS   accessible-for-notify
    STATUS       current
    DESCRIPTION  "The date and time at which a database change notification was
                  issued by the system."
    ::= { dbChangeNotificationsObjects 1 }


dbChangeSeqNum OBJECT-TYPE
    SYNTAX       Unsigned32
    MAX-ACCESS   accessible-for-notify
    STATUS       current
    DESCRIPTION  "A integer value indicating the place of a database change
                  notification message within the continual sequence of all
                  database messages issued by the system."
    ::= { dbChangeNotificationsObjects 2 }


dbChangeOID OBJECT-TYPE
    SYNTAX       OBJECT IDENTIFIER
    MAX-ACCESS   accessible-for-notify
    STATUS       current
    DESCRIPTION  "The OID of the object instance whose value has been changed in
                  the database."
    ::= { dbChangeNotificationsObjects 3 }

-----------------------------------------------------------------------
-- Condition Notification Control Objects
-----------------------------------------------------------------------

condNotifCtrlTable OBJECT-TYPE
    SYNTAX         SEQUENCE OF CondNotifCtrlEntry
    MAX-ACCESS     not-accessible
    STATUS         current
    DESCRIPTION   "This table contains one row for every condition notification
                   associated with a raise."
    ::= { condNotifCtrl 1 }


condNotifCtrlEntry OBJECT-TYPE
    SYNTAX       CondNotifCtrlEntry
    MAX-ACCESS   not-accessible
    STATUS       current
    DESCRIPTION  "The conceptual row object of the condition notification control 
                  table."
    INDEX        { condNotifObjId }
    ::= { condNotifCtrlTable 1 }


CondNotifCtrlEntry ::= SEQUENCE { condNotifObjId             OBJECT IDENTIFIER,
                                  condNotifSeverity          INTEGER,
                                  condNotifDefaultSeverity   INTEGER }

condNotifObjId   OBJECT-TYPE
    SYNTAX       OBJECT IDENTIFIER
    MAX-ACCESS   not-accessible
    STATUS       current
    DESCRIPTION  "The specific condition notification to set the severity for.
                  The value must correspond to the raise condition not the clear."
    ::= { condNotifCtrlEntry 1 }


condNotifSeverity OBJECT-TYPE
    SYNTAX        CondSeverity
    MAX-ACCESS    read-write
    STATUS        current
    DESCRIPTION  "The severity associated with the condition notification.
                  - Only certain values are permitted for the set:
                  default, critial, major, minor, notAlarmed.
			- Only certain values are visible for the get:
                  critial, major, minor, major-minor, notAlarmed"
    ::= { condNotifCtrlEntry 2 }


condNotifDefaultSeverity OBJECT-TYPE
    SYNTAX       CondSeverity
    MAX-ACCESS   read-only
    STATUS       current
    DESCRIPTION  "The default severity associated with the condition notification.
                	Only certain of the CondSeverity values are visible:
                  critial, major, minor, major-minor, notAlarmed"

    ::= { condNotifCtrlEntry 3 }


-----------------------------------------------------------------------
-- The envCondAttrTable is used to manage environmental alarm
-- configuration. 
------------------------------------------------------------------------

envCondAttrTable OBJECT-TYPE
    SYNTAX         SEQUENCE OF EnvCondAttrEntry
    MAX-ACCESS     not-accessible
    STATUS         current
    DESCRIPTION   "This table is used to manage the configuration of
                   environmental alarm inputs. It contains one row for
                   each environmental condition input on the NE."
    ::= { condNotifCtrl 2 }


envCondAttrEntry OBJECT-TYPE
    SYNTAX       EnvCondAttrEntry
    MAX-ACCESS   not-accessible
    STATUS       current
    DESCRIPTION  "The conceptual row object of the environmental condition
                  attribute table."
    INDEX        { envCondAttrHKIIdx }
    ::= { envCondAttrTable 1 }


EnvCondAttrEntry ::= SEQUENCE { envCondAttrHKIIdx        INTEGER,
                                envCondAttrSeverity      CondSeverity,
                                envCondAttrCodeType      EnvNotifCodeType,
                                envCondAttrDescription   DisplayString,
                                envCondAttrInputType     INTEGER }


envCondAttrHKIIdx OBJECT-TYPE
    SYNTAX       INTEGER (1..6)
    MAX-ACCESS   not-accessible
    STATUS       current
    DESCRIPTION  "The number of the housekeeping input which drives the
                  activation of the environmental condition configured by this
                  entry of the table."
    ::= { envCondAttrEntry 1 }


envCondAttrSeverity OBJECT-TYPE
    SYNTAX       CondSeverity
    MAX-ACCESS   read-write
    STATUS       current
    DESCRIPTION  "The severity reported for the configured environmental
                  condition when it is raised. The valid values are:
                  - minor
                  - major
                  - critical
                  - notAlarmed"
    ::= { envCondAttrEntry 2 }


envCondAttrCodeType OBJECT-TYPE
    SYNTAX       EnvNotifCodeType
    MAX-ACCESS   read-write
    STATUS       current
    DESCRIPTION  "The code for the specific environmental condition that
                  is reported when the housekeeping input indicates that
                  the condition is active."
    ::= { envCondAttrEntry 3 }


envCondAttrDescription OBJECT-TYPE
    SYNTAX       DisplayString (SIZE (0..40))
    MAX-ACCESS   read-write
    STATUS       current
    DESCRIPTION  "The textual decription of the environmental condition
                  that is reported when the condition is raised."
    ::= { envCondAttrEntry 4 }

                             
envCondAttrInputType OBJECT-TYPE
    SYNTAX       INTEGER { normallyOpen   (1),
                           normallyClosed (2),
                           disabled       (3) }
    MAX-ACCESS   read-write
    STATUS       current
    DESCRIPTION  "Specifies how the housekeeping input which drives the
                  reporting of the environmental condition is interpreted."
    ::= { envCondAttrEntry 5 }



-----------------------------------------------------------------------
-- Event Notification Control Objects
-----------------------------------------------------------------------

eventNotifState   OBJECT-TYPE
    SYNTAX        INTEGER { eventsEnabled    (1),
                            eventsDisabled   (2) }
    MAX-ACCESS    read-write
    STATUS        current
    DESCRIPTION  "Allows all events to be either disabled or enabled."
    ::= { eventNotifCtrl 1 }

-----------------------------------------------------------------------
-----------------------------------------------------------------------
-- Trap Definitions.
-----------------------------------------------------------------------
-----------------------------------------------------------------------


-----------------------------------------------------------------------
-- Event Notifications
-- 
-- The event trap types, as described in the BTI-7000-MIB, are against equipment
-- (such as, shelf, circuit pack and transceivers) and entities (such as, amplifiers and
-- Optical Supervisory Channel).
-- 
-- The trap notifications as defined in the BTI-7000-MIB include the following
-- information:
-- � Notification type (also known as Trap type in SNMPv1)� the name of the trap
-- as it appears in the BTI-7000-MIB
-- � Objects (also known as Variables in SNMPv1)� additional data values
-- embedded in the trap notification that carry data pertinent to the trap event
-- � Description - a general description of the meaning of the trap event
-- � Notification OID (also known as the combined Enterprise and Trap fields in
-- SNMPv1) - the notification object identifier is a string of numbers used to
-- identify objects, in this case traps, defined in the BTI-7000-MIB
-----------------------------------------------------------------------


shelfInvPluginEvt NOTIFICATION-TYPE
    OBJECTS      { shelfInvIdx,
                   shelfInvType,
                   shelfInvShortName,
                   shelfInvName,
                   shelfInvChassisPEC,
                   shelfInvChassisCLEI,
                   shelfInvRev,
                   shelfInvConfig,
                   evtDateAndTime,
                   trapSeqNum,
                   evtDescription,
                   evtObjectType,
                   evtCodeType }
    STATUS       current
    DESCRIPTION  "A shelf has been detected through the shelf interconnect."
    ::= { shelfInvEvtNotifications 0 1 }


shelfInvUnpluginEvt NOTIFICATION-TYPE
    OBJECTS      { shelfInvIdx,
                   evtDateAndTime,
                   trapSeqNum,
                   evtDescription,
                   evtObjectType,
                   evtCodeType }
    STATUS       current
    DESCRIPTION  "A previously detected shelf is no longer detected through the
                  shelf interconnect."
    ::= { shelfInvEvtNotifications 0 2 }


slotInvPluginEvt NOTIFICATION-TYPE
    OBJECTS      { slotInvShelfIdx,
                   slotInvSlotTypeIdx,
                   slotInvSlotIdx,
                   slotInvPackShortName,
                   slotInvPackName,
                   slotInvPackPEC,
                   slotInvPackCLEI,
                   slotInvPackSerialNum,
                   slotInvPackRev,
                   slotInvPackMfgDate,
                   slotInvPackMfgLoc,
                   slotInvPackTestDate,
                   slotInvPackTestLoc,
                   evtDateAndTime,
                   trapSeqNum,
                   evtDescription,
                   evtObjectType,
                   evtCodeType }
    STATUS       current
    DESCRIPTION  "A circuit pack has been inserted into the identified slot."
    ::= { slotInvEvtNotifications 0 1 }


slotInvUnpluginEvt NOTIFICATION-TYPE
    OBJECTS      { slotInvShelfIdx,
                   slotInvSlotTypeIdx,
                   slotInvSlotIdx,
                   evtDateAndTime,
                   trapSeqNum,
                   evtDescription,
                   evtObjectType,
                   evtCodeType }
    STATUS       current
    DESCRIPTION  "A circuit pack has been removed from the identified slot."
    ::= { slotInvEvtNotifications 0 2 }


slotInvUpgradeStageResultEvt NOTIFICATION-TYPE
    OBJECTS      { slotInvShelfIdx,
                   slotInvSlotTypeIdx,
                   slotInvSlotIdx,
                   slotInvUpgradeStage,
                   slotInvUpgradeResult,
                   evtDateAndTime,
                   trapSeqNum,
                   evtDescription,
                   evtObjectType,
                   evtCodeType }
    STATUS       current
    DESCRIPTION  "The software upgrade process on the circuit pack in the
                  identified slot has completed a stage."
    ::= { slotInvEvtNotifications 0 3 }
 

pluggableInvPluginEvt NOTIFICATION-TYPE
    OBJECTS      { pluggableInvShelfIdx,
                   pluggableInvSlotTypeIdx,
                   pluggableInvSlotIdx,
                   pluggableInvPortIdx,
                   pluggableInvType,
                   pluggableInvPEC,
                   pluggableInvCLEI,
                   pluggableInvVendorName,
                   pluggableInvVendorOUI,
                   pluggableInvVendorPartNum,
                   pluggableInvVendorRev,
                   pluggableInvVendorSerialNum,
                   pluggableInvMfgDate,
                   pluggableInvConnectorType,
                   pluggableInvMinBitRate,
                   pluggableInvMaxBitRate,
                   pluggableInvNomBitRate,
                   pluggableInvEncoding,
                   pluggableInvWavelength,
                   pluggableInvReach,
                   pluggableInvTxFaultImpl,
                   pluggableInvLOSImpl,
                   pluggableInvDDiagImpl,
                   pluggableInvTxDisableImpl,
                   pluggableInvMedia,
                   evtDateAndTime,
                   trapSeqNum,
                   evtDescription,
                   evtObjectType,
                   evtCodeType }
    STATUS       current
    DESCRIPTION  "A pluggable transceiver has been inserted into the identified
                  port."
    ::= { pluggableInvEvtNotifications 0 1 }


pluggableInvUnpluginEvt NOTIFICATION-TYPE
    OBJECTS      { pluggableInvShelfIdx,
                   pluggableInvSlotTypeIdx,
                   pluggableInvSlotIdx,
                   pluggableInvPortIdx,
                   evtDateAndTime,
                   trapSeqNum,
                   evtDescription,
                   evtObjectType,
                   evtCodeType }
    STATUS       current
    DESCRIPTION  "A pluggable transceiver has been removed from the identified
                  port."
    ::= { pluggableInvEvtNotifications 0 2 }


shelfStatusChangeEvt NOTIFICATION-TYPE
    OBJECTS      { shelfIdx,
                   shelfOperStatus,
                   shelfOperStatQlfr,
                   evtDateAndTime,
                   trapSeqNum,
                   evtDescription,
                   evtObjectType,
                   evtCodeType }
    STATUS       current
    DESCRIPTION  "Notification of a change in the shelf's operational status or
                  operational status qualifier."
    ::= { shelfEvtNotifications 0 1 }


cpStatusChangeEvt NOTIFICATION-TYPE
    OBJECTS      { cpTypeIdx,
                   cpShelfIdx,
                   cpSlotIdx,
                   cpOperStatus,
                   cpOperStatQlfr,
                   evtDateAndTime,
                   trapSeqNum,
                   evtDescription,
                   evtObjectType,
                   evtCodeType }
    STATUS       current
    DESCRIPTION  "Notification of a change in the circuit pack's operational
                  status or operational status qualifier."
    ::= { cpEvtNotifications 0 1 }


cpCheckUpgradeResultEvt NOTIFICATION-TYPE
    OBJECTS      { cpTypeIdx,
                   cpShelfIdx,
                   cpSlotIdx,
                   cpUpgradeResult,
                   evtDateAndTime,
                   trapSeqNum,
                   evtDescription,
                   evtObjectType,
                   evtCodeType }
    STATUS       current
    DESCRIPTION  "Indicates the result of the check upgrade step of the
                  system-wide software upgrade process."
    ::= { cpEvtNotifications 0 2 }


cpUpgradeTransferResultEvt NOTIFICATION-TYPE
    OBJECTS      { cpTypeIdx,
                   cpShelfIdx,
                   cpSlotIdx,
                   cpUpgradeResult,
                   evtDateAndTime,
                   trapSeqNum,
                   evtDescription,
                   evtObjectType,
                   evtCodeType }
    STATUS       current
    DESCRIPTION  "Indicates the result of the software download step of the
                  system-wide software upgrade process."
    ::= { cpEvtNotifications 0 3 }


cpUpgradeStageResultEvt NOTIFICATION-TYPE
    OBJECTS      { cpTypeIdx,
                   cpShelfIdx,
                   cpSlotIdx,
                   cpUpgradeStage,
                   cpUpgradeResult,
                   evtDateAndTime,
                   trapSeqNum,
                   evtDescription,
                   evtObjectType,
                   evtCodeType }
    STATUS       current
    DESCRIPTION  "The software upgrade process on the active circuit pack in the
                  identified slot has completed a stage."
    ::= { cpEvtNotifications 0 4 }


cpDbBackupResultEvt NOTIFICATION-TYPE
    OBJECTS      { cpTypeIdx,
                   cpShelfIdx,
                   cpSlotIdx,
                   dbBackupAndRestoreAddress,
                   dbBackupAndRestorePath,
                   dbBackupAndRestoreResult,
                   evtDateAndTime,
                   trapSeqNum,
                   evtDescription,
                   evtObjectType,
                   evtCodeType }
    STATUS       current
    DESCRIPTION  "Indicates the result of an NE database backup operation."
    ::= { cpEvtNotifications 0 5 }


cpDbRestoreTransferResultEvt NOTIFICATION-TYPE
    OBJECTS      { cpTypeIdx,
                   cpShelfIdx,
                   cpSlotIdx,
                   dbBackupAndRestoreAddress,
                   dbBackupAndRestorePath,
                   dbBackupAndRestoreResult,
                   evtDateAndTime,
                   trapSeqNum,
                   evtDescription,
                   evtObjectType,
                   evtCodeType }
    STATUS       current
    DESCRIPTION  "Indicates the result of the database download step of the NE
                  database restore process."
    ::= { cpEvtNotifications 0 6 }


cpDbInvokeResultEvt NOTIFICATION-TYPE
    OBJECTS      { cpTypeIdx,
                   cpShelfIdx,
                   cpSlotIdx,
                   dbBackupAndRestoreResult,
                   evtDateAndTime,
                   trapSeqNum,
                   evtDescription,
                   evtObjectType,
                   evtCodeType }
    STATUS       current
    DESCRIPTION  "Indicates the result of the invoke step of the NE database
                  restore process."
    ::= { cpEvtNotifications 0 7 }

-- Obsolete as of release 7.3.0
cpDbApplyResultEvt NOTIFICATION-TYPE
    OBJECTS      { cpTypeIdx,
                   cpShelfIdx,
                   cpSlotIdx,
                   dbBackupAndRestoreResult,
                   evtDateAndTime,
                   trapSeqNum,
                   evtDescription,
                   evtObjectType,
                   evtCodeType }
    STATUS       obsolete
    DESCRIPTION  "Indicates the result of the accept step of the NE database
                  restore process."
    ::= { cpEvtNotifications 0 8 }

oaStatusChangeEvt NOTIFICATION-TYPE
    OBJECTS      { oaTypeIdx,
                   oaShelfIdx,
                   oaSlotIdx,
                   oaIdx,
                   oaOperStatus,
                   oaOperStatQlfr,
                   evtDateAndTime,
                   trapSeqNum,
                   evtDescription,
                   evtObjectType,
                   evtCodeType }
    STATUS       current
    DESCRIPTION  "Notification of a change in the optical amplifier's
                  operational status or operational status qualifier."
    ::= { oaEvtNotifications 0 1 }


xcvrStatusChangeEvt NOTIFICATION-TYPE
    OBJECTS      { xcvrTypeIdx,
                   xcvrShelfIdx,
                   xcvrSlotIdx,
                   xcvrIdx,
                   xcvrOperStatus,
                   xcvrOperStatQlfr,
                   evtDateAndTime,
                   trapSeqNum,
                   evtDescription,
                   evtObjectType,
                   evtCodeType }
    STATUS       current
    DESCRIPTION  "Notification of a change in the transceiver's operational
                  status or operational status qualifier."
    ::= { xcvrEvtNotifications 0 1 }


xcvrProtSwitchEvt NOTIFICATION-TYPE
    OBJECTS      { xcvrTypeIdx,
                   xcvrShelfIdx,
                   xcvrSlotIdx,
                   xcvrIdx,
                   xcvrProtSwEvtType,
                   evtDateAndTime,
                   trapSeqNum,
                   evtDescription,
                   evtObjectType,
                   evtCodeType }
    STATUS       current
    DESCRIPTION  "A protection switch has occured on the optical transceiver
                  facility."
    ::= { xcvrEvtNotifications 0 2 }


xcvrTcaEvt NOTIFICATION-TYPE
    OBJECTS      { xcvrTypeIdx,
                   xcvrShelfIdx,
                   xcvrSlotIdx,
                   xcvrIdx,
                   tcaIntervalType,
                   tcaDateAndTime,
                   tcaMontype,
                   tcaValue,
                   tcaThreshold,
                   evtDateAndTime,
                   trapSeqNum,
                   evtDescription,
                   evtObjectType,
                   evtCodeType }
    STATUS       current
    DESCRIPTION  "This trap provides a threshold crossing alert for a
                  performance monitoring statistic on an optical transceiver
                  port."
    ::= { xcvrEvtNotifications 0 3 }


amdStatusChangeEvt NOTIFICATION-TYPE
    OBJECTS      { amdTypeIdx,
                   amdShelfIdx,
                   amdSlotIdx,
                   amdLineIdx,
                   amdPortIdx,
                   amdOperStatus,
                   amdOperStatQlfr,
                   evtDateAndTime,
                   trapSeqNum,
                   evtDescription,
                   evtObjectType,
                   evtCodeType }
    STATUS       obsolete
    DESCRIPTION  "Notification of a change in the operational status or
                  operational status qualifier of an active
                  multiplexer-demultiplexer port."
    ::= { amdEvtNotifications 0 1 }


oscStatusChangeEvt NOTIFICATION-TYPE
    OBJECTS      { oscShelfIdx,
                   oscSlotIdx,
                   oscIdx,
                   oscOperStatus,
                   oscOperStatQlfr,
                   evtDateAndTime,
                   trapSeqNum,
                   evtDescription,
                   evtObjectType,
                   evtCodeType }
    STATUS       current
    DESCRIPTION  "Notification of a change in the optical supervisory channels's
                  operational status or operational status qualifier."
    ::= { dataCommsEvtNotifications 0 1 }


netMgmtStatusChangeEvt NOTIFICATION-TYPE
    OBJECTS      { netMgmtIdx,
                   netMgmtOperStatus,
                   netMgmtOperStatQlfr,
                   evtDateAndTime,
                   trapSeqNum,
                   evtDescription,
                   evtObjectType,
                   evtCodeType }
    STATUS       current
    DESCRIPTION  "Notification of a change in the network management interface's
                  operational status or operational status qualifier."
    ::= { dataCommsEvtNotifications 0 2 }


ocnStatusChangeEvt NOTIFICATION-TYPE
    OBJECTS      { ocnTypeIdx,
                   ocnShelfIdx,
                   ocnSlotIdx,
                   ocnPortIdx,
                   ocnOperStatus,
                   ocnOperStatQlfr,
                   evtDateAndTime,
                   trapSeqNum,
                   evtDescription,
                   evtObjectType,
                   evtCodeType }
    STATUS       current
    DESCRIPTION  "Notification of a change in the operational status or
                  operational status qualifier of a SONET OC-N facility port."
    ::= { ocnEvtNotifications 0 1 }


ocnTcaEvt NOTIFICATION-TYPE
    OBJECTS      { ocnTypeIdx,
                   ocnShelfIdx,
                   ocnSlotIdx,
                   ocnPortIdx,
                   tcaIntervalType,
                   tcaDateAndTime,
                   tcaMontype,
                   tcaValue,
                   tcaThreshold,
                   evtDateAndTime,
                   trapSeqNum,
                   evtDescription,
                   evtObjectType,
                   evtCodeType }
    STATUS       current
    DESCRIPTION  "This trap provides a threshold crossing alert for a
                  performance monitoring statistic on a SONET OC-N facility."
    ::= { ocnEvtNotifications 0 2 }
  
  
ocnProtSwitchEvt NOTIFICATION-TYPE
    OBJECTS      { ocnTypeIdx,
                   ocnShelfIdx,
                   ocnSlotIdx,
                   ocnPortIdx,
                   ocnProtSwEvtType,
                   evtDateAndTime,
                   trapSeqNum,
                   evtDescription,
                   evtObjectType,
                   evtCodeType }
    STATUS       current
    DESCRIPTION  "A protection switch has occured on the identified OC-N
                  facility."
    ::= { ocnEvtNotifications 0 3 }


stsnProtSwitchEvt NOTIFICATION-TYPE
    OBJECTS      { stsnTypeIdx,
                   stsnShelfIdx,
                   stsnSlotIdx,
                   stsnPortIdx,
                   stsnIdx,
                   stsnProtSwEvtType,
                   evtDateAndTime,
                   trapSeqNum,
                   evtDescription,
                   evtObjectType,
                   evtCodeType }
    STATUS       current
    DESCRIPTION  "A protection switch has occured on the identified STS-N
                  channel."
    ::= { stsnEvtNotifications 0 2 }


stsnTcaEvt NOTIFICATION-TYPE
    OBJECTS      { stsnTypeIdx,
                   stsnShelfIdx,
                   stsnSlotIdx,
                   stsnPortIdx,
                   stsnIdx,
                   tcaIntervalType,
                   tcaDateAndTime,
                   tcaMontype,
                   tcaValue,
                   tcaThreshold,
                   evtDateAndTime,
                   trapSeqNum,
                   evtDescription,
                   evtObjectType,
                   evtCodeType }
    STATUS       current
    DESCRIPTION  "This trap provides a threshold crossing alert for a
                  performance monitoring statistic on a SONET STS-N facility."
    ::= { stsnEvtNotifications 0 3 }


stmnStatusChangeEvt NOTIFICATION-TYPE
    OBJECTS      { stmnTypeIdx,
                   stmnShelfIdx,
                   stmnSlotIdx,
                   stmnPortIdx,
                   stmnOperStatus,
                   stmnOperStatQlfr,
                   evtDateAndTime,
                   trapSeqNum,
                   evtDescription,
                   evtObjectType,
                   evtCodeType }
    STATUS       current
    DESCRIPTION  "Notification of a change in the operational status or
                  operational status qualifier of a SDH STM-N facility port."
    ::= { stmnEvtNotifications 0 1 }


stmnTcaEvt NOTIFICATION-TYPE
    OBJECTS      { stmnTypeIdx,
                   stmnShelfIdx,
                   stmnSlotIdx,
                   stmnPortIdx,
                   tcaIntervalType,
                   tcaDateAndTime,
                   tcaMontype,
                   tcaValue,
                   tcaThreshold,
                   evtDateAndTime,
                   trapSeqNum,
                   evtDescription,
                   evtObjectType,
                   evtCodeType }
    STATUS       current
    DESCRIPTION  "This trap provides a threshold crossing alert for a
                  performance monitoring statistic on a SDH STM-N facility."
    ::= { stmnEvtNotifications 0 2 }
    
    
stmnProtSwitchEvt NOTIFICATION-TYPE
    OBJECTS      { stmnTypeIdx,
                   stmnShelfIdx,
                   stmnSlotIdx,
                   stmnPortIdx,
                   stmnProtSwEvtType,
                   evtDateAndTime,
                   trapSeqNum,
                   evtDescription,
                   evtObjectType,
                   evtCodeType }
    STATUS       current
    DESCRIPTION  "A protection switch has occured on the identified STM-N
                  facility."
    ::= { stmnEvtNotifications 0 3 }


vcnProtSwitchEvt NOTIFICATION-TYPE
    OBJECTS      { vcnTypeIdx,
                   vcnShelfIdx,
                   vcnSlotIdx,
                   vcnPortIdx,
                   vcnIdx,
                   vcnProtSwEvtType,
                   evtDateAndTime,
                   trapSeqNum,
                   evtDescription,
                   evtObjectType,
                   evtCodeType }
    STATUS       current
    DESCRIPTION  "A protection switch has occured on the identified VC-N
                  channel."
    ::= { vcnEvtNotifications 0 2 }


vcnTcaEvt NOTIFICATION-TYPE
    OBJECTS      { vcnTypeIdx,
                   vcnShelfIdx,
                   vcnSlotIdx,
                   vcnPortIdx,
                   vcnIdx,
                   tcaIntervalType,
                   tcaDateAndTime,
                   tcaMontype,
                   tcaValue,
                   tcaThreshold,
                   evtDateAndTime,
                   trapSeqNum,
                   evtDescription,
                   evtObjectType,
                   evtCodeType }
    STATUS       current
    DESCRIPTION  "This trap provides a threshold crossing alert for a
                  performance monitoring statistic on a SDH VC-N facility."
    ::= { vcnEvtNotifications 0 3 }


geStatusChangeEvt NOTIFICATION-TYPE
    OBJECTS      { geShelfIdx,
                   geSlotIdx,
                   gePortIdx,
                   geOperStatus,
                   geOperStatQlfr,
                   evtDateAndTime,
                   trapSeqNum,
                   evtDescription,
                   evtObjectType,
                   evtCodeType }
    STATUS       current
    DESCRIPTION  "Notification of a change in the operational status or
                  operational status qualifier of a Gigabit Ethernet facility
                  port."
    ::= { geEvtNotifications 0 1 }


geTcaEvt NOTIFICATION-TYPE
    OBJECTS      { geShelfIdx,
                   geSlotIdx,
                   gePortIdx,
                   tcaIntervalType,
                   tcaDateAndTime,
                   tcaMontype,
                   tcaValue,
                   tcaThreshold,
                   evtDateAndTime,
                   trapSeqNum,
                   evtDescription,
                   evtObjectType,
                   evtCodeType }
    STATUS       current
    DESCRIPTION  "This trap provides a threshold crossing alert for a
                  performance monitoring statistic on a Gigabit Ethernet
                  facility."
    ::= { geEvtNotifications 0 2 }


fcStatusChangeEvt NOTIFICATION-TYPE
    OBJECTS      { fcShelfIdx,
                   fcSlotIdx,
                   fcPortIdx,
                   fcOperStatus,
                   fcOperStatQlfr,
                   evtDateAndTime,
                   trapSeqNum,
                   evtDescription,
                   evtObjectType,
                   evtCodeType }
    STATUS       current
    DESCRIPTION  "Notification of a change in the operational status or
                  operational status qualifier of a Fiber Channel facility
                  port."
    ::= { fcEvtNotifications 0 1 }


fcTcaEvt NOTIFICATION-TYPE
    OBJECTS      { fcShelfIdx,
                   fcSlotIdx,
                   fcPortIdx,
                   tcaIntervalType,
                   tcaDateAndTime,
                   tcaMontype,
                   tcaValue,
                   tcaThreshold,
                   evtDateAndTime,
                   trapSeqNum,
                   evtDescription,
                   evtObjectType,
                   evtCodeType }
    STATUS       current
    DESCRIPTION  "This trap provides a threshold crossing alert for a
                  performance monitoring statistic on a Fiber Channel facility."
    ::= { fcEvtNotifications 0 2 }


ethL1IFStatusChangeEvt NOTIFICATION-TYPE
    OBJECTS      { ethIntfShelfIdx,
                   ethIntfSlotIdx,
                   ethIntfPortTypeIdx,
                   ethIntfPortIdx,
                   ethIntfOperStatus,
                   ethIntfOperStatQlfr,
                   evtDateAndTime,
                   trapSeqNum,
                   evtDescription,
                   evtObjectType,
                   evtCodeType }
    STATUS       current
    DESCRIPTION  "Notification of a change in the operational status or
                  operational status qualifier of a L1 Ethernet facility
                  port."
    ::= { ethPortEvtNotifications 0 1 }
    
ethL1IFTcaEvt NOTIFICATION-TYPE
    OBJECTS      { ethIntfShelfIdx,
                   ethIntfSlotIdx,
                   ethIntfPortTypeIdx,
                   ethIntfPortIdx,
                   tcaIntervalType,
                   tcaDateAndTime,
                   tcaMontype,
                   tcaValue,
                   tcaThreshold,
                   evtDateAndTime,
                   trapSeqNum,
                   evtDescription,
                   evtObjectType,
                   evtCodeType }
    STATUS       current
    DESCRIPTION  "This trap provides a threshold crossing alert for a
                  performance monitoring statistic on an Ethernet Layer 1
                  interface facility."
    ::= { ethPortEvtNotifications 0 2 }
    
    
pvxL2IFTcaEvt NOTIFICATION-TYPE
    OBJECTS      { pvxL2IntfSwitchIdx,
                   pvxL2IntfShelfIdx,
                   pvxL2IntfSlotIdx,
                   pvxL2IntfPortTypeIdx,
                   pvxL2IntfPortIdx,
                   tcaIntervalType,
                   tcaDateAndTime,
                   tcaMontype,
                   tcaValue,
                   tcaThreshold,
                   evtDateAndTime,
                   trapSeqNum,
                   evtDescription,
                   evtObjectType,
                   evtCodeType }
    STATUS       current
    DESCRIPTION  "This trap provides a threshold crossing alert for a
                  performance monitoring statistic on a PVX Pack Ethernet Layer 2
                  interface facility."
    ::= { pvxL2EvtNotifications 0 2 }


briStatusChangeEvt NOTIFICATION-TYPE
    OBJECTS      { briShelfIdx,
                   briSlotIdx,
                   briPortIdx,
                   briOperStatus,
                   briOperStatQlfr,
                   evtDateAndTime,
                   trapSeqNum,
                   evtDescription,
                   evtObjectType,
                   evtCodeType }
    STATUS       current
    DESCRIPTION  "Notification of a change in the operational status or
                  operational status qualifier of a BRI facility port."
    ::= { briEvtNotifications 0 1 }

cpSynchronizationSwitchEvt NOTIFICATION-TYPE
    OBJECTS      { cpSynchronizationTypeIdx,
                   cpSynchronizationShelfIdx,
                   cpSynchronizationSlotIdx,
                   cpSynchronizationSwEvtType,
                   evtDateAndTime,
                   trapSeqNum,
                   evtDescription,
                   evtObjectType,
                   evtCodeType }
    STATUS       current
    DESCRIPTION  "A synchronization timing reference switch has occurred
                  on the identified circuit pack."
    ::= { cpSynchronizationEvtNotifications 0 1 }




-----------------------------------------------------------------------
-- Condition Notifications
-----------------------------------------------------------------------


-- shelfInvMissingCond and shelfInvMissingClear traps have been
-- replaced by the shelfInvSysCommCond and shelfInvSysCommClear
-- notifications and, as such, have been marked as obsolete

shelfInvMissingCond NOTIFICATION-TYPE
    OBJECTS      { shelfInvIdx,
                   condReportType,
                   condDateAndTime,
                   condSeverity,
                   condServiceAffecting,
                   trapSeqNum,
                   condDescription,
                   condObjectType,
                   condCodeType }
    STATUS       obsolete
    DESCRIPTION  "An expansion shelf is missing. To clear this condition, attach
                  an appropriate expansion shelf to the MSCP in the main shelf
                  of the system."
    ::= { shelfInvCondNotifications 0 1 }


shelfInvMissingClear NOTIFICATION-TYPE
    OBJECTS      { shelfInvIdx,
                   condReportType,
                   condDateAndTime,
                   condSeverity,
                   condServiceAffecting,
                   trapSeqNum,
                   condDescription,
                   condObjectType,
                   condCodeType }
    STATUS       obsolete
    DESCRIPTION  "A previously active shelf missing condition has cleared."
    ::= { shelfInvCondNotifications 0 2 }


shelfInvUnknownCond NOTIFICATION-TYPE
    OBJECTS      { shelfInvIdx,
                   condReportType,
                   condDateAndTime,
                   condSeverity,
                   condServiceAffecting,
                   trapSeqNum,
                   condDescription,
                   condObjectType,
                   condCodeType }
    STATUS       current
    DESCRIPTION  "A shelf is unknown to the system. This condition occurs
                  because the shelf is unknown to the system (for example, the
                  the FRU data cannot be read on the expansion shelf interface
                  (ESI) circuit pack in the expansion shelf). To clear this
                  condition, connect an appropriate shelf to its associated
                  MSCP."
    ::= { shelfInvCondNotifications 0 3 }


shelfInvUnknownClear NOTIFICATION-TYPE
    OBJECTS      { shelfInvIdx,
                   condReportType,
                   condDateAndTime,
                   condSeverity,
                   condServiceAffecting ,
                   trapSeqNum,
                   condDescription,
                   condObjectType,
                   condCodeType }
    STATUS       current
    DESCRIPTION  "A previously active shelf unknown condition has cleared."
    ::= { shelfInvCondNotifications 0 4 }


-- The shelfInvExpansionShelfCommLOSCond, shelfInvExpansionShelfCommLinkDownCond,
-- and shelfInvExpansionShelfCommDeviceUnsupportedCond traps provide specific
-- shelf communications failure indications and, as such, the shelfInvCommCond
-- and shelfInvCommClear notifications are marked as obsolete

shelfInvCommCond NOTIFICATION-TYPE
    OBJECTS      { shelfInvIdx,
                   condReportType,
                   condDateAndTime,
                   condSeverity,
                   condServiceAffecting,
                   trapSeqNum,
                   condDescription,
                   condObjectType,
                   condCodeType }
    STATUS       obsolete
    DESCRIPTION  "This condition indicates that a connected expansion shelf has
                  a communications failure between the multiport system control
                  processor (MSCP) and the expansion shelf interface (ESI)
                  circuit packs."
    ::= { shelfInvCondNotifications 0 5 }


shelfInvCommClear NOTIFICATION-TYPE
    OBJECTS      { shelfInvIdx,
                   condReportType,
                   condDateAndTime,
                   condSeverity,
                   condServiceAffecting,
                   trapSeqNum,
                   condDescription,
                   condObjectType,
                   condCodeType }
    STATUS       obsolete
    DESCRIPTION  "A previously active shelf communications condition has
                  cleared."
    ::= { shelfInvCondNotifications 0 6 }


shelfInvPwrFeedAFailCond NOTIFICATION-TYPE
    OBJECTS      { shelfInvIdx,
                   condReportType,
                   condDateAndTime,
                   condSeverity,
                   condServiceAffecting,
                   trapSeqNum,
                   condDescription,
                   condObjectType,
                   condCodeType }
    STATUS       current
    DESCRIPTION  "There is a power feed A failure. The system can continue to
                  function on power feed B. Plan to diagnose and correct the
                  problem as soon as possible."
    ::= { shelfInvCondNotifications 0 7 }


shelfInvPwrFeedAFailClear NOTIFICATION-TYPE
    OBJECTS      { shelfInvIdx,
                   condReportType,
                   condDateAndTime,
                   condSeverity,
                   condServiceAffecting,
                   trapSeqNum,
                   condDescription,
                   condObjectType,
                   condCodeType }
    STATUS       current
    DESCRIPTION  "A previously active Power feed A condition has cleared."
    ::= { shelfInvCondNotifications 0 8 }


shelfInvPwrFeedBFailCond NOTIFICATION-TYPE
    OBJECTS      { shelfInvIdx,
                   condReportType,
                   condDateAndTime,
                   condSeverity,
                   condServiceAffecting,
                   trapSeqNum,
                   condDescription,
                   condObjectType,
                   condCodeType }
    STATUS       current
    DESCRIPTION  "There is a power feed B failure. The system can continue to
                  function on power feed A. Plan to diagnose and correct the
                  problem as soon as possible."
    ::= { shelfInvCondNotifications 0 9 }


shelfInvPwrFeedBFailClear NOTIFICATION-TYPE
    OBJECTS      { shelfInvIdx,
                   condReportType,
                   condDateAndTime,
                   condSeverity,
                   condServiceAffecting,
                   trapSeqNum,
                   condDescription,
                   condObjectType,
                   condCodeType }
    STATUS       current
    DESCRIPTION  "A previously active Power feed B condition has cleared."
    ::= { shelfInvCondNotifications 0 10 }


shelfInvPwrBrownoutCond NOTIFICATION-TYPE
    OBJECTS      { shelfInvIdx,
                   condReportType,
                   condDateAndTime,
                   condSeverity,
                   condServiceAffecting,
                   trapSeqNum,
                   condDescription,
                   condObjectType,
                   condCodeType }
    STATUS       current
    DESCRIPTION  "There is a system power brownout. As voltage levels decrease,
                  the amplifiers fail, followed by the MSCP, and then the
                  cooling unit fails."
    ::= { shelfInvCondNotifications 0 11 }


shelfInvPwrBrownoutClear NOTIFICATION-TYPE
    OBJECTS      { shelfInvIdx,
                   condReportType,
                   condDateAndTime,
                   condSeverity,
                   condServiceAffecting,
                   trapSeqNum,
                   condDescription,
                   condObjectType,
                   condCodeType }
    STATUS       current
    DESCRIPTION  "A previously active power brownout condition on the shelf has
                  cleared."
    ::= { shelfInvCondNotifications 0 12 }


shelfInvSysCommCond NOTIFICATION-TYPE
    OBJECTS      { shelfInvIdx,
                   condReportType,
                   condDateAndTime,
                   condSeverity,
                   condServiceAffecting,
                   trapSeqNum,
                   condDescription,
                   condObjectType,
                   condCodeType }
    STATUS       deprecated
    DESCRIPTION  "This condition indicates that backplane communication between
                  the multiport system control processor (MSCP) and the affected
                  circuit pack is interrupted. Normal OAM&P operations to the
                  circuit pack, like provisioning and performance monitoring,
                  are affected while this alarm is active."
    ::= { shelfInvCondNotifications 0 13 }


shelfInvSysCommClear NOTIFICATION-TYPE
    OBJECTS      { shelfInvIdx,
                   condReportType,
                   condDateAndTime,
                   condSeverity,
                   condServiceAffecting,
                   trapSeqNum,
                   condDescription,
                   condObjectType,
                   condCodeType }
    STATUS       deprecated
    DESCRIPTION  "A previously active shelf missing condition has cleared."
    ::= { shelfInvCondNotifications 0 14 }


shelfInvExpansionShelfIdMismatchCond NOTIFICATION-TYPE
    OBJECTS      { shelfInvIdx,
                   shelfInvExpectedNEName,
                   shelfInvExpectedIPAddress,
                   shelfInvExpectedShelfNum,
                   shelfInvExpectedMSISerialNum,
                   shelfInvDiscoveredNEName,
                   shelfInvDiscoveredIPAddress,
                   shelfInvDiscoveredShelfNum,
                   shelfInvDiscoveredMSISerialNum,
                   condReportType,
                   condDateAndTime,
                   condSeverity,
                   condServiceAffecting,
                   trapSeqNum,
                   condDescription,
                   condObjectType,
                   condCodeType }
    STATUS       current
    DESCRIPTION  "Indicates that the identifying information of the discovered
                  expansion shelf does not match that of the expected shelf."
    ::= { shelfInvCondNotifications 0 15 }


shelfInvExpansionShelfIdMismatchClear NOTIFICATION-TYPE
    OBJECTS      { shelfInvIdx,
                   condReportType,
                   condDateAndTime,
                   condSeverity,
                   condServiceAffecting,
                   trapSeqNum,
                   condDescription,
                   condObjectType,
                   condCodeType }
    STATUS       current
    DESCRIPTION  "A previously active expansion shelf identifier mismatch
                  condition has cleared."
    ::= { shelfInvCondNotifications 0 16 }


shelfInvExpansionShelfCommLOSCond NOTIFICATION-TYPE
    OBJECTS      { shelfInvIdx,
                   condReportType,
                   condDateAndTime,
                   condSeverity,
                   condServiceAffecting,
                   trapSeqNum,
                   condDescription,
                   condObjectType,
                   condCodeType }
    STATUS       current
    DESCRIPTION  "This alarm indicates that a connected expansion shelf has a
                  loss of signal between the multiport system control processor
                  (MSCP) and the expansion shelf interface (ESI) circuit packs.
                  The most likely causes are a fiber cut or a fault with the
                  Molex connector and cable assembly."
    ::= { shelfInvCondNotifications 0 17 }



shelfInvExpansionShelfCommLOSClear NOTIFICATION-TYPE
    OBJECTS      { shelfInvIdx,
                   condReportType,
                   condDateAndTime,
                   condSeverity,
                   condServiceAffecting,
                   trapSeqNum,
                   condDescription,
                   condObjectType,
                   condCodeType }
    STATUS       current
    DESCRIPTION  "A previously active expansion shelf communications LOS
                  condition has cleared."
    ::= { shelfInvCondNotifications 0 18 }


shelfInvExpansionShelfCommLinkDownCond NOTIFICATION-TYPE
    OBJECTS      { shelfInvIdx,
                   condReportType,
                   condDateAndTime,
                   condSeverity,
                   condServiceAffecting,
                   trapSeqNum,
                   condDescription,
                   condObjectType,
                   condCodeType }
    STATUS       current
    DESCRIPTION  "This alarm indicates that a connected expansion shelf has a
                  communications failure between the multiport system control
                  processor (MSCP) and the expansion shelf interface (ESI)
                  circuit packs."
    ::= { shelfInvCondNotifications 0 19 }


shelfInvExpansionShelfCommLinkDownClear NOTIFICATION-TYPE
    OBJECTS      { shelfInvIdx,
                   condReportType,
                   condDateAndTime,
                   condSeverity,
                   condServiceAffecting,
                   trapSeqNum,
                   condDescription,
                   condObjectType,
                   condCodeType }
    STATUS       current
    DESCRIPTION  "A previously active expansion shelf communications link down
                  condition has cleared."
    ::= { shelfInvCondNotifications 0 20 }


shelfInvExpansionShelfCommDeviceUnsupportedCond NOTIFICATION-TYPE
    OBJECTS      { shelfInvIdx,
                   condReportType,
                   condDateAndTime,
                   condSeverity,
                   condServiceAffecting,
                   trapSeqNum,
                   condDescription,
                   condObjectType,
                   condCodeType }
    STATUS       current
    DESCRIPTION  "This alarm indicates that an unknown device is connected to
                  the expansion shelf port of the multiport system control
                  processor (MSCP) on the main shelf."
    ::= { shelfInvCondNotifications 0 21 }


shelfInvExpansionShelfCommDeviceUnsupportedClear NOTIFICATION-TYPE
    OBJECTS      { shelfInvIdx,
                   condReportType,
                   condDateAndTime,
                   condSeverity,
                   condServiceAffecting,
                   trapSeqNum,
                   condDescription,
                   condObjectType,
                   condCodeType }
    STATUS       current
    DESCRIPTION  "A previously active expansion shelf communications device
                  unsupported condition has cleared."
    ::= { shelfInvCondNotifications 0 22 }


shelfInvTempMaxCond NOTIFICATION-TYPE
    OBJECTS      { shelfInvIdx,
                   condReportType,
                   condDateAndTime,
                   condSeverity,
                   condServiceAffecting,
                   trapSeqNum,
                   condDescription,
                   condObjectType,
                   condCodeType }
    STATUS       current
    DESCRIPTION  "Indicates that the temperature on the identified shelf has
                  risen above the maximum threshold."
    ::= { shelfInvCondNotifications 0 23 }


shelfInvTempMaxClear NOTIFICATION-TYPE
    OBJECTS      { shelfInvIdx,
                   condReportType,
                   condDateAndTime,
                   condSeverity,
                   condServiceAffecting,
                   trapSeqNum,
                   condDescription,
                   condObjectType,
                   condCodeType }
    STATUS       current
    DESCRIPTION  "A previously active shelf inventory maximum temperature
                  condition has cleared."
    ::= { shelfInvCondNotifications 0 24 }


slotInvMissingCond NOTIFICATION-TYPE
    OBJECTS      { slotInvShelfIdx,
                   slotInvSlotTypeIdx,
                   slotInvSlotIdx,
                   condReportType,
                   condDateAndTime,
                   condSeverity,
                   condServiceAffecting,
                   trapSeqNum,
                   condDescription,
                   condObjectType,
                   condCodeType }
    STATUS       current
    DESCRIPTION  "A Circuit pack is missing. The alarm is triggered for one of
                  the following reasons: the provisioned circuit pack is missing
                  from its associated slot a filler circuit pack is missing from
                  an unprovisioned single-width or doublewidth slot a
                  single-width circuit pack is provisioned in a double-width
                  slot To clear this alarm, insert an appropriate single-width
                  or double-width circuit pack or filler circuit pack in the
                  associated single-width or double-width slot."
    ::= { slotInvCondNotifications 0 1 }


slotInvMissingClear NOTIFICATION-TYPE
    OBJECTS      { slotInvShelfIdx,
                   slotInvSlotTypeIdx,
                   slotInvSlotIdx,
                   condReportType,
                   condDateAndTime,
                   condSeverity,
                   condServiceAffecting,
                   trapSeqNum,
                   condDescription,
                   condObjectType,
                   condCodeType }
    STATUS       current
    DESCRIPTION  "A previously active circuit pack or replaceable unit missing
                  condition has cleared."
    ::= { slotInvCondNotifications 0 2 }


slotInvUnknownCond NOTIFICATION-TYPE
    OBJECTS      { slotInvShelfIdx,
                   slotInvSlotTypeIdx,
                   slotInvSlotIdx,
                   condReportType,
                   condDateAndTime,
                   condSeverity,
                   condServiceAffecting,
                   trapSeqNum,
                   condDescription,
                   condObjectType,
                   condCodeType }
    STATUS       current
    DESCRIPTION  "Circuit pack type is unknown to the system. This condition
                  occurs for the following two reasons: the circuit pack in the
                  associated slot is unknown to the system (for example, the
                  circuit pack is not supported by the software release running
                  on the system) two single-width circuit packs are in a
                  double-width slot To clear this condition, insert an
                  appropriate circuit pack in the associated slot."
    ::= { slotInvCondNotifications 0 3 }


slotInvUnknownClear NOTIFICATION-TYPE
    OBJECTS      { slotInvShelfIdx,
                   slotInvSlotTypeIdx,
                   slotInvSlotIdx,
                   condReportType,
                   condDateAndTime,
                   condSeverity,
                   condServiceAffecting,
                   trapSeqNum,
                   condDescription,
                   condObjectType,
                   condCodeType }
    STATUS       current
    DESCRIPTION  "A previously active circuit pack or replaceable unit unknown
                  condition has cleared."
    ::= { slotInvCondNotifications 0 4 }



slotInvCommCond NOTIFICATION-TYPE
    OBJECTS      { slotInvShelfIdx,
                   slotInvSlotTypeIdx,
                   slotInvSlotIdx,
                   condReportType,
                   condDateAndTime,
                   condSeverity,
                   condServiceAffecting,
                   trapSeqNum,
                   condDescription,
                   condObjectType,
                   condCodeType }
    STATUS       current
    DESCRIPTION  "This alarm indicates that backplane communication between the
                  multiport system control processor (MSCP) and the circuit pack
                  is interrupted. Normal OAM&P operations to the circuit pack,
                  like provisioning and performance monitoring, are affected
                  while this alarm is active. If an amplifier or wavelength
                  conversion circuit pack has been provisioned already, it
                  continues to operate normally."
    ::= { slotInvCondNotifications 0 5 }


slotInvCommClear NOTIFICATION-TYPE
    OBJECTS      { slotInvShelfIdx,
                   slotInvSlotTypeIdx,
                   slotInvSlotIdx,
                   condReportType,
                   condDateAndTime,
                   condSeverity,
                   condServiceAffecting,
                   trapSeqNum,
                   condDescription,
                   condObjectType,
                   condCodeType }
    STATUS       current
    DESCRIPTION  "A previously active circuit pack communications condition has
                  cleared."
    ::= { slotInvCondNotifications 0 6 }


slotInvFailCond NOTIFICATION-TYPE
    OBJECTS      { slotInvShelfIdx,
                   slotInvSlotTypeIdx,
                   slotInvSlotIdx,
                   condReportType,
                   condDateAndTime,
                   condSeverity,
                   condServiceAffecting,
                   trapSeqNum,
                   condDescription,
                   condObjectType,
                   condCodeType }
    STATUS       current
    DESCRIPTION  "There is a circuit pack failure. The alarm is critical when a
                  circuit pack is provisioned and that it has fails in its
                  associated slot."
    ::= { slotInvCondNotifications 0 7 }


slotInvFailClear NOTIFICATION-TYPE
    OBJECTS      { slotInvShelfIdx,
                   slotInvSlotTypeIdx,
                   slotInvSlotIdx,
                   condReportType,
                   condDateAndTime,
                   condSeverity,
                   condServiceAffecting,
                   trapSeqNum,
                   condDescription,
                   condObjectType,
                   condCodeType }
    STATUS       current
    DESCRIPTION  "A previously active circuit pack fail condition has cleared."
    ::= { slotInvCondNotifications 0 8 }


slotInvUpgradeInProgressCond NOTIFICATION-TYPE
    OBJECTS      { slotInvShelfIdx,
                   slotInvSlotTypeIdx,
                   slotInvSlotIdx,
                   condReportType,
                   condDateAndTime,
                   condSeverity,
                   condServiceAffecting,
                   trapSeqNum,
                   condDescription,
                   condObjectType,
                   condCodeType }
    STATUS       current
    DESCRIPTION  "A software upgrade process has begun on the circuit pack in
                  the identified slot."
    ::= { slotInvCondNotifications 0 9 }


slotInvUpgradeInProgressClear NOTIFICATION-TYPE
    OBJECTS      { slotInvShelfIdx,
                   slotInvSlotTypeIdx,
                   slotInvSlotIdx,
                   condReportType,
                   condDateAndTime,
                   condSeverity,
                   condServiceAffecting,
                   trapSeqNum,
                   condDescription,
                   condObjectType,
                   condCodeType }
    STATUS       current
    DESCRIPTION  "There is an auto upgrade in progress. This alarm is typically
                  seen when inserting a circuit pack other than a multiport
                  system control processor (MSCP)."
    ::= { slotInvCondNotifications 0 10 }


slotInvUpgradeFailureCond NOTIFICATION-TYPE
    OBJECTS      { slotInvShelfIdx,
                   slotInvSlotTypeIdx,
                   slotInvSlotIdx,

                   condReportType,
                   condDateAndTime,
                   condSeverity,
                   condServiceAffecting,
                   trapSeqNum,
                   condDescription,
                   condObjectType,
                   condCodeType }
    STATUS       current
    DESCRIPTION  "There is a circuit pack upgrade failure."
    ::= { slotInvCondNotifications 0 11 }


slotInvUpgradeFailureClear NOTIFICATION-TYPE
    OBJECTS      { slotInvShelfIdx,
                   slotInvSlotTypeIdx,
                   slotInvSlotIdx,
                   condReportType,
                   condDateAndTime,
                   condSeverity,
                   condServiceAffecting,
                   trapSeqNum,
                   condDescription,
                   condObjectType,
                   condCodeType }
    STATUS       current
    DESCRIPTION  "A previously active circuit pack software upgrade failure
                  condition has cleared."
    ::= { slotInvCondNotifications 0 12 }


slotInvVersionMismatchCond NOTIFICATION-TYPE
    OBJECTS      { slotInvShelfIdx,
                   slotInvSlotTypeIdx,
                   slotInvSlotIdx,
                   slotInvSWVersion,
                   neSWVersion,
                   condReportType,
                   condDateAndTime,
                   condSeverity,
                   condServiceAffecting,
                   trapSeqNum,
                   condDescription,
                   condObjectType,
                   condCodeType }
    STATUS       current
    DESCRIPTION  "The circuit pack in the indicated slot is running a software
                  version which is inconsistent with the committed software
                  version of the system."
    ::= { slotInvCondNotifications 0 13 }


slotInvVersionMismatchClear NOTIFICATION-TYPE
    OBJECTS      { slotInvShelfIdx,
                   slotInvSlotTypeIdx,
                   slotInvSlotIdx,
                   condReportType,
                   condDateAndTime,
                   condSeverity,
                   condServiceAffecting,
                   trapSeqNum,
                   condDescription,
                   condObjectType,
                   condCodeType }
    STATUS       current
    DESCRIPTION  "A previously active circuit pack software version mismatch
                  condition has cleared."
    ::= { slotInvCondNotifications 0 14 }


slotInvCoolingUnitFailCond NOTIFICATION-TYPE
    OBJECTS      { slotInvShelfIdx,
                   slotInvSlotTypeIdx,
                   slotInvSlotIdx,
                   condReportType,
                   condDateAndTime,
                   condSeverity,
                   condServiceAffecting,
                   trapSeqNum,
                   condDescription,
                   condObjectType,
                   condCodeType }
    STATUS       current
    DESCRIPTION  "A cooling unit failure has occurred. One or more fans have
                  failed in the cooling unit."
    ::= { slotInvCondNotifications 0 15 }


slotInvCoolingUnitFailClear NOTIFICATION-TYPE
    OBJECTS      { slotInvShelfIdx,
                   slotInvSlotTypeIdx,
                   slotInvSlotIdx,
                   condReportType,
                   condDateAndTime,
                   condSeverity,
                   condServiceAffecting,
                   trapSeqNum,
                   condDescription,
                   condObjectType,
                   condCodeType }
    STATUS       current
    DESCRIPTION  "A previously active shelf cooling unit failure condition has
                  cleared."
    ::= { slotInvCondNotifications 0 16 }


slotInvDspCommCond NOTIFICATION-TYPE
    OBJECTS      { slotInvShelfIdx,
                   slotInvSlotTypeIdx,
                   slotInvSlotIdx,
                   condReportType,
                   condDateAndTime,
                   condSeverity,
                   condServiceAffecting,
                   trapSeqNum,
                   condDescription,
                   condObjectType,
                   condCodeType }
    STATUS       current
    DESCRIPTION  "This alarm indicates that communication has failed either
                  between the DSP and the processor handling backplane
                  communications on an optical amplifier circuit pack, or
                  between the variable optical equalizer (VOE) and the processor
                  handling backplane communications on an active mux/demux
                  circuit pack Normal OAM&P operations to the circuit pack, like
                  provisioning and performance monitoring, is affected when this
                  alarm is active."
    ::= { slotInvCondNotifications 0 17 }


slotInvDspCommClear NOTIFICATION-TYPE
    OBJECTS      { slotInvShelfIdx,
                   slotInvSlotTypeIdx,
                   slotInvSlotIdx,
                   condReportType,
                   condDateAndTime,
                   condSeverity,
                   condServiceAffecting,
                   trapSeqNum,
                   condDescription,
                   condObjectType,
                   condCodeType }
    STATUS       current
    DESCRIPTION  "A previously active DSP control communications condition has
                  been cleared."
    ::= { slotInvCondNotifications 0 18 }


slotInvUnsupportedPackCond NOTIFICATION-TYPE
    OBJECTS      { slotInvShelfIdx,
                   slotInvSlotTypeIdx,
                   slotInvSlotIdx,
                   condReportType,
                   condDateAndTime,
                   condSeverity,
                   condServiceAffecting,
                   trapSeqNum,
                   condDescription,
                   condObjectType,
                   condCodeType }
    STATUS       current
    DESCRIPTION  "A replaceable unit inventory item is unsupported. In this
                  case, a multiport system control processor (MSCP) circuit pack
                  is plugged into any slot of the expansion shelf. However,
                  MSCPs are only supported in slot five of the main shelf."
    ::= { slotInvCondNotifications 0 19 }


slotInvUnsupportedPackClear NOTIFICATION-TYPE
    OBJECTS      { slotInvShelfIdx,
                   slotInvSlotTypeIdx,
                   slotInvSlotIdx,
                   condReportType,
                   condDateAndTime,
                   condSeverity,
                   condServiceAffecting,
                   trapSeqNum,
                   condDescription,
                   condObjectType,
                   condCodeType }
    STATUS       current
    DESCRIPTION  "A previously active unsupported pack condition has cleared."
    ::= { slotInvCondNotifications 0 20 }

slotInvCoolingUnitMismatchCond NOTIFICATION-TYPE
    OBJECTS      { slotInvShelfIdx,
                   slotInvSlotTypeIdx,
                   slotInvSlotIdx,
                   condReportType,
                   condDateAndTime,
                   condSeverity,
                   condServiceAffecting,
                   trapSeqNum,
                   condDescription,
                   condObjectType,
                   condCodeType }
    STATUS       current
    DESCRIPTION  "The shelf is plugged in with a wring cooling unit."
    ::= { slotInvCondNotifications 0 21 }


slotInvCoolingUnitMismatchClear NOTIFICATION-TYPE
    OBJECTS      { slotInvShelfIdx,
                   slotInvSlotTypeIdx,
                   slotInvSlotIdx,
                   condReportType,
                   condDateAndTime,
                   condSeverity,
                   condServiceAffecting,
                   trapSeqNum,
                   condDescription,
                   condObjectType,
                   condCodeType }
    STATUS       current
    DESCRIPTION  "A previously active cooling unit mismatch condition has cleared."
    ::= { slotInvCondNotifications 0 22 }

slotInvPwrFeedAFuseFailCond NOTIFICATION-TYPE
    OBJECTS      { slotInvShelfIdx,
                   slotInvSlotTypeIdx,
                   slotInvSlotIdx,
                   condReportType,
                   condDateAndTime,
                   condSeverity,
                   condServiceAffecting,
                   trapSeqNum,
                   condDescription,
                   condObjectType,
                   condCodeType }
    STATUS       current
    DESCRIPTION  "There is a circuit pack failure. The alarm is critical when a
                  circuit pack is provisioned and that it has fails in its
                  associated slot."
    ::= { slotInvCondNotifications 0 23 }

slotInvPwrFeedAFuseFailClear NOTIFICATION-TYPE
    OBJECTS      { slotInvShelfIdx,
                   slotInvSlotTypeIdx,
                   slotInvSlotIdx,
                   condReportType,
                   condDateAndTime,
                   condSeverity,
                   condServiceAffecting,
                   trapSeqNum,
                   condDescription,
                   condObjectType,
                   condCodeType }
    STATUS       current
    DESCRIPTION  "A previously active circuit pack fail condition has cleared."
    ::= { slotInvCondNotifications 0 24 }

slotInvPwrFeedBFuseFailCond NOTIFICATION-TYPE
    OBJECTS      { slotInvShelfIdx,
                   slotInvSlotTypeIdx,
                   slotInvSlotIdx,
                   condReportType,
                   condDateAndTime,
                   condSeverity,
                   condServiceAffecting,
                   trapSeqNum,
                   condDescription,
                   condObjectType,
                   condCodeType }
    STATUS       current
    DESCRIPTION  "There is a circuit pack failure. The alarm is critical when a
                  circuit pack is provisioned and that it has fails in its
                  associated slot."
    ::= { slotInvCondNotifications 0 25 }

slotInvPwrFeedBFuseFailClear NOTIFICATION-TYPE
    OBJECTS      { slotInvShelfIdx,
                   slotInvSlotTypeIdx,
                   slotInvSlotIdx,
                   condReportType,
                   condDateAndTime,
                   condSeverity,
                   condServiceAffecting,
                   trapSeqNum,
                   condDescription,
                   condObjectType,
                   condCodeType }
    STATUS       current
    DESCRIPTION  "A previously active circuit pack fail condition has cleared."
    ::= { slotInvCondNotifications 0 26 }

slotInvPowerFailCond NOTIFICATION-TYPE
    OBJECTS      { slotInvShelfIdx,
                   slotInvSlotTypeIdx,
                   slotInvSlotIdx,
                   condReportType,
                   condDateAndTime,
                   condSeverity,
                   condServiceAffecting,
                   trapSeqNum,
                   condDescription,
                   condObjectType,
                   condCodeType }
    STATUS       current
    DESCRIPTION  "There is a circuit pack failure. The alarm is critical when a
                  circuit pack is provisioned and that it has fails in its
                  associated slot."
    ::= { slotInvCondNotifications 0 27 }

slotInvPowerFailClear NOTIFICATION-TYPE
    OBJECTS      { slotInvShelfIdx,
                   slotInvSlotTypeIdx,
                   slotInvSlotIdx,
                   condReportType,
                   condDateAndTime,
                   condSeverity,
                   condServiceAffecting,
                   trapSeqNum,
                   condDescription,
                   condObjectType,
                   condCodeType }
    STATUS       current
    DESCRIPTION  "A previously active circuit pack fail condition has cleared."
    ::= { slotInvCondNotifications 0 28 }

slotInvHiTempAutoShutdownCond NOTIFICATION-TYPE
    OBJECTS      { slotInvShelfIdx,
                   slotInvSlotTypeIdx,
                   slotInvSlotIdx,
                   condReportType,
                   condDateAndTime,
                   condSeverity,
                   condServiceAffecting,
                   trapSeqNum,
                   condDescription,
                   condObjectType,
                   condCodeType }
    STATUS       current
    DESCRIPTION  "There is a circuit pack failure. The alarm is critical when a
                  circuit pack is provisioned and that it has fails in its
                  associated slot."
    ::= { slotInvCondNotifications 0 29 }

slotInvHiTempAutoShutdownClear NOTIFICATION-TYPE
    OBJECTS      { slotInvShelfIdx,
                   slotInvSlotTypeIdx,
                   slotInvSlotIdx,
                   condReportType,
                   condDateAndTime,
                   condSeverity,
                   condServiceAffecting,
                   trapSeqNum,
                   condDescription,
                   condObjectType,
                   condCodeType }
    STATUS       current
    DESCRIPTION  "A previously active circuit pack fail condition has cleared."
    ::= { slotInvCondNotifications 0 30 }

slotInvHTThreshExceededCond NOTIFICATION-TYPE
    OBJECTS      { slotInvShelfIdx,
                   slotInvSlotTypeIdx,
                   slotInvSlotIdx,
                   condReportType,
                   condDateAndTime,
                   condSeverity,
                   condServiceAffecting,
                   trapSeqNum,
                   condDescription,
                   condObjectType,
                   condCodeType }
    STATUS       current
    DESCRIPTION  "There is a circuit pack failure. The alarm is critical when a
                  circuit pack is provisioned and that it has fails in its
                  associated slot."
    ::= { slotInvCondNotifications 0 31 }

slotInvHTThreshExceededClear NOTIFICATION-TYPE
    OBJECTS      { slotInvShelfIdx,
                   slotInvSlotTypeIdx,
                   slotInvSlotIdx,
                   condReportType,
                   condDateAndTime,
                   condSeverity,
                   condServiceAffecting,
                   trapSeqNum,
                   condDescription,
                   condObjectType,
                   condCodeType }
    STATUS       current
    DESCRIPTION  "A previously active circuit pack fail condition has cleared."
    ::= { slotInvCondNotifications 0 32 }

slotInvHTSThreshExceededCond NOTIFICATION-TYPE
    OBJECTS      { slotInvShelfIdx,
                   slotInvSlotTypeIdx,
                   slotInvSlotIdx,
                   condReportType,
                   condDateAndTime,
                   condSeverity,
                   condServiceAffecting,
                   trapSeqNum,
                   condDescription,
                   condObjectType,
                   condCodeType }
    STATUS       current
    DESCRIPTION  "There is a circuit pack failure. The alarm is critical when a
                  circuit pack is provisioned and that it has fails in its
                  associated slot."
    ::= { slotInvCondNotifications 0 33 }

slotInvHTSThreshExceededClear NOTIFICATION-TYPE
    OBJECTS      { slotInvShelfIdx,
                   slotInvSlotTypeIdx,
                   slotInvSlotIdx,
                   condReportType,
                   condDateAndTime,
                   condSeverity,
                   condServiceAffecting,
                   trapSeqNum,
                   condDescription,
                   condObjectType,
                   condCodeType }
    STATUS       current
    DESCRIPTION  "A previously active circuit pack fail condition has cleared."
    ::= { slotInvCondNotifications 0 34 }

slotInvHTASUnsupportedCond NOTIFICATION-TYPE
    OBJECTS      { slotInvShelfIdx,
                   slotInvSlotTypeIdx,
                   slotInvSlotIdx,
                   condReportType,
                   condDateAndTime,
                   condSeverity,
                   condServiceAffecting,
                   trapSeqNum,
                   condDescription,
                   condObjectType,
                   condCodeType }
    STATUS       current
    DESCRIPTION  "There is a circuit pack failure. The alarm is critical when a
                  circuit pack is provisioned and that it has fails in its
                  associated slot."
    ::= { slotInvCondNotifications 0 35 }

slotInvHTASUnsupportedClear NOTIFICATION-TYPE
    OBJECTS      { slotInvShelfIdx,
                   slotInvSlotTypeIdx,
                   slotInvSlotIdx,
                   condReportType,
                   condDateAndTime,
                   condSeverity,
                   condServiceAffecting,
                   trapSeqNum,
                   condDescription,
                   condObjectType,
                   condCodeType }
    STATUS       current
    DESCRIPTION  "A previously active circuit pack fail condition has cleared."
    ::= { slotInvCondNotifications 0 36 }



shelfMismatchCond NOTIFICATION-TYPE
    OBJECTS      { shelfIdx,
                   condReportType,
                   condDateAndTime,
                   condSeverity,
                   condServiceAffecting,
                   trapSeqNum,
                   condDescription,
                   condObjectType,
                   condCodeType }
    STATUS       current
    DESCRIPTION  "The type of the physically detected shelf does not match the
                  provisioned shelf type."
    ::= { shelfCondNotifications 0 1 }


shelfMismatchClear NOTIFICATION-TYPE
    OBJECTS      { shelfIdx,
                   condReportType,
                   condDateAndTime,
                   condSeverity,
                   condServiceAffecting,
                   trapSeqNum,
                   condDescription,
                   condObjectType,
                   condCodeType }
    STATUS       current
    DESCRIPTION  "A previously active shelf type mismatch condition has
                  cleared."
    ::= { shelfCondNotifications 0 2 }


shelfMissingCond NOTIFICATION-TYPE
    OBJECTS      { shelfIdx,
                   condReportType,
                   condDateAndTime,
                   condSeverity,
                   condServiceAffecting,
                   trapSeqNum,
                   condDescription,
                   condObjectType,
                   condCodeType }
    STATUS       current
    DESCRIPTION  "An expansion shelf is missing. To clear this alarm, attach an
                  appropriate expansion shelf to the MSCP in the main shelf of
                  the system."
    ::= { shelfCondNotifications 0 3 }


shelfMissingClear NOTIFICATION-TYPE
    OBJECTS      { shelfIdx,
                   condReportType,
                   condDateAndTime,
                   condSeverity,
                   condServiceAffecting,
                   trapSeqNum,
                   condDescription,
                   condObjectType,
                   condCodeType }
    STATUS       current
    DESCRIPTION  "A previously active expansion shelf missing condition has
                  cleared."
    ::= { shelfCondNotifications 0 4 }

shelfConfigurationMismatchCond NOTIFICATION-TYPE
    OBJECTS      { shelfIdx,
                   shelfProvConfig,
                   shelfDiscConfig,
                   condReportType,
                   condDateAndTime,
                   condSeverity,
                   condServiceAffecting,
                   trapSeqNum,
                   condDescription,
                   condObjectType,
                   condCodeType }
    STATUS       deprecated
    DESCRIPTION  "The configuration type of the physically detected expansion
                  shelf does not match the provisioned expansion shelf
                  configuration type."
    ::= { shelfCondNotifications 0 5 }


shelfConfigurationMismatchClear NOTIFICATION-TYPE
    OBJECTS      { shelfIdx,
                   condReportType,
                   condDateAndTime,
                   condSeverity,
                   condServiceAffecting,
                   trapSeqNum,
                   condDescription,
                   condObjectType,
                   condCodeType }
    STATUS       deprecated
    DESCRIPTION  "A previously active expansion shelf configuration mismatch
                  condition has cleared."
    ::= { shelfCondNotifications 0 6 }

cpMismatchCond NOTIFICATION-TYPE
    OBJECTS      { cpTypeIdx,
                   cpShelfIdx,
                   cpSlotIdx,
                   condReportType,
                   condDateAndTime,
                   condSeverity,
                   condServiceAffecting,
                   trapSeqNum,
                   condDescription,
                   condObjectType,
                   condCodeType }
    STATUS       current
    DESCRIPTION  "There is a circuit pack mismatch. There is a mismatch between
                  the equipment provisioned for the slot and the physical
                  circuit pack that is inserted in the slot."
    ::= { cpCondNotifications 0 1 }


cpMismatchClear NOTIFICATION-TYPE
    OBJECTS      { cpTypeIdx,
                   cpShelfIdx,
                   cpSlotIdx,
                   condReportType,
                   condDateAndTime,
                   condSeverity,
                   condServiceAffecting,
                   trapSeqNum,
                   condDescription,
                   condObjectType,
                   condCodeType }
    STATUS       current
    DESCRIPTION  "A previously active circuit pack type mismatch condition has
                  cleared."
    ::= { cpCondNotifications 0 2 }


cpConnectorMismatchCond NOTIFICATION-TYPE
    OBJECTS      { cpTypeIdx,
                   cpShelfIdx,
                   cpSlotIdx,
                   condReportType,
                   condDateAndTime,
                   condSeverity,
                   condServiceAffecting,
                   trapSeqNum,
                   condDescription,
                   condObjectType,
                   condCodeType }
    STATUS       current
    DESCRIPTION  "A connector mismatch alarm occurs on a circuit pack that is
                  provisioned with a connector type that is different to the one
                  actually inserted."
    ::= { cpCondNotifications 0 3 }


cpConnectorMismatchClear NOTIFICATION-TYPE
    OBJECTS      { cpTypeIdx,
                   cpShelfIdx,
                   cpSlotIdx,
                   condReportType,
                   condDateAndTime,
                   condSeverity,
                   condServiceAffecting,
                   trapSeqNum,
                   condDescription,
                   condObjectType,
                   condCodeType }
    STATUS       current
    DESCRIPTION  "A previously active optical fiber connector type mismatch
                  condition has cleared."
    ::= { cpCondNotifications 0 4 }


cpInvalidProvCond NOTIFICATION-TYPE
    OBJECTS      { cpTypeIdx,
                   cpShelfIdx,
                   cpSlotIdx,
                   condReportType,
                   condDateAndTime,
                   condSeverity,
                   condServiceAffecting,
                   trapSeqNum,
                   condDescription,
                   condObjectType,
                   condCodeType }
    STATUS       current
    DESCRIPTION  "The type of circuit pack that is provisioned in a slot that is
                  invalid for the shelf slot configuration."
    ::= { cpCondNotifications 0 5 }


cpInvalidProvClear NOTIFICATION-TYPE
    OBJECTS      { cpTypeIdx,
                   cpShelfIdx,
                   cpSlotIdx,
                   condReportType,
                   condDateAndTime,
                   condSeverity,
                   condServiceAffecting,
                   trapSeqNum,
                   condDescription,
                   condObjectType,
                   condCodeType }
    STATUS       current
    DESCRIPTION  "A previously active invalid circuit pack provisioning
                  condition has cleared."
    ::= { cpCondNotifications 0 6 }


cpSoftwareBankAFailCond NOTIFICATION-TYPE
    OBJECTS      { cpTypeIdx,
                   cpShelfIdx,
                   cpSlotIdx,
                   condReportType,
                   condDateAndTime,
                   condSeverity,
                   condServiceAffecting,
                   trapSeqNum,
                   condDescription,
                   condObjectType,
                   condCodeType }
    STATUS       current
    DESCRIPTION  "There is a hardware failure in software bank A storage device.
                  During this alarm, software backups, upgrades and restores
                  cannot occur. When the MSCP is rebooting, the LEDs on the MSI
                  and the MSCP are lit."
    ::= { cpCondNotifications 0 7 }


cpSoftwareBankAFailClear NOTIFICATION-TYPE
    OBJECTS      { cpTypeIdx,
                   cpShelfIdx,
                   cpSlotIdx,
                   condReportType,
                   condDateAndTime,
                   condSeverity,
                   condServiceAffecting,
                   trapSeqNum,
                   condDescription,
                   condObjectType,
                   condCodeType }
    STATUS       current
    DESCRIPTION  "A previously active software Bank A failure condition has
                  cleared."
    ::= { cpCondNotifications 0 8 }


cpSoftwareBankBFailCond NOTIFICATION-TYPE
    OBJECTS      { cpTypeIdx,
                   cpShelfIdx,
                   cpSlotIdx,
                   condReportType,
                   condDateAndTime,
                   condSeverity,
                   condServiceAffecting,
                   trapSeqNum,
                   condDescription,
                   condObjectType,
                   condCodeType }
    STATUS       current
    DESCRIPTION  "There is a hardware failure in software bank B storage device.
                  During this alarm, software backups, upgrades, and restores
                  cannot occur. When the MSCP is rebooting, the LEDs on the MSI
                  and the MSCP are lit."
    ::= { cpCondNotifications 0 9 }


cpSoftwareBankBFailClear NOTIFICATION-TYPE
    OBJECTS      { cpTypeIdx,
                   cpShelfIdx,
                   cpSlotIdx,
                   condReportType,
                   condDateAndTime,
                   condSeverity,
                   condServiceAffecting,
                   trapSeqNum,
                   condDescription,
                   condObjectType,
                   condCodeType }
    STATUS       current
    DESCRIPTION  "A previously active software Bank B failure condition has
                  cleared."
    ::= { cpCondNotifications 0 10 }


cpUpgradeInProgressCond NOTIFICATION-TYPE
    OBJECTS      { cpTypeIdx,
                   cpShelfIdx,
                   cpSlotIdx,
                   condReportType,
                   condDateAndTime,
                   condSeverity,
                   condServiceAffecting,
                   trapSeqNum,
                   condDescription,
                   condObjectType,
                   condCodeType }
    STATUS       current
    DESCRIPTION  "Indicates that a system-wide software upgrade process is in
                  progress on the NE."
    ::= { cpCondNotifications 0 11 }


cpUpgradeInProgressClear NOTIFICATION-TYPE
    OBJECTS      { cpTypeIdx,
                   cpShelfIdx,
                   cpSlotIdx,
                   condReportType,
                   condDateAndTime,
                   condSeverity,
                   condServiceAffecting,
                   trapSeqNum,
                   condDescription,
                   condObjectType,
                   condCodeType }
    STATUS       current
    DESCRIPTION  "A previously active system-wide upgrade in progress condition
                  has cleared."
    ::= { cpCondNotifications 0 12 }


cpUpgradeFailCond NOTIFICATION-TYPE
    OBJECTS      { cpTypeIdx,
                   cpShelfIdx,
                   cpSlotIdx,
                   condReportType,
                   condDateAndTime,
                   condSeverity,
                   condServiceAffecting,
                   trapSeqNum,
                   condDescription,
                   condObjectType,
                   condCodeType }
    STATUS       current
    DESCRIPTION  "Indicates that the system-wide upgrade procedure has failed to
                  complete successfully."
    ::= { cpCondNotifications 0 15 }


cpUpgradeFailClear NOTIFICATION-TYPE
    OBJECTS      { cpTypeIdx,
                   cpShelfIdx,
                   cpSlotIdx,
                   condReportType,
                   condDateAndTime,
                   condSeverity,
                   condServiceAffecting,
                   trapSeqNum,
                   condDescription,
                   condObjectType,
                   condCodeType }
    STATUS       current
    DESCRIPTION  "A previously active circuit pack upgrade failure condition has
                  cleared."
    ::= { cpCondNotifications 0 16 }


cpDbRestoreInProgressCond NOTIFICATION-TYPE
    OBJECTS      { cpTypeIdx,
                   cpShelfIdx,
                   cpSlotIdx,
                   condReportType,
                   condDateAndTime,
                   condSeverity,
                   condServiceAffecting,
                   trapSeqNum,
                   condDescription,
                   condObjectType,
                   condCodeType }
    STATUS       current
    DESCRIPTION  "There is a database restore in progress on the system."
    ::= { cpCondNotifications 0 17 }


cpDbRestoreInProgressClear NOTIFICATION-TYPE
    OBJECTS      { cpTypeIdx,
                   cpShelfIdx,
                   cpSlotIdx,
                   condReportType,
                   condDateAndTime,
                   condSeverity,
                   condServiceAffecting,
                   trapSeqNum,
                   condDescription,
                   condObjectType,
                   condCodeType }
    STATUS       current
    DESCRIPTION  "A previously active NE database restore condition has
                  cleared."
    ::= { cpCondNotifications 0 18 }


cpDbRecoveryFailCond NOTIFICATION-TYPE
    OBJECTS      { cpTypeIdx,
                   cpShelfIdx,
                   cpSlotIdx,
                   condReportType,
                   condDateAndTime,
                   condSeverity,
                   condServiceAffecting,
                   trapSeqNum,
                   condDescription,
                   condObjectType,
                   condCodeType }
    STATUS       current
    DESCRIPTION  "There is a database recovery failure. If a new MSCP circuit
                  pack fails to acquire the database from the system, a database
                  recovery failure alarm can be triggered after replacing the
                  MSCP."
    ::= { cpCondNotifications 0 19 }


cpDbRecoveryFailClear NOTIFICATION-TYPE
    OBJECTS      { cpTypeIdx,
                   cpShelfIdx,
                   cpSlotIdx,
                   condReportType,
                   condDateAndTime,
                   condSeverity,
                   condServiceAffecting,
                   trapSeqNum,
                   condDescription,
                   condObjectType,
                   condCodeType }
    STATUS       current
    DESCRIPTION  "A previously active NE database recovery failure condition has
                  cleared."
    ::= { cpCondNotifications 0 20 }


cpFanFeedFailCond NOTIFICATION-TYPE
    OBJECTS      { cpTypeIdx,
                   cpShelfIdx,
                   cpSlotIdx,
                   condReportType,
                   condDateAndTime,
                   condSeverity,
                   condServiceAffecting,
                   trapSeqNum,
                   condDescription,
                   condObjectType,
                   condCodeType }
    STATUS       current
    DESCRIPTION  "A cooling unit feed failure has occurred on a BTI 7030 shelf.
                  There are two cooling unit power feeds from the SCP to the
                  cooling unit. If one power feeds fails, a minor alarm is
                  raised. If both power feed fails, a major alarm is raised."
    ::= { cpCondNotifications 0 21 }


cpFanFeedFailClear NOTIFICATION-TYPE
    OBJECTS      { cpTypeIdx,
                   cpShelfIdx,
                   cpSlotIdx,
                   condReportType,
                   condDateAndTime,
                   condSeverity,
                   condServiceAffecting,
                   trapSeqNum,
                   condDescription,
                   condObjectType,
                   condCodeType }
    STATUS       current
    DESCRIPTION  "A previously active fan power feed failure condition has
                  cleared."
    ::= { cpCondNotifications 0 22 }


cpStorageCardFailCond NOTIFICATION-TYPE
    OBJECTS      { cpTypeIdx,
                   cpShelfIdx,
                   cpSlotIdx,
                   condReportType,
                   condDateAndTime,
                   condSeverity,
                   condServiceAffecting,
                   trapSeqNum,
                   condDescription,
                   condObjectType,
                   condCodeType }
    STATUS       current
    DESCRIPTION  "Indicates that the database storage card has failed."
    ::= { cpCondNotifications 0 23 }


cpStorageCardFailClear NOTIFICATION-TYPE
    OBJECTS      { cpTypeIdx,
                   cpShelfIdx,
                   cpSlotIdx,
                   condReportType,
                   condDateAndTime,
                   condSeverity,
                   condServiceAffecting,
                   trapSeqNum,
                   condDescription,
                   condObjectType,
                   condCodeType }
    STATUS       current
    DESCRIPTION  "A previously active database storage card failure condition
                  has cleared."
    ::= { cpCondNotifications 0 24 }

cpDbDeletionInProgressCond NOTIFICATION-TYPE
    OBJECTS      { cpTypeIdx,
                   cpShelfIdx,
                   cpSlotIdx,
                   condReportType,
                   condDateAndTime,
                   condSeverity,
                   condServiceAffecting,
                   trapSeqNum,
                   condDescription,
                   condObjectType,
                   condCodeType }
    STATUS       current
    DESCRIPTION  "There is a database deletion in progress on the system."
    ::= { cpCondNotifications 0 25 }


cpDbDeletionInProgressClear NOTIFICATION-TYPE
    OBJECTS      { cpTypeIdx,
                   cpShelfIdx,
                   cpSlotIdx,
                   condReportType,
                   condDateAndTime,
                   condSeverity,
                   condServiceAffecting,
                   trapSeqNum,
                   condDescription,
                   condObjectType,
                   condCodeType }
    STATUS       current
    DESCRIPTION  "A previously active NE database deletion condition has
                  cleared."
    ::= { cpCondNotifications 0 26 }


cpDegradeCond NOTIFICATION-TYPE
    OBJECTS      { cpTypeIdx,
                   cpShelfIdx,
                   cpSlotIdx,
                   condReportType,
                   condDateAndTime,
                   condSeverity,
                   condServiceAffecting,
                   trapSeqNum,
                   condDescription,
                   condObjectType,
                   condCodeType }
    STATUS       current
    DESCRIPTION  "Indicates that a failure or degradation has been detected
                  in one or more physical components on the identified
                  circuit pack, which may lead to a failure of the pack to
                  provide service normally."
    ::= { cpCondNotifications 0 27 }


cpDegradeClear NOTIFICATION-TYPE
    OBJECTS      { cpTypeIdx,
                   cpShelfIdx,
                   cpSlotIdx,
                   condReportType,
                   condDateAndTime,
                   condSeverity,
                   condServiceAffecting,
                   trapSeqNum,
                   condDescription,
                   condObjectType,
                   condCodeType }
    STATUS       current
    DESCRIPTION  "A previously active Circuit Pack Degrade condition has
                  cleared."
    ::= { cpCondNotifications 0 28 }


oaCaseTempCond NOTIFICATION-TYPE
    OBJECTS      { oaTypeIdx,
                   oaShelfIdx,
                   oaSlotIdx,
                   oaIdx,
                   oaCaseTemp,
                   oaCaseTempMaxTh,
                   condReportType,
                   condDateAndTime,
                   condSeverity,
                   condServiceAffecting,
                   trapSeqNum,
                   condDescription,
                   condObjectType,
                   condCodeType }
    STATUS       current
    DESCRIPTION  "A case temperature high threshold is exceeded. A warning is
                  raised to indicate that the amplifier is nearing its shutdown
                  threshold. The circuit pack in the associated slot has
                  exceeded its case temperature high threshold. If the case
                  temperature continues to rise to its shutdown threshold, the
                  circuit pack automatically shuts down."
    ::= { oaCondNotifications 0 1 }


oaCaseTempClear NOTIFICATION-TYPE
    OBJECTS      { oaTypeIdx,
                   oaShelfIdx,
                   oaSlotIdx,
                   oaIdx,
                   condReportType,
                   condDateAndTime,
                   condSeverity,
                   condServiceAffecting,
                   trapSeqNum,
                   condDescription,
                   condObjectType,
                   condCodeType }
    STATUS       current
    DESCRIPTION  "A previously active optical amplifier case temperature
                  condition has cleared."
    ::= { oaCondNotifications 0 2 }


oaCaseTempShutdownCond NOTIFICATION-TYPE
    OBJECTS      { oaTypeIdx,
                   oaShelfIdx,
                   oaSlotIdx,
                   oaIdx,
                   oaCaseTemp,
                   oaCaseTempMaxShutdownTh,
                   condReportType,
                   condDateAndTime,
                   condSeverity,
                   condServiceAffecting,
                   trapSeqNum,
                   condDescription,
                   condObjectType,
                   condCodeType }
    STATUS       current
    DESCRIPTION  "A case temperature high threshold shutdown has occurred. The
                  optical amplifier is shutdown and taken out-of-service by the
                  system. The pump lasers are turned off and there is no
                  amplification."
    ::= { oaCondNotifications 0 3 }


oaCaseTempShutdownClear NOTIFICATION-TYPE
    OBJECTS      { oaTypeIdx,
                   oaShelfIdx,
                   oaSlotIdx,
                   oaIdx,
                   condReportType,
                   condDateAndTime,
                   condSeverity,
                   condServiceAffecting,
                   trapSeqNum,
                   condDescription,
                   condObjectType,
                   condCodeType }
    STATUS       current
    DESCRIPTION  "A previously active optical amplifier case temperature
                  shutdown condition has cleared."
    ::= { oaCondNotifications 0 4 }


oaLaserMinTempShutdownCond NOTIFICATION-TYPE
    OBJECTS      { oaTypeIdx,
                   oaShelfIdx,
                   oaSlotIdx,
                   oaIdx,
                   oaLaser1Temp,
                   oaLaser2Temp,
                   oaLaserTempMinShutdownTh,
                   condReportType,
                   condDateAndTime,
                   condSeverity,
                   condServiceAffecting,
                   trapSeqNum,
                   condDescription,
                   condObjectType,
                   condCodeType }
    STATUS       current
    DESCRIPTION  "A pump laser temperature low threshold shutdown has occurred.
                  The optical amplifier is shutdown and taken out-of-service by
                  the system."
    ::= { oaCondNotifications 0 5 }


oaLaserMinTempShutdownClear NOTIFICATION-TYPE
    OBJECTS      { oaTypeIdx,
                   oaShelfIdx,
                   oaSlotIdx,
                   oaIdx,
                   condReportType,
                   condDateAndTime,
                   condSeverity,
                   condServiceAffecting,
                   trapSeqNum,
                   condDescription,
                   condObjectType,
                   condCodeType }
    STATUS       current
    DESCRIPTION  "A previously active optical amplifier minimum temperature
                  shutdown condition has cleared."
    ::= { oaCondNotifications 0 6 }


oaLaserMaxTempShutdownCond NOTIFICATION-TYPE
    OBJECTS      { oaTypeIdx,
                   oaShelfIdx,
                   oaSlotIdx,
                   oaIdx,
                   oaLaser1Temp,
                   oaLaser2Temp,
                   oaLaserTempMaxShutdownTh,
                   condReportType,
                   condDateAndTime,
                   condSeverity,
                   condServiceAffecting,
                   trapSeqNum,
                   condDescription,
                   condObjectType,
                   condCodeType }
    STATUS       current
    DESCRIPTION  "A pump laser temperature high threshold shutdown has occurred.
                  The optical amplifier is shutdown and taken out-of-service by
                  the system."
    ::= { oaCondNotifications 0 7 }


oaLaserMaxTempShutdownClear NOTIFICATION-TYPE
    OBJECTS      { oaTypeIdx,
                   oaShelfIdx,
                   oaSlotIdx,
                   oaIdx,
                   condReportType,
                   condDateAndTime,
                   condSeverity,
                   condServiceAffecting,
                   trapSeqNum,
                   condDescription,
                   condObjectType,
                   condCodeType }
    STATUS       current
    DESCRIPTION  "A previously active optical amplifier maximum temperature
                  shutdown condition has cleared."
    ::= { oaCondNotifications 0 8 }


oaOpticalPwrReceivedMinCond NOTIFICATION-TYPE
    OBJECTS      { oaTypeIdx,
                   oaShelfIdx,
                   oaSlotIdx,
                   oaIdx,
                   oaOpticalPwrReceived,
                   oaOpticalPwrReceivedMinTh,
                   condReportType,
                   condDateAndTime,
                   condSeverity,
                   condServiceAffecting,
                   trapSeqNum,
                   condDescription,
                   condObjectType,
                   condCodeType }
    STATUS       current
    DESCRIPTION  "The optical power received (OPR) low threshold is exceeded.
                  The input signal to an optical amplifier has reached the
                  optical power received low threshold. If the input signal
                  drops to below the input sensitivity level, the circuit pack
                  will degrade in performance."
    ::= { oaCondNotifications 0 9 }


oaOpticalPwrReceivedMinClear NOTIFICATION-TYPE
    OBJECTS      { oaTypeIdx,
                   oaShelfIdx,
                   oaSlotIdx,
                   oaIdx,
                   condReportType,
                   condDateAndTime,
                   condSeverity,
                   condServiceAffecting,
                   trapSeqNum,
                   condDescription,
                   condObjectType,
                   condCodeType }
    STATUS       current
    DESCRIPTION  "A previously active optical amplifier minimum power received
                  condition has cleared."
    ::= { oaCondNotifications 0 10 }


oaOpticalPwrReceivedMaxCond NOTIFICATION-TYPE
    OBJECTS      { oaTypeIdx,
                   oaShelfIdx,
                   oaSlotIdx,
                   oaIdx,
                   oaOpticalPwrReceived,
                   oaOpticalPwrReceivedMaxTh,
                   condReportType,
                   condDateAndTime,
                   condSeverity,
                   condServiceAffecting,
                   trapSeqNum,
                   condDescription,
                   condObjectType,
                   condCodeType }
    STATUS       current
    DESCRIPTION  "The optical power received (OPR) high threshold is crossed.
                  The input signal to an optical amplifier has reached the
                  optical power received high threshold."
    ::= { oaCondNotifications 0 11 }


oaOpticalPwrReceivedMaxClear NOTIFICATION-TYPE
    OBJECTS      { oaTypeIdx,
                   oaShelfIdx,
                   oaSlotIdx,
                   oaIdx,
                   condReportType,
                   condDateAndTime,
                   condSeverity,
                   condServiceAffecting,
                   trapSeqNum,
                   condDescription,
                   condObjectType,
                   condCodeType }
    STATUS       current
    DESCRIPTION  "A previously active optical amplifier maximum power received
                  condition has cleared."
    ::= { oaCondNotifications 0 12 }


oaSSIOpticalPwrReceivedMaxCond NOTIFICATION-TYPE
    OBJECTS      { oaTypeIdx,
                   oaShelfIdx,
                   oaSlotIdx,
                   oaIdx,
                   oaSSIOpticalPwrReceived,
                   oaSSIOpticalPwrReceivedMaxTh,
                   condReportType,
                   condDateAndTime,
                   condSeverity,
                   condServiceAffecting,
                   trapSeqNum,
                   condDescription,
                   condObjectType,
                   condCodeType }
    STATUS       current
    DESCRIPTION  "A second stage input optical power received (OPR) high
                  threshold crossing has occurred."
    ::= { oaCondNotifications 0 13 }


oaSSIOpticalPwrReceivedMaxClear NOTIFICATION-TYPE
    OBJECTS      { oaTypeIdx,
                   oaShelfIdx,
                   oaSlotIdx,
                   oaIdx,
                   condReportType,
                   condDateAndTime,
                   condSeverity,
                   condServiceAffecting,
                   trapSeqNum,
                   condDescription,
                   condObjectType,
                   condCodeType }
    STATUS       current
    DESCRIPTION  "A previously active optical amplifier second stage input
                  maximum power received condition has cleared."
    ::= { oaCondNotifications 0 14 }


oaBackReflectionSafetyCond NOTIFICATION-TYPE
    OBJECTS      { oaTypeIdx,
                   oaShelfIdx,
                   oaSlotIdx,
                   oaIdx,
                   oaBackReflectionSafetyTh,
                   condReportType,
                   condDateAndTime,
                   condSeverity,
                   condServiceAffecting,
                   trapSeqNum,
                   condDescription,
                   condObjectType,
                   condCodeType }
    STATUS       current
    DESCRIPTION  "The Optical Back Reflection - High Threshold Safety Override
                  alarm indicates someone has activated the optical power
                  received optical back reflection high threshold safety
                  override (OPR-OBR-HTSO) command to override the automatic
                  power reduction (APR) feature of the amplifier lasers. This
                  command overrides the APR feature of the amplifier for 20 to
                  600 seconds. When the timer expires, the alarm clears."
    ::= { oaCondNotifications 0 17 }


oaBackReflectionSafetyClear NOTIFICATION-TYPE
    OBJECTS      { oaTypeIdx,
                   oaShelfIdx,
                   oaSlotIdx,
                   oaIdx,
                   condReportType,
                   condDateAndTime,
                   condSeverity,
                   condServiceAffecting,
                   trapSeqNum,
                   condDescription,
                   condObjectType,
                   condCodeType }
    STATUS       current
    DESCRIPTION  "A previously active optical amplifier back reflection safety
                  condition has cleared."
    ::= { oaCondNotifications 0 18 }


oaOpticalPwrTransmittedMinCond NOTIFICATION-TYPE
    OBJECTS      { oaTypeIdx,
                   oaShelfIdx,
                   oaSlotIdx,
                   oaIdx,
                   oaOpticalPwrTransmitted,
                   oaOpticalPwrTransmittedMinTh,
                   condReportType,
                   condDateAndTime,
                   condSeverity,
                   condServiceAffecting,
                   trapSeqNum,
                   condDescription,
                   condObjectType,
                   condCodeType }
    STATUS       current
    DESCRIPTION  "The optical power transmitted (OPT) low threshold is crossed."
    ::= { oaCondNotifications 0 19 }


oaOpticalPwrTransmittedMinClear NOTIFICATION-TYPE
    OBJECTS      { oaTypeIdx,
                   oaShelfIdx,
                   oaSlotIdx,
                   oaIdx,
                   condReportType,
                   condDateAndTime,
                   condSeverity,
                   condServiceAffecting,
                   trapSeqNum,
                   condDescription,
                   condObjectType,
                   condCodeType }
    STATUS       current
    DESCRIPTION  "A previously active optical amplifier minimum transmitted
                  power condition has cleared."
    ::= { oaCondNotifications 0 20 }


oaOpticalPwrTransmittedMaxCond NOTIFICATION-TYPE
    OBJECTS      { oaTypeIdx,
                   oaShelfIdx,
                   oaSlotIdx,
                   oaIdx,
                   oaOpticalPwrTransmitted,
                   oaOpticalPwrTransmittedMaxTh,
                   condReportType,
                   condDateAndTime,
                   condSeverity,
                   condServiceAffecting,
                   trapSeqNum,
                   condDescription,
                   condObjectType,
                   condCodeType }
    STATUS       current
    DESCRIPTION  "The optical power transmitted (OPT) high threshold has been
                  exceeded on the amplifier."
    ::= { oaCondNotifications 0 21 }


oaOpticalPwrTransmittedMaxClear NOTIFICATION-TYPE
    OBJECTS      { oaTypeIdx,
                   oaShelfIdx,
                   oaSlotIdx,
                   oaIdx,
                   condReportType,
                   condDateAndTime,
                   condSeverity,
                   condServiceAffecting,
                   trapSeqNum,
                   condDescription,
                   condObjectType,
                   condCodeType }
    STATUS       current
    DESCRIPTION  "A previously active optical amplifier maximum transmitted
                  power condition has cleared."
    ::= { oaCondNotifications 0 22 }


oaMSInsertionLossCond NOTIFICATION-TYPE
    OBJECTS      { oaTypeIdx,
                   oaShelfIdx,
                   oaSlotIdx,
                   oaIdx,
                   oaMSInsertionLoss,
                   oaMSInsertionLossMaxTh,
                   condReportType,
                   condDateAndTime,
                   condSeverity,
                   condServiceAffecting,
                   trapSeqNum,
                   condDescription,
                   condObjectType,
                   condCodeType }
    STATUS       current
    DESCRIPTION  "A mid-stage insertion loss high threshold is exceeded for a
                  mid-stage amplifier."
    ::= { oaCondNotifications 0 23 }


oaMSInsertionLossClear NOTIFICATION-TYPE
    OBJECTS      { oaTypeIdx,
                   oaShelfIdx,
                   oaSlotIdx,
                   oaIdx,
                   condReportType,
                   condDateAndTime,
                   condSeverity,
                   condServiceAffecting,
                   trapSeqNum,
                   condDescription,
                   condObjectType,
                   condCodeType }
    STATUS       current
    DESCRIPTION  "A previously active optical amplifier midstage insertion loss
                  condition has cleared."
    ::= { oaCondNotifications 0 24 }


oaAmplifierConditioningCond NOTIFICATION-TYPE
    OBJECTS      { oaTypeIdx,
                   oaShelfIdx,
                   oaSlotIdx,
                   oaIdx,
                   condReportType,
                   condDateAndTime,
                   condSeverity,
                   condServiceAffecting,
                   trapSeqNum,
                   condDescription,
                   condObjectType,
                   condCodeType }
    STATUS       current
    DESCRIPTION  "There is an amplifier conditioning problem. When an amplifier
                  is initially plugged in, thermo-electric coolers (TEC) work to
                  control the pump laser temperature to between 16 degrees and
                  34 degrees Celsius. Until the pump laser temperature is within
                  range, the amplifier conditioning problem is present. If the
                  amplifier conditioning problem persists for more than 30
                  minutes, the condition is cleared and either a laser
                  temperature low threshold or a laser temperature high
                  threshold alarm is raised."
    ::= { oaCondNotifications 0 25 }


oaAmplifierConditioningClear NOTIFICATION-TYPE
    OBJECTS      { oaTypeIdx,
                   oaShelfIdx,

                   oaSlotIdx,
                   oaIdx,
                   condReportType,
                   condDateAndTime,
                   condSeverity,
                   condServiceAffecting,
                   trapSeqNum,
                   condDescription,
                   condObjectType,
                   condCodeType }
    STATUS       current
    DESCRIPTION  "A previously active optical amplifier conditioning condition
                  has cleared."
    ::= { oaCondNotifications 0 26 }


oaDspCommCond NOTIFICATION-TYPE
    OBJECTS      { oaTypeIdx,
                   oaShelfIdx,
                   oaSlotIdx,
                   oaIdx,
                   condReportType,
                   condDateAndTime,
                   condSeverity,
                   condServiceAffecting,
                   trapSeqNum,
                   condDescription,
                   condObjectType,
                   condCodeType }
    STATUS       current
    DESCRIPTION  "This alarm indicates that communication has failed between the
                  DSP and the processor handling backplane communications on an
                  optical amplifier circuit pack. Normal OAM&P operations to the
                  circuit pack, like provisioning and performance monitoring, is
                  affected when this alarm is active."
    ::= { oaCondNotifications 0 27 }


oaDspCommClear NOTIFICATION-TYPE
    OBJECTS      { oaTypeIdx, 
                   oaShelfIdx,
                   oaSlotIdx,
                   oaIdx,
                   condReportType,
                   condDateAndTime,
                   condSeverity,
                   condServiceAffecting,
                   trapSeqNum,
                   condDescription,
                   condObjectType,
                   condCodeType }
    STATUS       current
    DESCRIPTION  "A previously active optical amplifier DSP communications
                  condition has cleared."
    ::= { oaCondNotifications 0 28 }


oaBackReflectionSafetyOverrideCond NOTIFICATION-TYPE
    OBJECTS      { oaTypeIdx,
                   oaShelfIdx,
                   oaSlotIdx,
                   oaIdx,
                   condReportType,
                   condDateAndTime,
                   condSeverity,
                   condServiceAffecting ,
                   trapSeqNum,
                   condDescription,
                   condObjectType,
                   condCodeType }
    STATUS       current
    DESCRIPTION  "The Optical Back Reflection - High Threshold Safety Override
                  alarm indicates someone has activated the high threshold
                  safety override command to override the automatic power
                  reduction (APR) feature of the amplifier lasers. This command
                  overrides the APR feature of the amplifier for 20 to 600
                  seconds. When the timer expires, the alarm clears."
    ::= { oaCondNotifications 0 41 }


oaBackReflectionSafetyOverrideClear NOTIFICATION-TYPE
    OBJECTS      { oaTypeIdx,
                   oaShelfIdx,
                   oaSlotIdx,
                   oaIdx,
                   condReportType,
                   condDateAndTime,
                   condSeverity,
                   condServiceAffecting,
                   trapSeqNum,
                   condDescription,
                   condObjectType,
                   condCodeType }
    STATUS       current
    DESCRIPTION  "A previously active back reflection safety override condition
                  has been cleared."
    ::= { oaCondNotifications 0 42 }
    
    
oaBackReflectionHighThresholdCond NOTIFICATION-TYPE
    OBJECTS      { oaTypeIdx,
                   oaShelfIdx,
                   oaSlotIdx,
                   oaIdx,
                   condReportType,
                   condDateAndTime,
                   condSeverity,
                   condServiceAffecting ,
                   trapSeqNum,
                   condDescription,
                   condObjectType,
                   condCodeType }
    STATUS       current
    DESCRIPTION  "The Optical Amplifier Back Reflection High Threshold alarm
                  indicates that the measured optical back reflection power has
                  exceeded the high threshold. This serves as a warning that
                  optical back reflection is operating at an elevated level, and
                  that continued increases in the optical back reflection level
                  may result in an automatic laser safety shutdown."
    ::= { oaCondNotifications 0 43 }
    
    
oaBackReflectionHighThresholdClear NOTIFICATION-TYPE
    OBJECTS      { oaTypeIdx,
                   oaShelfIdx,
                   oaSlotIdx,
                   oaIdx,
                   condReportType,
                   condDateAndTime,
                   condSeverity,
                   condServiceAffecting,
                   trapSeqNum,
                   condDescription,
                   condObjectType,
                   condCodeType }
    STATUS       current
    DESCRIPTION  "A previously active back reflection high threshold condition
                  has been cleared."
    ::= { oaCondNotifications 0 44 }
    

oscLossOfSignalCond NOTIFICATION-TYPE
    OBJECTS      { oscShelfIdx,
                   oscSlotIdx,
                   oscIdx,
                   condReportType,
                   condDateAndTime,
                   condSeverity,
                   condServiceAffecting,
                   trapSeqNum,
                   condDescription,
                   condObjectType,
                   condCodeType }
    STATUS       current
    DESCRIPTION  "This condition indicates that an SFP transceiver has
                  experienced an input power drop that is below the manufacturer
                  s preset threshold."
    ::= { dataCommsCondNotifications 0 1 }


oscLossOfSignalClear NOTIFICATION-TYPE
    OBJECTS      { oscShelfIdx,
                   oscSlotIdx,
                   oscIdx,
                   condReportType,
                   condDateAndTime,
                   condSeverity,
                   condServiceAffecting,
                   trapSeqNum,
                   condDescription,
                   condObjectType,
                   condCodeType }
    STATUS       current
    DESCRIPTION  "A previously active optical supervisory channel loss of signal
                  condition has cleared."
    ::= { dataCommsCondNotifications 0 2 }


oscSfpMissingCond NOTIFICATION-TYPE
    OBJECTS      { oscShelfIdx,
                   oscSlotIdx,
                   oscIdx,
                   condReportType,
                   condDateAndTime,
                   condSeverity,
                   condServiceAffecting,
                   trapSeqNum,
                   condDescription,
                   condObjectType,
                   condCodeType }
    STATUS       current
    DESCRIPTION  "An SFP transceiver is missing from its associated port in an
                  MSCP circuit pack. To clear this alarm, insert an appropriate
                  transceiver in the associated port of the MSCP circuit pack."
    ::= { dataCommsCondNotifications 0 3 }


oscSfpMissingClear NOTIFICATION-TYPE
    OBJECTS      { oscShelfIdx,
                   oscSlotIdx,
                   oscIdx,
                   condReportType,
                   condDateAndTime,
                   condSeverity,
                   condServiceAffecting,
                   trapSeqNum,
                   condDescription,
                   condObjectType,
                   condCodeType }
    STATUS       current
    DESCRIPTION  "A previously active optical supervisory channel SFP missing
                  condition has cleared."
    ::= { dataCommsCondNotifications 0 4 }


pluggableInvUnknownCond NOTIFICATION-TYPE
    OBJECTS      { pluggableInvShelfIdx,
                   pluggableInvSlotTypeIdx,
                   pluggableInvSlotIdx,
                   pluggableInvPortIdx,
                   condReportType,
                   condDateAndTime,
                   condSeverity,
                   condServiceAffecting,
                   trapSeqNum,
                   condDescription,
                   condObjectType,
                   condCodeType }
    STATUS       current
    DESCRIPTION  "The SFP or XFP transceiver type is unknown to the system. This
                  alarm occurs because the transceiver is not supported by the
                  current software. To clear this alarm, insert a readable SFP
                  or XFP transceiver in the associated port of the circuit
                  pack."
    ::= { pluggableInvCondNotifications 0 1 }


pluggableInvUnknownClear NOTIFICATION-TYPE
    OBJECTS      { pluggableInvShelfIdx,
                   pluggableInvSlotTypeIdx,
                   pluggableInvSlotIdx,
                   pluggableInvPortIdx,
                   condReportType,
                   condDateAndTime,
                   condSeverity,
                   condServiceAffecting,
                   trapSeqNum,
                   condDescription,
                   condObjectType,
                   condCodeType }
    STATUS       current
    DESCRIPTION  "A previously active Pluggable Inventory Unknown condition has
                  cleared."
    ::= { pluggableInvCondNotifications 0 2 }



pluggableInvCommCond NOTIFICATION-TYPE
    OBJECTS      { pluggableInvShelfIdx,
                   pluggableInvSlotTypeIdx,
                   pluggableInvSlotIdx,
                   pluggableInvPortIdx,
                   condReportType,
                   condDateAndTime,
                   condSeverity,
                   condServiceAffecting,
                   trapSeqNum,
                   condDescription,
                   condObjectType,
                   condCodeType }
    STATUS       current
    DESCRIPTION  "This alarm indicates that communication between a circuit pack
                  and an inserted small form factor pluggable (SFP) transceiver
                  is not reliable."
    ::= { pluggableInvCondNotifications 0 3 }


pluggableInvCommClear NOTIFICATION-TYPE
    OBJECTS      { pluggableInvShelfIdx,
                   pluggableInvSlotTypeIdx,
                   pluggableInvSlotIdx,
                   pluggableInvPortIdx,
                   condReportType,
                   condDateAndTime,
                   condSeverity,
                   condServiceAffecting,
                   trapSeqNum,
                   condDescription,
                   condObjectType,
                   condCodeType }
    STATUS       current
    DESCRIPTION  "A previously active Pluggable Inventory communications
                  condition has cleared."
    ::= { pluggableInvCondNotifications 0 4 }



pluggableInvFailCond NOTIFICATION-TYPE
    OBJECTS      { pluggableInvShelfIdx,
                   pluggableInvSlotTypeIdx,
                   pluggableInvSlotIdx,
                   pluggableInvPortIdx,
                   condReportType,
                   condDateAndTime,
                   condSeverity,
                   condServiceAffecting,
                   trapSeqNum,
                   condDescription,
                   condObjectType,
                   condCodeType }
    STATUS       current
    DESCRIPTION  "There is an SFP or XFP transceiver failure."
    ::= { pluggableInvCondNotifications 0 5 }


pluggableInvFailClear NOTIFICATION-TYPE
    OBJECTS      { pluggableInvShelfIdx,
                   pluggableInvSlotTypeIdx,
                   pluggableInvSlotIdx,
                   pluggableInvPortIdx,
                   condReportType,
                   condDateAndTime,
                   condSeverity,
                   condServiceAffecting,
                   trapSeqNum,
                   condDescription,
                   condObjectType,
                   condCodeType }
    STATUS       current
    DESCRIPTION  "A previously active Pluggable Inventory fail condition has
                  cleared."
    ::= { pluggableInvCondNotifications 0 6 }


pluggableInvMismatchCond NOTIFICATION-TYPE
    OBJECTS      { pluggableInvShelfIdx,
                   pluggableInvSlotTypeIdx,
                   pluggableInvSlotIdx,
                   pluggableInvPortIdx,
                   condReportType,
                   condDateAndTime,
                   condSeverity,
                   condServiceAffecting,
                   trapSeqNum,
                   condDescription,
                   condObjectType,
                   condCodeType }
    STATUS       current
    DESCRIPTION  "There is an SFP mismatch condition active. There is a mismatch
                  between the SFP transceiver provisioned for a port of a
                  circuit pack and the physical SFP transceiver that is inserted
                  in the port."
    ::= { pluggableInvCondNotifications 0 7 }


pluggableInvMismatchClear NOTIFICATION-TYPE
    OBJECTS      { pluggableInvShelfIdx,
                   pluggableInvSlotTypeIdx,
                   pluggableInvSlotIdx,
                   pluggableInvPortIdx,
                   condReportType,
                   condDateAndTime,
                   condSeverity,
                   condServiceAffecting,
                   trapSeqNum,
                   condDescription,
                   condObjectType,
                   condCodeType }
    STATUS       current
    DESCRIPTION  "A previously active Pluggable Inventory mismatch condition has
                  cleared."
    ::= { pluggableInvCondNotifications 0 8 }


pluggableInvMissingCond NOTIFICATION-TYPE
    OBJECTS      { pluggableInvShelfIdx,
                   pluggableInvSlotTypeIdx,
                   pluggableInvSlotIdx,
                   pluggableInvPortIdx,
                   condReportType,
                   condDateAndTime,
                   condSeverity,
                   condServiceAffecting,
                   trapSeqNum,
                   condDescription,
                   condObjectType,
                   condCodeType }
    STATUS       current
    DESCRIPTION  "There is an SFP or XFP missing from the indicated port."
    ::= { pluggableInvCondNotifications 0 9 }


pluggableInvMissingClear NOTIFICATION-TYPE
    OBJECTS      { pluggableInvShelfIdx,
                   pluggableInvSlotTypeIdx,
                   pluggableInvSlotIdx,
                   pluggableInvPortIdx,
                   condReportType,
                   condDateAndTime,
                   condSeverity,
                   condServiceAffecting,
                   trapSeqNum,
                   condDescription,
                   condObjectType,
                   condCodeType }
    STATUS       current
    DESCRIPTION  "A previously active Pluggable Inventory missing condition has
                  cleared."
    ::= { pluggableInvCondNotifications 0 10 }

pluggableInvUnsupportedCond NOTIFICATION-TYPE
    OBJECTS      { pluggableInvShelfIdx,
                   pluggableInvSlotTypeIdx,
                   pluggableInvSlotIdx,
                   pluggableInvPortIdx,
                   condReportType,
                   condDateAndTime,
                   condSeverity,
                   condServiceAffecting,
                   trapSeqNum,
                   condDescription,
                   condObjectType,
                   condCodeType }
    STATUS       current
    DESCRIPTION  "The electrical SFP transceiver type is NOT supported in the given
                  port. This alarm occurs when an electrical SFP is plugged into a
                  port that does not support GE. To clear this alarm, remove the
                  electrical SFP."

    ::= { pluggableInvCondNotifications 0 11 }

pluggableInvUnsupportedClear NOTIFICATION-TYPE
    OBJECTS      { pluggableInvShelfIdx,
                   pluggableInvSlotTypeIdx,
                   pluggableInvSlotIdx,
                   pluggableInvPortIdx,
                   condReportType,
                   condDateAndTime,
                   condSeverity,
                   condServiceAffecting,
                   trapSeqNum,
                   condDescription,
                   condObjectType,
                   condCodeType }
    STATUS       current
    DESCRIPTION  "A previously active Pluggable unsupported condition has cleared."

    ::= { pluggableInvCondNotifications 0 12 }

xcvrMissingCond NOTIFICATION-TYPE
    OBJECTS      { xcvrTypeIdx,
                   xcvrShelfIdx,
                   xcvrSlotIdx,
                   xcvrIdx,
                   condReportType,
                   condDateAndTime,
                   condSeverity,
                   condServiceAffecting,
                   trapSeqNum,
                   condDescription,
                   condObjectType,
                   condCodeType }
    STATUS       current
    DESCRIPTION  "An SFP or XFP transceiver is missing from its associated port
                  in a circuit pack."
    ::= { xcvrCondNotifications 0 1 }


xcvrMissingClear NOTIFICATION-TYPE
    OBJECTS      { xcvrTypeIdx,
                   xcvrShelfIdx,
                   xcvrSlotIdx,
                   xcvrIdx,
                   condReportType,
                   condDateAndTime,
                   condSeverity,
                   condServiceAffecting,
                   trapSeqNum,
                   condDescription,
                   condObjectType,
                   condCodeType }
    STATUS       current
    DESCRIPTION  "A previously active transceiver port missing condition has
                  cleared."
    ::= { xcvrCondNotifications 0 2 }


xcvrMismatchCond NOTIFICATION-TYPE
    OBJECTS      { xcvrTypeIdx,
                   xcvrShelfIdx,
                   xcvrSlotIdx,
                   xcvrIdx,
                   condReportType,
                   condDateAndTime,
                   condSeverity,
                   condServiceAffecting,
                   trapSeqNum,
                   condDescription,
                   condObjectType,
                   condCodeType }
    STATUS       current
    DESCRIPTION  "There is a mismatch between the SFP or XFP transceiver
                  provisioned for a port of a circuit pack and the physical SFP
                  or XFP transceiver that is inserted in the port. The
                  provisioned SFP or XFP transceiver must match the transceiver
                  in the port."
    ::= { xcvrCondNotifications 0 3 }


xcvrMismatchClear NOTIFICATION-TYPE
    OBJECTS      { xcvrTypeIdx,
                   xcvrShelfIdx,
                   xcvrSlotIdx,
                   xcvrIdx,
                   condReportType,
                   condDateAndTime,
                   condSeverity,
                   condServiceAffecting,
                   trapSeqNum,
                   condDescription,
                   condObjectType,
                   condCodeType }
    STATUS       current
    DESCRIPTION  "A previously active transceiver port type mismatch condition
                  has cleared."
    ::= { xcvrCondNotifications 0 4 }


xcvrRFICond NOTIFICATION-TYPE
    OBJECTS      { xcvrTypeIdx,
                   xcvrShelfIdx,
                   xcvrSlotIdx,
                   xcvrIdx,
                   condReportType,
                   condDateAndTime,
                   condSeverity,
                   condServiceAffecting,
                   trapSeqNum,
                   condDescription,
                   condObjectType,
                   condCodeType }
    STATUS       current
    DESCRIPTION  "Remote Fault Indication: The source port to which the
                  specified destination transceiver port is cross-connected has
                  a service-affecting fault active against it."
    ::= { xcvrCondNotifications 0 5 }


xcvrRFIClear NOTIFICATION-TYPE
    OBJECTS      { xcvrTypeIdx,
                   xcvrShelfIdx,
                   xcvrSlotIdx,
                   xcvrIdx,
                   condReportType,
                   condDateAndTime,
                   condSeverity,
                   condServiceAffecting,
                   trapSeqNum,
                   condDescription,
                   condObjectType,
                   condCodeType }
    STATUS       current
    DESCRIPTION  "A previously active transceiver RFI condition has cleared."
    ::= { xcvrCondNotifications 0 6 }


xcvrLossOfSignalCond NOTIFICATION-TYPE
    OBJECTS      { xcvrTypeIdx,
                   xcvrShelfIdx,
                   xcvrSlotIdx,
                   xcvrIdx,
                   condReportType,
                   condDateAndTime,
                   condSeverity,
                   condServiceAffecting,
                   trapSeqNum,
                   condDescription,
                   condObjectType,
                   condCodeType }
    STATUS       current
    DESCRIPTION  "This alarm indicates that an SFP transceiver has experienced
                  an input power drop that is below the preset minimum
                  threshold."
    ::= { xcvrCondNotifications 0 7 }


xcvrLossOfSignalClear NOTIFICATION-TYPE
    OBJECTS      { xcvrTypeIdx,
                   xcvrShelfIdx,
                   xcvrSlotIdx,
                   xcvrIdx,
                   condReportType,
                   condDateAndTime,
                   condSeverity,
                   condServiceAffecting,
                   trapSeqNum,
                   condDescription,
                   condObjectType,
                   condCodeType }
    STATUS       current
    DESCRIPTION  "A previously active transceiver port Loss Of Signal condition
                  has cleared."
    ::= { xcvrCondNotifications 0 8 }


xcvrLossOfLockCond NOTIFICATION-TYPE
    OBJECTS      { xcvrTypeIdx,
                   xcvrShelfIdx,
                   xcvrSlotIdx,
                   xcvrIdx,
                   condReportType,
                   condDateAndTime,
                   condSeverity,
                   condServiceAffecting,
                   trapSeqNum,
                   condDescription,
                   condObjectType,
                   condCodeType }
    STATUS       current
    DESCRIPTION  "This alarm indicates that a transceiver port is unable to lock
                  on the incoming bit stream. This is a result of either: the
                  provisioned protocol does not match the incoming signal, or
                  the incoming signal is excessively degraded."
    ::= { xcvrCondNotifications 0 9 }


xcvrLossOfLockClear NOTIFICATION-TYPE
    OBJECTS      { xcvrTypeIdx,
                   xcvrShelfIdx,
                   xcvrSlotIdx,
                   xcvrIdx,
                   condReportType,
                   condDateAndTime,
                   condSeverity,
                   condServiceAffecting,
                   trapSeqNum,
                   condDescription,
                   condObjectType,
                   condCodeType }
    STATUS       current
    DESCRIPTION  "A previously active transceiver port Loss Of Lock condition
                  has cleared."
    ::= { xcvrCondNotifications 0 10 }


xcvrOpticalPwrReceivedMinCond NOTIFICATION-TYPE
    OBJECTS      { xcvrTypeIdx,
                   xcvrShelfIdx,
                   xcvrSlotIdx,
                   xcvrIdx,

                   xcvrOpticalPwrReceived,
                   xcvrOpticalPwrReceivedMinTh,
                   condReportType,
                   condDateAndTime,
                   condSeverity,
                   condServiceAffecting,
                   trapSeqNum,
                   condDescription,
                   condObjectType,
                   condCodeType }
    STATUS       current
    DESCRIPTION  "The optical power received (OPR) low threshold is not met. The
                  input signal to a transceiver has reached the optical power
                  received low threshold. If the input signal drops to below the
                  input sensitivity level, the transceiver degrades in
                  performance."
    ::= { xcvrCondNotifications 0 11 }


xcvrOpticalPwrReceivedMinClear NOTIFICATION-TYPE
    OBJECTS      { xcvrTypeIdx,
                   xcvrShelfIdx,
                   xcvrSlotIdx,
                   xcvrIdx,
                   condReportType,
                   condDateAndTime,
                   condSeverity,
                   condServiceAffecting,
                   trapSeqNum,
                   condDescription,
                   condObjectType,
                   condCodeType }
    STATUS       current
    DESCRIPTION  "A previously active transceiver port minimum power received
                  condition has cleared."
    ::= { xcvrCondNotifications 0 12 }


xcvrOpticalPwrReceivedMaxCond NOTIFICATION-TYPE
    OBJECTS      { xcvrTypeIdx,
                   xcvrShelfIdx,
                   xcvrSlotIdx,
                   xcvrIdx,
                   xcvrOpticalPwrReceived,
                   xcvrOpticalPwrReceivedMaxTh,
                   condReportType,
                   condDateAndTime,
                   condSeverity,
                   condServiceAffecting,
                   trapSeqNum,
                   condDescription,
                   condObjectType,
                   condCodeType }
    STATUS       current
    DESCRIPTION  "The optical power received (OPR) high threshold is exceeded.
                  The input signal to a transceiver has reached the optical
                  power received high threshold."
    ::= { xcvrCondNotifications 0 13 }


xcvrOpticalPwrReceivedMaxClear NOTIFICATION-TYPE
    OBJECTS      { xcvrTypeIdx,
                   xcvrShelfIdx,
                   xcvrSlotIdx,
                   xcvrIdx,
                   condReportType,
                   condDateAndTime,
                   condSeverity,
                   condServiceAffecting,
                   trapSeqNum,
                   condDescription,
                   condObjectType,
                   condCodeType }
    STATUS       current
    DESCRIPTION  "A previously active transceiver port maximum power received
                  condition has cleared."
    ::= { xcvrCondNotifications 0 14 }


xcvrOpticalPwrTransmittedMinCond NOTIFICATION-TYPE
    OBJECTS      { xcvrTypeIdx,
                   xcvrShelfIdx,
                   xcvrSlotIdx,
                   xcvrIdx,
                   xcvrOpticalPwrTransmitted,
                   xcvrOpticalPwrTransmittedMinTh,
                   condReportType,
                   condDateAndTime,
                   condSeverity,
                   condServiceAffecting,
                   trapSeqNum,
                   condDescription,
                   condObjectType,
                   condCodeType }
    STATUS       current
    DESCRIPTION  "The optical power transmitted (OPT) is below the low threshold
                  for the transceiver."
    ::= { xcvrCondNotifications 0 15 }


xcvrOpticalPwrTransmittedMinClear NOTIFICATION-TYPE
    OBJECTS      { xcvrTypeIdx,
                   xcvrShelfIdx,
                   xcvrSlotIdx,
                   xcvrIdx,
                   condReportType,
                   condDateAndTime,
                   condSeverity,
                   condServiceAffecting,
                   trapSeqNum,
                   condDescription,
                   condObjectType,
                   condCodeType }
    STATUS       current
    DESCRIPTION  "A previously active transceiver port minimum power transmitted
                  condition has cleared."
    ::= { xcvrCondNotifications 0 16 }


xcvrOpticalPwrTransmittedMaxCond NOTIFICATION-TYPE
    OBJECTS      { xcvrTypeIdx,
                   xcvrShelfIdx,
                   xcvrSlotIdx,
                   xcvrIdx,
                   xcvrOpticalPwrTransmitted,
                   xcvrOpticalPwrTransmittedMaxTh,
                   condReportType,
                   condDateAndTime,
                   condSeverity,
                   condServiceAffecting,
                   trapSeqNum,
                   condDescription,
                   condObjectType,
                   condCodeType }
    STATUS       current
    DESCRIPTION  "The optical power transmitted (OPT) high threshold for a
                  transceiver is exceeded."
    ::= { xcvrCondNotifications 0 17 }


xcvrOpticalPwrTransmittedMaxClear NOTIFICATION-TYPE
    OBJECTS      { xcvrTypeIdx,
                   xcvrShelfIdx,
                   xcvrSlotIdx,
                   xcvrIdx,
                   condReportType,
                   condDateAndTime,
                   condSeverity,
                   condServiceAffecting,
                   trapSeqNum,
                   condDescription,
                   condObjectType,
                   condCodeType }
    STATUS       current
    DESCRIPTION  "A previously active transceiver port maximum power transmitted
                  condition has cleared."
    ::= { xcvrCondNotifications 0 18 }


xcvrLossOfFrameCond NOTIFICATION-TYPE
    OBJECTS      { xcvrTypeIdx,
                   xcvrShelfIdx,
                   xcvrSlotIdx,
                   xcvrIdx,

                   condReportType,
                   condDateAndTime,
                   condSeverity,
                   condServiceAffecting,
                   trapSeqNum,
                   condDescription,
                   condObjectType,
                   condCodeType }
    STATUS       current
    DESCRIPTION  "A transceiver reports a SONET or SDH loss of frame for a
                  transceiver that is provisioned to receive a SONET or SDH
                  protocol."
    ::= { xcvrCondNotifications 0 19 }


xcvrLossOfFrameClear NOTIFICATION-TYPE
    OBJECTS      { xcvrTypeIdx,
                   xcvrShelfIdx,
                   xcvrSlotIdx,

                   xcvrIdx,
                   condReportType,
                   condDateAndTime,
                   condSeverity,
                   condServiceAffecting,
                   trapSeqNum,
                   condDescription,
                   condObjectType,
                   condCodeType }
    STATUS       current
    DESCRIPTION  "A previously active loss of frame condition has cleared."
    ::= { xcvrCondNotifications 0 20 }


xcvrLossOfSyncCond NOTIFICATION-TYPE
    OBJECTS      { xcvrTypeIdx,
                   xcvrShelfIdx,
                   xcvrSlotIdx,
                   xcvrIdx,
                   condReportType,
                   condDateAndTime,
                   condSeverity,
                   condServiceAffecting,
                   trapSeqNum,
                   condDescription,
                   condObjectType,
                   condCodeType }
    STATUS       current
    DESCRIPTION  "Indicates that a loss of synchronization condition has been
                  detected by the transceiver port on the incoming gigabit
                  ethernet or 10GELAN protocol."
    ::= { xcvrCondNotifications 0 21 }


xcvrLossOfSyncClear NOTIFICATION-TYPE
    OBJECTS      { xcvrTypeIdx,
                   xcvrShelfIdx,
                   xcvrSlotIdx,
                   xcvrIdx,
                   condReportType,
                   condDateAndTime,
                   condSeverity,
                   condServiceAffecting,
                   trapSeqNum,
                   condDescription,
                   condObjectType,
                   condCodeType }
    STATUS       current
    DESCRIPTION  "A previously active loss of synchronization condition has
                  cleared."
    ::= { xcvrCondNotifications 0 22 }


xcvrLoopbackCond NOTIFICATION-TYPE
    OBJECTS      { xcvrTypeIdx,
                   xcvrShelfIdx,
                   xcvrSlotIdx,
                   xcvrIdx,
                   condReportType,
                   condDateAndTime,
                   condSeverity,
                   condServiceAffecting,
                   trapSeqNum,
                   condDescription,
                   condObjectType,
                   condCodeType }
    STATUS       current
    DESCRIPTION  "Indicates that the transceiver has been provisioned to enter
                  loopback mode."
    ::= { xcvrCondNotifications 0 27 }


xcvrLoopbackClear NOTIFICATION-TYPE
    OBJECTS      { xcvrTypeIdx,
                   xcvrShelfIdx,
                   xcvrSlotIdx,
                   xcvrIdx,
                   condReportType,
                   condDateAndTime,
                   condSeverity,
                   condServiceAffecting,
                   trapSeqNum,
                   condDescription,
                   condObjectType,
                   condCodeType }
    STATUS       current
    DESCRIPTION  "A previously active loopback condition on the transceiver has
                  been cleared."
    ::= { xcvrCondNotifications 0 28 }


xcvrForcedSwitchToProtectionCond NOTIFICATION-TYPE
    OBJECTS      { xcvrTypeIdx,
                   xcvrShelfIdx,
                   xcvrSlotIdx,
                   xcvrIdx,
                   condReportType,
                   condDateAndTime,
                   condSeverity,
                   condServiceAffecting,
                   trapSeqNum,
                   condDescription,
                   condObjectType,
                   condCodeType }
    STATUS       current
    DESCRIPTION  "The active transceiver of a protected transceiver pair has
                  been forced to switch to the Protection transceiver."
    ::= { xcvrCondNotifications 0 29 }


xcvrForcedSwitchToProtectionClear NOTIFICATION-TYPE
    OBJECTS      { xcvrTypeIdx,
                   xcvrShelfIdx,
                   xcvrSlotIdx,
                   xcvrIdx,
                   condReportType,
                   condDateAndTime,
                   condSeverity,
                   condServiceAffecting,
                   trapSeqNum,
                   condDescription,
                   condObjectType,
                   condCodeType }
    STATUS       current
    DESCRIPTION  "A previously active Forced Switch To Protection condition has
                  cleared."
    ::= { xcvrCondNotifications 0 30 }


xcvrForcedSwitchToWorkingCond NOTIFICATION-TYPE
    OBJECTS      { xcvrTypeIdx,
                   xcvrShelfIdx,
                   xcvrSlotIdx,
                   xcvrIdx,
                   condReportType,
                   condDateAndTime,
                   condSeverity,
                   condServiceAffecting,
                   trapSeqNum,
                   condDescription,
                   condObjectType,
                   condCodeType }
    STATUS       current
    DESCRIPTION  "The active transceiver of a protected transceiver pair has
                  been forced to switch to the Working transceiver."
    ::= { xcvrCondNotifications 0 31 }


xcvrForcedSwitchToWorkingClear NOTIFICATION-TYPE
    OBJECTS      { xcvrTypeIdx,
                   xcvrShelfIdx,
                   xcvrSlotIdx,
                   xcvrIdx,
                   condReportType,
                   condDateAndTime,
                   condSeverity,
                   condServiceAffecting,
                   trapSeqNum,
                   condDescription,
                   condObjectType,
                   condCodeType }
    STATUS       current
    DESCRIPTION  "A previously active Forced Switch To Working condition has
                  cleared."
    ::= { xcvrCondNotifications 0 32 }


xcvrLockoutProtectionCond NOTIFICATION-TYPE
    OBJECTS      { xcvrTypeIdx,
                   xcvrShelfIdx,
                   xcvrSlotIdx,
                   xcvrIdx,
                   condReportType,
                   condDateAndTime,
                   condSeverity,
                   condServiceAffecting,
                   trapSeqNum,
                   condDescription,
                   condObjectType,
                   condCodeType }
    STATUS       current
    DESCRIPTION  "The Protection transceiver of a protected transceiver pair has
                  been locked out."
    ::= { xcvrCondNotifications 0 33 }


xcvrLockoutProtectionClear NOTIFICATION-TYPE
    OBJECTS      { xcvrTypeIdx,
                   xcvrShelfIdx,
                   xcvrSlotIdx,
                   xcvrIdx,
                   condReportType,
                   condDateAndTime,
                   condSeverity,
                   condServiceAffecting,
                   trapSeqNum,
                   condDescription,
                   condObjectType,
                   condCodeType }
    STATUS       current
    DESCRIPTION  "A previously active Lockout Protection condition has cleared."
    ::= { xcvrCondNotifications 0 34 }


xcvrLockoutWorkingCond NOTIFICATION-TYPE
    OBJECTS      { xcvrTypeIdx,
                   xcvrShelfIdx,
                   xcvrSlotIdx,
                   xcvrIdx,
                   condReportType,
                   condDateAndTime,
                   condSeverity,
                   condServiceAffecting,
                   trapSeqNum,
                   condDescription,
                   condObjectType,
                   condCodeType }
    STATUS       current
    DESCRIPTION  "The Working transceiver of a protected transceiver pair has
                  been locked out."
    ::= { xcvrCondNotifications 0 35 }


xcvrLockoutWorkingClear NOTIFICATION-TYPE
    OBJECTS      { xcvrTypeIdx,
                   xcvrShelfIdx,
                   xcvrSlotIdx,
                   xcvrIdx,
                   condReportType,
                   condDateAndTime,
                   condSeverity,
                   condServiceAffecting,
                   trapSeqNum,
                   condDescription,
                   condObjectType,
                   condCodeType }
    STATUS       current
    DESCRIPTION  "A previously active Lockout Working condition has cleared."
    ::= { xcvrCondNotifications 0 36 }


xcvrTempMaxCond NOTIFICATION-TYPE
    OBJECTS      { xcvrTypeIdx,
                   xcvrShelfIdx,
                   xcvrSlotIdx,
                   xcvrIdx,
                   condReportType,
                   condDateAndTime,
                   condSeverity,
                   condServiceAffecting,
                   trapSeqNum,
                   condDescription,
                   condObjectType,
                   condCodeType }
    STATUS       current
    DESCRIPTION  "Indicates that the temperature of the physical transceiver has
                  risen above the maximum threshold."
    ::= { xcvrCondNotifications 0 37 }


xcvrTempMaxClear NOTIFICATION-TYPE
    OBJECTS      { xcvrTypeIdx,
                   xcvrShelfIdx,
                   xcvrSlotIdx,
                   xcvrIdx,
                   condReportType,
                   condDateAndTime,
                   condSeverity,
                   condServiceAffecting,
                   trapSeqNum,
                   condDescription,
                   condObjectType,
                   condCodeType }
    STATUS       current
    DESCRIPTION  "A previously active Temperature Exceeded Maximum condition has
                  cleared."
    ::= { xcvrCondNotifications 0 38 }


xcvrWavelengthNotAchievableCond NOTIFICATION-TYPE
    OBJECTS      { xcvrTypeIdx,
                   xcvrShelfIdx,
                   xcvrSlotIdx,
                   xcvrIdx,
                   condReportType,
                   condDateAndTime,
                   condSeverity,
                   condServiceAffecting,
                   trapSeqNum,
                   condDescription,
                   condObjectType,
                   condCodeType }
    STATUS       current
    DESCRIPTION  "Indicates that the transceiver is not currently able to tune
                  to the set wavelength."
    ::= { xcvrCondNotifications 0 39 }


xcvrWavelengthNotAchievableClear NOTIFICATION-TYPE
    OBJECTS      { xcvrTypeIdx,
                   xcvrShelfIdx,
                   xcvrSlotIdx,
                   xcvrIdx,
                   condReportType,
                   condDateAndTime,
                   condSeverity,
                   condServiceAffecting,
                   trapSeqNum,
                   condDescription,
                   condObjectType,
                   condCodeType }
    STATUS       current
    DESCRIPTION  "A previously active Wavelength Not Achievable condition has
                  cleared."
    ::= { xcvrCondNotifications 0 40 }


xcvrAlarmIndicationSignalCond NOTIFICATION-TYPE
    OBJECTS      { xcvrTypeIdx,
                   xcvrShelfIdx,
                   xcvrSlotIdx,
                   xcvrIdx,
                   condReportType,
                   condDateAndTime,
                   condSeverity,
                   condServiceAffecting,
                   trapSeqNum,
                   condDescription,
                   condObjectType,
                   condCodeType }
    STATUS       current
    DESCRIPTION  "An Alarm Indication Signal indication is active on the
                  transceiver port."
    ::= { xcvrCondNotifications 0 41 }


xcvrAlarmIndicationSignalClear NOTIFICATION-TYPE
    OBJECTS      { xcvrTypeIdx,
                   xcvrShelfIdx,
                   xcvrSlotIdx,
                   xcvrIdx,
                   condReportType,
                   condDateAndTime,
                   condSeverity,
                   condServiceAffecting,
                   trapSeqNum,
                   condDescription,
                   condObjectType,
                   condCodeType }
    STATUS       current
    DESCRIPTION  "A previously active Alarm Indication Signal condition has
                  cleared."
    ::= { xcvrCondNotifications 0 42 }


xcvrTraceMismatchCond NOTIFICATION-TYPE
    OBJECTS      { xcvrTypeIdx,
                   xcvrShelfIdx,
                   xcvrSlotIdx,
                   xcvrIdx,
                   xcvrReceivedTraceLabel,
                   xcvrExpectedTraceLabel,
                   condReportType,
                   condDateAndTime,
                   condSeverity,
                   condServiceAffecting,
                   trapSeqNum,
                   condDescription,
                   condObjectType,
                   condCodeType }
    STATUS       current
    DESCRIPTION  "This condition indicates that the received trace label on the
                  transciever port does not match the expected trace label."
    ::= { xcvrCondNotifications 0 43 }


xcvrTraceMismatchClear NOTIFICATION-TYPE
    OBJECTS      { xcvrTypeIdx,
                   xcvrShelfIdx,
                   xcvrSlotIdx,
                   xcvrIdx,
                   condReportType,
                   condDateAndTime,
                   condSeverity,
                   condServiceAffecting,
                   trapSeqNum,
                   condDescription,
                   condObjectType,
                   condCodeType }
    STATUS       current
    DESCRIPTION  "A previously active Trace Mismatch condition has cleared."
    ::= { xcvrCondNotifications 0 44 }


xcvrRemoteFaultCond NOTIFICATION-TYPE
    OBJECTS      { xcvrTypeIdx,
                   xcvrShelfIdx,
                   xcvrSlotIdx,
                   xcvrIdx,
                   condReportType,
                   condDateAndTime,
                   condSeverity,
                   condServiceAffecting,
                   trapSeqNum,
                   condDescription,
                   condObjectType,
                   condCodeType }
    STATUS       current
    DESCRIPTION  "A remote fault indication is active on the traceiver port."
    ::= { xcvrCondNotifications 0 45 }


xcvrRemoteFaultClear NOTIFICATION-TYPE
    OBJECTS      { xcvrTypeIdx,
                   xcvrShelfIdx,
                   xcvrSlotIdx,
                   xcvrIdx,
                   condReportType,
                   condDateAndTime,
                   condSeverity,
                   condServiceAffecting,
                   trapSeqNum,
                   condDescription,
                   condObjectType,
                   condCodeType }
    STATUS       current
    DESCRIPTION  "A previously raised remote fault indication has cleared."
    ::= { xcvrCondNotifications 0 46 }

xcvrSignalDegradeCond NOTIFICATION-TYPE
    OBJECTS      { xcvrTypeIdx,
                   xcvrShelfIdx,
                   xcvrSlotIdx,
                   xcvrIdx,
                   condReportType,
                   condDateAndTime,
                   condSeverity,
                   condServiceAffecting,
                   trapSeqNum,
                   condDescription,
                   condObjectType,
                   condCodeType }
    STATUS       current
    DESCRIPTION  "The Signal Degrade BER threshold has been crossed on the
                  transiever port."
    ::= { xcvrCondNotifications 0 47 }


xcvrSignalDegradeClear NOTIFICATION-TYPE
    OBJECTS      { xcvrTypeIdx,
                   xcvrShelfIdx,
                   xcvrSlotIdx,
                   xcvrIdx,
                   condReportType,
                   condDateAndTime,
                   condSeverity,
                   condServiceAffecting,
                   trapSeqNum,
                   condDescription,
                   condObjectType,
                   condCodeType }
    STATUS       current
    DESCRIPTION  "A previously active Signal Degrade condition has cleared."
    ::= { xcvrCondNotifications 0 48 }


xcvrOTNPayloadMismatchCond NOTIFICATION-TYPE
    OBJECTS      { xcvrTypeIdx,
                   xcvrShelfIdx,
                   xcvrSlotIdx,
                   xcvrIdx,
                   condReportType,
                   condDateAndTime,
                   condSeverity,
                   condServiceAffecting,
                   trapSeqNum,
                   condDescription,
                   condObjectType,
                   condCodeType }
    STATUS       current
    DESCRIPTION  "An OTN payload mismatch is active on the transceiver port
                  facility."
    ::= { xcvrCondNotifications 0 49 }


xcvrOTNPayloadMismatchClear NOTIFICATION-TYPE
    OBJECTS      { xcvrTypeIdx,
                   xcvrShelfIdx,
                   xcvrSlotIdx,
                   xcvrIdx,
                   condReportType,
                   condDateAndTime,
                   condSeverity,
                   condServiceAffecting,
                   trapSeqNum,
                   condDescription,
                   condObjectType,
                   condCodeType }
    STATUS       current
    DESCRIPTION  "A previously active OTN payload mismatch condition on the
                  transceiver port facility has cleared."
    ::= { xcvrCondNotifications 0 50 }


xcvrLFCond NOTIFICATION-TYPE
    OBJECTS      { xcvrTypeIdx,
                   xcvrShelfIdx,
                   xcvrSlotIdx,
                   xcvrIdx,
                   condReportType,
                   condDateAndTime,
                   condSeverity,
                   condServiceAffecting,
                   trapSeqNum,
                   condDescription,
                   condObjectType,
                   condCodeType }
    STATUS       current
    DESCRIPTION  "Local Failure: Raised when a port detects and incoming local
                  failure indication is received."
    ::= { xcvrCondNotifications 0 51 }


xcvrLFClear NOTIFICATION-TYPE
    OBJECTS      { xcvrTypeIdx,
                   xcvrShelfIdx,
                   xcvrSlotIdx,
                   xcvrIdx,
                   condReportType,
                   condDateAndTime,
                   condSeverity,
                   condServiceAffecting,
                   trapSeqNum,
                   condDescription,
                   condObjectType,
                   condCodeType }
    STATUS       current
    DESCRIPTION  "A previously active transceiver LF condition has cleared."
    ::= { xcvrCondNotifications 0 52 }

xcvrOpenConnectionIndicatorCond NOTIFICATION-TYPE
    OBJECTS      { xcvrTypeIdx,
                   xcvrShelfIdx,
                   xcvrSlotIdx,
                   xcvrIdx,
                   condReportType,
                   condDateAndTime,
                   condSeverity,
                   condServiceAffecting,
                   trapSeqNum,
                   condDescription,
                   condObjectType,
                   condCodeType }
    STATUS       current
    DESCRIPTION  "An Open Connection Indicator is active on the
                  transceiver port."
    ::= { xcvrCondNotifications 0 53 }


xcvrOpenConnectionIndicatorClear NOTIFICATION-TYPE
    OBJECTS      { xcvrTypeIdx,
                   xcvrShelfIdx,
                   xcvrSlotIdx,
                   xcvrIdx,
                   condReportType,
                   condDateAndTime,
                   condSeverity,
                   condServiceAffecting,
                   trapSeqNum,
                   condDescription,
                   condObjectType,
                   condCodeType }
    STATUS       current
    DESCRIPTION  "A previously active Open Connection Indicator condition has
                  cleared."
    ::= { xcvrCondNotifications 0 54 }
    

xcvrReceivedLockoutCond NOTIFICATION-TYPE
    OBJECTS      { xcvrTypeIdx,
                   xcvrShelfIdx,
                   xcvrSlotIdx,
                   xcvrIdx,
                   condReportType,
                   condDateAndTime,
                   condSeverity,
                   condServiceAffecting,
                   trapSeqNum,
                   condDescription,
                   condObjectType,
                   condCodeType }
    STATUS       current
    DESCRIPTION  "A Received Lockout indication is active on the
                  transceiver port."
    ::= { xcvrCondNotifications 0 55 }


xcvrReceivedLockoutClear NOTIFICATION-TYPE
    OBJECTS      { xcvrTypeIdx,
                   xcvrShelfIdx,
                   xcvrSlotIdx,
                   xcvrIdx,
                   condReportType,
                   condDateAndTime,
                   condSeverity,
                   condServiceAffecting,
                   trapSeqNum,
                   condDescription,
                   condObjectType,
                   condCodeType }
    STATUS       current
    DESCRIPTION  "A previously active Received Lockout condition has
                  cleared."
    ::= { xcvrCondNotifications 0 56 }


xcvrBackwardDefectIndicatorCond NOTIFICATION-TYPE
    OBJECTS      { xcvrTypeIdx,
                   xcvrShelfIdx,
                   xcvrSlotIdx,
                   xcvrIdx,
                   condReportType,
                   condDateAndTime,
                   condSeverity,
                   condServiceAffecting,
                   trapSeqNum,
                   condDescription,
                   condObjectType,
                   condCodeType }
    STATUS       current
    DESCRIPTION  "A Backward Defect Indicator is active on the
                  transceiver port."
    ::= { xcvrCondNotifications 0 57 }


xcvrBackwardDefectIndicatorClear NOTIFICATION-TYPE
    OBJECTS      { xcvrTypeIdx,
                   xcvrShelfIdx,
                   xcvrSlotIdx,
                   xcvrIdx,
                   condReportType,
                   condDateAndTime,
                   condSeverity,
                   condServiceAffecting,
                   trapSeqNum,
                   condDescription,
                   condObjectType,
                   condCodeType }
    STATUS       current
    DESCRIPTION  "A previously active Backward Defect Indicator condition has
                  cleared."
    ::= { xcvrCondNotifications 0 58 }

amdLossOfSignalCond NOTIFICATION-TYPE
    OBJECTS      { amdTypeIdx,
                   amdShelfIdx,
                   amdSlotIdx,
                   amdLineIdx,
                   amdPortIdx,
                   condReportType,
                   condDateAndTime,
                   condSeverity,
                   condServiceAffecting,
                   trapSeqNum,
                   condDescription,
                   condObjectType,
                   condCodeType }
    STATUS       obsolete
    DESCRIPTION  "This condition indicates that an active mux/demux that has
                  experienced an input power drop that is below the preset
                  threshold. This can be against either a channel or the
                  composite line port."
    ::= { amdCondNotifications 0 1 }


amdLossOfSignalClear NOTIFICATION-TYPE
    OBJECTS      { amdTypeIdx,
                   amdShelfIdx,
                   amdSlotIdx,
                   amdLineIdx,
                   amdPortIdx,
                   condReportType,
                   condDateAndTime,
                   condSeverity,
                   condServiceAffecting,
                   trapSeqNum,
                   condDescription,
                   condObjectType,
                   condCodeType }
    STATUS       obsolete
    DESCRIPTION  "A previously raised active multiplexer-demultiplexer loss of
                  signal condition has cleared."
    ::= { amdCondNotifications 0 2 }


amdOpticalPwrReceivedMinCond NOTIFICATION-TYPE
    OBJECTS      { amdTypeIdx,
                   amdShelfIdx,
                   amdSlotIdx,
                   amdLineIdx,
                   amdPortIdx,
                   amdOpticalPwrReceived,
                   amdOpticalPwrReceivedMinTh,
                   condReportType,
                   condDateAndTime,
                   condSeverity,
                   condServiceAffecting,
                   trapSeqNum,
                   condDescription,
                   condObjectType,
                   condCodeType }
    STATUS       obsolete
    DESCRIPTION  "Indicates that the input power for the active
                  multiplexer-demultiplexer facility has fallen below the
                  minimum threshold."
    ::= { amdCondNotifications 0 3 }


amdOpticalPwrReceivedMinClear NOTIFICATION-TYPE
    OBJECTS      { amdTypeIdx,
                   amdShelfIdx,
                   amdSlotIdx,
                   amdLineIdx,
                   amdPortIdx,
                   condReportType,
                   condDateAndTime,
                   condSeverity,
                   condServiceAffecting,
                   trapSeqNum,
                   condDescription,
                   condObjectType,
                   condCodeType }
    STATUS       obsolete
    DESCRIPTION  "A previously raised active multiplexer-demultiplexer minimum
                  power received condition has cleared."
    ::= { amdCondNotifications 0 4 }


amdOpticalPwrReceivedMaxCond NOTIFICATION-TYPE
    OBJECTS      { amdTypeIdx,
                   amdShelfIdx,
                   amdSlotIdx,
                   amdLineIdx,
                   amdPortIdx,
                   amdOpticalPwrReceived,
                   amdOpticalPwrReceivedMaxTh,
                   condReportType,
                   condDateAndTime,
                   condSeverity,
                   condServiceAffecting,
                   trapSeqNum,
                   condDescription,
                   condObjectType,
                   condCodeType }
    STATUS       obsolete
    DESCRIPTION  "Indicates that the input power for the active
                  multiplexer-demultiplexer facility has risen above the maximum
                  threshold."
    ::= { amdCondNotifications 0 5 }


amdOpticalPwrReceivedMaxClear NOTIFICATION-TYPE
    OBJECTS      { amdTypeIdx,
                   amdShelfIdx,
                   amdSlotIdx,
                   amdLineIdx,
                   amdPortIdx,
                   condReportType,
                   condDateAndTime,
                   condSeverity,
                   condServiceAffecting,
                   trapSeqNum,
                   condDescription,
                   condObjectType,
                   condCodeType }
    STATUS       obsolete
    DESCRIPTION  "A previously raised active multiplexer-demultiplexer maximum
                  power received condition has cleared."
    ::= { amdCondNotifications 0 6 }


amdTPLNACond NOTIFICATION-TYPE
    OBJECTS      { amdTypeIdx,
                   amdShelfIdx,
                   amdSlotIdx,
                   amdLineIdx,
                   amdPortIdx,
                   amdOpticalPwrTransmitted,
                   amdOpticalPwrTransmittedTarget,
                   condReportType,
                   condDateAndTime,
                   condSeverity,
                   condServiceAffecting,
                   trapSeqNum,
                   condDescription,
                   condObjectType,
                   condCodeType }
    STATUS       obsolete
    DESCRIPTION  "A channel target power level not achieved (TPLNA) condition is
                  triggered when the output power for a channel of a 32-Channel
                  DWDM Active Mux/Demux (D32AMD) module is above or below the
                  target power transmitted level for that channel."
    ::= { amdCondNotifications 0 7 }


amdTPLNAClear NOTIFICATION-TYPE
    OBJECTS      { amdTypeIdx,
                   amdShelfIdx,
                   amdSlotIdx,
                   amdLineIdx,
                   amdPortIdx,
                   condReportType,
                   condDateAndTime,
                   condSeverity,
                   condServiceAffecting,
                   trapSeqNum,
                   condDescription,
                   condObjectType,
                   condCodeType }
    STATUS       obsolete
    DESCRIPTION  "A previously raised active target power level not achieved
                  condition has been cleared."
    ::= { amdCondNotifications 0 8 }


amdTALNACond NOTIFICATION-TYPE
    OBJECTS      { amdTypeIdx,
                   amdShelfIdx,
                   amdSlotIdx,
                   amdLineIdx,
                   amdPortIdx,
                   amdOpticalAttentuation,
                   amdOpticalAttenuationTarget,
                   condReportType,
                   condDateAndTime,
                   condSeverity,
                   condServiceAffecting,
                   trapSeqNum,
                   condDescription,
                   condObjectType,
                   condCodeType }
    STATUS       obsolete
    DESCRIPTION  "The target attenuation level not achieved (TALNA) condition is
                  triggered when the attenuation for a 32-Channel DWDM Active
                  Mux/Demux (D32AMD) is outside the preset attenuation levels
                  for a composite line."
    ::= { amdCondNotifications 0 9 }


amdTALNAClear NOTIFICATION-TYPE
    OBJECTS      { amdTypeIdx,
                   amdShelfIdx,
                   amdSlotIdx,
                   amdLineIdx,
                   amdPortIdx,
                   condReportType,
                   condDateAndTime,
                   condSeverity,
                   condServiceAffecting,
                   trapSeqNum,
                   condDescription,
                   condObjectType,
                   condCodeType }
    STATUS       obsolete
    DESCRIPTION  "A previously raised active target attenuation level not
                  achieved condition has been cleared."
    ::= { amdCondNotifications 0 10 }


ocnLossOfSignalCond NOTIFICATION-TYPE
    OBJECTS      { ocnTypeIdx,
                   ocnShelfIdx,
                   ocnSlotIdx,
                   ocnPortIdx,
                   condReportType,
                   condDateAndTime,
                   condSeverity,
                   condServiceAffecting,
                   trapSeqNum,
                   condDescription,
                   condObjectType,
                   condCodeType }
    STATUS       current
    DESCRIPTION  "This notification indicates that there is no input signal
                  detected on the OC-N port."
    ::= { ocnCondNotifications 0 1 }


ocnLossOfSignalClear NOTIFICATION-TYPE
    OBJECTS      { ocnTypeIdx,
                   ocnShelfIdx,
                   ocnSlotIdx,
                   ocnPortIdx,
                   condReportType,
                   condDateAndTime,
                   condSeverity,
                   condServiceAffecting,
                   trapSeqNum,
                   condDescription,
                   condObjectType,
                   condCodeType }
    STATUS       current
    DESCRIPTION  "This notification indicates that a previously active OC-N Loss
                  of Signal condition has been cleared."
    ::= { ocnCondNotifications 0 2 }


ocnXcvrMismatchCond NOTIFICATION-TYPE
    OBJECTS      { ocnTypeIdx,
                   ocnShelfIdx,
                   ocnSlotIdx,
                   ocnPortIdx,
                   condReportType,
                   condDateAndTime,
                   condSeverity,
                   condServiceAffecting,
                   trapSeqNum,
                   condDescription,
                   condObjectType,
                   condCodeType }
    STATUS       current
    DESCRIPTION  "There is a mismatch between the SFP or XFP transceiver
                  provisioned for the OC-N facility port and the physical
                  transceiver that is inserted in the port. The SFP or XFP
                  transceiver in the port must match the attributes provisioned
                  for the OC-N facility."
    ::= { ocnCondNotifications 0 3 }


ocnXcvrMismatchClear NOTIFICATION-TYPE
    OBJECTS      { ocnTypeIdx,
                   ocnShelfIdx,
                   ocnSlotIdx,
                   ocnPortIdx,
                   condReportType,
                   condDateAndTime,
                   condSeverity,
                   condServiceAffecting,
                   trapSeqNum,
                   condDescription,
                   condObjectType,
                   condCodeType }
    STATUS       current
    DESCRIPTION  "A previously active OC-N Mismatch condition has cleared."
    ::= { ocnCondNotifications 0 4 }


ocnOpticalPwrReceivedMinCond NOTIFICATION-TYPE
    OBJECTS      { ocnTypeIdx,
                   ocnShelfIdx,
                   ocnSlotIdx,
                   ocnPortIdx,
                   ocnOpticalPwrReceived,
                   ocnOpticalPwrReceivedMinTh,
                   condReportType,
                   condDateAndTime,
                   condSeverity,
                   condServiceAffecting,
                   trapSeqNum,
                   condDescription,
                   condObjectType,
                   condCodeType }
    STATUS       current
    DESCRIPTION  "Indicates that the input power for the OC-N facility has
                  fallen below the minimum threshold."
    ::= { ocnCondNotifications 0 5 }


ocnOpticalPwrReceivedMinClear NOTIFICATION-TYPE
    OBJECTS      { ocnTypeIdx,
                   ocnShelfIdx,
                   ocnSlotIdx,
                   ocnPortIdx,
                   condReportType,
                   condDateAndTime,
                   condSeverity,
                   condServiceAffecting,
                   trapSeqNum,
                   condDescription,
                   condObjectType,
                   condCodeType }
    STATUS       current
    DESCRIPTION  "A previously active OC-N minimum power recieved condition has
                  cleared."
    ::= { ocnCondNotifications 0 6 }


ocnOpticalPwrReceivedMaxCond NOTIFICATION-TYPE
    OBJECTS      { ocnTypeIdx,
                   ocnShelfIdx,
                   ocnSlotIdx,
                   ocnPortIdx,
                   ocnOpticalPwrReceived,
                   ocnOpticalPwrReceivedMaxTh,
                   condReportType,
                   condDateAndTime,
                   condSeverity,
                   condServiceAffecting,
                   trapSeqNum,
                   condDescription,
                   condObjectType,
                   condCodeType }
    STATUS       current
    DESCRIPTION  "Indicates that the input power for the OC-N facility has risen
                  above the maximum threshold."
    ::= { ocnCondNotifications 0 7 }


ocnOpticalPwrReceivedMaxClear NOTIFICATION-TYPE
    OBJECTS      { ocnTypeIdx,
                   ocnShelfIdx,
                   ocnSlotIdx,
                   ocnPortIdx,
                   condReportType,
                   condDateAndTime,
                   condSeverity,
                   condServiceAffecting,
                   trapSeqNum,
                   condDescription,
                   condObjectType,
                   condCodeType }
    STATUS       current
    DESCRIPTION  "A previously active OC-N maximum power recieved condition has
                  cleared."
    ::= { ocnCondNotifications 0 8 }


ocnOpticalPwrTransmittedMinCond NOTIFICATION-TYPE
    OBJECTS      { ocnTypeIdx,
                   ocnShelfIdx,
                   ocnSlotIdx,
                   ocnPortIdx,
                   ocnOpticalPwrTransmitted,
                   ocnOpticalPwrTransmittedMinTh,
                   condReportType,
                   condDateAndTime,
                   condSeverity,
                   condServiceAffecting,
                   trapSeqNum,
                   condDescription,
                   condObjectType,
                   condCodeType }
    STATUS       current
    DESCRIPTION  "Indicates that the output power for the OC-N facility has
                  fallen below the minimum threshold."
    ::= { ocnCondNotifications 0 9 }


ocnOpticalPwrTransmittedMinClear NOTIFICATION-TYPE
    OBJECTS      { ocnTypeIdx,
                   ocnShelfIdx,
                   ocnSlotIdx,
                   ocnPortIdx,
                   condReportType,
                   condDateAndTime,
                   condSeverity,
                   condServiceAffecting,
                   trapSeqNum,
                   condDescription,
                   condObjectType,
                   condCodeType }
    STATUS       current
    DESCRIPTION  "A previously active OC-N minimum power transmitted condition
                  has cleared."
    ::= { ocnCondNotifications 0 10 }


ocnOpticalPwrTransmittedMaxCond NOTIFICATION-TYPE
    OBJECTS      { ocnTypeIdx,
                   ocnShelfIdx,
                   ocnSlotIdx,
                   ocnPortIdx,
                   ocnOpticalPwrTransmitted,
                   ocnOpticalPwrTransmittedMaxTh,
                   condReportType,
                   condDateAndTime,
                   condSeverity,
                   condServiceAffecting,
                   trapSeqNum,
                   condDescription,
                   condObjectType,
                   condCodeType }
    STATUS       current
    DESCRIPTION  "Indicates that the output power for the OC-N facility has
                  risen above the maximum threshold."
    ::= { ocnCondNotifications 0 11 }


ocnOpticalPwrTransmittedMaxClear NOTIFICATION-TYPE
    OBJECTS      { ocnTypeIdx,
                   ocnShelfIdx,
                   ocnSlotIdx,
                   ocnPortIdx,
                   condReportType,
                   condDateAndTime,
                   condSeverity,
                   condServiceAffecting,
                   trapSeqNum,
                   condDescription,
                   condObjectType,
                   condCodeType }
    STATUS       current
    DESCRIPTION  "A previously active OC-N maximum power transmitted condition
                  has cleared."
    ::= { ocnCondNotifications 0 12 }


ocnLossOfFrameCond NOTIFICATION-TYPE
    OBJECTS      { ocnTypeIdx,
                   ocnShelfIdx,
                   ocnSlotIdx,
                   ocnPortIdx,
                   condReportType,
                   condDateAndTime,
                   condSeverity,
                   condServiceAffecting,
                   trapSeqNum,
                   condDescription,
                   condObjectType,
                   condCodeType }
    STATUS       current
    DESCRIPTION  "An OC-N Loss of Frame condition is active on the port."
    ::= { ocnCondNotifications 0 13 }


ocnLossOfFrameClear NOTIFICATION-TYPE
    OBJECTS      { ocnTypeIdx,
                   ocnShelfIdx,
                   ocnSlotIdx,
                   ocnPortIdx,
                   condReportType,
                   condDateAndTime,
                   condSeverity,
                   condServiceAffecting,
                   trapSeqNum,
                   condDescription,
                   condObjectType,
                   condCodeType }
    STATUS       current
    DESCRIPTION  "A previously active OC-N Loss of Frame condition has cleared."
    ::= { ocnCondNotifications 0 14 }


ocnSignalDegradeCond NOTIFICATION-TYPE
    OBJECTS      { ocnTypeIdx,
                   ocnShelfIdx,
                   ocnSlotIdx,
                   ocnPortIdx,
                   ocnBER,
                   ocnBERTh,
                   condReportType,
                   condDateAndTime,
                   condSeverity,
                   condServiceAffecting,
                   trapSeqNum,
                   condDescription,
                   condObjectType,
                   condCodeType }
    STATUS       current
    DESCRIPTION  "A signal degrade condition on the OC-N facility is active.
                  This indicates that the detected bit error rate exceeds the
                  degrade threshold."
    ::= { ocnCondNotifications 0 15 }


ocnSignalDegradeClear NOTIFICATION-TYPE
    OBJECTS      { ocnTypeIdx,
                   ocnShelfIdx,
                   ocnSlotIdx,
                   ocnPortIdx,
                   condReportType,
                   condDateAndTime,
                   condSeverity,
                   condServiceAffecting,
                   trapSeqNum,
                   condDescription,
                   condObjectType,
                   condCodeType }
    STATUS       current
    DESCRIPTION  "A previously active OC-N Signal Degrade condition has
                  cleared."
    ::= { ocnCondNotifications 0 16 }


ocnAlarmIndicationSignalCond NOTIFICATION-TYPE
    OBJECTS      { ocnTypeIdx,
                   ocnShelfIdx,
                   ocnSlotIdx,
                   ocnPortIdx,
                   condReportType,
                   condDateAndTime,
                   condSeverity,
                   condServiceAffecting,
                   trapSeqNum,
                   condDescription,
                   condObjectType,
                   condCodeType }
    STATUS       current
    DESCRIPTION  "An OC-N Line-level Alarm Indication Signal indication is
                  active on facility."
    ::= { ocnCondNotifications 0 17 }


ocnAlarmIndicationSignalClear NOTIFICATION-TYPE
    OBJECTS      { ocnTypeIdx,
                   ocnShelfIdx,
                   ocnSlotIdx,
                   ocnPortIdx,
                   condReportType,
                   condDateAndTime,
                   condSeverity,
                   condServiceAffecting,
                   trapSeqNum,
                   condDescription,
                   condObjectType,
                   condCodeType }
    STATUS       current
    DESCRIPTION  "A previously active OC-N Alarm Indication Signal condition has
                  cleared."
    ::= { ocnCondNotifications 0 18 }


ocnLoopbackCond NOTIFICATION-TYPE
    OBJECTS      { ocnTypeIdx,
                   ocnShelfIdx,
                   ocnSlotIdx,
                   ocnPortIdx,
                   condReportType,
                   condDateAndTime,
                   condSeverity,
                   condServiceAffecting,
                   trapSeqNum,
                   condDescription,
                   condObjectType,
                   condCodeType }
    STATUS       current
    DESCRIPTION  "Indicates that the OC-N facility has been provisioned to enter
                  loopback mode."
    ::= { ocnCondNotifications 0 19 }


ocnLoopbackClear NOTIFICATION-TYPE
    OBJECTS      { ocnTypeIdx,
                   ocnShelfIdx,
                   ocnSlotIdx,
                   ocnPortIdx,
                   condReportType,
                   condDateAndTime,
                   condSeverity,
                   condServiceAffecting,
                   trapSeqNum,
                   condDescription,
                   condObjectType,
                   condCodeType }
    STATUS       current
    DESCRIPTION  "A previously active loopback condition on the OC-N facility
                  has been cleared."
    ::= { ocnCondNotifications 0 20 }


ocnLossOfPrimaryTimingReferenceCond NOTIFICATION-TYPE
    OBJECTS      { ocnTypeIdx,
                   ocnShelfIdx,
                   ocnSlotIdx,
                   ocnPortIdx,
                   condReportType,
                   condDateAndTime,
                   condSeverity,
                   condServiceAffecting,
                   trapSeqNum,
                   condDescription,
                   condObjectType,
                   condCodeType }
    STATUS       current
    DESCRIPTION  "Indicates that the primary timing reference signal for the
                  identified OC-N facility is missing or faulty and cannot be
                  locked on."
    ::= { ocnCondNotifications 0 21 }


ocnLossOfPrimaryTimingReferenceClear NOTIFICATION-TYPE
    OBJECTS      { ocnTypeIdx,
                   ocnShelfIdx,
                   ocnSlotIdx,
                   ocnPortIdx,
                   condReportType,
                   condDateAndTime,
                   condSeverity,
                   condServiceAffecting,
                   trapSeqNum,
                   condDescription,
                   condObjectType,
                   condCodeType }
    STATUS       current
    DESCRIPTION  "A previously active OC-N Loss of Primary Timing Reference
                  condition has cleared."
    ::= { ocnCondNotifications 0 22 }


ocnLossOfSecondaryTimingReferenceCond NOTIFICATION-TYPE
    OBJECTS      { ocnTypeIdx,
                   ocnShelfIdx,
                   ocnSlotIdx,
                   ocnPortIdx,
                   condReportType,
                   condDateAndTime,
                   condSeverity,
                   condServiceAffecting,
                   trapSeqNum,
                   condDescription,
                   condObjectType,
                   condCodeType }
    STATUS       current
    DESCRIPTION  "Indicates that the secondary timing reference signal for the
                  identified OC-N facility is missing or faulty and cannot be
                  locked on."
    ::= { ocnCondNotifications 0 23 }


ocnLossOfSecondaryTimingReferenceClear NOTIFICATION-TYPE
    OBJECTS      { ocnTypeIdx,
                   ocnShelfIdx,
                   ocnSlotIdx,
                   ocnPortIdx,
                   condReportType,
                   condDateAndTime,
                   condSeverity,
                   condServiceAffecting,
                   trapSeqNum,
                   condDescription,
                   condObjectType,
                   condCodeType }
    STATUS       current
    DESCRIPTION  "A previously active OC-N Loss of Secondary Timing Reference
                  condition has cleared."
    ::= { ocnCondNotifications 0 24 }

ocnOTNPayloadMismatchCond NOTIFICATION-TYPE
    OBJECTS      { ocnTypeIdx,
                   ocnShelfIdx,
                   ocnSlotIdx,
                   ocnPortIdx,
                   condReportType,
                   condDateAndTime,
                   condSeverity,
                   condServiceAffecting,
                   trapSeqNum,
                   condDescription,
                   condObjectType,
                   condCodeType }
    STATUS       current
    DESCRIPTION  "An OTN payload mismatch is active on the facility."
    ::= { ocnCondNotifications 0 25 }


ocnOTNPayloadMismatchClear NOTIFICATION-TYPE
    OBJECTS      { ocnTypeIdx,
                   ocnShelfIdx,
                   ocnSlotIdx,
                   ocnPortIdx,
                   condReportType,
                   condDateAndTime,
                   condSeverity,
                   condServiceAffecting,
                   trapSeqNum,
                   condDescription,
                   condObjectType,
                   condCodeType }
    STATUS       current
    DESCRIPTION  "A previously active OTN payload mismatch condition has
                  cleared."
    ::= { ocnCondNotifications 0 26 }
    
ocnForcedSwitchToProtectionCond NOTIFICATION-TYPE
    OBJECTS      { ocnTypeIdx,
                   ocnShelfIdx,
                   ocnSlotIdx,
                   ocnPortIdx,
                   condReportType,
                   condDateAndTime,
                   condSeverity,
                   condServiceAffecting,
                   trapSeqNum,
                   condDescription,
                   condObjectType,
                   condCodeType }
    STATUS       current
    DESCRIPTION  "The active line of a protected line pair has
                  been forced to switch to the Protection line."
    ::= { ocnCondNotifications 0 27 }


ocnForcedSwitchToProtectionClear NOTIFICATION-TYPE
    OBJECTS      { ocnTypeIdx,
                   ocnShelfIdx,
                   ocnSlotIdx,
                   ocnPortIdx,
                   condReportType,
                   condDateAndTime,
                   condSeverity,
                   condServiceAffecting,
                   trapSeqNum,
                   condDescription,
                   condObjectType,
                   condCodeType }
    STATUS       current
    DESCRIPTION  "A previously active Forced Switch To Protection condition has
                  cleared."
    ::= { ocnCondNotifications 0 28 }


ocnForcedSwitchToWorkingCond NOTIFICATION-TYPE
    OBJECTS      { ocnTypeIdx,
                   ocnShelfIdx,
                   ocnSlotIdx,
                   ocnPortIdx,
                   condReportType,
                   condDateAndTime,
                   condSeverity,
                   condServiceAffecting,
                   trapSeqNum,
                   condDescription,
                   condObjectType,
                   condCodeType }
    STATUS       current
    DESCRIPTION  "The active line of a protected line pair has
                  been forced to switch to the Working line."
    ::= { ocnCondNotifications 0 29 }


ocnForcedSwitchToWorkingClear NOTIFICATION-TYPE
    OBJECTS      { ocnTypeIdx,
                   ocnShelfIdx,
                   ocnSlotIdx,
                   ocnPortIdx,
                   condReportType,
                   condDateAndTime,
                   condSeverity,
                   condServiceAffecting,
                   trapSeqNum,
                   condDescription,
                   condObjectType,
                   condCodeType }
    STATUS       current
    DESCRIPTION  "A previously active Forced Switch To Working condition has
                  cleared."
    ::= { ocnCondNotifications 0 30 }


ocnLockoutProtectionCond NOTIFICATION-TYPE
    OBJECTS      { ocnTypeIdx,
                   ocnShelfIdx,
                   ocnSlotIdx,
                   ocnPortIdx,
                   condReportType,
                   condDateAndTime,
                   condSeverity,
                   condServiceAffecting,
                   trapSeqNum,
                   condDescription,
                   condObjectType,
                   condCodeType }
    STATUS       current
    DESCRIPTION  "The Protection line of a protected line pair has
                  been locked out."
    ::= { ocnCondNotifications 0 31 }


ocnLockoutProtectionClear NOTIFICATION-TYPE
    OBJECTS      { ocnTypeIdx,
                   ocnShelfIdx,
                   ocnSlotIdx,
                   ocnPortIdx,
                   condReportType,
                   condDateAndTime,
                   condSeverity,
                   condServiceAffecting,
                   trapSeqNum,
                   condDescription,
                   condObjectType,
                   condCodeType }
    STATUS       current
    DESCRIPTION  "A previously active Lockout Protection condition has cleared."
    ::= { ocnCondNotifications 0 32 }


ocnLockoutWorkingCond NOTIFICATION-TYPE
    OBJECTS      { ocnTypeIdx,
                   ocnShelfIdx,
                   ocnSlotIdx,
                   ocnPortIdx,
                   condReportType,
                   condDateAndTime,
                   condSeverity,
                   condServiceAffecting,
                   trapSeqNum,
                   condDescription,
                   condObjectType,
                   condCodeType }
    STATUS       current
    DESCRIPTION  "The Working line of a protected line pair has
                  been locked out."
    ::= { ocnCondNotifications 0 33 }


ocnLockoutWorkingClear NOTIFICATION-TYPE
    OBJECTS      { ocnTypeIdx,
                   ocnShelfIdx,
                   ocnSlotIdx,
                   ocnPortIdx,
                   condReportType,
                   condDateAndTime,
                   condSeverity,
                   condServiceAffecting,
                   trapSeqNum,
                   condDescription,
                   condObjectType,
                   condCodeType }
    STATUS       current
    DESCRIPTION  "A previously active Lockout Working condition has cleared."
    ::= { ocnCondNotifications 0 34 }

ocnWavelengthNotAchievableCond NOTIFICATION-TYPE
    OBJECTS      { ocnTypeIdx,
                   ocnShelfIdx,
                   ocnSlotIdx,
                   ocnPortIdx,
                   condReportType,
                   condDateAndTime,
                   condSeverity,
                   condServiceAffecting,
                   trapSeqNum,
                   condDescription,
                   condObjectType,
                   condCodeType }
    STATUS       current
    DESCRIPTION  "The tunable pluggable cannot be tuned to the provisioned wavelength."
    ::= { ocnCondNotifications 0 35 }

ocnWavelengthNotAchievableClear NOTIFICATION-TYPE
    OBJECTS      { ocnTypeIdx,
                   ocnShelfIdx,
                   ocnSlotIdx,
                   ocnPortIdx,
                   condReportType,
                   condDateAndTime,
                   condSeverity,
                   condServiceAffecting,
                   trapSeqNum,
                   condDescription,
                   condObjectType,
                   condCodeType }
    STATUS       current
    DESCRIPTION  "A previously active Wavelength Not Achievable condition has
                  cleared."
    ::= { ocnCondNotifications 0 36 }


stsnAlarmIndicationSignalCond NOTIFICATION-TYPE
    OBJECTS      { stsnTypeIdx,
                   stsnShelfIdx,
                   stsnSlotIdx,
                   stsnPortIdx,
                   stsnIdx,
                   condReportType,
                   condDateAndTime,
                   condSeverity,
                   condServiceAffecting,
                   trapSeqNum,
                   condDescription,
                   condObjectType,
                   condCodeType }
    STATUS       current
    DESCRIPTION  "A Path-level Alarm Indication Signal indication is active on
                  the STS-N channel."
    ::= { stsnCondNotifications 0 1 }


stsnAlarmIndicationSignalClear NOTIFICATION-TYPE
    OBJECTS      { stsnTypeIdx,
                   stsnShelfIdx,
                   stsnSlotIdx,
                   stsnPortIdx,
                   stsnIdx,
                   condReportType,
                   condDateAndTime,
                   condSeverity,
                   condServiceAffecting,
                   trapSeqNum,
                   condDescription,
                   condObjectType,
                   condCodeType }
    STATUS       current
    DESCRIPTION  "A previously active STS-N Alarm Indication Signal condition
                  has cleared."
    ::= { stsnCondNotifications 0 2 }


stsnLossOfPointerCond NOTIFICATION-TYPE
    OBJECTS      { stsnTypeIdx,
                   stsnShelfIdx,
                   stsnSlotIdx,
                   stsnPortIdx,
                   stsnIdx,
                   condReportType,
                   condDateAndTime,
                   condSeverity,
                   condServiceAffecting,
                   trapSeqNum,
                   condDescription,
                   condObjectType,
                   condCodeType }
    STATUS       current
    DESCRIPTION  "A Loss of Pointer condition is active on the STS-N channel."
    ::= { stsnCondNotifications 0 3 }


stsnLossOfPointerClear NOTIFICATION-TYPE
    OBJECTS      { stsnTypeIdx,
                   stsnShelfIdx,
                   stsnSlotIdx,
                   stsnPortIdx,
                   stsnIdx,
                   condReportType,
                   condDateAndTime,
                   condSeverity,
                   condServiceAffecting,
                   trapSeqNum,
                   condDescription,
                   condObjectType,
                   condCodeType }
    STATUS       current
    DESCRIPTION  "A previously raised STS-N Loss of Pointer condition has
                  cleared."
    ::= { stsnCondNotifications 0 4 }


stsnUnequippedCond NOTIFICATION-TYPE
    OBJECTS      { stsnTypeIdx,
                   stsnShelfIdx,
                   stsnSlotIdx,
                   stsnPortIdx,
                   stsnIdx,
                   condReportType,
                   condDateAndTime,
                   condSeverity,
                   condServiceAffecting,
                   trapSeqNum,
                   condDescription,
                   condObjectType,
                   condCodeType }
    STATUS       current
    DESCRIPTION  "An Unequipped indication has been detected for the STS-N
                  channel."
    ::= { stsnCondNotifications 0 5 }


stsnUnequippedClear NOTIFICATION-TYPE
    OBJECTS      { stsnTypeIdx,
                   stsnShelfIdx,
                   stsnSlotIdx,
                   stsnPortIdx,
                   stsnIdx,
                   condReportType,
                   condDateAndTime,
                   condSeverity,
                   condServiceAffecting,
                   trapSeqNum,
                   condDescription,
                   condObjectType,
                   condCodeType }
    STATUS       current
    DESCRIPTION  "A previously raised STS-N Unequipped condition has cleared."
    ::= { stsnCondNotifications 0 6 }


stsnSignalDegradeCond NOTIFICATION-TYPE
    OBJECTS      { stsnTypeIdx,
                   stsnShelfIdx,
                   stsnSlotIdx,
                   stsnPortIdx,
                   stsnIdx,
                   stsnBER,
                   stsnBERTh,
                   condReportType,
                   condDateAndTime,
                   condSeverity,
                   condServiceAffecting,
                   trapSeqNum,
                   condDescription,
                   condObjectType,
                   condCodeType }
    STATUS       current
    DESCRIPTION  "A signal degrade condition on the STS-N channel is active.
                  This indicates that the detected bit error rate exceeds the
                  degrade threshold."
    ::= { stsnCondNotifications 0 7 }


stsnSignalDegradeClear NOTIFICATION-TYPE
    OBJECTS      { stsnTypeIdx,
                   stsnShelfIdx,
                   stsnSlotIdx,
                   stsnPortIdx,
                   stsnIdx,
                   condReportType,
                   condDateAndTime,
                   condSeverity,
                   condServiceAffecting,
                   trapSeqNum,
                   condDescription,
                   condObjectType,
                   condCodeType }
    STATUS       current
    DESCRIPTION  "A previously raised STS-N signal degrade condition has
                  cleared."
    ::= { stsnCondNotifications 0 8 }


stsnForcedSwitchToProtectionCond NOTIFICATION-TYPE
    OBJECTS      { stsnTypeIdx,
                   stsnShelfIdx,
                   stsnSlotIdx,
                   stsnPortIdx,
                   stsnIdx,
                   condReportType,
                   condDateAndTime,
                   condSeverity,
                   condServiceAffecting,
                   trapSeqNum,
                   condDescription,
                   condObjectType,
                   condCodeType }
    STATUS       current
    DESCRIPTION  "The active STS-N channel of a protected STS-N channel pair has
                  been forced to switch to the Protection transceiver."
    ::= { stsnCondNotifications 0 9 }


stsnForcedSwitchToProtectionClear NOTIFICATION-TYPE
    OBJECTS      { stsnTypeIdx,
                   stsnShelfIdx,
                   stsnSlotIdx,
                   stsnPortIdx,
                   stsnIdx,
                   condReportType,
                   condDateAndTime,
                   condSeverity,
                   condServiceAffecting,
                   trapSeqNum,
                   condDescription,
                   condObjectType,
                   condCodeType }
    STATUS       current
    DESCRIPTION  "A previously raised STS-N Forced Switch To Protection
                  condition has cleared."
    ::= { stsnCondNotifications 0 10 }


stsnForcedSwitchToWorkingCond NOTIFICATION-TYPE
    OBJECTS      { stsnTypeIdx,
                   stsnShelfIdx,
                   stsnSlotIdx,
                   stsnPortIdx,
                   stsnIdx,
                   condReportType,
                   condDateAndTime,
                   condSeverity,
                   condServiceAffecting,
                   trapSeqNum,
                   condDescription,
                   condObjectType,
                   condCodeType }
    STATUS       current
    DESCRIPTION  "The active STS-N channel of a protected STS-N channel pair has
                  been forced to switch to the Working transceiver."
    ::= { stsnCondNotifications 0 11 }


stsnForcedSwitchToWorkingClear NOTIFICATION-TYPE
    OBJECTS      { stsnTypeIdx,
                   stsnShelfIdx,
                   stsnSlotIdx,
                   stsnPortIdx,
                   stsnIdx,
                   condReportType,
                   condDateAndTime,
                   condSeverity,
                   condServiceAffecting,
                   trapSeqNum,
                   condDescription,
                   condObjectType,
                   condCodeType }
    STATUS       current
    DESCRIPTION  "A previously raised STS-N Forced Switch To Working condition
                  has cleared."
    ::= { stsnCondNotifications 0 12 }


stsnLockoutProtectionCond NOTIFICATION-TYPE
    OBJECTS      { stsnTypeIdx,
                   stsnShelfIdx,
                   stsnSlotIdx,
                   stsnPortIdx,
                   stsnIdx,
                   condReportType,
                   condDateAndTime,
                   condSeverity,
                   condServiceAffecting,
                   trapSeqNum,
                   condDescription,
                   condObjectType,
                   condCodeType }
    STATUS       current
    DESCRIPTION  "The Protection STS-N channel of a protected STS-N channel pair
                  has been locked out."
    ::= { stsnCondNotifications 0 13 }


stsnLockoutProtectionClear NOTIFICATION-TYPE
    OBJECTS      { stsnTypeIdx,
                   stsnShelfIdx,
                   stsnSlotIdx,
                   stsnPortIdx,
                   stsnIdx,
                   condReportType,
                   condDateAndTime,
                   condSeverity,
                   condServiceAffecting,
                   trapSeqNum,
                   condDescription,
                   condObjectType,
                   condCodeType }
    STATUS       current
    DESCRIPTION  "A previously raised STS-N Lockout Protection condition has
                  cleared."
    ::= { stsnCondNotifications 0 14 }


stsnLockoutWorkingCond NOTIFICATION-TYPE
    OBJECTS      { stsnTypeIdx,
                   stsnShelfIdx,
                   stsnSlotIdx,
                   stsnPortIdx,
                   stsnIdx,
                   condReportType,
                   condDateAndTime,
                   condSeverity,
                   condServiceAffecting,
                   trapSeqNum,
                   condDescription,
                   condObjectType,
                   condCodeType }
    STATUS       current
    DESCRIPTION  "The Working STS-N channel of a protected STS-N channel pair
                  has been locked out."
    ::= { stsnCondNotifications 0 15 }


stsnLockoutWorkingClear NOTIFICATION-TYPE
    OBJECTS      { stsnTypeIdx,
                   stsnShelfIdx,
                   stsnSlotIdx,
                   stsnPortIdx,
                   stsnIdx,
                   condReportType,
                   condDateAndTime,
                   condSeverity,
                   condServiceAffecting,
                   trapSeqNum,
                   condDescription,
                   condObjectType,
                   condCodeType }
    STATUS       current
    DESCRIPTION  "A previously raised STS-N Lockout Working condition has
                  cleared."
    ::= { stsnCondNotifications 0 16 }

stsnConcatMismatchCond NOTIFICATION-TYPE
    OBJECTS      { stsnTypeIdx,
                   stsnShelfIdx,
                   stsnSlotIdx,
                   stsnPortIdx,
                   stsnIdx,
                   condReportType,
                   condDateAndTime,
                   condSeverity,
                   condServiceAffecting,
                   trapSeqNum,
                   condDescription,
                   condObjectType,
                   condCodeType }
    STATUS       current
    DESCRIPTION  "A connection provisioning does not match has been detected for
                  the STS-N channel."
    ::= { stsnCondNotifications 0 17 }


stsnConcatMismatchClear NOTIFICATION-TYPE
    OBJECTS      { stsnTypeIdx,
                   stsnShelfIdx,
                   stsnSlotIdx,
                   stsnPortIdx,
                   stsnIdx,
                   condReportType,
                   condDateAndTime,
                   condSeverity,
                   condServiceAffecting,
                   trapSeqNum,
                   condDescription,
                   condObjectType,
                   condCodeType }
    STATUS       current
    DESCRIPTION  "A previously raised STS-N Concat Mismatch condition has
                  cleared."
    ::= { stsnCondNotifications 0 18 }



stmnLossOfSignalCond NOTIFICATION-TYPE
    OBJECTS      { stmnTypeIdx,
                   stmnShelfIdx,
                   stmnSlotIdx,
                   stmnPortIdx,
                   condReportType,
                   condDateAndTime,
                   condSeverity,
                   condServiceAffecting,
                   trapSeqNum,
                   condDescription,
                   condObjectType,
                   condCodeType }
    STATUS       current
    DESCRIPTION  "This notification indicates that there is no input signal
                  detected on the STM-N port."
    ::= { stmnCondNotifications 0 1 }


stmnLossOfSignalClear NOTIFICATION-TYPE
    OBJECTS      { stmnTypeIdx,
                   stmnShelfIdx,
                   stmnSlotIdx,
                   stmnPortIdx,
                   condReportType,
                   condDateAndTime,
                   condSeverity,
                   condServiceAffecting,
                   trapSeqNum,
                   condDescription,
                   condObjectType,
                   condCodeType }
    STATUS       current
    DESCRIPTION  "This notification indicates that a previously active STM-N
                  Loss of Signal condition has been cleared."
    ::= { stmnCondNotifications 0 2 }


stmnXcvrMismatchCond NOTIFICATION-TYPE
    OBJECTS      { stmnTypeIdx,
                   stmnShelfIdx,
                   stmnSlotIdx,
                   stmnPortIdx,
                   condReportType,
                   condDateAndTime,
                   condSeverity,
                   condServiceAffecting,
                   trapSeqNum,
                   condDescription,
                   condObjectType,
                   condCodeType }
    STATUS       current
    DESCRIPTION  "There is a mismatch between the SFP or XFP transceiver
                  provisioned for the STM-N facility port and the physical
                  transceiver that is inserted in the port. The SFP or XFP
                  transceiver in the port must match the attributes provisioned
                  for the STM-N facility."
    ::= { stmnCondNotifications 0 3 }


stmnXcvrMismatchClear NOTIFICATION-TYPE
    OBJECTS      { stmnTypeIdx,
                   stmnShelfIdx,
                   stmnSlotIdx,
                   stmnPortIdx,
                   condReportType,
                   condDateAndTime,
                   condSeverity,
                   condServiceAffecting,
                   trapSeqNum,
                   condDescription,
                   condObjectType,
                   condCodeType }
    STATUS       current
    DESCRIPTION  "A previously active STM-N Mismatch condition has cleared."
    ::= { stmnCondNotifications 0 4 }


stmnOpticalPwrReceivedMinCond NOTIFICATION-TYPE
    OBJECTS      { stmnTypeIdx,
                   stmnShelfIdx,
                   stmnSlotIdx,
                   stmnPortIdx,
                   stmnOpticalPwrReceived,
                   stmnOpticalPwrReceivedMinTh,
                   condReportType,
                   condDateAndTime,
                   condSeverity,
                   condServiceAffecting,
                   trapSeqNum,
                   condDescription,
                   condObjectType,
                   condCodeType }
    STATUS       current
    DESCRIPTION  "Indicates that the input power for the STM-N facility has
                  fallen below the minimum threshold."
    ::= { stmnCondNotifications 0 5 }


stmnOpticalPwrReceivedMinClear NOTIFICATION-TYPE
    OBJECTS      { stmnTypeIdx,
                   stmnShelfIdx,
                   stmnSlotIdx,
                   stmnPortIdx,
                   condReportType,
                   condDateAndTime,
                   condSeverity,
                   condServiceAffecting,
                   trapSeqNum,
                   condDescription,
                   condObjectType,
                   condCodeType }
    STATUS       current
    DESCRIPTION  "A previously active STM-N minimum power recieved condition has
                  cleared."
    ::= { stmnCondNotifications 0 6 }


stmnOpticalPwrReceivedMaxCond NOTIFICATION-TYPE
    OBJECTS      { stmnTypeIdx,
                   stmnShelfIdx,
                   stmnSlotIdx,
                   stmnPortIdx,
                   stmnOpticalPwrReceived,
                   stmnOpticalPwrReceivedMaxTh,
                   condReportType,
                   condDateAndTime,
                   condSeverity,
                   condServiceAffecting,
                   trapSeqNum,
                   condDescription,
                   condObjectType,
                   condCodeType }
    STATUS       current
    DESCRIPTION  "Indicates that the input power for the STM-N facility has
                  risen above the maximum threshold."
    ::= { stmnCondNotifications 0 7 }


stmnOpticalPwrReceivedMaxClear NOTIFICATION-TYPE
    OBJECTS      { stmnTypeIdx,
                   stmnShelfIdx,
                   stmnSlotIdx,
                   stmnPortIdx,
                   condReportType,
                   condDateAndTime,
                   condSeverity,
                   condServiceAffecting,
                   trapSeqNum,
                   condDescription,
                   condObjectType,
                   condCodeType }
    STATUS       current
    DESCRIPTION  "A previously active STM-N maximum power recieved condition has
                  cleared."
    ::= { stmnCondNotifications 0 8 }


stmnOpticalPwrTransmittedMinCond NOTIFICATION-TYPE
    OBJECTS      { stmnTypeIdx,
                   stmnShelfIdx,
                   stmnSlotIdx,
                   stmnPortIdx,
                   stmnOpticalPwrTransmitted,
                   stmnOpticalPwrTransmittedMinTh,
                   condReportType,
                   condDateAndTime,
                   condSeverity,
                   condServiceAffecting,
                   trapSeqNum,
                   condDescription,
                   condObjectType,
                   condCodeType }
    STATUS       current
    DESCRIPTION  "Indicates that the output power for the STM-N facility has
                  fallen below the minimum threshold."
    ::= { stmnCondNotifications 0 9 }


stmnOpticalPwrTransmittedMinClear NOTIFICATION-TYPE
    OBJECTS      { stmnTypeIdx,
                   stmnShelfIdx,
                   stmnSlotIdx,
                   stmnPortIdx,
                   condReportType,
                   condDateAndTime,
                   condSeverity,
                   condServiceAffecting,
                   trapSeqNum,
                   condDescription,
                   condObjectType,
                   condCodeType }
    STATUS       current
    DESCRIPTION  "A previously active STM-N minimum power transmitted condition
                  has cleared."
    ::= { stmnCondNotifications 0 10 }


stmnOpticalPwrTransmittedMaxCond NOTIFICATION-TYPE
    OBJECTS      { stmnTypeIdx,
                   stmnShelfIdx,
                   stmnSlotIdx,
                   stmnPortIdx,
                   stmnOpticalPwrTransmitted,
                   stmnOpticalPwrTransmittedMaxTh,
                   condReportType,
                   condDateAndTime,
                   condSeverity,
                   condServiceAffecting,
                   trapSeqNum,
                   condDescription,
                   condObjectType,
                   condCodeType }
    STATUS       current
    DESCRIPTION  "Indicates that the output power for the STM-N facility has
                  risen above the maximum threshold."
    ::= { stmnCondNotifications 0 11 }


stmnOpticalPwrTransmittedMaxClear NOTIFICATION-TYPE
    OBJECTS      { stmnTypeIdx,
                   stmnShelfIdx,
                   stmnSlotIdx,
                   stmnPortIdx,
                   condReportType,
                   condDateAndTime,
                   condSeverity,
                   condServiceAffecting,
                   trapSeqNum,
                   condDescription,
                   condObjectType,
                   condCodeType }
    STATUS       current
    DESCRIPTION  "A previously active STM-N maximum power transmitted condition
                  has cleared."
    ::= { stmnCondNotifications 0 12 }


stmnLossOfFrameCond NOTIFICATION-TYPE
    OBJECTS      { stmnTypeIdx,
                   stmnShelfIdx,
                   stmnSlotIdx,
                   stmnPortIdx,
                   condReportType,
                   condDateAndTime,
                   condSeverity,
                   condServiceAffecting,
                   trapSeqNum,
                   condDescription,
                   condObjectType,
                   condCodeType }
    STATUS       current
    DESCRIPTION  "An STM-N Loss of Frame condition is active on the port."
    ::= { stmnCondNotifications 0 13 }


stmnLossOfFrameClear NOTIFICATION-TYPE
    OBJECTS      { stmnTypeIdx,
                   stmnShelfIdx,
                   stmnSlotIdx,
                   stmnPortIdx,
                   condReportType,
                   condDateAndTime,
                   condSeverity,
                   condServiceAffecting,
                   trapSeqNum,
                   condDescription,
                   condObjectType,
                   condCodeType }
    STATUS       current
    DESCRIPTION  "A previously active STM-N Loss of Frame condition has
                  cleared."
    ::= { stmnCondNotifications 0 14 }


stmnSignalDegradeCond NOTIFICATION-TYPE
    OBJECTS      { stmnTypeIdx,
                   stmnShelfIdx,
                   stmnSlotIdx,
                   stmnPortIdx,
                   stmnBER,
                   stmnBERTh,
                   condReportType,
                   condDateAndTime,
                   condSeverity,
                   condServiceAffecting,
                   trapSeqNum,
                   condDescription,
                   condObjectType,
                   condCodeType }
    STATUS       current
    DESCRIPTION  "A signal degrade condition on the STM-N facility is active.
                  This indicates that the detected bit error rate exceeds the
                  degrade threshold."
    ::= { stmnCondNotifications 0 15 }


stmnSignalDegradeClear NOTIFICATION-TYPE
    OBJECTS      { stmnTypeIdx,
                   stmnShelfIdx,
                   stmnSlotIdx,
                   stmnPortIdx,
                   condReportType,
                   condDateAndTime,
                   condSeverity,
                   condServiceAffecting,
                   trapSeqNum,
                   condDescription,
                   condObjectType,
                   condCodeType }
    STATUS       current
    DESCRIPTION  "A previously active STM-N Signal Degrade condition has
                  cleared."
    ::= { stmnCondNotifications 0 16 }


stmnAlarmIndicationSignalCond NOTIFICATION-TYPE
    OBJECTS      { stmnTypeIdx,
                   stmnShelfIdx,
                   stmnSlotIdx,
                   stmnPortIdx,
                   condReportType,
                   condDateAndTime,
                   condSeverity,
                   condServiceAffecting,
                   trapSeqNum,
                   condDescription,
                   condObjectType,
                   condCodeType }
    STATUS       current
    DESCRIPTION  "An STM-N Line-level Alarm Indication Signal indication is
                  active on facility."
    ::= { stmnCondNotifications 0 17 }


stmnAlarmIndicationSignalClear NOTIFICATION-TYPE
    OBJECTS      { stmnTypeIdx,
                   stmnShelfIdx,
                   stmnSlotIdx,
                   stmnPortIdx,
                   condReportType,
                   condDateAndTime,
                   condSeverity,
                   condServiceAffecting,
                   trapSeqNum,
                   condDescription,
                   condObjectType,
                   condCodeType }
    STATUS       current
    DESCRIPTION  "A previously active STM-N Alarm Indication Signal condition
                  has cleared."
    ::= { stmnCondNotifications 0 18 }


stmnLoopbackCond NOTIFICATION-TYPE
    OBJECTS      { stmnTypeIdx,
                   stmnShelfIdx,
                   stmnSlotIdx,
                   stmnPortIdx,
                   condReportType,
                   condDateAndTime,
                   condSeverity,
                   condServiceAffecting,
                   trapSeqNum,
                   condDescription,
                   condObjectType,
                   condCodeType }
    STATUS       current
    DESCRIPTION  "Indicates that the STM-N facility has been provisioned to
                  enter loopback mode."
    ::= { stmnCondNotifications 0 19 }


stmnLoopbackClear NOTIFICATION-TYPE
    OBJECTS      { stmnTypeIdx,
                   stmnShelfIdx,
                   stmnSlotIdx,
                   stmnPortIdx,
                   condReportType,
                   condDateAndTime,
                   condSeverity,
                   condServiceAffecting,
                   trapSeqNum,
                   condDescription,
                   condObjectType,
                   condCodeType }
    STATUS       current
    DESCRIPTION  "A previously active loopback condition on the STM-N facility
                  has been cleared."
    ::= { stmnCondNotifications 0 20 }


stmnLossOfPrimaryTimingReferenceCond NOTIFICATION-TYPE
    OBJECTS      { stmnTypeIdx,
                   stmnShelfIdx,
                   stmnSlotIdx,
                   stmnPortIdx,
                   condReportType,
                   condDateAndTime,
                   condSeverity,
                   condServiceAffecting,
                   trapSeqNum,
                   condDescription,
                   condObjectType,
                   condCodeType }
    STATUS       current
    DESCRIPTION  "Indicates that the primary timing reference signal for the
                  identified STM-N facility is missing or faulty and cannot be
                  locked on."
    ::= { stmnCondNotifications 0 21 }


stmnLossOfPrimaryTimingReferenceClear NOTIFICATION-TYPE
    OBJECTS      { stmnTypeIdx,
                   stmnShelfIdx,
                   stmnSlotIdx,
                   stmnPortIdx,
                   condReportType,
                   condDateAndTime,
                   condSeverity,
                   condServiceAffecting,
                   trapSeqNum,
                   condDescription,
                   condObjectType,
                   condCodeType }
    STATUS       current
    DESCRIPTION  "A previously active STM-N Loss of Primary Timing Reference
                  condition has cleared."
    ::= { stmnCondNotifications 0 22 }


stmnLossOfSecondaryTimingReferenceCond NOTIFICATION-TYPE
    OBJECTS      { stmnTypeIdx,
                   stmnShelfIdx,
                   stmnSlotIdx,
                   stmnPortIdx,
                   condReportType,
                   condDateAndTime,
                   condSeverity,
                   condServiceAffecting,
                   trapSeqNum,
                   condDescription,
                   condObjectType,
                   condCodeType }
    STATUS       current
    DESCRIPTION  "Indicates that the secondary timing reference signal for the
                  identified STM-N facility is missing or faulty and cannot be
                  locked on."
    ::= { stmnCondNotifications 0 23 }


stmnLossOfSecondaryTimingReferenceClear NOTIFICATION-TYPE
    OBJECTS      { stmnTypeIdx,
                   stmnShelfIdx,
                   stmnSlotIdx,
                   stmnPortIdx,
                   condReportType,
                   condDateAndTime,
                   condSeverity,
                   condServiceAffecting,
                   trapSeqNum,
                   condDescription,
                   condObjectType,
                   condCodeType }
    STATUS       current
    DESCRIPTION  "A previously active STM-N Loss of Secondary Timing Reference
                  condition has cleared."
    ::= { stmnCondNotifications 0 24 }

stmnOTNPayloadMismatchCond NOTIFICATION-TYPE
    OBJECTS      { stmnTypeIdx,
                   stmnShelfIdx,
                   stmnSlotIdx,
                   stmnPortIdx,
                   condReportType,
                   condDateAndTime,
                   condSeverity,
                   condServiceAffecting,
                   trapSeqNum,
                   condDescription,
                   condObjectType,
                   condCodeType }
    STATUS       current
    DESCRIPTION  "An OTN payload mismatch is active on the facility."
    ::= { stmnCondNotifications 0 25 }


stmnOTNPayloadMismatchClear NOTIFICATION-TYPE
    OBJECTS      { stmnTypeIdx,
                   stmnShelfIdx,
                   stmnSlotIdx,
                   stmnPortIdx,
                   condReportType,
                   condDateAndTime,
                   condSeverity,
                   condServiceAffecting,
                   trapSeqNum,
                   condDescription,
                   condObjectType,
                   condCodeType }
    STATUS       current
    DESCRIPTION  "A previously active OTN payload mismatch condition has
                  cleared."
    ::= { stmnCondNotifications 0 26 }
    
stmnForcedSwitchToProtectionCond NOTIFICATION-TYPE
    OBJECTS      { stmnTypeIdx,
                   stmnShelfIdx,
                   stmnSlotIdx,
                   stmnPortIdx,
                   condReportType,
                   condDateAndTime,
                   condSeverity,
                   condServiceAffecting,
                   trapSeqNum,
                   condDescription,
                   condObjectType,
                   condCodeType }
    STATUS       current
    DESCRIPTION  "The active line of a protected line pair has
                  been forced to switch to the Protection line."
    ::= { stmnCondNotifications 0 27 }


stmnForcedSwitchToProtectionClear NOTIFICATION-TYPE
    OBJECTS      { stmnTypeIdx,
                   stmnShelfIdx,
                   stmnSlotIdx,
                   stmnPortIdx,
                   condReportType,
                   condDateAndTime,
                   condSeverity,
                   condServiceAffecting,
                   trapSeqNum,
                   condDescription,
                   condObjectType,
                   condCodeType }
    STATUS       current
    DESCRIPTION  "A previously active Forced Switch To Protection condition has
                  cleared."
    ::= { stmnCondNotifications 0 28 }


stmnForcedSwitchToWorkingCond NOTIFICATION-TYPE
    OBJECTS      { stmnTypeIdx,
                   stmnShelfIdx,
                   stmnSlotIdx,
                   stmnPortIdx,
                   condReportType,
                   condDateAndTime,
                   condSeverity,
                   condServiceAffecting,
                   trapSeqNum,
                   condDescription,
                   condObjectType,
                   condCodeType }
    STATUS       current
    DESCRIPTION  "The active line of a protected line pair has
                  been forced to switch to the Working line."
    ::= { stmnCondNotifications 0 29 }


stmnForcedSwitchToWorkingClear NOTIFICATION-TYPE
    OBJECTS      { stmnTypeIdx,
                   stmnShelfIdx,
                   stmnSlotIdx,
                   stmnPortIdx,
                   condReportType,
                   condDateAndTime,
                   condSeverity,
                   condServiceAffecting,
                   trapSeqNum,
                   condDescription,
                   condObjectType,
                   condCodeType }
    STATUS       current
    DESCRIPTION  "A previously active Forced Switch To Working condition has
                  cleared."
    ::= { stmnCondNotifications 0 30 }


stmnLockoutProtectionCond NOTIFICATION-TYPE
    OBJECTS      { stmnTypeIdx,
                   stmnShelfIdx,
                   stmnSlotIdx,
                   stmnPortIdx,
                   condReportType,
                   condDateAndTime,
                   condSeverity,
                   condServiceAffecting,
                   trapSeqNum,
                   condDescription,
                   condObjectType,
                   condCodeType }
    STATUS       current
    DESCRIPTION  "The Protection line of a protected line pair has
                  been locked out."
    ::= { stmnCondNotifications 0 31 }


stmnLockoutProtectionClear NOTIFICATION-TYPE
    OBJECTS      { stmnTypeIdx,
                   stmnShelfIdx,
                   stmnSlotIdx,
                   stmnPortIdx,
                   condReportType,
                   condDateAndTime,
                   condSeverity,
                   condServiceAffecting,
                   trapSeqNum,
                   condDescription,
                   condObjectType,
                   condCodeType }
    STATUS       current
    DESCRIPTION  "A previously active Lockout Protection condition has cleared."
    ::= { stmnCondNotifications 0 32 }


stmnLockoutWorkingCond NOTIFICATION-TYPE
    OBJECTS      { stmnTypeIdx,
                   stmnShelfIdx,
                   stmnSlotIdx,
                   stmnPortIdx,
                   condReportType,
                   condDateAndTime,
                   condSeverity,
                   condServiceAffecting,
                   trapSeqNum,
                   condDescription,
                   condObjectType,
                   condCodeType }
    STATUS       current
    DESCRIPTION  "The Working line of a protected line pair has
                  been locked out."
    ::= { stmnCondNotifications 0 33 }


stmnLockoutWorkingClear NOTIFICATION-TYPE
    OBJECTS      { stmnTypeIdx,
                   stmnShelfIdx,
                   stmnSlotIdx,
                   stmnPortIdx,
                   condReportType,
                   condDateAndTime,
                   condSeverity,
                   condServiceAffecting,
                   trapSeqNum,
                   condDescription,
                   condObjectType,
                   condCodeType }
    STATUS       current
    DESCRIPTION  "A previously active Lockout Working condition has cleared."
    ::= { stmnCondNotifications 0 34 }


stmnWavelengthNotAchievableCond NOTIFICATION-TYPE
    OBJECTS      { stmnTypeIdx,
                   stmnShelfIdx,
                   stmnSlotIdx,
                   stmnPortIdx,
                   condReportType,
                   condDateAndTime,
                   condSeverity,
                   condServiceAffecting,
                   trapSeqNum,
                   condDescription,
                   condObjectType,
                   condCodeType }
    STATUS       current
    DESCRIPTION  "A previously active Wavelength Not Achievable condition has cleared."
    ::= { stmnCondNotifications 0 35 }


stmnWavelengthNotAchievableClear NOTIFICATION-TYPE
    OBJECTS      { stmnTypeIdx,
                   stmnShelfIdx,
                   stmnSlotIdx,
                   stmnPortIdx,
                   condReportType,
                   condDateAndTime,
                   condSeverity,
                   condServiceAffecting,
                   trapSeqNum,
                   condDescription,
                   condObjectType,
                   condCodeType }
    STATUS       current
    DESCRIPTION  "A previously active Lockout Working condition has cleared."
    ::= { stmnCondNotifications 0 36 }

    
vcnAlarmIndicationSignalCond NOTIFICATION-TYPE
    OBJECTS      { vcnTypeIdx,
                   vcnShelfIdx,
                   vcnSlotIdx,
                   vcnPortIdx,
                   vcnIdx,
                   condReportType,
                   condDateAndTime,
                   condSeverity,
                   condServiceAffecting,
                   trapSeqNum,
                   condDescription,
                   condObjectType,
                   condCodeType }
    STATUS       current
    DESCRIPTION  "A Path-level Alarm Indication Signal indication is active on
                  the VC-N channel."
    ::= { vcnCondNotifications 0 1 }


vcnAlarmIndicationSignalClear NOTIFICATION-TYPE
    OBJECTS      { vcnTypeIdx,
                   vcnShelfIdx,
                   vcnSlotIdx,
                   vcnPortIdx,
                   vcnIdx,
                   condReportType,
                   condDateAndTime,
                   condSeverity,
                   condServiceAffecting,
                   trapSeqNum,
                   condDescription,
                   condObjectType,
                   condCodeType }
    STATUS       current
    DESCRIPTION  "A previously active VC-N Alarm Indication Signal condition has
                  cleared."
    ::= { vcnCondNotifications 0 2 }


vcnLossOfPointerCond NOTIFICATION-TYPE
    OBJECTS      { vcnTypeIdx,
                   vcnShelfIdx,
                   vcnSlotIdx,
                   vcnPortIdx,
                   vcnIdx,
                   condReportType,
                   condDateAndTime,
                   condSeverity,
                   condServiceAffecting,
                   trapSeqNum,
                   condDescription,
                   condObjectType,
                   condCodeType }
    STATUS       current
    DESCRIPTION  "A Loss of Pointer condition is active on the VC-N channel."
    ::= { vcnCondNotifications 0 3 }


vcnLossOfPointerClear NOTIFICATION-TYPE
    OBJECTS      { vcnTypeIdx,
                   vcnShelfIdx,
                   vcnSlotIdx,
                   vcnPortIdx,
                   vcnIdx,
                   condReportType,
                   condDateAndTime,
                   condSeverity,
                   condServiceAffecting,
                   trapSeqNum,
                   condDescription,
                   condObjectType,
                   condCodeType }
    STATUS       current
    DESCRIPTION  "A previously raised VC-N Loss of Pointer condition has
                  cleared."
    ::= { vcnCondNotifications 0 4 }


vcnUnequippedCond NOTIFICATION-TYPE
    OBJECTS      { vcnTypeIdx,
                   vcnShelfIdx,
                   vcnSlotIdx,
                   vcnPortIdx,
                   vcnIdx,
                   condReportType,
                   condDateAndTime,
                   condSeverity,
                   condServiceAffecting,
                   trapSeqNum,
                   condDescription,
                   condObjectType,
                   condCodeType }
    STATUS       current
    DESCRIPTION  "An Unequipped indication has been detected for the VC-N
                  channel."
    ::= { vcnCondNotifications 0 5 }


vcnUnequippedClear NOTIFICATION-TYPE
    OBJECTS      { vcnTypeIdx,
                   vcnShelfIdx,
                   vcnSlotIdx,
                   vcnPortIdx,
                   vcnIdx,
                   condReportType,
                   condDateAndTime,
                   condSeverity,
                   condServiceAffecting,
                   trapSeqNum,
                   condDescription,
                   condObjectType,
                   condCodeType }
    STATUS       current
    DESCRIPTION  "A previously raised VC-N Unequipped condition has cleared."
    ::= { vcnCondNotifications 0 6 }


vcnSignalDegradeCond NOTIFICATION-TYPE
    OBJECTS      { vcnTypeIdx,
                   vcnShelfIdx,
                   vcnSlotIdx,
                   vcnPortIdx,
                   vcnIdx,
                   vcnBER,
                   vcnBERTh,
                   condReportType,
                   condDateAndTime,
                   condSeverity,
                   condServiceAffecting,
                   trapSeqNum,
                   condDescription,
                   condObjectType,
                   condCodeType }
    STATUS       current
    DESCRIPTION  "A signal degrade condition on the VC-N channel is active. This
                  indicates that the detected bit error rate exceeds the degrade
                  threshold."
    ::= { vcnCondNotifications 0 7 }


vcnSignalDegradeClear NOTIFICATION-TYPE
    OBJECTS      { vcnTypeIdx,
                   vcnShelfIdx,
                   vcnSlotIdx,
                   vcnPortIdx,
                   vcnIdx,
                   condReportType,
                   condDateAndTime,
                   condSeverity,
                   condServiceAffecting,
                   trapSeqNum,
                   condDescription,
                   condObjectType,
                   condCodeType }
    STATUS       current
    DESCRIPTION  "A previously raised VC-N signal degrade condition has
                  cleared."
    ::= { vcnCondNotifications 0 8 }


vcnForcedSwitchToProtectionCond NOTIFICATION-TYPE
    OBJECTS      { vcnTypeIdx,
                   vcnShelfIdx,
                   vcnSlotIdx,
                   vcnPortIdx,
                   vcnIdx,
                   condReportType,
                   condDateAndTime,
                   condSeverity,
                   condServiceAffecting,
                   trapSeqNum,
                   condDescription,
                   condObjectType,
                   condCodeType }
    STATUS       current
    DESCRIPTION  "The active VC-N channel of a protected VC-N channel pair has
                  been forced to switch to the Protection transceiver."
    ::= { vcnCondNotifications 0 9 }


vcnForcedSwitchToProtectionClear NOTIFICATION-TYPE
    OBJECTS      { vcnTypeIdx,
                   vcnShelfIdx,
                   vcnSlotIdx,
                   vcnPortIdx,
                   vcnIdx,
                   condReportType,
                   condDateAndTime,
                   condSeverity,
                   condServiceAffecting,
                   trapSeqNum,
                   condDescription,
                   condObjectType,
                   condCodeType }
    STATUS       current
    DESCRIPTION  "A previously raised VC-N Forced Switch To Protection condition
                  has cleared."
    ::= { vcnCondNotifications 0 10 }


vcnForcedSwitchToWorkingCond NOTIFICATION-TYPE
    OBJECTS      { vcnTypeIdx,
                   vcnShelfIdx,
                   vcnSlotIdx,
                   vcnPortIdx,
                   vcnIdx,
                   condReportType,
                   condDateAndTime,
                   condSeverity,
                   condServiceAffecting,
                   trapSeqNum,
                   condDescription,
                   condObjectType,
                   condCodeType }
    STATUS       current
    DESCRIPTION  "The active VC-N channel of a protected VC-N channel pair has
                  been forced to switch to the Working transceiver."
    ::= { vcnCondNotifications 0 11 }


vcnForcedSwitchToWorkingClear NOTIFICATION-TYPE
    OBJECTS      { vcnTypeIdx,
                   vcnShelfIdx,
                   vcnSlotIdx,
                   vcnPortIdx,
                   vcnIdx,
                   condReportType,
                   condDateAndTime,
                   condSeverity,
                   condServiceAffecting,
                   trapSeqNum,
                   condDescription,
                   condObjectType,
                   condCodeType }
    STATUS       current
    DESCRIPTION  "A previously raised VC-N Forced Switch To Working condition
                  has cleared."
    ::= { vcnCondNotifications 0 12 }


vcnLockoutProtectionCond NOTIFICATION-TYPE
    OBJECTS      { vcnTypeIdx,
                   vcnShelfIdx,
                   vcnSlotIdx,
                   vcnPortIdx,
                   vcnIdx,
                   condReportType,
                   condDateAndTime,
                   condSeverity,
                   condServiceAffecting,
                   trapSeqNum,
                   condDescription,
                   condObjectType,
                   condCodeType }
    STATUS       current
    DESCRIPTION  "The Protection VC-N channel of a protected VC-N channel pair
                  has been locked out."
    ::= { vcnCondNotifications 0 13 }


vcnLockoutProtectionClear NOTIFICATION-TYPE
    OBJECTS      { vcnTypeIdx,
                   vcnShelfIdx,
                   vcnSlotIdx,
                   vcnPortIdx,
                   vcnIdx,
                   condReportType,
                   condDateAndTime,
                   condSeverity,
                   condServiceAffecting,
                   trapSeqNum,
                   condDescription,
                   condObjectType,
                   condCodeType }
    STATUS       current
    DESCRIPTION  "A previously raised VC-N Lockout Protection condition has
                  cleared."
    ::= { vcnCondNotifications 0 14 }


vcnLockoutWorkingCond NOTIFICATION-TYPE
    OBJECTS      { vcnTypeIdx,
                   vcnShelfIdx,
                   vcnSlotIdx,
                   vcnPortIdx,
                   vcnIdx,
                   condReportType,
                   condDateAndTime,
                   condSeverity,
                   condServiceAffecting,
                   trapSeqNum,
                   condDescription,
                   condObjectType,
                   condCodeType }
    STATUS       current
    DESCRIPTION  "The Working VC-N channel of a protected VC-N channel pair has
                  been locked out."
    ::= { vcnCondNotifications 0 15 }


vcnLockoutWorkingClear NOTIFICATION-TYPE
    OBJECTS      { vcnTypeIdx,
                   vcnShelfIdx,
                   vcnSlotIdx,
                   vcnPortIdx,
                   vcnIdx,
                   condReportType,
                   condDateAndTime,
                   condSeverity,
                   condServiceAffecting,
                   trapSeqNum,
                   condDescription,
                   condObjectType,
                   condCodeType }
    STATUS       current
    DESCRIPTION  "A previously raised VC-N Lockout Working condition has
                  cleared."
    ::= { vcnCondNotifications 0 16 }

vcnConcatMismatchCond NOTIFICATION-TYPE
    OBJECTS      { vcnTypeIdx,
                   vcnShelfIdx,
                   vcnSlotIdx,
                   vcnPortIdx,
                   vcnIdx,
                   condReportType,
                   condDateAndTime,
                   condSeverity,
                   condServiceAffecting,
                   trapSeqNum,
                   condDescription,
                   condObjectType,
                   condCodeType }
    STATUS       current
    DESCRIPTION  "A connection provisioning does not match has been detected for
                  the VC-N channel."
    ::= { vcnCondNotifications 0 17 }


vcnConcatMismatchClear NOTIFICATION-TYPE
    OBJECTS      { vcnTypeIdx,
                   vcnShelfIdx,
                   vcnSlotIdx,
                   vcnPortIdx,
                   vcnIdx,
                   condReportType,
                   condDateAndTime,
                   condSeverity,
                   condServiceAffecting,
                   trapSeqNum,
                   condDescription,
                   condObjectType,
                   condCodeType }
    STATUS       current
    DESCRIPTION  "A previously raised VC-N Concat Mismatch condition has
                  cleared."
    ::= { vcnCondNotifications 0 18 }
    
geLossOfSignalCond NOTIFICATION-TYPE
    OBJECTS      { geShelfIdx,
                   geSlotIdx,
                   gePortIdx,
                   condReportType,
                   condDateAndTime,
                   condSeverity,
                   condServiceAffecting,
                   trapSeqNum,
                   condDescription,
                   condObjectType,
                   condCodeType }
    STATUS       current
    DESCRIPTION  "This notification indicates that there is no input signal
                  detected on the Gigabit Ethernet port."
    ::= { geCondNotifications 0 1 }


geLossOfSignalClear NOTIFICATION-TYPE
    OBJECTS      { geShelfIdx,
                   geSlotIdx,
                   gePortIdx,
                   condReportType,
                   condDateAndTime,
                   condSeverity,
                   condServiceAffecting,
                   trapSeqNum,
                   condDescription,
                   condObjectType,
                   condCodeType }
    STATUS       current
    DESCRIPTION  "This notification indicates that a previously active GE Loss
                  of Signal condition has been cleared."
    ::= { geCondNotifications 0 2 }


geXcvrMismatchCond NOTIFICATION-TYPE
    OBJECTS      { geShelfIdx,
                   geSlotIdx,
                   gePortIdx,
                   condReportType,
                   condDateAndTime,
                   condSeverity,
                   condServiceAffecting,
                   trapSeqNum,
                   condDescription,
                   condObjectType,
                   condCodeType }
    STATUS       current
    DESCRIPTION  "There is a mismatch between the SFP or XFP transceiver
                  provisioned for the Gigabit Ethernet facility port and the
                  physical transceiver that is inserted in the port. The SFP or
                  XFP transceiver in the port must match the attributes
                  provisioned for the GE facility."
    ::= { geCondNotifications 0 3 }


geXcvrMismatchClear NOTIFICATION-TYPE
    OBJECTS      { geShelfIdx,
                   geSlotIdx,
                   gePortIdx,
                   condReportType,
                   condDateAndTime,
                   condSeverity,
                   condServiceAffecting,
                   trapSeqNum,
                   condDescription,
                   condObjectType,
                   condCodeType }
    STATUS       current
    DESCRIPTION  "A previously active GE Mistmatch condition has cleared."
    ::= { geCondNotifications 0 4 }


geOpticalPwrReceivedMinCond NOTIFICATION-TYPE
    OBJECTS      { geShelfIdx,
                   geSlotIdx,
                   gePortIdx,
                   geOpticalPwrReceived,
                   geOpticalPwrReceivedMinTh,
                   condReportType,
                   condDateAndTime,
                   condSeverity,
                   condServiceAffecting,
                   trapSeqNum,
                   condDescription,
                   condObjectType,
                   condCodeType }
    STATUS       current
    DESCRIPTION  "Indicates that the input power for the Gigabit Ethernet
                  facility has fallen below the minimum threshold."
    ::= { geCondNotifications 0 5 }


geOpticalPwrReceivedMinClear NOTIFICATION-TYPE
    OBJECTS      { geShelfIdx,
                   geSlotIdx,
                   gePortIdx,
                   condReportType,
                   condDateAndTime,
                   condSeverity,
                   condServiceAffecting,
                   trapSeqNum,
                   condDescription,
                   condObjectType,
                   condCodeType }
    STATUS       current
    DESCRIPTION  "A previously active GE minimum power recieved condition has
                  cleared."
    ::= { geCondNotifications 0 6 }


geOpticalPwrReceivedMaxCond NOTIFICATION-TYPE
    OBJECTS      { geShelfIdx,
                   geSlotIdx,
                   gePortIdx,
                   geOpticalPwrReceived,
                   geOpticalPwrReceivedMaxTh,
                   condReportType,
                   condDateAndTime,
                   condSeverity,
                   condServiceAffecting,
                   trapSeqNum,
                   condDescription,
                   condObjectType,
                   condCodeType }
    STATUS       current
    DESCRIPTION  "Indicates that the input power for the Gigabity Ethernet
                  facility has risen above the maximum threshold."
    ::= { geCondNotifications 0 7 }


geOpticalPwrReceivedMaxClear NOTIFICATION-TYPE
    OBJECTS      { geShelfIdx,
                   geSlotIdx,
                   gePortIdx,
                   condReportType,
                   condDateAndTime,
                   condSeverity,
                   condServiceAffecting,
                   trapSeqNum,
                   condDescription,
                   condObjectType,
                   condCodeType }
    STATUS       current
    DESCRIPTION  "A previously active GE maximum power recieved condition has
                  cleared."
    ::= { geCondNotifications 0 8 }


geOpticalPwrTransmittedMinCond NOTIFICATION-TYPE
    OBJECTS      { geShelfIdx,
                   geSlotIdx,
                   gePortIdx,
                   geOpticalPwrTransmitted,
                   geOpticalPwrTransmittedMinTh,
                   condReportType,
                   condDateAndTime,
                   condSeverity,
                   condServiceAffecting,
                   trapSeqNum,
                   condDescription,
                   condObjectType,
                   condCodeType }
    STATUS       current
    DESCRIPTION  "Indicates that the output power for the Gigabit Ethernet
                  facility has fallen below the minimum threshold."
    ::= { geCondNotifications 0 9 }


geOpticalPwrTransmittedMinClear NOTIFICATION-TYPE
    OBJECTS      { geShelfIdx,
                   geSlotIdx,
                   gePortIdx,
                   condReportType,
                   condDateAndTime,
                   condSeverity,
                   condServiceAffecting,
                   trapSeqNum,
                   condDescription,
                   condObjectType,
                   condCodeType }
    STATUS       current
    DESCRIPTION  "A previously active GE minimum power transmitted condition has
                  cleared."
    ::= { geCondNotifications 0 10 }


geOpticalPwrTransmittedMaxCond NOTIFICATION-TYPE
    OBJECTS      { geShelfIdx,
                   geSlotIdx,
                   gePortIdx,
                   geOpticalPwrTransmitted,
                   geOpticalPwrTransmittedMaxTh,
                   condReportType,
                   condDateAndTime,
                   condSeverity,
                   condServiceAffecting,
                   trapSeqNum,
                   condDescription,
                   condObjectType,
                   condCodeType }
    STATUS       current
    DESCRIPTION  "Indicates that the output power for the Gigabit Ethernet
                  facility has risen above the maximum threshold."
    ::= { geCondNotifications 0 11 }


geOpticalPwrTransmittedMaxClear NOTIFICATION-TYPE
    OBJECTS      { geShelfIdx,
                   geSlotIdx,
                   gePortIdx,
                   condReportType,
                   condDateAndTime,
                   condSeverity,
                   condServiceAffecting,
                   trapSeqNum,
                   condDescription,
                   condObjectType,
                   condCodeType }
    STATUS       current
    DESCRIPTION  "A previously active GE maximum power transmitted condition has
                  cleared."
    ::= { geCondNotifications 0 12 }


geLossOfSyncCond NOTIFICATION-TYPE
    OBJECTS      { geShelfIdx,
                   geSlotIdx,
                   gePortIdx,
                   condReportType,
                   condDateAndTime,
                   condSeverity,
                   condServiceAffecting,
                   trapSeqNum,
                   condDescription,
                   condObjectType,
                   condCodeType }
    STATUS       current
    DESCRIPTION  "A Gigabit Ethernet Loss of Synchronization condition is active
                  on the port."
    ::= { geCondNotifications 0 13 }


geLossOfSyncClear NOTIFICATION-TYPE
    OBJECTS      { geShelfIdx,
                   geSlotIdx,
                   gePortIdx,
                   condReportType,
                   condDateAndTime,
                   condSeverity,
                   condServiceAffecting,
                   trapSeqNum,
                   condDescription,
                   condObjectType,
                   condCodeType }
    STATUS       current
    DESCRIPTION  "A previously active Gigabit Ethernet Loss of Synchronization
                  condition has cleared."
    ::= { geCondNotifications 0 14 }


geRemotePathFailureCond NOTIFICATION-TYPE
    OBJECTS      { geShelfIdx,
                   geSlotIdx,
                   gePortIdx,
                   condReportType,
                   condDateAndTime,
                   condSeverity,
                   condServiceAffecting,
                   trapSeqNum,
                   condDescription,
                   condObjectType,
                   condCodeType }
    STATUS       current
    DESCRIPTION  "A Gigabit Ethernet Remote Path Failure condition is active on
                  the port."
    ::= { geCondNotifications 0 15 }


geRemotePathFailureClear NOTIFICATION-TYPE
    OBJECTS      { geShelfIdx,
                   geSlotIdx,
                   gePortIdx,
                   condReportType,
                   condDateAndTime,
                   condSeverity,
                   condServiceAffecting,
                   trapSeqNum,
                   condDescription,
                   condObjectType,
                   condCodeType }
    STATUS       current
    DESCRIPTION  "A previously active GE Remote Path Failure condition has
                  cleared."
    ::= { geCondNotifications 0 16 }


geLossOfMultiframeCond NOTIFICATION-TYPE
    OBJECTS      { geShelfIdx,
                   geSlotIdx,
                   gePortIdx,
                   condReportType,
                   condDateAndTime,
                   condSeverity,
                   condServiceAffecting,
                   trapSeqNum,
                   condDescription,
                   condObjectType,
                   condCodeType }
    STATUS       current
    DESCRIPTION  "A Loss of Multiframe condition is active against the VCG that
                  is mapped to the identified Gigabit Ethernet port."
    ::= { geCondNotifications 0 17 }


geLossOfMultiframeClear NOTIFICATION-TYPE
    OBJECTS      { geShelfIdx,
                   geSlotIdx,
                   gePortIdx,
                   condReportType,
                   condDateAndTime,
                   condSeverity,
                   condServiceAffecting,
                   trapSeqNum,
                   condDescription,
                   condObjectType,
                   condCodeType }
    STATUS       current
    DESCRIPTION  "A previously raised GE Loss of Multiframe condition has
                  cleared."
    ::= { geCondNotifications 0 18 }


geLossOfSequenceCond NOTIFICATION-TYPE
    OBJECTS      { geShelfIdx,
                   geSlotIdx,
                   gePortIdx,
                   condReportType,
                   condDateAndTime,
                   condSeverity,
                   condServiceAffecting,
                   trapSeqNum,
                   condDescription,
                   condObjectType,
                   condCodeType }
    STATUS       current
    DESCRIPTION  "A Loss of Sequence condition is active against the VCG that is
                  mapped to the identified Gigabit Ethernet port."
    ::= { geCondNotifications 0 19 }


geLossOfSequenceClear NOTIFICATION-TYPE
    OBJECTS      { geShelfIdx,
                   geSlotIdx,
                   gePortIdx,
                   condReportType,
                   condDateAndTime,
                   condSeverity,
                   condServiceAffecting,
                   trapSeqNum,
                   condDescription,
                   condObjectType,
                   condCodeType }
    STATUS       current
    DESCRIPTION  "A previously active GE Loss of Sequence condition has
                  cleared."
    ::= { geCondNotifications 0 20 }


geLossOfAlignmentCond NOTIFICATION-TYPE
    OBJECTS      { geShelfIdx,
                   geSlotIdx,
                   gePortIdx,
                   condReportType,
                   condDateAndTime,
                   condSeverity,
                   condServiceAffecting,
                   trapSeqNum,
                   condDescription,
                   condObjectType,
                   condCodeType }
    STATUS       current
    DESCRIPTION  "A Loss of Alignment condition is active against the VCG that
                  is mapped to the identified Gigabit Ethernet port."
    ::= { geCondNotifications 0 21 }


geLossOfAlignmentClear NOTIFICATION-TYPE
    OBJECTS      { geShelfIdx,
                   geSlotIdx,
                   gePortIdx,
                   condReportType,
                   condDateAndTime,
                   condSeverity,
                   condServiceAffecting,
                   trapSeqNum,
                   condDescription,
                   condObjectType,
                   condCodeType }
    STATUS       current
    DESCRIPTION  "A previously active GE Loss of Alignment condition has
                  cleared."
    ::= { geCondNotifications 0 22 }


geLoopbackCond NOTIFICATION-TYPE
    OBJECTS      { geShelfIdx,
                   geSlotIdx,
                   gePortIdx,
                   condReportType,
                   condDateAndTime,
                   condSeverity,
                   condServiceAffecting,
                   trapSeqNum,
                   condDescription,
                   condObjectType,
                   condCodeType }
    STATUS       current
    DESCRIPTION  "Indicates that the Gigabit Ethernet facility has been
                  provisioned to enter loopback mode."
    ::= { geCondNotifications 0 23 }


geLoopbackClear NOTIFICATION-TYPE
    OBJECTS      { geShelfIdx,
                   geSlotIdx,
                   gePortIdx,
                   condReportType,
                   condDateAndTime,
                   condSeverity,
                   condServiceAffecting,
                   trapSeqNum,
                   condDescription,
                   condObjectType,
                   condCodeType }
    STATUS       current
    DESCRIPTION  "A previously active GE Loopback condition has cleared."
    ::= { geCondNotifications 0 24 }

geBandwidthMismatchCond NOTIFICATION-TYPE
    OBJECTS      { geShelfIdx,
                   geSlotIdx,
                   gePortIdx,
                   condReportType,
                   condDateAndTime,
                   condSeverity,
                   condServiceAffecting,
                   trapSeqNum,
                   condDescription,
                   condObjectType,
                   condCodeType }
    STATUS       current
    DESCRIPTION  "A GE bandwidth mismatch condition is active on the port."
    ::= { geCondNotifications 0 25 }


geBandwidthMismatchClear NOTIFICATION-TYPE
    OBJECTS      { geShelfIdx,
                   geSlotIdx,
                   gePortIdx,
                   condReportType,
                   condDateAndTime,
                   condSeverity,
                   condServiceAffecting,
                   trapSeqNum,
                   condDescription,
                   condObjectType,
                   condCodeType }
    STATUS       current
    DESCRIPTION  "A previously active GE bandwidth mismatch condition has
                  cleared."
    ::= { geCondNotifications 0 26 }

gePayloadMismatchCond NOTIFICATION-TYPE
    OBJECTS      { geShelfIdx,
                   geSlotIdx,
                   gePortIdx,
                   condReportType,
                   condDateAndTime,
                   condSeverity,
                   condServiceAffecting,
                   trapSeqNum,
                   condDescription,
                   condObjectType,
                   condCodeType }
    STATUS       current
    DESCRIPTION  "A GE payload mismatch condition is active on the port."
    ::= { geCondNotifications 0 27 }


gePayloadMismatchClear NOTIFICATION-TYPE
    OBJECTS      { geShelfIdx,
                   geSlotIdx,
                   gePortIdx,
                   condReportType,
                   condDateAndTime,
                   condSeverity,
                   condServiceAffecting,
                   trapSeqNum,
                   condDescription,
                   condObjectType,
                   condCodeType }
    STATUS       current
    DESCRIPTION  "A previously active GE payload mismatch condition has
                  cleared."
    ::= { geCondNotifications 0 28 }
    
fcLossOfSignalCond NOTIFICATION-TYPE
    OBJECTS      { fcShelfIdx,
                   fcSlotIdx,
                   fcPortIdx,
                   condReportType,
                   condDateAndTime,
                   condSeverity,
                   condServiceAffecting,
                   trapSeqNum,
                   condDescription,
                   condObjectType,
                   condCodeType }
    STATUS       current
    DESCRIPTION  "This notification indicates that there is no input signal
                  detected on the Fiber Channel port."
    ::= { fcCondNotifications 0 1 }


fcLossOfSignalClear NOTIFICATION-TYPE
    OBJECTS      { fcShelfIdx,
                   fcSlotIdx,
                   fcPortIdx,
                   condReportType,
                   condDateAndTime,
                   condSeverity,
                   condServiceAffecting,
                   trapSeqNum,
                   condDescription,
                   condObjectType,
                   condCodeType }
    STATUS       current
    DESCRIPTION  "This notification indicates that a previously active FC Loss
                  of Signal condition has been cleared."
    ::= { fcCondNotifications 0 2 }


fcXcvrMismatchCond NOTIFICATION-TYPE
    OBJECTS      { fcShelfIdx,
                   fcSlotIdx,
                   fcPortIdx,
                   condReportType,
                   condDateAndTime,
                   condSeverity,
                   condServiceAffecting,
                   trapSeqNum,
                   condDescription,
                   condObjectType,
                   condCodeType }
    STATUS       current
    DESCRIPTION  "There is a mismatch between the SFP or XFP transceiver
                  provisioned for the Fiber Channel facility port and the
                  physical transceiver that is inserted in the port. The SFP or
                  XFP transceiver in the port must match the attributes
                  provisioned for the FC facility."
    ::= { fcCondNotifications 0 3 }


fcXcvrMismatchClear NOTIFICATION-TYPE
    OBJECTS      { fcShelfIdx,
                   fcSlotIdx,
                   fcPortIdx,
                   condReportType,
                   condDateAndTime,
                   condSeverity,
                   condServiceAffecting,
                   trapSeqNum,
                   condDescription,
                   condObjectType,
                   condCodeType }
    STATUS       current
    DESCRIPTION  "A previously active FC XCVR Mistmatch condition has cleared."
    ::= { fcCondNotifications 0 4 }


fcOpticalPwrReceivedMinCond NOTIFICATION-TYPE
    OBJECTS      { fcShelfIdx,
                   fcSlotIdx,
                   fcPortIdx,
                   fcOpticalPwrReceived,
                   fcOpticalPwrReceivedMinTh,
                   condReportType,
                   condDateAndTime,
                   condSeverity,
                   condServiceAffecting,
                   trapSeqNum,
                   condDescription,
                   condObjectType,
                   condCodeType }
    STATUS       current
    DESCRIPTION  "Indicates that the input power for the Fiber Channel facility
                  has fallen below the minimum threshold."
    ::= { fcCondNotifications 0 5 }


fcOpticalPwrReceivedMinClear NOTIFICATION-TYPE
    OBJECTS      { fcShelfIdx,
                   fcSlotIdx,
                   fcPortIdx,
                   condReportType,
                   condDateAndTime,
                   condSeverity,
                   condServiceAffecting,
                   trapSeqNum,
                   condDescription,
                   condObjectType,
                   condCodeType }
    STATUS       current
    DESCRIPTION  "A previously active FC minimum power recieved condition has
                  cleared."
    ::= { fcCondNotifications 0 6 }


fcOpticalPwrReceivedMaxCond NOTIFICATION-TYPE
    OBJECTS      { fcShelfIdx,
                   fcSlotIdx,
                   fcPortIdx,
                   fcOpticalPwrReceived,
                   fcOpticalPwrReceivedMaxTh,
                   condReportType,
                   condDateAndTime,
                   condSeverity,
                   condServiceAffecting,
                   trapSeqNum,
                   condDescription,
                   condObjectType,
                   condCodeType }
    STATUS       current
    DESCRIPTION  "Indicates that the input power for the Fiber Channel facility
                  has risen above the maximum threshold."
    ::= { fcCondNotifications 0 7 }


fcOpticalPwrReceivedMaxClear NOTIFICATION-TYPE
    OBJECTS      { fcShelfIdx,
                   fcSlotIdx,
                   fcPortIdx,
                   condReportType,
                   condDateAndTime,
                   condSeverity,
                   condServiceAffecting,
                   trapSeqNum,
                   condDescription,
                   condObjectType,
                   condCodeType }
    STATUS       current
    DESCRIPTION  "A previously active FC maximum power recieved condition has
                  cleared."
    ::= { fcCondNotifications 0 8 }


fcOpticalPwrTransmittedMinCond NOTIFICATION-TYPE
    OBJECTS      { fcShelfIdx,
                   fcSlotIdx,
                   fcPortIdx,
                   fcOpticalPwrTransmitted,
                   fcOpticalPwrTransmittedMinTh,
                   condReportType,
                   condDateAndTime,
                   condSeverity,
                   condServiceAffecting,
                   trapSeqNum,
                   condDescription,
                   condObjectType,
                   condCodeType }
    STATUS       current
    DESCRIPTION  "Indicates that the output power for the Fiber Channel facility
                  has fallen below the minimum threshold."
    ::= { fcCondNotifications 0 9 }


fcOpticalPwrTransmittedMinClear NOTIFICATION-TYPE
    OBJECTS      { fcShelfIdx,
                   fcSlotIdx,
                   fcPortIdx,
                   condReportType,
                   condDateAndTime,
                   condSeverity,
                   condServiceAffecting,
                   trapSeqNum,
                   condDescription,
                   condObjectType,
                   condCodeType }
    STATUS       current
    DESCRIPTION  "A previously active FC minimum power transmitted condition has
                  cleared."
    ::= { fcCondNotifications 0 10 }


fcOpticalPwrTransmittedMaxCond NOTIFICATION-TYPE
    OBJECTS      { fcShelfIdx,
                   fcSlotIdx,
                   fcPortIdx,
                   fcOpticalPwrTransmitted,
                   fcOpticalPwrTransmittedMaxTh,
                   condReportType,
                   condDateAndTime,
                   condSeverity,
                   condServiceAffecting,
                   trapSeqNum,
                   condDescription,
                   condObjectType,
                   condCodeType }
    STATUS       current
    DESCRIPTION  "Indicates that the output power for the Fiber Channel facility
                  has risen above the maximum threshold."
    ::= { fcCondNotifications 0 11 }


fcOpticalPwrTransmittedMaxClear NOTIFICATION-TYPE
    OBJECTS      { fcShelfIdx,
                   fcSlotIdx,
                   fcPortIdx,
                   condReportType,
                   condDateAndTime,
                   condSeverity,
                   condServiceAffecting,
                   trapSeqNum,
                   condDescription,
                   condObjectType,
                   condCodeType }
    STATUS       current
    DESCRIPTION  "A previously active FC maximum power transmitted condition has
                  cleared."
    ::= { fcCondNotifications 0 12 }


fcLossOfSyncCond NOTIFICATION-TYPE
    OBJECTS      { fcShelfIdx,
                   fcSlotIdx,
                   fcPortIdx,
                   condReportType,
                   condDateAndTime,
                   condSeverity,
                   condServiceAffecting,
                   trapSeqNum,
                   condDescription,
                   condObjectType,
                   condCodeType }
    STATUS       current
    DESCRIPTION  "A Fiber Channel Loss of Synchronization condition is active on
                  the port."
    ::= { fcCondNotifications 0 13 }


fcLossOfSyncClear NOTIFICATION-TYPE
    OBJECTS      { fcShelfIdx,
                   fcSlotIdx,
                   fcPortIdx,
                   condReportType,
                   condDateAndTime,
                   condSeverity,
                   condServiceAffecting,
                   trapSeqNum,
                   condDescription,
                   condObjectType,
                   condCodeType }
    STATUS       current
    DESCRIPTION  "A previously active Fiber Channel Loss of Synchronization
                  condition has cleared."
    ::= { fcCondNotifications 0 14 }


fcRemotePathFailureCond NOTIFICATION-TYPE
    OBJECTS      { fcShelfIdx,
                   fcSlotIdx,
                   fcPortIdx,
                   condReportType,
                   condDateAndTime,
                   condSeverity,
                   condServiceAffecting,
                   trapSeqNum,
                   condDescription,
                   condObjectType,
                   condCodeType }
    STATUS       current
    DESCRIPTION  "A Fiber Channel Remote Path Failure condition is active on the
                  port."
    ::= { fcCondNotifications 0 15 }


fcRemotePathFailureClear NOTIFICATION-TYPE
    OBJECTS      { fcShelfIdx,
                   fcSlotIdx,
                   fcPortIdx,
                   condReportType,
                   condDateAndTime,
                   condSeverity,
                   condServiceAffecting,
                   trapSeqNum,
                   condDescription,
                   condObjectType,
                   condCodeType }
    STATUS       current
    DESCRIPTION  "A previously active FC Remote Path Failure condition has
                  cleared."
    ::= { fcCondNotifications 0 16 }


fcLossOfMultiframeCond NOTIFICATION-TYPE
    OBJECTS      { fcShelfIdx,
                   fcSlotIdx,
                   fcPortIdx,
                   condReportType,
                   condDateAndTime,
                   condSeverity,
                   condServiceAffecting,
                   trapSeqNum,
                   condDescription,
                   condObjectType,
                   condCodeType }
    STATUS       current
    DESCRIPTION  "A Loss of Multiframe condition is active against the VCG that
                  is mapped to the identified Fiber Channel port."
    ::= { fcCondNotifications 0 17 }


fcLossOfMultiframeClear NOTIFICATION-TYPE
    OBJECTS      { fcShelfIdx,
                   fcSlotIdx,
                   fcPortIdx,
                   condReportType,
                   condDateAndTime,
                   condSeverity,
                   condServiceAffecting,
                   trapSeqNum,
                   condDescription,
                   condObjectType,
                   condCodeType }
    STATUS       current
    DESCRIPTION  "A previously raised FC Loss of Multiframe condition has
                  cleared."
    ::= { fcCondNotifications 0 18 }


fcLossOfSequenceCond NOTIFICATION-TYPE
    OBJECTS      { fcShelfIdx,
                   fcSlotIdx,
                   fcPortIdx,
                   condReportType,
                   condDateAndTime,
                   condSeverity,
                   condServiceAffecting,
                   trapSeqNum,
                   condDescription,
                   condObjectType,
                   condCodeType }
    STATUS       current
    DESCRIPTION  "A Loss of Sequence condition is active against the VCG that is
                  mapped to the identified Fiber Channel port."
    ::= { fcCondNotifications 0 19 }


fcLossOfSequenceClear NOTIFICATION-TYPE
    OBJECTS      { fcShelfIdx,
                   fcSlotIdx,
                   fcPortIdx,
                   condReportType,
                   condDateAndTime,
                   condSeverity,
                   condServiceAffecting,
                   trapSeqNum,
                   condDescription,
                   condObjectType,
                   condCodeType }
    STATUS       current
    DESCRIPTION  "A previously active FC Loss of Sequence condition has
                  cleared."
    ::= { fcCondNotifications 0 20 }


fcLossOfAlignmentCond NOTIFICATION-TYPE
    OBJECTS      { fcShelfIdx,
                   fcSlotIdx,
                   fcPortIdx,
                   condReportType,
                   condDateAndTime,
                   condSeverity,
                   condServiceAffecting,
                   trapSeqNum,
                   condDescription,
                   condObjectType,
                   condCodeType }
    STATUS       current
    DESCRIPTION  "A Loss of Alignment condition is active against the VCG that
                  is mapped to the identified Fiber Channel port."
    ::= { fcCondNotifications 0 21 }


fcLossOfAlignmentClear NOTIFICATION-TYPE
    OBJECTS      { fcShelfIdx,
                   fcSlotIdx,
                   fcPortIdx,
                   condReportType,
                   condDateAndTime,
                   condSeverity,
                   condServiceAffecting,
                   trapSeqNum,
                   condDescription,
                   condObjectType,
                   condCodeType }
    STATUS       current
    DESCRIPTION  "A previously active FC Loss of Alignment condition has
                  cleared."
    ::= { fcCondNotifications 0 22 }


fcLoopbackCond NOTIFICATION-TYPE
    OBJECTS      { fcShelfIdx,
                   fcSlotIdx,
                   fcPortIdx,
                   condReportType,
                   condDateAndTime,
                   condSeverity,
                   condServiceAffecting,
                   trapSeqNum,
                   condDescription,
                   condObjectType,
                   condCodeType }
    STATUS       current
    DESCRIPTION  "Indicates that the Fiber Channel facility has been provisioned
                  to enter loopback mode."
    ::= { fcCondNotifications 0 23 }


fcLoopbackClear NOTIFICATION-TYPE
    OBJECTS      { fcShelfIdx,
                   fcSlotIdx,
                   fcPortIdx,
                   condReportType,
                   condDateAndTime,
                   condSeverity,
                   condServiceAffecting,
                   trapSeqNum,
                   condDescription,
                   condObjectType,
                   condCodeType }
    STATUS       current
    DESCRIPTION  "A previously active FC Loopback condition has cleared."
    ::= { fcCondNotifications 0 24 }

fcBandwidthMismatchCond NOTIFICATION-TYPE
    OBJECTS      { fcShelfIdx,
                   fcSlotIdx,
                   fcPortIdx,
                   condReportType,
                   condDateAndTime,
                   condSeverity,
                   condServiceAffecting,
                   trapSeqNum,
                   condDescription,
                   condObjectType,
                   condCodeType }
    STATUS       current
    DESCRIPTION  "A Fiber Channel bandwidth mismatch condition is active on the
                  port."
    ::= { fcCondNotifications 0 25 }


fcBandwidthMismatchClear NOTIFICATION-TYPE
    OBJECTS      { fcShelfIdx,
                   fcSlotIdx,
                   fcPortIdx,
                   condReportType,
                   condDateAndTime,
                   condSeverity,
                   condServiceAffecting,
                   trapSeqNum,
                   condDescription,
                   condObjectType,
                   condCodeType }
    STATUS       current
    DESCRIPTION  "A previously active Fiber Channel bandwidth mismatch condition
                  has cleared."
    ::= { fcCondNotifications 0 26 }

fcPayloadMismatchCond NOTIFICATION-TYPE
    OBJECTS      { fcShelfIdx,
                   fcSlotIdx,
                   fcPortIdx,
                   condReportType,
                   condDateAndTime,
                   condSeverity,
                   condServiceAffecting,
                   trapSeqNum,
                   condDescription,
                   condObjectType,
                   condCodeType }
    STATUS       current
    DESCRIPTION  "A Fiber Channel payload mismatch condition is active on the
                  port."
    ::= { fcCondNotifications 0 27 }


fcPayloadMismatchClear NOTIFICATION-TYPE
    OBJECTS      { fcShelfIdx,
                   fcSlotIdx,
                   fcPortIdx,
                   condReportType,
                   condDateAndTime,
                   condSeverity,
                   condServiceAffecting,
                   trapSeqNum,
                   condDescription,
                   condObjectType,
                   condCodeType }
    STATUS       current
    DESCRIPTION  "A previously active Fiber Channel payload mismatch condition
                  has cleared."
    ::= { fcCondNotifications 0 28 }
        

tl1UserLockoutCond NOTIFICATION-TYPE
    OBJECTS      { tl1UserIdx,
                   condReportType,
                   condDateAndTime,
                   condSeverity,
                   condServiceAffecting,
                   trapSeqNum,
                   condDescription,
                   condObjectType,
                   condCodeType }
    STATUS       current
    DESCRIPTION  "A user is locked out of the system. After three incorrect
                  attempts to login, a user is blocked from attempting to login
                  again for 60 seconds."
    ::= { adminCondNotifications 0 1 }


tl1UserLockoutClear NOTIFICATION-TYPE
    OBJECTS      { tl1UserIdx,
                   condReportType,
                   condDateAndTime,
                   condSeverity,
                   condServiceAffecting,
                   trapSeqNum,
                   condDescription,
                   condObjectType,
                   condCodeType }
    STATUS       current
    DESCRIPTION  "A previously active TL1 User Lockout condition has cleared."
    ::= { adminCondNotifications 0 2 }


tl1IpLockoutCond NOTIFICATION-TYPE
    OBJECTS      { tl1IpLockoutAddr,
                   condReportType,
                   condDateAndTime,
                   condSeverity,
                   condServiceAffecting,
                   trapSeqNum,
                   condDescription,
                   condObjectType,
                   condCodeType }
    STATUS       current
    DESCRIPTION  "After three incorrect attempts to login from the same IP
                  address, the IP address from which the three attempts are made
                  is blocked for 60 seconds. When this condition is present in
                  the actCondTable, the actCondTableEntryIdx will be set to the
                  networkElement OID and the actCondInstanceIdx will be set to
                  0."
    ::= { adminCondNotifications 0 3 }


tl1IpLockoutClear NOTIFICATION-TYPE
    OBJECTS      { tl1IpLockoutAddr,
                   condReportType,
                   condDateAndTime,
                   condSeverity,
                   condServiceAffecting ,
                   trapSeqNum,
                   condDescription,
                   condObjectType,
                   condCodeType }
    STATUS       current
    DESCRIPTION  "A previously active TL1 IP lockout condition has cleared."
    ::= { adminCondNotifications 0 4 }



----------------------------------------------
-- L1 ethernet port alarms
----------------------------------------------
olsSFPMissingCond NOTIFICATION-TYPE
    OBJECTS      { ethIntfShelfIdx,
                   ethIntfSlotIdx,
                   ethIntfPortTypeIdx,
                   ethIntfPortIdx,
                   condReportType,
                   condDateAndTime,
                   condSeverity,
                   condServiceAffecting,
                   trapSeqNum,
                   condDescription,
                   condObjectType,
                   condCodeType }
    STATUS       current
    DESCRIPTION  ""
    ::= { ethPortCondNotifications 0 1 }

olsSFPMissingClear NOTIFICATION-TYPE
    OBJECTS      { ethIntfShelfIdx,
                   ethIntfSlotIdx,
                   ethIntfPortTypeIdx,
                   ethIntfPortIdx,
                   condReportType,
                   condDateAndTime,
                   condSeverity,
                   condServiceAffecting,
                   trapSeqNum,
                   condDescription,
                   condObjectType,
                   condCodeType }
    STATUS       current
    DESCRIPTION  ""
    ::= { ethPortCondNotifications 0 2 }
    
olsSFPMismatchCond NOTIFICATION-TYPE
    OBJECTS      { ethIntfShelfIdx,
                   ethIntfSlotIdx,
                   ethIntfPortTypeIdx,
                   ethIntfPortIdx,
                   condReportType,
                   condDateAndTime,
                   condSeverity,
                   condServiceAffecting,
                   trapSeqNum,
                   condDescription,
                   condObjectType,
                   condCodeType }
    STATUS       current
    DESCRIPTION  ""
    ::= { ethPortCondNotifications 0 3 }

olsSFPMismatchClear NOTIFICATION-TYPE
    OBJECTS      { ethIntfShelfIdx,
                   ethIntfSlotIdx,
                   ethIntfPortTypeIdx,
                   ethIntfPortIdx,
                   condReportType,
                   condDateAndTime,
                   condSeverity,
                   condServiceAffecting,
                   trapSeqNum,
                   condDescription,
                   condObjectType,
                   condCodeType }
    STATUS       current
    DESCRIPTION  ""
    ::= { ethPortCondNotifications 0 4 }

olsInputLOSCond NOTIFICATION-TYPE
    OBJECTS      { ethIntfShelfIdx,
                   ethIntfSlotIdx,
                   ethIntfPortTypeIdx,
                   ethIntfPortIdx,
                   condReportType,
                   condDateAndTime,
                   condSeverity,
                   condServiceAffecting,
                   trapSeqNum,
                   condDescription,
                   condObjectType,
                   condCodeType }
    STATUS       current
    DESCRIPTION  ""
    ::= { ethPortCondNotifications 0 5 }

olsInputLOSClear NOTIFICATION-TYPE
    OBJECTS      { ethIntfShelfIdx,
                   ethIntfSlotIdx,
                   ethIntfPortTypeIdx,
                   ethIntfPortIdx,
                   condReportType,
                   condDateAndTime,
                   condSeverity,
                   condServiceAffecting,
                   trapSeqNum,
                   condDescription,
                   condObjectType,
                   condCodeType }
    STATUS       current
    DESCRIPTION  ""
    ::= { ethPortCondNotifications 0 6 }

olsOpticalPwrReceivedMinCond NOTIFICATION-TYPE
    OBJECTS      { ethIntfShelfIdx,
                   ethIntfSlotIdx,
                   ethIntfPortTypeIdx,
                   ethIntfPortIdx,
                   condReportType,
                   condDateAndTime,
                   condSeverity,
                   condServiceAffecting,
                   trapSeqNum,
                   condDescription,
                   condObjectType,
                   condCodeType }
    STATUS       current
    DESCRIPTION  ""
    ::= { ethPortCondNotifications 0 7 }

olsOpticalPwrReceivedMinClear NOTIFICATION-TYPE
    OBJECTS      { ethIntfShelfIdx,
                   ethIntfSlotIdx,
                   ethIntfPortTypeIdx,
                   ethIntfPortIdx,
                   condReportType,
                   condDateAndTime,
                   condSeverity,
                   condServiceAffecting,
                   trapSeqNum,
                   condDescription,
                   condObjectType,
                   condCodeType }
    STATUS       current
    DESCRIPTION  ""
    ::= { ethPortCondNotifications 0 8 }

olsOpticalPwrReceivedMaxCond NOTIFICATION-TYPE
    OBJECTS      { ethIntfShelfIdx,
                   ethIntfSlotIdx,
                   ethIntfPortTypeIdx,
                   ethIntfPortIdx,
                   condReportType,
                   condDateAndTime,
                   condSeverity,
                   condServiceAffecting,
                   trapSeqNum,
                   condDescription,
                   condObjectType,
                   condCodeType }
    STATUS       current
    DESCRIPTION  ""
    ::= { ethPortCondNotifications 0 9 }

olsOpticalPwrReceivedMaxClear NOTIFICATION-TYPE
    OBJECTS      { ethIntfShelfIdx,
                   ethIntfSlotIdx,
                   ethIntfPortTypeIdx,
                   ethIntfPortIdx,
                   condReportType,
                   condDateAndTime,
                   condSeverity,
                   condServiceAffecting,
                   trapSeqNum,
                   condDescription,
                   condObjectType,
                   condCodeType }
    STATUS       current
    DESCRIPTION  ""
    ::= { ethPortCondNotifications 0 10 }

olsOpticalPwrTransmittedMinCond NOTIFICATION-TYPE
    OBJECTS      { ethIntfShelfIdx,
                   ethIntfSlotIdx,
                   ethIntfPortTypeIdx,
                   ethIntfPortIdx,
                   condReportType,
                   condDateAndTime,
                   condSeverity,
                   condServiceAffecting,
                   trapSeqNum,
                   condDescription,
                   condObjectType,
                   condCodeType }
    STATUS       current
    DESCRIPTION  ""
    ::= { ethPortCondNotifications 0 11 }

olsOpticalPwrTransmittedMinClear NOTIFICATION-TYPE
    OBJECTS      { ethIntfShelfIdx,
                   ethIntfSlotIdx,
                   ethIntfPortTypeIdx,
                   ethIntfPortIdx,
                   condReportType,
                   condDateAndTime,
                   condSeverity,
                   condServiceAffecting,
                   trapSeqNum,
                   condDescription,
                   condObjectType,
                   condCodeType }
    STATUS       current
    DESCRIPTION  ""
    ::= { ethPortCondNotifications 0 12 }
 
olsOpticalPwrTransmittedMaxCond NOTIFICATION-TYPE
    OBJECTS      { ethIntfShelfIdx,
                   ethIntfSlotIdx,
                   ethIntfPortTypeIdx,
                   ethIntfPortIdx,
                   condReportType,
                   condDateAndTime,
                   condSeverity,
                   condServiceAffecting,
                   trapSeqNum,
                   condDescription,
                   condObjectType,
                   condCodeType }
    STATUS       current
    DESCRIPTION  ""
    ::= { ethPortCondNotifications 0 13 }
    
olsOpticalPwrTransmittedMaxClear NOTIFICATION-TYPE
    OBJECTS      { ethIntfShelfIdx,
                   ethIntfSlotIdx,
                   ethIntfPortTypeIdx,
                   ethIntfPortIdx,
                   condReportType,
                   condDateAndTime,
                   condSeverity,
                   condServiceAffecting,
                   trapSeqNum,
                   condDescription,
                   condObjectType,
                   condCodeType }
    STATUS       current
    DESCRIPTION  ""
    ::= { ethPortCondNotifications 0 14 }

olsTemperatureMaxCond NOTIFICATION-TYPE
    OBJECTS      { ethIntfShelfIdx,
                   ethIntfSlotIdx,
                   ethIntfPortTypeIdx,
                   ethIntfPortIdx,
                   condReportType,
                   condDateAndTime,
                   condSeverity,
                   condServiceAffecting,
                   trapSeqNum,
                   condDescription,
                   condObjectType,
                   condCodeType }
    STATUS       current
    DESCRIPTION  ""
    ::= { ethPortCondNotifications 0 15 }

olsTemperatureMaxClear NOTIFICATION-TYPE
    OBJECTS      { ethIntfShelfIdx,
                   ethIntfSlotIdx,
                   ethIntfPortTypeIdx,
                   ethIntfPortIdx,
                   condReportType,
                   condDateAndTime,
                   condSeverity,
                   condServiceAffecting,
                   trapSeqNum,
                   condDescription,
                   condObjectType,
                   condCodeType }
    STATUS       current
    DESCRIPTION  ""
    ::= { ethPortCondNotifications 0 16 }

olsLoopbackCond NOTIFICATION-TYPE
    OBJECTS      { ethIntfShelfIdx,
                   ethIntfSlotIdx,
                   ethIntfPortTypeIdx,
                   ethIntfPortIdx,
                   condReportType,
                   condDateAndTime,
                   condSeverity,
                   condServiceAffecting,
                   trapSeqNum,
                   condDescription,
                   condObjectType,
                   condCodeType }
    STATUS       current
    DESCRIPTION  ""
    ::= { ethPortCondNotifications 0 17 }

olsLoopbackClear NOTIFICATION-TYPE
    OBJECTS      { ethIntfShelfIdx,
                   ethIntfSlotIdx,
                   ethIntfPortTypeIdx,
                   ethIntfPortIdx,
                   condReportType,
                   condDateAndTime,
                   condSeverity,
                   condServiceAffecting,
                   trapSeqNum,
                   condDescription,
                   condObjectType,
                   condCodeType }
    STATUS       current
    DESCRIPTION  ""
    ::= { ethPortCondNotifications 0 18 }

olsLossOfSyncCond NOTIFICATION-TYPE
    OBJECTS      { ethIntfShelfIdx,
                   ethIntfSlotIdx,
                   ethIntfPortTypeIdx,
                   ethIntfPortIdx,
                   condReportType,
                   condDateAndTime,
                   condSeverity,
                   condServiceAffecting,
                   trapSeqNum,
                   condDescription,
                   condObjectType,
                   condCodeType }
    STATUS       current
    DESCRIPTION  ""
    ::= { ethPortCondNotifications 0 19 }
    
olsLossOfSyncClear NOTIFICATION-TYPE
    OBJECTS      { ethIntfShelfIdx,
                   ethIntfSlotIdx,
                   ethIntfPortTypeIdx,
                   ethIntfPortIdx,
                   condReportType,
                   condDateAndTime,
                   condSeverity,
                   condServiceAffecting,
                   trapSeqNum,
                   condDescription,
                   condObjectType,
                   condCodeType }
    STATUS       current
    DESCRIPTION  ""
    ::= { ethPortCondNotifications 0 20 } 


olsLossOfFrameCond NOTIFICATION-TYPE
    OBJECTS      { ethIntfShelfIdx,
                   ethIntfSlotIdx,
                   ethIntfPortTypeIdx,
                   ethIntfPortIdx,
                   condReportType,
                   condDateAndTime,
                   condSeverity,
                   condServiceAffecting,
                   trapSeqNum,
                   condDescription,
                   condObjectType,
                   condCodeType }
    STATUS       current
    DESCRIPTION  ""
    ::= { ethPortCondNotifications 0 21 }
    
olsLossOfFrameClear NOTIFICATION-TYPE
    OBJECTS      { ethIntfShelfIdx,
                   ethIntfSlotIdx,
                   ethIntfPortTypeIdx,
                   ethIntfPortIdx,
                   condReportType,
                   condDateAndTime,
                   condSeverity,
                   condServiceAffecting,
                   trapSeqNum,
                   condDescription,
                   condObjectType,
                   condCodeType }
    STATUS       current
    DESCRIPTION  ""
    ::= { ethPortCondNotifications 0 22 } 


olsAlarmIndicationSignalCond NOTIFICATION-TYPE
    OBJECTS      { ethIntfShelfIdx,
                   ethIntfSlotIdx,
                   ethIntfPortTypeIdx,
                   ethIntfPortIdx,
                   condReportType,
                   condDateAndTime,
                   condSeverity,
                   condServiceAffecting,
                   trapSeqNum,
                   condDescription,
                   condObjectType,
                   condCodeType }
    STATUS       current
    DESCRIPTION  ""
    ::= { ethPortCondNotifications 0 23 }
    
olsAlarmIndicationSignalClear NOTIFICATION-TYPE
    OBJECTS      { ethIntfShelfIdx,
                   ethIntfSlotIdx,
                   ethIntfPortTypeIdx,
                   ethIntfPortIdx,
                   condReportType,
                   condDateAndTime,
                   condSeverity,
                   condServiceAffecting,
                   trapSeqNum,
                   condDescription,
                   condObjectType,
                   condCodeType }
    STATUS       current
    DESCRIPTION  ""
    ::= { ethPortCondNotifications 0 24 } 

olsBackwardDefectIndicatorCond NOTIFICATION-TYPE
    OBJECTS      { ethIntfShelfIdx,
                   ethIntfSlotIdx,
                   ethIntfPortTypeIdx,
                   ethIntfPortIdx,
                   condReportType,
                   condDateAndTime,
                   condSeverity,
                   condServiceAffecting,
                   trapSeqNum,
                   condDescription,
                   condObjectType,
                   condCodeType }
    STATUS       current
    DESCRIPTION  ""
    ::= { ethPortCondNotifications 0 25 }
    
olsBackwardDefectIndicatorClear NOTIFICATION-TYPE
    OBJECTS      { ethIntfShelfIdx,
                   ethIntfSlotIdx,
                   ethIntfPortTypeIdx,
                   ethIntfPortIdx,
                   condReportType,
                   condDateAndTime,
                   condSeverity,
                   condServiceAffecting,
                   trapSeqNum,
                   condDescription,
                   condObjectType,
                   condCodeType }
    STATUS       current
    DESCRIPTION  ""
    ::= { ethPortCondNotifications 0 26 } 

olsSignalDegradeCond NOTIFICATION-TYPE
    OBJECTS      { ethIntfShelfIdx,
                   ethIntfSlotIdx,
                   ethIntfPortTypeIdx,
                   ethIntfPortIdx,
                   condReportType,
                   condDateAndTime,
                   condSeverity,
                   condServiceAffecting,
                   trapSeqNum,
                   condDescription,
                   condObjectType,
                   condCodeType }
    STATUS       current
    DESCRIPTION  ""
    ::= { ethPortCondNotifications 0 27 }
    
olsSignalDegradeClear NOTIFICATION-TYPE
    OBJECTS      { ethIntfShelfIdx,
                   ethIntfSlotIdx,
                   ethIntfPortTypeIdx,
                   ethIntfPortIdx,
                   condReportType,
                   condDateAndTime,
                   condSeverity,
                   condServiceAffecting,
                   trapSeqNum,
                   condDescription,
                   condObjectType,
                   condCodeType }
    STATUS       current
    DESCRIPTION  ""
    ::= { ethPortCondNotifications 0 28 } 


olsOTNPayloadMismatchCond NOTIFICATION-TYPE
    OBJECTS      { ethIntfShelfIdx,
                   ethIntfSlotIdx,
                   ethIntfPortTypeIdx,
                   ethIntfPortIdx,
                   condReportType,
                   condDateAndTime,
                   condSeverity,
                   condServiceAffecting,
                   trapSeqNum,
                   condDescription,
                   condObjectType,
                   condCodeType }
    STATUS       current
    DESCRIPTION  ""
    ::= { ethPortCondNotifications 0 29 }
    
olsOTNPayloadMismatchClear NOTIFICATION-TYPE
    OBJECTS      { ethIntfShelfIdx,
                   ethIntfSlotIdx,
                   ethIntfPortTypeIdx,
                   ethIntfPortIdx,
                   condReportType,
                   condDateAndTime,
                   condSeverity,
                   condServiceAffecting,
                   trapSeqNum,
                   condDescription,
                   condObjectType,
                   condCodeType }
    STATUS       current
    DESCRIPTION  ""
    ::= { ethPortCondNotifications 0 30 } 

olsOTUTrailTraceMismatchCond NOTIFICATION-TYPE
    OBJECTS      { ethIntfShelfIdx,
                   ethIntfSlotIdx,
                   ethIntfPortTypeIdx,
                   ethIntfPortIdx,
                   condReportType,
                   condDateAndTime,
                   condSeverity,
                   condServiceAffecting,
                   trapSeqNum,
                   condDescription,
                   condObjectType,
                   condCodeType }
    STATUS       current
    DESCRIPTION  ""
    ::= { ethPortCondNotifications 0 31 }
    
olsOTUTrailTraceMismatchClear NOTIFICATION-TYPE
    OBJECTS      { ethIntfShelfIdx,
                   ethIntfSlotIdx,
                   ethIntfPortTypeIdx,
                   ethIntfPortIdx,
                   condReportType,
                   condDateAndTime,
                   condSeverity,
                   condServiceAffecting,
                   trapSeqNum,
                   condDescription,
                   condObjectType,
                   condCodeType }
    STATUS       current
    DESCRIPTION  ""
    ::= { ethPortCondNotifications 0 32 } 


olsRemoteFaultCond NOTIFICATION-TYPE
    OBJECTS      { ethIntfShelfIdx,
                   ethIntfSlotIdx,
                   ethIntfPortTypeIdx,
                   ethIntfPortIdx,
                   condReportType,
                   condDateAndTime,
                   condSeverity,
                   condServiceAffecting,
                   trapSeqNum,
                   condDescription,
                   condObjectType,
                   condCodeType }
    STATUS       current
    DESCRIPTION  "A remote fault indication is active on the ethernet interface."
    ::= { ethPortCondNotifications 0 33 }


olsRemoteFaultClear NOTIFICATION-TYPE
    OBJECTS      { ethIntfShelfIdx,
                   ethIntfSlotIdx,
                   ethIntfPortTypeIdx,
                   ethIntfPortIdx,
                   condReportType,
                   condDateAndTime,
                   condSeverity,
                   condServiceAffecting,
                   trapSeqNum,
                   condDescription,
                   condObjectType,
                   condCodeType }
    STATUS       current
    DESCRIPTION  "A previously raised remote fault indication has cleared."
    ::= { ethPortCondNotifications 0 34 }

olsLocalFaultCond NOTIFICATION-TYPE
    OBJECTS      { ethIntfShelfIdx,
                   ethIntfSlotIdx,
                   ethIntfPortTypeIdx,
                   ethIntfPortIdx,
                   condReportType,
                   condDateAndTime,
                   condSeverity,
                   condServiceAffecting,
                   trapSeqNum,
                   condDescription,
                   condObjectType,
                   condCodeType }
    STATUS       current
    DESCRIPTION  "A local fault indication is active on the ethernet interface."
    ::= { ethPortCondNotifications 0 35 }


olsLocalFaultClear NOTIFICATION-TYPE
    OBJECTS      { ethIntfShelfIdx,
                   ethIntfSlotIdx,
                   ethIntfPortTypeIdx,
                   ethIntfPortIdx,
                   condReportType,
                   condDateAndTime,
                   condSeverity,
                   condServiceAffecting,
                   trapSeqNum,
                   condDescription,
                   condObjectType,
                   condCodeType }
    STATUS       current
    DESCRIPTION  "A previously raised local fault indication has cleared."
    ::= { ethPortCondNotifications 0 36 }


olsWavelengthNotAchievableCond NOTIFICATION-TYPE
    OBJECTS      { ethIntfShelfIdx,
                   ethIntfSlotIdx,
                   ethIntfPortTypeIdx,
                   ethIntfPortIdx,
                   condReportType,
                   condDateAndTime,
                   condSeverity,
                   condServiceAffecting,
                   trapSeqNum,
                   condDescription,
                   condObjectType,
                   condCodeType }
    STATUS       current
    DESCRIPTION  ""
    ::= { ethPortCondNotifications 0 37 }
    
    
olsWavelengthNotAchievableClear NOTIFICATION-TYPE
    OBJECTS      { ethIntfShelfIdx,
                   ethIntfSlotIdx,
                   ethIntfPortTypeIdx,
                   ethIntfPortIdx,
                   condReportType,
                   condDateAndTime,
                   condSeverity,
                   condServiceAffecting,
                   trapSeqNum,
                   condDescription,
                   condObjectType,
                   condCodeType }
    STATUS       current
    DESCRIPTION  ""
    ::= { ethPortCondNotifications 0 38 } 

--------------------------------------
-- L2 alarms 
--------------------------------------
olsLinkDownCond NOTIFICATION-TYPE
    OBJECTS      { pvxL2IntfSwitchIdx,
                   pvxL2IntfShelfIdx,
                   pvxL2IntfSlotIdx,
                   pvxL2IntfPortTypeIdx,
                   pvxL2IntfPortIdx,
                   condReportType,
                   condDateAndTime,
                   condSeverity,
                   condServiceAffecting,
                   trapSeqNum,
                   condDescription,
                   condObjectType,
                   condCodeType }
    STATUS       current
    DESCRIPTION  "PVX L2 port link down."
    ::= { pvxL2PortCondNotifications 0 1 }
    
olsLinkDownClear NOTIFICATION-TYPE
    OBJECTS      { pvxL2IntfSwitchIdx,
                   pvxL2IntfShelfIdx,
                   pvxL2IntfSlotIdx,
                   pvxL2IntfPortTypeIdx,
                   pvxL2IntfPortIdx,
                   condReportType,
                   condDateAndTime,
                   condSeverity,
                   condServiceAffecting,
                   trapSeqNum,
                   condDescription,
                   condObjectType,
                   condCodeType }
    STATUS       current
    DESCRIPTION  "PVX L2 port link down has cleared."
    ::= { pvxL2PortCondNotifications 0 2 }

--------------------------------------
-- ODU-N alarms 
--------------------------------------
odunPayloadMismatchCond NOTIFICATION-TYPE
    OBJECTS      { odunTypeIdx,
                   odunShelfIdx,
                   odunSlotIdx,
                   odunPortIdx,
                   odunIdx,
                   condReportType,
                   condDateAndTime,
                   condSeverity,
                   condServiceAffecting,
                   trapSeqNum,
                   condDescription,
                   condObjectType,
                   condCodeType }
    STATUS       current
    DESCRIPTION  "A payload mismatch is active on the ODU-N facility."
    ::= { odunCondNotifications 0 1 }
    
odunPayloadMismatchClear NOTIFICATION-TYPE
    OBJECTS      { odunTypeIdx,
                   odunShelfIdx,
                   odunSlotIdx,
                   odunPortIdx,
                   odunIdx,
                   condReportType,
                   condDateAndTime,
                   condSeverity,
                   condServiceAffecting,
                   trapSeqNum,
                   condDescription,
                   condObjectType,
                   condCodeType }
    STATUS       current
    DESCRIPTION  "A previously active ODU-N facility payload mismatch condition
                  has cleared."    
   ::= { odunCondNotifications 0 2 }

    
odunOpenConnectionIndicatorCond NOTIFICATION-TYPE
    OBJECTS      { odunTypeIdx,
                   odunShelfIdx,
                   odunSlotIdx,
                   odunPortIdx,
                   odunIdx,
                   condReportType,
                   condDateAndTime,
                   condSeverity,
                   condServiceAffecting,
                   trapSeqNum,
                   condDescription,
                   condObjectType,
                   condCodeType }
    STATUS       current
    DESCRIPTION  "An OCI is active on the ODU-N facility."
    ::= { odunCondNotifications 0 3 }

odunOpenConnectionIndicatorClear NOTIFICATION-TYPE
    OBJECTS      { odunTypeIdx,
                   odunShelfIdx,
                   odunSlotIdx,
                   odunPortIdx,
                   odunIdx,
                   condReportType,
                   condDateAndTime,
                   condSeverity,
                   condServiceAffecting,
                   trapSeqNum,
                   condDescription,
                   condObjectType,
                   condCodeType }
    STATUS       current
    DESCRIPTION  "A previously active ODU-N OCI condition has cleared."
    ::= { odunCondNotifications 0 4 }
   

--------------------------------------
-- BRI alarms 
--------------------------------------
briLossOfSignalCond NOTIFICATION-TYPE
    OBJECTS      { briShelfIdx,
                   briSlotIdx,
                   briPortIdx,
                   condReportType,
                   condDateAndTime,
                   condSeverity,
                   condServiceAffecting,
                   trapSeqNum,
                   condDescription,
                   condObjectType,
                   condCodeType }
    STATUS       current
    DESCRIPTION  "This notification indicates that there is no input signal
                  detected on the BRI port."
    ::= { briCondNotifications 0 1 }


briLossOfSignalClear NOTIFICATION-TYPE
    OBJECTS      { briShelfIdx,
                   briSlotIdx,
                   briPortIdx,
                   condReportType,
                   condDateAndTime,
                   condSeverity,
                   condServiceAffecting,
                   trapSeqNum,
                   condDescription,
                   condObjectType,
                   condCodeType }
    STATUS       current
    DESCRIPTION  "This notification indicates that a previously active BRI Loss
                  of Signal condition has been cleared."
    ::= { briCondNotifications 0 2 }


briXcvrMismatchCond NOTIFICATION-TYPE
    OBJECTS      { briShelfIdx,
                   briSlotIdx,
                   briPortIdx,
                   condReportType,
                   condDateAndTime,
                   condSeverity,
                   condServiceAffecting,
                   trapSeqNum,
                   condDescription,
                   condObjectType,
                   condCodeType }
    STATUS       current
    DESCRIPTION  "There is a mismatch between the SFP or XFP transceiver
                  provisioned for the BRI facility port and the
                  physical transceiver that is inserted in the port. The SFP or
                  XFP transceiver in the port must match the attributes
                  provisioned for the BRI facility."
    ::= { briCondNotifications 0 3 }


briXcvrMismatchClear NOTIFICATION-TYPE
    OBJECTS      { briShelfIdx,
                   briSlotIdx,
                   briPortIdx,
                   condReportType,
                   condDateAndTime,
                   condSeverity,
                   condServiceAffecting,
                   trapSeqNum,
                   condDescription,
                   condObjectType,
                   condCodeType }
    STATUS       current
    DESCRIPTION  "A previously active BRI XCVR Mistmatch condition has cleared."
    ::= { briCondNotifications 0 4 }


briOpticalPwrReceivedMinCond NOTIFICATION-TYPE
    OBJECTS      { briShelfIdx,
                   briSlotIdx,
                   briPortIdx,
                   briOpticalPwrReceived,
                   briOpticalPwrReceivedMinTh,
                   condReportType,
                   condDateAndTime,
                   condSeverity,
                   condServiceAffecting,
                   trapSeqNum,
                   condDescription,
                   condObjectType,
                   condCodeType }
    STATUS       current
    DESCRIPTION  "Indicates that the input power for the BRI facility
                  has fallen below the minimum threshold."
    ::= { briCondNotifications 0 5 }


briOpticalPwrReceivedMinClear NOTIFICATION-TYPE
    OBJECTS      { briShelfIdx,
                   briSlotIdx,
                   briPortIdx,
                   condReportType,
                   condDateAndTime,
                   condSeverity,
                   condServiceAffecting,
                   trapSeqNum,
                   condDescription,
                   condObjectType,
                   condCodeType }
    STATUS       current
    DESCRIPTION  "A previously active BRI minimum power recieved condition has
                  cleared."
    ::= { briCondNotifications 0 6 }


briOpticalPwrReceivedMaxCond NOTIFICATION-TYPE
    OBJECTS      { briShelfIdx,
                   briSlotIdx,
                   briPortIdx,
                   briOpticalPwrReceived,
                   briOpticalPwrReceivedMaxTh,
                   condReportType,
                   condDateAndTime,
                   condSeverity,
                   condServiceAffecting,
                   trapSeqNum,
                   condDescription,
                   condObjectType,
                   condCodeType }
    STATUS       current
    DESCRIPTION  "Indicates that the input power for the BRI facility
                  has risen above the maximum threshold."
    ::= { briCondNotifications 0 7 }


briOpticalPwrReceivedMaxClear NOTIFICATION-TYPE
    OBJECTS      { briShelfIdx,
                   briSlotIdx,
                   briPortIdx,
                   condReportType,
                   condDateAndTime,
                   condSeverity,
                   condServiceAffecting,
                   trapSeqNum,
                   condDescription,
                   condObjectType,
                   condCodeType }
    STATUS       current
    DESCRIPTION  "A previously active BRI maximum power recieved condition has
                  cleared."
    ::= { briCondNotifications 0 8 }


briOpticalPwrTransmittedMinCond NOTIFICATION-TYPE
    OBJECTS      { briShelfIdx,
                   briSlotIdx,
                   briPortIdx,
                   briOpticalPwrTransmitted,
                   briOpticalPwrTransmittedMinTh,
                   condReportType,
                   condDateAndTime,
                   condSeverity,
                   condServiceAffecting,
                   trapSeqNum,
                   condDescription,
                   condObjectType,
                   condCodeType }
    STATUS       current
    DESCRIPTION  "Indicates that the output power for the BRI facility
                  has fallen below the minimum threshold."
    ::= { briCondNotifications 0 9 }


briOpticalPwrTransmittedMinClear NOTIFICATION-TYPE
    OBJECTS      { briShelfIdx,
                   briSlotIdx,
                   briPortIdx,
                   condReportType,
                   condDateAndTime,
                   condSeverity,
                   condServiceAffecting,
                   trapSeqNum,
                   condDescription,
                   condObjectType,
                   condCodeType }
    STATUS       current
    DESCRIPTION  "A previously active BRI minimum power transmitted condition has
                  cleared."
    ::= { briCondNotifications 0 10 }


briOpticalPwrTransmittedMaxCond NOTIFICATION-TYPE
    OBJECTS      { briShelfIdx,
                   briSlotIdx,
                   briPortIdx,
                   briOpticalPwrTransmitted,
                   briOpticalPwrTransmittedMaxTh,
                   condReportType,
                   condDateAndTime,
                   condSeverity,
                   condServiceAffecting,
                   trapSeqNum,
                   condDescription,
                   condObjectType,
                   condCodeType }
    STATUS       current
    DESCRIPTION  "Indicates that the output power for the BRI facility
                  has risen above the maximum threshold."
    ::= { briCondNotifications 0 11 }


briOpticalPwrTransmittedMaxClear NOTIFICATION-TYPE
    OBJECTS      { briShelfIdx,
                   briSlotIdx,
                   briPortIdx,
                   condReportType,
                   condDateAndTime,
                   condSeverity,
                   condServiceAffecting,
                   trapSeqNum,
                   condDescription,
                   condObjectType,
                   condCodeType }
    STATUS       current
    DESCRIPTION  "A previously active BRI maximum power transmitted condition has
                  cleared."
    ::= { briCondNotifications 0 12 }


briLossOfMultiframeCond NOTIFICATION-TYPE
    OBJECTS      { briShelfIdx,
                   briSlotIdx,
                   briPortIdx,
                   condReportType,
                   condDateAndTime,
                   condSeverity,
                   condServiceAffecting,
                   trapSeqNum,
                   condDescription,
                   condObjectType,
                   condCodeType }
    STATUS       current
    DESCRIPTION  "A Loss of Multiframe condition is active against the VCG that
                  is mapped to the identified BRI port."
    ::= { briCondNotifications 0 13 }


briLossOfMultiframeClear NOTIFICATION-TYPE
    OBJECTS      { briShelfIdx,
                   briSlotIdx,
                   briPortIdx,
                   condReportType,
                   condDateAndTime,
                   condSeverity,
                   condServiceAffecting,
                   trapSeqNum,
                   condDescription,
                   condObjectType,
                   condCodeType }
    STATUS       current
    DESCRIPTION  "A previously raised BRI Loss of Multiframe condition has
                  cleared."
    ::= { briCondNotifications 0 14 }


briLossOfSequenceCond NOTIFICATION-TYPE
    OBJECTS      { briShelfIdx,
                   briSlotIdx,
                   briPortIdx,
                   condReportType,
                   condDateAndTime,
                   condSeverity,
                   condServiceAffecting,
                   trapSeqNum,
                   condDescription,
                   condObjectType,
                   condCodeType }
    STATUS       current
    DESCRIPTION  "A Loss of Sequence condition is active against the VCG that is
                  mapped to the identified BRI port."
    ::= { briCondNotifications 0 15 }


briLossOfSequenceClear NOTIFICATION-TYPE
    OBJECTS      { briShelfIdx,
                   briSlotIdx,
                   briPortIdx,
                   condReportType,
                   condDateAndTime,
                   condSeverity,
                   condServiceAffecting,
                   trapSeqNum,
                   condDescription,
                   condObjectType,
                   condCodeType }
    STATUS       current
    DESCRIPTION  "A previously active BRI Loss of Sequence condition has
                  cleared."
    ::= { briCondNotifications 0 16 }


briLossOfAlignmentCond NOTIFICATION-TYPE
    OBJECTS      { briShelfIdx,
                   briSlotIdx,
                   briPortIdx,
                   condReportType,
                   condDateAndTime,
                   condSeverity,
                   condServiceAffecting,
                   trapSeqNum,
                   condDescription,
                   condObjectType,
                   condCodeType }
    STATUS       current
    DESCRIPTION  "A Loss of Alignment condition is active against the VCG that
                  is mapped to the identified BRI port."
    ::= { briCondNotifications 0 17 }


briLossOfAlignmentClear NOTIFICATION-TYPE
    OBJECTS      { briShelfIdx,
                   briSlotIdx,
                   briPortIdx,
                   condReportType,
                   condDateAndTime,
                   condSeverity,
                   condServiceAffecting,
                   trapSeqNum,
                   condDescription,
                   condObjectType,
                   condCodeType }
    STATUS       current
    DESCRIPTION  "A previously active BRI Loss of Alignment condition has
                  cleared."
    ::= { briCondNotifications 0 18 }


briLoopbackCond NOTIFICATION-TYPE
    OBJECTS      { briShelfIdx,
                   briSlotIdx,
                   briPortIdx,
                   condReportType,
                   condDateAndTime,
                   condSeverity,
                   condServiceAffecting,
                   trapSeqNum,
                   condDescription,
                   condObjectType,
                   condCodeType }
    STATUS       current
    DESCRIPTION  "Indicates that the BRI facility has been provisioned
                  to enter loopback mode."
    ::= { briCondNotifications 0 19 }


briLoopbackClear NOTIFICATION-TYPE
    OBJECTS      { briShelfIdx,
                   briSlotIdx,
                   briPortIdx,
                   condReportType,
                   condDateAndTime,
                   condSeverity,
                   condServiceAffecting,
                   trapSeqNum,
                   condDescription,
                   condObjectType,
                   condCodeType }
    STATUS       current
    DESCRIPTION  "A previously active BRI Loopback condition has cleared."
    ::= { briCondNotifications 0 20 }

briBandwidthMismatchCond NOTIFICATION-TYPE
    OBJECTS      { briShelfIdx,
                   briSlotIdx,
                   briPortIdx,
                   condReportType,
                   condDateAndTime,
                   condSeverity,
                   condServiceAffecting,
                   trapSeqNum,
                   condDescription,
                   condObjectType,
                   condCodeType }
    STATUS       current
    DESCRIPTION  "A BRI bandwidth mismatch condition is active on the
                  port."
    ::= { briCondNotifications 0 21 }

briBandwidthMismatchClear NOTIFICATION-TYPE
    OBJECTS      { briShelfIdx,
                   briSlotIdx,
                   briPortIdx,
                   condReportType,
                   condDateAndTime,
                   condSeverity,
                   condServiceAffecting,
                   trapSeqNum,
                   condDescription,
                   condObjectType,
                   condCodeType }
    STATUS       current
    DESCRIPTION  "A previously active BRI bandwidth mismatch condition
                  has cleared."
    ::= { briCondNotifications 0 22 }
    
briLossOfLockCond NOTIFICATION-TYPE
    OBJECTS      { briShelfIdx,
                   briSlotIdx,
                   briPortIdx,
                   condReportType,
                   condDateAndTime,
                   condSeverity,
                   condServiceAffecting,
                   trapSeqNum,
                   condDescription,
                   condObjectType,
                   condCodeType }
    STATUS       current
    DESCRIPTION  "This alarm indicates that a BRI port is unable to lock
                  on the incoming bit stream. This is a result of either: the
                  provisioned protocol does not match the incoming signal, or
                  the incoming signal is excessively degraded."
    ::= { briCondNotifications 0 23 }

briLossOfLockClear NOTIFICATION-TYPE
    OBJECTS      { briShelfIdx,
                   briSlotIdx,
                   briPortIdx,
                   condReportType,
                   condDateAndTime,
                   condSeverity,
                   condServiceAffecting,
                   trapSeqNum,
                   condDescription,
                   condObjectType,
                   condCodeType }
    STATUS       current
    DESCRIPTION  "A previously active BRI loss of lock condition
                  has cleared."
    ::= { briCondNotifications 0 24 }
    
briTxLockingCond NOTIFICATION-TYPE
    OBJECTS      { briShelfIdx,
                   briSlotIdx,
                   briPortIdx,
                   condReportType,
                   condDateAndTime,
                   condSeverity,
                   condServiceAffecting,
                   trapSeqNum,
                   condDescription,
                   condObjectType,
                   condCodeType }
    STATUS       current
    DESCRIPTION  "This alarm indicates that a BRI client port is in the
                  process of locking on the signal in the transmit direction."
    ::= { briCondNotifications 0 25 }
    
briTxLockingClear NOTIFICATION-TYPE
    OBJECTS      { briShelfIdx,
                   briSlotIdx,
                   briPortIdx,
                   condReportType,
                   condDateAndTime,
                   condSeverity,
                   condServiceAffecting,
                   trapSeqNum,
                   condDescription,
                   condObjectType,
                   condCodeType }
    STATUS       current
    DESCRIPTION  "A previously active BRI TX locking condition has cleared."
    ::= { briCondNotifications 0 26 }


--------------------------------------
-- NTP assoc alarms
--------------------------------------

ntpAssocSrvrNotReachableCond NOTIFICATION-TYPE
    OBJECTS      { ntpClientAssocIdx,
                   condReportType,
                   condDateAndTime,
                   condSeverity,
                   condServiceAffecting,
                   trapSeqNum,
                   condDescription,
                   condObjectType,
                   condCodeType }
    STATUS       current
    DESCRIPTION  "This alarm indicates that an NTP server can not be reached.
                  This is a result of either: an invalid IP address, network
                  problems or the server is down."
    ::= { ntpcCondNotifications 0 1 }

ntpAssocSrvrNotReachableClear NOTIFICATION-TYPE
    OBJECTS      { ntpClientAssocIdx,
                   condReportType,
                   condDateAndTime,
                   condSeverity,
                   condServiceAffecting,
                   trapSeqNum,
                   condDescription,
                   condObjectType,
                   condCodeType }
    STATUS       current
    DESCRIPTION  "A previously active NTP server not reachable condition
                  has cleared."
    ::= { ntpcCondNotifications 0 2 }

ntpAssocSrvrNotRespondingCond NOTIFICATION-TYPE
    OBJECTS      { ntpClientAssocIdx,
                   condReportType,
                   condDateAndTime,
                   condSeverity,
                   condServiceAffecting,
                   trapSeqNum,
                   condDescription,
                   condObjectType,
                   condCodeType }
    STATUS       current
    DESCRIPTION  "This alarm indicates that an NTP server is reachable but
                  is not responding to the NTP requests correctly. This can
                  be a result of either: the server does not have the service
                  running or there is a server is having problems."
    ::= { ntpcCondNotifications 0 3 }

ntpAssocSrvrNotRespondingClear NOTIFICATION-TYPE
    OBJECTS      { ntpClientAssocIdx,
                   condReportType,
                   condDateAndTime,
                   condSeverity,
                   condServiceAffecting,
                   trapSeqNum,
                   condDescription,
                   condObjectType,
                   condCodeType }
    STATUS       current
    DESCRIPTION  "A previously active NTP server not responding condition
                  has cleared."
    ::= { ntpcCondNotifications 0 4 }

ntpAssocAuthenFailedCond NOTIFICATION-TYPE
    OBJECTS      { ntpClientAssocIdx,
                   condReportType,
                   condDateAndTime,
                   condSeverity,
                   condServiceAffecting,
                   trapSeqNum,
                   condDescription,
                   condObjectType,
                   condCodeType }
    STATUS       current
    DESCRIPTION  "This alarm indicates that NTP authentication has failed.
                  This can be a result of either: the key is configured
                  incorrectly on the client side or the NTP server does not
                  accept the key."
    ::= { ntpcCondNotifications 0 5 }

ntpAssocAuthenFailedClear NOTIFICATION-TYPE
    OBJECTS      { ntpClientAssocIdx,
                   condReportType,
                   condDateAndTime,
                   condSeverity,
                   condServiceAffecting,
                   trapSeqNum,
                   condDescription,
                   condObjectType,
                   condCodeType }
    STATUS       current
    DESCRIPTION  "A previously active NTP authentication failed condition
                  has cleared."
    ::= { ntpcCondNotifications 0 6 }

ntpTimeAndDateUpdateEvt NOTIFICATION-TYPE
    OBJECTS      { ntpOldTimeAndDate,
                   ntpNewTimeAndDate,
                   evtDateAndTime,
                   trapSeqNum,
                   evtDescription,
                   evtObjectType,
                   evtCodeType }
    STATUS       current
    DESCRIPTION  "This event occurs when the NTP client updates the system date and time
                  based on a selected reference clocks source."
    ::= { ntpcEvtNotifications 0 1 }

ntpTimingRefUpdateEvt NOTIFICATION-TYPE
    OBJECTS      { ntpRefIP,
                   ntpRefStratum,
                   evtDateAndTime,
                   trapSeqNum,
                   evtDescription,
                   evtObjectType,
                   evtCodeType }
    STATUS       current
    DESCRIPTION  "This event occurs when the NTP client has selected a reference clock
                  source from a list provided. This is the NTP association list."
    ::= { ntpcEvtNotifications 0 2 }

--------------------------------------
-- Environmental alarms
--------------------------------------

envAttrUnsupportedCond NOTIFICATION-TYPE
    OBJECTS      { envCondAttrHKIIdx,
                   condReportType,
                   condDateAndTime,
                   condSeverity,
                   condServiceAffecting,
                   trapSeqNum,
                   condDescription,
                   condObjectType,
                   condCodeType }
    STATUS       current
    DESCRIPTION  "Indicates that an environmental alarm detection is
                  configured against a housekeeping input port which is
                  located on equipment which does not support the configured
                  function."
    ::= { envCondNotifications 0 1 }


envAttrUnsupportedClear NOTIFICATION-TYPE
    OBJECTS      { envCondAttrHKIIdx,
                   condReportType,
                   condDateAndTime,
                   condSeverity,
                   condServiceAffecting,
                   trapSeqNum,
                   condDescription,
                   condObjectType,
                   condCodeType }
    STATUS       current
    DESCRIPTION  "A previously active environmental attribute unsupported alarm has cleared."
    ::= { envCondNotifications 0 2 }
    

envAirComprCond NOTIFICATION-TYPE
    OBJECTS      { envCondAttrHKIIdx,
                   condReportType,
                   condDateAndTime,
                   condSeverity,
                   condServiceAffecting,
                   trapSeqNum,
                   condDescription,
                   condObjectType,
                   condCodeType }
    STATUS       current
    DESCRIPTION  "Indicates that an environmental air compressor failure
                  alarm is raised."
    ::= { envCondNotifications 0 3 }


envAirComprClear NOTIFICATION-TYPE
    OBJECTS      { envCondAttrHKIIdx,
                   condReportType,
                   condDateAndTime,
                   condSeverity,
                   condServiceAffecting,
                   trapSeqNum,
                   condDescription,
                   condObjectType,
                   condCodeType }
    STATUS       current
    DESCRIPTION  "A previously active environmental air compressor failure
                  alarm has cleared."
    ::= { envCondNotifications 0 4 }
    

envAirCondCond NOTIFICATION-TYPE
    OBJECTS      { envCondAttrHKIIdx,
                   condReportType,
                   condDateAndTime,
                   condSeverity,
                   condServiceAffecting,
                   trapSeqNum,
                   condDescription,
                   condObjectType,
                   condCodeType }
    STATUS       current
    DESCRIPTION  "Indicates that an environmental air conditioning failure
                  alarm is raised."
    ::= { envCondNotifications 0 5 }


envAirCondClear NOTIFICATION-TYPE
    OBJECTS      { envCondAttrHKIIdx,
                   condReportType,
                   condDateAndTime,
                   condSeverity,
                   condServiceAffecting,
                   trapSeqNum,
                   condDescription,
                   condObjectType,
                   condCodeType }
    STATUS       current
    DESCRIPTION  "A previously active environmental air conditioning failure
                  alarm has cleared."
    ::= { envCondNotifications 0 6 }
    

envAirDryrCond NOTIFICATION-TYPE
    OBJECTS      { envCondAttrHKIIdx,
                   condReportType,
                   condDateAndTime,
                   condSeverity,
                   condServiceAffecting,
                   trapSeqNum,
                   condDescription,
                   condObjectType,
                   condCodeType }
    STATUS       current
    DESCRIPTION  "Indicates that an environmental air dryer failure
                  alarm is raised."
    ::= { envCondNotifications 0 7 }


envAirDryrClear NOTIFICATION-TYPE
    OBJECTS      { envCondAttrHKIIdx,
                   condReportType,
                   condDateAndTime,
                   condSeverity,
                   condServiceAffecting,
                   trapSeqNum,
                   condDescription,
                   condObjectType,
                   condCodeType }
    STATUS       current
    DESCRIPTION  "A previously active environmental air dryer failure
                  alarm has cleared."
    ::= { envCondNotifications 0 8 }
    

envBatDschrdCond NOTIFICATION-TYPE
    OBJECTS      { envCondAttrHKIIdx,
                   condReportType,
                   condDateAndTime,
                   condSeverity,
                   condServiceAffecting,
                   trapSeqNum,
                   condDescription,
                   condObjectType,
                   condCodeType }
    STATUS       current
    DESCRIPTION  "Indicates that an environmental battery discharging
                  alarm is raised."
    ::= { envCondNotifications 0 9 }


envBatDschrdClear NOTIFICATION-TYPE
    OBJECTS      { envCondAttrHKIIdx,
                   condReportType,
                   condDateAndTime,
                   condSeverity,
                   condServiceAffecting,
                   trapSeqNum,
                   condDescription,
                   condObjectType,
                   condCodeType }
    STATUS       current
    DESCRIPTION  "A previously active environmental battery discharging
                  alarm has cleared."
    ::= { envCondNotifications 0 10 }
    

envBatteryCond NOTIFICATION-TYPE
    OBJECTS      { envCondAttrHKIIdx,
                   condReportType,
                   condDateAndTime,
                   condSeverity,
                   condServiceAffecting,
                   trapSeqNum,
                   condDescription,
                   condObjectType,
                   condCodeType }
    STATUS       current
    DESCRIPTION  "Indicates that an environmental battery failure
                  alarm is raised."
    ::= { envCondNotifications 0 11 }


envBatteryClear NOTIFICATION-TYPE
    OBJECTS      { envCondAttrHKIIdx,
                   condReportType,
                   condDateAndTime,
                   condSeverity,
                   condServiceAffecting,
                   trapSeqNum,
                   condDescription,
                   condObjectType,
                   condCodeType }
    STATUS       current
    DESCRIPTION  "A previously active environmental battery failure
                  alarm has cleared."
    ::= { envCondNotifications 0 12 }
    

envClFanCond NOTIFICATION-TYPE
    OBJECTS      { envCondAttrHKIIdx,
                   condReportType,
                   condDateAndTime,
                   condSeverity,
                   condServiceAffecting,
                   trapSeqNum,
                   condDescription,
                   condObjectType,
                   condCodeType }
    STATUS       current
    DESCRIPTION  "Indicates that an environmental cooling fan failure
                  alarm is raised."
    ::= { envCondNotifications 0 13 }


envClFanClear NOTIFICATION-TYPE
    OBJECTS      { envCondAttrHKIIdx,
                   condReportType,
                   condDateAndTime,
                   condSeverity,
                   condServiceAffecting,
                   trapSeqNum,
                   condDescription,
                   condObjectType,
                   condCodeType }
    STATUS       current
    DESCRIPTION  "A previously active environmental cooling fan failure
                  alarm has cleared."
    ::= { envCondNotifications 0 14 }
    

envCpMajorCond NOTIFICATION-TYPE
    OBJECTS      { envCondAttrHKIIdx,
                   condReportType,
                   condDateAndTime,
                   condSeverity,
                   condServiceAffecting,
                   trapSeqNum,
                   condDescription,
                   condObjectType,
                   condCodeType }
    STATUS       current
    DESCRIPTION  "Indicates that an environmental centralized power major
                  alarm is raised."
    ::= { envCondNotifications 0 15 }


envCpMajorClear NOTIFICATION-TYPE
    OBJECTS      { envCondAttrHKIIdx,
                   condReportType,
                   condDateAndTime,
                   condSeverity,
                   condServiceAffecting,
                   trapSeqNum,
                   condDescription,
                   condObjectType,
                   condCodeType }
    STATUS       current
    DESCRIPTION  "A previously active environmental centralized power major
                  alarm has cleared."
    ::= { envCondNotifications 0 16 }
    

envCpMinorCond NOTIFICATION-TYPE
    OBJECTS      { envCondAttrHKIIdx,
                   condReportType,
                   condDateAndTime,
                   condSeverity,
                   condServiceAffecting,
                   trapSeqNum,
                   condDescription,
                   condObjectType,
                   condCodeType }
    STATUS       current
    DESCRIPTION  "Indicates that an environmental centralized power minor
                  alarm is raised."
    ::= { envCondNotifications 0 17 }


envCpMinorClear NOTIFICATION-TYPE
    OBJECTS      { envCondAttrHKIIdx,
                   condReportType,
                   condDateAndTime,
                   condSeverity,
                   condServiceAffecting,
                   trapSeqNum,
                   condDescription,
                   condObjectType,
                   condCodeType }
    STATUS       current
    DESCRIPTION  "A previously active environmental centralized power minor
                  alarm has cleared."
    ::= { envCondNotifications 0 18 }
    

envDoorOpenCond NOTIFICATION-TYPE
    OBJECTS      { envCondAttrHKIIdx,
                   condReportType,
                   condDateAndTime,
                   condSeverity,
                   condServiceAffecting,
                   trapSeqNum,
                   condDescription,
                   condObjectType,
                   condCodeType }
    STATUS       current
    DESCRIPTION  "Indicates that an environmental door open
                  alarm is raised."
    ::= { envCondNotifications 0 19 }


envDoorOpenClear NOTIFICATION-TYPE
    OBJECTS      { envCondAttrHKIIdx,
                   condReportType,
                   condDateAndTime,
                   condSeverity,
                   condServiceAffecting,
                   trapSeqNum,
                   condDescription,
                   condObjectType,
                   condCodeType }
    STATUS       current
    DESCRIPTION  "A previously active environmental door open
                  alarm has cleared."
    ::= { envCondNotifications 0 20 }
    

envEngineCond NOTIFICATION-TYPE
    OBJECTS      { envCondAttrHKIIdx,
                   condReportType,
                   condDateAndTime,
                   condSeverity,
                   condServiceAffecting,
                   trapSeqNum,
                   condDescription,
                   condObjectType,
                   condCodeType }
    STATUS       current
    DESCRIPTION  "Indicates that an environmental engine failure
                  alarm is raised."
    ::= { envCondNotifications 0 21 }


envEngineClear NOTIFICATION-TYPE
    OBJECTS      { envCondAttrHKIIdx,
                   condReportType,
                   condDateAndTime,
                   condSeverity,
                   condServiceAffecting,
                   trapSeqNum,
                   condDescription,
                   condObjectType,
                   condCodeType }
    STATUS       current
    DESCRIPTION  "A previously active environmental engine failure
                  alarm has cleared."
    ::= { envCondNotifications 0 22 }
    

envEngOprgCond NOTIFICATION-TYPE
    OBJECTS      { envCondAttrHKIIdx,
                   condReportType,
                   condDateAndTime,
                   condSeverity,
                   condServiceAffecting,
                   trapSeqNum,
                   condDescription,
                   condObjectType,
                   condCodeType }
    STATUS       current
    DESCRIPTION  "Indicates that an environmental engine operating
                  alarm is raised."
    ::= { envCondNotifications 0 23 }


envEngOprgClear NOTIFICATION-TYPE
    OBJECTS      { envCondAttrHKIIdx,
                   condReportType,
                   condDateAndTime,
                   condSeverity,
                   condServiceAffecting,
                   trapSeqNum,
                   condDescription,
                   condObjectType,
                   condCodeType }
    STATUS       current
    DESCRIPTION  "A previously active environmental engine operating
                  alarm has cleared."
    ::= { envCondNotifications 0 24 }
    

envExplGsCond NOTIFICATION-TYPE
    OBJECTS      { envCondAttrHKIIdx,
                   condReportType,
                   condDateAndTime,
                   condSeverity,
                   condServiceAffecting,
                   trapSeqNum,
                   condDescription,
                   condObjectType,
                   condCodeType }
    STATUS       current
    DESCRIPTION  "Indicates that an environmental explosive gas
                  alarm is raised."
    ::= { envCondNotifications 0 25 }


envExplGsClear NOTIFICATION-TYPE
    OBJECTS      { envCondAttrHKIIdx,
                   condReportType,
                   condDateAndTime,
                   condSeverity,
                   condServiceAffecting,
                   trapSeqNum,
                   condDescription,
                   condObjectType,
                   condCodeType }
    STATUS       current
    DESCRIPTION  "A previously active environmental explosive gas
                  alarm has cleared."
    ::= { envCondNotifications 0 26 }
    

envFirDetrCond NOTIFICATION-TYPE
    OBJECTS      { envCondAttrHKIIdx,
                   condReportType,
                   condDateAndTime,
                   condSeverity,
                   condServiceAffecting,
                   trapSeqNum,
                   condDescription,
                   condObjectType,
                   condCodeType }
    STATUS       current
    DESCRIPTION  "Indicates that an environmental fire detector failure
                  alarm is raised."
    ::= { envCondNotifications 0 27 }


envFirDetrClear NOTIFICATION-TYPE
    OBJECTS      { envCondAttrHKIIdx,
                   condReportType,
                   condDateAndTime,
                   condSeverity,
                   condServiceAffecting,
                   trapSeqNum,
                   condDescription,
                   condObjectType,
                   condCodeType }
    STATUS       current
    DESCRIPTION  "A previously active environmental fire detector failure
                  alarm has cleared."
    ::= { envCondNotifications 0 28 }
    

envFireCond NOTIFICATION-TYPE
    OBJECTS      { envCondAttrHKIIdx,
                   condReportType,
                   condDateAndTime,
                   condSeverity,
                   condServiceAffecting,
                   trapSeqNum,
                   condDescription,
                   condObjectType,
                   condCodeType }
    STATUS       current
    DESCRIPTION  "Indicates that an environmental fire
                  alarm is raised."
    ::= { envCondNotifications 0 29 }


envFireClear NOTIFICATION-TYPE
    OBJECTS      { envCondAttrHKIIdx,
                   condReportType,
                   condDateAndTime,
                   condSeverity,
                   condServiceAffecting,
                   trapSeqNum,
                   condDescription,
                   condObjectType,
                   condCodeType }
    STATUS       current
    DESCRIPTION  "A previously active environmental fire
                  alarm has cleared."
    ::= { envCondNotifications 0 30 }
    

envFloodCond NOTIFICATION-TYPE
    OBJECTS      { envCondAttrHKIIdx,
                   condReportType,
                   condDateAndTime,
                   condSeverity,
                   condServiceAffecting,
                   trapSeqNum,
                   condDescription,
                   condObjectType,
                   condCodeType }
    STATUS       current
    DESCRIPTION  "Indicates that an environmental flood
                  alarm is raised."
    ::= { envCondNotifications 0 31 }


envFloodClear NOTIFICATION-TYPE
    OBJECTS      { envCondAttrHKIIdx,
                   condReportType,
                   condDateAndTime,
                   condSeverity,
                   condServiceAffecting,
                   trapSeqNum,
                   condDescription,
                   condObjectType,
                   condCodeType }
    STATUS       current
    DESCRIPTION  "A previously active environmental flood
                  alarm has cleared."
    ::= { envCondNotifications 0 32 }
    

envFuseCond NOTIFICATION-TYPE
    OBJECTS      { envCondAttrHKIIdx,
                   condReportType,
                   condDateAndTime,
                   condSeverity,
                   condServiceAffecting,
                   trapSeqNum,
                   condDescription,
                   condObjectType,
                   condCodeType }
    STATUS       current
    DESCRIPTION  "Indicates that an environmental fuse
                  alarm is raised."
    ::= { envCondNotifications 0 33 }


envFuseClear NOTIFICATION-TYPE
    OBJECTS      { envCondAttrHKIIdx,
                   condReportType,
                   condDateAndTime,
                   condSeverity,
                   condServiceAffecting,
                   trapSeqNum,
                   condDescription,
                   condObjectType,
                   condCodeType }
    STATUS       current
    DESCRIPTION  "A previously active environmental fuse
                  alarm has cleared."
    ::= { envCondNotifications 0 34 }
    

envGenCond NOTIFICATION-TYPE
    OBJECTS      { envCondAttrHKIIdx,
                   condReportType,
                   condDateAndTime,
                   condSeverity,
                   condServiceAffecting,
                   trapSeqNum,
                   condDescription,
                   condObjectType,
                   condCodeType }
    STATUS       current
    DESCRIPTION  "Indicates that an environmental generator failure
                  alarm is raised."
    ::= { envCondNotifications 0 35 }


envGenClear NOTIFICATION-TYPE
    OBJECTS      { envCondAttrHKIIdx,
                   condReportType,
                   condDateAndTime,
                   condSeverity,
                   condServiceAffecting,
                   trapSeqNum,
                   condDescription,
                   condObjectType,
                   condCodeType }
    STATUS       current
    DESCRIPTION  "A previously active environmental generator failure
                  alarm has cleared."
    ::= { envCondNotifications 0 36 }
    

envGenericCond NOTIFICATION-TYPE
    OBJECTS      { envCondAttrHKIIdx,
                   condReportType,
                   condDateAndTime,
                   condSeverity,
                   condServiceAffecting,
                   trapSeqNum,
                   condDescription,
                   condObjectType,
                   condCodeType }
    STATUS       current
    DESCRIPTION  "Indicates that an environmental generic
                  alarm is raised."
    ::= { envCondNotifications 0 37 }


envGenericClear NOTIFICATION-TYPE
    OBJECTS      { envCondAttrHKIIdx,
                   condReportType,
                   condDateAndTime,
                   condSeverity,
                   condServiceAffecting,
                   trapSeqNum,
                   condDescription,
                   condObjectType,
                   condCodeType }
    STATUS       current
    DESCRIPTION  "A previously active environmental generic
                  alarm has cleared."
    ::= { envCondNotifications 0 38 }
    

envHiAirCond NOTIFICATION-TYPE
    OBJECTS      { envCondAttrHKIIdx,
                   condReportType,
                   condDateAndTime,
                   condSeverity,
                   condServiceAffecting,
                   trapSeqNum,
                   condDescription,
                   condObjectType,
                   condCodeType }
    STATUS       current
    DESCRIPTION  "Indicates that an environmental high airflow
                  alarm is raised."
    ::= { envCondNotifications 0 39 }


envHiAirClear NOTIFICATION-TYPE
    OBJECTS      { envCondAttrHKIIdx,
                   condReportType,
                   condDateAndTime,
                   condSeverity,
                   condServiceAffecting,
                   trapSeqNum,
                   condDescription,
                   condObjectType,
                   condCodeType }
    STATUS       current
    DESCRIPTION  "A previously active environmental high airflow
                  alarm has cleared."
    ::= { envCondNotifications 0 40 }
    

envHiHumCond NOTIFICATION-TYPE
    OBJECTS      { envCondAttrHKIIdx,
                   condReportType,
                   condDateAndTime,
                   condSeverity,
                   condServiceAffecting,
                   trapSeqNum,
                   condDescription,
                   condObjectType,
                   condCodeType }
    STATUS       current
    DESCRIPTION  "Indicates that an environmental high humidity
                  alarm is raised."
    ::= { envCondNotifications 0 41 }


envHiHumClear NOTIFICATION-TYPE
    OBJECTS      { envCondAttrHKIIdx,
                   condReportType,
                   condDateAndTime,
                   condSeverity,
                   condServiceAffecting,
                   trapSeqNum,
                   condDescription,
                   condObjectType,
                   condCodeType }
    STATUS       current
    DESCRIPTION  "A previously active environmental high humidity
                  alarm has cleared."
    ::= { envCondNotifications 0 42 }
    

envHiTempCond NOTIFICATION-TYPE
    OBJECTS      { envCondAttrHKIIdx,
                   condReportType,
                   condDateAndTime,
                   condSeverity,
                   condServiceAffecting,
                   trapSeqNum,
                   condDescription,
                   condObjectType,
                   condCodeType }
    STATUS       current
    DESCRIPTION  "Indicates that an environmental high temperature
                  alarm is raised."
    ::= { envCondNotifications 0 43 }


envHiTempClear NOTIFICATION-TYPE
    OBJECTS      { envCondAttrHKIIdx,
                   condReportType,
                   condDateAndTime,
                   condSeverity,
                   condServiceAffecting,
                   trapSeqNum,
                   condDescription,
                   condObjectType,
                   condCodeType }
    STATUS       current
    DESCRIPTION  "A previously active environmental high temperature
                  alarm has cleared."
    ::= { envCondNotifications 0 44 }
    

envHiWindCond NOTIFICATION-TYPE
    OBJECTS      { envCondAttrHKIIdx,
                   condReportType,
                   condDateAndTime,
                   condSeverity,
                   condServiceAffecting,
                   trapSeqNum,
                   condDescription,
                   condObjectType,
                   condCodeType }
    STATUS       current
    DESCRIPTION  "Indicates that an environmental high wind
                  alarm is raised."
    ::= { envCondNotifications 0 45 }


envHiWindClear NOTIFICATION-TYPE
    OBJECTS      { envCondAttrHKIIdx,
                   condReportType,
                   condDateAndTime,
                   condSeverity,
                   condServiceAffecting,
                   trapSeqNum,
                   condDescription,
                   condObjectType,
                   condCodeType }
    STATUS       current
    DESCRIPTION  "A previously active environmental high wind
                  alarm has cleared."
    ::= { envCondNotifications 0 46 }
    

envHiWtrCond NOTIFICATION-TYPE
    OBJECTS      { envCondAttrHKIIdx,
                   condReportType,
                   condDateAndTime,
                   condSeverity,
                   condServiceAffecting,
                   trapSeqNum,
                   condDescription,
                   condObjectType,
                   condCodeType }
    STATUS       current
    DESCRIPTION  "Indicates that an environmental high water
                  alarm is raised."
    ::= { envCondNotifications 0 47 }


envHiWtrClear NOTIFICATION-TYPE
    OBJECTS      { envCondAttrHKIIdx,
                   condReportType,
                   condDateAndTime,
                   condSeverity,
                   condServiceAffecting,
                   trapSeqNum,
                   condDescription,
                   condObjectType,
                   condCodeType }
    STATUS       current
    DESCRIPTION  "A previously active environmental high water
                  alarm has cleared."
    ::= { envCondNotifications 0 48 }
    

envIceBuildupCond NOTIFICATION-TYPE
    OBJECTS      { envCondAttrHKIIdx,
                   condReportType,
                   condDateAndTime,
                   condSeverity,
                   condServiceAffecting,
                   trapSeqNum,
                   condDescription,
                   condObjectType,
                   condCodeType }
    STATUS       current
    DESCRIPTION  "Indicates that an environmental ice buildup
                  alarm is raised."
    ::= { envCondNotifications 0 49 }


envIceBuildupClear NOTIFICATION-TYPE
    OBJECTS      { envCondAttrHKIIdx,
                   condReportType,
                   condDateAndTime,
                   condSeverity,
                   condServiceAffecting,
                   trapSeqNum,
                   condDescription,
                   condObjectType,
                   condCodeType }
    STATUS       current
    DESCRIPTION  "A previously active environmental ice buildup
                  alarm has cleared."
    ::= { envCondNotifications 0 50 }
    

envIntruderCond NOTIFICATION-TYPE
    OBJECTS      { envCondAttrHKIIdx,
                   condReportType,
                   condDateAndTime,
                   condSeverity,
                   condServiceAffecting,
                   trapSeqNum,
                   condDescription,
                   condObjectType,
                   condCodeType }
    STATUS       current
    DESCRIPTION  "Indicates that an environmental intrusion
                  alarm is raised."
    ::= { envCondNotifications 0 51 }


envIntruderClear NOTIFICATION-TYPE
    OBJECTS      { envCondAttrHKIIdx,
                   condReportType,
                   condDateAndTime,
                   condSeverity,
                   condServiceAffecting,
                   trapSeqNum,
                   condDescription,
                   condObjectType,
                   condCodeType }
    STATUS       current
    DESCRIPTION  "A previously active environmental intrusion
                  alarm has cleared."
    ::= { envCondNotifications 0 52 }
    

envLwBatvgCond NOTIFICATION-TYPE
    OBJECTS      { envCondAttrHKIIdx,
                   condReportType,
                   condDateAndTime,
                   condSeverity,
                   condServiceAffecting,
                   trapSeqNum,
                   condDescription,
                   condObjectType,
                   condCodeType }
    STATUS       current
    DESCRIPTION  "Indicates that an environmental low battery voltage
                  alarm is raised."
    ::= { envCondNotifications 0 53 }


envLwBatvgClear NOTIFICATION-TYPE
    OBJECTS      { envCondAttrHKIIdx,
                   condReportType,
                   condDateAndTime,
                   condSeverity,
                   condServiceAffecting,
                   trapSeqNum,
                   condDescription,
                   condObjectType,
                   condCodeType }
    STATUS       current
    DESCRIPTION  "A previously active environmental low battery voltage
                  alarm has cleared."
    ::= { envCondNotifications 0 54 }
    

envLwFuelCond NOTIFICATION-TYPE
    OBJECTS      { envCondAttrHKIIdx,
                   condReportType,
                   condDateAndTime,
                   condSeverity,
                   condServiceAffecting,
                   trapSeqNum,
                   condDescription,
                   condObjectType,
                   condCodeType }
    STATUS       current
    DESCRIPTION  "Indicates that an environmental low fuel
                  alarm is raised."
    ::= { envCondNotifications 0 55 }


envLwFuelClear NOTIFICATION-TYPE
    OBJECTS      { envCondAttrHKIIdx,
                   condReportType,
                   condDateAndTime,
                   condSeverity,
                   condServiceAffecting,
                   trapSeqNum,
                   condDescription,
                   condObjectType,
                   condCodeType }
    STATUS       current
    DESCRIPTION  "A previously active environmental low fuel
                  alarm has cleared."
    ::= { envCondNotifications 0 56 }
    

envLwHumCond NOTIFICATION-TYPE
    OBJECTS      { envCondAttrHKIIdx,
                   condReportType,
                   condDateAndTime,
                   condSeverity,
                   condServiceAffecting,
                   trapSeqNum,
                   condDescription,
                   condObjectType,
                   condCodeType }
    STATUS       current
    DESCRIPTION  "Indicates that an environmental low humidity
                  alarm is raised."
    ::= { envCondNotifications 0 57 }


envLwHumClear NOTIFICATION-TYPE
    OBJECTS      { envCondAttrHKIIdx,
                   condReportType,
                   condDateAndTime,
                   condSeverity,
                   condServiceAffecting,
                   trapSeqNum,
                   condDescription,
                   condObjectType,
                   condCodeType }
    STATUS       current
    DESCRIPTION  "A previously active environmental low humidity
                  alarm has cleared."
    ::= { envCondNotifications 0 58 }
    

envLwPresCond NOTIFICATION-TYPE
    OBJECTS      { envCondAttrHKIIdx,
                   condReportType,
                   condDateAndTime,
                   condSeverity,
                   condServiceAffecting,
                   trapSeqNum,
                   condDescription,
                   condObjectType,
                   condCodeType }
    STATUS       current
    DESCRIPTION  "Indicates that an environmental low cable pressure
                  alarm is raised."
    ::= { envCondNotifications 0 59 }


envLwPresClear NOTIFICATION-TYPE
    OBJECTS      { envCondAttrHKIIdx,
                   condReportType,
                   condDateAndTime,
                   condSeverity,
                   condServiceAffecting,
                   trapSeqNum,
                   condDescription,
                   condObjectType,
                   condCodeType }
    STATUS       current
    DESCRIPTION  "A previously active environmental low cable pressure
                  alarm has cleared."
    ::= { envCondNotifications 0 60 }
    

envLwTempCond NOTIFICATION-TYPE
    OBJECTS      { envCondAttrHKIIdx,
                   condReportType,
                   condDateAndTime,
                   condSeverity,
                   condServiceAffecting,
                   trapSeqNum,
                   condDescription,
                   condObjectType,
                   condCodeType }
    STATUS       current
    DESCRIPTION  "Indicates that an environmental low temperature
                  alarm is raised."
    ::= { envCondNotifications 0 61 }


envLwTempClear NOTIFICATION-TYPE
    OBJECTS      { envCondAttrHKIIdx,
                   condReportType,
                   condDateAndTime,
                   condSeverity,
                   condServiceAffecting,
                   trapSeqNum,
                   condDescription,
                   condObjectType,
                   condCodeType }
    STATUS       current
    DESCRIPTION  "A previously active environmental low temperature
                  alarm has cleared."
    ::= { envCondNotifications 0 62 }
    

envLwWtrCond NOTIFICATION-TYPE
    OBJECTS      { envCondAttrHKIIdx,
                   condReportType,
                   condDateAndTime,
                   condSeverity,
                   condServiceAffecting,
                   trapSeqNum,
                   condDescription,
                   condObjectType,
                   condCodeType }
    STATUS       current
    DESCRIPTION  "Indicates that an environmental low water
                  alarm is raised."
    ::= { envCondNotifications 0 63 }


envLwWtrClear NOTIFICATION-TYPE
    OBJECTS      { envCondAttrHKIIdx,
                   condReportType,
                   condDateAndTime,
                   condSeverity,
                   condServiceAffecting,
                   trapSeqNum,
                   condDescription,
                   condObjectType,
                   condCodeType }
    STATUS       current
    DESCRIPTION  "A previously active environmental low water
                  alarm has cleared."
    ::= { envCondNotifications 0 64 }
    

envMiscCond NOTIFICATION-TYPE
    OBJECTS      { envCondAttrHKIIdx,
                   condReportType,
                   condDateAndTime,
                   condSeverity,
                   condServiceAffecting,
                   trapSeqNum,
                   condDescription,
                   condObjectType,
                   condCodeType }
    STATUS       current
    DESCRIPTION  "Indicates that an environmental miscellaneous
                  alarm is raised."
    ::= { envCondNotifications 0 65 }


envMiscClear NOTIFICATION-TYPE
    OBJECTS      { envCondAttrHKIIdx,
                   condReportType,
                   condDateAndTime,
                   condSeverity,
                   condServiceAffecting,
                   trapSeqNum,
                   condDescription,
                   condObjectType,
                   condCodeType }
    STATUS       current
    DESCRIPTION  "A previously active environmental miscellaneous
                  alarm has cleared."
    ::= { envCondNotifications 0 66 }
    

envOpenDrCond NOTIFICATION-TYPE
    OBJECTS      { envCondAttrHKIIdx,
                   condReportType,
                   condDateAndTime,
                   condSeverity,
                   condServiceAffecting,
                   trapSeqNum,
                   condDescription,
                   condObjectType,
                   condCodeType }
    STATUS       current
    DESCRIPTION  "Indicates that an environmental open door
                  alarm is raised."
    ::= { envCondNotifications 0 67 }


envOpenDrClear NOTIFICATION-TYPE
    OBJECTS      { envCondAttrHKIIdx,
                   condReportType,
                   condDateAndTime,
                   condSeverity,
                   condServiceAffecting,
                   trapSeqNum,
                   condDescription,
                   condObjectType,
                   condCodeType }
    STATUS       current
    DESCRIPTION  "A previously active environmental open door
                  alarm has cleared."
    ::= { envCondNotifications 0 68 }
    

envPowerCond NOTIFICATION-TYPE
    OBJECTS      { envCondAttrHKIIdx,
                   condReportType,
                   condDateAndTime,
                   condSeverity,
                   condServiceAffecting,
                   trapSeqNum,
                   condDescription,
                   condObjectType,
                   condCodeType }
    STATUS       current
    DESCRIPTION  "Indicates that an environmental power failure
                  alarm is raised."
    ::= { envCondNotifications 0 69 }


envPowerClear NOTIFICATION-TYPE
    OBJECTS      { envCondAttrHKIIdx,
                   condReportType,
                   condDateAndTime,
                   condSeverity,
                   condServiceAffecting,
                   trapSeqNum,
                   condDescription,
                   condObjectType,
                   condCodeType }
    STATUS       current
    DESCRIPTION  "A previously active environmental power failure
                  alarm has cleared."
    ::= { envCondNotifications 0 70 }
    

envPumpCond NOTIFICATION-TYPE
    OBJECTS      { envCondAttrHKIIdx,
                   condReportType,
                   condDateAndTime,
                   condSeverity,
                   condServiceAffecting,
                   trapSeqNum,
                   condDescription,
                   condObjectType,
                   condCodeType }
    STATUS       current
    DESCRIPTION  "Indicates that an environmental pump failure
                  alarm is raised."
    ::= { envCondNotifications 0 71 }


envPumpClear NOTIFICATION-TYPE
    OBJECTS      { envCondAttrHKIIdx,
                   condReportType,
                   condDateAndTime,
                   condSeverity,
                   condServiceAffecting,
                   trapSeqNum,
                   condDescription,
                   condObjectType,
                   condCodeType }
    STATUS       current
    DESCRIPTION  "A previously active environmental pump failure
                  alarm has cleared."
    ::= { envCondNotifications 0 72 }
    

envRectCond NOTIFICATION-TYPE
    OBJECTS      { envCondAttrHKIIdx,
                   condReportType,
                   condDateAndTime,
                   condSeverity,
                   condServiceAffecting,
                   trapSeqNum,
                   condDescription,
                   condObjectType,
                   condCodeType }
    STATUS       current
    DESCRIPTION  "Indicates that an environmental rectifier failure
                  alarm is raised."
    ::= { envCondNotifications 0 73 }


envRectClear NOTIFICATION-TYPE
    OBJECTS      { envCondAttrHKIIdx,
                   condReportType,
                   condDateAndTime,
                   condSeverity,
                   condServiceAffecting,
                   trapSeqNum,
                   condDescription,
                   condObjectType,
                   condCodeType }
    STATUS       current
    DESCRIPTION  "A previously active environmental rectifier failure
                  alarm has cleared."
    ::= { envCondNotifications 0 74 }
    

envRectHiCond NOTIFICATION-TYPE
    OBJECTS      { envCondAttrHKIIdx,
                   condReportType,
                   condDateAndTime,
                   condSeverity,
                   condServiceAffecting,
                   trapSeqNum,
                   condDescription,
                   condObjectType,
                   condCodeType }
    STATUS       current
    DESCRIPTION  "Indicates that an environmental rectifier high voltage
                  alarm is raised."
    ::= { envCondNotifications 0 75 }


envRectHiClear NOTIFICATION-TYPE
    OBJECTS      { envCondAttrHKIIdx,
                   condReportType,
                   condDateAndTime,
                   condSeverity,
                   condServiceAffecting,
                   trapSeqNum,
                   condDescription,
                   condObjectType,
                   condCodeType }
    STATUS       current
    DESCRIPTION  "A previously active environmental rectifier high voltage
                  alarm has cleared."
    ::= { envCondNotifications 0 76 }
    

envRectLoCond NOTIFICATION-TYPE
    OBJECTS      { envCondAttrHKIIdx,
                   condReportType,
                   condDateAndTime,
                   condSeverity,
                   condServiceAffecting,
                   trapSeqNum,
                   condDescription,
                   condObjectType,
                   condCodeType }
    STATUS       current
    DESCRIPTION  "Indicates that an environmental rectifier low voltage
                  alarm is raised."
    ::= { envCondNotifications 0 77 }


envRectLoClear NOTIFICATION-TYPE
    OBJECTS      { envCondAttrHKIIdx,
                   condReportType,
                   condDateAndTime,
                   condSeverity,
                   condServiceAffecting,
                   trapSeqNum,
                   condDescription,
                   condObjectType,
                   condCodeType }
    STATUS       current
    DESCRIPTION  "A previously active environmental rectifier low voltage
                  alarm has cleared."
    ::= { envCondNotifications 0 78 }
    

envSmokeCond NOTIFICATION-TYPE
    OBJECTS      { envCondAttrHKIIdx,
                   condReportType,
                   condDateAndTime,
                   condSeverity,
                   condServiceAffecting,
                   trapSeqNum,
                   condDescription,
                   condObjectType,
                   condCodeType }
    STATUS       current
    DESCRIPTION  "Indicates that an environmental smoke
                  alarm is raised."
    ::= { envCondNotifications 0 79 }


envSmokeClear NOTIFICATION-TYPE
    OBJECTS      { envCondAttrHKIIdx,
                   condReportType,
                   condDateAndTime,
                   condSeverity,
                   condServiceAffecting,
                   trapSeqNum,
                   condDescription,
                   condObjectType,
                   condCodeType }
    STATUS       current
    DESCRIPTION  "A previously active environmental smoke
                  alarm has cleared."
    ::= { envCondNotifications 0 80 }
    

envToxicGasCond NOTIFICATION-TYPE
    OBJECTS      { envCondAttrHKIIdx,
                   condReportType,
                   condDateAndTime,
                   condSeverity,
                   condServiceAffecting,
                   trapSeqNum,
                   condDescription,
                   condObjectType,
                   condCodeType }
    STATUS       current
    DESCRIPTION  "Indicates that an environmental toxic gas
                  alarm is raised."
    ::= { envCondNotifications 0 81 }


envToxicGasClear NOTIFICATION-TYPE
    OBJECTS      { envCondAttrHKIIdx,
                   condReportType,
                   condDateAndTime,
                   condSeverity,
                   condServiceAffecting,
                   trapSeqNum,
                   condDescription,
                   condObjectType,
                   condCodeType }
    STATUS       current
    DESCRIPTION  "A previously active environmental toxic gas
                  alarm has cleared."
    ::= { envCondNotifications 0 82 }
    

envVentnCond NOTIFICATION-TYPE
    OBJECTS      { envCondAttrHKIIdx,
                   condReportType,
                   condDateAndTime,
                   condSeverity,
                   condServiceAffecting,
                   trapSeqNum,
                   condDescription,
                   condObjectType,
                   condCodeType }
    STATUS       current
    DESCRIPTION  "Indicates that an environmental ventilation system failure
                  alarm is raised."
    ::= { envCondNotifications 0 83 }


envVentnClear NOTIFICATION-TYPE
    OBJECTS      { envCondAttrHKIIdx,
                   condReportType,
                   condDateAndTime,
                   condSeverity,
                   condServiceAffecting,
                   trapSeqNum,
                   condDescription,
                   condObjectType,
                   condCodeType }
    STATUS       current
    DESCRIPTION  "A previously active environmental ventilation system failure
                  alarm has cleared."
    ::= { envCondNotifications 0 84 }
    


-----------------------------------------------------------------------
-- Database Change Notifications
-- 
-- When a provisioning or database change is made on the system, a database change
-- trap is sent, signifying that an update has been made to the persisted database on
-- the system.
-- 
-- A listing of database change notifications is contained in the 
-- following table.
-----------------------------------------------------------------------

dbChangeEvt NOTIFICATION-TYPE
    OBJECTS      { dbChangeDateAndTime,
                   dbChangeSeqNum,
                   dbChangeOID,
                   trapSeqNum,
                   evtDescription,
                   evtObjectType,
                   evtCodeType }
    STATUS       current
    DESCRIPTION  "This message indicates that a change has been made in the
                  value of the provisioned object identified by the dbChangeOID
                  Var-Bind. If multiple objects have been changed in the same
                  transaction, there will be multiple occurrances of the
                  dbChangeOID object listed in the Var-Bind list."
    ::= { dbChangeNotifications 0 2 }

dbChangeSecuEvt NOTIFICATION-TYPE
    OBJECTS      { dbChangeDateAndTime,
                   dbChangeSeqNum,
                   trapSeqNum,
                   evtDescription,
                   evtObjectType,
                   evtCodeType }
    STATUS       current
    DESCRIPTION  "This message indicates that a change has been made in the
                  value of the SNMP community string, SNMP trap reciever, or
                  Tl1User."
    ::= { dbChangeNotifications 0 3 }


-----------------------------------------------------------------------
-- LLDP Events
-----------------------------------------------------------------------

pvxLldpRemTablesChangeEvt NOTIFICATION-TYPE
    OBJECTS      {
                    pvxL2IntfSwitchIdx }
    STATUS        current
    DESCRIPTION "A pvxLldpRemTablesChangeEvt notification is sent when the value
            of pvxLldpStatsRemTablesLastChangeTime changes.  It can be
            utilized by an NMS to trigger LLDP remote systems table
            maintenance polls. Note that transmission of lldpRemTablesChange
            notifications are throttled by the agent.

            The agent must not generate more than one lldpRemTablesChange
            notification-event in the indicated period, where a
            'notification-event' is the transmission of a single
            notification PDU type to a list of notification destinations.
            If additional changes in lldpRemoteSystemsData object
            groups occur within the indicated throttling period,
            then these trap- events must be suppressed by the
            agent.

            By default the throttling period is set to 60 seconds."

   ::= { pvxLldpEvtNotifications 0 1 }


END -- End of BTI-7000-MIB Module, must a /NL character at the end this line!
