-- extracted from draft-kajos-hmultimediamib-00.txt
-- at Mon Nov 15 17:11:06 1999

        MULTI-MEDIA-REG-TC DEFINITIONS ::= BEGIN
        
        IMPORTS
        
            MODULE-IDENTITY, OBJECT-IDENTITY,
            experimental
                FROM SNMPv2-SMI
        
            TEXTUAL-CONVENTION
                FROM SNMPv2-TC;
        
        multimediaRegMib MODULE-IDENTITY
            LAST-UPDATED "9805291200Z"
            ORGANIZATION "Cisco Systems, Inc."
            CONTACT-INFO
                "       Dan Klenke
                        Cisco Systems, Inc
        
                Postal: 170 West Tasman Drive
                        San Jose, CA 95134-1706
        
                E-mail: dklenke@Cisco.com"

            DESCRIPTION
                "Defines a set of Textual Conventions used within the set
                of MultiMedia MIB modules.
        
               Defines OBJECT IDENTIFIERs for rooting associated mib
                modules under this tree"
            REVISION      "9805291200Z"
            DESCRIPTION
                "The initial version of the mib."
            ::= { experimental 323  } -- temporary TBD later
        
        --
        --
        --
        -- TEXTUAL Conventions
        
        MmUtf8String ::= TEXTUAL-CONVENTION
            DISPLAY-HINT "255a"
            STATUS  current
            DESCRIPTION
               "To facilitate internationalization, this TC represents
               information taken from the ISO/IEC IS 10646-1 character
         set, encoded as an octet string using the UTF-8 character
        encoding scheme described in RFC 2044 [8].  For strings in 7-bit US-
        ASCII, there is no impact since the UTF-8 representation is
        identical to the US-ASCII encoding."
            SYNTAX  OCTET STRING (SIZE (0..255))
        
        
        MmE164String ::= TEXTUAL-CONVENTION
            DISPLAY-HINT "128a"
            STATUS  current
            DESCRIPTION
                "A UTF-8 string limited to the character set defined for E.164,
                '0123456789*#,<quote>' "
        -- note that <quote> represents the double quote <"> which cannot be 
        -- contained in a SMI description clause
            SYNTAX OCTET STRING (SIZE (1..128))
        
        
        MmTAddressTag ::= TEXTUAL-CONVENTION
            STATUS       current
            DESCRIPTION
                "A tag to identify the type of the transport address contained
                in the TAddress textual convention.  The values correlate to the
                TransportAddress defined in the H.225.0 V2 ITU protocol
                specification. The tag indicates how to interpret the

        value of a TAddress  data type defined in this specification.  All
        TAddress  values are in network byte order
        
                                TAddress size       TAddress contents
                         ipv4      6 octets         IPv4 (4 octets), port (2 octets)
                         ipv6     18                IPv6 (16), port (2)
                         ipx      12                net (4), node (6), port (2)
                         nsap     1-20              nsap(1-20)
                         netbios  16                netbios(16)
                 "
            SYNTAX    INTEGER {
                          other(0),
                          ipv4(1),
                          ipv6(2),
                          ipx(3),
                          nsap(4),
                    netbios(5)
                      }
        
        MmGlobalIdentifier ::= TEXTUAL-CONVENTION
            DISPLAY-HINT "8d-9,3x,1d,2x:2x:2x"
            STATUS       current
            DESCRIPTION
                "A 16 octet field containing a unique identifier.  The
                identifier contains the following fields:
        
                   60 bit       nanosecond time (octets 1-7, low 4 bits of octet 8)
                   4  bit       version  (hi 4 bits of octet 8)
                   3  octet     0 (a variant field)
                   1  octet     hi 2bits 0, low 6bits clock sequence.
                   6  octet     MAC Address
        
                See Reference for generation of this value.
                "
            REFERENCE "ITU H225.0 Version 2"
            SYNTAX    OCTET STRING(SIZE(16))
        
        
        MmAliasTag::= TEXTUAL-CONVENTION
            STATUS       current
            DESCRIPTION
                "A tag to identify the type of the Alias address contained in
                 the MmAliasAddress data type.  The values correlate to the
                 AliasAddress defined in the H.225.0 V2 ITU protocol specification.
                 The tag indicates how to interpret the value of an AliasAddress
                 data type defined in that specification.
                                      AliasAddress contents
                         other        unknown
                         e164         MmE164String
                         h323Id       MmUtf8String
                         urlId        MmUtf8String containing a URL
                   transportId  MmTAddressTag, TAddress
                         emailId      MmUtf8String containing e-mail address
                         partyNumber  contains PartyNumber
               "
            SYNTAX    INTEGER {
                        other(0),
                        e164(1),
                        h323Id(2),
                        urlId(3),
                  transportId(4),
                        emailId(5),
                        partyNumber(6)
                      }
        
        
        MmAliasAddress ::= TEXTUAL-CONVENTION
            DISPLAY-HINT "512a"
            STATUS       current
            DESCRIPTION
                "A data type corresponding to AliasAddress defined in H.225.0.
                The value of an object of this type has the syntax and
                symantics identified by MmAliasTag.  An object defined as
                MmAliasAddress must have a corresponding MmAliasTag object."
            REFERENCE "ITU H225.0 Version 2"
            SYNTAX    OCTET STRING (SIZE(1..512))
        
        
        MmEndpointID ::= TEXTUAL-CONVENTION
            STATUS       current
            DESCRIPTION
                "A data type corresponding to EndpointIdentifier defined
        in H.225.0."
            REFERENCE "ITU H225.0 Version 2"
            SYNTAX    OCTET STRING (SIZE(1..128))
        
        MmGatekeeperID ::= TEXTUAL-CONVENTION
            STATUS       current
            DESCRIPTION
                "A data type corresponding to GatekeeperIdentifier defined in H.225.0."
            REFERENCE "ITU H225.0 Version 2"
            SYNTAX    OCTET STRING (SIZE(1..128))
        
        MmH225Crv::= TEXTUAL-CONVENTION
            STATUS       current
            DESCRIPTION
                "A data type corresponding to the Call Reference Value defined 		in H.225.0."
            REFERENCE "ITU H225.0 Version 2"
            SYNTAX    INTEGER (0..65535)
        
        --
        -- define OIDS for rooting mib modules under this tree
        --
        mmRtpRoot OBJECT-IDENTITY
            STATUS     current
            DESCRIPTION
                "Subtree for root of Mm Rtp mib."
            ::= { multimediaRegMib 1 }
        
        mmH323Root OBJECT-IDENTITY
            STATUS     current
            DESCRIPTION
                "Subtree for root of H323 mib modules."
            ::= { multimediaRegMib 2 }
        
        mmH320Root OBJECT-IDENTITY
            STATUS     current
            DESCRIPTION
                "Subtree for root of H320 mib modules."
            ::= { multimediaRegMib 3 }
        
        mmH245Root OBJECT-IDENTITY
            STATUS     current
            DESCRIPTION
                "Subtree for root of H245 mib modules."
            ::= { multimediaRegMib 4 }
        
        
        END
