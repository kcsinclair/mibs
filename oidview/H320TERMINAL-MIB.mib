-- extracted from draft-kajos-hmultimediamib-00.txt
-- at Mon Nov 15 17:11:06 1999

        H320TERMINAL-MIB DEFINITIONS ::= BEGIN
             IMPORTS
                  MODULE-IDENTITY, OBJECT-TYPE, Integer32,
                  experimental, TimeTicks, IpAddress, Unsigned32
                       FROM SNMPv2-SMI
                  DisplayString, DateAndTime, TEXTUAL-CONVENTION,
                  RowStatus
                       FROM SNMPv2-TC
                  MODULE-COMPLIANCE, OBJECT-GROUP
                       FROM SNMPv2-CONF
                  IsdnSignalingProtocol
                       FROM ISDN-MIB;  -- RFC2127
        
             h320TerminalMIB MODULE-IDENTITY
                  LAST-UPDATED "9808011400Z" -- August 1, 1998
                  ORGANIZATION "VTEL Corp."
                  CONTACT-INFO
                       "Joon Maeng
                       VTEL Corp.
                       Postal: 108 Wild Basin Rd.
                                 Austin, TX 78746
                                 USA
                       TEL: (512)437-4567
                       Email: Joon_Maeng@vtel.com"
                  DESCRIPTION
                       "This MIB module supports the functions of  an ITU
                       H.320 terminal"
                  REVISION "9808011400Z" -- August 1, 1998
                  DESCRIPTION
                       " The draft version of the H320 terminal mib"
             ::= {experimental 320 3} -- temporary OID.  TBD.
        
             -- Textual conventions (to be moved to overall TC at the top level)
        
             LineRates ::=TEXTUAL-CONVENTION
                  STATUS current
                  DESCRIPTION
                       "This object represents the line rate capabilities of
                       the H.320 entity. This includes the various line rates
                       that it supports. It is encoded as bits in
                       an octet string as follows:
        
                            Capability          Bit#
                             64 Kbits/s          0
                             2x64 Kbits/s   1

                            3x64 Kbits/s   2
                            4x64 Kbis/s    3
                            5x64 Kbits/s   4
                            6x64 Kbit/s    5
                            384 Kbits/s    6
                            2x384 Kbits/s  7
                            3x384 Kbits/s  8
                            5x384 Kbits/s  9
                            1536 Kbits/s   10
                            1920 Kbits/s   11
                            128 Kbits/s    12
                            92 Kbits/s     13
                            256 Kbits/s    14
                            320 Kbits/s    15
                            512 Kbits/s    16
                            768 Kbits/s    17
                            1152 Kbits/s   18
                            1452 Kbits/s   19        

                       Bits are numbered starting with the most
                       significant bit of the first byte being bit 0, the
                       least significant bit of the first byte being bit
                       7, the most significant bit of the second byte
                       being bit 8, and so on.  A one bit encodes that
                       the capability is supported, a zero bit encodes that
                       the capability is not supported."
        
                  SYNTAX    Integer32
        
             VideoFormats ::=TEXTUAL-CONVENTION
                  STATUS current
                  DESCRIPTION
                       "This object represents the video capabilities of the
                       H320 entity. This includes the various video algorithms
		        that it supports. It is encoded as bits in an octet string,
                       with the following definitions:
        
                            Capability          Bit #
        
                            h261CIFVideo   	0
                            h261QCIFVideo  	1
                            h263SQCIFVideo 	2
                            h263QCIFVideo  	3
                            h263CIFVideo   	4
                            h263CIF4Video  	5
                            h263CIF16Video 	6
                            h262SPMLSIFVideo  	7
                            h262SPML2SIFVideo   8
                            h262SPML4SIFVideo   9
                            h262MPMLSIFVideo    10
                            h262MPML2SIFVideo   11
                            h262MPML4SIFVideo   12

                       Bits are numbered starting with the most
                       significant bit of the first byte being bit 0, the
                       least significant bit of the first byte being bit
                       7, the most significant bit of the second byte
                       being bit 8, and so on.  A one bit encodes that
                       the capability is supported, a zero bit encodes that
                       the capability is not supported."
        
                  SYNTAX Integer32
        
             AudioTypes ::=TEXTUAL-CONVENTION
                  STATUS current
                  DESCRIPTION
                       "This object represents the audio capabilities of the
                       H320 entity. This includes the various audio algorithms that
                       it supports. It is encoded as bits in an octet string,
                       with the following definitions:
        
                                      Capability          Bit #
        
                                      g711-ALaw64KAudio   0
                                      g711-ALaw56KAudio   1
                                      g711-ULaw64KAudio   2
                                      g711-ULaw56KAudio   3
                                      g722-64KAudio       4
                                      g722-56KAudio       5
                                      g722-48KAudio       6
                                      g728Audio           7
                                      g723.1-5.3KAudio    8
                                      g723.1-6.4KAudio    9
                                      g729Audio           10
        
                       Bits are numbered starting with the most
                       significant bit of the first byte being bit 0, the
                       least significant bit of the first byte being bit
                       7, the most significant bit of the second byte
                       being bit 8, and so on.  A one bit encodes that
                       the capability is supported, a zero bit encodes that
                       the capability is not supported."
        
                  SYNTAX Integer32
        
             system              OBJECT IDENTIFIER ::= { h320TerminalMIB 1}
             configuration       OBJECT IDENTIFIER ::= { h320TerminalMIB 2}
             callSites           OBJECT IDENTIFIER ::= { h320TerminalMIB 3}
             control             OBJECT IDENTIFIER ::= { h320TerminalMIB 4}
        
             -- System description group.  Implementation of the system description
             -- group is mandatory. If an agent is not configured to have a
             -- value for  any of these variables, a string of length 0 is returned.
             -- (note: since we need the system description group for H320 terminal
             -- H323 terminal, H320 MCU and H.323 gateway, should we
             -- separate?)
        
             sysDescr OBJECT-TYPE
                       SYNTAX DisplayString (SIZE (0..255))
                       MAX-ACCESS read-only
                       STATUS current
                       DESCRIPTION
                       "A textual description of the terminal.  This value
	               should include the full name and version
                       identification of the system's hardware type and software."
                  ::= { system 1 }
        
             sysContact OBJECT-TYPE
                       SYNTAX DisplayString (SIZE (0..255))
                       MAX-ACCESS read-only
                       STATUS current
                       DESCRIPTION
                       "The textual identification of the contact person
                        for this managed node, together with information
                        on how to contact this person."
                  ::= { system 2 }
        
             syst35CountryCode OBJECT-TYPE
                       SYNTAX INTEGER (0..255)
                       MAX-ACCESS read-only
                       STATUS current
                       DESCRIPTION
                       "Country code, per T.35."
                  ::= { system 3 }
        
             syst35CountryCodeExtention OBJECT-TYPE
                       SYNTAX INTEGER (0..255)
                       MAX-ACCESS read-only
                       STATUS current
                       DESCRIPTION
                       "Assigned nationally."
                  ::= { system 4 }

             syst35ManufacturerCode OBJECT-TYPE
                       SYNTAX INTEGER (0..65535)
                       MAX-ACCESS read-only
                       STATUS current
                       DESCRIPTION
                       "Assigned nationally."
                  ::= { system 5 }
        
             sysLocation OBJECT-TYPE
                       SYNTAX DisplayString (SIZE (0..255))
                       MAX-ACCESS read-only
                       STATUS current
                       DESCRIPTION
                       "The physical location of this system. For instance, closet,
                       terminal room and so on"
                  ::= { system 6 }
        
             sysH320TerminalUptime OBJECT-TYPE
                       SYNTAX TimeTicks
                       MAX-ACCESS read-only
                       STATUS current
                       DESCRIPTION
                       "The amount of time (in hundredths of a second) since
                       this H320 terminal was last initialized.  Note that this
                       is different from sysUpTime in MIB-II [ ] because
                       sysUpTime is the uptime of the network management
                       portion of the system."
                  ::= { system 7 }
        
             sysH320TerminalLocalTime OBJECT-TYPE
                       SYNTAX DateAndTime
                       MAX-ACCESS read-write
                       STATUS current
                       DESCRIPTION
                                 "The local date and time of day."
             ::= { system 8 }
        
             sysH320TerminalDiagnostics OBJECT-TYPE
                       SYNTAX INTEGER { noResults(1), passed(2),
                                           hardwareFault(3), softwareFault(4) }
                       MAX-ACCESS read-only
                       STATUS current
                       DESCRIPTION
                                 "Indicates the results of the last diagnostic
			        routine performed.
        
                       noResults(1)        No diagnostic has yet been performed,
                       passed(2)      the diagnostic has been passed,
                       hardwareFault(3)    Hardware fault was detected,
                       softwareFault(4)    Software fault was detected."
             ::= { system 9 }
        
             sysH320TerminalStatus OBJECT-TYPE
                       SYNTAX INTEGER {
                       callSetup (1),
                                      callinProgress(2),
                                      callHangUp(3),
                                      idle(4)
                       }
                       MAX-ACCESS read-only
                       STATUS current
                       DESCRIPTION
                                 "General status of the terminal"
             ::= { system 10 }
        
             sysH320TerminalIfType OBJECT-TYPE
                  SYNTAX  Integer32
                  MAX-ACCESS  read-only
                  STATUS  current
                  DESCRIPTION
                       "The interface type on which this terminal can be called.
                       The interface type identified by this value is the
                       same type of as the ifType from Interface Table
                       in RFC1213. It should only use ifTypes - ds1, e1,
                       basicISDN, primaryISDN."
             ::= { system 11 }
        
        
             -- H320 terminal configuration
             -- This group contains objects to configure the H320 terminal.
        
             configH320TerminalSiteName OBJECT-TYPE
                       SYNTAX DisplayString (SIZE (0..255))
                       MAX-ACCESS read-write
                       STATUS current
                       DESCRIPTION
                       "Name of the site where the H320 terminal is located.
                       For instance, conference room 1 in Austin, or New York,
                       and so on. sysLocation provides the location information
                       for the maintenance people and this object inform where
                       the conference participants are."
             ::= { configuration 1 }
        
             configH320TerminalVideoSystem OBJECT-TYPE
                       SYNTAX INTEGER {
                       ntsc(1),
                       pal(2),
                       secam(3),
                       others(4)
                       }
                  MAX-ACCESS read-write
                       STATUS current
                       DESCRIPTION
                       "Video format standard used by the terminal"
                  ::= { configuration  2 }
        
             configH320TerminalIPAddress OBJECT-TYPE
                            SYNTAX IpAddress
                            MAX-ACCESS read-write
                            STATUS current
                            DESCRIPTION
                            "The IP address of the h.320 terminal."
                  ::= { configuration 3 }
        
        
             configH320ISDNSwitchType OBJECT-TYPE
                       SYNTAX IsdnSignalingProtocol
                  MAX-ACCESS read-write
                       STATUS current
                       DESCRIPTION
                       "Type of ISDN switch interface to the h.320 terminal.
                       Switch types are specified in ISDN-MIB. "
             ::= { configuration 4  }
        
             configH320ISDNAddrNumber OBJECT-TYPE
                  SYNTAX    Integer32
                  MAX-ACCESS read-write
                  STATUS current
                  DESCRIPTION
                       "The number of addresses that each terminal has."
             ::= { configuration 5 }
        
        
             configISDNAddrTable OBJECT-TYPE
                  SYNTAX    SEQUENCE OF ConfigISDNAddrEntry
                  MAX-ACCESS not-accessible
                  STATUS current
                  DESCRIPTION
                       "AN ISDN address table."
             ::= { configuration 6  }
        
             configISDNAddrEntry OBJECT-TYPE
                       SYNTAX ConfigISDNAddrEntry
                       MAX-ACCESS not-accessible
                       STATUS current
                       DESCRIPTION
                       "AN ISDN address row. "
                  INDEX { configH320AddrIndex }
             ::= { configISDNAddrTable 1  }
             ConfigISDNAddrEntry ::=
                       SEQUENCE {
                       configH320AddrIndex
                            INTEGER,
                       configH320ISDNAddress
                            DisplayString,
                       configH320ISDNSPID
                            DisplayString
                       }
        
             configH320AddrIndex OBJECT-TYPE
                       SYNTAX INTEGER (1..256)
                       MAX-ACCESS not-accessible
                       STATUS current
                       DESCRIPTION
                       "A unique value for each ISDN address entry.
                       the value ranges between 1 and the value of
                       cionfigISDNAddrNumber. "
             ::= { configISDNAddrEntry 1  }
        
             configH320ISDNAddress OBJECT-TYPE
                       SYNTAX DisplayString (SIZE (0..255))
                       MAX-ACCESS read-write
                       STATUS current
                       DESCRIPTION
                       "ISDN port address. "
             ::= { configISDNAddrEntry 2  }
        
             configH320ISDNSPID OBJECT-TYPE
                       SYNTAX DisplayString (SIZE (0..255))
                       MAX-ACCESS read-write
                       STATUS current
                       DESCRIPTION
                       "ISDN port SPID. "
             ::= { configISDNAddrEntry 3  }
        
             -- Site group
             -- This group contains the calling parameters for other video
             -- conferencing systems this system is capable of calling.
        
                  h320CallSiteNumber OBJECT-TYPE
                            SYNTAX  Integer32
                            MAX-ACCESS  read-write
                            STATUS  current
                       DESCRIPTION
                                 "The number of site entries that this system
                       contains."
                  ::= { callSites 1 }
        
             -- Site table
        
             -- This table is the collection of all video conferencing systems that
             -- this system can call and their associated parameters(phone numbers,
             -- line rates, etc.).
        
             h320XferNextIndex OBJECT-TYPE
                       SYNTAX  INTEGER (1..2147483647)
                       MAX-ACCESS  read-only
                       STATUS  current
                       DESCRIPTION
                       "Identifies the next value of h320SiteIndex to be used
                       in a row creation attempt for the h320CallSiteTable.
                       If  new rows cannot be created, this object will
                       have a value of 0."
                ::= { callSites 2 }
        
        
                   h320CallSiteTable OBJECT-TYPE
                       SYNTAX  SEQUENCE OF H320CallSiteEntry
                       MAX-ACCESS  not-accessible
                       STATUS  current
                       DESCRIPTION
                       "A list of video conferencing site entries.  The total
                       number of site entries is given by the value of
                       h320CallsiteNumber."
                   ::= { callSites 3 }
        
                   h320CallSiteEntry OBJECT-TYPE
                       SYNTAX  H320CallSiteEntry
                       MAX-ACCESS  not-accessible
                       STATUS  current
                       DESCRIPTION
                            "A video conference site row.  Rows are created by
                       an SNMP SET request setting the value of
                       h320SiteRowStatus to 'createandGo.  Rows are deleted
                       by an SNMP SET request setting the value of
                       h320SiteRowStatus to 'destroy'."
                       INDEX   { h320SiteIndex }
                  ::= { h320CallSiteTable 1 }
        
                   H320CallSiteEntry ::=
                  SEQUENCE {
                                 h320SiteIndex
                                      INTEGER,
                       h320SiteName
                            DisplayString,
                       h320SiteIfType
                            Integer32,
                       h320SiteLineRate
                            LineRates,
                       h320CallMode
                            INTEGER,

                       h320VideoMode
                            VideoFormats,
                       h320AudioMode
                            AudioTypes,
                       h320ISDNAddrNumber
                            Integer32,
                       h320SiteRowStatus
                            RowStatus
                  }
        
                  h320SiteIndex OBJECT-TYPE
                       SYNTAX  INTEGER (1..2147483647)
                       MAX-ACCESS  not-accessible
                       STATUS  current
                       DESCRIPTION
                            "A unique value for each video conference Site
                       entry. The value ranges between 1 and the value
                       of h320SiteNumber."
                  ::= { h320CallSiteEntry 1 }
        
                  h320SiteName OBJECT-TYPE
                       SYNTAX  DisplayString (SIZE (0..255))
                       MAX-ACCESS  read-create
                       STATUS  current
                       DESCRIPTION
                                 "A textual string assigning a name to a video
                       conference system."
                  ::= { h320CallSiteEntry 2 }
        
             h320SiteIfType OBJECT-TYPE
                  SYNTAX  Integer32
                  MAX-ACCESS  read-create
                  STATUS  current
                  DESCRIPTION
                       "The interface type on which this site can be called.
                       The interface type identified by this value is the
                       same type of as the ifType from Interface Table
                       in RFC1213. It should onlye use ifTypes - ds1, e1,
                       basicISDN, primaryISDN."
             ::= { h320CallSiteEntry 3 }
        
             h320SiteLineRate    OBJECT-TYPE
                  SYNTAX LineRates
                  MAX-ACCESS  read-create
                  STATUS  current
                  DESCRIPTION
                       "The line rate that the terminal can be called."
             ::= { h320CallSiteEntry 4 }
        
                  h320CallMode OBJECT-TYPE
                       SYNTAX  INTEGER{
                       manualConfig(1),
                       autoConfig(2)
                       }
                  MAX-ACCESS  read-create
                  STATUS  current
                       DESCRIPTION
                                 "1 means the remote terminal supports
                       the autoconfiguration.
                       2 means the manual configuration is required to
                       call the remote terminal.  In this case the,
                       following audio, video and data mode shall be
                       used for the manual configuration."
                   ::= { h320CallSiteEntry 5 }
        
                  h320VideoMode OBJECT-TYPE
                       SYNTAX  VideoFormats
                       MAX-ACCESS  read-create
                       STATUS  current
                       DESCRIPTION
                                 "A video mode for manual configuration."
                  ::= { h320CallSiteEntry 6 }
        
                  h320AudioMode OBJECT-TYPE
                       SYNTAX AudioTypes
                       MAX-ACCESS  read-create
                       STATUS  current
                       DESCRIPTION
                                 "An audio mode for manual configuration."
                  ::= { h320CallSiteEntry 7 }
        
             h320ISDNAddrNumber OBJECT-TYPE
                            SYNTAX  Integer32
                            MAX-ACCESS  read-create
                            STATUS  current
                       DESCRIPTION
                                 "The number of ISDN addresses needed to make a
                       call to the remote terminal."
                  ::= { h320CallSiteEntry 8 }
        
             h320SiteRowStatus OBJECT-TYPE
                  SYNTAX     RowStatus
                  MAX-ACCESS read-create
                  STATUS     current
                  DESCRIPTION
                            "The row status of the entry. This object is required
                       to create or delete rows administratively.
                            An agent implementing this object is not required to
                       support the values 'createAndWait' and 'notInService'."
             ::= { h320CallSiteEntry 9 }
        
             h320ISDNAddrTable OBJECT-TYPE
                       SYNTAX  SEQUENCE OF H320ISDNAddrEntry
                       MAX-ACCESS  not-accessible
                       STATUS  current
                       DESCRIPTION
                       "A list of ISDN addresses to call the remote site.
                       This is an extended table of the base table
                       h320CallSiteTable."
                  ::= { callSites 4 }
        
                  h320ISDNAddrEntry OBJECT-TYPE
                       SYNTAX  H320ISDNAddrEntry
                       MAX-ACCESS  not-accessible
                       STATUS  current
                       DESCRIPTION
                            "A video conference site row. Rows are created by
                       an SNMP SET request setting the value of
                       h320AddrRowStatus to 'createandGo.  Rows are deleted
                       by an SNMP SET request setting the value of
                       h320AddrRowStatus to 'destroy'"
                       INDEX   { h320SiteIndex, h320AddrIndex }
                  ::= { h320ISDNAddrTable 1 }
        
                  H320ISDNAddrEntry ::=
                  SEQUENCE {
                       h320AddrIndex
                            Unsigned32,
                       h320ISDNAddress
                            DisplayString,
                       h320AddrRowStatus
                            RowStatus
                       }
        
                  h320AddrIndex OBJECT-TYPE
                       SYNTAX  Unsigned32 (1..24)
                       MAX-ACCESS  not-accessible
                       STATUS  current
                       DESCRIPTION
                            "A unique value for each ISDN address entry.
                       The value ranges between 1 and the value
                       of h320AddrNumberin the base table."
                   ::= { h320ISDNAddrEntry 1 }
        
                  h320ISDNAddress OBJECT-TYPE
                       SYNTAX  DisplayString (SIZE (0..255))
                       MAX-ACCESS  read-create
                       STATUS  current
                       DESCRIPTION
                             "A textual string assigning an address of the
                       conference system."
                   ::= { h320ISDNAddrEntry 2 }
        
             h320AddrRowStatus OBJECT-TYPE
                  SYNTAX     RowStatus
                  MAX-ACCESS read-create
                  STATUS     current
                  DESCRIPTION
                            "The row status of the entry. This object is required
                       to create or delete rows administratively.
                            An agent implementing this object is not required to
                       support the values 'createAndWait' and 'notInService'."
             ::= { h320ISDNAddrEntry 3 }
        
             -- Terminal control group
             -- This group contains variables used to control a H.320 terminal.        
             controlH320TerminalAdmin OBJECT-TYPE
                     SYNTAX INTEGER { run(1), reset(2), diagnose(3), stop(4) }
                       MAX-ACCESS read-write
                       STATUS current
                       DESCRIPTION
                            "The desired state of the H320 terminal.
                       Setting the value if this object to these values
                       will have the following actions:
                       run(1)         The H320 terminal will enter the run state,
                       reset(2)       The H320 terminal will reset,
                       diagnose(3)    Will activate the diagnostic routine,
                       stop(4)        Will halt the H320 terminal."
             ::= { control 1 }
        
             controlH320TerminalCallSetUp  OBJECT-TYPE
                  SYNTAX  Integer32
                  MAX-ACCESS  read-write
                  STATUS  current
                  DESCRIPTION
                       "Dial another video conference terminal. Set this value
                       to the index of the site of the video conference site
                       you want to dial in the Site Table in the
                       h320CallSignalingMIB and the system will be dialed."
             ::= { control 2 }
        
             controlH320TerminalCallHangup OBJECT-TYPE
                  SYNTAX  Integer32
                  MAX-ACCESS  read-write
                  STATUS  current
                  DESCRIPTION
                       "Hang up the video conference call in progress now."
             ::= { control 3 }
             controlH320EnableLocalLoopback  OBJECT-TYPE
                  SYNTAX  INTEGER {
                            enable(1),
                            disable(2)
                            }
                  MAX-ACCESS  read-write
                  STATUS  current
                  DESCRIPTION
                       "Enable or disable local loop back on a video
                       conference system. Local loopbacks loop back the
                       audio, video and data streams in a call. Once looped
                       back, a new call will show up and the user can
                       observe the audio/video/data rates to assure that
                       these components are working properly."
             ::= { control 4 }
        
             controlH320EnableRemoteLoopback  OBJECT-TYPE
                  SYNTAX  INTEGER{
                            enable(1),
                            disable(2)
                            }
                  MAX-ACCESS  read-write
                  STATUS  current
                  DESCRIPTION
                       "Enable or disable remote loop back on a video
                       conference system. Remote loopbacks loop back the
                       audio and video streams from the remote system in
                       a call.. When the remote system calls in, a new call
                       will show and the user can observe the audio/video/data
                       rates to assure that these components are coming in
                       properly from the remote system."
             ::= { control 5 }
        
             --
             -- CONFORMANCE
             --
        
             h320TerminalMIBConfs     OBJECT IDENTIFIER ::= {
        h320TerminalMIB 5 }
             h320TerminalMIIBGroups   OBJECT IDENTIFIER ::= {
        h320TerminalMIBConfs 1
        }
             h320TerminalMIBCompl     OBJECT IDENTIFIER ::= {
        h320TerminalMIBConfs 2
        }
        
             --
             -- Groups for conformance
             --
        
             h320TerminalDesrGroup    OBJECT-GROUP
                  OBJECTS {
                       sysDescr,
                       sysContact,
                       syst35CountryCode,
                       syst35CountryCodeExtention,
                       syst35ManufacturerCode,
                       sysLocation,
                       sysH320TerminalUptime,
                       sysH320TerminalLocalTime,
                       sysH320TerminalDiagnostics,
                       sysH320TerminalStatus,
                       sysH320TerminalIfType
                                 }
                  STATUS current
                  DESCRIPTION
                       "A collection of objects providing the description of
                       the terminal"
             ::= { h320TerminalMIIBGroups 1}
        
        
        
             h320TerminalConfgGroup  OBJECT-GROUP
                  OBJECTS {
                       configH320TerminalSiteName,
                       configH320TerminalVideoSystem,
                            configH320TerminalIPAddress,
                       configH320ISDNSwitchType,
                       configH320ISDNAddrNumber,
                       configH320ISDNAddress,
                       configH320ISDNSPID
                       }
                  STATUS current
                  DESCRIPTION
                       "A collection of objects providing the ability to
                       configure the terminal"
             ::= { h320TerminalMIIBGroups 2}
        
             h320TerminalCallSitesGroup OBJECT-GROUP
                  OBJECTS   {
                            h320CallSiteNumber,
                       h320XferNextIndex,
                       h320SiteName,
                       h320SiteIfType,
                       h320SiteLineRate,
                       h320CallMode,
                       h320VideoMode,
                       h320AudioMode,
                       h320ISDNAddrNumber,
                       h320SiteRowStatus,
                       h320ISDNAddress,
                       h320AddrRowStatus
                  }
                  STATUS current
                  DESCRIPTION
                       "A collection of objects providing the information

        		about the site the terminal can call"
             ::= { h320TerminalMIIBGroups 3}
        
        
             h320TerminalControlGroup  OBJECT-GROUP
                  OBJECTS {
                       controlH320TerminalAdmin,
                       controlH320TerminalCallSetUp,
                       controlH320TerminalCallHangup,
                       controlH320EnableLocalLoopback,
                       controlH320EnableRemoteLoopback
                       }
                  STATUS current
                  DESCRIPTION
                       "A collection of objects providing the ability to
                       invoke terminal functions"
             ::= { h320TerminalMIIBGroups 4}
        
             h320TErminalCompliance   MODULE-COMPLIANCE
                  STATUS    current
                  DESCRIPTION
                       "The set of objects required for compliance"
                  -- unconditionally mandatory groups
                  MODULE
                       MANDATORY-GROUPS     {
                            h320TerminalDesrGroup,
                            h320TerminalConfgGroup,
                            h320TerminalCallSitesGroup
             }
        
                  -- optional group
                  GROUP          h320TerminalControlGroup
                  DESCRIPTION
                       "This group is optional.  H320 entities under a
                       centralized control via  a network management protocol
                       are strongly encouraged to use this group to enable
                       the remote control functions such as dialing and hang up."
             ::= { h320TerminalMIBCompl 1 }
        
        END
