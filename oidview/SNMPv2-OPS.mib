-- extracted from draft-irtf-nmrg-smi-ops-00.txt
-- at Fri Dec 24 21:43:22 1999

SNMPv2-OPS DEFINITIONS ::= BEGIN

IMPORTS ObjectName FROM SNMPv2-SMI;

  OPERATION-TYPE MACRO ::=
  BEGIN
    TYPE NOTATION ::=
                  ArgumentsPart
                  ErrorsPart
                  ResultsPart
                  CreatesPart
                  DeletesPart
                  "STATUS" Status
                  "DESCRIPTION" Text
                  ReferPart

    VALUE NOTATION ::=
                  value(VALUE ObjectName)

    ArgumentsPart ::=
                  "ARGUMENTS" "{" Parameters "}"
                | empty

    ErrorsPart ::=
                  "ERRORS" "{" NamedNumbers "}" -- INTEGER enumerations
                | empty

    ResultsPart ::=
                  "RESULTS" "{" Parameters "}"
                | empty

    CreatesPart ::=
                  "CREATES" "{" Rows "}"
                | empty

    DeletesPart ::=
                  "DELETES" "{" Rows "}"
                | empty

    Parameters ::=
                  Parameter
                | Parameters "," Parameter

    Parameter ::=
                  identifier Syntax

    Syntax ::=
                  type

                | "BITS" "{" NamedBits "}"

    NamedBits ::=
                  NamedBit
                | NamedBits "," NamedBit

    NamedBit ::=
                  identifier "(" number ")" -- number is nonnegative

    NamedNumbers ::=
                  NamedNumber
                | NamedNumbers "," NamedNumber

    NamedNumber ::=
                  identifier "(" number ")"

    Rows ::=
                  Row
                | Rows "," Row
    Row ::=
                  value(ObjectName)

    Status ::=
                  "current"
                | "deprecated"
                | "obsolete"

    ReferPart ::=
                  "REFERENCE" Text
                | empty

    -- a character string as defined in [RFC2578]
    Text ::= value(IA5String)
  END
END

-- 
--    Copyright (C) The Internet Society (1999). All Rights Reserved.
-- 
--    This document and translations of it may be copied and furnished to
--    others, and derivative works that comment on or otherwise explain it
--    or assist in its implementation may be prepared, copied, published
--    and distributed, in whole or in part, without restriction of any
--    kind, provided that the above copyright notice and this paragraph are
--    included on all such copies and derivative works.  However, this
--    document itself may not be modified in any way, such as by removing
--    the copyright notice or references to the Internet Society or other
--    Internet organizations, except as needed for the  purpose of
--    developing Internet standards in which case the procedures for
--    copyrights defined in the Internet Standards process must be
--    followed, or as required to translate it into languages other than
--    English.
-- 
--    The limited permissions granted above are perpetual and will not be
--    revoked by the Internet Society or its successors or assigns.
-- 
--    This document and the information contained herein is provided on an
--    "AS IS" basis and THE INTERNET SOCIETY AND THE INTERNET ENGINEERING
--    TASK FORCE DISCLAIMS ALL WARRANTIES, EXPRESS OR IMPLIED, INCLUDING
--    BUT NOT LIMITED TO ANY WARRANTY THAT THE USE OF THE INFORMATION
--    HEREIN WILL NOT INFRINGE ANY RIGHTS OR ANY IMPLIED WARRANTIES OF
--    MERCHANTABILITY OR FITNESS FOR A PARTICULAR PURPOSE.
