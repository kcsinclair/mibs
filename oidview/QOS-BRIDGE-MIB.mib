-- extracted from draft-smith-bridge-qosmib-00.txt
-- at Tue Jun 13 07:07:24 2000

QOS-BRIDGE-MIB DEFINITIONS ::= BEGIN

    IMPORTS
    OBJECT-TYPE, MODULE-IDENTITY, mib-2
         FROM SNMPv2-SMI
    TEXTUAL-CONVENTION, RowStatus
         FROM SNMPv2-TC
    MODULE-COMPLIANCE, OBJECT-GROUP
         FROM SNMPv2-CONF
    dot1qVlanIndex
        FROM Q-BRIDGE-MIB;

dot1dQosMib MODULE-IDENTITY
    LAST-UPDATED "200006070000Z"
    ORGANIZATION "Extreme Networks"
    CONTACT-INFO
       "       Andrew Smith (author)
               Extreme Networks
               3585 Monroe St.
               Santa Clara, CA 95051, USA
       E-mail: andrew@extremenetworks.com"
    DESCRIPTION
       "This MIB defines the additional objects necessary to manage the
       Quality-of-Service aspects of a bridge device that uses the
       IETF's Differentiated Services Architecture described in RFC 2475
       and the Conceptual Model for DiffServ Routers in draft-ietf-
       diffserv-model-03.txt. It is to be used in conjunction with the
       Diffserv MIB described in draft-ietf-diffserv-mib-03.txt."
    REVISION "200006070000Z"
    DESCRIPTION
       "Initial version, published as RFC xxxx."
    ::= { mib-2 12346 }  -- anybody who uses this unassigned
                         -- number deserves the wrath of IANA

dot1dQosObjects        OBJECT IDENTIFIER ::= { dot1dQosMib 1 }
dot1dQosTables         OBJECT IDENTIFIER ::= { dot1dQosMib 2 }
dot1dQosMIBConformance OBJECT IDENTIFIER ::= { dot1dQosMib 3 }


-- These textual conventions have no effect on either the syntax
-- nor the semantics of any managed object.  Objects defined
-- using this convention are always encoded by means of the
-- rules that define their primitive type.
Dot1dUserPri ::= TEXTUAL-CONVENTION
    DISPLAY-HINT "d"
    STATUS   current
    DESCRIPTION
       "The IEEE 802.1 user_priority that may be used for discriminating
       or marking a traffic stream."
    SYNTAX   INTEGER (0..7)

--
-- IEEE 802.1D user_priority Table
--

dot1dQosUserPriTable OBJECT-TYPE
    SYNTAX      SEQUENCE OF Dot1dQosUserPriEntry
    MAX-ACCESS   not-accessible
    STATUS      current
    DESCRIPTION
       "A table of user_priority entries that each signifies a traffic
       class in 802.1D bridges. All entries exist in this table at all
       times.  Its entries may be used as destinations for
       diffServClassifierFilter pointers for traffic classification
       purposes and for diffServActionSpecific pointers for traffic
       marking purposes."
    REFERENCE
        "[MODEL] section 4.2.4"
    ::= { dot1dQosTables 1 }

dot1dQosUserPriEntry OBJECT-TYPE
    SYNTAX       Dot1dQosUserPriEntry
    MAX-ACCESS   not-accessible
    STATUS      current
    DESCRIPTION
       "An entry that describes a single 802.1D user_priority filter."
    INDEX { dot1dQosUserPri }
    ::= { dot1dQosUserPriTable 1 }

Dot1dQosUserPriEntry ::= SEQUENCE {
    dot1dQosUserPri       Dot1dUserPri
}

dot1dQosUserPri OBJECT-TYPE
    SYNTAX         Dot1dUserPri
    MAX-ACCESS     read-only
    STATUS        current
    DESCRIPTION
       "A user_priority value for the filter. Filters may be shared by
       multiple interfaces in the same system."
    ::= { dot1dQosUserPriEntry 1 }

--
-- IEEE 802.1Q Vlan Classification Table
--

dot1dQosVlanClfrTable OBJECT-TYPE
    SYNTAX      SEQUENCE OF Dot1dQosVlanClfrEntry
    MAX-ACCESS   not-accessible
    STATUS      current
    DESCRIPTION
       "A table of VLAN entries for use in QoS classification in
       bridges.  Its entries may be used as destinations for
       diffServClassifierFilter pointers for traffic classification
       purposes."
    REFERENCE
        "[MODEL] section 4.2.4, [BRIDGEMIB] dot1qVlanCurrentTable."
    ::= { dot1dQosTables 2 }

dot1dQosVlanClfrEntry OBJECT-TYPE
    SYNTAX       Dot1dQosVlanClfrEntry
    MAX-ACCESS   not-accessible
    STATUS      current
    DESCRIPTION
       "An entry that describes a classifier element for a single 802.1Q
       VLAN."
    INDEX { dot1qVlanIndex }
    ::= { dot1dQosVlanClfrTable 1 }

Dot1dQosVlanClfrEntry ::= SEQUENCE {
    dot1dQosVlanStatus   RowStatus
}

dot1dQosVlanStatus OBJECT-TYPE
    SYNTAX       RowStatus
    MAX-ACCESS   read-create
    STATUS       current
    DESCRIPTION
       "The RowStatus variable controls the activation, deactivation, or
       deletion of a filter for a VLAN for use in QoS classification.

       Note that, even though this table is indexed by dot1qVlanIndex,
       this does not imply that there must be an equivalent entry in
       either dot1qVlanCurrentTable or dot1qVlanStaticTable."
    ::= { dot1dQosVlanClfrEntry 1 }

--
-- Usage of this MIB module in conjunction with the Diffserv MIB.
--
--    Classifiers - this MIB defines two new classifier filter
--       element types:
--
--       - to compare the IEEE 802.1D user_priority value
--         from a packet. Classifier elements are each one of the
--         entries from dot1dQosUserPriTable and may be pointed to
--         by diffServClassifierFilter values.
--
--       - to compare the IEEE 802.1Q VLAN with which a packet is
--         associated. Note that this classification is considered
--         to take place on all packets that pass through this
--         particular element regardless of their incoming or outgoing
--         tagged/untagged status: i.e. the QoS classifier is considered
--         to take place "after" the IEEE 802.1Q VLAN ingress rules have
--         been applied. Therefore, the VLAN identifier implied is the
--         one which the Bridge MIB considers to be attached to each
--         packet. Such classifier filter elements are each one of the
--         entries from dot1dQosVlanClfrTable and may be pointed to by
--         diffServClassifierFilter values.
--
--    Meters - this MIB includes no new definitions or usage for Meters.
--
--    Actions - this MIB includes no new definitions for Actions.
--
--       A Marker action, to mark packets with an 802.1D user_priority
--       value, may be defined by creating a diffServActionEntry
--       which has a diffServActionSpecific pointing at one of the
--       entries in dot1dQosUserPriTable. Note that this remarking
--       action, which is considered to take place for all packets that
--       pass through this particular element regardless of their
--       incoming or outgoing tagged/untagges status, is not one that is
--       supported by the standard IEEE 802.1D model.
--
--       Note that remarking with a VLAN-ID is not considered to be a
--       QoS action - facilities for handling VLAN-ID tags in
--       accordance with IEEE 802.1Q are provided in the Bridge MIB
--       [BRIDGEMIB].
--
--    Queues, Algorithmic Droppers and Schedulers - this MIB includes no
--       new definitions or usage for these elements.
--
--
-- MIB Compliance statements.
--

dot1dQosMIBCompliances OBJECT IDENTIFIER ::= { dot1dQosMIBConformance 1 }
dot1dQosMIBGroups      OBJECT IDENTIFIER ::= { dot1dQosMIBConformance 2 }

dot1dQosMIBCompliance MODULE-COMPLIANCE
    STATUS current
    DESCRIPTION
       "This MIB may be implemented as a read-only or as a read-create
       MIB."
    MODULE -- This Module
    MANDATORY-GROUPS { dot1dQosMIBUserPriGroup }

    GROUP dot1dQosMIBVlanGroup
    DESCRIPTION
       "This group is mandatory for devices that implement QoS
       classification based upon VLAN assignment."

    OBJECT dot1dQosVlanStatus
    MIN-ACCESS read-only
    DESCRIPTION
       "Write access is not required."

    ::= { dot1dQosMIBCompliances 1 }


dot1dQosMIBUserPriGroup OBJECT-GROUP
    OBJECTS { dot1dQosUserPri }
    STATUS current
    DESCRIPTION
       "The user_priority Group defines the MIB Objects that represent
       802.1D user_priority values and describe a table of entries that
       may be used as destinations for diffServClassifierFilter and
       diffServActionSpecific pointers."
    ::= { dot1dQosMIBGroups 1 }

dot1dQosMIBVlanGroup OBJECT-GROUP
    OBJECTS { dot1dQosVlanStatus }
    STATUS current
    DESCRIPTION
       "The VLAN Group defines the MIB Objects that represent VLANs and
       describe a table of entries that may be used as destinations for
       diffServClassifierFilter pointers."
    ::= { dot1dQosMIBGroups 2 }

END
