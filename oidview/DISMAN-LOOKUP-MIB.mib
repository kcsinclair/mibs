-- extracted from draft-ietf-disman-remops-mib-04.txt
-- at Mon Nov 15 17:10:44 1999

  DISMAN-LOOKUP-MIB DEFINITIONS ::= BEGIN

  IMPORTS
      MODULE-IDENTITY, OBJECT-TYPE, Integer32,
      experimental, Unsigned32
          FROM SNMPv2-SMI                  -- RFC1902
      RowStatus
          FROM SNMPv2-TC                   -- RFC1903
      MODULE-COMPLIANCE, OBJECT-GROUP
          FROM SNMPv2-CONF                 -- RFC1904
      SnmpAdminString
          FROM SNMP-FRAMEWORK-MIB          -- RFC2271
      HostAddressType, HostAddress
          FROM DISMAN-PING-MIB;

   lookupMIB MODULE-IDENTITY
      LAST-UPDATED "9904230000Z"
      ORGANIZATION "IETF Distributed Management Working Group"
      CONTACT-INFO
          "Kenneth White

          International Business Machines Corporation
          Network Computing Software Division
          Research Triangle Park, NC, USA

          E-mail: wkenneth@us.ibm.com"
      DESCRIPTION
          "The Lookup MIB (DISMAN-LOOKUP-MIB) enables determination
          of either the name corresponding to a host address or of
          the address associated with a host name at a remote host."
      ::= { experimental 84 3 }

   -- Top level structure of the MIB

   lookupObjects        OBJECT IDENTIFIER ::= { lookupMIB 1 }
   lookupConformance    OBJECT IDENTIFIER ::= { lookupMIB 2 }

   -- Simple Object Definitions

   lookupMaxConcurrentRequests OBJECT-TYPE
      SYNTAX      Integer32 (1..100)
      MAX-ACCESS  read-write
      STATUS      current
      DESCRIPTION
         "The maximum number of concurrent active lookup requests
         that are allowed within an agent implementation."
      DEFVAL { 10 }
      ::= { lookupObjects 1 }

   lookupPurgeTime OBJECT-TYPE
      SYNTAX      Integer32 (0..86400)
      UNITS       "seconds"
      MAX-ACCESS  read-write
      STATUS      current
      DESCRIPTION
         "The amount of time to wait before automatically
         deleting an entry in the lookupTable
         after the lookup operation represented by an
         lookupEntry has completed."
      DEFVAL { 900 }  -- 15 minutes as default
      ::= { lookupObjects 2 }

   -- Lookup Table

   lookupTable OBJECT-TYPE
      SYNTAX      SEQUENCE OF LookupEntry
      MAX-ACCESS  not-accessible
      STATUS      current
      DESCRIPTION
          "Defines the Lookup Table for provide
          the capability of performing a lookup operation,
          gethostbyname or gethostbyaddr, from a remote host."
     ::= { lookupObjects 3 }

   lookupEntry OBJECT-TYPE
      SYNTAX      LookupEntry
      MAX-ACCESS  not-accessible
      STATUS      current
      DESCRIPTION
          "Defines an entry in the lookupTable."
      INDEX {
               lookupOwnerIndex,
               lookupOperationName,
               lookupAddressType,
               lookupAddress
            }
      ::= { lookupTable 1 }

   LookupEntry ::=
      SEQUENCE {
          lookupOwnerIndex         SnmpAdminString,
          lookupOperationName      SnmpAdminString,
          lookupAddressType        HostAddressType,
          lookupAddress            HostAddress,
          lookupOperStatus         INTEGER,
          lookupResultType         HostAddressType,
          lookupResult             HostAddress,
          lookupTime               Unsigned32,
          lookupRc                 Unsigned32,
          lookupRowStatus          RowStatus
      }

   lookupOwnerIndex OBJECT-TYPE
      SYNTAX      SnmpAdminString (SIZE(0..32))
      MAX-ACCESS  not-accessible
      STATUS      current
      DESCRIPTION
         "To facilitate the provisioning of access control by a security
         administrator using the View-Based Access Control Model (RFC 2275,
         VACM) for tables in which multiple users may need to independently
         create or modify entries, the initial index is used as an 'owner
         index'.  Such an initial index has a syntax of SnmpAdminString,
         and can thus be trivially mapped to a securityName or groupName
         as defined in VACM, in accordance with a security policy.

         All entries in that table belonging to a particular user will
         have the same value for this initial index.  For a given user's
         entries in a particular table, the object identifiers for the
         information in these entries will have the same subidentifiers
         (except for the 'column' subidentifier) up to the end of the
         encoded owner index. To configure VACM to permit access to this
         portion of the table, one would create vacmViewTreeFamilyTable
         entries with the value of vacmViewTreeFamilySubtree including the
         owner index portion, and vacmViewTreeFamilyMask 'wildcarding' the
         column subidentifier.  More elaborate configurations are
         possible."
      ::= { lookupEntry 1 }

   lookupOperationName OBJECT-TYPE
      SYNTAX      SnmpAdminString
      MAX-ACCESS  not-accessible
      STATUS      current
      DESCRIPTION
          "The name of a lookup operation.  This is locally unique, within
          the scope of an lookupOwnerIndex."
      ::= { lookupEntry 2 }

   lookupAddressType OBJECT-TYPE
      SYNTAX      HostAddressType
      MAX-ACCESS  not-accessible
      STATUS      current
      DESCRIPTION
          "Specifies the type of address for either performing a
          gethostbyname or a gethostbyaddr call at a remote host.
          Specification of a dnsName(2) implies that gethostbyname
          should be called to return a numeric address.
          Use of a value of either ipv4(3) or ipv6(4) implies that
          a gethostbyaddr call should occur to return the symbolic
          name of a remote host."
      ::= { lookupEntry 3 }

   lookupAddress OBJECT-TYPE
      SYNTAX      HostAddress
      MAX-ACCESS  not-accessible
      STATUS      current
      DESCRIPTION
          "Specifies the address used for a DNS Lookup at a
          remote host.  The corresponding lookupAddressType
          objects determines its type as well as the function
          that can be requested."
      ::= { lookupEntry 4 }

   lookupOperStatus OBJECT-TYPE
      SYNTAX      INTEGER {
                            up(1),    -- operation is in progress
                            down(2)   -- operation has stopped
                          }
      MAX-ACCESS  read-only
      STATUS      current
      DESCRIPTION
          "Reflects the operational state of an lookupEntry:

             up(1)    - Operation is active.
             down(1)  - Operation has stopped."
      ::= { lookupEntry 5 }

   lookupResultType OBJECT-TYPE
      SYNTAX      HostAddressType
      MAX-ACCESS  read-only
      STATUS      current
      DESCRIPTION
          "Indicates the type of result of a remote lookup
          operation.  A value of none(1) implies that
          either the operation hasn't been started or that
          it has failed."
      ::= { lookupEntry 6 }

   lookupResult OBJECT-TYPE
      SYNTAX      HostAddress
      MAX-ACCESS  read-only
      STATUS      current
      DESCRIPTION
          "Reflects the results of a remote lookup operation
          as per the value of lookupResultType."
      ::= { lookupEntry 7 }

   lookupTime OBJECT-TYPE
      SYNTAX      Unsigned32
      UNITS       "seconds"
      MAX-ACCESS  read-only
      STATUS      current
      DESCRIPTION
          "Reports the number of seconds that a lookup
          operation required to be completed at a remote host.
          Completed means operation failure as well as
          success."
      ::= { lookupEntry 8 }

   lookupRc OBJECT-TYPE
      SYNTAX      Unsigned32
      MAX-ACCESS  read-only
      STATUS      current
      DESCRIPTION
          "The system specific return code from a lookup
          operation.  All implementations must return a value
          of 0 for this object when the remote lookup
          operation succeeds.  A non-zero value for this
          objects indicates failure.  It is recommended that
          implementations that support errno use it as the
          value of this object to aid a management
          application in determining the cause of failure."
      ::= { lookupEntry 9 }

   lookupRowStatus OBJECT-TYPE
      SYNTAX      RowStatus
      MAX-ACCESS  read-create
      STATUS      current
      DESCRIPTION
          "This object allows entries to be created and deleted
          in the lookupTable.

          A remote DNS Lookup operation is started when an
          entry in this table is created via an SNMP SET
          request and the entry is activated.  This
          can occur by setting the value of this object
          to CreateAndGo(4) during row creation or
          by setting this object to active(1) after
          the row is created.

          A remote lookup operation starts when its entry
          first becomes active(1).  Transitions in and
          out of active(1) state have no effect on the
          operational behavior of a remote lookup
          operation, with the exception that deletion of
          an entry in this table by setting its RowStatus
          object to destroy(6) will stop an active
          remote DNS Lookup operation.

          The operational state of a remote lookup operation
          can be determined by examination of it's
          lookupOperStatus object."
      REFERENCE
          "RFC 2579, 'Textual Conventions for SMIv2.'"
      ::= { lookupEntry 10 }

   -- Conformance information
   -- Compliance statements

   lookupCompliances OBJECT IDENTIFIER ::= { lookupConformance 1 }
   lookupGroups      OBJECT IDENTIFIER ::= { lookupConformance 2 }

   -- Compliance statements
   lookupCompliance MODULE-COMPLIANCE
      STATUS  current
      DESCRIPTION
              "The compliance statement for the DISMAN-LOOKUP-MIB."
      MODULE  -- this module
          MANDATORY-GROUPS {
                              lookupGroup
                            }

          OBJECT lookupMaxConcurrentRequests
          MIN-ACCESS  read-only
          DESCRIPTION
              "The agent is not required to support a SET
              operation to this object."

          OBJECT lookupPurgeTime
          MIN-ACCESS  read-only
          DESCRIPTION
              "The agent is not required to support a SET
              operation to this object."
      ::= { lookupCompliances 1 }

   -- MIB groupings

   lookupGroup OBJECT-GROUP
     OBJECTS {
               lookupMaxConcurrentRequests,
               lookupPurgeTime,
               lookupOperStatus,
               lookupResultType,
               lookupResult,
               lookupTime,
               lookupRc,
               lookupRowStatus
             }
     STATUS  current
     DESCRIPTION
         "The group of objects that comprise the remote
         Lookup operation."
      ::= { lookupGroups 1 }

  END

-- 
-- Copyright (C) The Internet Society (1997).  All Rights Reserved.
-- 
-- This document and translations of it may be copied and furnished to
-- others, and derivative works that comment on or otherwise explain it or
-- assist in its implementation may be prepared, copied, published and
-- distributed, in whole or in part, without restriction of any kind,
-- provided that the above copyright notice and this paragraph are included
-- on all such copies and derivative works.  However, this document itself
-- may not be modified in any way, such as by removing the copyright notice
-- or references to the Internet Society or other Internet organizations,
-- except as needed for the purpose of developing Internet standards in
-- which case the procedures for copyrights defined in the Internet
-- Standards process must be followed, or as required to translate it into
-- languages other than English.
-- 
-- The limited permissions granted above are perpetual and will not be
-- revoked by the Internet Society or its successors or assigns.
-- This document and the information contained herein is provided on an "AS
-- IS" basis and THE INTERNET SOCIETY AND THE INTERNET ENGINEERING TASK
-- FORCE DISCLAIMS ALL WARRANTIES, EXPRESS OR IMPLIED, INCLUDING BUT NOT
-- LIMITED TO ANY WARRANTY THAT THE USE OF THE INFORMATION HEREIN WILL NOT
-- INFRINGE ANY RIGHTS OR ANY IMPLIED WARRANTIES OF MERCHANTABILITY OR
-- FITNESS FOR A PARTICULAR PURPOSE.
