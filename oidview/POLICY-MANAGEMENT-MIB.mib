-- extracted from draft-ietf-snmpconf-pm-03.txt
-- at Fri Oct 13 07:11:17 2000

POLICY-MANAGEMENT-MIB DEFINITIONS ::= BEGIN
IMPORTS
    MODULE-IDENTITY, OBJECT-TYPE,
    Counter32, Integer32, Gauge32, Unsigned32,
    experimental                                 FROM SNMPv2-SMI
    RowStatus, RowPointer, TEXTUAL-CONVENTION    FROM SNMPv2-TC
    MODULE-COMPLIANCE, OBJECT-GROUP              FROM SNMPv2-CONF;

--  Policy-Based Management MIB

policyMgt MODULE-IDENTITY
    LAST-UPDATED "200010111500Z"  -- October 11, 2000
    ORGANIZATION "IETF SNMP Configuration Working Group"
    CONTACT-INFO
        "Steve Waldbusser

        Phone: +1-650-948-6500
        Fax:   +1-650-745-0671
        Email: waldbusser@nextbeacon.com

        Jon Saperia
        JDS Consulting, Inc.
        174 Chapman St.
        Watertown MA 02472-3063
        USA
        Phone: +1-617-744-1079
        Fax:   +1-617-249-0874
        Email: saperia@jdscons.com

        Thippanna Hongal
        Riverstone Networks, Inc.
        5200 Great America Parkway
        Santa Clara, CA, 95054
        USA

        Phone: +1-408-878-6562
        Fax:   +1-408-878-6501
        Email: hongal@riverstonenet.com"
    DESCRIPTION
        "The MIB module for rule-based configuration of SNMP
        infrastructures."

    REVISION "200010111500Z"    -- October 11, 2000
    DESCRIPTION
        "The original version of this MIB, published as RFCXXXX."
    ::= { experimental 107 }

UTF8String ::= TEXTUAL-CONVENTION
    DISPLAY-HINT "255a"
    STATUS       current
    DESCRIPTION
        "An octet string containing information typically in
        human-readable form.

        To facilitate internationalization, this
        information is represented using the ISO/IEC
        IS 10646-1 character set, encoded as an octet
        string using the UTF-8 transformation format
        described in [RFC2279].

        Since additional code points are added by
        amendments to the 10646 standard from time
        to time, implementations must be prepared to
        encounter any code point from 0x00000000 to
        0x7fffffff.  Byte sequences that do not
        correspond to the valid UTF-8 encoding of a
        code point or are outside this range are
        prohibited.

        The use of control codes should be avoided.

        When it is necessary to represent a newline,
        the control code sequence CR LF should be used.

        For code points not directly supported by user
        interface hardware or software, an alternative
        means of entry and display, such as hexadecimal,
        may be provided.

        For information encoded in 7-bit US-ASCII,
        the UTF-8 encoding is identical to the
        US-ASCII encoding.

        UTF-8 may require multiple bytes to represent a
        single character / code point; thus the length
        of this object in octets may be different from
        the number of characters encoded.  Similarly,
        size constraints refer to the number of encoded
        octets, not the number of characters represented
        by an encoding.

        Note that when this TC is used for an object that
        is used or envisioned to be used as an index, then
        a SIZE restriction MUST be specified so that the
        number of sub-identifiers for any object instance
        does not exceed the limit of 128, as defined by
        [RFC1905].

        Note that the size of an UTF8String object is
        measured in octets, not characters."
       SYNTAX       OCTET STRING

-- The policy group

pmPolicyTable OBJECT-TYPE
    SYNTAX      SEQUENCE OF PmPolicyEntry
    MAX-ACCESS  not-accessible
    STATUS      current
    DESCRIPTION
        "The policy table. A policy is a pairing of a
        policyFilter and a policyAction which is used to apply the
        action to a selected set of elements."
    ::= { policyMgt 1 }

pmPolicyEntry OBJECT-TYPE
    SYNTAX      PmPolicyEntry
    MAX-ACCESS  not-accessible
    STATUS      current
    DESCRIPTION
        "An entry in the policy table."
    INDEX { pmPolicyIndex }
    ::= { pmPolicyTable 1 }

PmPolicyEntry ::= SEQUENCE {
    pmPolicyIndex              Unsigned32,
    pmPolicyFilter             UTF8String,
    pmPolicyCalendar           RowPointer,
    pmPolicyAction             UTF8String,
    pmPolicyFilterMaxLatency   Unsigned32,
    pmPolicyActionMaxLatency   Unsigned32,
    pmPolicyPrecedence         Unsigned32,
    pmPolicyGroup              UTF8String,
    pmPolicyDescription        UTF8String,
    pmPolicyMatches            Gauge32,
    pmPolicyExecutionErrors    Counter32,
    pmPolicyDebugging          INTEGER,
    pmPolicyStatus             RowStatus
}

pmPolicyIndex OBJECT-TYPE
    SYNTAX      Unsigned32
    MAX-ACCESS  not-accessible
    STATUS      current
    DESCRIPTION
         "A unique index for this policy entry."
    ::= { pmPolicyEntry 1 }

pmPolicyFilter OBJECT-TYPE
    SYNTAX      UTF8String
    MAX-ACCESS  read-create
    STATUS      current
    DESCRIPTION
         "A policyFilter is an expression which results in a boolean
         value which represents whether or not an element is a member
         of a set of elements upon which an action is to be
         performed.

         The format of this expression is the policy expression
         language. Filter evaluation stops immediately when any error
         is detected without executing the policyAction.

         The policyFilter is evaluated for various elements. Any
         element for which the policyFilter returns any nonzero value
         will match the filter and will have the associated
         policyAction executed on that element."
    ::= { pmPolicyEntry 2 }

pmPolicyCalendar OBJECT-TYPE
    SYNTAX      RowPointer
    MAX-ACCESS  read-create
    STATUS      current
    DESCRIPTION
         "A pointer to an entry in the schedTable of the Scheduling
         MIB [20]. This policy is active when specified by the
         associated schedule entry.

         If the value of this object is 0.0, this policy is always
         active."
    ::= { pmPolicyEntry 3 }

pmPolicyAction OBJECT-TYPE
    SYNTAX      UTF8String
    MAX-ACCESS  read-create
    STATUS      current
    DESCRIPTION
         "A pmPolicyAction is an operation performed on a set of
         elements. The format of this expression is the policy
         expression language.

         Action evaluation stops immediately when any error is
         detected."
    ::= { pmPolicyEntry 4 }

pmPolicyFilterMaxLatency OBJECT-TYPE
    SYNTAX      Unsigned32
    UNITS       "milliseconds"
    MAX-ACCESS  read-create
    STATUS      current
    DESCRIPTION
        "Every element under the control of this agent is
        re-checked periodically to see if it is under control of this
        policy by re-running the filter expression for this policy.
        This object lets the manager control the maximum amount of
        time that may pass before an element is re-checked.

        In other words, in any given interval of this duration, all
        elements must be re-checked. Note that it is an
        implementation-dependent matter as to how the policy agent
        schedules the checking of various elements within this
        interval."
    ::= { pmPolicyEntry 5 }

pmPolicyActionMaxLatency OBJECT-TYPE
    SYNTAX      Unsigned32
    UNITS       "milliseconds"
    MAX-ACCESS  read-create
    STATUS      current
    DESCRIPTION
        "Every element that matches this policy's filter and is
        therefore under control of this policy will have this policy's
        action executed periodically to ensure that the element
        remains in the state dictated by the policy.
        This object lets the manager control the maximum amount of
        time that may pass before an element has the action run on
        it.

        In other words, in any given interval of this duration, all
        elements under control of this policy must have the action run
        on them. Note that it is an implementation-dependent matter as
        to how the policy agent schedules the policy action on various
        elements within this interval."
    ::= { pmPolicyEntry 6 }

pmPolicyPrecedence OBJECT-TYPE
    SYNTAX      Unsigned32 (0..65535)
    MAX-ACCESS  read-create
    STATUS      current
    DESCRIPTION
        "The order in which policies on the local system are
        evaluated. A policy with a higher precedence value will
        be evaluated after a policy with a lower precedence. For
        example, a policy with a precedence value of 999 will be
        evaluated after a policy with a precedence value of 998.
        These values must be unique on the local policy system
        that realizes this module. The value for a particular
        policy should be the same across an administrative
        domain, though that is not mandatory.

        When the local policy system performs the evaluation in the
        pmPolicyFilter for the policy identified by this row it will
        also read the pmTrackingElementToPolicyStatus object for each
        object returned as a result of the policy evaluation.  If that
        object is set to modified(3), then the pmPolicyAction shall
        not be taken on that element.

        The value of precedence(4), of pmTrackingElementToPolicyStatus
        is an indication that when an evaluation was performed by
        another policy, the pmTrackingElementToPolicyStatus was found
        to have a value of on(1) and that policy had a higher
        precedence value than the policy that initially set the value
        of the pmTrackingElementToPolicyStatus to on(1). In this
        event, the pmTrackingElementToPolicyPrecedence object shall
        have the value of the pmPolicyIndex for the policy with the
        higher precedence value entered. If the policy identified by
        this row of the pmPolicyTable has a higher precedence value
        than the value found in pmTrackingElementToPolicyPrecedence
        then the pmPolicyAction should be performed on the element and
        the pmTrackingElementToPolicyPrecedence object updated with
        the value of the pmPolicyIndex for this policy. The only
        exception to these rules is when the policy that has the
        higher precedence value in not currently running, i.e., the
        schedule is off."
    ::= { pmPolicyEntry 7 }

pmPolicyGroup OBJECT-TYPE
    SYNTAX      UTF8String (SIZE (0..32))
    MAX-ACCESS  read-create
    STATUS      current
    DESCRIPTION
        "An administratively assigned string that is used to group
        policies. Any combination is legal, the pmPolicyGroup object
        does not constrain precedence. That is precedence is evaluated
        independent of grouping though adminstrators might group
        related policies together for clarity."
    ::= { pmPolicyEntry 8 }

pmPolicyDescription OBJECT-TYPE
    SYNTAX      UTF8String (SIZE (0..255))
    MAX-ACCESS  read-create
    STATUS      current
    DESCRIPTION
         "A description of this rule and its significance, typically
         provided by a human."
    ::= { pmPolicyEntry 9 }

pmPolicyMatches OBJECT-TYPE
    SYNTAX      Gauge32
    UNITS       "elements"
    MAX-ACCESS  read-create
    STATUS      current
    DESCRIPTION
         "The number of elements that are currently matched by the
         associated pmPolicyFilter."
    ::= { pmPolicyEntry 10 }

pmPolicyExecutionErrors OBJECT-TYPE
    SYNTAX      Counter32
    UNITS       "errors"
    MAX-ACCESS  read-only
    STATUS      current
    DESCRIPTION
         "The number of times execution of this policy has been
         terminated due to run-time errors."
    ::= { pmPolicyEntry 11 }

pmPolicyDebugging OBJECT-TYPE
    SYNTAX      INTEGER {
                    off(0),
                    on(1)
                }
    MAX-ACCESS  read-create
    STATUS      current
    DESCRIPTION
         "The status of debugging for this policy. If this is turned
         on(1), log entries will be created in the pmDebuggingTable
         for each run-time error that is experienced by this policy."
    DEFVAL { off }
    ::= { pmPolicyEntry 12 }

pmPolicyStatus OBJECT-TYPE
    SYNTAX      RowStatus
    MAX-ACCESS  read-create
    STATUS      current
    DESCRIPTION
         "The status of this pmPolicyEntry."
    ::= { pmPolicyEntry 13 }

-- Element Type Registration Table

-- The Element Type Registration table is used for the manager to
-- learn what element types are being managed by the system and to
-- register new types if necessary. An element type is registered by
-- providing the OID of an SNMP object (i.e., without the
-- instance). Each SNMP instance that exists under that object is a
-- distinct element. The address of the element is the index part of
-- the discovered OID. This address will be supplied to policy filters
-- and actions so that these expressions can inspect and configure the
-- element.
--
-- Before registering an element type, it is the responsibility of a
-- manager to inspect the table and see if it is already registered
-- (by the agent or another manager). Note that entries that differ
-- only in the last OID (which specifies which object in an entry) are
-- effectively duplicates and should be treated as such by the
-- manager.

pmElementTypeRegTable OBJECT-TYPE
    SYNTAX      SEQUENCE OF PmElementTypeRegEntry
    MAX-ACCESS  not-accessible
    STATUS      current
    DESCRIPTION
        "A registration table for element types managed by this
        system."
    ::= { policyMgt 2 }

pmElementTypeRegEntry OBJECT-TYPE
    SYNTAX      PmElementTypeRegEntry
    MAX-ACCESS  not-accessible
    STATUS      current
    DESCRIPTION
        "A registration of an element type."
    INDEX       { pmElementTypeRegIndex }
    ::= { pmElementTypeRegTable 1 }

PmElementTypeRegEntry ::= SEQUENCE {
    pmElementTypeRegIndex         Unsigned32,
    pmElementTypeRegOIDPrefix     OBJECT IDENTIFIER,
    pmElementTypeRegName          UTF8String,
    pmElementTypeRegRowStatus     RowStatus
}

pmElementTypeRegIndex OBJECT-TYPE
    SYNTAX      Unsigned32
    MAX-ACCESS  not-accessible
    STATUS      current
    DESCRIPTION
        "A unique index for this entry."
    ::= { pmElementTypeRegEntry 1 }

pmElementTypeRegOIDPrefix OBJECT-TYPE
    SYNTAX      OBJECT IDENTIFIER
    MAX-ACCESS  read-create
    STATUS      current
    DESCRIPTION
        "An OBJECT IDENTIFIER subtree under which all instances of
        this element type may be found.

        This OBJECT IDENTIFIER should be specified up to, but not
        including, any index objects. The agent will discover all
        instances in the system that are members of the specified
        subtree. It will then execute policy filters (and potentially
        policy actions) for each instance discovered.
        Each invocation of the policy filter will be supplied with a
        parameter. This is derived by taking the last N
        sub-identifiers from the discovered instance, where N is:

           X = number of sub-identifiers in pmElementTypeRegOIDPrefix
           Y = number of sub-identifiers in discovered instance

           N = Y - X
        "
    ::= { pmElementTypeRegEntry 2 }

pmElementTypeRegName OBJECT-TYPE
    SYNTAX      UTF8String (SIZE (0..32))
    MAX-ACCESS  read-create
    STATUS      current
    DESCRIPTION
        "A descriptive label for this registered type."
    ::= { pmElementTypeRegEntry 3 }

pmElementTypeRegRowStatus OBJECT-TYPE
    SYNTAX      RowStatus
    MAX-ACCESS  read-create
    STATUS      current
    DESCRIPTION
        "The status of this registration entry."
    ::= { pmElementTypeRegEntry 4 }

-- roleTable

-- The Role Table associates role strings to elements. It is the
-- responsibility of the agent to keep track of any re-indexing of the
-- underlying SNMP variables and to continue to associate role strings
-- with the element with which they were initially configured.
--
-- The agent must store role string associations in NVRAM.
--
-- The Role String table is visible through 2 SNMP tables. The
-- pmRoleESTable is a read-create table that organized role strings
-- sorted by element. This table is used to create and modify role
-- strings and their associations.
-- The pmRoleSETable is a read-only table that organizes role strings
-- sorted by string. This table is read-only.

pmRoleESTable OBJECT-TYPE
    SYNTAX      SEQUENCE OF PmRoleESEntry
    MAX-ACCESS  not-accessible
    STATUS      current
    DESCRIPTION
         "The role string table with element as the major index."
    ::= { policyMgt 3 }

pmRoleESEntry OBJECT-TYPE
    SYNTAX      PmRoleESEntry
    MAX-ACCESS  not-accessible
    STATUS      current
    DESCRIPTION
         "A role string entry associates a role string with an
         individual element."
    INDEX       { pmRoleESElement, pmRoleESString }
    ::= { pmRoleESTable 1 }

PmRoleESEntry ::= SEQUENCE {
    pmRoleESElement        RowPointer,
    pmRoleESString         UTF8String,
    pmRoleESStatus         RowStatus
}

pmRoleESElement OBJECT-TYPE
    SYNTAX      RowPointer
    MAX-ACCESS  not-accessible
    STATUS      current
    DESCRIPTION
         "The element to which this role string is associated.

         If the agent assigns new indexes in the MIB table to
         represent the same underlying element (re-indexing), the
         agent will modify this value to contain the new index for the
         underlying element."
    ::= { pmRoleESEntry 1 }

pmRoleESString OBJECT-TYPE
    SYNTAX      UTF8String (SIZE (0..64))
    MAX-ACCESS  not-accessible
    STATUS      current
    DESCRIPTION
         "The role string that is associated with an element through
         this table.

         A role string is an administratively specified characteristic
         of a managed element (for example, an interface). It is a
         selector for policy rules, to determine the applicability of
         the rule to a particular managed element."
    ::= { pmRoleESEntry 2 }

pmRoleESStatus OBJECT-TYPE
    SYNTAX      RowStatus
    MAX-ACCESS  read-create
    STATUS      current
    DESCRIPTION
         "The status of this role string."
    ::= { pmRoleESEntry 3 }

pmRoleSETable OBJECT-TYPE
    SYNTAX      SEQUENCE OF PmRoleSEEntry
    MAX-ACCESS  not-accessible
    STATUS      current
    DESCRIPTION
         "A read-only version of the role string table with
         roleString as the major index. The purpose of this
         table is to make it easy to retrieve all elements that
         share a common string."
    ::= { policyMgt 4 }

pmRoleSEEntry OBJECT-TYPE
    SYNTAX      PmRoleSEEntry
    MAX-ACCESS  not-accessible
    STATUS      current
    DESCRIPTION
         "A role string entry associates a role string with an
         individual element."
    INDEX       { pmRoleSEString, pmRoleSEElement }
    ::= { pmRoleSETable 1 }

PmRoleSEEntry ::= SEQUENCE {
    pmRoleSEString         UTF8String,
    pmRoleSEElement        RowPointer
}

pmRoleSEString OBJECT-TYPE
    SYNTAX      UTF8String (SIZE (0..64))
    MAX-ACCESS  not-accessible
    STATUS      current
    DESCRIPTION
         "The role string that is associated with an element through
         this table.
         A role string is an administratively specified characteristic
         of a managed element (for example, an interface). It is a
         selector for policy rules, to determine the applicability of
         the rule to a particular managed element."
    ::= { pmRoleSEEntry 1 }

pmRoleSEElement OBJECT-TYPE
    SYNTAX      RowPointer
    MAX-ACCESS  read-only
    STATUS      current
    DESCRIPTION
         "The element to which this role string is associated.

         If the agent assigns new indexes in the MIB table to
         represent the same underlying element (re-indexing), the
         agent will modify this value to contain the new index for the
         underlying element."
    ::= { pmRoleSEEntry 2 }

-- Capabilities table

-- Note that with this table it is not necessary to list all OIDs that
-- a mechanism specific MIB Module supports, just the base OID if
-- the implementation is a fully compliant one. If the implementation
-- is not, then additional rows will exist in the table that list
-- the limitations or enhancements.

pmCapabilitiesTable OBJECT-TYPE
    SYNTAX      SEQUENCE OF PmCapabilitiesEntry
    MAX-ACCESS  not-accessible
    STATUS      current
    DESCRIPTION
         "The pmCapabilitiesTable contains a description of
         the inherent capabilities of the system."
    ::= { policyMgt 5 }

pmCapabilitiesEntry OBJECT-TYPE
    SYNTAX      PmCapabilitiesEntry
    MAX-ACCESS  not-accessible
    STATUS      current
    DESCRIPTION
         "The description of a capability or limitation of a
         capability of the system. An entry will exist for each
         domain and mechanism specific ability the system has. In
         the case of a domain specific capability with no mechanism
         specific parameters, the pmCapabilitiesSubType and all other
         columns may be null. Entries will exist that contain
         values for the pmCapabilitiesRestrictOID,
         pmCapabilitiesRestrictType, pmCapabilitiesRestrictValue
         and pmCapabilitiesRestrictString objects only when
         an implementation is reporting a mechanism specific
         restriction. Multiple entries are possible when more
         than one restriction for a type or subtype are needed."
    INDEX       { pmCapabilitiesIndex }
    ::= { pmCapabilitiesTable 1 }

PmCapabilitiesEntry ::= SEQUENCE {
    pmCapabilitiesIndex              Unsigned32,
    pmCapabilitiesType               OBJECT IDENTIFIER,
    pmCapabilitiesSubType            OBJECT IDENTIFIER,
    pmCapabilitiesModificationOID    OBJECT IDENTIFIER,
    pmCapabilitiesModificationType   INTEGER,
    pmCapabilitiesModificationValue  Integer32,
    pmCapabilitiesModificationString OCTET STRING
}

pmCapabilitiesIndex OBJECT-TYPE
    SYNTAX      Unsigned32
    MAX-ACCESS  not-accessible
    STATUS      current
    DESCRIPTION
         "A unique index for this entry."
    ::= { pmCapabilitiesEntry 1 }

pmCapabilitiesType OBJECT-TYPE
    SYNTAX      OBJECT IDENTIFIER
    MAX-ACCESS  read-only
    STATUS      current
    DESCRIPTION
         "The type of the capability represented by this entry.
         The IANA will publish the list of identifiers that are valid
         values for this object."
    ::= { pmCapabilitiesEntry 2 }

pmCapabilitiesSubType OBJECT-TYPE
    SYNTAX      OBJECT IDENTIFIER
    MAX-ACCESS  read-only
    STATUS      current
    DESCRIPTION
         "The sub type of capability is a pointer to a mechanism specific
          set of capabilities supporting a base technology. In the case of
          DIFFSERV, the OID value here would be the base OID of the
          Differentiated Services Policy MIB Module."
    ::= { pmCapabilitiesEntry 3 }

pmCapabilitiesModificationOID OBJECT-TYPE
    SYNTAX      OBJECT IDENTIFIER
    MAX-ACCESS  read-only
    STATUS      current
    DESCRIPTION
         "The OID of the object that is either not supported, supported
         with one or more limitations, or expanded by an implementation
         specific module. If this columnar object is other than null then
         there must be at least an entry in pmCapabilitiesModificationType.
         Note that this need not be a leaf node or scalar object. If
         an entire table is not supported, this value can be the base OID
         for the table."
    ::= { pmCapabilitiesEntry 4 }

pmCapabilitiesModificationType OBJECT-TYPE
    SYNTAX      INTEGER {
                    unsupported(0),
                    restricted(1),
                    additional(2),
                    addvalue(3),
                    maxlimit(4),
                    minlimit(5)
                }
    MAX-ACCESS  read-only
    STATUS      current
    DESCRIPTION
         "An unsupported value indicates that the OID in
          pmCapabilitiesModificationOID is not supported on
          this system. A value of 1 indicates that the OID
          is supported but with restricted values
          These constraints are described in the
          pmCapabilitiesModificationValue and
          pmCapabilitiesModificationString objects. A value of
          2 indicates a vendor specific extension to a standard.
          The OID of the new object is pmCapabilitiesModificationOID.
          For some implementations, additional functions may be
          provided. addvalue indicates that this row of the table
          describes an additional value that the object can take.
          The specific value is in the pmCapabilitiesModificationValue.
          The values of 4 and 5 indicate restrictions or the removal
          of restrictions for the object identified."
    ::= { pmCapabilitiesEntry 5 }

pmCapabilitiesModificationValue OBJECT-TYPE
    SYNTAX      Integer32 (0..2147483647)
    MAX-ACCESS  read-only
    STATUS      current
    DESCRIPTION
         "If the value of pmCapabilitiesModificationType is 0, this
          object will be null since 0 indicates no support for the
          object at all. A value of 1 in the
          pmCapabilitiesModificationType will be further modified by a
          single integer value in this object that corresponds to
          enumerated integer values that are not supported by the
          system for the object that is identified in this row. This
          value can also represent the limit values in the
          pmCapabilitiesModificationType object."
    ::= { pmCapabilitiesEntry 6 }

pmCapabilitiesModificationString OBJECT-TYPE
    SYNTAX      OCTET STRING
    MAX-ACCESS  read-only
    STATUS      current
    DESCRIPTION
         "Any additional details or description or parameters needed."
    ::= { pmCapabilitiesEntry 7 }

-- Policy Tracking

pmTrackingPolicyToElementTable OBJECT-TYPE
    SYNTAX      SEQUENCE OF PmTrackingPolicyToElementEntry
    MAX-ACCESS  not-accessible
    STATUS      current
    DESCRIPTION
         "The pmTrackingPolicyToElementTable describes what elements
         are under control of a policy."
    ::= { policyMgt 6 }

pmTrackingPolicyToElementEntry OBJECT-TYPE
    SYNTAX      PmTrackingPolicyToElementEntry
    MAX-ACCESS  not-accessible
    STATUS      current
    DESCRIPTION
         "An entry in the pmTrackingPolicyToElementTable.  The
         pmPolicyIndex in the index specifies the policy tracked by
         this entry."
    INDEX       { pmPolicyIndex, pmTrackingPolicyToElementElement }
    ::= { pmTrackingPolicyToElementTable 1 }

PmTrackingPolicyToElementEntry ::= SEQUENCE {
    pmTrackingPolicyToElementElement          RowPointer,
    pmTrackingPolicyToElementStatus           INTEGER
}

pmTrackingPolicyToElementElement OBJECT-TYPE
    SYNTAX      RowPointer
    MAX-ACCESS  not-accessible
    STATUS      current
    DESCRIPTION
         "The element this policy is configuring."
    ::= { pmTrackingPolicyToElementEntry 1 }

pmTrackingPolicyToElementStatus OBJECT-TYPE
    SYNTAX      INTEGER {
                    off(0),
                    on(1)
                }
    MAX-ACCESS  read-only
    STATUS      current
    DESCRIPTION
         "The status of this policy-element relationship. This value
         will be 1 if the associated policyFilter returned 1 for this
         element and if the calendar for the policy is active.

         Entries will only exist in this table if their status is
         on(1). Thus, on(1) is the only value of this object that can
         be retrieved. This object exists so that it can serve as the
         'payload' in the varbind instead of the
         pmTrackingPolicyToElementElement object which is much longer
         and is already in the index (it would otherwise be
         duplicated)."
    ::= { pmTrackingPolicyToElementEntry 2 }

-- Element to Policy Table

pmTrackingElementToPolicyTable OBJECT-TYPE
    SYNTAX      SEQUENCE OF PmTrackingElementToPolicyEntry
    MAX-ACCESS  not-accessible
    STATUS      current
    DESCRIPTION
         "The pmTrackingElementToPolicyTable describes what policies
         are controlling an element."
    ::= { policyMgt 7 }

pmTrackingElementToPolicyEntry OBJECT-TYPE
    SYNTAX      PmTrackingElementToPolicyEntry
    MAX-ACCESS  not-accessible
    STATUS      current
    DESCRIPTION
         "An entry in the pmTrackingElementToPolicyTable. The
         pmPolicyIndex in the index specifies the policy tracked by
         this entry."
    INDEX       { pmTrackingElementToPolicyElement, pmPolicyIndex }
    ::= { pmTrackingElementToPolicyTable 1 }

PmTrackingElementToPolicyEntry ::= SEQUENCE {
    pmTrackingElementToPolicyElement          RowPointer,
    pmTrackingElementToPolicyStatus           INTEGER
}

pmTrackingElementToPolicyElement OBJECT-TYPE
    SYNTAX      RowPointer
    MAX-ACCESS  not-accessible
    STATUS      current
    DESCRIPTION
         "The element this policy is configuring."
    ::= { pmTrackingElementToPolicyEntry 1 }

pmTrackingElementToPolicyStatus OBJECT-TYPE
    SYNTAX      INTEGER {
                    off(0),
                    on(1),
                    forceOff(2)
                }
    MAX-ACCESS  read-write
    STATUS      current
    DESCRIPTION
         "The status of this policy-element relationship. This value
         will be 1 if the associated policyFilter returned 1 for this
         element and if the calendar for the policy is active.

         Entries will not exist in this table if their status would be
         off(0).

         A policy can be forcibly disabled on a particular element
         by setting this value to forceOff(2). The agent should then
         act as if the policyFilter failed for this element. The
         forceOff(2) state will persist (even across reboots) until
         this value is set to on(1) by a management request. Even if
         the policyFilter later fails for this element, this value
         will stay in the forceOff(2) state."
    ::= { pmTrackingElementToPolicyEntry 2 }

-- Policy Debugging Table

-- Policies that have debugging turned on will generate a log entry in
-- the policy debugging table for every runtine error that occurs in
-- either the filter or action expression.

pmDebuggingTable OBJECT-TYPE
    SYNTAX      SEQUENCE OF PmDebuggingEntry
    MAX-ACCESS  not-accessible
    STATUS      current
    DESCRIPTION
         "The pmDebuggingPolicyTable logs debugging messages when
         policies experience runtime errors."
    ::= { policyMgt 8 }

pmDebuggingEntry OBJECT-TYPE
    SYNTAX      PmDebuggingEntry
    MAX-ACCESS  not-accessible
    STATUS      current
    DESCRIPTION
         "An entry in the pmDebuggingTable. The pmPolicyIndex in the
         index specifies the policy that encountered the error that
         led to this log entry."
    INDEX       { pmPolicyIndex, pmDebuggingElement,
                  pmDebuggingLogIndex }
    ::= { pmDebuggingTable 1 }

PmDebuggingEntry ::= SEQUENCE {
    pmDebuggingElement          RowPointer,
    pmDebuggingLogIndex         Unsigned32,
    pmDebuggingMessage          UTF8String
}

pmDebuggingElement OBJECT-TYPE
    SYNTAX      RowPointer
    MAX-ACCESS  read-only
    STATUS      current
    DESCRIPTION
         "The element the policy was executing on when it encountered
         the error that led to this log entry."
    ::= { pmDebuggingEntry 1 }

pmDebuggingLogIndex OBJECT-TYPE
    SYNTAX      Unsigned32
    MAX-ACCESS  read-only
    STATUS      current
    DESCRIPTION
         "A unique index for this log entry amongst other log entries
         for this policy/element combination."
    ::= { pmDebuggingEntry 2 }

pmDebuggingMessage OBJECT-TYPE
    SYNTAX      UTF8String (SIZE (0..128))
    MAX-ACCESS  read-only
    STATUS      current
    DESCRIPTION
         "An error message generated by the expression runtime system."
    ::= { pmDebuggingEntry 3 }

-- Compliance Statements

    pmConformance   OBJECT IDENTIFIER ::= { policyMgt 20 }
    pmCompliances   OBJECT IDENTIFIER ::= { pmConformance 1 }
    pmGroups        OBJECT IDENTIFIER ::= { pmConformance 2 }

pmCompliance MODULE-COMPLIANCE
    STATUS  current
    DESCRIPTION
        "Describes the requirements for conformance to
        the Policy-Based Management MIB"
    MODULE  -- this module
        MANDATORY-GROUPS { pmPolicyManagementGroup }
    ::= { pmCompliances 1 }

pmPolicyManagementGroup OBJECT-GROUP
    OBJECTS { pmPolicyFilter, pmPolicyCalendar, pmPolicyAction,
              pmPolicyFilterMaxLatency, pmPolicyActionMaxLatency,
              pmPolicyPrecedence, pmPolicyGroup,
              pmPolicyDescription, pmPolicyMatches,
              pmPolicyExecutionErrors, pmPolicyDebugging,
              pmPolicyStatus,
              pmElementTypeRegOIDPrefix,
              pmElementTypeRegName, pmElementTypeRegRowStatus,
              pmRoleESStatus, pmRoleSEElement, pmCapabilitiesType,
              pmCapabilitiesSubType, pmCapabilitiesModificationOID,
              pmCapabilitiesModificationType,
              pmCapabilitiesModificationValue,
              pmCapabilitiesModificationString,
              pmTrackingPolicyToElementStatus,
              pmTrackingElementToPolicyStatus,
              pmDebuggingElement, pmDebuggingLogIndex,
              pmDebuggingMessage }
    STATUS  current
    DESCRIPTION
        "Objects that allow for the creation and management of
        configuration policies."
    ::=  { pmGroups 1 }

pmBaseFunctionLibrary OBJECT IDENTIFIER ::= { pmGroups 2 }

END

-- 
-- Copyright (C) The Internet Society (2000). All Rights Reserved.
-- 
-- This document and translations of it may be copied and
-- furnished to others, and derivative works that comment on or
-- otherwise explain it or assist in its implementation may be
-- prepared, copied, published and distributed, in whole or in
-- part, without restriction of any kind, provided that the above
-- copyright notice and this paragraph are included on all such
-- copies and derivative works.  However, this document itself
-- may not be modified in any way, such as by removing the
-- copyright notice or references to the Internet Society or
-- other Internet organizations, except as needed for the
-- purpose of developing Internet standards in which case the
-- procedures for copyrights defined in the Internet Standards
-- process must be followed, or as required to translate it into
-- languages other than English.
-- 
-- The limited permissions granted above are perpetual and will
-- not be revoked by the Internet Society or its successors or
-- assigns.
-- 
-- This document and the information contained herein is provided
-- on an "AS IS" basis and THE INTERNET SOCIETY AND THE INTERNET
-- ENGINEERING TASK FORCE DISCLAIMS ALL WARRANTIES, EXPRESS OR
-- IMPLIED, INCLUDING BUT NOT LIMITED TO ANY WARRANTY THAT THE
-- USE OF THE INFORMATION HEREIN WILL NOT INFRINGE ANY RIGHTS OR
-- ANY IMPLIED WARRANTIES OF MERCHANTABILITY OR FITNESS FOR A
-- PARTICULAR PURPOSE.
