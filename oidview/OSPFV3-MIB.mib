-- extracted from draft-ietf-ospf-ospfv3-mib-02.txt
-- at Wed Apr 12 07:06:58 2000

     OSPFV3-MIB DEFINITIONS ::= BEGIN

         IMPORTS
                 MODULE-IDENTITY, OBJECT-TYPE, experimental,
                 Counter32, Gauge32, Integer32, IpAddress
                     FROM SNMPv2-SMI
                 TruthValue, RowStatus
                     FROM SNMPv2-TC
                 MODULE-COMPLIANCE, OBJECT-GROUP
                     FROM SNMPv2-CONF
                 Ipv6IfIndex, Ipv6Address, Ipv6AddressPrefix
                     FROM IPV6-TC
                 AreaID, RouterID, Metric, BigMetric, Status, PositiveInteger,
                 HelloRange, UpToMaxAge, DesignatedRouterPriority
                     FROM OSPF-MIB
                 ;

     ospfv3Mib MODULE-IDENTITY
               LAST-UPDATED "9909071305Z"
               ORGANIZATION "IETF OSPF Working Group"
               CONTACT-INFO
              "       Dan Joyal
              Postal: Nortel Networks
                      600 Technology Park Drive
                      Billerica, MA  01821
                      USA
              Tel:    +1-978-288-2629
              E-Mail: djoyal@nortelnetworks.com"
           DESCRIPTION
              "The MIB module to describe the OSPF Version for IPv6"
           ::= { experimental 102 } --mib-2 OID to be assigned


     ospfv3 OBJECT IDENTIFIER ::= { ospfv3Mib 1 }


     --  OSPFv3 General Variables

     --      These parameters apply globally to the Router's
     --      OSPFv3 Process.

     ospfv3GeneralGroup OBJECT IDENTIFIER ::= { ospfv3 1 }
         ospfv3RouterId OBJECT-TYPE
             SYNTAX   RouterID
             MAX-ACCESS   read-write
             STATUS   current
             DESCRIPTION
                "A  32-bit  integer  uniquely  identifying  the
                router in the Autonomous System.

                By  convention,  to  ensure  uniqueness,   this
                should  default  to  the  value  of  one of the
                router's IPv4 interface addresses if IPv4 is
                configured."
           ::= { ospfv3GeneralGroup 1 }


         ospfv3AdminStat OBJECT-TYPE
             SYNTAX   Status
             MAX-ACCESS   read-write
             STATUS   current
             DESCRIPTION
                "The  administrative  status  of  OSPFv3  in  the
                router.   The  value 'enabled' denotes that the
                OSPFv3 Process is active on at least  one  inter-
                face;  'disabled'  disables  it  on  all inter-
                faces."
            ::= { ospfv3GeneralGroup 2 }

         ospfv3VersionNumber OBJECT-TYPE
             SYNTAX   INTEGER { version3 (3) }
             MAX-ACCESS   read-only
             STATUS   current
             DESCRIPTION
                "The version number of OSPF for IPv6 is 3."
           ::= { ospfv3GeneralGroup 3 }


         ospfv3AreaBdrRtrStatus OBJECT-TYPE
             SYNTAX   TruthValue
             MAX-ACCESS   read-only
             STATUS   current
             DESCRIPTION
                "A flag to note whether this router is an  area
                border router."
             REFERENCE
                "OSPF Version 2, Section 3 Splitting the AS into
                 Areas"
           ::= { ospfv3GeneralGroup 4 }


         ospfv3ASBdrRtrStatus OBJECT-TYPE
             SYNTAX   TruthValue
             MAX-ACCESS   read-write
             STATUS   current
             DESCRIPTION
                "A flag to note whether this router is  config-
                ured as an Autonomous System border router."
            REFERENCE
               "OSPF Version 2, Section 3.3  Classification  of
               routers"
           ::= { ospfv3GeneralGroup 5 }


         ospfv3AsScopeLsaCount OBJECT-TYPE
             SYNTAX   Gauge32
             MAX-ACCESS   read-only
             STATUS   current
             DESCRIPTION
                "The number of AS-Scope (e.g. AS-External) link-state
                advertisements in the link-state database."
           ::= { ospfv3GeneralGroup 6 }


         ospfv3AsScopeLsaCksumSum OBJECT-TYPE
             SYNTAX   Integer32
             MAX-ACCESS   read-only
             STATUS   current
             DESCRIPTION
                "The 32-bit unsigned sum of the LS checksums of
                the  AS-scoped link-state advertisements  con-
                tained in the link-state database. This sum
                can  be  used  to determine if there has been a
                change in a router's link state  database,  and
                to  compare  the  link-state  database  of  two
                routers."
            ::= { ospfv3GeneralGroup 7 }


         ospfv3OriginateNewLsas OBJECT-TYPE
             SYNTAX   Counter32
             MAX-ACCESS   read-only
             STATUS   current
             DESCRIPTION
                "The number of  new  link-state  advertisements
                that  have been originated.  This number is in-
                cremented each time the router originates a new
                LSA."
            ::= { ospfv3GeneralGroup 8 }


         ospfv3RxNewLsas OBJECT-TYPE
             SYNTAX   Counter32
             MAX-ACCESS   read-only
             STATUS   current
             DESCRIPTION
                "The number of  link-state  advertisements  re-
                ceived  determined  to  be  new instantiations.
                This number does not include  newer  instantia-
                tions  of self-originated link-state advertise-
                ments."
            ::= { ospfv3GeneralGroup 9 }

         ospfv3ExtAreaLsdbLimit OBJECT-TYPE
             SYNTAX   Integer32 (-1..'7FFFFFFF'h)
             MAX-ACCESS   read-write
             STATUS   current
             DESCRIPTION
                "The  maximum   number   of   non-default   AS-
                external-LSAs entries that can be stored in the
                link-state database.  If the value is -1,  then
                there is no limit.

                When the number of non-default AS-external-LSAs
                in   a  router's  link-state  database  reaches
                ospfv3ExtAreaLsdbLimit, the router  enters  Overflow-
                State.   The   router  never  holds  more  than
                ospfv3ExtAreaLsdbLimit  non-default  AS-external-LSAs
                in  its  database. OspfExtAreaLsdbLimit MUST be set
                identically in all routers attached to the OSPFv3
                backbone  and/or  any regular OSPFv3 area. (i.e.,
                OSPFv3 stub areas and NSSAs are excluded)."
            DEFVAL { -1 }
            ::= { ospfv3GeneralGroup 10 }

         ospfv3MulticastExtensions OBJECT-TYPE
             SYNTAX   Integer32
             MAX-ACCESS   read-write
             STATUS   current
             DESCRIPTION
                "A Bit Mask indicating whether  the  router  is
                forwarding  IPv6  multicast datagrams
                based on the algorithms defined in  the  Multi-
                cast Extensions to OSPF.

                Bit 0, if set, indicates that  the  router  can
                forward  IPv6 multicast datagrams in the router's
                directly attached areas (called intra-area mul-
                ticast routing).

                Bit 1, if set, indicates that  the  router  can
                forward  IPv6  multicast  datagrams  between OSPFv3
                areas (called inter-area multicast routing).

                Bit 2, if set, indicates that  the  router  can
                forward  IPv6  multicast  datagrams between Auto-
                nomous Systems (called inter-AS multicast rout-
                ing).

                Only certain combinations of bit  settings  are
                allowed,  namely: 0 (no multicast forwarding is
                enabled), 1 (intra-area multicasting  only),  3
                (intra-area  and  inter-area  multicasting),  5
                (intra-area and inter-AS  multicasting)  and  7
                (multicasting  everywhere). By default, no mul-
                ticast forwarding is enabled."
            DEFVAL { 0 }
            ::= { ospfv3GeneralGroup 11 }

         ospfv3ExitOverflowInterval OBJECT-TYPE
             SYNTAX   PositiveInteger
             MAX-ACCESS   read-write
             STATUS   current
             DESCRIPTION
                "The number of  seconds  that,  after  entering
                OverflowState,  a  router will attempt to leave
                OverflowState. This allows the router to  again
                originate  non-default  AS-External-LSAs.  When
                set to 0, the router will not  leave  Overflow-
                State until restarted."
            DEFVAL { 0 }
            ::= { ospfv3GeneralGroup 12 }

         ospfv3DemandExtensions OBJECT-TYPE
             SYNTAX   TruthValue
             MAX-ACCESS   read-write
             STATUS   current
             DESCRIPTION
                "The router's support for demand routing."
            REFERENCE
               "OSPF Version 2, Appendix on Demand Routing"
           ::= { ospfv3GeneralGroup 13 }


     --      The OSPFv3 Area Data Structure contains information
     --      regarding the various areas. The interfaces and
     --      virtual links are configured as part of these areas.
     --      Area 0.0.0.0, by definition, is the Backbone Area


         ospfv3AreaTable OBJECT-TYPE
             SYNTAX   SEQUENCE OF Ospfv3AreaEntry
             MAX-ACCESS   not-accessible
             STATUS   current
             DESCRIPTION
                "Information describing the configured  parame-
                ters  and cumulative statistics of the router's
                attached areas."
            REFERENCE
               "OSPF Version 2, Section 6  The Area Data Struc-
               ture"
           ::= { ospfv3 2 }


         ospfv3AreaEntry OBJECT-TYPE
             SYNTAX   Ospfv3AreaEntry
             MAX-ACCESS   not-accessible
             STATUS   current
             DESCRIPTION
                "Information describing the configured  parame-
                ters  and  cumulative  statistics of one of the
                router's attached areas."
            INDEX { ospfv3AreaId }
            ::= { ospfv3AreaTable 1 }

     Ospfv3AreaEntry ::=
         SEQUENCE {
             ospfv3AreaId
                 AreaID,
             ospfv3ImportAsExtern
                 INTEGER,
             ospfv3SpfRuns
                 Counter32,
             ospfv3AreaBdrRtrCount
                 Gauge32,
             ospfv3AsBdrRtrCount
                 Gauge32,
             ospfv3AreaScopeLsaCount
                 Gauge32,
             ospfv3AreaScopeLsaCksumSum
                 Integer32,
             ospfv3AreaSummary
                 INTEGER,
             ospfv3AreaStatus
                 RowStatus,
             ospfv3StubMetric
                 BigMetric
                   }

         ospfv3AreaId OBJECT-TYPE
             SYNTAX   AreaID
             MAX-ACCESS   read-only
             STATUS   current
             DESCRIPTION
                "A 32-bit integer uniquely identifying an area.
                Area ID 0.0.0.0 is used for the OSPFv3 backbone."
            REFERENCE
               "OSPF Version 2, Appendix C.2 Area parameters"
           ::= { ospfv3AreaEntry 1 }


         ospfv3ImportAsExtern OBJECT-TYPE
             SYNTAX   INTEGER    {
                         importExternal (1),   -- normal area
                         importNoExternal (2), -- stub area
                         importNssa (3)        -- not-so-stubby-area
                       }
             MAX-ACCESS   read-create
             STATUS   current
             DESCRIPTION
                "The area's support for importing  AS  external
                link- state advertisements."
            REFERENCE
               "OSPF Version 2, Appendix C.2 Area parameters"
           DEFVAL { importExternal }
           ::= { ospfv3AreaEntry 2 }


         ospfv3SpfRuns OBJECT-TYPE
             SYNTAX   Counter32
             MAX-ACCESS   read-only
             STATUS   current
             DESCRIPTION
                "The number of times that the intra-area  route
                table  has  been  calculated  using this area's
                link-state database.  This  is  typically  done
                using Dijkstra's algorithm."
            ::= { ospfv3AreaEntry 3 }


         ospfv3AreaBdrRtrCount OBJECT-TYPE
             SYNTAX   Gauge32
             MAX-ACCESS   read-only
             STATUS   current
             DESCRIPTION
                "The total number of area border routers reach-
                able within this area.  This is initially zero,
                and is calculated in each SPF Pass."
            ::= { ospfv3AreaEntry 4 }

         ospfv3AsBdrRtrCount OBJECT-TYPE
             SYNTAX   Gauge32
             MAX-ACCESS   read-only
             STATUS   current
             DESCRIPTION
                "The total number of Autonomous  System  border
                routers  reachable  within  this area.  This is
                initially zero, and is calculated in  each  SPF
                Pass."
            ::= { ospfv3AreaEntry 5 }


         ospfv3AreaScopeLsaCount OBJECT-TYPE
             SYNTAX   Gauge32
             MAX-ACCESS   read-only
             STATUS   current
             DESCRIPTION
                "The total number of Area-Scope link-state advertisements
                in  this  area's link-state database."
            ::= { ospfv3AreaEntry 6 }


         ospfv3AreaScopeLsaCksumSum OBJECT-TYPE
             SYNTAX   Integer32
             MAX-ACCESS   read-only
             STATUS   current
             DESCRIPTION
                "The 32-bit unsigned sum of the Area-Scope link-state
                advertisements'  LS  checksums  contained in this
                area's link-state database.  The sum can be used
                to determine if  there  has been  a  change  in a
                router's link state database, and to compare the
                link-state database of two routers."
            DEFVAL   { 0 }
            ::= { ospfv3AreaEntry 7 }

         ospfv3AreaSummary OBJECT-TYPE
             SYNTAX   INTEGER    {
                         noAreaSummary (1),
                         sendAreaSummary (2)
                       }
             MAX-ACCESS   read-create
             STATUS   current
             DESCRIPTION
                "The variable ospfv3AreaSummary controls the  im-
                port  of  summary LSAs into stub areas.  It has
                no effect on other areas.

                If it is noAreaSummary, the router will neither
                originate  nor  propagate summary LSAs into the
                stub area.  It will rely entirely  on  its  de-
                fault route.

                If it is sendAreaSummary, the router will  both
                summarize and propagate summary LSAs."
            DEFVAL   { noAreaSummary }
            ::= { ospfv3AreaEntry 8 }


         ospfv3AreaStatus OBJECT-TYPE
             SYNTAX   RowStatus
             MAX-ACCESS   read-create
             STATUS   current
             DESCRIPTION
                "This variable displays the status of  the  en-
                try.  Setting it to 'invalid' has the effect of
                rendering it inoperative.  The internal  effect
                (row removal) is implementation dependent."
            ::= { ospfv3AreaEntry 9 }


         ospfv3StubMetric OBJECT-TYPE
             SYNTAX   BigMetric
             MAX-ACCESS   read-create
             STATUS   current
             DESCRIPTION
                "The metric value advertised for the default route
                 into Stub and NSSA areas."
            ::= { ospfv3AreaEntry 10 }


     --  OSPFv3 AS-Scope Link State Database

     --      The Link State Database contains the AS-Scope Link State
     --      Advertisements from throughout the areas that the
     --      device is attached to.


         ospfv3AsLsdbTable OBJECT-TYPE
             SYNTAX   SEQUENCE OF Ospfv3AsLsdbEntry
             MAX-ACCESS   not-accessible
             STATUS   current
             DESCRIPTION
                "The OSPFv3 Process's AS-Scope Link State Database."
           ::= { ospfv3 3 }


         ospfv3AsLsdbEntry OBJECT-TYPE
             SYNTAX   Ospfv3AsLsdbEntry
             MAX-ACCESS   not-accessible
             STATUS   current
             DESCRIPTION
                "A single AS-Scope Link State Advertisement."
            INDEX { ospfv3AsLsdbType,
                    ospfv3AsLsdbRouterId,
                    ospfv3AsLsdbLsid }
            ::= { ospfv3AsLsdbTable 1 }

     Ospfv3AsLsdbEntry ::=
         SEQUENCE {
             ospfv3AsLsdbType
                 INTEGER,
             ospfv3AsLsdbRouterId
                 RouterID,
             ospfv3AsLsdbLsid
                 IpAddress,
             ospfv3AsLsdbSequence
                 Integer32,
             ospfv3AsLsdbAge
                 Integer32,
             ospfv3AsLsdbChecksum
                 Integer32,
             ospfv3AsLsdbAdvertisement
                 OCTET STRING
                   }

         ospfv3AsLsdbType OBJECT-TYPE
             SYNTAX   INTEGER    {
                         asExternalLink (16389)   -- 0x4005
                       }
             MAX-ACCESS   read-only
             STATUS   current
             DESCRIPTION
                "The type  of  the  link  state  advertisement.
                Each  link state type has a separate advertise-
                ment format. Unrecognized AS-Scope LSAs with the
                U-bit set are also store in this database."
           ::= { ospfv3AsLsdbEntry 1 }


         ospfv3AsLsdbRouterId OBJECT-TYPE
             SYNTAX   RouterID
             MAX-ACCESS   read-only
             STATUS   current
             DESCRIPTION
                "The 32 bit number that uniquely identifies the
                originating router in the Autonomous System."
            REFERENCE
               "OSPF Version 2, Appendix C.1 Global parameters"
           ::= { ospfv3AsLsdbEntry 2 }


         ospfv3AsLsdbLsid OBJECT-TYPE
             SYNTAX   IpAddress
             MAX-ACCESS   read-only
             STATUS   current
             DESCRIPTION
                "The Link State ID is an LS Type Specific field
                containing either a Router ID or a unique identifier;
                it identifies the piece of the  routing  domain
                that is being described by the advertisement.
                In contrast to OSPF for IPv4, the LSID has no
                addressing semantics."
           ::= { ospfv3AsLsdbEntry 3 }


     --  Note that the OSPF Sequence Number is a 32 bit signed
     --  integer.  It starts with the value '80000001'h,
     --  or -'7FFFFFFF'h, and increments until '7FFFFFFF'h
     --  Thus, a typical sequence number will be very negative.

         ospfv3AsLsdbSequence OBJECT-TYPE
             SYNTAX   Integer32
             MAX-ACCESS   read-only
             STATUS   current
             DESCRIPTION
                "The sequence number field is a  signed  32-bit
                integer.   It  is used to detect old and dupli-
                cate link state advertisements.  The  space  of
                sequence  numbers  is  linearly  ordered.   The
                larger the sequence number the more recent  the
                advertisement."
            REFERENCE
               "OSPF Version  2,  Section  12.1.6  LS  sequence
               number"
           ::= { ospfv3AsLsdbEntry 4 }


         ospfv3AsLsdbAge OBJECT-TYPE
             SYNTAX   Integer32    -- Should be 0..MaxAge
             MAX-ACCESS   read-only
             STATUS   current
             DESCRIPTION
                "This field is the age of the link state adver-
                tisement in seconds."
            REFERENCE
               "OSPF Version 2, Section 12.1.1 LS age"
           ::= { ospfv3AsLsdbEntry 5 }

         ospfv3AsLsdbChecksum OBJECT-TYPE
             SYNTAX   Integer32
             MAX-ACCESS   read-only
             STATUS   current
             DESCRIPTION
                "This field is the  checksum  of  the  complete
                contents  of  the  advertisement, excepting the
                age field.  The age field is excepted  so  that
                an   advertisement's  age  can  be  incremented
                without updating the  checksum.   The  checksum
                used  is  the same that is used for ISO connec-
                tionless datagrams; it is commonly referred  to
                as the Fletcher checksum."
            REFERENCE
               "OSPF Version 2, Section 12.1.7 LS checksum"
           ::= { ospfv3AsLsdbEntry 6 }


         ospfv3AsLsdbAdvertisement OBJECT-TYPE
             SYNTAX   OCTET STRING (SIZE (1..65535))
             MAX-ACCESS   read-only
             STATUS   current
             DESCRIPTION
                "The entire Link State Advertisement, including
                its header."
           ::= { ospfv3AsLsdbEntry 7 }


     --  OSPFv3 Area-Scope Link State Database

     --      The Link State Database contains the Area-Scope Link State
     --      Advertisements from throughout the area that the
     --      device is attached to.


         ospfv3AreaLsdbTable OBJECT-TYPE
             SYNTAX   SEQUENCE OF Ospfv3AreaLsdbEntry
             MAX-ACCESS   not-accessible
             STATUS   current
             DESCRIPTION
                "The OSPFv3 Process's Area-Scope Link State Database."
           ::= { ospfv3 4 }


         ospfv3AreaLsdbEntry OBJECT-TYPE
             SYNTAX   Ospfv3AreaLsdbEntry
             MAX-ACCESS   not-accessible
             STATUS   current
             DESCRIPTION
                "A single Area-Scope Link State Advertisement."
            INDEX { ospfv3AreaLsdbAreaId,
                    ospfv3AreaLsdbType,
                    ospfv3AreaLsdbRouterId,
                    ospfv3AreaLsdbLsid }
            ::= { ospfv3AreaLsdbTable 1 }

     Ospfv3AreaLsdbEntry ::=
         SEQUENCE {
             ospfv3AreaLsdbAreaId
                 AreaID,
             ospfv3AreaLsdbType
                 INTEGER,
             ospfv3AreaLsdbRouterId
                 RouterID,
             ospfv3AreaLsdbLsid
                 IpAddress,
             ospfv3AreaLsdbSequence
                 Integer32,
             ospfv3AreaLsdbAge
                 Integer32,
             ospfv3AreaLsdbChecksum
                 Integer32,
             ospfv3AreaLsdbAdvertisement
                 OCTET STRING
                   }

         ospfv3AreaLsdbAreaId OBJECT-TYPE
             SYNTAX  AreaID
             MAX-ACCESS  read-only
             STATUS  current
             DESCRIPTION
                     "'The 32 bit identifier of the Area from which the LSA
                     was received.'
                              REFERENCE
                     'OSPF Version 2, Appendix C.2 Area parameters'"
             ::= { ospfv3AreaLsdbEntry 1 }


         ospfv3AreaLsdbType OBJECT-TYPE
             SYNTAX   INTEGER    {
                         routerLsa          (8193),  -- 0x2001
                         networkLsa         (8194),  -- 0x2002
                         interAreaPrefixLsa (8195),  -- 0x2003
                         interAreaRouterLsa (8196),  -- 0x2004
                         groupMembershipLsa (8198),  -- 0x2006
                         nssaExternalLsa    (8199),  -- 0x2007
                         intraAreaPrefixLsa (8201)   -- 0x2009
                       }
             MAX-ACCESS   read-only
             STATUS   current
             DESCRIPTION
                "The type  of  the  link  state  advertisement.
                Each  link state type has a separate advertise-
                ment format. Unrecognized Area-Scope LSAs with
                the U-bit set are also stored in this database."
           ::= { ospfv3AreaLsdbEntry 2 }


         ospfv3AreaLsdbRouterId OBJECT-TYPE
             SYNTAX   RouterID
             MAX-ACCESS   read-only
             STATUS   current
             DESCRIPTION
                "The 32 bit number that uniquely identifies the
                originating router in the Autonomous System."
            REFERENCE
               "OSPF Version 2, Appendix C.1 Global parameters"
           ::= { ospfv3AreaLsdbEntry 3 }


         ospfv3AreaLsdbLsid OBJECT-TYPE
             SYNTAX   IpAddress
             MAX-ACCESS   read-only
             STATUS   current
             DESCRIPTION
                "The Link State ID is an LS Type Specific field
                containing either a Router ID or a unique identifier;
                it identifies the piece of the  routing  domain
                that is being described by the advertisement.
                In contrast to OSPF for IPv4, the LSID has no
                addressing semantics."
           ::= { ospfv3AreaLsdbEntry 4 }


     --  Note that the OSPF Sequence Number is a 32 bit signed
     --  integer.  It starts with the value '80000001'h,
     --  or -'7FFFFFFF'h, and increments until '7FFFFFFF'h
     --  Thus, a typical sequence number will be very negative.

         ospfv3AreaLsdbSequence OBJECT-TYPE
             SYNTAX   Integer32
             MAX-ACCESS   read-only
             STATUS   current
             DESCRIPTION
                "The sequence number field is a  signed  32-bit
                integer.   It  is used to detect old and dupli-
                cate link state advertisements.  The  space  of
                sequence  numbers  is  linearly  ordered.   The
                larger the sequence number the more recent  the
                advertisement."
            REFERENCE
               "OSPF Version  2,  Section  12.1.6  LS  sequence
               number"
           ::= { ospfv3AreaLsdbEntry 5 }


         ospfv3AreaLsdbAge OBJECT-TYPE
             SYNTAX   Integer32    -- Should be 0..MaxAge
             MAX-ACCESS   read-only
             STATUS   current
             DESCRIPTION
                "This field is the age of the link state adver-
                tisement in seconds."
            REFERENCE
               "OSPF Version 2, Section 12.1.1 LS age"
           ::= { ospfv3AreaLsdbEntry 6 }

         ospfv3AreaLsdbChecksum OBJECT-TYPE
             SYNTAX   Integer32
             MAX-ACCESS   read-only
             STATUS   current
             DESCRIPTION
                "This field is the  checksum  of  the  complete
                contents  of  the  advertisement, excepting the
                age field.  The age field is excepted  so  that
                an   advertisement's  age  can  be  incremented
                without updating the  checksum.   The  checksum
                used  is  the same that is used for ISO connec-
                tionless datagrams; it is commonly referred  to
                as the Fletcher checksum."

            REFERENCE
               "OSPF Version 2, Section 12.1.7 LS checksum"
           ::= { ospfv3AreaLsdbEntry 7 }


         ospfv3AreaLsdbAdvertisement OBJECT-TYPE
             SYNTAX   OCTET STRING (SIZE (1..65535))
             MAX-ACCESS   read-only
             STATUS   current
             DESCRIPTION
                "The entire Link State Advertisement, including
                its header."
           ::= { ospfv3AreaLsdbEntry 8 }


     --  OSPFv3 Link-Scope Link State Database

     --      The Link State Database contains the Link-Scope Link State
     --      Advertisements from the links that the
     --      device is attached to.


         ospfv3LinkLsdbTable OBJECT-TYPE
             SYNTAX   SEQUENCE OF Ospfv3LinkLsdbEntry
             MAX-ACCESS   not-accessible
             STATUS   current
             DESCRIPTION
                "The OSPFv3 Process's Link-Scope Link State Database."
           ::= { ospfv3 5 }


         ospfv3LinkLsdbEntry OBJECT-TYPE
             SYNTAX   Ospfv3LinkLsdbEntry
             MAX-ACCESS   not-accessible
             STATUS   current
             DESCRIPTION
                "A single Link-Scope Link State Advertisement."
            INDEX { ospfv3LinkLsdbIfIndex,
                    ospfv3LinkLsdbType,
                    ospfv3LinkLsdbRouterId,
                    ospfv3LinkLsdbLsid }
            ::= { ospfv3LinkLsdbTable 1 }

     Ospfv3LinkLsdbEntry ::=
         SEQUENCE {
             ospfv3LinkLsdbIfIndex
                 Ipv6IfIndex,
             ospfv3LinkLsdbType
                 INTEGER,
             ospfv3LinkLsdbRouterId
                 RouterID,
             ospfv3LinkLsdbLsid
                 IpAddress,
             ospfv3LinkLsdbSequence
                 Integer32,
             ospfv3LinkLsdbAge
                 Integer32,
             ospfv3LinkLsdbChecksum
                 Integer32,
             ospfv3LinkLsdbAdvertisement
                 OCTET STRING
                   }

         ospfv3LinkLsdbIfIndex OBJECT-TYPE
             SYNTAX  Ipv6IfIndex
             MAX-ACCESS  read-only
             STATUS  current
             DESCRIPTION
                     "'The identifier of the link from which the LSA
                     was received.'
                              REFERENCE
                     'OSPF Version 2, Appendix C.2 Area parameters'"
             ::= { ospfv3LinkLsdbEntry 1 }


         ospfv3LinkLsdbType OBJECT-TYPE
             SYNTAX   INTEGER    {
                         linkLsa (8)   -- 0x0008
                       }
             MAX-ACCESS   read-only
             STATUS   current
             DESCRIPTION
                "The type  of  the  link  state  advertisement.
                Each  link state type has a separate advertise-
                ment format. Unrecognized Link-Scope LSAs with
                the U-bit set are also stored in this database."
           ::= { ospfv3LinkLsdbEntry 2 }


         ospfv3LinkLsdbRouterId OBJECT-TYPE
             SYNTAX   RouterID
             MAX-ACCESS   read-only
             STATUS   current
             DESCRIPTION
                "The 32 bit number that uniquely identifies the
                originating router in the Autonomous System."
            REFERENCE
               "OSPF Version 2, Appendix C.1 Global parameters"
           ::= { ospfv3LinkLsdbEntry 3 }


         ospfv3LinkLsdbLsid OBJECT-TYPE
             SYNTAX   IpAddress
             MAX-ACCESS   read-only
             STATUS   current
             DESCRIPTION
                "The Link State ID is an LS Type Specific field
                containing either a Router ID or a unique identifier;
                it identifies the piece of the  routing  domain
                that is being described by the advertisement.
                In contrast to OSPF for IPv4, the LSID has no
                addressing semantics."
           ::= { ospfv3LinkLsdbEntry 4 }


     --  Note that the OSPF Sequence Number is a 32 bit signed
     --  integer.  It starts with the value '80000001'h,
     --  or -'7FFFFFFF'h, and increments until '7FFFFFFF'h
     --  Thus, a typical sequence number will be very negative.

         ospfv3LinkLsdbSequence OBJECT-TYPE
             SYNTAX   Integer32
             MAX-ACCESS   read-only
             STATUS   current
             DESCRIPTION
                "The sequence number field is a  signed  32-bit
                integer.   It  is used to detect old and dupli-
                cate link state advertisements.  The  space  of
                sequence  numbers  is  linearly  ordered.   The
                larger the sequence number the more recent  the
                advertisement."
            REFERENCE
               "OSPF Version  2,  Section  12.1.6  LS  sequence
               number"
           ::= { ospfv3LinkLsdbEntry 5 }

         ospfv3LinkLsdbAge OBJECT-TYPE
             SYNTAX   Integer32    -- Should be 0..MaxAge
             MAX-ACCESS   read-only
             STATUS   current
             DESCRIPTION
                "This field is the age of the link state adver-
                tisement in seconds."
            REFERENCE
               "OSPF Version 2, Section 12.1.1 LS age"
           ::= { ospfv3LinkLsdbEntry 6 }

         ospfv3LinkLsdbChecksum OBJECT-TYPE
             SYNTAX   Integer32
             MAX-ACCESS   read-only
             STATUS   current
             DESCRIPTION
                "This field is the  checksum  of  the  complete
                contents  of  the  advertisement, excepting the
                age field.  The age field is excepted  so  that
                an   advertisement's  age  can  be  incremented
                without updating the  checksum.   The  checksum
                used  is  the same that is used for ISO connec-
                tionless datagrams; it is commonly referred  to
                as the Fletcher checksum."
            REFERENCE
               "OSPF Version 2, Section 12.1.7 LS checksum"
           ::= { ospfv3LinkLsdbEntry 7 }


         ospfv3LinkLsdbAdvertisement OBJECT-TYPE
             SYNTAX   OCTET STRING (SIZE (1..65535))
             MAX-ACCESS   read-only
             STATUS   current
             DESCRIPTION
                "The entire Link State Advertisement, including
                its header."
           ::= { ospfv3LinkLsdbEntry 8 }


     --  OSPF Host Table

     --      The Host/Metric Table indicates what hosts are directly
     --      attached to the Router, and what metrics and types of
     --      service should be advertised for them.
         ospfv3HostTable OBJECT-TYPE
             SYNTAX   SEQUENCE OF Ospfv3HostEntry
             MAX-ACCESS   not-accessible
             STATUS   current
             DESCRIPTION
                "The list of Hosts, and their metrics, that the
                router will advertise as host routes."
            REFERENCE
               "OSPF Version 2, Appendix C.6  Host route param-
               eters"
           ::= { ospfv3 6 }


         ospfv3HostEntry OBJECT-TYPE
             SYNTAX   Ospfv3HostEntry
             MAX-ACCESS   not-accessible
             STATUS   current
             DESCRIPTION
                "A metric to be advertised when a given host is reachable."
            INDEX { ospfv3HostIpv6Address }
            ::= { ospfv3HostTable 1 }


     Ospfv3HostEntry ::=
         SEQUENCE {
             ospfv3HostIpv6Address
                 Ipv6Address,
             ospfv3HostMetric
                 Metric,
             ospfv3HostStatus
                 RowStatus,
             ospfv3HostAreaID
                 AreaID
                   }

         ospfv3HostIpv6Address OBJECT-TYPE
             SYNTAX   Ipv6Address
             MAX-ACCESS   read-only
             STATUS   current
             DESCRIPTION
                "The IPv6 Address of the Host. Must be a Global
                 or Site-local address."
            REFERENCE
               "OSPF Version 2, Appendix C.6 Host route parame-
               ters"
           ::= { ospfv3HostEntry 1 }


         ospfv3HostMetric OBJECT-TYPE
             SYNTAX   Metric
             MAX-ACCESS   read-create
             STATUS   current
             DESCRIPTION
                "The Metric to be advertised."
            REFERENCE
               "OSPF Version 2, Appendix C.6 Host route parame-
               ters"
           ::= { ospfv3HostEntry 2 }

         ospfv3HostStatus OBJECT-TYPE
             SYNTAX   RowStatus
             MAX-ACCESS   read-create
             STATUS   current
             DESCRIPTION
                "This variable displays the status of  the  en-
                try.  Setting it to 'invalid' has the effect of
                rendering it inoperative.  The internal  effect
                (row removal) is implementation dependent."
            ::= { ospfv3HostEntry 3 }


         ospfv3HostAreaID OBJECT-TYPE
             SYNTAX   AreaID
             MAX-ACCESS   read-create
             STATUS   current
             DESCRIPTION
                "The Area the Host Entry is to be found within.
                By  default, the area that a subsuming OSPFv3 in-
                terface is in, or 0.0.0.0"
            REFERENCE
               "OSPF Version 2, Appendix C.2 Area parameters"
           ::= { ospfv3HostEntry 4 }


     --  OSPFv3 Interface Table

         ospfv3IfTable OBJECT-TYPE
             SYNTAX   SEQUENCE OF Ospfv3IfEntry
             MAX-ACCESS   not-accessible
             STATUS   current
             DESCRIPTION
                "The OSPFv3 Interface Table describes the  inter-
                faces from the viewpoint of OSPFv3."
            REFERENCE
               "OSPF Version 2, Appendix C.3  Router  interface
               parameters"
           ::= { ospfv3 7 }


         ospfv3IfEntry OBJECT-TYPE
             SYNTAX   Ospfv3IfEntry
             MAX-ACCESS   not-accessible
             STATUS   current
             DESCRIPTION
                "The OSPFv3 Interface Entry describes one  inter-
                face from the viewpoint of OSPFv3."
            INDEX { ospfv3IfIndex }
            ::= { ospfv3IfTable 1 }

     Ospfv3IfEntry ::=
         SEQUENCE {
             ospfv3IfIndex
                 Ipv6IfIndex,
             ospfv3IfAreaId
                 AreaID,
             ospfv3IfType
                 INTEGER,
             ospfv3IfAdminStat
                 Status,
             ospfv3IfRtrPriority
                 DesignatedRouterPriority,
             ospfv3IfTransitDelay
                 UpToMaxAge,
             ospfv3IfRetransInterval
                 UpToMaxAge,
             ospfv3IfHelloInterval
                 HelloRange,
             ospfv3IfRtrDeadInterval
                 PositiveInteger,
             ospfv3IfPollInterval
                 PositiveInteger,
             ospfv3IfState
                 INTEGER,
             ospfv3IfDesignatedRouter
                 RouterID,

             ospfv3IfBackupDesignatedRouter
                 RouterID,
             ospfv3IfEvents
                 Counter32,
             ospfv3IfStatus
                 RowStatus,
             ospfv3IfMulticastForwarding
                 INTEGER,
             ospfv3IfDemand
                 TruthValue,
             ospfv3IfMetricValue
                 Metric,
             ospfv3IfLinkScopeLsaCount
                 Gauge32,
             ospfv3IfLinkLsaCksumSum
                 Integer32,
             ospfv3IfInstId
                 Integer32
                   }

         ospfv3IfIndex OBJECT-TYPE
             SYNTAX   Ipv6IfIndex
             MAX-ACCESS   read-only
             STATUS   current
             DESCRIPTION
                "The interface index of this OSPFv3 interface.
                 It corresponds to the interface index of the
                 Ipv6 interface on which OSPFv3 is configured."
            ::= { ospfv3IfEntry 1 }


         ospfv3IfAreaId OBJECT-TYPE
             SYNTAX   AreaID
             MAX-ACCESS   read-create
             STATUS   current
             DESCRIPTION
                "A 32-bit integer uniquely identifying the area
                to  which  the  interface  connects.   Area  ID
                0.0.0.0 is used for the OSPFv3 backbone."
            DEFVAL   { '00000000'H }    -- 0.0.0.0
            ::= { ospfv3IfEntry 2 }

         ospfv3IfType OBJECT-TYPE
             SYNTAX   INTEGER    {
                         broadcast (1),
                         nbma (2),
                         pointToPoint (3),
                         pointToMultipoint (5)
                       }
             MAX-ACCESS   read-create
             STATUS   current
             DESCRIPTION
                "The OSPFv3 interface type."
            ::= { ospfv3IfEntry 3 }


         ospfv3IfAdminStat OBJECT-TYPE
             SYNTAX   Status
             MAX-ACCESS   read-create
             STATUS   current
             DESCRIPTION
                "The OSPFv3 interface's  administrative  status.
                The  value formed on the interface, and the in-
                terface will be advertised as an internal route
                to  some  area.   The  value 'disabled' denotes
                that the interface is external to OSPFv3."
            DEFVAL { enabled }
            ::= { ospfv3IfEntry 4 }

         ospfv3IfRtrPriority OBJECT-TYPE
             SYNTAX   DesignatedRouterPriority
             MAX-ACCESS   read-create
             STATUS   current
             DESCRIPTION
                "The  priority  of  this  interface.   Used  in
                multi-access  networks,  this  field is used in
                the designated router election algorithm.   The
                value 0 signifies that the router is not eligi-
                ble to become the  designated  router  on  this
                particular  network.   In the event of a tie in
                this value, routers will use their Router ID as
                a tie breaker."
            DEFVAL { 1 }
            ::= { ospfv3IfEntry 5 }


         ospfv3IfTransitDelay OBJECT-TYPE
             SYNTAX   UpToMaxAge
             MAX-ACCESS   read-create
             STATUS   current
             DESCRIPTION
                "The estimated number of seconds  it  takes  to
                transmit  a  link state update packet over this
                interface."
            DEFVAL { 1 }
            ::= { ospfv3IfEntry 6 }


         ospfv3IfRetransInterval OBJECT-TYPE
             SYNTAX   UpToMaxAge
             MAX-ACCESS   read-create
             STATUS   current
             DESCRIPTION
                "The number of seconds between  link-state  ad-
                vertisement  retransmissions,  for  adjacencies
                belonging to this  interface.   This  value  is
                also used when retransmitting database descrip-
                tion and link-state request packets."
            DEFVAL { 5 }
            ::= { ospfv3IfEntry 7 }


         ospfv3IfHelloInterval OBJECT-TYPE
             SYNTAX   HelloRange
             MAX-ACCESS   read-create
             STATUS   current
             DESCRIPTION
                "The length of time, in  seconds,  between  the
                Hello  packets that the router sends on the in-
                terface.  This value must be the same  for  all
                routers attached to a common network."
            DEFVAL { 10 }
            ::= { ospfv3IfEntry 8 }


         ospfv3IfRtrDeadInterval OBJECT-TYPE
             SYNTAX   PositiveInteger
             MAX-ACCESS   read-create
             STATUS   current
             DESCRIPTION
                "The number of seconds that  a  router's  Hello
                packets  have  not been seen before it's neigh-
                bors declare the router down.  This  should  be
                some  multiple  of  the  Hello  interval.  This
                value must be the same for all routers attached
                to a common network."
            DEFVAL { 40 }
            ::= { ospfv3IfEntry 9 }


         ospfv3IfPollInterval OBJECT-TYPE
             SYNTAX   PositiveInteger
             MAX-ACCESS   read-create
             STATUS   current
             DESCRIPTION
                "The larger time interval, in seconds,  between
                the  Hello  packets  sent  to  an inactive non-
                broadcast multi- access neighbor."
            DEFVAL { 120 }
            ::= { ospfv3IfEntry 10 }


         ospfv3IfState OBJECT-TYPE
             SYNTAX   INTEGER    {
                         down (1),
                         loopback (2),
                         waiting (3),
                         pointToPoint (4),
                         designatedRouter (5),
                         backupDesignatedRouter (6),
                         otherDesignatedRouter (7)
                       }
             MAX-ACCESS   read-only
             STATUS   current
             DESCRIPTION
                "The OSPFv3 Interface State."
            DEFVAL { down }
            ::= { ospfv3IfEntry 11 }


         ospfv3IfDesignatedRouter OBJECT-TYPE
             SYNTAX   RouterID
             MAX-ACCESS   read-only
             STATUS   current
             DESCRIPTION
                "The Router ID of the Designated Router."
            DEFVAL   { '00000000'H }  -- 0.0.0.0
            ::= { ospfv3IfEntry 12 }

         ospfv3IfBackupDesignatedRouter OBJECT-TYPE
             SYNTAX   RouterID
             MAX-ACCESS   read-only
             STATUS   current
             DESCRIPTION
                "The  Router ID of  the  Backup   Designated
                Router."
            DEFVAL   { '00000000'H }  -- 0.0.0.0
            ::= { ospfv3IfEntry 14 }

         ospfv3IfEvents OBJECT-TYPE
             SYNTAX   Counter32
             MAX-ACCESS   read-only
             STATUS   current
             DESCRIPTION
                "The number of times this  OSPF  interface  has
                changed its state, or an error has occurred."
            ::= { ospfv3IfEntry 15 }


         ospfv3IfStatus OBJECT-TYPE
             SYNTAX   RowStatus
             MAX-ACCESS   read-create
             STATUS   current
             DESCRIPTION
                "This variable displays the status of  the  en-
                try.  Setting it to 'invalid' has the effect of
                rendering it inoperative.  The internal  effect
                (row removal) is implementation dependent."
            ::= { ospfv3IfEntry 17 }


         ospfv3IfMulticastForwarding OBJECT-TYPE
             SYNTAX   INTEGER    {
                                 blocked (1),       -- no multicast forwarding
                                 multicast (2),     -- using multicast address
                                 unicast (3)        -- to each OSPFv3 neighbor
                       }
             MAX-ACCESS   read-create
             STATUS   current
             DESCRIPTION
                "The way multicasts should  forwarded  on  this
                interface;  not  forwarded,  forwarded  as data
                link multicasts, or forwarded as data link uni-
                casts.   Data link multicasting is not meaning-
                ful on point to point and NBMA interfaces,  and
                setting ospfv3MulticastForwarding to 0 effective-
                ly disables all multicast forwarding."
            DEFVAL { blocked }
            ::= { ospfv3IfEntry 18 }


         ospfv3IfDemand OBJECT-TYPE
             SYNTAX   TruthValue
             MAX-ACCESS   read-create
             STATUS   current
             DESCRIPTION
                "Indicates whether Demand OSPFv3 procedures (hel-
                lo supression to FULL neighbors and setting the
                DoNotAge flag on proogated LSAs) should be per-
                formed on this interface."
            DEFVAL { false }
            ::= { ospfv3IfEntry 19 }


         ospfv3IfMetricValue OBJECT-TYPE
             SYNTAX   Metric
             MAX-ACCESS   read-create
             STATUS   current
             DESCRIPTION
                "The metric assigned to this interface.
                 The default value of the Metric is
                 10^8 / ifSpeed."
            ::= { ospfv3IfEntry 20 }


         ospfv3IfLinkScopeLsaCount OBJECT-TYPE
             SYNTAX   Gauge32
             MAX-ACCESS   read-only
             STATUS   current
             DESCRIPTION
                "The total number of Link-Scope link-state advertisements
                in  this  link's link-state database."
            ::= { ospfv3IfEntry 21 }


         ospfv3IfLinkLsaCksumSum OBJECT-TYPE
             SYNTAX   Integer32
             MAX-ACCESS   read-only
             STATUS   current
             DESCRIPTION
                "The 32-bit unsigned sum of the Link-Scope link-state
                advertisements'  LS  checksums  contained in this
                link's link-state database.  The sum can be used
                to determine if  there  has been  a  change  in a
                router's link state database, and to compare the
                link-state database of two routers."
            DEFVAL   { 0 }
            ::= { ospfv3IfEntry 22 }


         ospfv3IfInstId OBJECT-TYPE
             SYNTAX   Integer32
             MAX-ACCESS   read-create
             STATUS   current
             DESCRIPTION
                "Enables multiple instances of OSPFv3 to be run over
                a single link. Each protocol instance would be assigned
                a separate ID. This ID has local link significance only."
            DEFVAL   { 0 }
            ::= { ospfv3IfEntry 23 }


     --  OSPFv3 Virtual Interface Table

     --      The Virtual Interface Table describes the virtual
     --      links that the OSPFv3 Process is configured to
     --      carry on.

         ospfv3VirtIfTable OBJECT-TYPE
             SYNTAX   SEQUENCE OF Ospfv3VirtIfEntry
             MAX-ACCESS   not-accessible
             STATUS   current
             DESCRIPTION
                "Information about this router's virtual inter-
                faces."
            REFERENCE
               "OSPF Version  2,  Appendix  C.4   Virtual  link
               parameters"
           ::= { ospfv3 8 }


         ospfv3VirtIfEntry OBJECT-TYPE
             SYNTAX   Ospfv3VirtIfEntry
             MAX-ACCESS   not-accessible
             STATUS   current
             DESCRIPTION
                "Information about a single Virtual Interface."
            INDEX { ospfv3VirtIfAreaId, ospfv3VirtIfNeighbor }
            ::= { ospfv3VirtIfTable 1 }

     Ospfv3VirtIfEntry ::=
         SEQUENCE {
             ospfv3VirtIfAreaId
                 AreaID,
             ospfv3VirtIfNeighbor
                 RouterID,
             ospfv3VirtIfIndex
                 Ipv6IfIndex,
             ospfv3VirtIfTransitDelay
                 UpToMaxAge,
             ospfv3VirtIfRetransInterval
                 UpToMaxAge,
             ospfv3VirtIfHelloInterval
                 HelloRange,
             ospfv3VirtIfRtrDeadInterval
                 PositiveInteger,
             ospfv3VirtIfState
                 INTEGER,
             ospfv3VirtIfEvents
                 Counter32,
             ospfv3VirtIfStatus
                 RowStatus,
             ospfv3VirtIfLinkScopeLsaCount
                 Gauge32,
             ospfv3VirtIfLinkLsaCksumSum
                 Integer32
                   }

         ospfv3VirtIfAreaId OBJECT-TYPE
             SYNTAX   AreaID
             MAX-ACCESS   read-only
             STATUS   current
             DESCRIPTION
                "The  Transit  Area  that  the   Virtual   Link
                traverses.  By definition, this is not 0.0.0.0"
            ::= { ospfv3VirtIfEntry 1 }


         ospfv3VirtIfNeighbor OBJECT-TYPE
             SYNTAX   RouterID
             MAX-ACCESS   read-only
             STATUS   current
             DESCRIPTION
                "The Router ID of the Virtual Neighbor."
            ::= { ospfv3VirtIfEntry 2 }


         ospfv3VirtIfIndex OBJECT-TYPE
             SYNTAX   Ipv6IfIndex
             MAX-ACCESS   read-create
             STATUS   current
             DESCRIPTION
                "The interface index of this OSPFv3 virtual interface.
                It must be unique among all the interface indices
                on the router."
            ::= { ospfv3VirtIfEntry 3 }


         ospfv3VirtIfTransitDelay OBJECT-TYPE
             SYNTAX   UpToMaxAge
             MAX-ACCESS   read-create
             STATUS   current
             DESCRIPTION
                "The estimated number of seconds  it  takes  to
                transmit  a link- state update packet over this
                interface."
            DEFVAL { 1 }
            ::= { ospfv3VirtIfEntry 4 }


         ospfv3VirtIfRetransInterval OBJECT-TYPE
             SYNTAX   UpToMaxAge
             MAX-ACCESS   read-create
             STATUS   current
             DESCRIPTION
                "The number of seconds between  link-state  ad-
                vertisement  retransmissions,  for  adjacencies
                belonging to this  interface.   This  value  is
                also used when retransmitting database descrip-
                tion  and  link-state  request  packets.   This
                value  should  be well over the expected round-
                trip time."
            DEFVAL { 5 }
            ::= { ospfv3VirtIfEntry 5 }

         ospfv3VirtIfHelloInterval OBJECT-TYPE
             SYNTAX   HelloRange
             MAX-ACCESS   read-create
             STATUS   current
             DESCRIPTION
                "The length of time, in  seconds,  between  the
                Hello  packets that the router sends on the in-
                terface.  This value must be the same  for  the
                virtual neighbor."
            DEFVAL { 10 }
            ::= { ospfv3VirtIfEntry 6 }


         ospfv3VirtIfRtrDeadInterval OBJECT-TYPE
             SYNTAX   PositiveInteger
             MAX-ACCESS   read-create
             STATUS   current
             DESCRIPTION
                "The number of seconds that  a  router's  Hello
                packets  have  not been seen before it's neigh-
                bors declare the router down.  This  should  be
                some  multiple  of  the  Hello  interval.  This
                value must be the same for the  virtual  neigh-
                bor."
            DEFVAL { 60 }
            ::= { ospfv3VirtIfEntry 7 }


         ospfv3VirtIfState OBJECT-TYPE
             SYNTAX   INTEGER    {
                         down (1),            -- these use the same encoding
                         pointToPoint (4)     -- as the ospfv3IfTable
                       }
             MAX-ACCESS   read-only
             STATUS   current
             DESCRIPTION
                "OSPF virtual interface states."
            DEFVAL   { down }
            ::= { ospfv3VirtIfEntry 8 }


         ospfv3VirtIfEvents OBJECT-TYPE
             SYNTAX   Counter32
             MAX-ACCESS   read-only
             STATUS   current
             DESCRIPTION
                "The number of state changes or error events on
                this Virtual Link"
            ::= { ospfv3VirtIfEntry 9 }


         ospfv3VirtIfStatus OBJECT-TYPE
             SYNTAX   RowStatus
             MAX-ACCESS   read-create
             STATUS   current
             DESCRIPTION
                "This variable displays the status of  the  en-
                try.  Setting it to 'invalid' has the effect of
                rendering it inoperative.  The internal  effect
                (row removal) is implementation dependent."
            ::= { ospfv3VirtIfEntry 10 }


         ospfv3VirtIfLinkScopeLsaCount OBJECT-TYPE
             SYNTAX   Gauge32
             MAX-ACCESS   read-only
             STATUS   current
             DESCRIPTION
                "The total number of Link-Scope link-state advertisements
                in  this  virtual link's link-state database."
            ::= { ospfv3VirtIfEntry 11 }


         ospfv3VirtIfLinkLsaCksumSum OBJECT-TYPE
             SYNTAX   Integer32
             MAX-ACCESS   read-only
             STATUS   current
             DESCRIPTION
                "The 32-bit unsigned sum of the Link-Scope link-state
                advertisements'  LS  checksums  contained in this
                virtual link's link-state database.  The sum can be used
                to determine if  there  has been  a  change  in a
                router's link state database, and to compare the
                link-state database of two routers."
            DEFVAL   { 0 }
            ::= { ospfv3VirtIfEntry 12 }



     --  OSPFv3 Neighbor Table
     --      The OSPFv3 Neighbor Table describes all neighbors in
     --      the locality of the subject router.

         ospfv3NbrTable OBJECT-TYPE
             SYNTAX   SEQUENCE OF Ospfv3NbrEntry
             MAX-ACCESS   not-accessible
             STATUS   current
             DESCRIPTION
                "A table of non-virtual neighbor information."
            REFERENCE
               "OSPF Version 2, Section 10  The  Neighbor  Data
               Structure"
           ::= { ospfv3 9 }


         ospfv3NbrEntry OBJECT-TYPE
             SYNTAX   Ospfv3NbrEntry
             MAX-ACCESS   not-accessible
             STATUS   current
             DESCRIPTION
                "The information regarding a single neighbor."
            REFERENCE
               "OSPF Version 2, Section 10  The  Neighbor  Data
               Structure"
           INDEX { ospfv3NbrIfIndex, ospfv3NbrRtrId }
           ::= { ospfv3NbrTable 1 }

     Ospfv3NbrEntry ::=
         SEQUENCE {
             ospfv3NbrIfIndex
                 Ipv6IfIndex,
             ospfv3NbrRtrId
                 RouterID,
             ospfv3NbrOptions
                 Integer32,
             ospfv3NbrPriority
                 DesignatedRouterPriority,
             ospfv3NbrState
                 INTEGER,
             ospfv3NbrEvents
                 Counter32,
             ospfv3NbrLsRetransQLen
                 Gauge32,
             ospfv3NbmaNbrStatus
                 RowStatus,

             ospfv3NbmaNbrPermanence
                 INTEGER,
             ospfv3NbrHelloSuppressed
                 TruthValue,
             ospfv3NbrIfId
                 Ipv6IfIndex
                   }

         ospfv3NbrIfIndex OBJECT-TYPE
             SYNTAX   Ipv6IfIndex
             MAX-ACCESS   read-only
             STATUS   current
             DESCRIPTION
                "The local link ID of the link over which the
                 neighbor can be reached."
            ::= { ospfv3NbrEntry 1 }


         ospfv3NbrRtrId OBJECT-TYPE
             SYNTAX   RouterID
             MAX-ACCESS   read-only
             STATUS   current
             DESCRIPTION
                "A 32-bit integer (represented as a type  IpAd-
                dress)  uniquely  identifying  the  neighboring
                router in the Autonomous System."
            ::= { ospfv3NbrEntry 2 }


         ospfv3NbrOptions OBJECT-TYPE
             SYNTAX   Integer32
             MAX-ACCESS   read-only
             STATUS   current
             DESCRIPTION
                "A Bit Mask corresponding to the neighbor's op-
                tions field."
           DEFVAL { 0 }
           ::= { ospfv3NbrEntry 3 }


         ospfv3NbrPriority OBJECT-TYPE
             SYNTAX   DesignatedRouterPriority
             MAX-ACCESS   read-create
             STATUS   current
             DESCRIPTION
                "The priority of this neighbor in the designat-
                ed router election algorithm.  The value 0 sig-
                nifies that the neighbor is not eligible to be-
                come  the  designated router on this particular
                network."
            DEFVAL { 1 }
            ::= { ospfv3NbrEntry 4 }


         ospfv3NbrState OBJECT-TYPE
             SYNTAX   INTEGER    {
                         down (1),
                         attempt (2),
                         init (3),
                         twoWay (4),
                         exchangeStart (5),
                         exchange (6),
                         loading (7),
                         full (8)
                       }
             MAX-ACCESS   read-only
             STATUS   current
             DESCRIPTION
                "The State of the relationship with this Neigh-
                bor."
            REFERENCE
               "OSPF Version 2, Section 10.1 Neighbor States"
           DEFVAL   { down }
           ::= { ospfv3NbrEntry 5 }


         ospfv3NbrEvents OBJECT-TYPE
             SYNTAX   Counter32
             MAX-ACCESS   read-only
             STATUS   current
             DESCRIPTION
                "The number of times this neighbor relationship
                has changed state, or an error has occurred."
            ::= { ospfv3NbrEntry 6 }


         ospfv3NbrLsRetransQLen OBJECT-TYPE
             SYNTAX   Gauge32
             MAX-ACCESS   read-only
             STATUS   current
             DESCRIPTION
                "The  current  length  of  the   retransmission
                queue."
            ::= { ospfv3NbrEntry 7 }


         ospfv3NbmaNbrStatus OBJECT-TYPE
             SYNTAX   RowStatus
             MAX-ACCESS   read-create
             STATUS   current
             DESCRIPTION
                "This variable displays the status of  the  en-
                try.  Setting it to 'invalid' has the effect of
                rendering it inoperative.  The internal  effect
                (row removal) is implementation dependent."
            ::= { ospfv3NbrEntry 8 }


         ospfv3NbmaNbrPermanence OBJECT-TYPE
             SYNTAX   INTEGER    {
                         dynamic (1),        -- learned through protocol
                         permanent (2)       -- configured address
                       }
             MAX-ACCESS   read-only
             STATUS   current
             DESCRIPTION
                "This variable displays the status of  the  en-
                try.   'dynamic'  and  'permanent' refer to how
                the neighbor became known."
            DEFVAL { permanent }
            ::= { ospfv3NbrEntry 9 }


         ospfv3NbrHelloSuppressed OBJECT-TYPE
             SYNTAX   TruthValue
             MAX-ACCESS   read-only
             STATUS   current
             DESCRIPTION
                "Indicates whether Hellos are being  suppressed
                to the neighbor"
            ::= { ospfv3NbrEntry 10 }


         ospfv3NbrIfId OBJECT-TYPE
             SYNTAX   Ipv6IfIndex
             MAX-ACCESS   read-only
             STATUS   current
             DESCRIPTION
                "The interface ID that the neighbor advertises
                in its Hello Packets on this link, that is, the
                neighbor's local interface index."
            ::= { ospfv3NbrEntry 11 }


     --  OSPFv3 Virtual Neighbor Table

     --      This table describes all virtual neighbors.
     --      Since Virtual Links are configured in the
     --      virtual interface table, this table is read-only.

         ospfv3VirtNbrTable OBJECT-TYPE
             SYNTAX   SEQUENCE OF Ospfv3VirtNbrEntry
             MAX-ACCESS   not-accessible
             STATUS   current
             DESCRIPTION
                "A table of virtual neighbor information."
            REFERENCE
               "OSPF Version 2, Section 15  Virtual Links"
           ::= { ospfv3 10 }


         ospfv3VirtNbrEntry OBJECT-TYPE
             SYNTAX   Ospfv3VirtNbrEntry

             MAX-ACCESS   not-accessible
             STATUS   current
             DESCRIPTION
                "Virtual neighbor information."
            INDEX { ospfv3VirtNbrArea, ospfv3VirtNbrRtrId }
            ::= { ospfv3VirtNbrTable 1 }

     Ospfv3VirtNbrEntry ::=
         SEQUENCE {
             ospfv3VirtNbrArea
                 AreaID,
             ospfv3VirtNbrRtrId
                 RouterID,
             ospfv3VirtNbrIfIndex
                 Ipv6IfIndex,
             ospfv3VirtNbrIpv6Addr
                 Ipv6Address,
             ospfv3VirtNbrOptions
                 Integer32,
             ospfv3VirtNbrState
                 INTEGER,
             ospfv3VirtNbrEvents
                 Counter32,
             ospfv3VirtNbrLsRetransQLen
                 Gauge32,
             ospfv3VirtNbrHelloSuppressed
                 TruthValue,
             ospfv3VirtNbrIfId
                 Ipv6IfIndex
                   }

         ospfv3VirtNbrArea OBJECT-TYPE
             SYNTAX   AreaID
             MAX-ACCESS   read-only
             STATUS   current
             DESCRIPTION
                "The Transit Area Identifier."
            ::= { ospfv3VirtNbrEntry 1 }


         ospfv3VirtNbrRtrId OBJECT-TYPE
             SYNTAX   RouterID
             MAX-ACCESS   read-only
             STATUS   current
             DESCRIPTION
                "A  32-bit  integer  uniquely  identifying  the
                neighboring router in the Autonomous System."
            ::= { ospfv3VirtNbrEntry 2 }


         ospfv3VirtNbrIfIndex OBJECT-TYPE
             SYNTAX   Ipv6IfIndex
             MAX-ACCESS   read-only
             STATUS   current
             DESCRIPTION
                "The local link ID for the virtual link over
                which the neighbor can be reached."
            ::= { ospfv3VirtNbrEntry 3 }


         ospfv3VirtNbrIpv6Addr OBJECT-TYPE
             SYNTAX   Ipv6Address
             MAX-ACCESS   read-only
             STATUS   current
             DESCRIPTION
                "The IPv6 address used to reach this Virtual Neighbor.
                It must be a Site-Local or Global scope address."
            ::= { ospfv3VirtNbrEntry 4 }


         ospfv3VirtNbrOptions OBJECT-TYPE
             SYNTAX   Integer32
             MAX-ACCESS   read-only
             STATUS   current
             DESCRIPTION
                "A Bit Mask corresponding to the neighbor's op-
                tions field."
            ::= { ospfv3VirtNbrEntry 5 }


         ospfv3VirtNbrState OBJECT-TYPE
             SYNTAX   INTEGER    {
                         down (1),
                         attempt (2),
                         init (3),
                         twoWay (4),
                         exchangeStart (5),
                         exchange (6),
                         loading (7),
                         full (8)
                       }
             MAX-ACCESS   read-only
             STATUS   current
             DESCRIPTION
                "The state of the  Virtual  Neighbor  Relation-
                ship."
            ::= { ospfv3VirtNbrEntry 6 }


         ospfv3VirtNbrEvents OBJECT-TYPE
             SYNTAX   Counter32
             MAX-ACCESS   read-only
             STATUS   current
             DESCRIPTION
                "The number of  times  this  virtual  link  has
                changed its state, or an error has occurred."
            ::= { ospfv3VirtNbrEntry 7 }


         ospfv3VirtNbrLsRetransQLen OBJECT-TYPE
             SYNTAX   Gauge32
             MAX-ACCESS   read-only
             STATUS   current
             DESCRIPTION
                "The  current  length  of  the   retransmission
                queue."
            ::= { ospfv3VirtNbrEntry 8 }


         ospfv3VirtNbrHelloSuppressed OBJECT-TYPE
             SYNTAX   TruthValue
             MAX-ACCESS   read-only
             STATUS   current
             DESCRIPTION
                "Indicates whether Hellos are being  suppressed
                to the neighbor"
            ::= { ospfv3VirtNbrEntry 9 }


         ospfv3VirtNbrIfId OBJECT-TYPE
             SYNTAX   Ipv6IfIndex
             MAX-ACCESS   read-only
             STATUS   current
             DESCRIPTION
                "The interface ID that the neighbor advertises
                in its Hello Packets on this virtual link, that is,
                the neighbor's local interface index."
            ::= { ospfv3VirtNbrEntry 10 }


     --
     --      The OSPFv3 Area Aggregate Table
     --

         ospfv3AreaAggregateTable OBJECT-TYPE
             SYNTAX   SEQUENCE OF Ospfv3AreaAggregateEntry
             MAX-ACCESS   not-accessible
             STATUS   current
             DESCRIPTION
                "A range of IPv6 prefixes specified by a
                prefix/prefix length  pair. Note that if
                ranges are configured such that one range sub-
                sumes  another range the most specific match is
                the preferred one."
           ::= { ospfv3 11 }


         ospfv3AreaAggregateEntry OBJECT-TYPE
             SYNTAX   Ospfv3AreaAggregateEntry
             MAX-ACCESS   not-accessible
             STATUS   current
             DESCRIPTION
                "A range of IPv6 prefixes specified by a
                prefix/prefix length  pair. Note that if
                ranges are configured such that one range sub-
                sumes  another range the most specific match is
                the preferred one."
            REFERENCE
               "OSPF Version 2, Appendix C.2  Area parameters"
           INDEX { ospfv3AreaAggregateAreaID, ospfv3AreaAggregateAreaLsdbType,
                   ospfv3AreaAggregateIndex }
           ::= { ospfv3AreaAggregateTable 1 }


     Ospfv3AreaAggregateEntry ::=
         SEQUENCE {
             ospfv3AreaAggregateAreaID
                 AreaID,
             ospfv3AreaAggregateAreaLsdbType
                 INTEGER,
             ospfv3AreaAggregateIndex
                 INTEGER,
             ospfv3AreaAggregatePrefix
                 Ipv6AddressPrefix,
             ospfv3AreaAggregatePrefixLen
                 INTEGER,
             ospfv3AreaAggregateStatus
                 RowStatus,
             ospfv3AreaAggregateEffect
                 INTEGER
                   }

         ospfv3AreaAggregateAreaID OBJECT-TYPE
             SYNTAX   AreaID
             MAX-ACCESS   read-only
             STATUS   current
             DESCRIPTION
                "The Area the Address Aggregate is to be  found
                within."
            REFERENCE
               "OSPF Version 2, Appendix C.2 Area parameters"
           ::= { ospfv3AreaAggregateEntry 1 }


         ospfv3AreaAggregateAreaLsdbType OBJECT-TYPE
             SYNTAX   INTEGER    {
                         interAreaPrefixLsa (8195), -- 0x2003
                         nssaExternalLsa    (8199)  -- 0x2007
                       }
             MAX-ACCESS   read-only
             STATUS   current
             DESCRIPTION
                "The type of the Address Aggregate.  This field
                specifies  the  Area Lsdb type that this Address Ag-
                gregate applies to."
            REFERENCE
               "OSPF Version 2, Appendix A.4.1 The  Link  State
               Advertisement header"
           ::= { ospfv3AreaAggregateEntry 2 }


         ospfv3AreaAggregateIndex OBJECT-TYPE
             SYNTAX   INTEGER (1..2147483647)
             MAX-ACCESS   read-only
             STATUS   current
             DESCRIPTION
                "A unique identifier for this aggregate table entry."
           ::= { ospfv3AreaAggregateEntry 3 }


         ospfv3AreaAggregatePrefix OBJECT-TYPE
             SYNTAX   Ipv6AddressPrefix
             MAX-ACCESS   read-create
             STATUS   current
             DESCRIPTION
                "The IPv6 Prefix."
            REFERENCE
               "OSPF Version 2, Appendix C.2 Area parameters"
           ::= { ospfv3AreaAggregateEntry 4 }

         ospfv3AreaAggregatePrefixLen OBJECT-TYPE
             SYNTAX   INTEGER ( 3..128 )
             UNITS    "bits"
             MAX-ACCESS   read-create
             STATUS   current
             DESCRIPTION
               "The length of the prefix (in bits). A prefix can
               not be shorter than 3 bits."
            REFERENCE
               "OSPF Version 2, Appendix C.2 Area parameters"
           ::= { ospfv3AreaAggregateEntry 5 }


         ospfv3AreaAggregateStatus OBJECT-TYPE
             SYNTAX   RowStatus
             MAX-ACCESS   read-create
             STATUS   current
             DESCRIPTION
                "This variable displays the status of  the  en-
                try.  Setting it to 'invalid' has the effect of
                rendering it inoperative.  The internal  effect
                (row removal) is implementation dependent."
            ::= { ospfv3AreaAggregateEntry 6 }


         ospfv3AreaAggregateEffect OBJECT-TYPE
             SYNTAX   INTEGER    {
                         advertiseMatching (1),
                         doNotAdvertiseMatching (2)
                       }
             MAX-ACCESS   read-create
             STATUS   current
             DESCRIPTION
                "Prefixes subsumed by ranges either trigger  the
                advertisement  of  the indicated aggregate (ad-
                vertiseMatching), or result in the prefix not
                being advertised at all outside the area."
            DEFVAL   { advertiseMatching }
            ::= { ospfv3AreaAggregateEntry 7 }


     -- conformance information

     ospfv3Conformance OBJECT IDENTIFIER ::= { ospfv3 12 }
     ospfv3Groups      OBJECT IDENTIFIER ::= { ospfv3Conformance 1 }
     ospfv3Compliances OBJECT IDENTIFIER ::= { ospfv3Conformance 2 }

     -- compliance statements

         ospfv3Compliance MODULE-COMPLIANCE
             STATUS  current
             DESCRIPTION
                "The compliance statement "
            MODULE  -- this module
            MANDATORY-GROUPS {
                         ospfv3BasicGroup,
                         ospfv3AreaGroup,
                         ospfv3IfGroup,
                         ospfv3VirtIfGroup,
                         ospfv3NbrGroup,
                         ospfv3VirtNbrGroup,
                         ospfv3AreaAggregateGroup
                }
            ::= { ospfv3Compliances 1 }


     -- units of conformance

         ospfv3BasicGroup    OBJECT-GROUP
             OBJECTS {
                         ospfv3RouterId,
                         ospfv3AdminStat,
                         ospfv3VersionNumber,
                         ospfv3AreaBdrRtrStatus,
                         ospfv3ASBdrRtrStatus,
                         ospfv3AsScopeLsaCount,
                         ospfv3AsScopeLsaCksumSum,
                         ospfv3OriginateNewLsas,
                         ospfv3RxNewLsas,
                         ospfv3ExtAreaLsdbLimit,
                         ospfv3MulticastExtensions,
                         ospfv3ExitOverflowInterval,
                         ospfv3DemandExtensions
             }
             STATUS  current
             DESCRIPTION
                "These objects are required for OSPFv3 systems."
            ::= { ospfv3Groups 1 }

         ospfv3AreaGroup    OBJECT-GROUP
             OBJECTS {
                         ospfv3AreaId,
                         ospfv3ImportAsExtern,
                         ospfv3SpfRuns,
                         ospfv3AreaBdrRtrCount,
                         ospfv3AsBdrRtrCount,
                         ospfv3AreaScopeLsaCount,
                         ospfv3AreaScopeLsaCksumSum,
                         ospfv3AreaSummary,
                         ospfv3AreaStatus,
                         ospfv3StubMetric
             }
             STATUS  current
             DESCRIPTION
                "These objects are required for OSPFv3 systems
                supporting areas."
            ::= { ospfv3Groups 2 }


         ospfv3AsLsdbGroup    OBJECT-GROUP
             OBJECTS {
                         ospfv3AsLsdbType,
                         ospfv3AsLsdbRouterId,
                         ospfv3AsLsdbLsid,
                         ospfv3AsLsdbSequence,
                         ospfv3AsLsdbAge,
                         ospfv3AsLsdbChecksum,
                         ospfv3AsLsdbAdvertisement
             }
             STATUS  current
             DESCRIPTION
                "These objects are required for OSPFv3 systems
                that display their AS-scope link state database."
            ::= { ospfv3Groups 3 }


         ospfv3AreaLsdbGroup    OBJECT-GROUP
             OBJECTS {
                         ospfv3AreaLsdbAreaId,
                         ospfv3AreaLsdbType,
                         ospfv3AreaLsdbRouterId,
                         ospfv3AreaLsdbLsid,
                         ospfv3AreaLsdbSequence,
                         ospfv3AreaLsdbAge,
                         ospfv3AreaLsdbChecksum,
                         ospfv3AreaLsdbAdvertisement
             }
             STATUS  current
             DESCRIPTION
                "These objects are required for OSPF6 systems
                that display their Area-scope link state database."
            ::= { ospfv3Groups 4 }


         ospfv3LinkLsdbGroup    OBJECT-GROUP
             OBJECTS {
                         ospfv3LinkLsdbIfIndex,
                         ospfv3LinkLsdbType,
                         ospfv3LinkLsdbRouterId,
                         ospfv3LinkLsdbLsid,
                         ospfv3LinkLsdbSequence,
                         ospfv3LinkLsdbAge,
                         ospfv3LinkLsdbChecksum,
                         ospfv3LinkLsdbAdvertisement
             }
             STATUS  current
             DESCRIPTION
                "These objects are required for OSPFv3  systems
                that display their Link-scope link state database."
            ::= { ospfv3Groups 5 }


         ospfv3HostGroup    OBJECT-GROUP
             OBJECTS {
                         ospfv3HostIpv6Address,
                         ospfv3HostMetric,
                         ospfv3HostStatus,
                         ospfv3HostAreaID
             }
             STATUS  current
             DESCRIPTION
                "These objects are required  for  OSPFv3  systems
                that support attached hosts."
            ::= { ospfv3Groups 6 }


         ospfv3IfGroup    OBJECT-GROUP
             OBJECTS {
                         ospfv3IfIndex,
                         ospfv3IfAreaId,
                         ospfv3IfType,
                         ospfv3IfAdminStat,
                         ospfv3IfRtrPriority,
                         ospfv3IfTransitDelay,
                         ospfv3IfRetransInterval,
                         ospfv3IfHelloInterval,
                         ospfv3IfRtrDeadInterval,
                         ospfv3IfPollInterval,
                         ospfv3IfState,
                         ospfv3IfDesignatedRouter,
                         ospfv3IfBackupDesignatedRouter,
                         ospfv3IfEvents,
                         ospfv3IfStatus,
                         ospfv3IfMulticastForwarding,
                         ospfv3IfDemand,
                         ospfv3IfMetricValue,
                         ospfv3IfLinkScopeLsaCount,
                         ospfv3IfLinkLsaCksumSum,
                         ospfv3IfInstId
             }
             STATUS  current
             DESCRIPTION
                "These interface objects are required for OSPFv3 systems."
            ::= { ospfv3Groups 7 }


         ospfv3VirtIfGroup    OBJECT-GROUP
             OBJECTS {
                         ospfv3VirtIfAreaId,
                         ospfv3VirtIfNeighbor,
                         ospfv3VirtIfIndex,
                         ospfv3VirtIfTransitDelay,
                         ospfv3VirtIfRetransInterval,
                         ospfv3VirtIfHelloInterval,
                         ospfv3VirtIfRtrDeadInterval,
                         ospfv3VirtIfState,
                         ospfv3VirtIfEvents,
                         ospfv3VirtIfStatus,
                         ospfv3VirtIfLinkScopeLsaCount,
                         ospfv3VirtIfLinkLsaCksumSum
             }
             STATUS  current
             DESCRIPTION
                "These virtual interface objects are required for OSPFv3 systems."
            ::= { ospfv3Groups 8 }


         ospfv3NbrGroup    OBJECT-GROUP
             OBJECTS {
                         ospfv3NbrIfIndex,
                         ospfv3NbrRtrId,
                         ospfv3NbrOptions,
                         ospfv3NbrPriority,
                         ospfv3NbrState,
                         ospfv3NbrEvents,
                         ospfv3NbrLsRetransQLen,
                         ospfv3NbmaNbrStatus,
                         ospfv3NbmaNbrPermanence,
                         ospfv3NbrHelloSuppressed,
                         ospfv3NbrIfId
             }
             STATUS  current
             DESCRIPTION
                "These neighbor objects are required for OSPFv3 systems."
            ::= { ospfv3Groups 9 }


         ospfv3VirtNbrGroup    OBJECT-GROUP
             OBJECTS {
                         ospfv3VirtNbrArea,
                         ospfv3VirtNbrRtrId,
                         ospfv3VirtNbrIfIndex,
                         ospfv3VirtNbrIpv6Addr,
                         ospfv3VirtNbrOptions,
                         ospfv3VirtNbrState,
                         ospfv3VirtNbrEvents,
                         ospfv3VirtNbrLsRetransQLen,
                         ospfv3VirtNbrHelloSuppressed,
                         ospfv3VirtNbrIfId
             }
             STATUS  current
             DESCRIPTION
                "These virtual neighbor objects are required for OSPFv3 systems."
            ::= { ospfv3Groups 10 }


         ospfv3AreaAggregateGroup    OBJECT-GROUP
             OBJECTS {
                         ospfv3AreaAggregateAreaID,
                         ospfv3AreaAggregateAreaLsdbType,
                         ospfv3AreaAggregateIndex,
                         ospfv3AreaAggregatePrefix,
                         ospfv3AreaAggregatePrefixLen,
                         ospfv3AreaAggregateStatus,
                         ospfv3AreaAggregateEffect
             }
             STATUS  current
             DESCRIPTION
                "These area aggregate objects are required for OSPFv3 systems."
            ::= { ospfv3Groups 11 }

     END

-- 
--      Copyright  (C)  The  Internet  Society  (1999).   All   Rights
--      Reserved.
-- 
--      This document  and  translations  of  it  may  be  copied  and
--      furnished  to  others, and derivative works that comment on or
--      otherwise explain it or assist in its  implementation  may  be
--      prepared,  copied,  published  and distributed, in whole or in
--      part, without restriction of any kind, provided that the above
--      copyright  notice  and this paragraph are included on all such
--      copies and derivative works.  However,  this  document  itself
--      may  not  be  modified  in  any  way,  such as by removing the
--      copyright notice or references  to  the  Internet  Society  or
--      other Internet organizations, except as needed for the purpose
--      of developing Internet standards in which case the  procedures
--      for  copyrights defined in the Internet Standards process must
--      be followed, or as required to  translate  it  into  languages
--      other than English.
-- 
--      The limited permissions granted above are perpetual  and  will
--      not  be  revoked  by the Internet Society or its successors or
--      assigns.
-- 
--      This document and the information contained herein is provided
--      on  an "AS IS" basis and THE INTERNET SOCIETY AND THE INTERNET
--      ENGINEERING TASK FORCE DISCLAIMS ALL  WARRANTIES,  EXPRESS  OR
--      IMPLIED,  INCLUDING  BUT  NOT LIMITED TO ANY WARRANTY THAT THE
--      USE OF THE INFORMATION HEREIN WILL NOT INFRINGE ANY RIGHTS  OR
--      ANY  IMPLIED  WARRANTIES  OF  MERCHANTABILITY OR FITNESS FOR A
--      PARTICULAR PURPOSE.
--
