-- extracted from draft-ietf-entmib-ext-00.txt
-- at Mon Nov 15 17:10:57 1999

ENTITY-EXTENSIONS-MIB DEFINITIONS ::= BEGIN

IMPORTS
    MODULE-IDENTITY, OBJECT-TYPE
        FROM SNMPv2-SMI
    MODULE-COMPLIANCE, OBJECT-GROUP
        FROM SNMPv2-CONF
    SnmpEngineID, SnmpAdminString
        FROM SNMP-FRAMEWORK-MIB
    entityMIBObjects, entPhysicalEntry, entLogicalEntry,
    entityCompliances, entityGroups, entityPhysicalGroup
        FROM ENTITY-MIB;

entityXMIB MODULE-IDENTITY
    LAST-UPDATED "9803110000Z"
    ORGANIZATION "IETF Entity MIB Working Group"
    CONTACT-INFO
       "IETF Entity MIB WG Mailing List
        WG Subscribe:
           majordomo@cisco.com
           message body: subscribe entmib
        WG Discussion:
           entmib@cisco.com
        WG Archive:
           ftp://ftpeng.cisco.com/ftp/entmib/entmib

        Andy Bierman
        Cisco Systems Inc.
        170 West Tasman Drive
        San Jose, CA 95134
        408-527-3711
        abierman@cisco.com

        Keith McCloghrie
        Cisco Systems Inc.
        170 West Tasman Drive
        San Jose, CA 95134
        408-526-5260
        kzm@cisco.com"
    DESCRIPTION
            "The extension MIB module for physical entity information."
    ::= { experimental xx }

--
--  New Entity MIB Object Groups
--
entityPhysicalX  OBJECT IDENTIFIER ::= { entityMIBObjects 5 }
entityLogicalX   OBJECT IDENTIFIER ::= { entityMIBObjects 6 }

--  ***********************************************************
--
--     E N T I T Y     P H Y S I C A L    E X T E N S I O N S
--
--  ***********************************************************

-- entPhysicalTable extensions
entPhysicalXTable OBJECT-TYPE
    SYNTAX      SEQUENCE OF EntPhysicalXEntry
    MAX-ACCESS  not-accessible
    STATUS      current
    DESCRIPTION
            "This table contains one row per physical element
            represented in the entPhysicalTable."
    ::= { entityPhysicalX 1 }

entPhysicalXEntry       OBJECT-TYPE
    SYNTAX      EntPhysicalXEntry
    MAX-ACCESS  not-accessible
    STATUS      current
    DESCRIPTION
            "Information about a particular physical entity."
    AUGMENTS   { entPhysicalEntry }
    ::= { entPhysicalXTable 1 }

EntPhysicalXEntry ::= SEQUENCE {
      entPhysicalAlias          SnmpAdminString
}

entPhysicalAlias    OBJECT-TYPE
    SYNTAX      SnmpAdminString (SIZE (0..32))
    MAX-ACCESS  read-write
    STATUS      current
    DESCRIPTION
            "This object is an 'alias' name for the physical entity as
            specified by a network manager, and provides a non-volatile
            'handle' for the physical entity.

            On the first instantiation of an physical entity, the value
            of entPhysicalAlias associated with that entity is set to
            the zero-length string. An agent may instead choose to set
            the value to a locally unique default value instead of a
            zero-length string.

            If write access is implemented for an instance of
            entPhysicalAlias, and a value is written into the instance,
            the agent must retain the supplied value in the
            entPhysicalAlias instance associated with the same physical
            entity for as long as that entity remains instantiated,
            including across all re-initializations/reboots of the
            network management system, including those which result in a
            change of the physical entity's entPhysicalIndex value."
    ::= { entPhysicalXEntry 1 }

--  ***********************************************************
--
--     E N T I T Y     L O G I C A L    E X T E N S I O N S
--
--  ***********************************************************

-- entLogicalTable extensions
entLogicalXTable OBJECT-TYPE
    SYNTAX      SEQUENCE OF EntLogicalXEntry
    MAX-ACCESS  not-accessible
    STATUS      current
    DESCRIPTION
            "This table contains one row per logical entity represented
            in the entLogicalTable."
    ::= { entityLogicalX 1 }

entLogicalXEntry       OBJECT-TYPE
    SYNTAX      EntLogicalXEntry
    MAX-ACCESS  not-accessible
    STATUS      current
    DESCRIPTION
            "Information about a particular logical entity."
    AUGMENTS   { entLogicalEntry }
    ::= { entLogicalXTable 1 }

EntLogicalXEntry ::= SEQUENCE {
      entLogicalContextEngineID      SnmpEngineID,
      entLogicalContextName          SnmpAdminString
}

entLogicalContextEngineID    OBJECT-TYPE
    SYNTAX      SnmpEngineID
    MAX-ACCESS  read-only
    STATUS      current
    DESCRIPTION
            "The contextEngineID that can be used to send an SNMPv3
            message concerning information held by this logical entity,
            to the address specified by the associated
            'entLogicalTAddress/entLogicalTDomain' pair."
    ::= { entLogicalXEntry 1 }

entLogicalContextName    OBJECT-TYPE
    SYNTAX      SnmpAdminString
    MAX-ACCESS  read-only
    STATUS      current
    DESCRIPTION
            "The contextName that can be used to send an SNMPv3 message
            concerning information held by this logical entity, to the
            address specified by the associated
            'entLogicalTAddress/entLogicalTDomain' pair."
    ::= { entLogicalXEntry 2 }

-- conformance information
-- compliance statements

entityPhysicalXCompliance MODULE-COMPLIANCE
    STATUS  current
    DESCRIPTION
            "The compliance statement for SNMP entities which implement
            the Entity MIB PhysicalX Extensions.
    MODULE  -- this module
        MANDATORY-GROUPS {
                entityPhysicalGroup,
                entityPhysicalXGroup
        }

        OBJECT entPhysicalAlias
        MIN-ACCESS   read-only
        DESCRIPTION
                      "Write access is required if the associated
                      entPhysicalClass value is equal to 'chassis(3)'.
                      Otherwise, write access is not required."
    ::= {  entityCompliances 2 }

entityLogicalXCompliance MODULE-COMPLIANCE
    STATUS  current
    DESCRIPTION
            "The compliance statement for SNMP entities which implement
            the Entity MIB LogicalX Extensions.
    MODULE  -- this module
        MANDATORY-GROUPS {
                entityLogicalGroup,
                entityLogicalXGroup
        }
    ::= {  entityCompliances 3 }


-- MIB groupings
entityPhysicalXGroup    OBJECT-GROUP
    OBJECTS {
        entPhysicalAlias
    }
    STATUS  current
    DESCRIPTION
            "The collection of objects which are used to represent
            extended physical component information for which a single
            agent provides management information."
    ::= { entityGroups 6 }

entityLogicalXGroup    OBJECT-GROUP
    OBJECTS {
        entLogicalContextEngineID,
        entLogicalContextName,
    }
    STATUS  current
    DESCRIPTION
            "The collection of objects which are used to represent
            extended logical entity information for which a single agent
            provides management information."
    ::= { entityGroups 7 }

END
