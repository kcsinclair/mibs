-- extracted from draft-kajos-hmultimediamib-00.txt
-- at Mon Nov 15 17:11:06 1999

        H320ENTIRY-MIB DEFINITIONS ::= BEGIN
             IMPORTS
                  MODULE-IDENTITY, OBJECT-TYPE, Counter32,
                  experimental, NOTIFICATION-TYPE, Integer32
                       FROM SNMPv2-SMI
                  TEXTUAL-CONVENTION, DisplayString
                       FROM SNMPv2-TC
                  MODULE-COMPLIANCE, OBJECT-GROUP, NOTIFICATION-GROUP
                       FROM SNMPv2-CONF;
        
        
             h320EntityMIB MODULE-IDENTITY
                  LAST-UPDATED "9808011400Z" -- August 1, 1998
                  ORGANIZATION "VTEL Corp. "
                  CONTACT-INFO
                       "Joon Maeng
                       VTEL Corp.
                        Postal: 108 Wild Basin Rd.
                                      Austin, TX 78746
                                      USA
                       TEL: (512)437-4567
                       Email: Joon_Maeng@vtel.com"
                  DESCRIPTION
                       "This MIB module supports the common functions of the
                       IUT H.320 terminal, MCU and H.320/H.323 gateway"
                  REVISION "9808011400Z" -- August 1, 1998
                  DESCRIPTION
                       " The draft version of the H320 entity mib"
                  ::= {experimental 221 2} -- temporary OID. TBD.
        
             -- Textual conventions (to be moved to overall TC at the top level)
        
             LineRates ::=TEXTUAL-CONVENTION
                  STATUS current
                  DESCRIPTION
                       "This object represents the line rate capabilities of
                       the H.320 entity. This includes the various line rates
                       that it supports. It is encoded as bits in
                       an octet string as follows:
        
                            Capability          Bit#
                            64 Kbits/s     0
                            2x64 Kbits/s   1
                            3x64 Kbits/s   2
                            4x64 Kbis/s    3
                            5x64 Kbits/s   4
                            6x64 Kbit/s    5
                            384 Kbits/s    6
                            2x384 Kbits/s  7
                            3x384 Kbits/s  8
                            5x384 Kbits/s  9
                            1536 Kbits/s   10
                            1920 Kbits/s   11
                            128 Kbits/s    12
                            192 Kbits/s    13
                            256 Kbits/s    14
                            320 Kbits/s    15
                            512 Kbits/s    16
                            768 Kbits/s    17
                            1152 Kbits/s   18
                            1452 Kbits/s   19
        
                       Bits are numbered starting with the most
                       significant bit of the first byte being bit 0, the
                       least significant bit of the first byte being bit
                       7, the most significant bit of the second byte
                       being bit 8, and so on.  A one bit encodes that
                       the capability is supported, a zero bit encodes that
                       the capability is not supported."
        
                  SYNTAX    Integer32
        
             VideoFormats ::=TEXTUAL-CONVENTION
                  STATUS current
                  DESCRIPTION
                       "This object represents the video capabilities of the
                       H320 entity. This includes the various video algorithms that
                       it supports. It is encoded as bits in an octet string,
                       with the following definitions:
        
                            Capability          Bit #
                            h261CIFVideo        0
                            h261QCIFVideo       1
                            h263SQCIFVideo      2
                            h263QCIFVideo       3
                            h263CIFVideo        4
                            h263CIF4Video       5
                            h263CIF16Video      6
                            h262SPMLSIFVideo    7
                            h262SPML2SIFVideo   8
                            h262SPML4SIFVideo   9
                            h262MPMLSIFVideo         10
                            h262MPML2SIFVideo        11
                            h262MPML4SIFVideo        12
        
                       Bits are numbered starting with the most
                       significant bit of the first byte being bit 0, the
                       least significant bit of the first byte being bit
                       7, the most significant bit of the second byte
                       being bit 8, and so on.  A one bit encodes that
                       the capability is supported, a zero bit encodes that
                       the capability is not supported."
        
                  SYNTAX Integer32
        
             AudioTypes ::=TEXTUAL-CONVENTION
                  STATUS current
                  DESCRIPTION
                       "This object represents the audio capabilities of the
                       H320 entity. This includes the various audio algorithms
        		That it supports. It is encoded as bits in an octet string, 
			with the following definitions:
        
                                     Capability          Bit #
        
                                      g711-ALaw64KAudio   0
                                      g711-ALaw56KAudio   1
                                      g711-ULaw64KAudio   2
                                      g711-ULaw56KAudio   3
                                      g722-64KAudio  	  4
                                      g722-56KAudio       5
                                      g722-48KAudio       6
                                      g728Audio           7
                                      g723.1-5.3KAudio    8
                                      g723.1-6.4KAudio    9
                                      g729Audio           10
        
                       Bits are numbered starting with the most
                       significant bit of the first byte being bit 0, the
                       least significant bit of the first byte being bit
                       7, the most significant bit of the second byte
                       being bit 8, and so on.  A one bit encodes that
                       the capability is supported, a zero bit encodes that
                       the capability is not supported."
        
                  SYNTAX Integer32
             capability     OBJECT IDENTIFIER ::= { h320EntityMIB 1  }
             callStatus     OBJECT IDENTIFIER ::= { h320EntityMIB 2  }
             h221Stats OBJECT IDENTIFIER ::= { h320EntityMIB 3  }
             events         OBJECT IDENTIFIER ::= { h320EntityMIB 4  }
        
             -- H320 entity capability
             --
        
             capsH320Table OBJECT-TYPE
                  SYNTAX  SEQUENCE OF CapsH320Entry
                  MAX-ACCESS  not-accessible
                  STATUS  current
                  DESCRIPTION
             "A list of capability entries.  Objects are grouped as a
	        table so that one can use this table in the H.320 terminal,
                the H.320 MCU, and the H.320/H.323 gateway.
                The total number of capability entries is
                equal to the number of H.320 entities in a system.
                For instance, there will be one row of capability
                in the table of the H.320 terminal.  The number of rows
                will be equal to the number of H320 entities in the MCU
                and the H320/H323 gateway"
                   ::= { capability 1 }
        
                  capsH320Entry  OBJECT-TYPE
                       SYNTAX  CapsH320Entry
                       MAX-ACCESS  not-accessible
                       STATUS  current
                       DESCRIPTION
                            "A capability  row."
                       INDEX   { terminalIndex }
                  ::= { capsH320Table 1 }
        
                  CapsH320Entry ::=
                  SEQUENCE {
                                 terminalIndex
                                      INTEGER,
                       capsH320EntityLineRate
                            LineRates,
                       capsH320EntityVideoFormats
                            VideoFormats,
                       capsH320EntityMaxVideoRate
                            Integer32,
                       capsH320EntityAudioTypes
                            AudioTypes,
                       capsH320EntityDataCaps
                            Integer32,
                       capsH320EntityEncryp
                            Integer32,
                       capsH320EntryRDC
                            Integer32
                  }
        
                  terminalIndex OBJECT-TYPE
                       SYNTAX  INTEGER (1..2147483647)
                       MAX-ACCESS  not-accessible
                       STATUS  current
                       DESCRIPTION
                       "A unique value for each video conference entity.
                       The value ranges between 1 and the number of H.320 entities
                       in a System.  For instance, the table in the H.320 terminal
		        has one row and the H.323/H320 gateway or the H.320 MCU may
                       have multiple rows of the H.320 capability. "
                  ::= { capsH320Entry 1 }
        
             capsH320EntityLineRate OBJECT-TYPE
                  SYNTAX LineRates
                       MAX-ACCESS read-only
                  STATUS current
                  DESCRIPTION
                       "This object represents the line rate capabilities of                    						the H.320 entity.  Supported line rates are indicated by
                       an octet string marked with 1s."
        
             ::= { capsH320Entry 2 }
        
             capsH320EntityVideoFormats OBJECT-TYPE
                  SYNTAX VideoFormats
                       MAX-ACCESS read-only
                  STATUS current
                  DESCRIPTION
                       "This object represents the video capabilities of the
                       H.320 entity. This includes the various video algorithms
                          that it supports."
        
             ::= { capsH320Entry 3 }
        
             capsH320EntityMaxVideoRate OBJECT-TYPE
                  SYNTAX  Integer32
                  MAX-ACCESS  read-only
                  STATUS  current
                  DESCRIPTION
                       "The maximum bit rate that the video channel can do."
             ::= { capsH320Entry 4 }
        
             capsH320EntityAudioTypes OBJECT-TYPE
                  SYNTAX AudioTypes
                  MAX-ACCESS read-only
                  STATUS current
                  DESCRIPTION
                       "This object represents the audio capabilities of the
                       H320 entity. This includes the various audio algorithms
                          that it supports."
             ::= { capsH320Entry 5 }
        
                  capsH320EntityDataCaps OBJECT-TYPE
                  SYNTAX Integer32
                  MAX-ACCESS read-only
                  STATUS current
                  DESCRIPTION
                       "This object represents the data capability of the
                       entity. It is encoded as bits in an octet string,
                       with the following definitions:
        
                                Capability          Bit #
                                 t.120               0
                                 Others              1
        
                       Bits are numbered starting with the most
                       significant bit of the first byte being bit 0, the
                       least significant bit of the first byte being bit
                       7, the most significant bit of the second byte
                       being bit 8, and so on.  A one bit encodes that
                       the capability is supported, a zero bit encodes
        	       that the capability is not supported."
             ::= { capsH320Entry 6 }
        
             capsH320EntityEncryp OBJECT-TYPE
                  SYNTAX Integer32
                  MAX-ACCESS read-only
                  STATUS current
                  DESCRIPTION
                       "This object represents the encryption capability of the
                       entity.
        
                            Capability          Bit #
                                 H.233/H.234         0
                                 Others              1
        
                       Bits are numbered starting with the most
                       significant bit of the first byte being bit 0, the
                       least significant bit of the first byte being bit
                       7, the most significant bit of the second byte
                       being bit 8, and so on.  A one bit encodes that
                       the capability is supported, a zero bit encodes that
                       the capability is not supported."
                  ::= { capsH320Entry 7 }
        
             capsH320EntryRDC OBJECT-TYPE
                  SYNTAX Integer32
                  MAX-ACCESS read-only
                  STATUS current
                  DESCRIPTION
                       "This object represents the Remote Device Control
                       capability of the entity.
        
                       Capability          Bit #
                       H.281               0   -- Far-end Camera Control
                            Others              1
        
                       Bits are numbered starting with the most
                       significant bit of the first byte being bit 0, the
                       least significant bit of the first byte being bit
                       7, the most significant bit of the second byte
                       being bit 8, and so on.  A one bit encodes that
                       the capability is supported, a zero bit encodes that
                       the capability is not supported."
                  ::= { capsH320Entry 8 }
        
             -- Call status group
             -- This group provides the information about the status of
             -- the calls in progress
        
             callStatusTable OBJECT-TYPE
                       SYNTAX  SEQUENCE OF CallStatusEntry
                       MAX-ACCESS  not-accessible
                       STATUS  current
                       DESCRIPTION
                       "A list of call status entries.  Objects are grouped as a
                           table so that one can use this table in the H.320
                           terminal, the H.320 MCU, and the H.320/H.323 gateway.
                       The total number of call status entries is equal to the
                          number of H.320 entities in a system. For instance, there
                          will be one row of call status in the table of the H.320
                          terminal.  The number of rows will be equal to the number
                          of H320 entities in the MCU and the H320/H323 gateway"
        
                   ::= { callStatus 1 }
        
                  callStatusEntry  OBJECT-TYPE
                       SYNTAX  CallStatusEntry
                       MAX-ACCESS  not-accessible
                       STATUS  current
                       DESCRIPTION
                            "A call status  row."
                       AUGMENTS { capsH320Entry }
                   ::= { callStatusTable 1 }
        
                  CallStatusEntry ::=
                  SEQUENCE {
                       h320CurrentCallStatus
                            INTEGER,
                       h320CallSiteName
                            DisplayString,
                       h320CallLineRate
                            LineRates,
                       h320CallVideoInFormat
                            VideoFormats,
                       h320CallVideoOutFormat
                            VideoFormats,
                       h320CallAudioInFormat
                            AudioTypes,
                       h320CallAudioOutFormat
                            AudioTypes,
                       h320CallData
                            INTEGER,
                       h320CallEncryp
                            INTEGER,
                       h320CallRDC
                            INTEGER
                  }
        
        
             h320CurrentCallStatus OBJECT-TYPE
                  SYNTAX  INTEGER {
                       idle(1),
                       connecting(2),
                       connected(3),
                       disconnecting(4),
                       disconnected(5)
                       }
                  MAX-ACCESS  read-only
                  STATUS  current
                  DESCRIPTION
                       "The current call status."
             ::= { callStatusEntry 2 }
        
             h320CallSiteName OBJECT-TYPE
                  SYNTAX  DisplayString (SIZE (0..255))
                  MAX-ACCESS  read-only
                  STATUS  current
                  DESCRIPTION
                       "The address to which this call is made. "
             ::= { callStatusEntry 3 }
        
             h320CallLineRate OBJECT-TYPE
                  SYNTAX LineRates
                  MAX-ACCESS  read-only
                  STATUS  current
                  DESCRIPTION
                       "This object represents the line rate being used
                       in the current call in progress."
             ::= { callStatusEntry 4 }
             h320CallVideoInFormat OBJECT-TYPE
                  SYNTAX VideoFormats
                  MAX-ACCESS read-only
                  STATUS current
                  DESCRIPTION
                       "This object represents the video decoding format being
                       used in the current call in progress."
             ::= { callStatusEntry 5 }
        
             h320CallVideoOutFormat OBJECT-TYPE
                  SYNTAX VideoFormats
                  MAX-ACCESS read-only
                  STATUS current
                  DESCRIPTION
                       "This object represents the video encoding format being
                       used in the current call in progress."
             ::= { callStatusEntry 6 }
        
             h320CallAudioInFormat OBJECT-TYPE
                  SYNTAX AudioTypes
                  MAX-ACCESS read-only
                  STATUS current
                  DESCRIPTION
                       "This object represents the audio decoding format
                       being used in the current call in progress."
             ::= { callStatusEntry 7 }
        
             h320CallAudioOutFormat OBJECT-TYPE
                  SYNTAX AudioTypes
                  MAX-ACCESS read-only
                  STATUS current
                  DESCRIPTION
                       "This object represents the audio encoding format
                       being used in the current call in progress."
             ::= { callStatusEntry 8 }
        
             h320CallData OBJECT-TYPE
                  SYNTAX INTEGER {
                       t120(1),
                       other(2)
                       }
                  MAX-ACCESS read-only
                  STATUS current
                  DESCRIPTION
                       "This object represents the type of data communication
                       protocol used in the call.
                       1 indicates T.120 is used .
                       2 indicates other type of data is used."
             ::= { callStatusEntry 9 }
        
             h320CallEncryp OBJECT-TYPE
                  SYNTAX INTEGER {
                       h233(1),
                       other(2)
                       }
                  MAX-ACCESS read-only
                  STATUS current
                  DESCRIPTION
                       "This object indicates the type of encryption
                       protocol used in the call.
                       1 indicates the encryption based on H.323.
                       2 indicates other type of encryption."
             ::= { callStatusEntry 10 }
        
             h320CallRDC OBJECT-TYPE
                  SYNTAX INTEGER {
                       h281FECC(1),
                       other(2)
                       }
                  MAX-ACCESS read-only
                  STATUS current
                  DESCRIPTION
                       "This object indicates the type of remote device
                       control.
                       1 indicates the FECC is used.
                       2 indicates other type of device is used. "
             ::= { callStatusEntry 11 }
        
             --
             -- H.221 statistics
             --
        
             h221StatsTable OBJECT-TYPE
                       SYNTAX  SEQUENCE OF H221StatsEntry
                       MAX-ACCESS  not-accessible
                       STATUS  current
                       DESCRIPTION
                       "A list of statistics entries.  Objects are grouped as a
                       table so that one can use this table in the H.320 terminal,
                      the H.320 MCU, and the H.320/H.323 gateway.
                       The total number of statistics entries is
                      equal to the number of H.320 entities in a system.
                       For instance, there will be one row of statistics
                      in the table of the H.320 terminal.  The number of rows
                       will be equal to the number of H320 entities in the MCU
                       and the H320/H323 gateway"
                  ::= { h221Stats 1 }
        
                  h221StatsEntry  OBJECT-TYPE
                       SYNTAX  H221StatsEntry
                       MAX-ACCESS  not-accessible
                       STATUS  current
                       DESCRIPTION
                            "A h221 statistics row."
                       AUGMENTS { capsH320Entry }
                  ::= { h221StatsTable 1 }
        
                H221StatsEntry ::=
                  SEQUENCE {
                       h221InFrames
                            Counter32,
                       h221OutFrames
                            Counter32,
                       h221InFrameErrs
                            Counter32,
                       h221FrameAlignmentErrs
                            Counter32,
                       h221MultiFrameAlignmentErrs
                            Counter32,
                       h221ErrorPerformance
                            Counter32,
                       h221BASErrs
                            Counter32
                       }
             h221InFrames OBJECT-TYPE
                       SYNTAX Counter32
                       MAX-ACCESS read-only
                       STATUS current
                       DESCRIPTION
                                  "The number of H.221 frames received"
             ::= { h221StatsEntry 2 }
        
             h221OutFrames OBJECT-TYPE
                       SYNTAX Counter32
                       MAX-ACCESS read-only
                  STATUS current
                       DESCRIPTION
                                 "The number of H.221 frames sent"
             ::= { h221StatsEntry 3 }
        
             h221InFrameErrs OBJECT-TYPE
                       SYNTAX Counter32
                       MAX-ACCESS read-only
                       STATUS current
                       DESCRIPTION
                                 "The number of error frames received"
             ::= { h221StatsEntry 4 }
        
             h221FrameAlignmentErrs OBJECT-TYPE
                       SYNTAX  Counter32
                       MAX-ACCESS read-only
                       STATUS current
                       DESCRIPTION
                                 "The number of frame alignment errors received"
             ::= { h221StatsEntry 5 }
             h221MultiFrameAlignmentErrs OBJECT-TYPE
                       SYNTAX Counter32
                       MAX-ACCESS read-only
                       STATUS current
                       DESCRIPTION
                       "The number of multiple frame alignment errors received"
             ::= { h221StatsEntry 6 }
        
             h221ErrorPerformance OBJECT-TYPE
                       SYNTAX Counter32
                       MAX-ACCESS read-only
                       STATUS current
                       DESCRIPTION
                       "The quality of the 64 Kbps connection can be monitored
                       by counting the number of  CRC blocks in error (E-bit = 1)
                       within a period of one second (50 blocks).
                       Percentage of CRC blocks in error  Error rate
                       70% CRC blocks in error            10E-4
                       12% CRC blocks in error            10E-5
                       1.2% CRC blocks in error           10E-6
                       0.12% CRC blocks in error          10E-7
                       0.012% CRC blocks in error         10E-8"
             ::= { h221StatsEntry 7 }
        
             h221BASErrs OBJECT-TYPE
                       SYNTAX Counter32
                       MAX-ACCESS read-only
                       STATUS current
                       DESCRIPTION
                                 "The number of H.221 BAS errors received"
             ::= { h221StatsEntry 8 }
        
             -- Notification group
             --
        
             h221TooManyErrors NOTIFICATION-TYPE
                  OBJECTS { h221ErrorPerformance }
                  STATUS    current
                  DESCRIPTION
                       "This message will be sent when there are
                       excessive line errors."
             ::= { events 1 }
        
             h320ConnectionEstablished NOTIFICATION-TYPE
                  OBJECTS { h320CurrentCallStatus }
                  STATUS current
                  DESCRIPTION
                       "This message will be sent when a wide area network
                       connection is established with another video
                       conference site."
             ::= { events 2 }
             h320ConnectionTerminated NOTIFICATION-TYPE
                  OBJECTS { h320CurrentCallStatus }
                  STATUS current
                  DESCRIPTION
                       "This message will be generated when a wide area
                       network connection to another video conference
                       system drops. "
             ::= { events 3 }
        
             -- CONFORMANCE
             --
        
             h320EntityMIBConfs  OBJECT IDENTIFIER ::= { h320EntityMIB 4 }
             h320EntityMIBGroups OBJECT IDENTIFIER ::= { h320EntityMIBConfs 1 }
             h320EntityMIBCompl  OBJECT IDENTIFIER ::= { h320EntityMIBConfs 2 }
        
             --
             -- Groups for conformance
             --
        
             h320CapsGroups OBJECT-GROUP
                  OBJECTS {
                       capsH320EntityLineRate,
                       capsH320EntityVideoFormats,
                       capsH320EntityMaxVideoRate,
                       capsH320EntityAudioTypes,
                       capsH320EntityDataCaps,
                       capsH320EntityEncryp,
                       capsH320EntryRDC
                  }
                  STATUS current
                  DESCRIPTION
                       "A collection of objects providing capabilities of
                       the entity"
             ::= {h320EntityMIBGroups 1}
        
             h320CallStatusGroup OBJECT-GROUP
                  OBJECTS {
                       h320CurrentCallStatus,
                       h320CallSiteName,
                       h320CallLineRate,
                       h320CallVideoInFormat,
                       h320CallVideoOutFormat,
                       h320CallAudioInFormat,
                       h320CallAudioOutFormat,
                       h320CallData,
                       h320CallRDC
                  }
                  STATUS current
                  DESCRIPTION
                       "A collection of objects providing the ability to
                       invoke terminal functions"
             ::= { h320EntityMIBGroups 2}
             h221StatsGroup OBJECT-GROUP
                  OBJECTS {
                       h221InFrames,
                       h221OutFrames,
                       h221InFrameErrs,
                       h221FrameAlignmentErrs,
                       h221MultiFrameAlignmentErrs,
                       h221ErrorPerformance,
                       h221BASErrs
                  }
                  STATUS current
                  DESCRIPTION
                       "A collection of objects providing the ability to invoke
                       terminal functions"
             ::= { h320EntityMIBGroups 3}
        
        
        
             h320EventsGroup     NOTIFICATION-GROUP
                  NOTIFICATIONS {
                       h221TooManyErrors,
                       h320ConnectionEstablished,
                       h320ConnectionTerminated
                  }
                  STATUS current
                  DESCRIPTION
                       "An object providing the ability to invoke
                       a notification function"
             ::= { h320EntityMIBGroups 4}
        
             h221StatsCompliance MODULE-COMPLIANCE
                  STATUS    current
                  DESCRIPTION
                       "The set of objects required for compliance"
             -- Unconditionally mandatory groups
                  MODULE
                  MANDATORY-GROUPS     { h320CapsGroups, h320CallStatusGroup,
                            h221StatsGroup, h320EventsGroup }
        
             ::= { h320EntityMIBCompl 1 }
        
        END
