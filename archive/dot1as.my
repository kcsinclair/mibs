IEEE8021-AS-MIB DEFINITIONS ::= BEGIN
-- =============================================================
-- MIB for support of 802.1AS Timing and Synchronization in 
-- IEEE 802.1Q Bridged Local Area Networks
-- =============================================================

IMPORTS
    MODULE-IDENTITY, OBJECT-TYPE, Unsigned32, Integer32
        FROM SNMPv2-SMI
    TEXTUAL-CONVENTION, TruthValue, RowStatus
        FROM SNMPv2-TC
    MODULE-COMPLIANCE, OBJECT-GROUP
        FROM SNMPv2-CONF
    ifEntry, ifGeneralInformationGroup
        FROM IF-MIB
    ;

ieee8021AsTimeSyncMib MODULE-IDENTITY
    LAST-UPDATED "201001310000Z" -- January 31, 2010
    ORGANIZATION "IEEE 802.1 Working Group"
    CONTACT-INFO 
            "WG-URL: http://www.ieee802.org/1/index.html
            WG-EMail: STDS-802-1@IEEE.ORG

            Contact: Geoffrey M. Garner
            Postal:  196 Ambassador Drive
                     Red Bank, NJ 07701
                     USA
            E-mail:  gmgarner@alum.mit.edu"

    DESCRIPTION
            "The Management Information Base module for 
            IEEE 802.1AS time synchronization protocol."

    REVISION "201001310000Z" -- January 31, 2010

    DESCRIPTION
            "Published as part of IEEE Draft P802.1AS/D6.7

             Copyright (C) IEEE (2010)."  

  ::= { iso(1) org(3) ieee(111)
         standards-association-numbers-series-standards (2)
         lan-man-stds (802) ieee802dot1 (1) ieee802dot1mibs (1) 20 }

ieee8021AsMIBObjects    OBJECT IDENTIFIER ::= {ieee8021AsTimeSyncMib 1}
ieee8021AsConformance   OBJECT IDENTIFIER ::= {ieee8021AsTimeSyncMib 2}

-- =============================================================
-- Textual Conventions
-- =============================================================

ClockIdentity ::= TEXTUAL-CONVENTION
    DISPLAY-HINT 
        "1x:"
    STATUS current
    DESCRIPTION
        "Represents an 802 MAC address represented in the
         `canonical' order defined by IEEE 802.1a, EUI-64.  EUI-48 
         converts to EUI-64 as specified by IEEE.  The convertion 
         assigns values 255 and 254 to octets 3 and 4 respectively,
         where octet 0 is the most significant and octet 7 the least.
         For example, EUI-48 of AC:DE:48:23:45:67 would extend to 
         AC:DE:48:FF:FE:23:45:67."
    REFERENCE    "6.3.3.6 and 8.5.2.2.1"
    SYNTAX OCTET STRING (SIZE (8))


IEEE8021ASClockClassValue ::= TEXTUAL-CONVENTION
    STATUS       current
    DESCRIPTION
        "Clock Class Value from IEEE Std 1588-2008 7.6.2.4,
         with the following interpretation placed on the value:

         6: A clock that is synchronized to a primary refernce 
            time source,
         7: A clock that has previously been designated as clockClass
            6  but that has lost the ability to synchronize to a primary
            reference time source and is in holdover mode and within
            holdover specifications,
        13: A clock that is synchronized to an application-specific
            source of time,
        14: A clock that has previously been designated as clockClass 13
            but that has lost the ability to synchronize to an
            application-specific source of time and is in holdover mode
            and within holdover specifications,
        52: Degradation alternative A for a clock of clockClass 7 that
            is not within holdover specification,
        58: Degradation alternative A for a clock of clockClass 14 that
            is not within holdover specification,
        68..122: For use by alternate PTP profiles (68..122),
       133..170: For use by alternate PTP profiles (133..170),
       187: Degradation alternative B for a clock of clockClass 7 that
            is not within holdover specification,
       193: Degradation alternative B for a clock of clockClass 14 that
            is not within holdover specification,
       216..232: For use by alternate PTP profiles,
       248:  Default none of the other clockClass definitions apply,
       255:  A slave-only clock(255)."
    REFERENCE    "14.2.3 and IEEE Std 1588-2008 7.6.2.4"
    SYNTAX     INTEGER {
        primarySync(6),
        primarySyncLost(7),
        applicationSpecificSync(13),
        applicationSpecficSyncLost(14),
        primarySyncAlternativeA(52),
        applicationSpecificAlternativeA(58),
        primarySyncAlternativeB(187),
        applicationSpecficAlternativeB(193),
        defaultClock(248),
        slaveOnlyClock(255)
        }

IEEE8021ASClockAccuracyValue ::= TEXTUAL-CONVENTION
    STATUS       current
    DESCRIPTION
        "Clock Accuracy Value from 8.6.2.3, with the following
         interpretation placed on the value:

         32: The time is accurate to within 25 ns,
         33: The time is accurate to within 100 ns,
         34: The time is accurate to within 250 ns,
         35: The time is accurate to within 1 us,
         36: The time is accurate to within 2.5 us,
         37: The time is accurate to within 10 us,
         38: The time is accurate to within 25 us,
         39: The time is accurate to within 100 us,
         40: The time is accurate to within 250 us,
         41: The time is accurate to within 1 ms,
         42: The time is accurate to within 2.5 ms,
         43: The time is accurate to within 10 ms,
         44: The time is accurate to within 25 ms,
         45: The time is accurate to within 100 ms,
         46: The time is accurate to within 250 ms,
         47: The time is accurate to within 1 s,
         48: The time is accurate to within 10 s,
         49: The time is accurate to within > 10 s,
        254: Default indicating unknown"
    REFERENCE    "8.6.2.3"
    SYNTAX     INTEGER {
        timeAccurateTo25ns(32),
        timeAccurateTo100ns(33),
        timeAccurateTo250ns(34),
        timeAccurateTo1us(35),
        timeAccurateTo2dot5us(36),
        timeAccurateTo10us(37),
        timeAccurateTo25us(38),
        timeAccurateTo100us(39),
        timeAccurateTo250us(40),
        timeAccurateTo1ms(41),
        timeAccurateTo2dot5ms(42),
        timeAccurateTo10ms(43),
        timeAccurateTo25ms(44),
        timeAccurateTo100ms(45),
        timeAccurateTo250ms(46),
        timeAccurateTo1s(47),
        timeAccurateTo10s(48),
        timeAccurateToGT10s(49),
        timeAccurateToUnknown(254)
        }

IEEE8021ASTimeSourceValue ::= TEXTUAL-CONVENTION
    STATUS       current
    DESCRIPTION
        "The timeSource is an information only attribute indicating 
         the type of source of time used by a ClockMaster, 
         representing categories.  For example, the GPS entry would 
         include not only the GPS system of the U.S. Department of 
         Defense but the European Galileo system and other present and 
         future satellite-based timing systems.

         In the absence of a default value set by a user of this 
         standard, the default value of timeSource shall be OTHER. See 
          7.6.2.6 of IEEE Std 1588 - 2008 for more detailed description of 
         timeSourceIndicates the source of time used by the grandmaster
         clock.  

         The following interpretation placed on the value:
            16:  Atomic Clock,
            32:  GPS,
            48:  Terrestrial Radio,
            64:  PTP,
            80:  NTP,
            96:  Hand Set,
           144:  Other,
           160:  Internal Oscillator "
    REFERENCE  "8.6.2.7 and Table 8-3"
    SYNTAX      INTEGER {
            atomicClock(16),
            gps(32),
            terrestrialRadio(48),
            ptp(64),
            ntp(80),
            handSet(96),
            other(144),
            internalOscillator(160)
           } 


-- =================================================================
-- subtrees in the IEEE8021-AS-MIB
-- System Time-Aware Parameters/Capability 
-- =================================================================


-- =================================================================
-- The Default data set represent native time capability of a time- 
-- aware system and is consistent with respective IEEE 1588 data set.
-- =================================================================
ieee8021AsDefaultDS   
    OBJECT IDENTIFIER ::= { ieee8021AsMIBObjects 1 }

ieee8021AsDefaultDSClockIdentity OBJECT-TYPE
    SYNTAX      ClockIdentity
    MAX-ACCESS  read-only
    STATUS      current
    DESCRIPTION
              "Globally unique manufacturer-assigned clock identifier
               for the local clock. The identifier is based on an 
               EUI-64."
    REFERENCE   "14.2.1"
    ::= { ieee8021AsDefaultDS 1 }


ieee8021AsDefaultDSNumberPorts OBJECT-TYPE
    SYNTAX      Unsigned32(0..255)
    MAX-ACCESS  read-only
    STATUS      current
    DESCRIPTION
                "The number of PTP ports on the device. Ordinary clocks
                have a single port."
    REFERENCE   "14.2.2"
    ::= { ieee8021AsDefaultDS 2 }


ieee8021AsDefaultDSClockClass OBJECT-TYPE
    SYNTAX      IEEE8021ASClockClassValue
    MAX-ACCESS  read-only
    STATUS      current
    DESCRIPTION
                "Denotes the traceability of the time or frequency of the
                local clock."
    REFERENCE   "14.2.3"
    DEFVAL { defaultClock }
    ::= { ieee8021AsDefaultDS 3 }


ieee8021AsDefaultDSClockAccuracy OBJECT-TYPE
    SYNTAX      IEEE8021ASClockAccuracyValue
    MAX-ACCESS  read-only
    STATUS      current
    DESCRIPTION
                "Characterizes local clock for the purpose of the best 
                 master clock algorithm."
    REFERENCE   "14.2.4"
    ::= { ieee8021AsDefaultDS 4 }


ieee8021AsDefaultDSOffsetScaledLogVariance OBJECT-TYPE
    SYNTAX      Integer32(-32768..32767)
    MAX-ACCESS  read-only
    STATUS      current
    DESCRIPTION
              "Clock variance of the local clock expressed as a 
               base-2 logarithm multiplied by a scale factor of 256.
               Hysteresis is applied requiring the underlying computed
               variance to move by at least 128 before a change is
               reported.
               A value of -37268 indicates value is too large to be
               represented or has not been computed."
    REFERENCE   "14.2.5"
    ::= { ieee8021AsDefaultDS 5 }

ieee8021AsDefaultDSPriority1 OBJECT-TYPE
    SYNTAX      Unsigned32(0..255)
    MAX-ACCESS  read-write
    STATUS      current
    DESCRIPTION
                "Most-significant priority declaration in the execution of 
               the best master clock algorithm. Lower values take
               precedence. The value of priority1 shall be 255 for a
               time-aware system that is not grandmaster-capable. 
               The value of priority1 shall be less than 255 for a 
               time-aware system that is grandmaster-capable. The value
               0 shall be reserved for future management use, i.e., the  
               valueof priority1 shall be set to 0 only via management
               action, and shall not be specified as a default value by 
               a user of this standard."
    REFERENCE   "14.2.6"
    ::= { ieee8021AsDefaultDS 6 }


ieee8021AsDefaultDSPriority2 OBJECT-TYPE
    SYNTAX      Unsigned32(0..255)
    MAX-ACCESS  read-write
    STATUS      current
    DESCRIPTION
                "Least-significant priority declaration in the execution
                of the best master clock algorithm. Lower values take
                precedence.  The default value is 248"
    REFERENCE   "14.2.7"
    DEFVAL { 248 }
    ::= { ieee8021AsDefaultDS 7 }


ieee8021AsDefaultDSGmCapable OBJECT-TYPE
    SYNTAX      TruthValue
    MAX-ACCESS  read-only
    STATUS      current
    DESCRIPTION
                "True (1) if master clock capable; false (2)
                otherwise."
    REFERENCE   "14.2.8"
    ::= { ieee8021AsDefaultDS 8 }


ieee8021AsDefaultDSCurrentUTCOffset OBJECT-TYPE
    SYNTAX      Integer32(-32768..32767)
    MAX-ACCESS  read-only
    STATUS      current
    DESCRIPTION
                "The value of defaultDScurrentUTCOffset is the offset 
                 in seconds between TAI and UTC." 
    REFERENCE   "14.2.9"
    ::= { ieee8021AsDefaultDS 9 }


ieee8021AsDefaultDSCurrentUTCOffsetValid OBJECT-TYPE
    SYNTAX      TruthValue
    MAX-ACCESS  read-only
    STATUS      current
    DESCRIPTION
                "True (1) if defaultDSCurrentUTCOffset is known to
                 be correct; false (2) otherwise."
    REFERENCE   "14.2.10"
    ::= { ieee8021AsDefaultDS 10 }


ieee8021AsDefaultDSLeap59 OBJECT-TYPE
    SYNTAX      TruthValue
    MAX-ACCESS  read-only
    STATUS      current
    DESCRIPTION
                "In PTP systems whose epoch is the PTP epoch, a true (1) 
                value indicates that the last minute of the current UTC
                day contains 59 seconds. If the epoch is not PTP, or the
                 last minute of the UTC day contains 60 seconds, the value
                is false (2)."
    REFERENCE   "14.2.11"
    ::= { ieee8021AsDefaultDS 11 }


ieee8021AsDefaultDSLeap61 OBJECT-TYPE
    SYNTAX      TruthValue
    MAX-ACCESS  read-only
    STATUS      current
    DESCRIPTION
                "In PTP systems whose epoch is the PTP epoch, a true (1) 
                 value indicates that the last minute of the current UTC
                 day contains 61 seconds. If the epoch is not PTP, or the
                 last minute of the UTC day contains 60 seconds, the value
                is false (2)."    
    REFERENCE   "14.2.12"
    ::= { ieee8021AsDefaultDS 12 }


ieee8021AsDefaultDSTimeTraceable OBJECT-TYPE
    SYNTAX      TruthValue
    MAX-ACCESS  read-only
    STATUS      current
    DESCRIPTION
                "True (1) if the timescale and the value of 
                 defaultDSCurrentUTCOffset are traceable to a
                 primary reference; false (2) otherwise."
    REFERENCE   "14.2.13"
    ::= { ieee8021AsDefaultDS 13 }


ieee8021AsDefaultDSFrequencyTraceable OBJECT-TYPE
    SYNTAX      TruthValue
    MAX-ACCESS  read-only
    STATUS      current
    DESCRIPTION
                "True (1) if the frequency determining the timescale is
                 traceable to a primary reference; false (2) otherwise."
    REFERENCE   "14.2.14"
    ::= { ieee8021AsDefaultDS 14 }


ieee8021AsDefaultDSTimeSource OBJECT-TYPE
    SYNTAX      IEEE8021ASTimeSourceValue 
    MAX-ACCESS  read-only
    STATUS      current
    DESCRIPTION
                "Indicates the source of time used by the grandmaster
                 clock."
    REFERENCE   "14.2.15"
    ::= { ieee8021AsDefaultDS 15 }


-- =================================================================
-- The Current data set represent this system's topological location 
-- relative to the known Grand Master system. 
-- This data set is consistent with respective IEEE 1588 data set.
-- =================================================================
ieee8021AsCurrentDS   
    OBJECT IDENTIFIER ::= { ieee8021AsMIBObjects 2 }

ieee8021AsCurrentDSStepsRemoved OBJECT-TYPE
    SYNTAX      Integer32(-32768..32767)
    MAX-ACCESS  read-only
    STATUS      current
    DESCRIPTION
              "The number of communication paths traversed between the
               local clock and the grandmaster clock.  For example, 2 
               switch from GM, then the value is 3. "
    REFERENCE   "14.3.1"
    DEFVAL { 0 }
    ::= { ieee8021AsCurrentDS 1 }


ieee8021AsCurrentDSOffsetFromMasterHs OBJECT-TYPE
    SYNTAX      Integer32
    UNITS       "2**-16 ns * 2**64"
    MAX-ACCESS  read-only
    STATUS      current
    DESCRIPTION
               "The most significant 32 bits of the offset, signed  
                96 bit number in 2**-16 ns, an implementation-specific 
                computation of the current value of the time difference 
                between a master and a slave as computed by the slave. 

                This object MUST be read at the same time as 
                   ieee8021AsCurrentDSOffsetFromMasterMs, and                 
                ieee8021AsCurrentDSOffsetFromMasterLs, which 
                represents middle and least significant 32 bits of 
                values, respectively, in order for the read operation
                to succeed.
                "
    REFERENCE   "14.3.2"
    ::= { ieee8021AsCurrentDS 2 }

ieee8021AsCurrentDSOffsetFromMasterMs OBJECT-TYPE
    SYNTAX      Integer32
    UNITS       "2**-16 ns * 2**32"
    MAX-ACCESS  read-only
    STATUS      current
    DESCRIPTION
               "The middle significant 32 bits of the offset, signed  
                96 bit number in 2**-16 ns, an implementation-specific 
                computation of the current value of the time difference 
                between a master and a slave as computed by the slave. 

                This object MUST be read at the same time as 
                   ieee8021AsCurrentDSOffsetFromMasterHs, and                 
                ieee8021AsCurrentDSOffsetFromMasterLs, which 
                represents most (highest) and least significant 32 bits 
                of values, respectively, in order for the read operation
                to succeed.
                "
    REFERENCE   "14.3.2"
    ::= { ieee8021AsCurrentDS 3 }

ieee8021AsCurrentDSOffsetFromMasterLs OBJECT-TYPE
    SYNTAX      Integer32
    UNITS       "2**-16 ns"
    MAX-ACCESS  read-only
    STATUS      current
    DESCRIPTION
               "The least significant 32 bits of the offset, signed  
                96 bit number in 2**-16 ns, an implementation-specific 
                computation of the current value of the time difference 
                between a master and a slave as computed by the slave. 

                This object MUST be read at the same time as 
                   ieee8021AsCurrentDSOffsetFromMasterHs, and                 
                ieee8021AsCurrentDSOffsetFromMasterMs, which 
                represents most (highest) and middle significant 32 bits
                of values, respectively, in order for the read operation
                to succeed.
                "
    REFERENCE   "14.3.2"
    ::= { ieee8021AsCurrentDS 4 }

-- =================================================================
-- The Parent data set represent timing upstream (toward Grand Master) 
-- system's parameters as measured at this system. 
-- This data set is consistent with respective IEEE 1588 data set.
-- =================================================================
ieee8021AsParentDS    
    OBJECT IDENTIFIER ::= { ieee8021AsMIBObjects 3 }

ieee8021AsParentDSParentClockIdentity OBJECT-TYPE
    SYNTAX      ClockIdentity
    MAX-ACCESS  read-only
    STATUS      current
    DESCRIPTION
                "Clock identifier (clockIdentity) of the local clock's 
                 parent clock.  The initial value is set to 
                 ieee8021AsDefaultDSClockIdentity."
    REFERENCE   "14.4.1"
    ::= { ieee8021AsParentDS 1 }

ieee8021AsParentDSParentPortNumber OBJECT-TYPE
    SYNTAX      Unsigned32(0..65535)
    MAX-ACCESS  read-only
    STATUS      current
    DESCRIPTION
                "Port number (portNumber)of the local clock.s parent 
                 clock. The initial value is zero."
    REFERENCE   "14.4.1"
    DEFVAL { 0 }
    ::= { ieee8021AsParentDS 2 }

ieee8021AsParentDSCumlativeRateRatio OBJECT-TYPE
    SYNTAX      Integer32
    MAX-ACCESS  read-only
    STATUS      current
    DESCRIPTION
                "An estimate of the ratio of the frequency of the
                 grandmaster to the frequency of the LocalClock entity
                 of this time-aware system. Cumulative rate ratio is
                  expressed as the fractional frequency offset multiplied
                 by 2**41, i.e., the quantity (rateRatio - 1.0)(2**41),
                 where rateRatio is computed by the PortSyncSyncReceive
                 state machine (see 10.2.7.1.4)."
    REFERENCE   "14.4.2"
   ::= { ieee8021AsParentDS 3 }

ieee8021AsParentDSGrandmasterIdentity OBJECT-TYPE
    SYNTAX      ClockIdentity
    MAX-ACCESS  read-only
    STATUS      current
    DESCRIPTION
                "Clock identifier (clockIdentity) of the grandmaster.
                 The initial value is set to 
                 ieee8021AsDefaultDSClockIdentity."
    REFERENCE   "14.4.3"
    ::= { ieee8021AsParentDS 4 }

ieee8021AsParentDSGrandmasterClockClass OBJECT-TYPE
    SYNTAX      IEEE8021ASClockClassValue
    MAX-ACCESS  read-only
    STATUS      current
    DESCRIPTION
                "Denotes the traceability of the time or frequency of the
                 grandmaster.  The initial value is set to 
                 ieee8021AsDefaultDSClockClass."
    REFERENCE   "14.4.4"
    ::= { ieee8021AsParentDS 5 }

ieee8021AsParentDSGrandmasterClockAccuracy OBJECT-TYPE
    SYNTAX      IEEE8021ASClockAccuracyValue
    MAX-ACCESS  read-only
    STATUS      current
    DESCRIPTION
                "Characterizes the grandmaster clock for the purpose of 
                 the best master clock algorithm.  The initial value is 
                 set to ieee8021AsDefaultDSClockAccuracy."
    REFERENCE   "14.4.5"
    ::= { ieee8021AsParentDS 6 }

ieee8021AsParentDSGrandmasterOffsetScaledLogVariance OBJECT-TYPE
    SYNTAX      Integer32(-32768..32767)
    MAX-ACCESS  read-only
    STATUS      current
    DESCRIPTION
                "Clock Allan variance of the local clock expressed as a 
                 base-2 logarithm multiplied by a scale factor of 256.
                 Hysteresis is applied requiring the underlying computed
                 variance to move by at least 128 before a change is
                  reported. A value of -37268 indicates value is too large
                 to be represented or has not been computed.   
                 The initialvalue is set to 
                 ieee8021AsDefaultDSOffsetScaledLogVariance."
    REFERENCE   "14.4.6"
    ::= { ieee8021AsParentDS 7 }

ieee8021AsParentDSGrandmasterPriority1 OBJECT-TYPE
    SYNTAX      Unsigned32(0..255)
    MAX-ACCESS  read-only
    STATUS      current
    DESCRIPTION
                "Grandmaster's most-significant priority declaration in 
                 the execution of the best master clock algorithm. 
                 Lower values take precedence.  The initialvalue is set 
                 to ieee8021AsDefaultDSPriority1."
    REFERENCE   "14.4.7"
    ::= { ieee8021AsParentDS 8 }

ieee8021AsParentDSGrandmasterPriority2 OBJECT-TYPE
    SYNTAX      Unsigned32(0..255)
    MAX-ACCESS  read-only
    STATUS      current
    DESCRIPTION
               "Grandmaster's least-significant priority declaration in 
               the execution of the best master clock algorithm. 
                Lower values take precedence.  The initialvalue is set to 
               ieee8021AsDefaultDSDSPriority2."
    REFERENCE   "14.4.8"
    ::= { ieee8021AsParentDS 9 }

-- =================================================================
-- TimePropertiesDS represents the grand master's parameters, as 
-- measured at this system and are derived from 802.1AS protocol.
-- This data set is consistent with respective IEEE 1588 data set.
-- =================================================================
ieee8021AsTimePropertiesDS
    OBJECT IDENTIFIER ::= { ieee8021AsMIBObjects 4 }

ieee8021AsTimePropertiesDSCurrentUtcOffset OBJECT-TYPE
    SYNTAX      Integer32(-32768..32767)
    MAX-ACCESS  read-only
    STATUS      current
    DESCRIPTION
                "The value of timePropertiesDScurrentUTCOffset is the offset 
                 in seconds between TAI and UTC."
    REFERENCE   "14.5.1"
    ::= { ieee8021AsTimePropertiesDS 1 }

ieee8021AsTimePropertiesDSCurrentUtcOffsetValid OBJECT-TYPE
    SYNTAX      TruthValue
    MAX-ACCESS  read-only
    STATUS      current
    DESCRIPTION
                "True (1) if timePropertiesDSCurrentUTCOffset is known to
                 be correct; false (2) otherwise.  The initial value is 
                 set to ieee8021AsDefaultDSCurrentUTCOffsetValid."
    REFERENCE   "14.5.2"
    ::= { ieee8021AsTimePropertiesDS 2 }

ieee8021AsTimePropertiesDSLeap59 OBJECT-TYPE
    SYNTAX      TruthValue
    MAX-ACCESS  read-only
    STATUS      current
    DESCRIPTION
                "In PTP systems whose epoch is the PTP epoch, a true (1) 
                 value indicates that the last minute of the current UTC
                 day contains 59 seconds. If the epoch is not PTP, or the
                 last minute of the UTC day contains 60 seconds, the value
                is false (2).  The initial value is set to 
                ieee8021AsDefaultDSLeap59."
    REFERENCE   "14.5.3"
    ::= { ieee8021AsTimePropertiesDS 3 }

ieee8021AsTimePropertiesDSLeap61 OBJECT-TYPE
    SYNTAX      TruthValue
    MAX-ACCESS  read-only
    STATUS      current
    DESCRIPTION
                "In PTP systems whose epoch is the PTP epoch, a true (1) 
                 value indicates that the last minute of the current UTC
                 day contains 61 seconds. If the epoch is not PTP, or the
                 last minute of the UTC day contains 60 seconds, the value
                is false (2).   The initial value is set to 
                ieee8021AsDefaultDSLeap61."
    REFERENCE   "14.5.4"
    ::= { ieee8021AsTimePropertiesDS 4 }

ieee8021AsTimePropertiesDSTimeTraceable OBJECT-TYPE
    SYNTAX      TruthValue
    MAX-ACCESS  read-only
    STATUS      current
    DESCRIPTION
                "True (1) if the timescale and the value of 
                 timePropertiesDSCurrentUTCOffset are traceable to a
                 primary reference; false (2) otherwise.  The initial 
                 value is set to ieee8021AsDefaultDSTimeTraceable."

    REFERENCE   "14.5.5"
    ::= { ieee8021AsTimePropertiesDS 5 }

ieee8021AsTimePropertiesDSFrequencyTraceable OBJECT-TYPE
    SYNTAX      TruthValue
    MAX-ACCESS  read-only
    STATUS      current
    DESCRIPTION
                "True (1) if the frequency determining the timescale is
                 traceable to a primary reference; false (2) otherwise.  
                 The initial value is set to 
                 ieee8021AsDefaultDSFrequencyTraceable."

    REFERENCE   "14.5.6"
    ::= { ieee8021AsTimePropertiesDS 6 }

ieee8021AsTimePropertiesDSTimeSource OBJECT-TYPE
    SYNTAX      IEEE8021ASTimeSourceValue
    MAX-ACCESS  read-only
    STATUS      current
    DESCRIPTION
                "Indicates the source of time used by the grandmaster
                 clock.
                 The initial value is set to 
                 ieee8021AsDefaultDSTimeSource."

    REFERENCE   "14.5.7"
    ::= { ieee8021AsTimePropertiesDS 7 }

-- =============================================================
-- The Time-Sync parameters for each .1AS capable port. 
-- One Table per Bridge Component or a end station.
-- One entry per port.
-- =============================================================

ieee8021AsPortDSIfTable   OBJECT-TYPE
    SYNTAX      SEQUENCE OF Ieee8021AsPortDSIfEntry
    MAX-ACCESS  not-accessible
    STATUS      current
    DESCRIPTION
       "A table of time-aware port related variables in a time-aware 
        bridge or for a time-aware end station.  A value of 1 is used in 
        a bridge or an end station that does not have multiple 
        components.
       "
    REFERENCE
       "IEEE 802.1AS clause 14.6"
    ::= { ieee8021AsMIBObjects 5 }

ieee8021AsPortDSIfEntry   OBJECT-TYPE
    SYNTAX      Ieee8021AsPortDSIfEntry
    MAX-ACCESS  not-accessible
    STATUS      current
    DESCRIPTION
       "A list of objects pertaining to a port of a time-aware bridge 
        component or a time-aware end station.
       "
    AUGMENTS { ifEntry }
    ::= { ieee8021AsPortDSIfTable 1 }

Ieee8021AsPortDSIfEntry ::=
     SEQUENCE {
         ifIeee8021AsPortDSClockIdentity               ClockIdentity,
         ifIeee8021AsPortDSPortNumber                  Unsigned32,
         ifIeee8021AsPortDSPortRole                    INTEGER,
         ifIeee8021AsPortDSPttPortEnabled              TruthValue,
         ifIeee8021AsPortDSIsMeasuringPdelay           TruthValue,
         ifIeee8021AsPortDSAsCapable                   TruthValue,
         ifIeee8021AsPortDSNeighborPropDelayHs         Unsigned32,
         ifIeee8021AsPortDSNeighborPropDelayMs         Unsigned32,
         ifIeee8021AsPortDSNeighborPropDelayLs         Unsigned32,
         ifIeee8021AsPortDSNeighborPropDelayThreshHs   Unsigned32,
         ifIeee8021AsPortDSNeighborPropDelayThreshMs   Unsigned32,
         ifIeee8021AsPortDSNeighborPropDelayThreshLs   Unsigned32,
         ifIeee8021AsPortDSDelayAsymmetryHs            Integer32,
         ifIeee8021AsPortDSDelayAsymmetryMs            Unsigned32,
         ifIeee8021AsPortDSDelayAsymmetryLs            Unsigned32,
         ifIeee8021AsPortDSNeighborRateRatio           Integer32,
         ifIeee8021AsPortDSLogAnnounceInterval         Integer32,
         ifIeee8021AsPortDSAnnounceReceiptTimeout      Unsigned32,
         ifIeee8021AsPortDSLogSyncInterval             Integer32,
         ifIeee8021AsPortDSSyncReceiptTimeout          Unsigned32,
         ifIeee8021AsPortDSSyncReceiptTimeoutTimeIntervalHs Unsigned32,
         ifIeee8021AsPortDSSyncReceiptTimeoutTimeIntervalMs Unsigned32,
         ifIeee8021AsPortDSSyncReceiptTimeoutTimeIntervalLs Unsigned32,
         ifIeee8021AsPortDSLogPdelayReqInterval        Integer32,
         ifIeee8021AsPortDSAllowedLostResponses        Unsigned32,
         ifIeee8021AsPortDSVersionNumber               Unsigned32,
         ifIeee8021AsPortDSNupMs                       Unsigned32,
         ifIeee8021AsPortDSNupLs                       Unsigned32,
         ifIeee8021AsPortDSNdownMs                     Unsigned32,
         ifIeee8021AsPortDSNdownLs                     Unsigned32,
         ifIeee8021AsPortDSAcceptableMasterTableEnabled TruthValue
      }

ifIeee8021AsPortDSClockIdentity OBJECT-TYPE
    SYNTAX      ClockIdentity
    MAX-ACCESS  read-only
    STATUS      current
    DESCRIPTION
                "Globally unique manufacturer-assigned clock identifier
                for the local clock port. The identifier is based on an
                EUI-64."
    REFERENCE   "14.6.2"
    ::= { ieee8021AsPortDSIfEntry 1 }


ifIeee8021AsPortDSPortNumber OBJECT-TYPE
    SYNTAX      Unsigned32(0..65535)
    MAX-ACCESS  read-only
    STATUS      current
    DESCRIPTION
                "Port Number"
    REFERENCE   "14.6.2"
    ::= { ieee8021AsPortDSIfEntry 2 }

ifIeee8021AsPortDSPortRole OBJECT-TYPE
    SYNTAX      INTEGER {
            disabledPort(3),
            masterPort(6),
            passivePort(7),
            slavePort(9)
           }
    MAX-ACCESS  read-only
    STATUS      current
    DESCRIPTION
                "The value is the value of the port role of this port 
                 (see Table 10-1), and is taken from the enumeration in
                 Table 14-5. All other values reserved.  The enumeration
                 values are consistent with IEEE Std 1588TM-2008, 
                 Table 8. The initialization value is 3 (DisabledPort)."
    REFERENCE   "14.6.3"
    DEFVAL { 3 }
    ::= { ieee8021AsPortDSIfEntry 3 }


ifIeee8021AsPortDSPttPortEnabled OBJECT-TYPE
    SYNTAX      TruthValue
    MAX-ACCESS  read-write
    STATUS      current
    DESCRIPTION
                "802.1AS function enable for a given port.  True (1) if 
                 the time-synchronization and best master selection
                 functions of the port are enabled;
                 False (2) otherwise.
        The contents of this table SHALL be maintained across a restart
        of the system.
       "
    REFERENCE   "14.6.4"
    DEFVAL { 1 }
    ::= { ieee8021AsPortDSIfEntry 4 }


ifIeee8021AsPortDSIsMeasuringPdelay OBJECT-TYPE
    SYNTAX      TruthValue
    MAX-ACCESS  read-only
    STATUS      current
    DESCRIPTION
                "True (1) if the port is measuring link propagation delay;
                False (2) otherwise."
    REFERENCE   "14.6.5"
    ::= { ieee8021AsPortDSIfEntry 5 }


ifIeee8021AsPortDSAsCapable OBJECT-TYPE
    SYNTAX      TruthValue
    MAX-ACCESS  read-only
    STATUS      current
    DESCRIPTION
                "True (1) if and only if it is determined that this 
                 time-aware ystem and the time-aware system at the 
                 other ends of the link attached to this port can
                 interoperate with each other via the IEEE 802.1AS 
                 protocol; False (2) otherwise."
    REFERENCE   "14.6.6"
    ::= { ieee8021AsPortDSIfEntry 6 }

ifIeee8021AsPortDSNeighborPropDelayHs OBJECT-TYPE
    SYNTAX      Unsigned32
    UNITS       "2**-16 ns * 2**64"
    MAX-ACCESS  read-only
    STATUS      current
    DESCRIPTION
               "The most (highest) significant 32 bits, unsigned  
                96 bit number in 2**-16 ns, the value is equal to the 
                value of the per-port global variable
                neighborPropDelay (see 10.2.4.6).  It is an
                estimate of the current one-way propagation time on the
                link attached to this port, measured as specified for
                the respective medium (see 11.2.15, 12.5, and E.4).
                The value is zero for ports attached to IEEE 802.3 EPON
                links and for the master port of an IEEE 802.11 link,
                because one-way propagation delay is not measured on
                the latter and not directly measured on the former. It
                is recommended that the data type be scaled in ns. The
                initialization value is zero.

                This object MUST be read at the same time as 
                 ieee8021AsPortDSNeighborPropDelayMs, and                 
                ieee8021AsPortDSNeighborPropDelayLs, which 
                represents middle and least significant 32 bits
                of values, respectively, in order for the read operation
                to succeed.
                "
    REFERENCE   "14.6.7"
    DEFVAL { 0 }
    ::= { ieee8021AsPortDSIfEntry 7 }

ifIeee8021AsPortDSNeighborPropDelayMs OBJECT-TYPE
    SYNTAX      Unsigned32
    UNITS       "2**-16 ns * 2**32"
    MAX-ACCESS  read-only
    STATUS      current
    DESCRIPTION
                "The second most (middle) significant 32 bits, unsigned 
                 96 bit number in 2**-16 ns, the value is equal to the 
                 value of the per-port global variable
                 neighborPropDelay (see 10.2.4.6).  It is an
                 estimate of the current one-way propagation time on the
                 link attached to this port, measured as specified for
                 the respective medium (see 11.2.15, 12.5, and E.4).
                 The value is zero for ports attached to IEEE 802.3 EPON
                 links and for the master port of an IEEE 802.11 link,
                 because one-way propagation delay is not measured on
                 the latter and not directly measured on the former. It
                 is recommended that the data type be scaled in ns. The
                 initialization value is zero.

                This object MUST be read at the same time as 
                 ieee8021AsPortDSNeighborPropDelayHs, and                 
                ieee8021AsPortDSNeighborPropDelayLs, which 
                represents most (highest) and least significant 32 bits
                of values, respectively, in order for the read operation
                to succeed.
                "
    REFERENCE   "14.6.7"
    DEFVAL { 0 }
    ::= { ieee8021AsPortDSIfEntry 8 }

ifIeee8021AsPortDSNeighborPropDelayLs OBJECT-TYPE
    SYNTAX      Unsigned32
    UNITS       "2**-16 ns"
    MAX-ACCESS  read-only
    STATUS      current
    DESCRIPTION
                "The least significant 32 bits, unsigned  
                 96 bit number in 2**-16 ns, the value is equal to the 
                 value of the per-port global variable
                 neighborPropDelay (see 10.2.4.6).  It is an
                 estimate of the current one-way propagation time on the
                 link attached to this port, measured as specified for
                 the respective medium (see 11.2.15, 12.5, and E.4).
                 The value is zero for ports attached to IEEE 802.3 EPON
                 links and for the master port of an IEEE 802.11 link,
                 because one-way propagation delay is not measured on
                 the latter and not directly measured on the former. It
                 is recommended that the data type be scaled in ns. The
                 initialization value is zero.

                This object MUST be read at the same time as 
                 ieee8021AsPortDSNeighborPropDelayHs, and                 
                ieee8021AsPortDSNeighborPropDelayMs, which 
                represents most (highest) and middle significant 32 bits
                of values, respectively, in order for the read operation
                to succeed.
                "
    REFERENCE   "14.6.7"
    DEFVAL { 0 }
    ::= { ieee8021AsPortDSIfEntry 9 }


ifIeee8021AsPortDSNeighborPropDelayThreshHs OBJECT-TYPE
    SYNTAX      Unsigned32
    UNITS       "2**-16 ns * 2 ** 64"
    MAX-ACCESS  read-write
    STATUS      current
    DESCRIPTION
               "The most (highest) significant 32 bits, unsigned  
                96 bit number in 2**-16 ns, the value is equal to the 
                value of the per-port global variable 
                neighborPropDelayThresh (see 11.2.12.5). It 
                is the propagation time threshold, above which a port
                is not considered capable of participating in the
                802.1AS protocol

                This object MUST be read or writen at the same time as 
                         ieee8021AsPortDSNeighborPropDelayThreshMs, and                 
                ieee8021AsPortDSNeighborPropDelayThreshLs, which 
                represents middle and least significant 32 bits
                of values, respectively, in order for the read or write 
                operation to succeed.

                The contents of this variable SHALL be maintained  
                across a restart of the system.
       "
    REFERENCE   "14.6.8"
    ::= { ieee8021AsPortDSIfEntry 10 }

ifIeee8021AsPortDSNeighborPropDelayThreshMs OBJECT-TYPE
    SYNTAX      Unsigned32
    UNITS       "2**-16 ns * 2 ** 32"
    MAX-ACCESS  read-write
    STATUS      current
    DESCRIPTION
               "The middle significant 32 bits, unsigned  
                96 bit number in 2**-16 ns, the value is equal to the 
                value of the per-port global variable 
                neighborPropDelayThresh (see 11.2.12.5). It 
                is the propagation time threshold, above which a port
                is not considered capable of participating in the
                802.1AS protocol

                This object MUST be read or written at the same time as 
                         ieee8021AsPortDSNeighborPropDelayThreshHs, and                 
                ieee8021AsPortDSNeighborPropDelayThreshLs, which 
                represents most (highest) and least significant 32 bits
                of values, respectively, in order for the read or write 
                operation to succeed.

                The contents of this variable SHALL be maintained  
                across a restart of the system.
     "
     REFERENCE   "14.6.8"
    ::= { ieee8021AsPortDSIfEntry 11 }

ifIeee8021AsPortDSNeighborPropDelayThreshLs OBJECT-TYPE
    SYNTAX      Unsigned32
    UNITS       "2**-16 ns"
    MAX-ACCESS  read-write
    STATUS      current
    DESCRIPTION
               "The least significant 32 bits, unsigned  
                96 bit number in 2**-16 ns, the value is equal to the 
                value of the per-port global variable 
                neighborPropDelayThresh (see 11.2.12.5). It 
                is the propagation time threshold, above which a port
                is not considered capable of participating in the
                802.1AS protocol

                This object MUST be read at the same time as 
                         ieee8021AsPortDSNeighborPropDelayThreshHs, and                 
                ieee8021AsPortDSNeighborPropDelayThreshMs, which 
                represents most (highest) and middle significant 32 bits
                of values, respectively, in order for the read or write 
                operation to succeed.

                The contents of this variable SHALL be maintained  
                across a restart of the system.
      "
     REFERENCE   "14.6.8"
    ::= { ieee8021AsPortDSIfEntry 12 }

ifIeee8021AsPortDSDelayAsymmetryHs OBJECT-TYPE
    SYNTAX      Integer32
    UNITS       "2**-16 ns * 2**64"
    MAX-ACCESS  read-write
    STATUS      current
    DESCRIPTION
                "The most (highest) significant 32 bits, signed  
                96 bit number in 2**-16 ns.  
                For ports attached to full-duplex, IEEE 802.3 media, the
                value is the propagation delay asymmetry (see 8.3),
                which is equal to the per-port global variable
                delayAsymmetry (see 10.2.4.7). The initialization value 
                is the propagation delay asymmetry between transmit and 
                receive in the physical layer path, if known, or
                0 otherwise. For ports attached to other media, the
                value is 0.

                This object MUST be read or written at the same time as 
                ieee8021AsPortDSDelayAsymmetryMs, and 
                ieee8021AsPortDSDelayAsymmetryLs, which 
                represents middle and least significant 32 bits
                of values, respectively, in order for the read or write 
                operation to succeed.

                The contents of this variable SHALL be maintained  
                across a restart of the system.
       "
    REFERENCE   "14.6.9 and 8.3"
    ::= { ieee8021AsPortDSIfEntry 13 }

ifIeee8021AsPortDSDelayAsymmetryMs OBJECT-TYPE
    SYNTAX      Unsigned32
    UNITS       "2**-16 ns * 2**32"
    MAX-ACCESS  read-write
    STATUS      current
    DESCRIPTION
               "The middle significant 32 bits, signed  
                96 bit number in 2**-16 ns.  
                For ports attached to full-duplex, IEEE 802.3 media, the
                value is the propagation delay asymmetry (see 8.3),
                which is equal to the per-port global variable
                delayAsymmetry (see 10.2.4.7). The initialization value 
                is the propagation delay asymmetry between transmit and 
                receive in the physical layer path, if known, or
                0 otherwise. For ports attached to other media, the
                value is 0.

                This object MUST be read or written at the same time as 
                ieee8021AsPortDSDelayAsymmetryHs, and 
                ieee8021AsPortDSDelayAsymmetryLs, which 
                represents middle and least significant 32 bits
                of values, respectively, in order for the read or write 
                operation to succeed.

                The contents of this variable SHALL be maintained  
                across a restart of the system.
       "
    REFERENCE   "14.6.9 and 8.3"
    ::= { ieee8021AsPortDSIfEntry 14 }

ifIeee8021AsPortDSDelayAsymmetryLs OBJECT-TYPE
    SYNTAX      Unsigned32
    UNITS       "2**-16 ns"
    MAX-ACCESS  read-write
    STATUS      current
    DESCRIPTION
                "The least significant 32 bits, signed  
                96 bit number in 2**-16 ns.  
                For ports attached to full-duplex, IEEE 802.3 media, the
                value is the propagation delay asymmetry (see 8.3),
                which is equal to the per-port global variable
                delayAsymmetry (see 10.2.4.7). The initialization value 
                is the propagation delay asymmetry between transmit and 
                receive in the physical layer path, if known, or
                0 otherwise. For ports attached to other media, the
                value is 0.

                This object MUST be read or written at the same time as 
                ieee8021AsPortDSDelayAsymmetryHs, and 
                ieee8021AsPortDSDelayAsymmetryLs, which 
                represents most (highest) and least significant 32 bits
                of values, respectively, in order for the read or write 
                operation to succeed.

                The contents of this variable SHALL be maintained  
                across a restart of the system.
       "
    REFERENCE   "14.6.9 and 8.3"
    ::= { ieee8021AsPortDSIfEntry 15 }


ifIeee8021AsPortDSNeighborRateRatio OBJECT-TYPE
    SYNTAX      Integer32
    MAX-ACCESS  read-only
    STATUS      current
    DESCRIPTION
                "An estimate of the ratio of the frequency of the
                  LocalClock entity of the time-aware system at the other
                 end of the link attached to this port, to the frequency
                  of the LocalClock entity of this time-aware system (see
                 10.2.4.5). Neighbor rate ratio is expressed as the
                 fractional frequency offset multiplied by 2**41, i.e.,
                 the quantity (neighborRateRatio - 1.0)(2**41)."
    REFERENCE   "14.6.10"
    ::= { ieee8021AsPortDSIfEntry 16 }


ifIeee8021AsPortDSLogAnnounceInterval OBJECT-TYPE
    SYNTAX      Integer32(-128..127)
    MAX-ACCESS  read-write
    STATUS      current
    DESCRIPTION
                "The value is the logarithm to the base 2 of the of the
                 Announce message transmission interval, see 10.6.2.2.
                 The initialization value is 0.

                The contents of this variable SHALL be maintained  
                across a restart of the system.
       "
    REFERENCE   "14.6.11"
    DEFVAL { 0 }
    ::= { ieee8021AsPortDSIfEntry 17 }


ifIeee8021AsPortDSAnnounceReceiptTimeout OBJECT-TYPE
    SYNTAX      Unsigned32(2..255)
    MAX-ACCESS  read-write
    STATUS      current
    DESCRIPTION
                "The value is the number of Announce message transmission
                 intervals that a slave port waits without receiving an
                 Announce message, before assuming that the master is no
                 longer transmitting Announce messages and the BMCA
                 needs to be run, if appropriate. The initialization
                 value is 2.

                The contents of this variable SHALL be maintained  
                across a restart of the system.
       "
    REFERENCE   "14.6.12"
    DEFVAL { 2 }
    ::= { ieee8021AsPortDSIfEntry 18 }


ifIeee8021AsPortDSLogSyncInterval OBJECT-TYPE
    SYNTAX      Integer32(-128..127)
    MAX-ACCESS  read-write
    STATUS      current
    DESCRIPTION
                "The value is the logarithm to the base 2 of the
                 time-synchronization transmission interval, see
                 10.6.2.3. The initialization value is -3.

                The contents of this variable SHALL be maintained  
                across a restart of the system.
       "
    REFERENCE   "14.6.13"
    DEFVAL { -3 }
    ::= { ieee8021AsPortDSIfEntry 19 }


ifIeee8021AsPortDSSyncReceiptTimeout OBJECT-TYPE
    SYNTAX      Unsigned32(2..255)
    MAX-ACCESS  read-write
    STATUS      current
    DESCRIPTION
                "The value is the number of time-synchronization
                 transmission inervals that a slave port waits without
                 receiving synchronization information, before assuming
                 that the master is no longer transmitting
                 synchronization information and that the BMCA needs to
                 be run, if appropriate. The initialziation value is 3.

                The contents of this variable SHALL be maintained  
                across a restart of the system.
       "
    REFERENCE   "14.6.14"
    DEFVAL { 3 }
    ::= { ieee8021AsPortDSIfEntry 20 }


ifIeee8021AsPortDSSyncReceiptTimeoutTimeIntervalHs OBJECT-TYPE
    SYNTAX      Unsigned32
    UNITS       "2**-16 ns"
    MAX-ACCESS  read-only
    STATUS      current
    DESCRIPTION
               "The most (highest) significant 32 bits, of unsigned  
                96 bit number in 2**-16 ns.  
                The value is equal to the value of the per port global
                variable syncReceiptTimeoutTimeInterval (see 10.2.4.2).
                It is the time interval after which sync receipt
                timeout occurs if time-synchronization information has
                not been received during the interval.

                This object MUST be read  at the same time as 
                ieee8021AsPortDSSyncReceiptTimeoutTimeIntervalMs, and 
                ieee8021AsPortDSSyncReceiptTimeoutTimeIntervalLs, which 
                represents middle and least significant 32 bits
                of values, respectively, in order for the read 
                operation to succeed.

                Default value is calculated per 10.2.4.2, or 
                '0000 0000 0000 165A 0BC0 0000'h. 

                The contents of this variable SHALL be maintained  
                across a restart of the system.
               "
    REFERENCE   "14.6.15"
    DEFVAL { '00000000'h }
    ::= { ieee8021AsPortDSIfEntry 21 }

ifIeee8021AsPortDSSyncReceiptTimeoutTimeIntervalMs OBJECT-TYPE
    SYNTAX      Unsigned32
    UNITS       "2**-16 ns * 2**32"
    MAX-ACCESS  read-only
    STATUS      current
    DESCRIPTION
               "The middle significant 32 bits, unsigned  
                96 bit number in 2**-16 ns.  
                The value is equal to the value of the per port global
                variable syncReceiptTimeoutTimeInterval (see 10.2.4.2).
                It is the time interval after which sync receipt
                timeout occurs if time-synchronization information has
                not been received during the interval.

                This object MUST be read  at the same time as 
                ieee8021AsPortDSSyncReceiptTimeoutTimeIntervalHs, and 
                ieee8021AsPortDSSyncReceiptTimeoutTimeIntervalLs, which 
                represents most (highest) and least significant 32 bits
                of values, respectively, in order for the read 
                operation to succeed.

                Default value is calculated per 10.2.4.2, or 
                '0000 0000 0000 165A 0BC0 0000'h. 

                The contents of this variable SHALL be maintained  
                across a restart of the system.
               "
    REFERENCE   "14.6.15"
    DEFVAL { '0000165A'h }
    ::= { ieee8021AsPortDSIfEntry 22 }

ifIeee8021AsPortDSSyncReceiptTimeoutTimeIntervalLs OBJECT-TYPE
    SYNTAX      Unsigned32
    UNITS       "2**-16 ns"
    MAX-ACCESS  read-only
    STATUS      current
    DESCRIPTION
               "The least significant 32 bits, unsigned  
                96 bit number in 2**-16 ns.  
                The value is equal to the value of the per port global
                variable syncReceiptTimeoutTimeInterval (see 10.2.4.2).
                It is the time interval after which sync receipt
                timeout occurs if time-synchronization information has
                not been received during the interval.

                This object MUST be read  at the same time as 
                ieee8021AsPortDSSyncReceiptTimeoutTimeIntervalHs, and 
                ieee8021AsPortDSSyncReceiptTimeoutTimeIntervalMs, which 
                represents most (highest) and middle significant 32 bits
                of values, respectively, in order for the read 
                operation to succeed.

                Default value is calculated per 10.2.4.2, or 
                '0000 0000 0000 165A 0BC0 0000'h. 

                The contents of this variable SHALL be maintained  
                across a restart of the system.
               "
    REFERENCE   "14.6.15"
    DEFVAL { '0BC00000'h }
    ::= { ieee8021AsPortDSIfEntry 23 }


ifIeee8021AsPortDSLogPdelayReqInterval OBJECT-TYPE
    SYNTAX      Integer32(-128..127)
    MAX-ACCESS  read-write
    STATUS      current
    DESCRIPTION
                "For full-duplex, IEEE 802.3 media and CSN media that use
                the peer delay mechanism to measure path delay (see
                 E.4.3.1), the value is the logarithm to the base 2 of the
                Pdelay_Req message transmission interval, see 11.5.2.2.
                For these media, the initialization value is 0. For all
                other media, the value is 127.

                The contents of this variable SHALL be maintained  
                across a restart of the system.
       "
    REFERENCE   "14.6.16"
    ::= { ieee8021AsPortDSIfEntry 24 }


ifIeee8021AsPortDSAllowedLostResponses OBJECT-TYPE
    SYNTAX      Unsigned32(0..65535)
    MAX-ACCESS  read-write
    STATUS      current
    DESCRIPTION
                "The value is equal to the value of the per-port global
                 variable allowedLostResponses (see 11.2.12.3). It is
                 the number of Pdelay_Req messages for which a valid
                 response is not received, above which a port is
                 considered to not be exchanging peer delay messages
                 with its neighbor.

                The contents of this variable SHALL be maintained  
                across a restart of the system.
       "
    REFERENCE   "14.6.17 and 11.5.3"
    DEFVAL { 3 }
    ::= { ieee8021AsPortDSIfEntry 25 }


ifIeee8021AsPortDSVersionNumber OBJECT-TYPE
    SYNTAX      Unsigned32(0..63)
    MAX-ACCESS  read-only
    STATUS      current
    DESCRIPTION
                "Indicates the PTP version in use on the port.
                 The version number for this standard is set to  
                 the value 2.

                The contents of this variable SHALL be maintained  
                across a restart of the system.
       "
    REFERENCE   "14.6.18"
    DEFVAL { 2 }
    ::= { ieee8021AsPortDSIfEntry 26 }


ifIeee8021AsPortDSNupMs OBJECT-TYPE
    SYNTAX      Unsigned32
    MAX-ACCESS  read-write
    STATUS      current
    DESCRIPTION
               "The most significant 32 bits, of unsigned  
                64 bit fixed point number between 0 and less than 2. 
                For an OLT port of an IEEE 802.3 EPON link, the value is
                the effective index of refraction for the EPON upstream
                wavelength light of the optical path (see 13.1.4 and
                13.7.1.2). The initialization value is 1. For all
                other ports, the value is 0.

                This object MUST be read or written at the same time as 
                ieee8021AsPortDSNupLs, which represents least
                significant 32 bits of the value in order for the read 
                or write operation to succeed.

                The contents of this variable SHALL be maintained  
                across a restart of the system.
                "
    REFERENCE   "14.6.19"
    ::= { ieee8021AsPortDSIfEntry 27 }

ifIeee8021AsPortDSNupLs OBJECT-TYPE
    SYNTAX      Unsigned32
    MAX-ACCESS  read-write
    STATUS      current
    DESCRIPTION
                "The least significant 32 bits, of unsigned  
                64 bit fixed point number between 0 and less than 2. 
                For an OLT port of an IEEE 802.3 EPON link, the value is
                the effective index of refraction for the EPON upstream
                wavelength light of the optical path (see 13.1.4 and
                13.7.1.2). The initialization value is 1. For all
                other ports, the value is 0.

                This object MUST be read or written at the same time as 
                ieee8021AsPortDSNupMs, which represents the most
                significant 32 bits of the value in order for the read 
                or write operation to succeed.

                The contents of this variable SHALL be maintained  
                across a restart of the system.
                "
    REFERENCE   "14.6.19"
    ::= { ieee8021AsPortDSIfEntry 28 }

ifIeee8021AsPortDSNdownMs OBJECT-TYPE
    SYNTAX      Unsigned32
    MAX-ACCESS  read-write
    STATUS      current
    DESCRIPTION
                "The least significant 32 bits, of unsigned  
                64 bit fixed point number between 0 and less than 2. 
                 For an OLT port of an IEEE 802.3 EPON link, the value is
                the effective index of refraction for the EPON
                downstream wavelength light of the optical path (see
                13.1.4 and 13.7.1.2). The initialization value is 1.0.
                other ports, the value is 0.

                This object MUST be read or written at the same time as 
                ieee8021AsPortDSNdownLs, which represents the least
                significant 32 bits of the value in order for the read 
                or write operation to succeed.

                The contents of this variable SHALL be maintained  
                across a restart of the system.
                "
    REFERENCE   "14.6.20"
    ::= { ieee8021AsPortDSIfEntry 29 }

ifIeee8021AsPortDSNdownLs OBJECT-TYPE
    SYNTAX      Unsigned32
    MAX-ACCESS  read-write
    STATUS      current
    DESCRIPTION
               "The least significant 32 bits, of unsigned  
                64 bit fixed point number between 0 and less than 2. 
                 For an OLT port of an IEEE 802.3 EPON link, the value is
                the effective index of refraction for the EPON
                downstream wavelength light of the optical path (see
                13.1.4 and 13.7.1.2). The initialization value is 1.0.
                other ports, the value is 0.

                This object MUST be read or written at the same time as 
                ieee8021AsPortDSNdownMs, which represents the most
                significant 32 bits of the value in order for the read 
                or write operation to succeed.

                The contents of this variable SHALL be maintained  
                across a restart of the system.
                "
    REFERENCE   "14.6.20"
    ::= { ieee8021AsPortDSIfEntry 30 }

ifIeee8021AsPortDSAcceptableMasterTableEnabled OBJECT-TYPE
    SYNTAX      TruthValue
    MAX-ACCESS  read-write
    STATUS      current
    DESCRIPTION
                "True (1) if acceptableMasterTableEnabled (see 13.1.3) in 
                a time-aware system contains an ONU port attached to an
                IEEE 802.3 EPON link, the default value is TRUE; False (2)
               if the time-aware system does not contain an ONU port
               attached to an IEEE 802.3 EPON link, the default value
               is FALSE.

                The contents of this variable SHALL be maintained  
                across a restart of the system.
       "
    REFERENCE   "14.6.21"
    DEFVAL { false }
    ::= { ieee8021AsPortDSIfEntry 31 }


-- ******************************************************************
-- Acceptable Master Table derived from IEEE 1588-2008. 
-- One Table per time-aware system, and used when any of the system 
-- is of type IEEE 802.3 EPON, i.e. if any of port in a corresponding   
-- system has ieee8021AsPortDSAcceptableMasterTableEnabled set to true.
-- Not used otherwise (Table exists without an entry).   
-- ******************************************************************


ieee8021AsAcceptableMasterTableDS
    OBJECT IDENTIFIER ::= { ieee8021AsMIBObjects 6 }

ieee8021AsAcceptableMasterTableDSBase
    OBJECT IDENTIFIER ::= { ieee8021AsAcceptableMasterTableDS 1 }

ieee8021AsAcceptableMasterTableDSMaster
    OBJECT IDENTIFIER ::= { ieee8021AsAcceptableMasterTableDS 2 }

ieee8021AsAcceptableMasterTableDSMaxTableSize OBJECT-TYPE
    SYNTAX      Unsigned32(0..65535)
    MAX-ACCESS  read-only
    STATUS      current
    DESCRIPTION
                "The value is the maximum size of the
                 AcceptableMasterTable. It is equal to the maxTableSize
                 member of the AcceptableMasterTable structure (see
                 13.1.3.2)"
    REFERENCE   "14.7.1 and 13.1.3.2"
    ::= { ieee8021AsAcceptableMasterTableDSBase 1 }

ieee8021AsAcceptableMasterTableDSActualTableSize OBJECT-TYPE
    SYNTAX      Unsigned32(0..65535)
    MAX-ACCESS  read-write
    STATUS      current
    DESCRIPTION
                "The value is the actual size of the
                 AcceptableMasterTable. It is equal to the
                 actualTableSize member of the AcceptableMasterTable
                 structure (see 13.1.3.2), i.e., the current number of
                 elements in the acceptable master array. The actual
                 table size is less than or equal to the max table size.

                 This value SHOULD  be reflect the number of entries in 
                 the ieee8021AsAcceptableMasterTableDSMasterTable.

                 For a time-aware system that contains an ONU attached
                 to an IEEE 802.3 EPON link, the initialization value
                 is 1. For a time-aware system that does not contain an
                 ONU attached to an IEEE 802.3 EPON link, the
                  initialization value is 0."
    REFERENCE   "14.7.2 and 13.1.3.2"
    ::= { ieee8021AsAcceptableMasterTableDSBase 2 }


ieee8021AsAcceptableMasterTableDSMasterTable   OBJECT-TYPE
    SYNTAX      SEQUENCE OF Ieee8021AsAcceptableMasterTableDSMasterEntry
    MAX-ACCESS  not-accessible
    STATUS      current
    DESCRIPTION
       "A table of time-aware port related variables in a time-aware 
        bridge or for a time-aware end station.  A value of 1 is used in 
       a bridge or an end station that does not have multiple 
       components.

        The contents of this table SHALL be maintained across a restart
        of the system.
       "
    REFERENCE
       "IEEE 802.1AS clause 14.7"
    ::= { ieee8021AsAcceptableMasterTableDSMaster 1 }


ieee8021AsAcceptableMasterTableDSMasterEntry   OBJECT-TYPE
    SYNTAX      Ieee8021AsAcceptableMasterTableDSMasterEntry
    MAX-ACCESS  not-accessible
    STATUS      current
    DESCRIPTION
       "A list of objects pertaining to a port of a time-aware bridge 
        component or a time-aware end station.
       "
    INDEX { ieee8021AsAcceptableMasterTableDSMasterId }
    ::= { ieee8021AsAcceptableMasterTableDSMasterTable 1 }


Ieee8021AsAcceptableMasterTableDSMasterEntry ::=
    SEQUENCE {
      ieee8021AsAcceptableMasterTableDSMasterId         Unsigned32,
      ieee8021AsAcceptableMasterClockIdentity           ClockIdentity,
      ieee8021AsAcceptableMasterPortNumber              Unsigned32,
      ieee8021AsAcceptableMasterAlternatePriority1      Unsigned32,
      ieee8021AsAcceptableMasterRowStatus               RowStatus
      } 

ieee8021AsAcceptableMasterTableDSMasterId   OBJECT-TYPE
    SYNTAX      Unsigned32
    MAX-ACCESS  not-accessible
    STATUS      current
    DESCRIPTION
       "Acceptbale Master row entry index in this 
        ieee8021AsAcceptableMasterTabdDSMaster Entry applies. 
        If the does not contain Media type of EPON, this variable
        (index) MUST be equalto 0."
    ::= { ieee8021AsAcceptableMasterTableDSMasterEntry 1 }

ieee8021AsAcceptableMasterClockIdentity OBJECT-TYPE
    SYNTAX      ClockIdentity
    MAX-ACCESS  read-create
    STATUS      current
    DESCRIPTION
                "Globally unique manufacturer-assigned clock identifier
                for the local clock port. The identifier is based on an
                EUI-64."
    REFERENCE   "14.7.3"
    ::= { ieee8021AsAcceptableMasterTableDSMasterEntry 2 }

ieee8021AsAcceptableMasterPortNumber OBJECT-TYPE
    SYNTAX      Unsigned32(0..65535)
    MAX-ACCESS  read-create
    STATUS      current
    DESCRIPTION
                "This object represents a Port or aggregated port
                 on a bridge component or end-station.   
                 This object and ieee8021AsAcceptableMasterClockIdentity
                 together forms AccetpableMasterDS Port Identity."
    REFERENCE   "14.7.3"
    ::= { ieee8021AsAcceptableMasterTableDSMasterEntry 3 }

ieee8021AsAcceptableMasterAlternatePriority1 OBJECT-TYPE
    SYNTAX      Unsigned32(0..255)
    MAX-ACCESS  read-create
    STATUS      current
    DESCRIPTION
                "If the alternatePriority1 member of the AcceptableMaster 
                  array element that corresponds to the sourcePortIdentity 
                of a received Announce message is greater than 0, the 
                value of the grandmasterPriority1 field of the Announce 
                message is replaced by the value of alternatePriority1 
                of this AcceptableMaster array element for use in the 
                invocation of BMCA"
    REFERENCE   "14.7.3 and 13.1.3.4"
    DEFVAL { 244 }
    ::= { ieee8021AsAcceptableMasterTableDSMasterEntry 4 }

ieee8021AsAcceptableMasterRowStatus OBJECT-TYPE
    SYNTAX      RowStatus
    MAX-ACCESS  read-create
    STATUS      current
    DESCRIPTION
       "This object indicates the status of an entry, and is used
        to create/delete entries.
       "
    REFERENCE  "14.7.3"
    ::= { ieee8021AsAcceptableMasterTableDSMasterEntry 5 }



-- ******************************************************************
-- IEEE 802.1AS MIB Module - Conformance Information
-- ******************************************************************

ieee8021AsCompliances OBJECT IDENTIFIER ::= { ieee8021AsConformance 1 }
ieee8021AsGroups      OBJECT IDENTIFIER ::= { ieee8021AsConformance 2 }

-- ******************************************************************
-- Units of conformance
-- ******************************************************************

ieee8021ASSystemDefaultReqdGroup OBJECT-GROUP
    OBJECTS {
       ieee8021AsDefaultDSClockIdentity,
       ieee8021AsDefaultDSNumberPorts,
       ieee8021AsDefaultDSClockClass,
       ieee8021AsDefaultDSClockAccuracy,
       ieee8021AsDefaultDSOffsetScaledLogVariance,
       ieee8021AsDefaultDSPriority1,
       ieee8021AsDefaultDSPriority2,
       ieee8021AsDefaultDSGmCapable,
       ieee8021AsDefaultDSCurrentUTCOffset,
       ieee8021AsDefaultDSCurrentUTCOffsetValid,
       ieee8021AsDefaultDSLeap59,
       ieee8021AsDefaultDSLeap61,
       ieee8021AsDefaultDSTimeTraceable,
       ieee8021AsDefaultDSFrequencyTraceable,
       ieee8021AsDefaultDSTimeSource
    }
    STATUS      current
    DESCRIPTION
       "Objects in the System Default required global group."
    ::= { ieee8021AsGroups 1 }

ieee8021ASSystemCurrentGroup OBJECT-GROUP
    OBJECTS {
          ieee8021AsCurrentDSStepsRemoved,
          ieee8021AsCurrentDSOffsetFromMasterHs,
          ieee8021AsCurrentDSOffsetFromMasterMs,
          ieee8021AsCurrentDSOffsetFromMasterLs
    }
    STATUS      current
    DESCRIPTION
       "Objects in the System Current global group."
    ::= { ieee8021AsGroups 2 }

ieee8021AsSystemClockParentGroup OBJECT-GROUP
    OBJECTS {
        ieee8021AsParentDSParentClockIdentity,
        ieee8021AsParentDSParentPortNumber,
        ieee8021AsParentDSCumlativeRateRatio,
        ieee8021AsParentDSGrandmasterIdentity,
        ieee8021AsParentDSGrandmasterClockClass,
        ieee8021AsParentDSGrandmasterClockAccuracy,
        ieee8021AsParentDSGrandmasterOffsetScaledLogVariance,
        ieee8021AsParentDSGrandmasterPriority1,
        ieee8021AsParentDSGrandmasterPriority2
    }
    STATUS      current
    DESCRIPTION
       "Objects in the Clock Parent global group."
    ::= { ieee8021AsGroups 3 }

ieee8021AsSystemTimePropertiesGroup OBJECT-GROUP
    OBJECTS {
         ieee8021AsTimePropertiesDSCurrentUtcOffset,
         ieee8021AsTimePropertiesDSCurrentUtcOffsetValid,
         ieee8021AsTimePropertiesDSLeap59,
         ieee8021AsTimePropertiesDSLeap61,
         ieee8021AsTimePropertiesDSTimeTraceable,
         ieee8021AsTimePropertiesDSFrequencyTraceable,
         ieee8021AsTimePropertiesDSTimeSource
    }
    STATUS      current
    DESCRIPTION
       "Objects for the Time Properties Global group."
    ::= { ieee8021AsGroups 4 }

ieee8021AsPortDataSetGlobalGroup OBJECT-GROUP
    OBJECTS {
           ifIeee8021AsPortDSClockIdentity,
           ifIeee8021AsPortDSPortNumber,
           ifIeee8021AsPortDSPortRole,
           ifIeee8021AsPortDSPttPortEnabled,
           ifIeee8021AsPortDSIsMeasuringPdelay,
           ifIeee8021AsPortDSAsCapable,
           ifIeee8021AsPortDSNeighborPropDelayHs,
           ifIeee8021AsPortDSNeighborPropDelayMs,
           ifIeee8021AsPortDSNeighborPropDelayLs,
           ifIeee8021AsPortDSNeighborPropDelayThreshHs,
           ifIeee8021AsPortDSNeighborPropDelayThreshMs,
           ifIeee8021AsPortDSNeighborPropDelayThreshLs,
           ifIeee8021AsPortDSDelayAsymmetryHs,
           ifIeee8021AsPortDSDelayAsymmetryMs,
           ifIeee8021AsPortDSDelayAsymmetryLs,
           ifIeee8021AsPortDSNeighborRateRatio,
           ifIeee8021AsPortDSLogAnnounceInterval,
           ifIeee8021AsPortDSAnnounceReceiptTimeout,
           ifIeee8021AsPortDSLogSyncInterval,
           ifIeee8021AsPortDSSyncReceiptTimeout,
           ifIeee8021AsPortDSSyncReceiptTimeoutTimeIntervalHs,
           ifIeee8021AsPortDSSyncReceiptTimeoutTimeIntervalMs,
           ifIeee8021AsPortDSSyncReceiptTimeoutTimeIntervalLs,
           ifIeee8021AsPortDSLogPdelayReqInterval,
           ifIeee8021AsPortDSAllowedLostResponses,
           ifIeee8021AsPortDSVersionNumber,
           ifIeee8021AsPortDSNupMs,
           ifIeee8021AsPortDSNupLs,
           ifIeee8021AsPortDSNdownMs,
           ifIeee8021AsPortDSNdownLs,
           ifIeee8021AsPortDSAcceptableMasterTableEnabled
    }
    STATUS      current
    DESCRIPTION
       "Objects for the port dataset media independant global group."
    ::= { ieee8021AsGroups 5 }

ieee8021AsAcceptableMasterBaseGroup OBJECT-GROUP
    OBJECTS {
      ieee8021AsAcceptableMasterTableDSMaxTableSize,
      ieee8021AsAcceptableMasterTableDSActualTableSize
    }
    STATUS      current
    DESCRIPTION
       "Objects for the Acceptble Master group."
    ::= { ieee8021AsGroups 6 }

ieee8021AsAcceptableMasterTableGroup OBJECT-GROUP
    OBJECTS {
      ieee8021AsAcceptableMasterClockIdentity,
      ieee8021AsAcceptableMasterPortNumber,
      ieee8021AsAcceptableMasterAlternatePriority1,
      ieee8021AsAcceptableMasterRowStatus
    }
    STATUS      current
    DESCRIPTION
       "Objects for the Acceptble Master group."
    ::= { ieee8021AsGroups 7 }


-- ******************************************************************
-- MIB Module Compliance statements
-- ******************************************************************

ieee8021AsCompliance MODULE-COMPLIANCE
    STATUS      current
    DESCRIPTION
       "The compliance statement for support by a bridge of
        the IEEE8021-AS-MIB module."

    MODULE SNMPv2-MIB -- The SNMPv2-MIB, RFC 3418
        MANDATORY-GROUPS {
            systemGroup
        }

    MODULE IF-MIB -- The interfaces MIB, RFC 2863
        MANDATORY-GROUPS {
            ifGeneralInformationGroup
        }

    MODULE
        MANDATORY-GROUPS {
            ieee8021ASSystemDefaultReqdGroup,
            ieee8021ASSystemCurrentGroup,
            ieee8021AsSystemClockParentGroup,
            ieee8021AsSystemTimePropertiesGroup,
            ieee8021AsPortDataSetGlobalGroup,
            ieee8021AsAcceptableMasterBaseGroup,
            ieee8021AsAcceptableMasterTableGroup
         }

    OBJECT ieee8021AsAcceptableMasterRowStatus
      SYNTAX       INTEGER { active(1), notInService(2) }
      WRITE-SYNTAX INTEGER { notInService(2), createAndGo(4),
                               destroy(6) }
      DESCRIPTION "Support for createAndWait is not required."

    ::= { ieee8021AsCompliances 1 }


END
