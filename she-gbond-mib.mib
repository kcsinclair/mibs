--
-- she-gbond-mib.mib
-- MIB generated by MG-SOFT Visual MIB Builder Version 6.0  Build 88
-- Tuesday, December 08, 2009 at 14:21:57
--

-- Start of ClearCase branch-information of current release:
--  she-gbond-mib.mib   /main/she_main_grf/6
-- End of ClearCase branch-information.

	SHE-GBOND-MIB DEFINITIONS ::= BEGIN
 
		IMPORTS
			she			
				FROM AN-MIB			
			ifIndex, ifSpeed, InterfaceIndex			
				FROM IF-MIB			
			sheAlarmTimeAndDate, sheAlarmReportingSource, sheAlarmReportingSourceType, sheAlarmSeverity			
				FROM SHE-ALARMING-MIB			
			SheControlStatusType			
				FROM SHE-TC-MIB			
			OBJECT-GROUP, MODULE-COMPLIANCE, NOTIFICATION-GROUP			
				FROM SNMPv2-CONF			
			TimeTicks, Unsigned32, Gauge32, Counter32, OBJECT-TYPE, 
			MODULE-IDENTITY, NOTIFICATION-TYPE			
				FROM SNMPv2-SMI			
			PhysAddress, TruthValue, TEXTUAL-CONVENTION			
				FROM SNMPv2-TC;
	
	
		sheGBondMIB MODULE-IDENTITY 
			LAST-UPDATED "200912081300Z"		-- December 08, 2009 at 13:00 GMT
			ORGANIZATION 
				"Nokia Siemens Networks"
			CONTACT-INFO 
				"Gerd Barchmann
				COO BCS BBA RD SDE
				
				gerd.barchmann@nsn.com
				+49 3834 555654"
			DESCRIPTION 
				"The objects in this MIB module are used to manage the
				multi-pair bonded xDSL Interfaces, defined in ITU-T
				recommendations G.998.1, G.998.2.
				
				This MIB module contain information for a used bonding
				scheme specific as GBOND-ATM or GBOND-ETH.
				
				The following references are used throughout this MIB module:
				
				[G.998.1] refers to:
				  ITU-T Recommendation G.998.1: 'ATM-based multi-pair bonding',
				  January 2005.
				
				[G.998.2] refers to:
				  ITU-T Recommendation G.998.1: 'Ethernet-based multi-pair
				  bonding', January 2005.
				
				[WT-157] refers to:
				  DSL Forum Technical Report: 'Management Framework for xDSL
				  Bonding', January 2007.
				
				Naming Conventions:
				  BCE   - Bonding Channel Entity
				  CO    - Central Office
				  CPE   - Customer Premises Equipment
				  GBS   - Generic Bonding Sublayer
				  SNR   - Signal to Noise Ratio"
			REVISION "200710260000Z"		-- October 26, 2007 at 00:00 GMT
			DESCRIPTION 
				"Initial version.
				A ifIndex with ifType atmbond(234) will represent a GBondPort of bondingtype atm.
				GBondPort's of type ethernet are currently not supported via this MIB."
			REVISION "200803171605Z"		-- March 17, 2008 at 16:05 GMT
			DESCRIPTION 
				"Updated version for SHE R2.8."
			REVISION "200806091324Z"		-- June 09, 2008 at 13:24 GMT
			DESCRIPTION 
				"Remove restrictions regarding eth bonding support."
			REVISION "200807141300Z"		-- July 14, 2008 at 13:00 GMT
			DESCRIPTION 
				"Correct description of possible bonding groups on various card types."
			REVISION "200810091023Z"		-- October 09, 2008 at 10:23 GMT
			DESCRIPTION 
				"Add requestID parameter to GbondPortStack control group for ACI management system usage only."
			REVISION "200912081412Z"		-- December 08, 2009 at 14:12 GMT
			DESCRIPTION 
				"Descriptional update for all controlRequest parameters to identify all commands, 
				which do not modify the NE configuration database."
			::= { she 26 }

		
	
--
-- Type definitions
--
	
		SheGBondControlRequestType ::= INTEGER
			{
			noRequest(1),
			createGBondPort(101),
			modifyGBondPortStack(102),
			deleteGBondPort(103),
			modifyGBondPortConfiguration(110),
			modifyGBondPortThreshConfiguration(111),
			modifyGBondAtmPortConfiguration(121),
			modifyGBondEthPortConfiguration(131)
			}

		SheGBondControlRequestResultType ::= INTEGER
			{
			noRequest(1),
			comExecStarted(30),
			paramFaulty(31),
			requestBusy(32),
			setDataFailed(34),
			aswTimeout(35),
			commandFailed(36),
			commandSucceeded(37),
			resourceUnavailable(51),
			comFailedOnFirmwareRestrictions(52),
			comFailedOnHWRestrictions(53),
			comFailedOnUnsupportedBondingType(54),
			comFailedOnUnsuitableLineConditions(55)
			}

	
--
-- Textual conventions
--
	
		SheGBondPortStackBondingType ::= TEXTUAL-CONVENTION
			STATUS current
			DESCRIPTION 
				"Describes if it is an ATM or Ethernet bond."
			SYNTAX INTEGER
				{
				atmBond(1),
				ethBond(2)
				}

		TruthValueOrUnknown ::= TEXTUAL-CONVENTION
			STATUS current
			DESCRIPTION 
				"This textual convention is an extension of the TruthValue
				convention. The latter defines a boolean value with
				possible values of true(1) and false(2). This
				extension permits the additional value of unknown(0), which
				can be returned as a result of GET operation, when an exact
				true or false value of the object cannot be determined."
			SYNTAX INTEGER
				{
				unknown(0),
				true(1),
				false(2)
				}

		SheGBondFltStatusType ::= TEXTUAL-CONVENTION
			STATUS current
			DESCRIPTION 
				"G.Bond (GBS) port Fault Status. This is a bitmap of possible
				conditions."
			SYNTAX BITS
				{
				noPeer(0),
				peerPowerLoss(1),
				bceSubTypeMismatch(2),
				lowRate(3)
				}

		SheGBondPortSideType ::= TEXTUAL-CONVENTION
			STATUS current
			DESCRIPTION 
				"G.Bond port mode of operation (subtype)."
			SYNTAX INTEGER
				{
				subscriber(1),
				office(2),
				unknown(3)
				}

		SheGBondEthPtmTcType ::= TEXTUAL-CONVENTION
			STATUS current
			DESCRIPTION 
				"This textual convention represents possible PTM-TC types in
				G.bond/Eth ports. The following values are defined:
				  tc6465         - 64/65-octet encapsulation, as defined in
				                   [802.3] Clause 61.3.3
				  tcHDLC         - HDLC encapsulation, as defined in [G.998.2]
				                   Annex B"
			SYNTAX INTEGER
				{
				tc6465(1),
				tcHDLC(2)
				}

	
--
-- Node definitions
--
	
--  Node definitions
-- 
-- Structured as recommended by RFC 4181, Appendix D
		sheGBondObjects OBJECT IDENTIFIER ::= { sheGBondMIB 1 }

		
		sheGBondPort OBJECT IDENTIFIER ::= { sheGBondObjects 1 }

		
		sheGBondPortStackTable OBJECT-TYPE
			SYNTAX SEQUENCE OF SheGBondPortStackEntry
			MAX-ACCESS not-accessible
			STATUS current
			DESCRIPTION
				"This table should be used to build a bonding group."
			::= { sheGBondPort 1 }

		
		sheGBondPortStackEntry OBJECT-TYPE
			SYNTAX SheGBondPortStackEntry
			MAX-ACCESS not-accessible
			STATUS current
			DESCRIPTION
				"A ifIndex with ifType atmbond(234) will represent a GBondPort of bondingtype atm.
				A ifIndex with ifType ethbond(500) will represent a GBondPort of bondingtype eth.
				
				Note:
				The ifType ethbond is currently not defined by IANA and this value is a proprietary define!"
			INDEX { ifIndex }
			::= { sheGBondPortStackTable 1 }

		
		SheGBondPortStackEntry ::=
			SEQUENCE { 
				sheGBondPortStackAssignedIfList
					OCTET STRING,
				sheGBondPortStackBondingType
					SheGBondPortStackBondingType
			 }

		sheGBondPortStackAssignedIfList OBJECT-TYPE
			SYNTAX OCTET STRING (SIZE (3..12))
			MAX-ACCESS read-only
			STATUS current
			DESCRIPTION
				"The list of bonded interfaces.
				Each entry consist of three octets which consist of two octets for ifIndex and one
				octet for channelnumber like [16-bit ifIndex, 8-bit channelnumber].
				
				The first two octets representing the ifIndex of the bonded interface.
				A single interface could only be one time member of this list.
				The third octet, represents a valid channelnumber because the maximum number of channels per interface is 2.
				
				Bonding of multiple channels from the same physical interface in one group is not allowed.
				A ifIndex-channelnumber couple could be always member of only one bond in the NE.
				
				Important Note:
				Only existing ifIndex-channelnumber combinations could be configured. 
				The VCI setting of VccTp connections which are transported via the selected
				channels should have a restricted value range (32..255) to support needed 
				SID numbering for atm bonding. 
				The current available chipset HW and chipset firmware has additional restrictions
				for the amount of ifIndex numbers, which could be bonded in one group.
				These are:
				1. All ifIndeces has to be placed on the same IU board.
				2. A maximum number of 4 interfaces/channels could be bonded in one group. 
				3. On one IU board only Indeces which are members of the same group could be bonded.
				
				4. Additional restriction for board IU_SHDSL48:IFX (only ethbond possible). 
				On this IU board only Indeces which are members of the same group of always 4 consecutive ports
				could be bonded. Out of these groups the following bonds are possible:
				1-2 and 3-4, 1-2-3 or 1-2-3-4
				
				5. Additional restriction for board IU_VDSL48:IFX (only ethbond possible). 
				Only ports which are members of the same group out of 8 consecutive ports could be bonded. These 
				groups are: Group1(1,2,5,6) and Group2(3,4,7,8). Out of these groups the following bonds are possible:
				1-2,5-6,3-4,7-8,1-2-5,3-4-7,1-2-5-6,1-4-7-8
				
				6. Additional restriction for board IU_ADSL72:CGH (only atmbond possible). 
				Only ports out of 8 consecutive ports could be bonded. Out of these groups the following bonds are possible:
				1-2,3-4,5-6,7-8,1-2-3,5-6-7,1-2-3-4,5-6-7-8
				
				R2.8 will only support ethbond for IU_SHDSL48:IFX!!"
			::= { sheGBondPortStackEntry 1 }

		
		sheGBondPortStackBondingType OBJECT-TYPE
			SYNTAX SheGBondPortStackBondingType
			MAX-ACCESS read-only
			STATUS current
			DESCRIPTION
				"Describes if it is an ATM or Ethernet bond. Depending on this parameter, only interfaces
				which support the requested bonding type could be added to the sheGBondPortStackAssignedIfList
				for this bondingport.
				
				Note:
				The used ifTypes for new created Gbond-port in the ifTable are atmbond(234) and ethbond(500).
				The value ethbond(500) is a proprietary defined value, because there is no official definition
				from IANA available up to now!"
			DEFVAL { atmBond }
			::= { sheGBondPortStackEntry 2 }

		
		sheGBondPortStackControl OBJECT IDENTIFIER ::= { sheGBondPort 2 }

		
-- 1.3.6.1.4.1.231.7.1.2.2.1.26.1.1.2.1
		sheGBondPortStackControlRequest OBJECT-TYPE
			SYNTAX SheGBondControlRequestType
			MAX-ACCESS read-write
			STATUS current
			DESCRIPTION
				"
				createGBondPort (101):
				 sheGBondPortStackControlAssignedIfList
				 sheGBondPortStackControlBondingType
				
				modifyGBondPortStack (102):
				 sheGBondPortStackControlIndex
				 sheGBondPortStackControlAssignedIfList
				
				deleteGBondPort (103):
				 sheGBondPortStackControlIndex
				"
			::= { sheGBondPortStackControl 1 }

		
		sheGBondPortStackControlIndex OBJECT-TYPE
			SYNTAX InterfaceIndex
			MAX-ACCESS read-write
			STATUS current
			DESCRIPTION
				"IfIndex of the configured bonding-port."
			::= { sheGBondPortStackControl 2 }

		
		sheGBondPortStackControlStatus OBJECT-TYPE
			SYNTAX SheControlStatusType
			MAX-ACCESS read-only
			STATUS current
			DESCRIPTION
				"The status of a user command. 
				"
			::= { sheGBondPortStackControl 3 }

		
		sheGBondPortStackControlTimer OBJECT-TYPE
			SYNTAX Gauge32
			MAX-ACCESS read-only
			STATUS current
			DESCRIPTION
				"The maximum wait time for the manager for a long running user command."
			::= { sheGBondPortStackControl 4 }

		
		sheGBondPortStackControlReqResult OBJECT-TYPE
			SYNTAX SheGBondControlRequestResultType
			MAX-ACCESS read-only
			STATUS current
			DESCRIPTION
				"The result of the last user command."
			::= { sheGBondPortStackControl 5 }

		
		sheGBondPortStackControlTimeStamp OBJECT-TYPE
			SYNTAX Unsigned32
			UNITS "sec"
			MAX-ACCESS read-only
			STATUS current
			DESCRIPTION
				"The time stamp of the last command (end of command)."
			::= { sheGBondPortStackControl 6 }

		
		sheGBondPortStackControlAssignedIfList OBJECT-TYPE
			SYNTAX OCTET STRING (SIZE (3..12))
			MAX-ACCESS read-write
			STATUS current
			DESCRIPTION
				"look at table"
			::= { sheGBondPortStackControl 7 }

		
		sheGBondPortStackControlBondingType OBJECT-TYPE
			SYNTAX SheGBondPortStackBondingType
			MAX-ACCESS read-write
			STATUS current
			DESCRIPTION
				"look at table.
				Could never be modified!"
			::= { sheGBondPortStackControl 8 }

		
		sheGBondPortStackControlACIRequestID OBJECT-TYPE
			SYNTAX Unsigned32
			MAX-ACCESS read-write
			STATUS current
			DESCRIPTION
				"This parameter is used by ACI management system to set an unique RequestID during GBondPortStack create command.
				The parameter has NO meaning for the NE himself and will just be returned with the sheGbondPortCreated trap."
			::= { sheGBondPortStackControl 9 }

		
--     G.Bond Port (BCS) group
		sheGBondPortConfTable OBJECT-TYPE
			SYNTAX SEQUENCE OF SheGBondPortConfEntry
			MAX-ACCESS not-accessible
			STATUS current
			DESCRIPTION
				"Table for Configuration of G.Bond GBS ports. Entries in this
				table MUST be maintained in a persistent manner"
			::= { sheGBondPort 3 }

		
		sheGBondPortConfEntry OBJECT-TYPE
			SYNTAX SheGBondPortConfEntry
			MAX-ACCESS not-accessible
			STATUS current
			DESCRIPTION
				"An entry in the G.Bond Port Configuration table.
				Each entry represents an G.Bond port indexed by the ifIndex.
				Note that an G.Bond GBS port runs on top of a single
				or multiple BCE port(s), which are also indexed by ifIndex and channelnumber."
			INDEX { ifIndex }
			::= { sheGBondPortConfTable 1 }

		
		SheGBondPortConfEntry ::=
			SEQUENCE { 
				sheGBondDiscoveryCode
					PhysAddress,
				sheGBondTargetUpDataRate
					Unsigned32,
				sheGBondTargetDownDataRate
					Unsigned32,
				sheGBondThreshLowUpRate
					Unsigned32,
				sheGBondThreshLowDownRate
					Unsigned32,
				sheGBondLowRateCrossingEnable
					TruthValue
			 }

		sheGBondDiscoveryCode OBJECT-TYPE
			SYNTAX PhysAddress (SIZE (6))
			MAX-ACCESS read-only
			STATUS current
			DESCRIPTION
				"A Discovery Code of the G.Bond port (GBS).
				A unique 6 octet long code used by the Discovery function.
				This object MUST be instantiated for the -O subtype GBS before
				writing operations on the sheGBondRemoteDiscoveryCode
				(Set_if_Clear and Clear_if_Same) are performed by BCEs
				associated with the GBS.
				The initial value of this object for -R subtype ports after
				reset is all zeroes. For -R subtype ports, the value of this
				object cannot be changed directly. This value may be changed
				as a result of writing operation on the
				sheGBondRemoteDiscoveryCode object of remote BCE of -O
				subtype, connected to one of the local BCEs associated with
				the GBS.
				
				Discovery MUST be performed when the link is Down.
				Attempts to change this object MUST be rejected (in case of
				SNMP with the error inconsistentValue), if the link is Up or
				Initializing.
				
				NOTE:
				NE will always ignore any setting for this parameter and IU select
				a valid code during handshake phase."
			REFERENCE
				"[802.3] 61.2.2.8.3, 61.2.2.8.4, 45.2.6.6.1, 45.2.6.8, 61A.2"
			::= { sheGBondPortConfEntry 1 }

		
		sheGBondTargetUpDataRate OBJECT-TYPE
			SYNTAX Unsigned32 (1..1000000 | 9999999)
			UNITS "Kbps"
			MAX-ACCESS read-only
			STATUS current
			DESCRIPTION
				"A desired G.Bond port Data Rate in the upstream direction,
				in Kbps, to be achieved during initialization, under
				restrictions placed upon the member BCEs by their respective
				configuration settings.
				This object represents a sum of individual BCE upstream data
				rates, modified to compensate for fragmentation and
				encapsulation overhead (e.g. for an Ethernet service, the
				target data rate of 10Mbps SHALL allow lossless transmission
				of full-duplex 10Mbps Ethernet frame stream with minimal
				inter-frame gap).
				Note that the target upstream data rate may not be achieved
				during initialization (e.g. due to unavailability of required
				BCEs) or the initial bandwidth could deteriorate, so that the
				actual upstream data rate (sheGBondUpDataRate) could be less
				than sheGBondTargetUpDataRate.
				
				The value between 1 and 1000000 indicates that the total
				upstream data rate of the G.Bond port after initialization
				SHALL be equal to the target data rate or less, if the target
				upstream data rate cannot be achieved under the restrictions
				configured for BCEs. In case the copper environment allows to
				achieve higher upstream data rate than that specified by this
				object, the excess capability SHALL be either converted to
				additional SNR margin or reclaimed by minimizing transmit
				power.
				
				The value of 9999999 means that the target data rate is not
				fixed and SHALL be set to the maximum attainable rate during
				initialization (Best Effort), under specified spectral
				restrictions and with desired SNR Margin per BCE.
				
				This object is valid for the -O subtype G.Bond ports
				and irrelevant for the -R subtypes.
				
				Changing of the Target Upstream Data Rate MUST be performed
				when the link is Down. Attempts to change this object MUST be
				rejected (In case of SNMP with the error inconsistentValue),
				if the link is Up or Initializing.
				
				This object MUST be maintained in a persistent manner.
				
				NOTE:
				Not configurable for VDSL2 based GBOND interfaces."
			DEFVAL { 9999999 }
			::= { sheGBondPortConfEntry 2 }

		
		sheGBondTargetDownDataRate OBJECT-TYPE
			SYNTAX Unsigned32 (1..1000000 | 9999999)
			UNITS "Kbps"
			MAX-ACCESS read-only
			STATUS current
			DESCRIPTION
				"A desired G.Bond port Data Rate in the downstream direction,
				in Kbps, to be achieved during initialization, under
				restrictions placed upon the member BCEs by their respective
				configuration settings.
				This object represents a sum of individual BCE downstream data
				rates, modified to compensate for fragmentation and
				encapsulation overhead (e.g. for an Ethernet service, the
				target data rate of 10Mbps SHALL allow lossless transmission
				of full-duplex 10Mbps Ethernet frame stream with minimal
				inter-frame gap).
				Note that the target downstream data rate may not be achieved
				during initialization (e.g. due to unavailability of required
				BCEs) or the initial bandwidth could deteriorate, so that the
				actual downstream data rate (sheGBondDownDataRate) could be less
				than sheGBondTargetDownDataRate.
				
				The value between 1 and 1000000 indicates that the total
				downstream data rate of the G.Bond port after initialization
				SHALL be equal to the target data rate or less, if the target
				downstream data rate cannot be achieved under the restrictions
				configured for BCEs. In case the copper environment allows to
				achieve higher downstream data rate than that specified by
				this object, the excess capability SHALL be either converted
				to additional SNR margin or reclaimed by minimizing transmit
				power.
				
				The value of 9999999 means that the target data rate is not
				fixed and SHALL be set to the maximum attainable rate during
				initialization (Best Effort), under specified spectral
				restrictions and with desired SNR Margin per BCE.
				
				This object is valid for the -O subtype G.Bond ports
				and irrelevant for the -R subtypes.
				
				Changing of the Target Downstream Data Rate MUST be performed
				when the link is Down. Attempts to change this object MUST be
				rejected (In case of SNMP with the error inconsistentValue),
				if the link is Up or Initializing.
				
				This object MUST be maintained in a persistent manner.
				
				NOTE:
				Not configurable for VDSL2 based GBOND interfaces."
			DEFVAL { 9999999 }
			::= { sheGBondPortConfEntry 3 }

		
		sheGBondThreshLowUpRate OBJECT-TYPE
			SYNTAX Unsigned32 (1..1000000)
			UNITS "Kbps"
			MAX-ACCESS read-only
			STATUS current
			DESCRIPTION
				"This object configures the G.Bond port low upstream rate
				crossing alarm threshold. When the current value of
				sheGBondUpDataRate for this port reaches/drops below or exceeds
				this threshold, a sheGBondLowUpRateCrossing notification MAY be
				generated if enabled by sheGBondLowRateCrossingEnable.
				This object is valid for the -O subtype G.Bond ports
				and irrelevant for the -R subtypes.
				
				This object MUST be maintained in a persistent manner.
				
				NOTE:
				Not configurable for VDSL2 based GBOND interfaces."
			::= { sheGBondPortConfEntry 4 }

		
		sheGBondThreshLowDownRate OBJECT-TYPE
			SYNTAX Unsigned32 (1..1000000)
			UNITS "Kbps"
			MAX-ACCESS read-only
			STATUS current
			DESCRIPTION
				"This object configures the G.Bond port low downstream rate
				crossing alarm threshold. When the current value of
				sheGBondDownDataRate for this port reaches/drops below or exceeds
				this threshold, a sheGBondLowDownRateCrossing notification MAY
				be generated if enabled by sheGBondLowRateCrossingEnable.
				
				This object is valid for the -O subtype G.Bond ports
				and irrelevant for the -R subtypes.
				
				This object MUST be maintained in a persistent manner.
				
				NOTE:
				Not configurable for VDSL2 based GBOND interfaces."
			::= { sheGBondPortConfEntry 5 }

		
		sheGBondLowRateCrossingEnable OBJECT-TYPE
			SYNTAX TruthValue
			MAX-ACCESS read-only
			STATUS current
			DESCRIPTION
				"Indicates whether sheGBondLowUpRateCrossing and
				sheGBondLowDownRateCrossing notifications should be generated
				for this interface.
				
				Value of true(1) indicates that the notifications are enabled.
				Value of false(2) indicates that the notifications are
				disabled.
				
				This object is valid for the -O subtype G.Bond ports
				and irrelevant for the -R subtypes.
				
				This object MUST be maintained in a persistent manner.
				
				NOTE:
				Not configurable for VDSL2 based GBOND interfaces."
			DEFVAL { false }
			::= { sheGBondPortConfEntry 6 }

		
		sheGBondPortConfControl OBJECT IDENTIFIER ::= { sheGBondPort 4 }

		
-- 1.3.6.1.4.1.231.7.1.2.2.1.26.1.1.4.1
		sheGBondPortConfControlRequest OBJECT-TYPE
			SYNTAX SheGBondControlRequestType
			MAX-ACCESS read-write
			STATUS current
			DESCRIPTION
				"
				modifyGBondPortConfiguration (110):
				 sheGBondPortControlIndex
				 sheGBondPortControlDiscoveryCode          (will be ignored by NE)
				 sheGBondPortConfControlTargetUpDataRate   (not configurable for VDSL2 based GBOND interfaces)
				 sheGBondPortConfControlTargetDownDataRate (not configurable for VDSL2 based GBOND interfaces)
				
				modifyGBondPortThreshConfiguration (111):    (not configurable for VDSL2 based GBOND interfaces)
				 sheGBondPortControlIndex
				 sheGBondPortConfControlThreshLowUpRate
				 sheGBondPortConfControlThreshLowDownRate
				 sheGBondPortConfControlLowRateCrossingEnable"
			::= { sheGBondPortConfControl 1 }

		
		sheGBondPortConfControlIndex OBJECT-TYPE
			SYNTAX InterfaceIndex
			MAX-ACCESS read-write
			STATUS current
			DESCRIPTION
				"IfIndex of the configured gbond-port."
			::= { sheGBondPortConfControl 2 }

		
		sheGBondPortConfControlStatus OBJECT-TYPE
			SYNTAX SheControlStatusType
			MAX-ACCESS read-only
			STATUS current
			DESCRIPTION
				"The status of a user command. 
				"
			::= { sheGBondPortConfControl 3 }

		
		sheGBondPortConfControlTimer OBJECT-TYPE
			SYNTAX Gauge32
			MAX-ACCESS read-only
			STATUS current
			DESCRIPTION
				"The maximum wait time for the manager for a long running user command. 
				"
			::= { sheGBondPortConfControl 4 }

		
		sheGBondPortConfControlReqResult OBJECT-TYPE
			SYNTAX SheGBondControlRequestResultType
			MAX-ACCESS read-only
			STATUS current
			DESCRIPTION
				"The result of the last user command."
			::= { sheGBondPortConfControl 5 }

		
		sheGBondPortConfControlTimeStamp OBJECT-TYPE
			SYNTAX Unsigned32
			UNITS "sec"
			MAX-ACCESS read-only
			STATUS current
			DESCRIPTION
				"The time stamp of the last command (end of command)."
			::= { sheGBondPortConfControl 6 }

		
		sheGBondPortConfControlDiscoveryCode OBJECT-TYPE
			SYNTAX PhysAddress
			MAX-ACCESS read-write
			STATUS current
			DESCRIPTION
				"look at table"
			::= { sheGBondPortConfControl 7 }

		
		sheGBondPortConfControlTargetUpDataRate OBJECT-TYPE
			SYNTAX Unsigned32 (1..1000000 | 9999999)
			UNITS "Kbps"
			MAX-ACCESS read-write
			STATUS current
			DESCRIPTION
				"look at table."
			::= { sheGBondPortConfControl 8 }

		
		sheGBondPortConfControlTargetDownDataRate OBJECT-TYPE
			SYNTAX Unsigned32 (1..1000000 | 9999999)
			UNITS "Kbps"
			MAX-ACCESS read-write
			STATUS current
			DESCRIPTION
				"look at table."
			::= { sheGBondPortConfControl 9 }

		
		sheGBondPortConfControlThreshLowUpRate OBJECT-TYPE
			SYNTAX Unsigned32 (1..1000000)
			UNITS "Kbps"
			MAX-ACCESS read-write
			STATUS current
			DESCRIPTION
				"look at table."
			::= { sheGBondPortConfControl 10 }

		
		sheGBondPortConfControlThreshLowDownRate OBJECT-TYPE
			SYNTAX Unsigned32 (1..1000000)
			UNITS "Kbps"
			MAX-ACCESS read-write
			STATUS current
			DESCRIPTION
				"look at table."
			::= { sheGBondPortConfControl 11 }

		
		sheGBondPortConfControlLowRateCrossingEnable OBJECT-TYPE
			SYNTAX TruthValue
			MAX-ACCESS read-write
			STATUS current
			DESCRIPTION
				"look at table."
			::= { sheGBondPortConfControl 12 }

		
		sheGBondPortCapabilityTable OBJECT-TYPE
			SYNTAX SEQUENCE OF SheGBondPortCapabilityEntry
			MAX-ACCESS not-accessible
			STATUS current
			DESCRIPTION
				"Table for Capabilities of G.Bond Ports. Entries in this table
				MUST be maintained in a persistent manner"
			::= { sheGBondPort 5 }

		
		sheGBondPortCapabilityEntry OBJECT-TYPE
			SYNTAX SheGBondPortCapabilityEntry
			MAX-ACCESS not-accessible
			STATUS current
			DESCRIPTION
				"An entry in the G.Bond Port Capability table.
				Each entry represents an G.Bond port indexed by the ifIndex.
				Note that a G.Bond GBS port runs on top of a single
				or multiple BCE port(s), which are also indexed by ifIndex and channelnumber."
			INDEX { ifIndex }
			::= { sheGBondPortCapabilityTable 1 }

		
		SheGBondPortCapabilityEntry ::=
			SEQUENCE { 
				sheGBondPeerBond
					TruthValueOrUnknown,
				sheGBondCapacity
					Unsigned32,
				sheGBondPeerCapacity
					Unsigned32
			 }

		sheGBondPeerBond OBJECT-TYPE
			SYNTAX TruthValueOrUnknown
			MAX-ACCESS read-only
			STATUS current
			DESCRIPTION
				"Bonding Capability of the G.Bond port (GBS) link partner.
				This object has a value of true(1) when the remote GBS
				supports the same bonding scheme as the local port.
				A value of false(2) is returned when the remote GBS does not
				support the same bonding scheme.
				Ports whose peers cannot be reached because of the link
				state, SHALL return a value if unknown(0).
				
				This object maps to the WT-157 attribute aGroupPeerBndScheme."
			REFERENCE
				"[WT-157] 5.5.1.3"
			::= { sheGBondPortCapabilityEntry 1 }

		
		sheGBondCapacity OBJECT-TYPE
			SYNTAX Unsigned32 (1..32)
			MAX-ACCESS read-only
			STATUS current
			DESCRIPTION
				"Number of BCEs that can be aggregated by the local GBS.
				The number of BCEs currently assigned to a particular G.Bond
				port (sheGBondNumBCEs) is never greater than sheGBondCapacity.
				
				This object maps to the WT-157 attribute aGroupCapacity."
			REFERENCE
				"[WT-157] 5.5.1.8"
			::= { sheGBondPortCapabilityEntry 2 }

		
		sheGBondPeerCapacity OBJECT-TYPE
			SYNTAX Unsigned32 (0 | 1..32)
			MAX-ACCESS read-only
			STATUS current
			DESCRIPTION
				"Number of BCEs that can be aggregated by the peer GBS port.
				Value of 0 is returned when peer Bonding Capacity is unknown
				(peer cannot be reached).
				
				This object maps to the WT-157 attribute aGroupRemoteCapacity."
			REFERENCE
				"[WT-157] 5.5.1.9"
			::= { sheGBondPortCapabilityEntry 3 }

		
		sheGBondPortStatusTable OBJECT-TYPE
			SYNTAX SEQUENCE OF SheGBondPortStatusEntry
			MAX-ACCESS not-accessible
			STATUS current
			DESCRIPTION
				"This table provides overall status information of G.Bond
				ports, complementing the generic status information from the
				ifTable of IF-MIB. Additional status information about
				connected BCEs is available from the relevant line MIBs
				
				This table contains live data from the equibcent. As such,
				it is NOT persistent."
			::= { sheGBondPort 6 }

		
		sheGBondPortStatusEntry OBJECT-TYPE
			SYNTAX SheGBondPortStatusEntry
			MAX-ACCESS not-accessible
			STATUS current
			DESCRIPTION
				"An entry in the G.Bond Port Status table.
				Each entry represents an G.Bond port indexed by the ifIndex.
				Note that an G.Bond GBS port runs on top of a single
				or multiple BCE port(s), which are also indexed by ifIndex and channelnumber."
			INDEX { ifIndex }
			::= { sheGBondPortStatusTable 1 }

		
		SheGBondPortStatusEntry ::=
			SEQUENCE { 
				sheGBondUpDataRate
					Gauge32,
				sheGBondDownDataRate
					Gauge32,
				sheGBondFltStatus
					SheGBondFltStatusType,
				sheGBondPortSide
					SheGBondPortSideType,
				sheGBondNumBCEs
					Unsigned32
			 }

		sheGBondUpDataRate OBJECT-TYPE
			SYNTAX Gauge32
			UNITS "bps"
			MAX-ACCESS read-only
			STATUS current
			DESCRIPTION
				"A current G.Bond port operational Data Rate in the upstream
				direction, in bps.
				This object represents an estimation of the sum of individual
				BCE upstream data rates, modified to compensate for
				fragmentation and encapsulation overhead (e.g. for an Ethernet
				service, the target data rate of 10Mbps SHALL allow lossless
				transmission of full-duplex 10Mbps Ethernet frame stream with
				minimal inter-frame gap).
				
				Note that for symmetrical interfaces sheGBondUpDataRate ==
				sheGBondDownDataRate == ifSpeed."
			::= { sheGBondPortStatusEntry 1 }

		
		sheGBondDownDataRate OBJECT-TYPE
			SYNTAX Gauge32
			UNITS "bps"
			MAX-ACCESS read-only
			STATUS current
			DESCRIPTION
				"A current G.Bond port operational Data Rate in the downstream
				direction, in bps.
				This object represents an estimation of the sum of individual
				BCE downstream data rates, modified to compensate for
				fragmentation and encapsulation overhead (e.g. for an Ethernet
				service, the target data rate of 10Mbps SHALL allow lossless
				transmission of full-duplex 10Mbps Ethernet frame stream with
				minimal inter-frame gap).
				
				Note that for symmetrical interfaces sheGBondUpDataRate ==
				sheGBondDownDataRate == ifSpeed."
			::= { sheGBondPortStatusEntry 2 }

		
		sheGBondFltStatus OBJECT-TYPE
			SYNTAX SheGBondFltStatusType
			MAX-ACCESS read-only
			STATUS current
			DESCRIPTION
				"G.Bond (GBS) port Fault Status. This is a bitmap of possible
				conditions. The various bit positions are:
				  noPeer              - peer PHY cannot be reached (e.g.
				                        no BCEs attached, all BCEs are Down
				                        etc.).
				  peerPowerLoss       - peer PHY has indicated impending unit
				                        failure due to loss of local power
				                        ('Dying Gasp').
				  bceSubTypeMismatch  - local BCEs in the aggregation group
				                        are not of the same sub-type, e.g.
				                        some BCEs in the local device are -O
				                        while others are -R subtype.
				  lowRate             - sheGBondUpRate/sheGBondDownRate of the port
				                        has reached or dropped below
				                        sheGBondThreshLowUpRate/
				                        sheGBondThreshLowUpRate.
				
				This object is intended to supplement ifOperStatus object
				in IF-MIB."
			REFERENCE
				"IF-MIB, ifOperStatus; MAU-MIB, ifMauMediaAvailable"
			::= { sheGBondPortStatusEntry 3 }

		
		sheGBondPortSide OBJECT-TYPE
			SYNTAX SheGBondPortSideType
			MAX-ACCESS read-only
			STATUS current
			DESCRIPTION
				"G.Bond port mode of operation (subtype).
				The value of 'subscriber' indicates the port is designated as
				'-R' subtype (all BCEs assigned to this port are of subtype
				'-R').
				The value of the 'office' indicates that the port is
				designated as '-O' subtype (all BCEs assigned to this port are
				of subtype '-O').
				The value of 'unknown' indicates that the port has no assigned
				BCEs yet or that the assigned BCEs are not of the same side
				(subTypeBCEMismatch).
				
				This object maps to the WT-157 attribute aGroupEnd."
			REFERENCE
				"[WT-157] 5.5.1.6"
			::= { sheGBondPortStatusEntry 4 }

		
		sheGBondNumBCEs OBJECT-TYPE
			SYNTAX Unsigned32 (0..32)
			MAX-ACCESS read-only
			STATUS current
			DESCRIPTION
				"Number of BCEs that is currently aggregated by the local GBS
				(assigned to the G.Bond port using ifStackTable).
				This number is never greater than sheGBondCapacity.
				
				This object SHALL be automatically incremented or decremented
				when a BCE is added or deleted to/from the G.Bond port using
				sheGbondPortStackTable.
				
				This object maps to the WT-157 attribute aGroupNumChannels"
			REFERENCE
				"[WT-157] 5.5.1.9"
			::= { sheGBondPortStatusEntry 5 }

		
--     Port Notifications Group
		sheGBondPortNotifications OBJECT IDENTIFIER ::= { sheGBondPort 7 }

		
--     ifIndex is not needed here since we are under specific GBS
		sheGBondLowUpRateCrossing NOTIFICATION-TYPE
			OBJECTS { sheGBondUpDataRate, sheGBondThreshLowUpRate }
			STATUS current
			DESCRIPTION 
				"This notification indicates that the G.Bond port' upstream
				data rate has reached/dropped below or exceeded the low
				upstream rate threshold, specified by sheGBondThreshLowUpRate.
				
				This notification MAY be send for the -O subtype ports
				while the port is up, on the crossing event in both
				directions: from normal (rate is above the threshold) to low
				(rate equals the threshold or below it) and from low to
				normal. This notification is not applicable to the -R
				subtypes.
				
				It is RECOMMENDED that a small debouncing period of 2.5 sec,
				between the detection of the condition and notification,
				is implemented to prevent simultaneous LinkUp/LinkDown and
				sheGBondLowUpRateCrossing notifications to be sent.
				
				The adaptive nature of the G.Bond technology allows the port
				to adapt itself to the changes in the copper environment,
				e.g. an impulse noise, alien crosstalk or a micro-interruption
				may temporarily drop one or more BCEs in the aggregation
				group, causing a rate degradation of the aggregated G.Bond
				link. The dropped BCEs would then try to re-initialize,
				possibly at a lower rate than before, adjusting the rate to
				provide required target SNR margin.
				
				Generation of this notification is controlled by the
				sheGBondLowRateCrossingEnable object."
			::= { sheGBondPortNotifications 1 }

		
--     ifIndex is not needed here since we are under specific GBS
		sheGBondLowDownRateCrossing NOTIFICATION-TYPE
			OBJECTS { sheGBondDownDataRate, sheGBondThreshLowDownRate }
			STATUS current
			DESCRIPTION 
				"This notification indicates that the G.Bond port' downstream
				data rate has reached/dropped below or exceeded the low
				downstream rate threshold, specified by
				sheGBondThreshLowDownRate.
				
				This notification MAY be send for the -O subtype ports
				while the port is up, on the crossing event in both
				directions: from normal (rate is above the threshold) to low
				(rate equals the threshold or below it) and from low to
				normal. This notification is not applicable to the -R
				subtypes.
				
				It is RECOMMENDED that a small debouncing period of 2.5 sec,
				between the detection of the condition and notification,
				is implemented to prevent simultaneous LinkUp/LinkDown and
				sheGBondLowDownRateCrossing notifications to be sent.
				
				The adaptive nature of the G.Bond technology allows the port
				to adapt itself to the changes in the copper environment,
				e.g. an impulse noise, alien crosstalk or a micro-interruption
				may temporarily drop one or more BCEs in the aggregation
				group, causing a rate degradation of the aggregated G.Bond
				link. The dropped BCEs would then try to re-initialize,
				possibly at a lower rate than before, adjusting the rate to
				provide required target SNR margin.
				
				Generation of this notification is controlled by the
				sheGBondLowRateCrossingEnable object."
			::= { sheGBondPortNotifications 2 }

		
--  Notifications for GBond port configurations.
		sheGBondPortConfNotifications OBJECT IDENTIFIER ::= { sheGBondPortNotifications 3 }

		
		sheGbondPortCreated NOTIFICATION-TYPE
			OBJECTS { sheGBondPortStackControlIndex, sheGBondPortStackControlTimeStamp, sheGBondPortStackControlAssignedIfList, sheGBondPortStackControlBondingType, sheGBondPortStackControlACIRequestID
				 }
			STATUS current
			DESCRIPTION 
				"Event for successful portstack creation."
			::= { sheGBondPortConfNotifications 1 }

		
		sheGbondPortStackModified NOTIFICATION-TYPE
			OBJECTS { sheGBondPortStackControlIndex, sheGBondPortStackControlTimeStamp, sheGBondPortStackControlAssignedIfList }
			STATUS current
			DESCRIPTION 
				"Event for successful portstack modification."
			::= { sheGBondPortConfNotifications 2 }

		
		sheGbondPortDeleted NOTIFICATION-TYPE
			OBJECTS { sheGBondPortStackControlIndex, sheGBondPortStackControlTimeStamp }
			STATUS current
			DESCRIPTION 
				"Event for successful portstack delete."
			::= { sheGBondPortConfNotifications 3 }

		
		sheGBondPortConfigurationModified NOTIFICATION-TYPE
			OBJECTS { sheGBondPortConfControlIndex, sheGBondPortConfControlTimeStamp, sheGBondPortConfControlDiscoveryCode, sheGBondPortConfControlTargetUpDataRate, sheGBondPortConfControlTargetDownDataRate
				 }
			STATUS current
			DESCRIPTION 
				"Event for successful port conf modification."
			::= { sheGBondPortConfNotifications 4 }

		
		sheGBondPortThreshConfigurationModified NOTIFICATION-TYPE
			OBJECTS { sheGBondPortConfControlIndex, sheGBondPortConfControlTimeStamp, sheGBondPortConfControlThreshLowUpRate, sheGBondPortConfControlThreshLowDownRate, sheGBondPortConfControlLowRateCrossingEnable
				 }
			STATUS current
			DESCRIPTION 
				"Event for successful port threshold modification."
			::= { sheGBondPortConfNotifications 5 }

		
		sheGbondPortReqResult NOTIFICATION-TYPE
			OBJECTS { sheGBondPortStackControlIndex, sheGBondPortStackControlRequest, sheGBondPortStackControlTimeStamp, sheGBondPortStackControlReqResult }
			STATUS current
			DESCRIPTION 
				"Result notification for long running commands."
			::= { sheGBondPortConfNotifications 6 }

		
		sheGBondPortActivationFailed NOTIFICATION-TYPE
			OBJECTS { sheAlarmTimeAndDate, sheAlarmReportingSource, sheAlarmReportingSourceType, sheAlarmSeverity }
			STATUS current
			DESCRIPTION 
				"Portalarm if the IU reject the gbond portactivation request."
			::= { sheGBondPortNotifications 4 }

		
--     Sections of the module
-- Structured as recommended by RFC 4181, Appendix D
		sheGBondAtmObjects OBJECT IDENTIFIER ::= { sheGBondMIB 3 }

		
--     Groups in the module
		sheGBondAtmPort OBJECT IDENTIFIER ::= { sheGBondAtmObjects 1 }

		
--     Textual Conventions
-- Port Notifications Group
-- sheGBondAtmPortNotifications OBJECT IDENTIFIER
--  ::= { sheGBondAtmPort 0 }
-- G.Bond ATM Port group
		sheGBondAtmPortConfTable OBJECT-TYPE
			SYNTAX SEQUENCE OF SheGBondAtmPortConfEntry
			MAX-ACCESS not-accessible
			STATUS current
			DESCRIPTION
				"Table for Configuration of G.Bond ATM ports. Entries in
				this table MUST be maintained in a persistent manner"
			::= { sheGBondAtmPort 1 }

		
		sheGBondAtmPortConfEntry OBJECT-TYPE
			SYNTAX SheGBondAtmPortConfEntry
			MAX-ACCESS not-accessible
			STATUS current
			DESCRIPTION
				"An entry in the G.Bond ATM Port Configuration table.
				Each entry represents an G.Bond ATM port indexed by the
				ifIndex. Additional configuration parameters are available
				via the sheGBondPortConfEntry of sheGBOND-MIB.
				Note that an G.Bond ATM port runs on top of a single or
				multiple BCE port(s), which are also indexed by ifIndex and channelnumber."
			INDEX { ifIndex }
			::= { sheGBondAtmPortConfTable 1 }

		
		SheGBondAtmPortConfEntry ::=
			SEQUENCE { 
				sheGBondAtmUpMaxDataRate
					Unsigned32,
				sheGBondAtmDownMaxDataRate
					Unsigned32,
				sheGBondAtmUpDiffDelayTolerence
					Unsigned32,
				sheGBondAtmDownDiffDelayTolerence
					Unsigned32
			 }

--     ATM Port conf Entry
		sheGBondAtmUpMaxDataRate OBJECT-TYPE
			SYNTAX Unsigned32 (1..1000000 | 9999999)
			UNITS "Kbps"
			MAX-ACCESS read-only
			STATUS current
			DESCRIPTION
				"The maximum net upstream data rate a bonding group
				is allowed to achieve to carry an ATM stream.If set
				to '9999999', this parameter is ignored."
			REFERENCE
				"[G.998.1] Sec. 11.4.1 - (4)"
			DEFVAL { 9999999 }
			::= { sheGBondAtmPortConfEntry 1 }

		
		sheGBondAtmDownMaxDataRate OBJECT-TYPE
			SYNTAX Unsigned32 (1..1000000 | 9999999)
			UNITS "Kbps"
			MAX-ACCESS read-only
			STATUS current
			DESCRIPTION
				"The maximum net downstream data rate a bonding group
				is allowed to achieve to carry an ATM stream.If set
				to '9999999', this parameter is ignored."
			REFERENCE
				"[G.998.1] Sec. 11.4.1 - (4)"
			DEFVAL { 9999999 }
			::= { sheGBondAtmPortConfEntry 2 }

		
		sheGBondAtmUpDiffDelayTolerence OBJECT-TYPE
			SYNTAX Unsigned32 (0..8176)
			UNITS "msec"
			MAX-ACCESS read-only
			STATUS current
			DESCRIPTION
				"The maximum upstream differential delay among member links in a bonding group."
			REFERENCE
				"[G.998.1] Sec. 11.4.1 - (6)"
			::= { sheGBondAtmPortConfEntry 3 }

		
		sheGBondAtmDownDiffDelayTolerence OBJECT-TYPE
			SYNTAX Unsigned32 (0..8176)
			UNITS "msec"
			MAX-ACCESS read-only
			STATUS current
			DESCRIPTION
				"The maximum downstream differential delay among member links in a bonding group."
			REFERENCE
				"[G.998.1] Sec. 11.4.1 - (6)"
			::= { sheGBondAtmPortConfEntry 4 }

		
		sheGBondAtmPortConfControl OBJECT IDENTIFIER ::= { sheGBondAtmPort 2 }

		
-- 1.3.6.1.4.1.231.7.1.2.2.1.26.3.1.2.1
		sheGBondAtmPortConfControlRequest OBJECT-TYPE
			SYNTAX SheGBondControlRequestType
			MAX-ACCESS read-write
			STATUS current
			DESCRIPTION
				"
				modifyGBondAtmPortConfiguration (121):
				 sheGBondAtmPortControlIndex
				 sheGBondAtmPortConfControlUpMaxDataRate
				 sheGBondAtmPortConfControlDownMaxDataRate
				 sheGBondAtmPortConfControlUpDiffDelayTolerence
				 sheGBondAtmPortConfControlDownDiffDelayTolerence
				"
			::= { sheGBondAtmPortConfControl 1 }

		
		sheGBondAtmPortConfControlIndex OBJECT-TYPE
			SYNTAX InterfaceIndex
			MAX-ACCESS read-write
			STATUS current
			DESCRIPTION
				"IfIndex of the configured gbond-port."
			::= { sheGBondAtmPortConfControl 2 }

		
		sheGBondAtmPortConfControlStatus OBJECT-TYPE
			SYNTAX SheControlStatusType
			MAX-ACCESS read-only
			STATUS current
			DESCRIPTION
				"The status of a user command. 
				"
			::= { sheGBondAtmPortConfControl 3 }

		
		sheGBondAtmPortConfControlTimer OBJECT-TYPE
			SYNTAX Gauge32
			MAX-ACCESS read-only
			STATUS current
			DESCRIPTION
				"The maximum wait time for the manager for a long running user command. 
				"
			::= { sheGBondAtmPortConfControl 4 }

		
		sheGBondAtmPortConfControlReqResult OBJECT-TYPE
			SYNTAX SheGBondControlRequestResultType
			MAX-ACCESS read-only
			STATUS current
			DESCRIPTION
				"The result of the last user command."
			::= { sheGBondAtmPortConfControl 5 }

		
		sheGBondAtmPortConfControlTimeStamp OBJECT-TYPE
			SYNTAX Unsigned32
			UNITS "sec"
			MAX-ACCESS read-only
			STATUS current
			DESCRIPTION
				"The time stamp of the last command (end of command)."
			::= { sheGBondAtmPortConfControl 6 }

		
		sheGBondAtmPortConfControlUpMaxDataRate OBJECT-TYPE
			SYNTAX Unsigned32 (1..1000000 | 9999999)
			UNITS "Kbps"
			MAX-ACCESS read-write
			STATUS current
			DESCRIPTION
				"look at table."
			::= { sheGBondAtmPortConfControl 7 }

		
		sheGBondAtmPortConfControlDownMaxDataRate OBJECT-TYPE
			SYNTAX Unsigned32 (1..1000000 | 9999999)
			UNITS "Kbps"
			MAX-ACCESS read-write
			STATUS current
			DESCRIPTION
				"look at table."
			::= { sheGBondAtmPortConfControl 8 }

		
		sheGBondAtmPortConfControlUpDiffDelayTolerence OBJECT-TYPE
			SYNTAX Unsigned32 (0..8176)
			UNITS "msec"
			MAX-ACCESS read-write
			STATUS current
			DESCRIPTION
				"look at table."
			::= { sheGBondAtmPortConfControl 9 }

		
		sheGBondAtmPortConfControlDownDiffDelayTolerence OBJECT-TYPE
			SYNTAX Unsigned32 (0..8176)
			UNITS "msec"
			MAX-ACCESS read-write
			STATUS current
			DESCRIPTION
				"look at table."
			::= { sheGBondAtmPortConfControl 10 }

		
		sheGBondAtmPortStatusTable OBJECT-TYPE
			SYNTAX SEQUENCE OF SheGBondAtmPortStatusEntry
			MAX-ACCESS not-accessible
			STATUS current
			DESCRIPTION
				"This table provides overall status information of G.Bond
				ATM ports, complementing the generic status information from
				the ifTable of IF-MIB and sheGBondFltStatus of GBOND-MIB.
				Additional status information about connected BCEs is
				available from the relevant line MIBs
				This table contains live data from the equipment. As such,
				it is NOT persistent."
			::= { sheGBondAtmPort 3 }

		
		sheGBondAtmPortStatusEntry OBJECT-TYPE
			SYNTAX SheGBondAtmPortStatusEntry
			MAX-ACCESS not-accessible
			STATUS current
			DESCRIPTION
				"An entry in the G.Bond ATM port Status table.
				Each entry represents a G.Bond ATM port indexed by the
				ifIndex.
				Note that an G.Bond GBS port runs on top of a single
				or multiple BCE port(s), which are also indexed by ifIndex and channelnumber."
			INDEX { ifIndex }
			::= { sheGBondAtmPortStatusTable 1 }

		
		SheGBondAtmPortStatusEntry ::=
			SEQUENCE { 
				sheGBondAtmShowTime
					TimeTicks,
				sheGBondAtmUpRxCellLossCount
					Counter32,
				sheGBondAtmDownRxCellLossCount
					Counter32
			 }

--     ATM Port status entries
		sheGBondAtmShowTime OBJECT-TYPE
			SYNTAX TimeTicks
			UNITS "seconds"
			MAX-ACCESS read-only
			STATUS current
			DESCRIPTION
				"The accumulated time when a bonding group is in normal operation."
			REFERENCE
				"[G.998.1] Sec. 11.4.2 - (3)"
			::= { sheGBondAtmPortStatusEntry 1 }

		
		sheGBondAtmUpRxCellLossCount OBJECT-TYPE
			SYNTAX Counter32
			MAX-ACCESS read-only
			STATUS current
			DESCRIPTION
				"The total number of cells that are lost at aggregation
				output in the upstream direction from a bonding group
				for the accumulation interval."
			REFERENCE
				"[G.998.1] Sec. 11.4.2 - (4)"
			::= { sheGBondAtmPortStatusEntry 2 }

		
		sheGBondAtmDownRxCellLossCount OBJECT-TYPE
			SYNTAX Counter32
			MAX-ACCESS read-only
			STATUS current
			DESCRIPTION
				"The total number of cells that are lost at aggregation
				output in the downstream direction from a bonding
				group for the accumulation interval."
			REFERENCE
				"[G.998.1] Sec. 11.4.2 - (4)"
			::= { sheGBondAtmPortStatusEntry 3 }

		
--  Notifications for GBond Atm port configurations.
		sheGBondAtmPortConfNotifications OBJECT IDENTIFIER ::= { sheGBondAtmPort 4 }

		
		sheGbondAtmPortModified NOTIFICATION-TYPE
			OBJECTS { sheGBondAtmPortConfControlIndex, sheGBondAtmPortConfControlTimeStamp, sheGBondAtmPortConfControlUpMaxDataRate, sheGBondAtmPortConfControlDownMaxDataRate, sheGBondAtmPortConfControlUpDiffDelayTolerence, 
				sheGBondAtmPortConfControlDownDiffDelayTolerence }
			STATUS current
			DESCRIPTION 
				"Event for successful Atm port modification."
			::= { sheGBondAtmPortConfNotifications 1 }

		
--  Sections of the module structured as recommended by RFC 4181, Appendix D.
-- The complete object group is currently NOT supported.
		sheGBondEthObjects OBJECT IDENTIFIER ::= { sheGBondMIB 5 }

		
--     Groups in the module
		sheGBondEthPort OBJECT IDENTIFIER ::= { sheGBondEthObjects 1 }

		
--     GBS Notifications group
-- empty --
-- GBS group
		sheGBondEthPortConfTable OBJECT-TYPE
			SYNTAX SEQUENCE OF SheGBondEthPortConfEntry
			MAX-ACCESS not-accessible
			STATUS current
			DESCRIPTION
				"Table for Configuration of G.Bond/Eth GBS ports. Entries in
				this table MUST be maintained in a persistent manner"
			::= { sheGBondEthPort 1 }

		
		sheGBondEthPortConfEntry OBJECT-TYPE
			SYNTAX SheGBondEthPortConfEntry
			MAX-ACCESS not-accessible
			STATUS current
			DESCRIPTION
				"An entry in the G.Bond/Eth Port Configuration table.
				Each entry represents an G.Bond Ethernet port indexed by the
				ifIndex.
				Note that an G.Bond/Eth GBS port runs on top of a single
				or multiple BCE port(s), which are also indexed by ifIndex."
			INDEX { ifIndex }
			::= { sheGBondEthPortConfTable 1 }

		
		SheGBondEthPortConfEntry ::=
			SEQUENCE { 
				sheGBondEthTcAdminType
					SheGBondEthPtmTcType
			 }

		sheGBondEthTcAdminType OBJECT-TYPE
			SYNTAX SheGBondEthPtmTcType
			MAX-ACCESS read-only
			STATUS current
			DESCRIPTION
				"Administrative (desired) PTM-TC encapsulation type of G.Bond/Eth port (GBS).
				Possible values are:
				  tc6465(1)  - 64/65-octet encapsulation
				  tcHDLC(2)  - HDLC encapsulation
				Attempts to set a port to a non-supported PTM-TC encapsulation type (see sheGBondEthTcTypesSupported)
				SHALL be rejected.
				
				Changing sheGBondEthTcAdminType is a traffic disruptive operation and as such
				SHALL be done when the link is Down. Attempts to cange this object SHALL be
				rejected if the link is Up or Initializing.
				
				This object maps to the WT-159 attribute aEthTcAdminType.
				This object MUST be maintained in a persistent manner."
			REFERENCE
				"[WT-159] 5.5.3.1"
			DEFVAL { tc6465 }
			::= { sheGBondEthPortConfEntry 1 }

		
		sheGBondEthPortConfControl OBJECT IDENTIFIER ::= { sheGBondEthPort 2 }

		
-- 1.3.6.1.4.1.231.7.1.2.2.1.26.5.1.2.1
		sheGBondEthPortConfControlRequest OBJECT-TYPE
			SYNTAX SheGBondControlRequestType
			MAX-ACCESS read-write
			STATUS current
			DESCRIPTION
				"
				modifyGBondEthPortConfiguration (131):
				 sheGBondEthPortControlIndex
				 sheGBondEthPortConfControlTcAdminType
				
				NOTE:
				Possible configuration depend on reported capability."
			::= { sheGBondEthPortConfControl 1 }

		
		sheGBondEthPortConfControlIndex OBJECT-TYPE
			SYNTAX InterfaceIndex
			MAX-ACCESS read-write
			STATUS current
			DESCRIPTION
				"IfIndex of the configured xdsl-interface."
			::= { sheGBondEthPortConfControl 2 }

		
		sheGBondEthPortConfControlStatus OBJECT-TYPE
			SYNTAX SheControlStatusType
			MAX-ACCESS read-only
			STATUS current
			DESCRIPTION
				"The status of a user command. 
				"
			::= { sheGBondEthPortConfControl 3 }

		
		sheGBondEthPortConfControlTimer OBJECT-TYPE
			SYNTAX Gauge32
			MAX-ACCESS read-only
			STATUS current
			DESCRIPTION
				"The maximum wait time for the manager for a long running user command. 
				"
			::= { sheGBondEthPortConfControl 4 }

		
		sheGBondEthPortConfControlReqResult OBJECT-TYPE
			SYNTAX SheGBondControlRequestResultType
			MAX-ACCESS read-only
			STATUS current
			DESCRIPTION
				"The result of the last user command."
			::= { sheGBondEthPortConfControl 5 }

		
		sheGBondEthPortConfControlTimeStamp OBJECT-TYPE
			SYNTAX Unsigned32
			UNITS "sec"
			MAX-ACCESS read-only
			STATUS current
			DESCRIPTION
				"The time stamp of the last command (end of command)."
			::= { sheGBondEthPortConfControl 6 }

		
		sheGBondEthPortConfControlTcAdminType OBJECT-TYPE
			SYNTAX SheGBondEthPtmTcType
			MAX-ACCESS read-write
			STATUS current
			DESCRIPTION
				"look at table."
			::= { sheGBondEthPortConfControl 7 }

		
		sheGBondEthPortCapabilityTable OBJECT-TYPE
			SYNTAX SEQUENCE OF SheGBondEthPortCapabilityEntry
			MAX-ACCESS not-accessible
			STATUS current
			DESCRIPTION
				"Table for Capabilities of G.Bond/Eth Ports. Entries in this
				table MUST be maintained in a persistent manner."
			::= { sheGBondEthPort 3 }

		
		sheGBondEthPortCapabilityEntry OBJECT-TYPE
			SYNTAX SheGBondEthPortCapabilityEntry
			MAX-ACCESS not-accessible
			STATUS current
			DESCRIPTION
				"An entry in the G.Bond/Eth Port Capability table.
				Each entry represents an G.Bond port indexed by the ifIndex.
				Note that a G.Bond GBS port runs on top of a single
				or multiple BCE port(s), which are also indexed by ifIndex."
			INDEX { ifIndex }
			::= { sheGBondEthPortCapabilityTable 1 }

		
		SheGBondEthPortCapabilityEntry ::=
			SEQUENCE { 
				sheGBondEthTcTypesSupported
					BITS
			 }

		sheGBondEthTcTypesSupported OBJECT-TYPE
			SYNTAX BITS
				{
				tc6465(0),
				tcHDLC(1)
				}
			MAX-ACCESS read-only
			STATUS current
			DESCRIPTION
				"PTM-TC Encapsulation types supported by the G.Bond/Eth port.
				This is a bitmap of possible encapsulation types. The various
				bit positions are:
				  tc6465   - GBS is capable of 64/65-octet encapsulation
				  tcHDLC   - GBS is capable of HDLC encapsulation
				
				A desired encapsulation is determined by sheGBondEthTcAdminType,
				while sheGBondEthTcOperType reflects the current operating mode.
				
				This object maps to the WT-159 attribute aEthTcTypesSupported."
			REFERENCE
				"[WT-159] 5.5.3.3"
			::= { sheGBondEthPortCapabilityEntry 1 }

		
		sheGBondEthPortStatusTable OBJECT-TYPE
			SYNTAX SEQUENCE OF SheGBondEthPortStatusEntry
			MAX-ACCESS not-accessible
			STATUS current
			DESCRIPTION
				"This table provides overall status information of G.Bond
				ports, complementing the generic status information from the
				ifTable of IF-MIB. Additional status information about
				connected BCEs is available from the relevant line MIBs
				This table contains live data from the equipment. As such,
				it is NOT persistent."
			::= { sheGBondEthPort 4 }

		
		sheGBondEthPortStatusEntry OBJECT-TYPE
			SYNTAX SheGBondEthPortStatusEntry
			MAX-ACCESS not-accessible
			STATUS current
			DESCRIPTION
				"An entry in the G.Bond/Eth Port Status table.
				Each entry represents an G.Bond/Eth port indexed by the
				ifIndex.
				Note that an G.Bond GBS port runs on top of a single
				or multiple BCE port(s), which are also indexed by ifIndex."
			INDEX { ifIndex }
			::= { sheGBondEthPortStatusTable 1 }

		
		SheGBondEthPortStatusEntry ::=
			SEQUENCE { 
				sheGBondEthTcOperType
					SheGBondEthPtmTcType,
				sheGBondEthInErrors
					Counter32,
				sheGBondEthInSmallFragments
					Counter32,
				sheGBondEthInLargeFragments
					Counter32,
				sheGBondEthInBadFragments
					Counter32,
				sheGBondEthInLostFragments
					Counter32,
				sheGBondEthInLostStarts
					Counter32,
				sheGBondEthInLostEnds
					Counter32,
				sheGBondEthInOverflows
					Counter32
			 }

		sheGBondEthTcOperType OBJECT-TYPE
			SYNTAX SheGBondEthPtmTcType
			MAX-ACCESS read-only
			STATUS current
			DESCRIPTION
				"Current operational encapsulation type of the G.Bond/Eth port.
				Possible values are:
				  tc6465(1)   - GBS uses 64/65-octet encapsulation
				  tcHDLC(2)   - GBS uses HDLC encapsulation
				
				The operational PTM-TC encapsulation type can be configured
				via sheGBondEthTcAdminType variable.
				
				This objects maps to the WT-159 aEthTcOperType."
			REFERENCE
				"[WT-159] 5.5.3.2"
			::= { sheGBondEthPortStatusEntry 1 }

		
		sheGBondEthInErrors OBJECT-TYPE
			SYNTAX Counter32
			MAX-ACCESS read-only
			STATUS current
			DESCRIPTION
				"A number of fragments that have been received across the
				gamma interface and discarded.
				
				This object maps to the WT-159 attribute aEthRxErrors.
				
				Discontinuities in the value of this counter can occur at
				re-initialization of the management system, and at other times
				as indicated by the value of ifCounterDiscontinuityTime,
				defined in IF-MIB."
			REFERENCE
				"[WT-159] 5.5.3.4"
			::= { sheGBondEthPortStatusEntry 2 }

		
		sheGBondEthInSmallFragments OBJECT-TYPE
			SYNTAX Counter32
			MAX-ACCESS read-only
			STATUS current
			DESCRIPTION
				"A number of fragments smaller than minFragmentSize
				(64 Bytes), that have been received across the gamma
				interface and discarded.
				
				This object maps to the WT-159 attribute aEthRxSmallFragments.
				
				Discontinuities in the value of this counter can occur at
				re-initialization of the management system, and at other times
				as indicated by the value of ifCounterDiscontinuityTime,
				defined in IF-MIB."
			REFERENCE
				"[WT-159] 5.5.3.5"
			::= { sheGBondEthPortStatusEntry 3 }

		
		sheGBondEthInLargeFragments OBJECT-TYPE
			SYNTAX Counter32
			MAX-ACCESS read-only
			STATUS current
			DESCRIPTION
				"A number of fragments larger than maxFragmentSize
				(512 Bytes), which have been received across the gamma
				interface and discarded.
				
				This object maps to the WT-159 attribute aEthRxLargeFragments.
				Discontinuities in the value of this counter can occur at
				re-initialization of the management system, and at other times
				as indicated by the value of ifCounterDiscontinuityTime,
				defined in IF-MIB."
			REFERENCE
				"[WT-159] 5.5.3.6"
			::= { sheGBondEthPortStatusEntry 4 }

		
		sheGBondEthInBadFragments OBJECT-TYPE
			SYNTAX Counter32
			MAX-ACCESS read-only
			STATUS current
			DESCRIPTION
				"A number of fragments which do not fit into the sequence
				expected by the frame assembly function, that have been
				received across the gamma interface and discarded (the
				frame buffer is flushed to the next valid frame start).
				
				This object maps to the WT-159 attribute aEthRxBadFragments.
				
				Discontinuities in the value of this counter can occur at
				re-initialization of the management system, and at other times
				as indicated by the value of ifCounterDiscontinuityTime,
				defined in IF-MIB."
			REFERENCE
				"[WT-159] 5.5.3.7"
			::= { sheGBondEthPortStatusEntry 5 }

		
		sheGBondEthInLostFragments OBJECT-TYPE
			SYNTAX Counter32
			MAX-ACCESS read-only
			STATUS current
			DESCRIPTION
				"A number of gaps in the sequence of fragments, which have
				been received across the gamma interface (the frame buffer is
				flushed to the next valid frame start, when fragment/fragments
				expected by the frame assembly function is/are not received).
				
				This object maps to the WT-159 attribute aEthRxLostFragments.
				
				Discontinuities in the value of this counter can occur at
				re-initialization of the management system, and at other times
				as indicated by the value of ifCounterDiscontinuityTime,
				defined in IF-MIB."
			REFERENCE
				"[WT-159] 5.5.3.8"
			::= { sheGBondEthPortStatusEntry 6 }

		
		sheGBondEthInLostStarts OBJECT-TYPE
			SYNTAX Counter32
			MAX-ACCESS read-only
			STATUS current
			DESCRIPTION
				"A number of missing StartOfPacket indicators expected by the
				frame assembly function.
				
				This object maps to the WT-159 attribute aEthRxLostStarts.
				
				Discontinuities in the value of this counter can occur at
				re-initialization of the management system, and at other times
				as indicated by the value of ifCounterDiscontinuityTime,
				defined in IF-MIB."
			REFERENCE
				"[WT-159] 5.5.3.9"
			::= { sheGBondEthPortStatusEntry 7 }

		
		sheGBondEthInLostEnds OBJECT-TYPE
			SYNTAX Counter32
			MAX-ACCESS read-only
			STATUS current
			DESCRIPTION
				"A number of missing EndOfPacket indicators expected by the
				frame assembly function.
				
				This object maps to the WT-159 attribute aEthRxLostEnds.
				
				Discontinuities in the value of this counter can occur at
				re-initialization of the management system, and at other times
				as indicated by the value of ifCounterDiscontinuityTime,
				defined in IF-MIB."
			REFERENCE
				"[WT-159] 5.5.3.10"
			::= { sheGBondEthPortStatusEntry 8 }

		
		sheGBondEthInOverflows OBJECT-TYPE
			SYNTAX Counter32
			MAX-ACCESS read-only
			STATUS current
			DESCRIPTION
				"A number of fragments, received across the gamma interface
				and discarded, which would have caused the frame assembly
				buffer to overflow.
				
				This object maps to the WT-159 attribute aEthRxOverflows.
				
				Discontinuities in the value of this counter can occur at
				re-initialization of the management system, and at other times
				as indicated by the value of ifCounterDiscontinuityTime,
				defined in IF-MIB."
			REFERENCE
				"[WT-159] 5.5.3.11"
			::= { sheGBondEthPortStatusEntry 9 }

		
--  Notifications for GBond Eth port configurations.
		sheGBondEthPortConfNotifications OBJECT IDENTIFIER ::= { sheGBondEthPort 5 }

		
		sheGbondEthPortModified NOTIFICATION-TYPE
			OBJECTS { sheGBondEthPortConfControlIndex, sheGBondEthPortConfControlTimeStamp, sheGBondEthPortConfControlTcAdminType }
			STATUS current
			DESCRIPTION 
				"Event for successful Eth port modification."
			::= { sheGBondEthPortConfNotifications 1 }

		
		sheGBondEthBce OBJECT IDENTIFIER ::= { sheGBondEthObjects 2 }

		
--     BCE group
		sheGBondEthBceStatusTable OBJECT-TYPE
			SYNTAX SEQUENCE OF SheGBondEthBceStatusEntry
			MAX-ACCESS not-accessible
			STATUS current
			DESCRIPTION
				"This table provides common status information of G.Bond/Eth
				BCE ports.
				
				This table contains live data from the equipment. As such,
				it is NOT persistent."
			::= { sheGBondEthBce 1 }

		
		sheGBondEthBceStatusEntry OBJECT-TYPE
			SYNTAX SheGBondEthBceStatusEntry
			MAX-ACCESS not-accessible
			STATUS current
			DESCRIPTION
				"An entry in the G.Bond/Eth BCE Status table.
				Each entry represents common aspects of a G.Bond/Eth BCE port
				indexed by the ifIndex. Note that a BCE port can be stacked
				below a single GBS port, also indexed by ifIndex,
				possibly together with other BCE ports."
			INDEX { ifIndex }
			::= { sheGBondEthBceStatusTable 1 }

		
		SheGBondEthBceStatusEntry ::=
			SEQUENCE { 
				sheGBondEthBceTcInCodingErrors
					Counter32,
				sheGBondEthBceTcInCrcErrors
					Counter32
			 }

		sheGBondEthBceTcInCodingErrors OBJECT-TYPE
			SYNTAX Counter32
			MAX-ACCESS read-only
			STATUS current
			DESCRIPTION
				"A number of PTM-TC encapsulation errors. This counter is
				incremented for each encapsulation error detected by the
				PTM-TC receive function.
				This object maps to WT-159 attribute
				aChannelPtmTcRxCodingViolations.
				
				Discontinuities in the value of this counter can occur at
				re-initialization of the management system, and at other times
				as indicated by the value of ifCounterDiscontinuityTime,
				defined in IF-MIB."
			REFERENCE
				"[WT-159] 5.5.7.5"
			::= { sheGBondEthBceStatusEntry 1 }

		
		sheGBondEthBceTcInCrcErrors OBJECT-TYPE
			SYNTAX Counter32
			MAX-ACCESS read-only
			STATUS current
			DESCRIPTION
				"A number of PTM-TC CRC errors. This counter is incremented
				for each CRC error detected by the PTM-TC receive function.
				
				This object maps to WT-159 attribute aChannelPtmTcRxCrcErrors.
				
				Discontinuities in the value of this counter can occur at
				re-initialization of the management system, and at other times
				as indicated by the value of ifCounterDiscontinuityTime,
				defined in IF-MIB."
			REFERENCE
				"[WT-159] 5.5.7.6"
			::= { sheGBondEthBceStatusEntry 2 }

		
		sheGBondConformance OBJECT IDENTIFIER ::= { sheGBondMIB 100 }

		
		sheGBondCompliances OBJECT IDENTIFIER ::= { sheGBondConformance 1 }

		
--     Compliance Statements
-- this module
-- this module
		sheGBondCompliance MODULE-COMPLIANCE
			STATUS current
			DESCRIPTION 
				"The compliance statement for SHE G.Bond interfaces.
				"
			MODULE -- this module
				MANDATORY-GROUPS { sheGBondBasicGroup, sheGBondDiscoveryGroup, sheGBondAlarmConfGroup, sheGBondNotificationGroup, sheGBondEthBasicGroup, 
					sheGBondEthBceGroup, sheGBondAtmBasicGroup, sheGBondPortStackGroup, sheGBondPortControlGroup, sheGBondPortConfNotificationGroup
					 }
			::= { sheGBondCompliances 1 }

		
--     Conformance Statements
-- 
		sheGBondGroups OBJECT IDENTIFIER ::= { sheGBondConformance 2 }

		
--     Object Groups
		sheGBondBasicGroup OBJECT-GROUP
			OBJECTS { sheGBondUpDataRate, sheGBondDownDataRate, sheGBondTargetUpDataRate, sheGBondTargetDownDataRate, sheGBondCapacity, 
				sheGBondNumBCEs, sheGBondPortSide, sheGBondFltStatus }
			STATUS current
			DESCRIPTION 
				"A collection of objects representing management information
				common to all types of G.Bond ports."
			::= { sheGBondGroups 1 }

		
		sheGBondDiscoveryGroup OBJECT-GROUP
			OBJECTS { sheGBondPeerBond, sheGBondPeerCapacity, sheGBondDiscoveryCode }
			STATUS current
			DESCRIPTION 
				"A collection of objects supporting OPTIONAL G.Bond discovery
				in G.Bond ports."
			::= { sheGBondGroups 2 }

		
		sheGBondAlarmConfGroup OBJECT-GROUP
			OBJECTS { sheGBondThreshLowUpRate, sheGBondThreshLowDownRate, sheGBondLowRateCrossingEnable }
			STATUS current
			DESCRIPTION 
				"A collection of objects required for configuration of alarm
				thresholds and notifications in G.Bond ports."
			::= { sheGBondGroups 3 }

		
		sheGBondNotificationGroup NOTIFICATION-GROUP
			NOTIFICATIONS { sheGBondLowUpRateCrossing, sheGBondLowDownRateCrossing, sheGBondPortActivationFailed }
			STATUS current
			DESCRIPTION 
				"This group supports notifications of significant conditions
				associated with G.Bond ports."
			::= { sheGBondGroups 4 }

		
--     Object Groups
		sheGBondEthBasicGroup OBJECT-GROUP
			OBJECTS { sheGBondEthTcTypesSupported, sheGBondEthTcAdminType, sheGBondEthTcOperType, sheGBondEthInErrors, sheGBondEthInSmallFragments, 
				sheGBondEthInLargeFragments, sheGBondEthInBadFragments, sheGBondEthInLostFragments, sheGBondEthInLostStarts, sheGBondEthInLostEnds, 
				sheGBondEthInOverflows, sheGBondEthBceTcInCodingErrors, sheGBondEthBceTcInCrcErrors }
			STATUS current
			DESCRIPTION 
				"A collection of objects representing management information
				for G.Bond/Eth GBS ports."
			::= { sheGBondGroups 5 }

		
		sheGBondEthBceGroup OBJECT-GROUP
			OBJECTS { sheGBondEthBceTcInCodingErrors, sheGBondEthBceTcInCrcErrors }
			STATUS current
			DESCRIPTION 
				"A collection of objects representing OPTIONAL management
				information for G.Bond/Eth BCE ports."
			::= { sheGBondGroups 6 }

		
--     Object Groups
		sheGBondAtmBasicGroup OBJECT-GROUP
			OBJECTS { sheGBondAtmUpMaxDataRate, sheGBondAtmDownMaxDataRate, sheGBondAtmUpDiffDelayTolerence, sheGBondAtmDownDiffDelayTolerence, sheGBondAtmShowTime, 
				sheGBondAtmUpRxCellLossCount, sheGBondAtmDownRxCellLossCount }
			STATUS current
			DESCRIPTION 
				"A collection of objects representing management
				information for G.Bond ATM ports."
			::= { sheGBondGroups 7 }

		
		sheGBondPortStackGroup OBJECT-GROUP
			OBJECTS { sheGBondPortStackAssignedIfList, sheGBondPortStackBondingType }
			STATUS current
			DESCRIPTION 
				"Description."
			::= { sheGBondGroups 8 }

		
		sheGBondPortControlGroup OBJECT-GROUP
			OBJECTS { sheGBondPortStackControlRequest, sheGBondPortStackControlIndex, sheGBondPortStackControlStatus, sheGBondPortStackControlTimer, sheGBondPortStackControlReqResult, 
				sheGBondPortStackControlTimeStamp, sheGBondPortStackControlAssignedIfList, sheGBondPortStackControlBondingType, sheGBondPortStackControlACIRequestID, sheGBondPortConfControlRequest, 
				sheGBondPortConfControlIndex, sheGBondPortConfControlStatus, sheGBondPortConfControlTimer, sheGBondPortConfControlReqResult, sheGBondPortConfControlTimeStamp, 
				sheGBondPortConfControlDiscoveryCode, sheGBondPortConfControlTargetUpDataRate, sheGBondPortConfControlTargetDownDataRate, sheGBondPortConfControlThreshLowUpRate, sheGBondPortConfControlThreshLowDownRate, 
				sheGBondPortConfControlLowRateCrossingEnable, sheGBondAtmPortConfControlRequest, sheGBondAtmPortConfControlIndex, sheGBondAtmPortConfControlStatus, sheGBondAtmPortConfControlTimer, 
				sheGBondAtmPortConfControlReqResult, sheGBondAtmPortConfControlTimeStamp, sheGBondAtmPortConfControlUpMaxDataRate, sheGBondAtmPortConfControlDownMaxDataRate, sheGBondAtmPortConfControlUpDiffDelayTolerence, 
				sheGBondAtmPortConfControlDownDiffDelayTolerence, sheGBondEthPortConfControlRequest, sheGBondEthPortConfControlIndex, sheGBondEthPortConfControlStatus, sheGBondEthPortConfControlTimer, 
				sheGBondEthPortConfControlReqResult, sheGBondEthPortConfControlTimeStamp, sheGBondEthPortConfControlTcAdminType }
			STATUS current
			DESCRIPTION 
				"Description."
			::= { sheGBondGroups 9 }

		
		sheGBondPortConfNotificationGroup NOTIFICATION-GROUP
			NOTIFICATIONS { sheGbondPortCreated, sheGbondPortStackModified, sheGbondPortDeleted, sheGBondPortConfigurationModified, sheGBondPortThreshConfigurationModified, 
				sheGbondAtmPortModified, sheGbondEthPortModified, sheGbondPortReqResult }
			STATUS current
			DESCRIPTION 
				"Description."
			::= { sheGBondGroups 10 }

		
	
	END

--
-- she-gbond-mib.mib
--
