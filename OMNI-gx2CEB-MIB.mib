OMNI-gx2CEB-MIB DEFINITIONS ::= BEGIN

    IMPORTS
	IpAddress, TimeTicks            
					      FROM RFC1155-SMI
	OBJECT-TYPE                     
					      FROM RFC-1212
	sysUpTime, DisplayString        
					      FROM RFC1213-MIB
	TRAP-TYPE                       
					      FROM RFC-1215
	gi, motproxies                   
					      FROM NLS-BBNIDENT-MIB
	gx2CEB
					      FROM GX2HFC-MIB

	trapIdentifier,trapNetworkElemModelNumber,
	trapNetworkElemSerialNum, trapPerceivedSeverity,
	trapNetworkElemOperState, trapNetworkElemAlarmStatus,
	trapNetworkElemAdminState, trapNetworkElemAvailStatus,
	trapText, trapNETrapLastTrapTimeStamp, trapChangedObjectId,
	trapChangedValueInteger, trapChangedValueDisplayString
					      FROM NLSBBN-TRAPS-MIB;



	       -- This MIB module uses the extended OBJECT-TYPE macro as
	       -- defined in RFC1212 and the TRAP-TYPE macro as defined
	       -- in RFC 1215.

		   --REVISION	"0" Sept 1, 2003
		   --DESCRIPTION
		   --			Added revision and description comment section


		--    OMNISTAR DM 1550 Laser Module (Return Path Transmetter)  MIB MODULE

	-- This MIB module defines information for management of HFC networks
		-- 
		-- The MIB module assumes that all generic (static) network element
		-- information is defined in a different module such as the HFC module
		-- The MIB consists of two groups:
		-- the device type descriptor subgroup and 
		-- gx2CEB Network Elements subgroup.
		-- The device type descriptor subgroup is used to define 
		-- parameters specific to gx2CEB device type.
		-- These parameters are common across all network elements
		-- from gx2CEB device type.
		--
		-- The gx2CEB Network Elements subgroup is
		-- a list of gx2CEB type elements in the
		-- current network topology with nominal
		-- and current parameter values for the
		-- individual network elements; the individual
		-- network elements are identified by  
		-- index from hfcCommonTable.
		-- That implies what hfcCommonTableIndex and
		-- gx2CEBTableIndex are equal for each individual
		-- network element.
		-- This table is an extension of the hfcCommonTable
		-- for all elements of gx2CEB type.
		--
		-- Both groups are mandatory for management of gx2CEB devices.

-- ****************************************************************************
		--
		-- All floating point numbers will be represented by an IEEE 32 Bit number.
		-- Conversion of this number must be done on the user interface to view the 
		-- actual floating point number. 
		--

		Float ::= Counter  -- UNSIGNED (32 BITS) 

-- ****************************************************************************

		-- gx2CEB Device Descriptor subgroup.

		-- The device type descriptor subgroup is used to define 
		-- parameters specific to gx2CEB device type.
		-- These parameters are common across all network elements
		-- from gx2CEB device type.


		gx2CEBDescriptor OBJECT IDENTIFIER ::= {gx2CEB 1}



--*****************************************************************************
		--              gx2CEB Table
		
		-- Contains a list of all gx2CEB type devices in
		-- the network. Each device is characterized with
		-- current network topology information, with nominal
		-- and current parameter values for the
		-- individual network elements;
		--
		-- The individual network elements indentified by  
		-- index from hfcCommonTable.
		-- That implies what hfcCommonTableIndex and
		-- gx2CEBTableIndex are equal for each individual
		-- nettwork element.
		-- This table should be used as an extension of the hfcCommonTable
		-- for all elements of gx2CEB type.


	       gx2CEBAnalogTable                    OBJECT-TYPE
			 SYNTAX             SEQUENCE OF Gx2CEBAnalogEntry
			 ACCESS             not-accessible
			 STATUS             mandatory
			 DESCRIPTION
			 "This table contains gx2CEB specific parameters with
			  nominal and current values."
			 ::= { gx2CEB 2 }


	       gx2CEBAnalogEntry               OBJECT-TYPE
			 SYNTAX             Gx2CEBAnalogEntry
			 ACCESS             not-accessible
			 STATUS             mandatory
			 DESCRIPTION
			 "This list contains the analog parameters and descriptions."
			 INDEX { gx2CEBAnalogTableIndex }
			 ::= { gx2CEBAnalogTable  1}

--*************************************************************************
--************ No Digital Table *******************************************
--*************************************************************************
	       gx2CEBStatusTable                    OBJECT-TYPE
			 SYNTAX             SEQUENCE OF Gx2CEBStatusEntry
			 ACCESS             not-accessible
			 STATUS             mandatory
			 DESCRIPTION
			 "This table contains gx2CEB specific parameters with
			  nominal and current values."
			 ::= { gx2CEB 3 }

	       gx2CEBStatusEntry               OBJECT-TYPE
			 SYNTAX             Gx2CEBStatusEntry
			 ACCESS             not-accessible
			 STATUS             mandatory
			 DESCRIPTION
			 "This list contains Status parameters and descriptions."
			 INDEX { gx2CEBStatusTableIndex }
			 ::= { gx2CEBStatusTable  2}

--*************************************************************************
	       gx2CEBFactoryTable                    OBJECT-TYPE
			 SYNTAX             SEQUENCE OF Gx2CEBFactoryEntry
			 ACCESS             not-accessible
			 STATUS             mandatory
			 DESCRIPTION
			 "This table contains gx2CEB specific parameters with
			  nominal and current values."
			 ::= { gx2CEB 4 }

	       gx2CEBFactoryEntry               OBJECT-TYPE
			 SYNTAX             Gx2CEBFactoryEntry
			 ACCESS             not-accessible
			 STATUS             mandatory
			 DESCRIPTION
			 "This list contains Factory parameters and descriptions."
			 INDEX { gx2CEBFactoryTableIndex }
			 ::= { gx2CEBFactoryTable  3}
--*************************************************************************

	      Gx2CEBAnalogEntry    ::= SEQUENCE  
	       {
		gx2CEBAnalogTableIndex         INTEGER,
		
		--           Analog Parameters

		ceblabelModTemp					DisplayString (SIZE (0..80)),
		cebuomModTemp					DisplayString (SIZE (0..80)),
		cebmajorHighModTemp				Float, 
		cebmajorLowModTemp				Float, 
		cebminorHighModTemp				Float,
		cebminorLowModTemp				Float, 
		cebcurrentValueModTemp			Float, 
		cebstateFlagModTemp				INTEGER,
		cebminValueModTemp				Float,
		cebmaxValueModTemp 				Float,
		cebalarmStateModTemp			INTEGER,

		ceblabelFanCurrent				DisplayString (SIZE (0..80)),
		cebuomFanCurrent				DisplayString (SIZE (0..80)),
		cebmajorHighFanCurrent			Float, 
		cebmajorLowFanCurrent			Float, 
		cebminorHighFanCurrent			Float,
		cebminorLowFanCurrent			Float, 
		cebcurrentValueFanCurrent		Float, 
		cebstateFlagFanCurrent			INTEGER,
		cebminValueFanCurrent	 		Float,
		cebmaxValueFanCurrent	 		Float,
		cebalarmStateFanCurrent			INTEGER,

		ceblabelAnalogVoltage01	   		DisplayString (SIZE (0..80)),
		cebuomAnalogVoltage01	   		DisplayString (SIZE (0..80)),
		cebmajorHighAnalogVoltage01		Float, 
		cebmajorLowAnalogVoltage01 		Float, 
		cebminorHighAnalogVoltage01		Float,
		cebminorLowAnalogVoltage01 		Float, 
		cebcurrentValueAnalogVoltage01	Float, 
		cebstateFlagAnalogVoltage01	  	INTEGER,
		cebminValueAnalogVoltage01	  	Float,
		cebmaxValueAnalogVoltage01	  	Float,
		cebalarmStateAnalogVoltage01  	INTEGER,

		ceblabelAnalogVoltage02	   		DisplayString (SIZE (0..80)),
		cebuomAnalogVoltage02	   		DisplayString (SIZE (0..80)),
		cebmajorHighAnalogVoltage02		Float, 
		cebmajorLowAnalogVoltage02 		Float, 
		cebminorHighAnalogVoltage02		Float,
		cebminorLowAnalogVoltage02 		Float, 
		cebcurrentValueAnalogVoltage02	Float, 
		cebstateFlagAnalogVoltage02	  	INTEGER,
		cebminValueAnalogVoltage02	  	Float,
		cebmaxValueAnalogVoltage02	  	Float,
		cebalarmStateAnalogVoltage02  	INTEGER,

		ceblabelAnalogVoltage03	   		DisplayString (SIZE (0..80)),
		cebuomAnalogVoltage03	   		DisplayString (SIZE (0..80)),
		cebmajorHighAnalogVoltage03		Float, 
		cebmajorLowAnalogVoltage03 		Float, 
		cebminorHighAnalogVoltage03		Float,
		cebminorLowAnalogVoltage03 		Float, 
		cebcurrentValueAnalogVoltage03	Float, 
		cebstateFlagAnalogVoltage03	  	INTEGER,
		cebminValueAnalogVoltage03	  	Float,
		cebmaxValueAnalogVoltage03	  	Float,
		cebalarmStateAnalogVoltage03  	INTEGER,

		ceblabelAnalogVoltage04	   		DisplayString (SIZE (0..80)),
		cebuomAnalogVoltage04	   		DisplayString (SIZE (0..80)),
		cebmajorHighAnalogVoltage04		Float, 
		cebmajorLowAnalogVoltage04 		Float, 
		cebminorHighAnalogVoltage04		Float,
		cebminorLowAnalogVoltage04 		Float, 
		cebcurrentValueAnalogVoltage04	Float, 
		cebstateFlagAnalogVoltage04	  	INTEGER,
		cebminValueAnalogVoltage04	  	Float,
		cebmaxValueAnalogVoltage04	  	Float,
		cebalarmStateAnalogVoltage04  	INTEGER,

		ceblabelAnalogVoltage05	   		DisplayString (SIZE (0..80)),
		cebuomAnalogVoltage05	   		DisplayString (SIZE (0..80)),
		cebmajorHighAnalogVoltage05		Float, 
		cebmajorLowAnalogVoltage05 		Float, 
		cebminorHighAnalogVoltage05		Float,
		cebminorLowAnalogVoltage05 		Float, 
		cebcurrentValueAnalogVoltage05	Float, 
		cebstateFlagAnalogVoltage05	  	INTEGER,
		cebminValueAnalogVoltage05	  	Float,
		cebmaxValueAnalogVoltage05	  	Float,
		cebalarmStateAnalogVoltage05  	INTEGER

		}

		-- ****************  Digital Parameters ***********************

 		-- ****************  Status Parameters ************************************
	    Gx2CEBStatusEntry    ::= SEQUENCE  
	    {
		gx2CEBStatusTableIndex		INTEGER,

		ceblabelBoot					DisplayString (SIZE (0..80)),
		cebvalueBoot					INTEGER,
		cebstateflagBoot				INTEGER,
		
		ceblabelFlash					DisplayString (SIZE (0..80)),
		cebvalueFlash					INTEGER,
		cebstateflagFlash				INTEGER,

		ceblabelFactoryDataCRC 			DisplayString (SIZE (0..80)),
		cebvalueFactoryDataCRC			INTEGER,
		cebstateflagFactoryDataCRC		INTEGER,

		ceblabelAlarmDataCrc			DisplayString (SIZE (0..80)),
		cebvalueAlarmDataCrc			INTEGER,
		cebstateflagAlarmDataCrc		INTEGER 

		}


		-- ****************  Factory Parameters *************************************
	    Gx2CEBFactoryEntry    ::= SEQUENCE  
	    {
		gx2CEBFactoryTableIndex			INTEGER,
		cebbootControlByte  			INTEGER,
		cebbootStatusByte   			INTEGER,
		cebbank1CRC    					INTEGER,
		cebbank2CRC    					INTEGER,
		cebprgEEPROMByte    			INTEGER,
		cebfactoryCRC    				INTEGER,
		cebcalculateCRC    				INTEGER,
		cebhourMeter    				INTEGER,
		cebflashPrgCntA    				INTEGER,
		cebflashPrgCntB    				INTEGER,
		cebflashBankARev    			DisplayString (SIZE (0..80)),
		cebflashBankBRev    			DisplayString (SIZE (0..80))


		}
            -- ************** Analog Parameters ****************************
		gx2CEBAnalogTableIndex			OBJECT-TYPE
			   SYNTAX				INTEGER (1..4294967295)
			   ACCESS				read-only
			   STATUS				mandatory
			   DESCRIPTION			
			   "The value of this object identifies the network
			    element. This index is equal to the
			    hfcCommonTableIndex for the same element."
			   ::= { gx2CEBAnalogEntry 1}

-- New Parameter						 

		ceblabelModTemp           OBJECT-TYPE
			   SYNTAX           DisplayString (SIZE (0..80))
			   ACCESS           read-only
			   STATUS           optional
			   DESCRIPTION
			   "The value of this object provides the label of the
			    Module Temperature Analog parameter."
			   ::= { gx2CEBAnalogEntry 2}

		cebuomModTemp             OBJECT-TYPE
			   SYNTAX           DisplayString (SIZE (0..80))
			   ACCESS           read-only
			   STATUS           optional
			   DESCRIPTION
			   "The value of this object provides the Unit of Measure of the
			    Module Temperature Analog parameter."
			   ::= { gx2CEBAnalogEntry 3}

		cebmajorHighModTemp       OBJECT-TYPE
			   SYNTAX           Float 
			   ACCESS           read-only
			   STATUS           mandatory
			   DESCRIPTION
			   "The value of this object provides the Major High alarm value
			    of the Module Temperature Analog parameter.
			   This value is a floating point number that is represented as 
			   an IEEE 32 bit number. All F's indicate the parameter is unused"
			   ::= { gx2CEBAnalogEntry 4}


		cebmajorLowModTemp        OBJECT-TYPE
			   SYNTAX           Float 
			   ACCESS           read-only
			   STATUS           mandatory
			   DESCRIPTION
			   "The value of this object provides the Major Low alarm value
			    of the Module Temperature Analog parameter.
			   This value is a floating point number that is represented as 
			   an IEEE 32 bit number. All F's indicate the parameter is unused"
			   ::= { gx2CEBAnalogEntry 5}

		cebminorHighModTemp       OBJECT-TYPE
			   SYNTAX           Float
			   ACCESS           read-only
			   STATUS           mandatory
			   DESCRIPTION
			   "The value of this object provides the Minor High alarm value
			    of the Module Temperature Analog parameter.
			   This value is a floating point number that is represented as 
			   an IEEE 32 bit number. All F's indicate the parameter is unused"
			   ::= { gx2CEBAnalogEntry 6}

		cebminorLowModTemp        OBJECT-TYPE
			   SYNTAX           Float 
			   ACCESS           read-only
			   STATUS           mandatory
			   DESCRIPTION
			   "The value of this object provides the Minor Low alarm value
			    of the Module Temperature Analog parameter.
			   This value is a floating point number that is represented as 
			   an IEEE 32 bit number. All F's indicate the parameter is unused"
			   ::= { gx2CEBAnalogEntry 7}

		cebcurrentValueModTemp    OBJECT-TYPE
			   SYNTAX           Float 
			   ACCESS           read-only
			   STATUS           mandatory
			   DESCRIPTION
			   "The value of this object provides the Current value
			    of the Module Temperature Analog parameter.
			   This value is a floating point number that is represented as 
			   an IEEE 32 bit number."
			   ::= { gx2CEBAnalogEntry 8}

		cebstateFlagModTemp       OBJECT-TYPE
			   SYNTAX           INTEGER
								{
								hidden(1),
								read-only(2),
								updateable(3)
								}
			   ACCESS           read-only
			   STATUS           mandatory
			   DESCRIPTION
			   "The value of this object provides the state
			    of the Module Temperature Analog parameter. (0-Hidden	
			          1-Read-Only, 2-Updateable)."
			   ::= { gx2CEBAnalogEntry 9}

		cebminValueModTemp        OBJECT-TYPE
			   SYNTAX           Float
			   ACCESS           read-only
			   STATUS           mandatory
			   DESCRIPTION
			   "The value of this object provides the minimum value
			    the Module Temperature Analog parameter can achive.
			   This value is a floating point number that is represented as 
			   an IEEE 32 bit number."
			   ::= { gx2CEBAnalogEntry 10}

		cebmaxValueModTemp        OBJECT-TYPE
			   SYNTAX           Float
			   ACCESS           read-only
			   STATUS           mandatory
			   DESCRIPTION
			   "The value of this object provides the maximum value
			    the Module Temperature Analog parameter can achive.
			   This value is a floating point number that is represented as 
			   an IEEE 32 bit number."
			   ::= { gx2CEBAnalogEntry 11}

		cebalarmStateModTemp      OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Module Temperature Analog parameter."
			   ::= { gx2CEBAnalogEntry 12}

-- New Parameter

		ceblabelFanCurrent               OBJECT-TYPE
			   SYNTAX           DisplayString (SIZE (0..80))
			   ACCESS           read-only
			   STATUS           optional
			   DESCRIPTION
			   "The value of this object provides the label of the
			    Fan Current Analog parameter."
			   ::= { gx2CEBAnalogEntry 13}

		cebuomFanCurrent                 OBJECT-TYPE
			   SYNTAX           DisplayString (SIZE (0..80))
			   ACCESS           read-only
			   STATUS           optional
			   DESCRIPTION
			   "The value of this object provides the Unit of Measure of the
			    Fan Current Analog parameter."
			   ::= { gx2CEBAnalogEntry 14}

		cebmajorHighFanCurrent           OBJECT-TYPE
			   SYNTAX           Float 
			   ACCESS           read-only
			   STATUS           mandatory
			   DESCRIPTION
			   "The value of this object provides the Major High alarm value
			    of the Fan Current Analog parameter.
			   This value is a floating point number that is represented as 
			   an IEEE 32 bit number. All F's indicate the parameter is unused"
			   ::= { gx2CEBAnalogEntry 15}


		cebmajorLowFanCurrent            OBJECT-TYPE
			   SYNTAX           Float 
			   ACCESS           read-only
			   STATUS           mandatory
			   DESCRIPTION
			   "The value of this object provides the Major Low alarm value
			    of the Fan Current Analog parameter.
			   This value is a floating point number that is represented as 
			   an IEEE 32 bit number. All F's indicate the parameter is unused"
			   ::= { gx2CEBAnalogEntry 16}

		cebminorHighFanCurrent           OBJECT-TYPE
			   SYNTAX           Float
			   ACCESS           read-only
			   STATUS           obsolete
			   DESCRIPTION
			   "The value of this object provides the Minor High alarm value
			    of the Fan Current Analog parameter.
			   This value is a floating point number that is represented as 
			   an IEEE 32 bit number. All F's indicate the parameter is unused"
			   ::= { gx2CEBAnalogEntry 17}

		cebminorLowFanCurrent            OBJECT-TYPE
			   SYNTAX           Float 
			   ACCESS           read-only
			   STATUS           obsolete
			   DESCRIPTION
			   "The value of this object provides the Minor Low alarm value
			    of the Fan Current Analog parameter.
			   This value is a floating point number that is represented as 
			   an IEEE 32 bit number. All F's indicate the parameter is unused"
			   ::= { gx2CEBAnalogEntry 18}

		cebcurrentValueFanCurrent        OBJECT-TYPE
			   SYNTAX           Float 
			   ACCESS           read-only
			   STATUS           mandatory
			   DESCRIPTION
			   "The value of this object provides the Current value
			    of the Fan Current Analog parameter.
			   This value is a floating point number that is represented as 
			   an IEEE 32 bit number."
			   ::= { gx2CEBAnalogEntry 19}

		cebstateFlagFanCurrent           OBJECT-TYPE
			   SYNTAX           INTEGER
								{
								hidden(1),
								read-only(2),
								updateable(3)
								}
			   ACCESS           read-only
			   STATUS           mandatory
			   DESCRIPTION
			   "The value of this object provides the state
			    of the Fan Current Analog parameter. (0-Hidden	
			          1-Read-Only, 2-Updateable)."
			   ::= { gx2CEBAnalogEntry 20}

		cebminValueFanCurrent            OBJECT-TYPE
			   SYNTAX           Float
			   ACCESS           read-only
			   STATUS           mandatory
			   DESCRIPTION
			   "The value of this object provides the minimum value
			    the Fan Current Analog parameter can achive.
			   This value is a floating point number that is represented as 
			   an IEEE 32 bit number."
			   ::= { gx2CEBAnalogEntry 21}

		cebmaxValueFanCurrent            OBJECT-TYPE
			   SYNTAX           Float
			   ACCESS           read-only
			   STATUS           mandatory
			   DESCRIPTION
			   "The value of this object provides the maximum value
			    the Fan Current Analog parameter can achive.
			   This value is a floating point number that is represented as 
			   an IEEE 32 bit number."
			   ::= { gx2CEBAnalogEntry 22}

		cebalarmStateFanCurrent          OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Fan Current Analog parameter."
			   ::= { gx2CEBAnalogEntry 23 }

-- New Parameter

		ceblabelAnalogVoltage01		OBJECT-TYPE
			   SYNTAX           DisplayString (SIZE (0..80))
			   ACCESS           read-only
			   STATUS           optional
			   DESCRIPTION
			   "The value of this object provides the label of the
			    Analog Voltage number 01 Analog parameter."
			   ::= { gx2CEBAnalogEntry 24}

		cebuomAnalogVoltage01                OBJECT-TYPE
			   SYNTAX           DisplayString (SIZE (0..80))
			   ACCESS           read-only
			   STATUS           optional
			   DESCRIPTION
			   "The value of this object provides the Unit of Measure of the
			    Analog Voltage number 01 Analog parameter."
			   ::= { gx2CEBAnalogEntry 25}

		cebmajorHighAnalogVoltage01          OBJECT-TYPE
			   SYNTAX           Float 
			   ACCESS           read-only
			   STATUS           mandatory
			   DESCRIPTION
			   "The value of this object provides the Major High alarm value
			    Analog Voltage number 01 Analog parameter.
			   This value is a floating point number that is represented as 
			   an IEEE 32 bit number. All F's indicate the parameter is unused"
			   ::= { gx2CEBAnalogEntry 26}


		cebmajorLowAnalogVoltage01           OBJECT-TYPE
			   SYNTAX           Float 
			   ACCESS           read-only
			   STATUS           mandatory
			   DESCRIPTION
			   "The value of this object provides the Major Low alarm value
			    Analog Voltage number 01 Analog parameter.
			   This value is a floating point number that is represented as 
			   an IEEE 32 bit number. All F's indicate the parameter is unused"
			   ::= { gx2CEBAnalogEntry 27}

		cebminorHighAnalogVoltage01          OBJECT-TYPE
			   SYNTAX           Float
			   ACCESS           read-only
			   STATUS           mandatory
			   DESCRIPTION
			   "The value of this object provides the Minor High alarm value
			    Analog Voltage number 01 Analog parameter.
			   This value is a floating point number that is represented as 
			   an IEEE 32 bit number. All F's indicate the parameter is unused"
			   ::= { gx2CEBAnalogEntry 28}

		cebminorLowAnalogVoltage01           OBJECT-TYPE
			   SYNTAX           Float 
			   ACCESS           read-only
			   STATUS           mandatory
			   DESCRIPTION
			   "The value of this object provides the Minor Low alarm value
			    Analog Voltage number 01 Analog parameter.
			   This value is a floating point number that is represented as 
			   an IEEE 32 bit number. All F's indicate the parameter is unused"
			   ::= { gx2CEBAnalogEntry 29}

		cebcurrentValueAnalogVoltage01       OBJECT-TYPE
			   SYNTAX           Float 
			   ACCESS           read-only
			   STATUS           mandatory
			   DESCRIPTION
			   "The value of this object provides the Current value
			    Analog Voltage number 01 Analog parameter.
			   This value is a floating point number that is represented as an IEEE 32 bit number."
			   ::= { gx2CEBAnalogEntry 30}

		cebstateFlagAnalogVoltage01          OBJECT-TYPE
			   SYNTAX           INTEGER
								{
								hidden(1),
								read-only(2),
								updateable(3)
								}
			   ACCESS           read-only
			   STATUS           mandatory
			   DESCRIPTION
			   "The value of this object provides the state of the
			    Analog Voltage number 01 Analog parameter.
			    (0-Hidden 1-Read-Only, 2-Updateable)."
			   ::= { gx2CEBAnalogEntry 31}

		cebminValueAnalogVoltage01           OBJECT-TYPE
			   SYNTAX           Float
			   ACCESS           read-only
			   STATUS           mandatory
			   DESCRIPTION
			   "The value of this object provides the minimum value
			    the Analog Voltage number 01 Analog parameter can achive.
			   This value is a floating point number that is represented as an IEEE 32 bit number."
			   ::= { gx2CEBAnalogEntry 32}

		cebmaxValueAnalogVoltage01           OBJECT-TYPE
			   SYNTAX           Float
			   ACCESS           read-only
			   STATUS           mandatory
			   DESCRIPTION
			   "The value of this object provides the maximum value
			    the Analog Voltage number 01 Analog parameter can achive.
			   This value is a floating point number that is represented as an IEEE 32 bit number."
			   ::= { gx2CEBAnalogEntry 33}

		cebalarmStateAnalogVoltage01         OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Analog Voltage number 01 Analog parameter."
			   ::= { gx2CEBAnalogEntry 34}
			   
-- New Parameter

		ceblabelAnalogVoltage02		OBJECT-TYPE
			   SYNTAX           DisplayString (SIZE (0..80))
			   ACCESS           read-only
			   STATUS           optional
			   DESCRIPTION
			   "The value of this object provides the label of the
			    Analog Voltage number 02 Analog parameter."
			   ::= { gx2CEBAnalogEntry 35}
										
		cebuomAnalogVoltage02                OBJECT-TYPE
			   SYNTAX           DisplayString (SIZE (0..80))
			   ACCESS           read-only
			   STATUS           optional
			   DESCRIPTION
			   "The value of this object provides the Unit of Measure of the
			    Analog Voltage number 02 Analog parameter."
			   ::= { gx2CEBAnalogEntry 36}

		cebmajorHighAnalogVoltage02          OBJECT-TYPE
			   SYNTAX           Float 
			   ACCESS           read-only
			   STATUS           mandatory
			   DESCRIPTION
			   "The value of this object provides the Major High alarm value
			    Analog Voltage number 02 Analog parameter.
			   This value is a floating point number that is represented as 
			   an IEEE 32 bit number. All F's indicate the parameter is unused"
			   ::= { gx2CEBAnalogEntry 37}


		cebmajorLowAnalogVoltage02           OBJECT-TYPE
			   SYNTAX           Float 
			   ACCESS           read-only
			   STATUS           mandatory
			   DESCRIPTION
			   "The value of this object provides the Major Low alarm value
			    Analog Voltage number 02 Analog parameter.
			   This value is a floating point number that is represented as 
			   an IEEE 32 bit number. All F's indicate the parameter is unused"
			   ::= { gx2CEBAnalogEntry 38}

		cebminorHighAnalogVoltage02          OBJECT-TYPE
			   SYNTAX           Float
			   ACCESS           read-only
			   STATUS           mandatory
			   DESCRIPTION
			   "The value of this object provides the Minor High alarm value
			    Analog Voltage number 02 Analog parameter.
			   This value is a floating point number that is represented as 
			   an IEEE 32 bit number. All F's indicate the parameter is unused"
			   ::= { gx2CEBAnalogEntry 39}

		cebminorLowAnalogVoltage02           OBJECT-TYPE
			   SYNTAX           Float 
			   ACCESS           read-only
			   STATUS           mandatory
			   DESCRIPTION
			   "The value of this object provides the Minor Low alarm value
			    Analog Voltage number 02 Analog parameter.
			   This value is a floating point number that is represented as 
			   an IEEE 32 bit number. All F's indicate the parameter is unused"
			   ::= { gx2CEBAnalogEntry 40}

		cebcurrentValueAnalogVoltage02       OBJECT-TYPE
			   SYNTAX           Float 
			   ACCESS           read-only
			   STATUS           mandatory
			   DESCRIPTION
			   "The value of this object provides the Current value
			    Analog Voltage number 02 Analog parameter.
			   This value is a floating point number that is represented as an IEEE 32 bit number."
			   ::= { gx2CEBAnalogEntry 41}

		cebstateFlagAnalogVoltage02          OBJECT-TYPE
			   SYNTAX           INTEGER
								{
								hidden(1),
								read-only(2),
								updateable(3)
								}
			   ACCESS           read-only
			   STATUS           mandatory
			   DESCRIPTION
			   "The value of this object provides the state of the
			    Analog Voltage number 02 Analog parameter.
			    (0-Hidden 1-Read-Only, 2-Updateable)."
			   ::= { gx2CEBAnalogEntry 42}

		cebminValueAnalogVoltage02           OBJECT-TYPE
			   SYNTAX           Float
			   ACCESS           read-only
			   STATUS           mandatory
			   DESCRIPTION
			   "The value of this object provides the minimum value
			    the Analog Voltage number 02 Analog parameter can achive.
			   This value is a floating point number that is represented as an IEEE 32 bit number."
			   ::= { gx2CEBAnalogEntry 43}

		cebmaxValueAnalogVoltage02           OBJECT-TYPE
			   SYNTAX           Float
			   ACCESS           read-only
			   STATUS           mandatory
			   DESCRIPTION
			   "The value of this object provides the maximum value
			    the Analog Voltage number 02 Analog parameter can achive.
			   This value is a floating point number that is represented as an IEEE 32 bit number."
			   ::= { gx2CEBAnalogEntry 44}

		cebalarmStateAnalogVoltage02         OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Analog Voltage number 02 Analog parameter."
			   ::= { gx2CEBAnalogEntry 45}
			   
-- New Parameter

		ceblabelAnalogVoltage03		OBJECT-TYPE
			   SYNTAX           DisplayString (SIZE (0..80))
			   ACCESS           read-only
			   STATUS           optional
			   DESCRIPTION
			   "The value of this object provides the label of the
			    Analog Voltage number 03 Analog parameter."
			   ::= { gx2CEBAnalogEntry 46}

		cebuomAnalogVoltage03                OBJECT-TYPE
			   SYNTAX           DisplayString (SIZE (0..80))
			   ACCESS           read-only
			   STATUS           optional
			   DESCRIPTION
			   "The value of this object provides the Unit of Measure of the
			    Analog Voltage number 03 Analog parameter."
			   ::= { gx2CEBAnalogEntry 47}

		cebmajorHighAnalogVoltage03          OBJECT-TYPE
			   SYNTAX           Float 
			   ACCESS           read-only
			   STATUS           mandatory
			   DESCRIPTION
			   "The value of this object provides the Major High alarm value
			    Analog Voltage number 03 Analog parameter.
			   This value is a floating point number that is represented as 
			   an IEEE 32 bit number. All F's indicate the parameter is unused"
			   ::= { gx2CEBAnalogEntry 48}


		cebmajorLowAnalogVoltage03           OBJECT-TYPE
			   SYNTAX           Float 
			   ACCESS           read-only
			   STATUS           mandatory
			   DESCRIPTION
			   "The value of this object provides the Major Low alarm value
			    Analog Voltage number 03 Analog parameter.
			   This value is a floating point number that is represented as 
			   an IEEE 32 bit number. All F's indicate the parameter is unused"
			   ::= { gx2CEBAnalogEntry 49}

		cebminorHighAnalogVoltage03          OBJECT-TYPE
			   SYNTAX           Float
			   ACCESS           read-only
			   STATUS           mandatory
			   DESCRIPTION
			   "The value of this object provides the Minor High alarm value
			    Analog Voltage number 03 Analog parameter.
			   This value is a floating point number that is represented as 
			   an IEEE 32 bit number. All F's indicate the parameter is unused"
			   ::= { gx2CEBAnalogEntry 50}

		cebminorLowAnalogVoltage03           OBJECT-TYPE
			   SYNTAX           Float 
			   ACCESS           read-only
			   STATUS           mandatory
			   DESCRIPTION
			   "The value of this object provides the Minor Low alarm value
			    Analog Voltage number 03 Analog parameter.
			   This value is a floating point number that is represented as 
			   an IEEE 32 bit number. All F's indicate the parameter is unused"
			   ::= { gx2CEBAnalogEntry 51}

		cebcurrentValueAnalogVoltage03       OBJECT-TYPE
			   SYNTAX           Float 
			   ACCESS           read-only
			   STATUS           mandatory
			   DESCRIPTION
			   "The value of this object provides the Current value
			    Analog Voltage number 03 Analog parameter.
			   This value is a floating point number that is represented as an IEEE 32 bit number."
			   ::= { gx2CEBAnalogEntry 52}

		cebstateFlagAnalogVoltage03          OBJECT-TYPE
			   SYNTAX           INTEGER
								{
								hidden(1),
								read-only(2),
								updateable(3)
								}
			   ACCESS           read-only
			   STATUS           mandatory
			   DESCRIPTION
			   "The value of this object provides the state of the
			    Analog Voltage number 03 Analog parameter.
			    (0-Hidden 1-Read-Only, 2-Updateable)."
			   ::= { gx2CEBAnalogEntry 53}

		cebminValueAnalogVoltage03           OBJECT-TYPE
			   SYNTAX           Float
			   ACCESS           read-only
			   STATUS           mandatory
			   DESCRIPTION
			   "The value of this object provides the minimum value
			    the Analog Voltage number 03 Analog parameter can achive.
			   This value is a floating point number that is represented as an IEEE 32 bit number."
			   ::= { gx2CEBAnalogEntry 54}

		cebmaxValueAnalogVoltage03           OBJECT-TYPE
			   SYNTAX           Float
			   ACCESS           read-only
			   STATUS           mandatory
			   DESCRIPTION
			   "The value of this object provides the maximum value
			    the Analog Voltage number 03 Analog parameter can achive.
			   This value is a floating point number that is represented as an IEEE 32 bit number."
			   ::= { gx2CEBAnalogEntry 55}

		cebalarmStateAnalogVoltage03         OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Analog Voltage number 03 Analog parameter."
			   ::= { gx2CEBAnalogEntry 56}
			   
-- New Parameter

		ceblabelAnalogVoltage04		OBJECT-TYPE
			   SYNTAX           DisplayString (SIZE (0..80))
			   ACCESS           read-only
			   STATUS           optional
			   DESCRIPTION
			   "The value of this object provides the label of the
			    Analog Voltage number 04 Analog parameter."
			   ::= { gx2CEBAnalogEntry 57}

		cebuomAnalogVoltage04                OBJECT-TYPE
			   SYNTAX           DisplayString (SIZE (0..80))
			   ACCESS           read-only
			   STATUS           optional
			   DESCRIPTION
			   "The value of this object provides the Unit of Measure of the
			    Analog Voltage number 04 Analog parameter."
			   ::= { gx2CEBAnalogEntry 58}

		cebmajorHighAnalogVoltage04          OBJECT-TYPE
			   SYNTAX           Float 
			   ACCESS           read-only
			   STATUS           mandatory
			   DESCRIPTION
			   "The value of this object provides the Major High alarm value
			    Analog Voltage number 04 Analog parameter.
			   This value is a floating point number that is represented as 
			   an IEEE 32 bit number. All F's indicate the parameter is unused"
			   ::= { gx2CEBAnalogEntry 59}


		cebmajorLowAnalogVoltage04           OBJECT-TYPE
			   SYNTAX           Float 
			   ACCESS           read-only
			   STATUS           mandatory
			   DESCRIPTION
			   "The value of this object provides the Major Low alarm value
			    Analog Voltage number 04 Analog parameter.
			   This value is a floating point number that is represented as 
			   an IEEE 32 bit number. All F's indicate the parameter is unused"
			   ::= { gx2CEBAnalogEntry 60}

		cebminorHighAnalogVoltage04          OBJECT-TYPE
			   SYNTAX           Float
			   ACCESS           read-only
			   STATUS           mandatory
			   DESCRIPTION
			   "The value of this object provides the Minor High alarm value
			    Analog Voltage number 04 Analog parameter.
			   This value is a floating point number that is represented as 
			   an IEEE 32 bit number. All F's indicate the parameter is unused"
			   ::= { gx2CEBAnalogEntry 61}

		cebminorLowAnalogVoltage04           OBJECT-TYPE
			   SYNTAX           Float 
			   ACCESS           read-only
			   STATUS           mandatory
			   DESCRIPTION
			   "The value of this object provides the Minor Low alarm value
			    Analog Voltage number 04 Analog parameter.
			   This value is a floating point number that is represented as 
			   an IEEE 32 bit number. All F's indicate the parameter is unused"
			   ::= { gx2CEBAnalogEntry 62}

		cebcurrentValueAnalogVoltage04       OBJECT-TYPE
			   SYNTAX           Float 
			   ACCESS           read-only
			   STATUS           mandatory
			   DESCRIPTION
			   "The value of this object provides the Current value
			    Analog Voltage number 04 Analog parameter.
			   This value is a floating point number that is represented as an IEEE 32 bit number."
			   ::= { gx2CEBAnalogEntry 63}

		cebstateFlagAnalogVoltage04          OBJECT-TYPE
			   SYNTAX           INTEGER
								{
								hidden(1),
								read-only(2),
								updateable(3)
								}
			   ACCESS           read-only
			   STATUS           mandatory
			   DESCRIPTION
			   "The value of this object provides the state of the
			    Analog Voltage number 04 Analog parameter.
			    (0-Hidden 1-Read-Only, 2-Updateable)."
			   ::= { gx2CEBAnalogEntry 64}

		cebminValueAnalogVoltage04           OBJECT-TYPE
			   SYNTAX           Float
			   ACCESS           read-only
			   STATUS           mandatory
			   DESCRIPTION
			   "The value of this object provides the minimum value
			    the Analog Voltage number 04 Analog parameter can achive.
			   This value is a floating point number that is represented as an IEEE 32 bit number."
			   ::= { gx2CEBAnalogEntry 65}

		cebmaxValueAnalogVoltage04           OBJECT-TYPE
			   SYNTAX           Float
			   ACCESS           read-only
			   STATUS           mandatory
			   DESCRIPTION
			   "The value of this object provides the maximum value
			    the Analog Voltage number 04 Analog parameter can achive.
			   This value is a floating point number that is represented as an IEEE 32 bit number."
			   ::= { gx2CEBAnalogEntry 66}

		cebalarmStateAnalogVoltage04         OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Analog Voltage number 04 Analog parameter."
			   ::= { gx2CEBAnalogEntry 67}
			   
-- New Parameter

		ceblabelAnalogVoltage05		OBJECT-TYPE
			   SYNTAX           DisplayString (SIZE (0..80))
			   ACCESS           read-only
			   STATUS           optional
			   DESCRIPTION
			   "The value of this object provides the label of the
			    Analog Voltage number 05 Analog parameter."
			   ::= { gx2CEBAnalogEntry 68}

		cebuomAnalogVoltage05                OBJECT-TYPE
			   SYNTAX           DisplayString (SIZE (0..80))
			   ACCESS           read-only
			   STATUS           optional
			   DESCRIPTION
			   "The value of this object provides the Unit of Measure of the
			    Analog Voltage number 05 Analog parameter."
			   ::= { gx2CEBAnalogEntry 69}

		cebmajorHighAnalogVoltage05          OBJECT-TYPE
			   SYNTAX           Float 
			   ACCESS           read-only
			   STATUS           mandatory
			   DESCRIPTION
			   "The value of this object provides the Major High alarm value
			    Analog Voltage number 05 Analog parameter.
			   This value is a floating point number that is represented as 
			   an IEEE 32 bit number. All F's indicate the parameter is unused"
			   ::= { gx2CEBAnalogEntry 70}


		cebmajorLowAnalogVoltage05           OBJECT-TYPE
			   SYNTAX           Float 
			   ACCESS           read-only
			   STATUS           mandatory
			   DESCRIPTION
			   "The value of this object provides the Major Low alarm value
			    Analog Voltage number 05 Analog parameter.
			   This value is a floating point number that is represented as 
			   an IEEE 32 bit number. All F's indicate the parameter is unused"
			   ::= { gx2CEBAnalogEntry 71}

		cebminorHighAnalogVoltage05          OBJECT-TYPE
			   SYNTAX           Float
			   ACCESS           read-only
			   STATUS           mandatory
			   DESCRIPTION
			   "The value of this object provides the Minor High alarm value
			    Analog Voltage number 05 Analog parameter.
			   This value is a floating point number that is represented as 
			   an IEEE 32 bit number. All F's indicate the parameter is unused"
			   ::= { gx2CEBAnalogEntry 72}

		cebminorLowAnalogVoltage05           OBJECT-TYPE
			   SYNTAX           Float 
			   ACCESS           read-only
			   STATUS           mandatory
			   DESCRIPTION
			   "The value of this object provides the Minor Low alarm value
			    Analog Voltage number 05 Analog parameter.
			   This value is a floating point number that is represented as 
			   an IEEE 32 bit number. All F's indicate the parameter is unused"
			   ::= { gx2CEBAnalogEntry 73}

		cebcurrentValueAnalogVoltage05       OBJECT-TYPE
			   SYNTAX           Float 
			   ACCESS           read-only
			   STATUS           mandatory
			   DESCRIPTION
			   "The value of this object provides the Current value
			    Analog Voltage number 05 Analog parameter.
			   This value is a floating point number that is represented as an IEEE 32 bit number."
			   ::= { gx2CEBAnalogEntry 74}

		cebstateFlagAnalogVoltage05          OBJECT-TYPE
			   SYNTAX           INTEGER
								{
								hidden(1),
								read-only(2),
								updateable(3)
								}
			   ACCESS           read-only
			   STATUS           mandatory
			   DESCRIPTION
			   "The value of this object provides the state of the
			    Analog Voltage number 05 Analog parameter.
			    (0-Hidden 1-Read-Only, 2-Updateable)."
			   ::= { gx2CEBAnalogEntry 75}

		cebminValueAnalogVoltage05           OBJECT-TYPE
			   SYNTAX           Float
			   ACCESS           read-only
			   STATUS           mandatory
			   DESCRIPTION
			   "The value of this object provides the minimum value
			    the Analog Voltage number 05 Analog parameter can achive.
			   This value is a floating point number that is represented as an IEEE 32 bit number."
			   ::= { gx2CEBAnalogEntry 76}

		cebmaxValueAnalogVoltage05           OBJECT-TYPE
			   SYNTAX           Float
			   ACCESS           read-only
			   STATUS           mandatory
			   DESCRIPTION
			   "The value of this object provides the maximum value
			    the Analog Voltage number 05 Analog parameter can achive.
			   This value is a floating point number that is represented as an IEEE 32 bit number."
			   ::= { gx2CEBAnalogEntry 77}

		cebalarmStateAnalogVoltage05         OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Analog Voltage number 01 Analog parameter."
			   ::= { gx2CEBAnalogEntry 78}
			   
			   
-- ************************ Digital parameters **********************************
-- ************************ STATUS parameters ***********************************

		gx2CEBStatusTableIndex			OBJECT-TYPE
			   SYNTAX				INTEGER (1..4294967295)
			   ACCESS				read-only
			   STATUS				mandatory
			   DESCRIPTION			
			   "The value of this object identifies the network
			    element. This index is equal to the
			    hfcCommonTableIndex for the same element."
			   ::= { gx2CEBStatusEntry 1}

--New Parameter
		ceblabelBoot               	OBJECT-TYPE
			   SYNTAX       		DisplayString (SIZE (0..80))         
			   ACCESS           	read-only
			   STATUS           	optional
			   DESCRIPTION
			   "The value of this object provides the label of the
			    Boot Status  Status parameter."
			   ::= { gx2CEBStatusEntry 2}

		cebvalueBoot              		OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (0-Ok, 1-Undetermined
			    2-Warning, 3-Minor, 4-Major, 5-Critical)."
			   ::= { gx2CEBStatusEntry 3}

		cebstateflagBoot     	OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2CEBStatusEntry  4}



--New Parameter
		ceblabelFlash               	OBJECT-TYPE
			   SYNTAX       		DisplayString (SIZE (0..80))         
			   ACCESS           	read-only
			   STATUS           	optional
			   DESCRIPTION
			   "The value of this object provides the label of the
			    Flash Status  Status parameter."
			   ::= { gx2CEBStatusEntry 5}

		cebvalueFlash              	OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (0-Ok, 1-Undetermined
			    2-Warning, 3-Minor, 4-Major, 5-Critical)."
			   ::= { gx2CEBStatusEntry 6}

		cebstateflagFlash     	OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2CEBStatusEntry  7}

--New Parameter
		ceblabelFactoryDataCRC           OBJECT-TYPE
			   SYNTAX       		DisplayString (SIZE (0..80))         
			   ACCESS           	read-only
			   STATUS           	optional
			   DESCRIPTION
			   "The value of this object provides the label of the
			    Factory Data CRC Status parameter."
			   ::= { gx2CEBStatusEntry 8}

		cebvalueFactoryDataCRC          	OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (0-Ok, 1-Undetermined
			    2-Warning, 3-Minor, 4-Major, 5-Critical)."
			   ::= { gx2CEBStatusEntry 9}

		cebstateflagFactoryDataCRC     	OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2CEBStatusEntry  10}


--New Parameter
		ceblabelAlarmDataCrc               	      OBJECT-TYPE
			   SYNTAX       		DisplayString (SIZE (0..80))         
			   ACCESS           	read-only
			   STATUS           	optional
			   DESCRIPTION
			   "The value of this object provides the label of the
			    Alarm Data Crc parameter."
			   ::= { gx2CEBStatusEntry 11}

		cebvalueAlarmDataCrc              		OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (0-Ok, 1-Undetermined
			    2-Warning, 3-Minor, 4-Major, 5-Critical)."
			   ::= { gx2CEBStatusEntry 12}

		cebstateflagAlarmDataCrc     	OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2CEBStatusEntry  13}

 
			   
            -- ************ FACTORY DATA ****************
		gx2CEBFactoryTableIndex			OBJECT-TYPE
			   SYNTAX				INTEGER (1..4294967295)
			   ACCESS				read-only
			   STATUS				mandatory
			   DESCRIPTION			
			   "The value of this object identifies the network
			    element. This index is equal to the
			    hfcCommonTableIndex for the same element."
			   ::= { gx2CEBFactoryEntry 1}

		cebbootControlByte          	OBJECT-TYPE
			   SYNTAX       		INTEGER
			   ACCESS           	read-only
			   STATUS           	mandatory
			   DESCRIPTION
			   "The value of this object indicates which bank the firmware
			    is currently being boot from."
			   ::= { gx2CEBFactoryEntry 2}

		cebbootStatusByte          	OBJECT-TYPE
			   SYNTAX       		INTEGER
			   ACCESS           	read-only
			   STATUS           	mandatory
			   DESCRIPTION
			   "This object indicates the status of the last boot.  Bit 2 = 
			   Bank 0/1 Active (0 = Bank 0, 1 = Bank 1), Bit 1 = Bank 1 Fail 
			   and Bit 0 = Bank 0 Fail (0 = Pass, 1 = Fail)"
			   ::= { gx2CEBFactoryEntry 3}

		cebbank1CRC          		OBJECT-TYPE
			   SYNTAX       		INTEGER
			   ACCESS           	read-only
			   STATUS           	mandatory
			   DESCRIPTION
			   "This object provides the CRC code of bank 0.  The display 
			   formate for the data is Hex."
			   ::= { gx2CEBFactoryEntry 4}

		cebbank2CRC          		OBJECT-TYPE
			   SYNTAX       		INTEGER
			   ACCESS           	read-only
			   STATUS           	mandatory
			   DESCRIPTION
			   "This object provides the CRC code of bank 1.The display 
			   formate for the data is Hex."
			   ::= { gx2CEBFactoryEntry 5}

		cebprgEEPROMByte          		OBJECT-TYPE
			   SYNTAX       		INTEGER
			   ACCESS           	read-only
			   STATUS           	mandatory
			   DESCRIPTION
			   "This object indicates if the EEPROM has been programmed"
			   ::= { gx2CEBFactoryEntry 6}

		cebfactoryCRC          		OBJECT-TYPE
			   SYNTAX       		INTEGER
			   ACCESS           	read-only
			   STATUS           	mandatory
			   DESCRIPTION
			   "This object provides the CRC code for the Factory data."
			   ::= { gx2CEBFactoryEntry 7}

		cebcalculateCRC          		OBJECT-TYPE
			   SYNTAX       		INTEGER
					    		{
							factory(1),
							na(2),
							alarm(3)
					    		}
			   ACCESS           	read-only
			   STATUS           	obsolete
			   DESCRIPTION
			   "This object indicates which of the Enums will have the CRC 
			   calculated."
			   ::= { gx2CEBFactoryEntry 8}

		cebhourMeter          		OBJECT-TYPE
			   SYNTAX       		INTEGER
			   ACCESS           	read-only
			   STATUS           	mandatory
			   DESCRIPTION
			   "This object provides the hour meter reading of the module."
			   ::= { gx2CEBFactoryEntry 9}

		cebflashPrgCntA          		OBJECT-TYPE
			   SYNTAX       		INTEGER
			   ACCESS           	read-only
			   STATUS           	mandatory
			   DESCRIPTION
			   "This object provides the number of times Bank 1 flash has been 
                      programmed."
			   ::= { gx2CEBFactoryEntry 10}

		cebflashPrgCntB          		OBJECT-TYPE
			   SYNTAX       		INTEGER
			   ACCESS           	read-only
			   STATUS           	mandatory
			   DESCRIPTION
			   "This object provides the number of times Bank 1 flash has been 
                      programmed."
			   ::= { gx2CEBFactoryEntry 11}

		cebflashBankARev          		OBJECT-TYPE
			   SYNTAX       		DisplayString (SIZE (0..80))
			   ACCESS           	read-only
			   STATUS           	mandatory
			   DESCRIPTION
			   "This object provides the revision of flash bank 0.  The rev is
			   2 characters."
			   ::= { gx2CEBFactoryEntry 12}

		cebflashBankBRev          		OBJECT-TYPE
			   SYNTAX       		DisplayString (SIZE (0..80))
			   ACCESS           	read-only
			   STATUS           	mandatory
			   DESCRIPTION
			   "This object provides the revision of flash bank 1.  The rev is
			   2 characters."
			   ::= { gx2CEBFactoryEntry 13}



-- ****************************************************************
--
-- TRAP DEFINITIONS
--
--
-- Every trap generated by an HFC agents will include first 9 identical
-- fields. If particular variable is not supported in
-- particular TRAP-TYPE then default value will be returned.
--
-- DESCRIPTION will include explanation of use of generic
-- variables (trapAdditionalInfo******.)  If no
-- DESCRIPTION is given then generic variables will contain
-- default values.
--
-- *****************************************************************

--***************************************************************************
-- ***********!!! THE TRAP SECTION HAS NOT BEEN COMPLETED YET !!! ***********
--***************************************************************************

-- **************************************************************************
--                        CEB Module traps
-- **************************************************************************
   trapCEBConfigChangeInteger TRAP-TYPE
       ENTERPRISE gx2CEB
       VARIABLES
	       {       
		trapIdentifier,
		trapNetworkElemModelNumber,
		trapNetworkElemSerialNum,
		trapPerceivedSeverity,
		trapNetworkElemOperState,
		trapNetworkElemAlarmStatus,  
		trapNetworkElemAdminState,
		trapNetworkElemAvailStatus,
		trapText,
		trapChangedObjectId,
		trapChangedValueInteger,
		trapNETrapLastTrapTimeStamp
	       }
       DESCRIPTION
	"This trap is issued if configuration of a single variable
	 with integer type was changed (via ANY interface).  
	 TrapChangedValueInteger variable may contain current reading
	 of that variable.
	 trapPerceivedSeverity - 'indeterminate'"
  ::= 1

   trapCEBConfigChangeDisplayString TRAP-TYPE
       ENTERPRISE gx2CEB
       VARIABLES
	       {       
		trapIdentifier,
		trapNetworkElemModelNumber,
		trapNetworkElemSerialNum,
		trapPerceivedSeverity,
		trapNetworkElemOperState,
		trapNetworkElemAlarmStatus,  
		trapNetworkElemAdminState,
		trapNetworkElemAvailStatus,
		trapText,
		trapChangedObjectId,
		trapChangedValueDisplayString,
		trapNETrapLastTrapTimeStamp
	       }
       DESCRIPTION
	"This trap is issued if configuration of a single variable
	 with DispalayString type was changed (via ANY interface).  
	 TrapChangedValueDisplayString variable may contain current reading
	 of that variable.
	 trapPerceivedSeverity - 'indeterminate'"
  ::= 2

  trapCEBfanCurrentAlarm TRAP-TYPE
	ENTERPRISE gx2CEB
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Fan Current 
	 parameter goes out of range.
	 trapAdditionalInfoInteger variable contains current reading of 
	 the this parameter."
  ::= 3

  trapCEBModuleTempAlarm TRAP-TYPE
	ENTERPRISE gx2CEB
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Module Temperature parameter goes out of range.
	 trapAdditionalInfoInteger variable contains current reading of 
	 the this parameter."
  ::= 4


  trapCEBFlashAlarm TRAP-TYPE
	ENTERPRISE gx2CEB
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Laser Modules detects an error during
	Flash memory operations."
  ::= 5

  trapCEBBankBootAlarm TRAP-TYPE
	ENTERPRISE gx2CEB
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Laser Modules detects an error while booting
	from bank 0 or bank 1."
  ::= 6

	trapCEBAlarmDataCRCAlarm TRAP-TYPE
	ENTERPRISE gx2CEB
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Alarm Data CRC is incorrect."
  ::= 7

	trapCEBFactoryDataCRCAlarm TRAP-TYPE
	ENTERPRISE gx2CEB
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Factory Data CRC is incorrect."
  ::= 8

  END
