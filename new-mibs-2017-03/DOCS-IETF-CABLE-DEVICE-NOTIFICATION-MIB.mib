DOCS-IETF-CABLE-DEVICE-NOTIFICATION-MIB DEFINITIONS ::= BEGIN

  IMPORTS
        MODULE-IDENTITY,
        OBJECT-TYPE,
        NOTIFICATION-TYPE,
        mib-2
              FROM SNMPv2-SMI -- RFC 2578
        MODULE-COMPLIANCE,



        OBJECT-GROUP,
        NOTIFICATION-GROUP
              FROM SNMPv2-CONF -- RFC 2580

        docsDevEvLevel,
        docsDevEvId,
        docsDevEvText
              FROM DOCS-CABLE-DEVICE-MIB -- RFC 2669

        docsIfCmtsCmStatusMacAddress,
        docsIfDocsisBaseCapability,
        docsIfCmtsCmStatusDocsisRegMode,
        docsIfCmtsCmStatusModulationType
              FROM DOCS-IF-MIB -- RFC 4546

        ifPhysAddress
              FROM IF-MIB;  -- RFC 2863

  docsDevNotifMIB MODULE-IDENTITY

        LAST-UPDATED    "201505120000Z"  -- May 12, 2015
        ORGANIZATION    "IETF IP over Cable Data Network
                         Working Group"

        CONTACT-INFO
            "        Azlina Ahmad
             Postal: Cisco Systems, Inc.
                     170 West Tasman Drive
                     San Jose, CA 95134, U.S.A.
             Phone:   408 853 7927
             E-mail: azlina@cisco.com

                     Greg Nakanishi
             Postal: Motorola
                     6450 Sequence Drive
                     San Diego, CA 92121, U.S.A.
             Phone:   858 404 2366
             E-mail: gnakanishi@motorola.com

             IETF IPCDN Working Group
             General Discussion: ipcdn@ietf.org



             Subscribe: http://www.ietf.org/mailman/listinfo/ipcdn
             Archive: ftp://ftp.ietf.org/ietf-mail-archive/ipcdn
             Co-chairs: Richard Woundy,
                          richard_woundy@cable.comcast.com
                        Jean-Francois Mule, jf.mule@cablelabs.com"

        DESCRIPTION
            "The Event Notification MIB is an extension of the
            CABLE DEVICE MIB.  It defines various notification
            objects for both cable modem and cable modem termination
            systems.  Two groups of SNMP notification objects are
            defined.  One group is for notifying cable modem events,
            and one group is for notifying cable modem termination
            system events.

            DOCSIS defines numerous events, and each event is
            assigned to a functional category.  This MIB defines
            a notification object for each functional category.
            The varbinding list of each notification includes
            information about the event that occurred on the
            device.

            Copyright (C) The Internet Society (2006).  This version
            of this MIB module is part of RFC 4547; see the RFC
            itself for full legal notices."

        REVISION "201505120000Z"  -- May 12, 2015
        DESCRIPTION "Add Energy Management notifications"

        REVISION "201411250000Z"  -- November 25, 2014
        DESCRIPTION "Add docsis31(5) to DocsisVersion"

        REVISION "200605240000Z" -- May 24, 2006
        DESCRIPTION
            "Initial version, published as RFC 4547."
        ::= { mib-2 132 }

docsDevNotifControl OBJECT IDENTIFIER ::= { docsDevNotifMIB 1 }
docsDevCmtsNotifs OBJECT IDENTIFIER ::= { docsDevNotifMIB 3 0 }

docsDevCmtsNotifControl OBJECT-TYPE
    SYNTAX BITS {
        cmtsInitRegReqFailNotif( 0),
        cmtsInitRegRspFailNotif( 1),
        cmtsInitRegAckFailNotif( 2),
        cmtsDynServReqFailNotif( 3),
        cmtsDynServRspFailNotif( 4),
        cmtsDynServAckFailNotif( 5),
        cmtsBpiInitNotif( 6),
        cmtsBPKMNotif( 7),
        cmtsDynamicSANotif( 8),
        cmtsDCCReqFailNotif( 9),
        cmtsDCCRspFailNotif( 10),
        cmtsDCCAckFailNotif( 11),
        cmtsEmModeEnterNotif( 12),
        cmtsEmModeExitNotif( 13)
    }
    MAX-ACCESS read-write
    STATUS current
    DESCRIPTION
       "The object is used to enable specific CMTS notifications.
        For example, if the first bit is set, then
        docsDevCmtsInitRegRspFailNotif is enabled.  If it is not set,
        the notification is disabled.  Note that notifications are
        also under the control of the MIB modules defined in
        RFC3413.

        If the device is rebooted,the value of this object SHOULD
        revert to the default value.
       "
    DEFVAL { {} }
    ::= { docsDevNotifControl 2 }

docsDevCmtsInitRegReqFailNotif NOTIFICATION-TYPE
    OBJECTS {
        docsDevEvLevel,
        docsDevEvId,
        docsDevEvText,
        docsIfCmtsCmStatusMacAddress,
        ifPhysAddress,
        docsIfCmtsCmStatusDocsisRegMode,
        docsIfDocsisBaseCapability,
        docsIfCmtsCmStatusModulationType
    }
    STATUS current
    DESCRIPTION
        "A notification to report the failure of a registration
         request from a CM during the CM initialization
         process that was detected on the CMTS.

         This notification sends additional information about
         the event by including the following objects in its
         varbinding list.
         - docsDevEvLevel: the priority level associated with the
           event.
         - docsDevEvId: the unique identifier of the event that
           occurred.
         - docsDevEvText: a textual description of the event.
         - docsIfCmtsCmStatusMacAddress: the MAC address of the CM
           with which this notification is associated.
         - ifPhysAddress: the MAC address of the CMTS
           (if there is a cable card/interface in the CMTS,
           then it is actually the MAC address of the cable
           interface that connected to the CM) cable interface
           connected to the CM.
         - docsIfCmtsCmStatusDocsisRegMode: the QOS level (1.0, 1.1)
           that the reporting CM is operating in.
         - docsIfDocsisBaseCapability: the highest
           version of the DOCSIS specification (1.0, 1.1, 2.0)
           that the device is capable of supporting.
         - docsIfCmtsCmStatusModulationType: the upstream
           modulation methodology used by the CM.
        "
    ::= { docsDevCmtsNotifs 1 }

docsDevCmtsInitRegRspFailNotif NOTIFICATION-TYPE
    OBJECTS {
        docsDevEvLevel,
        docsDevEvId,
        docsDevEvText,
        docsIfCmtsCmStatusMacAddress,
        ifPhysAddress,
        docsIfCmtsCmStatusDocsisRegMode,
        docsIfDocsisBaseCapability,
        docsIfCmtsCmStatusModulationType
    }
    STATUS current
    DESCRIPTION
        "A notification to report the failure of a registration
         response during the CM initialization
         process that was detected by the CMTS.

         This notification sends additional information about
         the event by including the following objects in its
         varbinding list.
         - docsDevEvLevel: the priority level associated with the
           event.
         - docsDevEvId: the unique identifier of the event that
           occurred.
         - docsDevEvText: a textual description of the event.
         - docsIfCmtsCmStatusMacAddress: the MAC address of the CM
           with which this notification is associated.
         - ifPhysAddress: the MAC address of the CMTS
           (if there is a cable card/interface in the CMTS,
           then it is actually the MAC address of the cable
           interface that connected to the CM) cable interface
           connected to the CM.
         - docsIfCmtsCmStatusDocsisRegMode: the QOS level (1.0, 1.1)
           that the reporting CM is operating in.
         - docsIfDocsisBaseCapability: the highest
           version of the DOCSIS specification (1.0, 1.1, 2.0)
           that the device is capable of supporting.
         - docsIfCmtsCmStatusModulationType: the upstream
           modulation methodology used by the CM.
        "
    ::= { docsDevCmtsNotifs 2 }

docsDevCmtsInitRegAckFailNotif NOTIFICATION-TYPE
    OBJECTS {
        docsDevEvLevel,
        docsDevEvId,
        docsDevEvText,
        docsIfCmtsCmStatusMacAddress,
        ifPhysAddress,
        docsIfCmtsCmStatusDocsisRegMode,
        docsIfDocsisBaseCapability,
        docsIfCmtsCmStatusModulationType
    }
    STATUS current
    DESCRIPTION
        "A notification to report the failure of a registration
         acknowledgement from the CM during the CM
         initialization process that was detected by the CMTS.

         This notification sends additional information about
         the event by including the following objects in its
         varbinding list.
         - docsDevEvLevel: the priority level associated with the
           event.
         - docsDevEvId: the unique identifier of the event that
           occurred.
         - docsDevEvText: a textual description of the event.
         - docsIfCmtsCmStatusMacAddress: the MAC address of the CM
           with which this notification is associated.
         - ifPhysAddress: the MAC address of the CMTS
           (if there is a cable card/interface in the CMTS,
           then it is actually the MAC address of the cable
           interface that connected to the CM) cable interface
           connected to the CM.
         - docsIfCmtsCmStatusDocsisRegMode: the QOS level (1.0, 1.1)
           that the reporting CM is operating in.
         - docsIfDocsisBaseCapability: the highest
           version of the DOCSIS specification (1.0, 1.1, 2.0)
           that the device is capable of supporting.
         - docsIfCmtsCmStatusModulationType: the upstream
           modulation methodology used by the CM.
        "
    ::= { docsDevCmtsNotifs 3 }

docsDevCmtsDynServReqFailNotif NOTIFICATION-TYPE
    OBJECTS {
        docsDevEvLevel,
        docsDevEvId,
        docsDevEvText,
        docsIfCmtsCmStatusMacAddress,
        ifPhysAddress,
        docsIfCmtsCmStatusDocsisRegMode,
        docsIfDocsisBaseCapability,
        docsIfCmtsCmStatusModulationType
     }
    STATUS current
    DESCRIPTION
        "A notification to report the failure of a dynamic service
         request during the dynamic services process
         that was detected by the CMTS.

         This notification sends additional information about
         the event by including the following objects in its
         varbinding list.
         - docsDevEvLevel: the priority level associated with the
           event.
         - docsDevEvId: the unique identifier of the event that
           occurred.
         - docsDevEvText: a textual description of the event.
         - docsIfCmtsCmStatusMacAddress: the MAC address of the CM
           with which this notification is associated.
         - ifPhysAddress: the MAC address of the CMTS
           (if there is a cable card/interface in the CMTS,
           then it is actually the MAC address of the cable
           interface that connected to the CM) cable interface
           connected to the CM.
         - docsIfCmtsCmStatusDocsisRegMode: the QOS level (1.0, 1.1)
           that the reporting CM is operating in.
         - docsIfDocsisBaseCapability: the highest
           version of the DOCSIS specification (1.0, 1.1, 2.0)
           that the device is capable of supporting.
         - docsIfCmtsCmStatusModulationType: the upstream
           modulation methodology used by the CM.
        "
    ::= { docsDevCmtsNotifs 4 }

docsDevCmtsDynServRspFailNotif NOTIFICATION-TYPE
    OBJECTS {
        docsDevEvLevel,
        docsDevEvId,
        docsDevEvText,
        docsIfCmtsCmStatusMacAddress,
        ifPhysAddress,
        docsIfCmtsCmStatusDocsisRegMode,
        docsIfDocsisBaseCapability,
        docsIfCmtsCmStatusModulationType
    }
    STATUS current
    DESCRIPTION
        "A notification to report the failure of a dynamic service
         response during the dynamic services process
         that was detected by the CMTS.

         This notification sends additional information about
         the event by including the following objects in its
         varbinding list.
         - docsDevEvLevel: the priority level associated with the
           event.
         - docsDevEvId: the unique identifier of the event that
           occurred.
         - docsDevEvText: a textual description of the event.
         - docsIfCmtsCmStatusMacAddress: the MAC address of the CM
           with which this notification is associated.
         - ifPhysAddress: the MAC address of the CMTS
           (if there is a cable card/interface in the CMTS,
           then it is actually the MAC address of the cable
           interface that connected to the CM) cable interface
           connected to the CM.
         - docsIfCmtsCmStatusDocsisRegMode: the QOS level (1.0, 1.1)
           that the reporting CM is operating in.
         - docsIfDocsisBaseCapability: the highest
           version of the DOCSIS specification (1.0, 1.1, 2.0)
           that the device is capable of supporting.
         - docsIfCmtsCmStatusModulationType: the upstream
           modulation methodology used by the CM.
        "
    ::= { docsDevCmtsNotifs 5 }

docsDevCmtsDynServAckFailNotif NOTIFICATION-TYPE
    OBJECTS {
        docsDevEvLevel,
        docsDevEvId,
        docsDevEvText,
        docsIfCmtsCmStatusMacAddress,
        ifPhysAddress,
        docsIfCmtsCmStatusDocsisRegMode,
        docsIfDocsisBaseCapability,
        docsIfCmtsCmStatusModulationType
    }
    STATUS current
    DESCRIPTION
        "A notification to report the failure of a dynamic service
         acknowledgement during the dynamic services
         process that was detected by the CMTS.

         This notification sends additional information about
         the event by including the following objects in its
         varbinding list.
         - docsDevEvLevel: the priority level associated with the
           event.
         - docsDevEvId: the unique identifier of the event that
           occurred.
         - docsDevEvText: a textual description of the event.
         - docsIfCmtsCmStatusMacAddress: the MAC address of the CM
           with which this notification is associated.
         - ifPhysAddress: the MAC address of the CMTS
           (if there is a cable card/interface in the CMTS,
           then it is actually the MAC address of the cable
           interface that connected to the CM) cable interface
           connected to the CM.
         - docsIfCmtsCmStatusDocsisRegMode: the QOS level (1.0, 1.1)
           that the reporting CM is operating in.
         - docsIfDocsisBaseCapability: the highest
           version of the DOCSIS specification (1.0, 1.1, 2.0)
           that the device is capable of supporting.
         - docsIfCmtsCmStatusModulationType: the upstream
           modulation methodology used by the CM.
        "
    ::= { docsDevCmtsNotifs 6 }


docsDevCmtsBpiInitNotif NOTIFICATION-TYPE
    OBJECTS {
        docsDevEvLevel,
        docsDevEvId,
        docsDevEvText,
        docsIfCmtsCmStatusMacAddress,
        ifPhysAddress,
        docsIfCmtsCmStatusDocsisRegMode,
        docsIfDocsisBaseCapability,
        docsIfCmtsCmStatusModulationType
    }
    STATUS current
    DESCRIPTION
        "A notification to report the failure of a BPI
         initialization attempt during the CM registration process
         that was detected by the CMTS.

         This notification sends additional information about
         the event by including the following objects in its
         varbinding list.
         - docsDevEvLevel: the priority level associated with the
           event.
         - docsDevEvId: the unique identifier of the event that
           occurred.
         - docsDevEvText: a textual description of the event.
         - docsIfCmtsCmStatusMacAddress: the MAC address of the CM
           with which this notification is associated.
         - ifPhysAddress: the MAC address of the CMTS
           (if there is a cable card/interface in the CMTS,
           then it is actually the MAC address of the cable
           interface that connected to the CM) cable interface
           connected to the CM.
         - docsIfCmtsCmStatusDocsisRegMode: the QOS level (1.0, 1.1)
           that the reporting CM is operating in.
         - docsIfDocsisBaseCapability: the highest
           version of the DOCSIS specification (1.0, 1.1, 2.0)
           that the device is capable of supporting.
         - docsIfCmtsCmStatusModulationType: the upstream
           modulation methodology used by the CM.
        "
    ::= { docsDevCmtsNotifs 7 }

docsDevCmtsBPKMNotif NOTIFICATION-TYPE
    OBJECTS {
        docsDevEvLevel,
        docsDevEvId,
        docsDevEvText,
        docsIfCmtsCmStatusMacAddress,
        ifPhysAddress,
        docsIfCmtsCmStatusDocsisRegMode,
        docsIfDocsisBaseCapability,
        docsIfCmtsCmStatusModulationType
    }
    STATUS current
    DESCRIPTION
        "A notification to report the failure of a BPKM operation
         that is detected by the CMTS.

         This notification sends additional information about
         the event by including the following objects in its
         varbinding list.
         - docsDevEvLevel: the priority level associated with the
           event.
         - docsDevEvId: the unique identifier of the event that
           occurred.
         - docsDevEvText: a textual description of the event.
         - docsIfCmtsCmStatusMacAddress: the MAC address of the CM
           with which this notification is associated.
         - ifPhysAddress: the MAC address of the CMTS
           (if there is a cable card/interface in the CMTS,
           then it is actually the MAC address of the cable
           interface that connected to the CM) cable interface
           connected to the CM.
         - docsIfCmtsCmStatusDocsisRegMode: the QOS level (1.0, 1.1)
           that the reporting CM is operating in.
         - docsIfDocsisBaseCapability: the highest
           version of the DOCSIS specification (1.0, 1.1, 2.0)
           that the device is capable of supporting.
         - docsIfCmtsCmStatusModulationType: the upstream
           modulation methodology used by the CM.
        "
    ::= { docsDevCmtsNotifs 8 }

docsDevCmtsDynamicSANotif NOTIFICATION-TYPE
    OBJECTS {
        docsDevEvLevel,
        docsDevEvId,
        docsDevEvText,
        docsIfCmtsCmStatusMacAddress,
        ifPhysAddress,
        docsIfCmtsCmStatusDocsisRegMode,
        docsIfDocsisBaseCapability,
        docsIfCmtsCmStatusModulationType
    }
    STATUS current
    DESCRIPTION
        "A notification to report the failure of a dynamic security
         association operation that is detected by the CMTS.

         This notification sends additional information about
         the event by including the following objects in its
         varbinding list.

         - docsDevEvLevel: the priority level associated with the
           event.
         - docsDevEvId: the unique identifier of the event that
           occurred.
         - docsDevEvText: a textual description of the event.
         - docsIfCmtsCmStatusMacAddress: the MAC address of the CM
           with which this notification is associated.
         - ifPhysAddress: the MAC address of the CMTS
           (if there is a cable card/interface in the CMTS,
           then it is actually the MAC address of the cable
           interface that connected to the CM) cable interface
           connected to the CM.
         - docsIfCmtsCmStatusDocsisRegMode: the QOS level (1.0, 1.1)
           that the reporting CM is operating in.
         - docsIfDocsisBaseCapability: the highest
           version of the DOCSIS specification (1.0, 1.1, 2.0)
           that the device is capable of supporting.
         - docsIfCmtsCmStatusModulationType: the upstream
           modulation methodology used by the CM.
        "
    ::= { docsDevCmtsNotifs 9 }

docsDevCmtsDCCReqFailNotif NOTIFICATION-TYPE
    OBJECTS {
        docsDevEvLevel,
        docsDevEvId,
        docsDevEvText,
        docsIfCmtsCmStatusMacAddress,
        ifPhysAddress,
        docsIfCmtsCmStatusDocsisRegMode,
        docsIfDocsisBaseCapability,
        docsIfCmtsCmStatusModulationType
    }
    STATUS current
    DESCRIPTION
        "A notification to report the failure of a dynamic channel
         change request during the dynamic channel
         change process and is detected by the CMTS.

         This notification sends additional information about
         the event by including the following objects in its
         varbinding list.
         - docsDevEvLevel: the priority level associated with the
           event.
         - docsDevEvId: the unique identifier of the event that
           occurred.
         - docsDevEvText: a textual description of the event.
         - docsIfCmtsCmStatusMacAddress: the MAC address of the CM
           with which this notification is associated.
         - ifPhysAddress: the MAC address of the CMTS
           (if there is a cable card/interface in the CMTS,
           then it is actually the MAC address of the cable
           interface that connected to the CM) cable interface
           connected to the CM.
         - docsIfCmtsCmStatusDocsisRegMode: the QOS level (1.0, 1.1)
           that the reporting CM is operating in.
         - docsIfDocsisBaseCapability: the highest
           version of the DOCSIS specification (1.0, 1.1, 2.0)
           that the device is capable of supporting.
         - docsIfCmtsCmStatusModulationType: the upstream
           modulation methodology used by the CM.
        "
    ::= { docsDevCmtsNotifs 10 }

docsDevCmtsDCCRspFailNotif NOTIFICATION-TYPE
    OBJECTS {
        docsDevEvLevel,
        docsDevEvId,
        docsDevEvText,
        docsIfCmtsCmStatusMacAddress,
        ifPhysAddress,
        docsIfCmtsCmStatusDocsisRegMode,
        docsIfDocsisBaseCapability,
        docsIfCmtsCmStatusModulationType
    }
    STATUS current
    DESCRIPTION
        "A notification to report the failure of a dynamic channel
         change response during the dynamic channel
         change process and is detected by the CMTS.

         This notification sends additional information about
         the event by including the following objects in its
         varbinding list.
         - docsDevEvLevel: the priority level associated with the
           event.
         - docsDevEvId: the unique identifier of the event that
           occurred.
         - docsDevEvText: a textual description of the event.

         - docsIfCmtsCmStatusMacAddress: the MAC address of the CM
           with which this notification is associated.
         - ifPhysAddress: the MAC address of the CMTS
           (if there is a cable card/interface in the CMTS,
           then it is actually the MAC address of the cable
           interface that connected to the CM) cable interface
           connected to the CM.
         - docsIfCmtsCmStatusDocsisRegMode: the QOS level (1.0, 1.1)
           that the reporting CM is operating in.
         - docsIfDocsisBaseCapability: the highest
           version of the DOCSIS specification (1.0, 1.1, 2.0)
           that the device is capable of supporting.
         - docsIfCmtsCmStatusModulationType: the upstream
           modulation methodology used by the CM.
        "
    ::= { docsDevCmtsNotifs 11 }

docsDevCmtsDCCAckFailNotif NOTIFICATION-TYPE
    OBJECTS {
        docsDevEvLevel,
        docsDevEvId,
        docsDevEvText,
        docsIfCmtsCmStatusMacAddress,
        ifPhysAddress,
        docsIfCmtsCmStatusDocsisRegMode,
        docsIfDocsisBaseCapability,
        docsIfCmtsCmStatusModulationType
    }
    STATUS current
    DESCRIPTION
        "A notification to report the failure of a dynamic channel
         change acknowledgement during the dynamic channel
         change process and is detected by the CMTS.

         This notification sends additional information about
         the event by including the following objects in its
         varbinding list.
         - docsDevEvLevel: the priority level associated with the
           event.
         - docsDevEvId: the unique identifier of the event that
           occurred.
         - docsDevEvText: a textual description of the event.
         - docsIfCmtsCmStatusMacAddress: the MAC address of the CM
           with which this notification is associated.
         - ifPhysAddress: the MAC address of the CMTS
           (if there is a cable card/interface in the CMTS,
           then it is actually the MAC address of the cable
           interface that connected to the CM) cable interface
           connected to the CM.
         - docsIfCmtsCmStatusDocsisRegMode: the QOS level (1.0, 1.1)
           that the reporting CM is operating in.
         - docsIfDocsisBaseCapability: the highest
           version of the DOCSIS specification (1.0, 1.1, 2.0)
           that the device is capable of supporting.
         - docsIfCmtsCmStatusModulationType: the upstream
           modulation methodology used by the CM.
        "
    ::= { docsDevCmtsNotifs 12}

docsDevCmtsEmModeEnterNotif NOTIFICATION-TYPE
    OBJECTS {
        docsDevEvLevel,
        docsDevEvId,
        docsDevEvText,
        docsIfCmtsCmStatusMacAddress,
        ifPhysAddress,
        docsIfCmtsCmStatusDocsisRegMode,
        docsIfDocsisBaseCapability,
        docsIfCmtsCmStatusModulationType
    }
    STATUS current
    DESCRIPTION
        "A notification to report entering energy management mode 
         for a particular modem attached to the CMTS.

         This notification sends additional information about
         the event by including the following objects in its
         varbinding list.
         - docsDevEvLevel: the priority level associated with the
           event.
         - docsDevEvId: the unique identifier of the event that
           occurred.
         - docsDevEvText: a textual description of the event.
         - docsIfCmtsCmStatusMacAddress: the MAC address of the CM
           with which this notification is associated.
         - ifPhysAddress: the MAC address of the CMTS
           (if there is a cable card/interface in the CMTS,
           then it is actually the MAC address of the cable
           interface that connected to the CM) cable interface
           connected to the CM.
         - docsIfCmtsCmStatusDocsisRegMode: the QOS level (1.0, 1.1)
           that the reporting CM is operating in.
         - docsIfDocsisBaseCapability: the highest
           version of the DOCSIS specification (1.0, 1.1, 2.0)
           that the device is capable of supporting.
         - docsIfCmtsCmStatusModulationType: the upstream
           modulation methodology used by the CM.
        "
    ::= { docsDevCmtsNotifs 13 }

docsDevCmtsEmModeExitNotif NOTIFICATION-TYPE
    OBJECTS {
        docsDevEvLevel,
        docsDevEvId,
        docsDevEvText,
        docsIfCmtsCmStatusMacAddress,
        ifPhysAddress,
        docsIfCmtsCmStatusDocsisRegMode,
        docsIfDocsisBaseCapability,
        docsIfCmtsCmStatusModulationType
    }
    STATUS current
    DESCRIPTION
        "A notification to report exiting energy management mode 
         for a particular modem attached to the CMTS.

         This notification sends additional information about
         the event by including the following objects in its
         varbinding list.
         - docsDevEvLevel: the priority level associated with the
           event.
         - docsDevEvId: the unique identifier of the event that
           occurred.
         - docsDevEvText: a textual description of the event.
         - docsIfCmtsCmStatusMacAddress: the MAC address of the CM
           with which this notification is associated.
         - ifPhysAddress: the MAC address of the CMTS
           (if there is a cable card/interface in the CMTS,
           then it is actually the MAC address of the cable
           interface that connected to the CM) cable interface
           connected to the CM.
         - docsIfCmtsCmStatusDocsisRegMode: the QOS level (1.0, 1.1)
           that the reporting CM is operating in.
         - docsIfDocsisBaseCapability: the highest
           version of the DOCSIS specification (1.0, 1.1, 2.0)
           that the device is capable of supporting.
         - docsIfCmtsCmStatusModulationType: the upstream
           modulation methodology used by the CM.
        "
    ::= { docsDevCmtsNotifs 14 }


--
--Conformance definitions
--

docsDevNotifConformance OBJECT IDENTIFIER
   ::= { docsDevNotifMIB 4 }
docsDevNotifGroups OBJECT IDENTIFIER
   ::= { docsDevNotifConformance 1 }
docsDevNotifCompliances OBJECT IDENTIFIER
   ::= { docsDevNotifConformance 2 }

docsDevCmtsNotifCompliance MODULE-COMPLIANCE
    STATUS current
    DESCRIPTION
        "The compliance statement for DOCSIS CMTS Notification
         and Control."
    MODULE --docsDevNotif
       MANDATORY-GROUPS {
          docsDevCmtsNotifControlGroup,
          docsDevCmtsNotificationGroup
       }
    ::= { docsDevNotifCompliances 2 }

docsDevCmtsNotifControlGroup OBJECT-GROUP
    OBJECTS {
        docsDevCmtsNotifControl
    }
    STATUS current
    DESCRIPTION
        "This group represents objects that allow control
         over CMTS Notifications."
    ::= { docsDevNotifGroups 3 }

docsDevCmtsNotificationGroup NOTIFICATION-GROUP
    NOTIFICATIONS {
        docsDevCmtsInitRegReqFailNotif,
        docsDevCmtsInitRegRspFailNotif,
        docsDevCmtsInitRegAckFailNotif ,
        docsDevCmtsDynServReqFailNotif,
        docsDevCmtsDynServRspFailNotif,
        docsDevCmtsDynServAckFailNotif,
        docsDevCmtsBpiInitNotif,
        docsDevCmtsBPKMNotif,
        docsDevCmtsDynamicSANotif,
        docsDevCmtsDCCReqFailNotif,
        docsDevCmtsDCCRspFailNotif,
        docsDevCmtsDCCAckFailNotif
    }
    STATUS current
    DESCRIPTION
        "A collection of CMTS notifications providing device
         status and control."
    ::= { docsDevNotifGroups 4 }

END
