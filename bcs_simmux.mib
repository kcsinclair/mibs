BCSSIMULCRYPTMUX-MIB DEFINITIONS ::= BEGIN

IMPORTS
        MODULE-IDENTITY,
        OBJECT-TYPE,
        Unsigned32,
        Integer32
                FROM SNMPv2-SMI
        bcs
                FROM BCS-IDENT-MIB;

bcsSimulcryptMux     MODULE-IDENTITY
        LAST-UPDATED "200602090000Z"

        ORGANIZATION "Motorola Connected Home Solutions"
        CONTACT-INFO "Motorola Technical Response Center
                      Inside USA     1-888-944-HELP (1-888-944-4357)
                      Outside USA    1-215-323-0044
                      TRC Hours:
                      Monday through Friday 8am - 7pm Eastern Standard Time
                      Saturdays            10am - 5pm Eastern Standard Time"

        DESCRIPTION  "The Simulcrypt MUX MIB module for Motorola BCS products."
 
        REVISION "200602090000Z"
        DESCRIPTION "Version 1.1; February 9, 2006
                    - Updated Contact Information."

        REVISION     "200401230000Z"
        DESCRIPTION
                     "Version 1.0:

                      June 24, 2003
                      - Initial Revision."

         ::= {bcs 8}


-- SIMULCRYPT MUX MIB STRUCTURE

   bcsSimMuxConfig                                        OBJECT IDENTIFIER ::= {bcsSimulcryptMux 1}
      bcsSimMuxConfigGeneral                              OBJECT IDENTIFIER ::= {bcsSimMuxConfig 1}
--       bcsSimMuxTcpPort                                                       {bcsSimMuxConfigGeneral 1}
--       bcsSimMuxUdpPort                                                       {bcsSimMuxConfigGeneral 2}
--       bcsSimMuxChannelTestRate                                               {bcsSimMuxConfigGeneral 3}
--       bcsSimMuxBandwidthAllocation                                           {bcsSimMuxConfigGeneral 4}
   bcsSimMuxStatus                                        OBJECT IDENTIFIER ::= {bcsSimulcryptMux 2}
      bcsSimMuxStatusGeneral                              OBJECT IDENTIFIER ::= {bcsSimMuxStatus 1}
--       bcsSimMuxMibSupportStatus                                              {bcsSimMuxStatusGeneral 1}
--       bcsSimMuxMaxEmmg                                                       {bcsSimMuxStatusGeneral 2}
--       bcsSimMuxMaxEmmgChannels                                               {bcsSimMuxConfigGeneral 3}
--       bcsSimMuxMaxEmmgChannelStreams                                         {bcsSimMuxConfigGeneral 4}
--    bcsSimMuxEmmgTable                                                        {bcsSimMuxStatus 2}
--       bcsSimMuxEmmgEntry                                                     {bcsSimMuxEmmgTable 1}
--          bcsSimMuxEmmgIndex                                                  {bcsSimMuxEmmgEntry 1}
--          bcsSimMuxEmmgTcpState                                               {bcsSimMuxEmmgEntry 2}
--          bcsSimMuxEmmgId                                                     {bcsSimMuxEmmgEntry 3}
--          bcsSimMuxEmmgChannelCount                                           {bcsSimMuxEmmgEntry 4}
--    bcsSimMuxEmmgChannelTable                                                 {bcsSimMuxStatus 3}
--       bcsSimMuxEmmgChannelEntry                                              {bcsSimMuxEmmgChannelTable 1}
--          bcsSimMuxEmmgChannelEmmgIndex                                       {bcsSimMuxEmmgChannelEntry 1}
--          bcsSimMuxEmmgChannelIndex                                           {bcsSimMuxEmmgChannelEntry 2}
--          bcsSimMuxEmmgChannelState                                           {bcsSimMuxEmmgChannelEntry 3}
--          bcsSimMuxEmmgChannelId                                              {bcsSimMuxEmmgChannelEntry 4}
--          bcsSimMuxEmmgChannelStreamType                                      {bcsSimMuxEmmgChannelEntry 5}
--          bcsSimMuxEmmgChannelStreamCount                                     {bcsSimMuxEmmgChannelEntry 6}
--    bcsSimMuxEmmgStreamTable                                                  {bcsSimMuxStatus 4}
--       bcsSimMuxEmmgStreamEntry                                               {bcsSimMuxEmmgStreamTable 1}
--          bcsSimMuxEmmgStreamEmmgIndex                                        {bcsSimMuxEmmgStreamEntry 1}
--          bcsSimMuxEmmgStreamChannelIndex                                     {bcsSimMuxEmmgStreamEntry 2}
--          bcsSimMuxEmmgStreamIndex                                            {bcsSimMuxEmmgStreamEntry 3}
--          bcsSimMuxEmmgStreamState                                            {bcsSimMuxEmmgStreamEntry 4}
--          bcsSimMuxEmmgStreamId                                               {bcsSimMuxEmmgStreamEntry 5}
--          bcsSimMuxEmmgStreamDataId                                           {bcsSimMuxEmmgStreamEntry 6}
--          bcsSimMuxEmmgStreamDataType                                         {bcsSimMuxEmmgStreamEntry 7}
--          bcsSimMuxEmmgStreamInsertCount                                      {bcsSimMuxEmmgStreamEntry 8}


-- ------------------------------------------------------------------------------
--
-- bcsSimMuxConfig
--
-- bcsSimMuxConfigGeneral
--

bcsSimMuxTcpPort OBJECT-TYPE
    SYNTAX Unsigned32
    MAX-ACCESS read-write
    STATUS current
    DESCRIPTION
        "This value specifies the TCP port number that the
         MUX will use to listen on for EMMG connections.

         SEM Note:
         Once written, a save must be performed via the semSaveConfig
         parameter and the SEM must be rebooted for the change to take
         effect."
::= { bcsSimMuxConfigGeneral 1 }

bcsSimMuxUdpPort OBJECT-TYPE
    SYNTAX Unsigned32
    MAX-ACCESS read-write
    STATUS current
    DESCRIPTION
        "This value specifies the UDP port number that the
         MUX will use to listen on for the EMMG connections.

         SEM Note:
         Once written, a save must be performed via the semSaveConfig
         parameter and the SEM must be rebooted for the change to take
         effect."
::= { bcsSimMuxConfigGeneral 2 }

bcsSimMuxChannelTestRate OBJECT-TYPE
    SYNTAX Unsigned32
    MAX-ACCESS read-write
    STATUS current
    DESCRIPTION
        "This value specifies the rate in milliseconds at which
         the channel test should be initiated by the MUX.

         SEM Note:
         Once written, a save must be performed via the semSaveConfig
         parameter and the SEM must be rebooted for the change to take
         effect."
::= { bcsSimMuxConfigGeneral 3 }

bcsSimMuxBandwidthAllocation OBJECT-TYPE
    SYNTAX Unsigned32
    MAX-ACCESS read-write
    STATUS current
    DESCRIPTION
        "This value specifies the bandwidth in kbps allocated to each connected mux
         as reported in the Stream_BW_allocation message.  A value of zero will
         cause the Mux to report the allocated bandwidth as Not Known. 

         SEM Note:
         Once written, a save must be performed via the semSaveConfig
         parameter and the SEM must be rebooted for the change to take
         effect."
::= { bcsSimMuxConfigGeneral 4 }


-- ------------------------------------------------------------------------------
--
-- bcsSimMuxStatus
--
-- bcsSimMuxStatusGeneral
--

bcsSimMuxMibSupportStatus OBJECT-TYPE
    SYNTAX INTEGER
       {
        notCapable (1),
        capable    (2),
        enabled    (3)
       }
    MAX-ACCESS read-only
    STATUS current
    DESCRIPTION
        "Indicates whether the device is capable of supporting
         and/or enabled to support the functionality of the
         bcsSimulcryptMux MIB."
::= { bcsSimMuxStatusGeneral 1 }

bcsSimMuxMaxEmmg OBJECT-TYPE
    SYNTAX Unsigned32
    MAX-ACCESS read-only
    STATUS current
    DESCRIPTION
        "This value represents the maximum number of EMMGs this device
         can support."
::= { bcsSimMuxStatusGeneral 2 }

bcsSimMuxMaxEmmgChannels OBJECT-TYPE
    SYNTAX Unsigned32
    MAX-ACCESS read-only
    STATUS current
    DESCRIPTION
        "This value represents the maximum number of channels per EMMG
         this device can support."
::= { bcsSimMuxStatusGeneral 3 }

bcsSimMuxMaxEmmgChannelStreams OBJECT-TYPE
    SYNTAX Unsigned32
    MAX-ACCESS read-only
    STATUS current
    DESCRIPTION
        "This value represents the maximum number of streams
         per EMMG channel this device can support."
::= { bcsSimMuxStatusGeneral 4 }


-- ------------------------------------------------------------------------------
--
-- bcsSimMuxEmmgTable
--

bcsSimMuxEmmgTable OBJECT-TYPE
    SYNTAX SEQUENCE OF BcsSimMuxEmmgEntry
    MAX-ACCESS not-accessible
    STATUS current
    DESCRIPTION
        "This status table contains EMMG specific information for
         up to bcsSimMuxMaxEmmg Mux <=> EMMG connections."
::= { bcsSimMuxStatus 2 }

bcsSimMuxEmmgEntry OBJECT-TYPE
    SYNTAX BcsSimMuxEmmgEntry
    MAX-ACCESS not-accessible
    STATUS current
    DESCRIPTION
        "A single entry in the bcsSimMuxEmmgTable table."
    INDEX { bcsSimMuxEmmgIndex }
::= { bcsSimMuxEmmgTable 1}

BcsSimMuxEmmgEntry ::= SEQUENCE
    {
     bcsSimMuxEmmgIndex           Integer32,
     bcsSimMuxEmmgTcpState        INTEGER,
     bcsSimMuxEmmgId              Unsigned32,
     bcsSimMuxEmmgChannelCount    Unsigned32
    }

bcsSimMuxEmmgIndex OBJECT-TYPE
    SYNTAX Integer32
    MAX-ACCESS not-accessible
    STATUS current
    DESCRIPTION
       "The EMMG index for this entry in the bcsSimMuxEmmgTable.
        Limit is bcsSimMuxMaxEmmg."
::= { bcsSimMuxEmmgEntry 1 }

bcsSimMuxEmmgTcpState OBJECT-TYPE
    SYNTAX INTEGER
       {
          open   (1),
          closed (2),
          error  (3)
       }
    MAX-ACCESS read-only
    STATUS current
    DESCRIPTION
       "This column specifies TCP state of this MUX <==> EMMG
        connection."
::= { bcsSimMuxEmmgEntry 2 }

bcsSimMuxEmmgId OBJECT-TYPE
    SYNTAX Unsigned32
    MAX-ACCESS read-only
    STATUS current
    DESCRIPTION
       "This column provides the EMMG ID."
::= { bcsSimMuxEmmgEntry 3 }

bcsSimMuxEmmgChannelCount OBJECT-TYPE
    SYNTAX Unsigned32
    MAX-ACCESS read-only
    STATUS current
    DESCRIPTION
       "This column provides the number of channels opened on
        this MUX <==> EMMG connection."
::= { bcsSimMuxEmmgEntry 4 }


-- ------------------------------------------------------------------------------
--
-- bcsSimMuxEmmgChannelTable
--

bcsSimMuxEmmgChannelTable OBJECT-TYPE
    SYNTAX SEQUENCE OF BcsSimMuxEmmgChannelEntry
    MAX-ACCESS not-accessible
    STATUS current
    DESCRIPTION
        "This status table presents MUX<==>EMMG channel specific
         information."
::= { bcsSimMuxStatus 3 }

bcsSimMuxEmmgChannelEntry OBJECT-TYPE
    SYNTAX BcsSimMuxEmmgChannelEntry
    MAX-ACCESS not-accessible
    STATUS current
    DESCRIPTION
        "A single entry in the bcsSimMuxEmmgChannelTable table."
    INDEX { bcsSimMuxEmmgChannelEmmgIndex,
            bcsSimMuxEmmgChannelIndex }
::= { bcsSimMuxEmmgChannelTable 1}

BcsSimMuxEmmgChannelEntry ::= SEQUENCE
    {
     bcsSimMuxEmmgChannelEmmgIndex      Integer32,
     bcsSimMuxEmmgChannelIndex          Integer32,
     bcsSimMuxEmmgChannelState          INTEGER,
     bcsSimMuxEmmgChannelId             Unsigned32,
     bcsSimMuxEmmgChannelStreamType     INTEGER,
     bcsSimMuxEmmgChannelStreamCount    Unsigned32
    }

bcsSimMuxEmmgChannelEmmgIndex OBJECT-TYPE
    SYNTAX Integer32
    MAX-ACCESS not-accessible
    STATUS current
    DESCRIPTION
       "The EMMG index for this entry in the bcsSimMuxEmmgChannelTable.
        Limit is bcsSimMuxMaxEmmg."
::= { bcsSimMuxEmmgChannelEntry 1 }

bcsSimMuxEmmgChannelIndex OBJECT-TYPE
    SYNTAX Integer32
    MAX-ACCESS not-accessible
    STATUS current
    DESCRIPTION
       "The Channel index for this entry in the bcsSimMuxEmmgChannelTable.
        Limit is bcsSimMuxMaxEmmgChannels."
::= { bcsSimMuxEmmgChannelEntry 2 }

bcsSimMuxEmmgChannelState OBJECT-TYPE
    SYNTAX INTEGER
        {
         open   (1),
         closed (2),
         error  (3)
        }
    MAX-ACCESS read-only
    STATUS current
    DESCRIPTION
       "This column specifies the Channel state."
::= { bcsSimMuxEmmgChannelEntry 3 }

bcsSimMuxEmmgChannelId OBJECT-TYPE
    SYNTAX Unsigned32
    MAX-ACCESS read-only
    STATUS current
    DESCRIPTION
       "This column specifies the Channel ID."
::= { bcsSimMuxEmmgChannelEntry 4 }

bcsSimMuxEmmgChannelStreamType OBJECT-TYPE
    SYNTAX INTEGER
        {
         section  (1),
         tsPacket (2)
        }
    MAX-ACCESS read-only
    STATUS current
    DESCRIPTION
       "This column specifies the type of stream data transfer.
        Streams can transfer data as sections or as transport
        stream packets.  The determination is made by the EMMG
        at channel setup time."
::= { bcsSimMuxEmmgChannelEntry 5 }

bcsSimMuxEmmgChannelStreamCount OBJECT-TYPE
    SYNTAX Unsigned32
    MAX-ACCESS read-only
    STATUS current
    DESCRIPTION
       "This column specifies the number of streams on this channel."
::= { bcsSimMuxEmmgChannelEntry 6 }


-- ------------------------------------------------------------------------------
--
-- bcsSimMuxEmmgStreamTable
--

bcsSimMuxEmmgStreamTable OBJECT-TYPE
    SYNTAX SEQUENCE OF BcsSimMuxEmmStreamEntry
    MAX-ACCESS not-accessible
    STATUS current
    DESCRIPTION
        "This status presents MUX<==>EMMG stream specific information."
::= { bcsSimMuxStatus 4 }

bcsSimMuxEmmgStreamEntry OBJECT-TYPE
    SYNTAX BcsSimMuxEmmStreamEntry
    MAX-ACCESS not-accessible
    STATUS current
    DESCRIPTION
        "A single entry in the bcsSimMuxEmmgStreamTable table."
    INDEX { bcsSimMuxEmmgStreamEmmgIndex,
            bcsSimMuxEmmgStreamChannelIndex,
            bcsSimMuxEmmgStreamIndex }
::= { bcsSimMuxEmmgStreamTable 1}

BcsSimMuxEmmStreamEntry ::= SEQUENCE
    {
     bcsSimMuxEmmgStreamEmmgIndex      Integer32,
     bcsSimMuxEmmgStreamChannelIndex   Integer32,
     bcsSimMuxEmmgStreamIndex          Integer32,
     bcsSimMuxEmmgStreamState          INTEGER,
     bcsSimMuxEmmgStreamId             Unsigned32,
     bcsSimMuxEmmgStreamDataId         Unsigned32,
     bcsSimMuxEmmgStreamDataType       INTEGER,
     bcsSimMuxEmmgStreamInsertCount    Unsigned32
    }

bcsSimMuxEmmgStreamEmmgIndex OBJECT-TYPE
    SYNTAX Integer32
    MAX-ACCESS not-accessible
    STATUS current
    DESCRIPTION
       "The EMMG index for this entry in the bcsSimMuxEmmgStreamTable.
        Limit is bcsSimMuxMaxEmmg."
::= { bcsSimMuxEmmgStreamEntry 1 }

bcsSimMuxEmmgStreamChannelIndex OBJECT-TYPE
    SYNTAX Integer32
    MAX-ACCESS not-accessible
    STATUS current
    DESCRIPTION
       "The Channel index for this entry in the bcsSimMuxEmmgStreamTable.
        Limit is bcsSimMuxMaxEmmgChannels."
::= { bcsSimMuxEmmgStreamEntry 2 }

bcsSimMuxEmmgStreamIndex OBJECT-TYPE
    SYNTAX Integer32
    MAX-ACCESS not-accessible
    STATUS current
    DESCRIPTION
       "The Stream index for this entry in the bcsSimMuxEmmgStreamTable.
        Limit is bcsSimMuxMaxEmmgChannelStreams."
::= { bcsSimMuxEmmgStreamEntry 3 }

bcsSimMuxEmmgStreamState OBJECT-TYPE
    SYNTAX INTEGER
        {
         open   (1),
         closed (2),
         error  (3)
        }
    MAX-ACCESS read-only
    STATUS current
    DESCRIPTION
       "This column specifies the Stream state."
::= { bcsSimMuxEmmgStreamEntry 4 }

bcsSimMuxEmmgStreamId OBJECT-TYPE
    SYNTAX Unsigned32
    MAX-ACCESS read-only
    STATUS current
    DESCRIPTION
       "This variable identifies the Stream ID."
::= { bcsSimMuxEmmgStreamEntry 5 }

bcsSimMuxEmmgStreamDataId OBJECT-TYPE
    SYNTAX Unsigned32
    MAX-ACCESS read-only
    STATUS current
    DESCRIPTION
       "This variable identifies the data ID associated with this
        stream."
::= { bcsSimMuxEmmgStreamEntry 6 }

bcsSimMuxEmmgStreamDataType OBJECT-TYPE
    SYNTAX INTEGER
        {
         emm-data     (1),
         private-data (2)
        }
    MAX-ACCESS read-only
    STATUS current
    DESCRIPTION
       "This variable identifies the data type carried on this stream.
        Currently supported values are:
        EMM-data      = 1
        Private-Data  = 2"
::= { bcsSimMuxEmmgStreamEntry 7 }

bcsSimMuxEmmgStreamInsertCount OBJECT-TYPE
    SYNTAX Unsigned32
    MAX-ACCESS read-only
    STATUS current
    DESCRIPTION
       "This variable maintains a count on the number of insertions
        on the stream."
::= { bcsSimMuxEmmgStreamEntry 8 }

-- ------------------------------------------------------------------------------
END
