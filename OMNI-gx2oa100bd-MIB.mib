OMNI-gx2oa100bd-MIB DEFINITIONS ::= BEGIN

    IMPORTS
	IpAddress, TimeTicks
					      FROM RFC1155-SMI
	OBJECT-TYPE
					      FROM RFC-1212
	sysUpTime, DisplayString
					      FROM RFC1213-MIB
	TRAP-TYPE
					      FROM RFC-1215
	gi, motproxies
					      FROM NLS-BBNIDENT-MIB
   gx2OA100BD
					      FROM GX2HFC-MIB

	trapIdentifier,trapNetworkElemModelNumber,
	trapNetworkElemSerialNum, trapPerceivedSeverity,
	trapNetworkElemOperState, trapNetworkElemAlarmStatus,
	trapNetworkElemAdminState, trapNetworkElemAvailStatus,
	trapText, trapNETrapLastTrapTimeStamp, trapChangedObjectId,
	trapChangedValueInteger, trapChangedValueDisplayString
					      FROM NLSBBN-TRAPS-MIB;



	       -- This MIB module uses the extended OBJECT-TYPE macro as
	       -- defined in RFC1212 and the TRAP-TYPE macro as defined
	       -- in RFC 1215.

		   --REVISION	"1" Jan 20, 2003
		   --DESCRIPTION
		   --			Added revision and description comment section

      --    OMNISTAR Optical Amplifier (high power, dual pump) MIB MODULE

	-- This MIB module defines information for management of HFC networks
		--
		-- The MIB module assumes that all generic (static) network element
		-- information is defined in a different module such as the HFC module
		-- The MIB consists of two groups:
		-- the device type descriptor subgroup and
      -- gx2oa100bd Network Elements subgroup.
		-- The device type descriptor subgroup is used to define
      -- parameters specific to gx2OA100BD device type.
		-- These parameters are common across all network elements
      -- from gx2oa100bd device type.
		--
      -- The gx2oa100bd Network Elements subgroup is
      -- a list of gx2oa100bd type elements in the
		-- current network topology with nominal
		-- and current parameter values for the
		-- individual network elements; the individual
		-- network elements are identified by
		-- index from hfcCommonTable.
		-- That implies what hfcCommonTableIndex and
      -- gx2oa100bdTableIndex are equal for each individual
		-- network element.
		-- This table is an extension of the hfcCommonTable
      -- for all elements of gx2oa100bd type.
		--
      -- Both groups are mandatory for management of gx2oa100bd devices.

-- ****************************************************************************
		--
		-- All floating point numbers will be represented by an IEEE 32 Bit number.
		-- Conversion of this number must be done on the user interface to view the
		-- actual floating point number.
		--

		Float ::= Counter  -- UNSIGNED (32 BITS)


-- ****************************************************************************

      -- gx2oa100bd Device Descriptor subgroup.

		-- The device type descriptor subgroup is used to define
      -- parameters specific to gx2OA100BD device type.
		-- These parameters are common across all network elements
      -- from gx2oa100bd device type.


      gx2OA100BDDescriptor OBJECT IDENTIFIER ::= {gx2OA100BD 1}



--*****************************************************************************
-- // Section: Table definitions
      --              gx2OA100BD Table

      -- Contains a list of all gx2OA100BD type devices in
		-- the network. Each device is characterized with
		-- current network topology information, with nominal
		-- and current parameter values for the
		-- individual network elements;
		--
		-- The individual network elements indentified by
		-- index from hfcCommonTable.
		-- That implies what hfcCommonTableIndex and
      -- gx2OA100BDTableIndex are equal for each individual
		-- nettwork element.
		-- This table should be used as an extension of the hfcCommonTable
      -- for all elements of gx2OA100BD type.

--*************************************************************************
-- // Section: Table definitions - Analog
          gx2OA100BDAnalogTable                    OBJECT-TYPE
          SYNTAX             SEQUENCE OF Gx2OA100BDAnalogEntry
			 ACCESS             not-accessible
			 STATUS             mandatory
			 DESCRIPTION
          "This table contains gx2OA100B specific parameters with
			  nominal and current values."
          ::= { gx2OA100BD 2 }


          gx2OA100BDAnalogEntry               OBJECT-TYPE
          SYNTAX             Gx2OA100BDAnalogEntry
			 ACCESS             not-accessible
			 STATUS             mandatory
			 DESCRIPTION
			 "This list contains digital product class and the
			  associated RF channel parameters and descriptions."
          INDEX { gx2OA100BDAnalogTableIndex }
          ::= { gx2OA100BDAnalogTable  1}

--*************************************************************************
-- // Section: Table definitions - Digital
          gx2OA100BDDigitalTable                    OBJECT-TYPE
          SYNTAX             SEQUENCE OF Gx2OA100BDDigitalEntry
			 ACCESS             not-accessible
			 STATUS             mandatory
			 DESCRIPTION
          "This table contains gx2OA100B specific parameters with
			  nominal and current values."
          ::= { gx2OA100BD 3 }

          gx2OA100BDDigitalEntry               OBJECT-TYPE
          SYNTAX             Gx2OA100BDDigitalEntry
			 ACCESS             not-accessible
			 STATUS             mandatory
			 DESCRIPTION
			 "This list contains digital product class and the
			  associated RF channel parameters and descriptions."
          INDEX { gx2OA100BDDigitalTableIndex }
          ::= { gx2OA100BDDigitalTable  2}

--*************************************************************************
-- // Section: Table definitions - Status
          gx2OA100BDStatusTable                    OBJECT-TYPE
          SYNTAX             SEQUENCE OF Gx2OA100BDStatusEntry
			 ACCESS             not-accessible
			 STATUS             mandatory
			 DESCRIPTION
          "This table contains gx2OA100B specific parameters with
			  nominal and current values."
          ::= { gx2OA100BD 4 }

          gx2OA100BDStatusEntry               OBJECT-TYPE
          SYNTAX             Gx2OA100BDStatusEntry
			 ACCESS             not-accessible
			 STATUS             mandatory
			 DESCRIPTION
			 "This list contains digital product class and the
			  associated RF channel parameters and descriptions."
          INDEX { gx2OA100BDStatusTableIndex }
          ::= { gx2OA100BDStatusTable  3}

--*************************************************************************
-- // Section: Table definitions - Factory
          gx2OA100BDFactoryTable                    OBJECT-TYPE
          SYNTAX             SEQUENCE OF Gx2OA100BDFactoryEntry
			 ACCESS             not-accessible
			 STATUS             mandatory
			 DESCRIPTION
          "This table contains gx2OA100B specific parameters with
			  nominal and current values."
          ::= { gx2OA100BD 5 }

          gx2OA100BDFactoryEntry               OBJECT-TYPE
          SYNTAX             Gx2OA100BDFactoryEntry
			 ACCESS             not-accessible
			 STATUS             mandatory
			 DESCRIPTION
			 "This list contains digital product class and the
			  associated RF channel parameters and descriptions."
          INDEX { gx2OA100BDFactoryTableIndex }
          ::= { gx2OA100BDFactoryTable  4}

--*************************************************************************
-- // Section: Table definitions - Hold Time 
	   gx2OA100BDHoldTimeTable                    OBJECT-TYPE
		 SYNTAX             SEQUENCE OF Gx2OA100BDHoldTimeEntry
			 ACCESS             not-accessible
			 STATUS             mandatory
			 DESCRIPTION
			 "This table contains gx2OA100BD specific parameters with
			  nominal and current values."
			 ::= { gx2OA100BD 6 }

          gx2OA100BDHoldTimeEntry               OBJECT-TYPE
		 SYNTAX             Gx2OA100BDHoldTimeEntry
			 ACCESS             not-accessible
			 STATUS             mandatory
			 DESCRIPTION
			 "This list contains digital product class and the
			  associated RF channel parameters and descriptions."
			 INDEX { gx2OA100BDHoldTimeTableIndex, gx2OA100BDHoldTimeSpecIndex }
			 ::= { gx2OA100BDHoldTimeTable  5}


--*************************************************************************
-- // Section: Analog parameters

      Gx2OA100BDAnalogEntry    ::= SEQUENCE
	   {
      gx2OA100BDAnalogTableIndex         INTEGER,
-- // Analog parameter : Module temperature
      oa100bdlabelModTemp        DisplayString (SIZE (0..80)),
      oa100bduomModTemp       DisplayString (SIZE (0..80)),
      oa100bdmajorHighModTemp    Float,
      oa100bdmajorLowModTemp     Float,
      oa100bdminorHighModTemp    Float,
      oa100bdminorLowModTemp     Float,
      oa100bdcurrentValueModTemp    Float,
      oa100bdstateFlagModTemp    INTEGER,
      oa100bdminValueModTemp     Float,
      oa100bdmaxValueModTemp     Float,
      oa100bdalarmStateModTemp      INTEGER,

-- // Analog parameter : Optical input power
      oa100bdlabelOptInPower     DisplayString (SIZE (0..80)),
      oa100bduomOptInPower       DisplayString (SIZE (0..80)),
      oa100bdmajorHighOptInPower    Float,
      oa100bdmajorLowOptInPower     Float,
      oa100bdminorHighOptInPower    Float,
      oa100bdminorLowOptInPower     Float,
      oa100bdcurrentValueOptInPower Float,
      oa100bdstateFlagOptInPower    INTEGER,
      oa100bdminValueOptInPower     Float,
      oa100bdmaxValueOptInPower     Float,
      oa100bdalarmStateOptInPower   INTEGER,

-- // Analog parameter : Optical output power
      oa100bdlabelOptOutPower    DisplayString (SIZE (0..80)),
      oa100bduomOptOutPower      DisplayString (SIZE (0..80)),
      oa100bdmajorHighOptOutPower   Float,
      oa100bdmajorLowOptOutPower    Float,
      oa100bdminorHighOptOutPower   Float,
      oa100bdminorLowOptOutPower    Float,
      oa100bdcurrentValueOptOutPower   Float,
      oa100bdstateFlagOptOutPower   INTEGER,
      oa100bdminValueOptOutPower    Float,
      oa100bdmaxValueOptOutPower    Float,
      oa100bdalarmStateOptOutPower  INTEGER,

-- // Analog parameter : Main TEC temperature
      oa100bdlabelMainTECTemp       DisplayString (SIZE (0..80)),
      oa100bduomMainTECTemp         DisplayString (SIZE (0..80)),
      oa100bdmajorHighMainTECTemp      Float,
      oa100bdmajorLowMainTECTemp    Float,
      oa100bdminorHighMainTECTemp      Float,
      oa100bdminorLowMainTECTemp    Float,
      oa100bdcurrentValueMainTECTemp      Float,
      oa100bdstateFlagMainTECTemp      INTEGER,
      oa100bdminValueMainTECTemp    Float,
      oa100bdmaxValueMainTECTemp    Float,
      oa100bdalarmStateMainTECTemp     INTEGER,

-- // Analog parameter : Main LASER power
      oa100bdlabelMainLaserPower     DisplayString (SIZE (0..80)),
      oa100bduomMainLaserPower       DisplayString (SIZE (0..80)),
      oa100bdmajorHighMainLaserPower    Float,
      oa100bdmajorLowMainLaserPower     Float,
      oa100bdminorHighMainLaserPower    Float,
      oa100bdminorLowMainLaserPower     Float,
      oa100bdcurrentValueMainLaserPower Float,
      oa100bdstateFlagMainLaserPower    INTEGER,
      oa100bdminValueMainLaserPower     Float,
      oa100bdmaxValueMainLaserPower     Float,
      oa100bdalarmStateMainLaserPower   INTEGER,

-- // Analog parameter : Aux TEC temperature
      oa100bdlabelAuxTECTemp       DisplayString (SIZE (0..80)),
      oa100bduomAuxTECTemp         DisplayString (SIZE (0..80)),
      oa100bdmajorHighAuxTECTemp      Float,
      oa100bdmajorLowAuxTECTemp    Float,
      oa100bdminorHighAuxTECTemp      Float,
      oa100bdminorLowAuxTECTemp    Float,
      oa100bdcurrentValueAuxTECTemp      Float,
      oa100bdstateFlagAuxTECTemp      INTEGER,
      oa100bdminValueAuxTECTemp    Float,
      oa100bdmaxValueAuxTECTemp    Float,
      oa100bdalarmStateAuxTECTemp     INTEGER,

-- // Analog parameter : Aux LASER power
      oa100bdlabelAuxLaserPower     DisplayString (SIZE (0..80)),
      oa100bduomAuxLaserPower       DisplayString (SIZE (0..80)),
      oa100bdmajorHighAuxLaserPower    Float,
      oa100bdmajorLowAuxLaserPower     Float,
      oa100bdminorHighAuxLaserPower    Float,
      oa100bdminorLowAuxLaserPower     Float,
      oa100bdcurrentValueAuxLaserPower Float,
      oa100bdstateFlagAuxLaserPower    INTEGER,
      oa100bdminValueAuxLaserPower     Float,
      oa100bdmaxValueAuxLaserPower     Float,
      oa100bdalarmStateAuxLaserPower   INTEGER,

-- // Analog parameter : Fan current
      oa100bdlabelFanCurrent     DisplayString (SIZE (0..80)),
      oa100bduomFanCurrent       DisplayString (SIZE (0..80)),
      oa100bdmajorHighFanCurrent    Float,
      oa100bdmajorLowFanCurrent     Float,
      oa100bdminorHighFanCurrent    Float,
      oa100bdminorLowFanCurrent     Float,
      oa100bdcurrentValueFanCurrent Float,
      oa100bdstateFlagFanCurrent    INTEGER,
      oa100bdminValueFanCurrent     Float,
      oa100bdmaxValueFanCurrent     Float,
      oa100bdalarmStateFanCurrent   INTEGER,

-- // Analog parameter : Output power setting
      oa100bdlabelOPSetting      DisplayString (SIZE (0..80)),
      oa100bduomOPSetting        DisplayString (SIZE (0..80)),
      oa100bdmajorHighOPSetting     Float,
      oa100bdmajorLowOPSetting      Float,
      oa100bdminorHighOPSetting     Float,
      oa100bdminorLowOPSetting      Float,
      oa100bdcurrentValueOPSetting  Float,
      oa100bdstateFlagOPSetting     INTEGER,
      oa100bdminValueOPSetting      Float,
      oa100bdmaxValueOPSetting      Float,
      oa100bdalarmStateOPSetting    INTEGER,

-- // Analog parameter : Laser power setting
      oa100bdlabelLPSetting      DisplayString (SIZE (0..80)),
      oa100bduomLPSetting        DisplayString (SIZE (0..80)),
      oa100bdmajorHighLPSetting     Float,
      oa100bdmajorLowLPSetting      Float,
      oa100bdminorHighLPSetting     Float,
      oa100bdminorLowLPSetting      Float,
      oa100bdcurrentValueLPSetting  Float,
      oa100bdstateFlagLPSetting     INTEGER,
      oa100bdminValueLPSetting      Float,
      oa100bdmaxValueLPSetting      Float,
      oa100bdalarmStateLPSetting    INTEGER,

-- // Analog parameter : Constant gain setting
      oa100bdlabelCGSetting      DisplayString (SIZE (0..80)),
      oa100bduomCGSetting        DisplayString (SIZE (0..80)),
      oa100bdmajorHighCGSetting     Float,
      oa100bdmajorLowCGSetting      Float,
      oa100bdminorHighCGSetting     Float,
      oa100bdminorLowCGSetting      Float,
      oa100bdcurrentValueCGSetting  Float,
      oa100bdstateFlagCGSetting     INTEGER,
      oa100bdminValueCGSetting      Float,
      oa100bdmaxValueCGSetting      Float,
      oa100bdalarmStateCGSetting    INTEGER,

-- // Analog parameter : optical input threshold
      oa100bdlabelOptThreshold      DisplayString (SIZE (0..80)),
      oa100bduomOptThreshold     DisplayString (SIZE (0..80)),
      oa100bdmajorHighOptThreshold  Float,
      oa100bdmajorLowOptThreshold   Float,
      oa100bdminorHighOptThreshold  Float,
      oa100bdminorLowOptThreshold   Float,
      oa100bdcurrentValueOptThreshold  Float,
      oa100bdstateFlagOptThreshold  INTEGER,
      oa100bdminValueOptThreshold   Float,
      oa100bdmaxValueOptThreshold   Float,
      oa100bdalarmStateOptThreshold INTEGER

		}

		-- ****************  Digital Parameters ***********************
-- // Section: Digital parameters

      Gx2OA100BDDigitalEntry   ::= SEQUENCE
      {
      gx2OA100BDDigitalTableIndex         INTEGER,

-- // Digital parameter : Mode setting
      oa100bdlabelModeSetting       DisplayString (SIZE (0..80)),
      oa100bdvalueModeSetting    INTEGER,
      oa100bdenumModeSetting     DisplayString (SIZE (0..80)),
      oa100bdstateFlagModeSetting      INTEGER,

-- // Digital parameter : Module state
      oa100bdlabelModuleState    DisplayString (SIZE (0..80)),
      oa100bdvalueModuleState    INTEGER,
      oa100bdenumModuleState     DisplayString (SIZE (0..80)),
      oa100bdstateFlagModuleState      INTEGER,

-- // Digital parameter : Factory default
      oa100bdlabelFactoryDefault    DisplayString (SIZE (0..80)),
      oa100bdvalueFactoryDefault    INTEGER,
      oa100bdenumFactoryDefault     DisplayString (SIZE (0..80)),
      oa100bdstateFlagFactoryDefault   INTEGER
		}

		-- ****************  Status Parameters ************************************
-- // Section: Status parameters
      Gx2OA100BDStatusEntry    ::= SEQUENCE
      {
      gx2OA100BDStatusTableIndex         INTEGER,

-- // Status parameter : boot
      oa100bdlabelBoot           DisplayString (SIZE (0..80)),
      oa100bdvalueBoot           INTEGER,
      oa100bdstateflagBoot          INTEGER,

-- // Status parameter : flash
      oa100bdlabelFlash          DisplayString (SIZE (0..80)),
      oa100bdvalueFlash          INTEGER,
      oa100bdstateflagFlash            INTEGER,

-- // Status parameter : Factory data crc
      oa100bdlabelFactoryDataCRC          DisplayString (SIZE (0..80)),
      oa100bdvalueFactoryDataCRC       INTEGER,
      oa100bdstateflagFactoryDataCRC      INTEGER,

-- // Status parameter : Alarm data crc
      oa100bdlabelAlarmDataCRC         DisplayString (SIZE (0..80)),
      oa100bdvalueAlarmDataCRC         INTEGER,
      oa100bdstateflagAlarmDataCRC     INTEGER,

-- // Status parameter : Calibration data crc
      oa100bdlabelCalibrationDataCRC      DisplayString (SIZE (0..80)),
      oa100bdvalueCalibrationDataCRC      INTEGER,
      oa100bdstateflagCalibrationDataCRC  INTEGER,

-- // Status parameter : optical power shutdown
      oa100bdlabelOptInShutdown        DisplayString (SIZE (0..80)),
      oa100bdvalueOptInShutdown        INTEGER,
      oa100bdstateflagOptInShutdown    INTEGER,

-- // Status parameter : Main TEC temp shutdown
      oa100bdlabelMainTECTempShutdown     DisplayString (SIZE (0..80)),
      oa100bdvalueMainTECTempShutdown     INTEGER,
      oa100bdstateflagMainTECTempShutdown    INTEGER,
-- // Status parameter : Aux TEC temp shutdown
      oa100bdlabelAuxTECTempShutdown      DisplayString (SIZE (0..80)),
      oa100bdvalueAuxTECTempShutdown      INTEGER,
      oa100bdstateflagAuxTECTempShutdown     INTEGER,
-- // Status parameter : power fail
      oa100bdlabelPowerFail         DisplayString (SIZE (0..80)),
      oa100bdvaluePowerFail         INTEGER,
      oa100bdstateflagPowerFail        INTEGER,

-- // Status parameter : Key switch
      oa100bdlabelKeySwitch         DisplayString (SIZE (0..80)),
      oa100bdvalueKeySwitch         INTEGER,
      oa100bdstateflagKeySwitch        INTEGER,

-- // Status parameter : Main laser current shutdown
      oa100bdlabelMainLaserCurrShutdown      DisplayString (SIZE (0..80)),
      oa100bdvalueMainLaserCurrShutdown      INTEGER,
      oa100bdstateflagMainLaserCurrShutdown  INTEGER,

-- // Status parameter : Aux laser current shutdown
      oa100bdlabelAuxLaserCurrShutdown    DisplayString (SIZE (0..80)),
      oa100bdvalueAuxLaserCurrShutdown    INTEGER,
      oa100bdstateflagAuxLaserCurrShutdown   INTEGER,


-- // Status parameter : Main laser power shutdown

      oa100bdlabelMainLaserPowShutdown    DisplayString (SIZE (0..80)),
      oa100bdvalueMainLaserPowShutdown    INTEGER,
      oa100bdstateflagMainLaserPowShutdown      INTEGER,

-- // Status parameter : Aux laser power shutdown

      oa100bdlabelAuxLaserPowShutdown     DisplayString (SIZE (0..80)),
      oa100bdvalueAuxLaserPowShutdown     INTEGER,
      oa100bdstateflagAuxLaserPowShutdown    INTEGER,


-- // Status parameter : ADC status
      oa100bdlabelADCStatus         DisplayString (SIZE (0..80)),
      oa100bdvalueADCStatus         INTEGER,
      oa100bdstateflagADCStatus        INTEGER,

-- // Status parameter : Constant gain
      oa100bdlabelConstGainStatus      DisplayString (SIZE (0..80)),
      oa100bdvalueConstGainStatus      INTEGER,
      oa100bdstateflagConstGainStatus     INTEGER,
-- // Status parameter : Hardware Error
      oa100bdlabelHardwareErrorStatus   DisplayString (SIZE (0..80)),
      oa100bdvalueHardwareErrorStatus    INTEGER,
      oa100bdstateflagHardwareErrorStatus INTEGER,

-- // Status parameter : standby
      oa100bdlabelStandbyStatus        DisplayString (SIZE (0..80)),
      oa100bdvalueStandbyStatus        INTEGER,
      oa100bdstateflagStandbyStatus    INTEGER

		}

		-- ****************  Factory Parameters *************************************
-- // Section: Factory parameters
      Gx2OA100BDFactoryEntry    ::= SEQUENCE
      {
      gx2OA100BDFactoryTableIndex         INTEGER,

      oa100bdbootControlByte     INTEGER,
      oa100bdbootStatusByte      INTEGER,
      oa100bdbank0CRC            INTEGER,
      oa100bdbank1CRC            INTEGER,
      oa100bdprgEEPROMByte       INTEGER,
      oa100bdfactoryCRC          INTEGER,
      oa100bdcalculateCRC        INTEGER,
      oa100bdhourMeter           INTEGER,
      oa100bdflashPrgCntA        INTEGER,
      oa100bdflashPrgCntB        INTEGER,
      oa100bdfwRev0              DisplayString (SIZE (0..80)),
      oa100bdfwRev1              DisplayString (SIZE (0..80))

		}

-- // Section: Analog parameter detail
      gx2OA100BDAnalogTableIndex              OBJECT-TYPE
			   SYNTAX           INTEGER (1..4294967295)
			   ACCESS           read-only
			   STATUS           mandatory
			   DESCRIPTION
			   "The value of this object identifies the network
			    element. This index is equal to the
			    hfcCommonTableIndex for the same element."
            ::= { gx2OA100BDAnalogEntry 1}

-- // New Parameter - Module Temperature

      oa100bdlabelModTemp              OBJECT-TYPE
			   SYNTAX           DisplayString (SIZE (0..80))
			   ACCESS           read-only
			   STATUS           optional
			   DESCRIPTION
			   "The value of this object provides the label of the
			    Module Temperature Analog parameter."
            ::= { gx2OA100BDAnalogEntry 2}

      oa100bduomModTemp                OBJECT-TYPE
			   SYNTAX           DisplayString (SIZE (0..80))
			   ACCESS           read-only
			   STATUS           optional
			   DESCRIPTION
			   "The value of this object provides the Unit of Measure of the
			    Module Temperature Analog parameter."
            ::= { gx2OA100BDAnalogEntry 3}

      oa100bdmajorHighModTemp          OBJECT-TYPE
			   SYNTAX           Float
			   ACCESS           read-only
			   STATUS           mandatory
			   DESCRIPTION
			   "The value of this object provides the Major High alarm value
			          of the Module Temperature Analog parameter. This value is a floating
			    point number that is represented as an IEEE 32 bit number."
            ::= { gx2OA100BDAnalogEntry 4}


      oa100bdmajorLowModTemp           OBJECT-TYPE
			   SYNTAX           Float
			   ACCESS           read-only
			   STATUS           mandatory
			   DESCRIPTION
			   "The value of this object provides the Major Low alarm value
			          of the Module Temperature Analog parameter. This value is a floating
			    point number that is represented as an IEEE 32 bit number."
            ::= { gx2OA100BDAnalogEntry 5}

      oa100bdminorHighModTemp          OBJECT-TYPE
			   SYNTAX           Float
			   ACCESS           read-only
			   STATUS           mandatory
			   DESCRIPTION
			   "The value of this object provides the Minor High alarm value
			          of the Module Temperature Analog parameter. This value is a floating
			    point number that is represented as an IEEE 32 bit number."
            ::= { gx2OA100BDAnalogEntry 6}

      oa100bdminorLowModTemp           OBJECT-TYPE
			   SYNTAX           Float
			   ACCESS           read-only
			   STATUS           mandatory
			   DESCRIPTION
			   "The value of this object provides the Minor Low alarm value
			          of the Module Temperature Analog parameter. This value is a floating
			    point number that is represented as an IEEE 32 bit number."
            ::= { gx2OA100BDAnalogEntry 7}

      oa100bdcurrentValueModTemp       OBJECT-TYPE
			   SYNTAX           Float
			   ACCESS           read-only
			   STATUS           mandatory
			   DESCRIPTION
			   "The value of this object provides the Current value
			          of the Module Temperature Analog parameter. This value is a floating
			    point number that is represented as an IEEE 32 bit number."
            ::= { gx2OA100BDAnalogEntry 8}

      oa100bdstateFlagModTemp          OBJECT-TYPE
			   SYNTAX           INTEGER
								{
								hidden(1),
								read-only(2),
								updateable(3)
								}
			   ACCESS           read-only
			   STATUS           mandatory
			   DESCRIPTION
			   "The value of this object provides the state
			    of the Module Temperature Analog parameter. (0-Hidden
			          1-Read-Only, 2-Updateable)."
            ::= { gx2OA100BDAnalogEntry 9}

      oa100bdminValueModTemp           OBJECT-TYPE
			   SYNTAX           Float
			   ACCESS           read-only
			   STATUS           mandatory
			   DESCRIPTION
			   "The value of this object provides the minimum value
			          of the Module Temperature Analog parameter. This value is a floating
			    point number that is represented as an IEEE 32 bit number."
            ::= { gx2OA100BDAnalogEntry 10}

      oa100bdmaxValueModTemp           OBJECT-TYPE
			   SYNTAX           Float
			   ACCESS           read-only
			   STATUS           mandatory
			   DESCRIPTION
			   "The value of this object provides the maximum value
			          of the Module Temperature Analog parameter. This value is a floating
			    point number that is represented as an IEEE 32 bit number."
            ::= { gx2OA100BDAnalogEntry 11}

      oa100bdalarmStateModTemp         OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Module Temperature Analog parameter."
            ::= { gx2OA100BDAnalogEntry 12}

-- // New Parameter - Optical Input Power

      oa100bdlabelOptInPower             OBJECT-TYPE
			   SYNTAX           DisplayString (SIZE (0..80))
			   ACCESS           read-only
			   STATUS           optional
			   DESCRIPTION
			   "The value of this object provides the label of the
			    Optical Input Power Analog parameter."
            ::= { gx2OA100BDAnalogEntry 13}

      oa100bduomOptInPower               OBJECT-TYPE
			   SYNTAX           DisplayString (SIZE (0..80))
			   ACCESS           read-only
			   STATUS           optional
			   DESCRIPTION
			   "The value of this object provides the Unit of Measure of the
			    Optical Input Power Analog parameter."
            ::= { gx2OA100BDAnalogEntry 14}

      oa100bdmajorHighOptInPower         OBJECT-TYPE
			   SYNTAX           Float
			   ACCESS           read-only
			   STATUS           mandatory
			   DESCRIPTION
			   "The value of this object provides the Major High alarm value
			          of the Optical Input Power Analog parameter. This value is a floating
			    point number that is represented as an IEEE 32 bit number."
            ::= { gx2OA100BDAnalogEntry 15}


      oa100bdmajorLowOptInPower          OBJECT-TYPE
			   SYNTAX           Float
			   ACCESS           read-only
			   STATUS           mandatory
			   DESCRIPTION
			   "The value of this object provides the Major Low alarm value
			          of the Optical Input Power Analog parameter. This value is a floating
			    point number that is represented as an IEEE 32 bit number."
            ::= { gx2OA100BDAnalogEntry 16}

      oa100bdminorHighOptInPower         OBJECT-TYPE
			   SYNTAX           Float
			   ACCESS           read-only
			   STATUS           mandatory
			   DESCRIPTION
			   "The value of this object provides the Minor High alarm value
			          of the Optical Input Power Analog parameter. This value is a floating
			    point number that is represented as an IEEE 32 bit number."
            ::= { gx2OA100BDAnalogEntry 17}

      oa100bdminorLowOptInPower          OBJECT-TYPE
			   SYNTAX           Float
			   ACCESS           read-only
			   STATUS           mandatory
			   DESCRIPTION
			   "The value of this object provides the Minor Low alarm value
			          of the Optical Input Power Analog parameter. This value is a floating
			    point number that is represented as an IEEE 32 bit number."
            ::= { gx2OA100BDAnalogEntry 18}

      oa100bdcurrentValueOptInPower      OBJECT-TYPE
			   SYNTAX           Float
			   ACCESS           read-only
			   STATUS           mandatory
			   DESCRIPTION
			   "The value of this object provides the Current value
			          of the Optical Input Power Analog parameter. This value is a floating
			    point number that is represented as an IEEE 32 bit number."
            ::= { gx2OA100BDAnalogEntry 19}

      oa100bdstateFlagOptInPower         OBJECT-TYPE
			   SYNTAX           INTEGER
								{
								hidden(1),
								read-only(2),
								updateable(3)
								}
			   ACCESS           read-only
			   STATUS           mandatory
			   DESCRIPTION
			   "The value of this object provides the state
			    of the Optical Input Power Analog parameter. (0-Hidden
			          1-Read-Only, 2-Updateable)."
            ::= { gx2OA100BDAnalogEntry 20}

      oa100bdminValueOptInPower          OBJECT-TYPE
			   SYNTAX           Float
			   ACCESS           read-only
			   STATUS           mandatory
			   DESCRIPTION
			   "The value of this object provides the minimum value
			          of the Optical Input Power Analog parameter. This value is a floating
			    point number that is represented as an IEEE 32 bit number."
            ::= { gx2OA100BDAnalogEntry 21}

      oa100bdmaxValueOptInPower          OBJECT-TYPE
			   SYNTAX           Float
			   ACCESS           read-only
			   STATUS           mandatory
			   DESCRIPTION
			   "The value of this object provides the maximum value
			          of the Optical Input Power Analog parameter. This value is a floating
			    point number that is represented as an IEEE 32 bit number."
            ::= { gx2OA100BDAnalogEntry 22}

      oa100bdalarmStateOptInPower        OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Optical Input Power Analog parameter."
            ::= { gx2OA100BDAnalogEntry 23}

-- // New Parameter - Optical Output Power

      oa100bdlabelOptOutPower             OBJECT-TYPE
			   SYNTAX           DisplayString (SIZE (0..80))
			   ACCESS           read-only
			   STATUS           optional
			   DESCRIPTION
			   "The value of this object provides the label of the
			    Optical Output Power Analog parameter."
            ::= { gx2OA100BDAnalogEntry 24}

      oa100bduomOptOutPower               OBJECT-TYPE
			   SYNTAX           DisplayString (SIZE (0..80))
			   ACCESS           read-only
			   STATUS           optional
			   DESCRIPTION
			   "The value of this object provides the Unit of Measure of the
			    Optical Output Power Analog parameter."
            ::= { gx2OA100BDAnalogEntry 25}

      oa100bdmajorHighOptOutPower         OBJECT-TYPE
			   SYNTAX           Float
			   ACCESS           read-only
			   STATUS           mandatory
			   DESCRIPTION
			   "The value of this object provides the Major High alarm value
			          of the Optical Output Power Analog parameter. This value is a floating
			    point number that is represented as an IEEE 32 bit number."
            ::= { gx2OA100BDAnalogEntry 26}


      oa100bdmajorLowOptOutPower          OBJECT-TYPE
			   SYNTAX           Float
			   ACCESS           read-only
			   STATUS           mandatory
			   DESCRIPTION
			   "The value of this object provides the Major Low alarm value
			          of the Optical Output Power Analog parameter. This value is a floating
			    point number that is represented as an IEEE 32 bit number."
            ::= { gx2OA100BDAnalogEntry 27}

      oa100bdminorHighOptOutPower         OBJECT-TYPE
			   SYNTAX           Float
			   ACCESS           read-only
			   STATUS           mandatory
			   DESCRIPTION
			   "The value of this object provides the Minor High alarm value
			          of the Optical Output Power Analog parameter. This value is a floating
			    point number that is represented as an IEEE 32 bit number."
            ::= { gx2OA100BDAnalogEntry 28}

      oa100bdminorLowOptOutPower          OBJECT-TYPE
			   SYNTAX           Float
			   ACCESS           read-only
			   STATUS           mandatory
			   DESCRIPTION
			   "The value of this object provides the Minor Low alarm value
			          of the Optical Output Power Analog parameter. This value is a floating
			    point number that is represented as an IEEE 32 bit number."
            ::= { gx2OA100BDAnalogEntry 29}

      oa100bdcurrentValueOptOutPower      OBJECT-TYPE
			   SYNTAX           Float
			   ACCESS           read-only
			   STATUS           mandatory
			   DESCRIPTION
			   "The value of this object provides the Current value
			          of the Optical Output Power Analog parameter. This value is a floating
			    point number that is represented as an IEEE 32 bit number."
            ::= { gx2OA100BDAnalogEntry 30}

      oa100bdstateFlagOptOutPower         OBJECT-TYPE
			   SYNTAX           INTEGER
								{
								hidden(1),
								read-only(2),
								updateable(3)
								}
			   ACCESS           read-only
			   STATUS           mandatory
			   DESCRIPTION
			   "The value of this object provides the state
			    of the Optical Output Power Analog parameter. (0-Hidden
			          1-Read-Only, 2-Updateable)."
            ::= { gx2OA100BDAnalogEntry 31}

      oa100bdminValueOptOutPower          OBJECT-TYPE
			   SYNTAX           Float
			   ACCESS           read-only
			   STATUS           mandatory
			   DESCRIPTION
			   "The value of this object provides the minimum value
			          of the Optical Output Power Analog parameter. This value is a floating
			    point number that is represented as an IEEE 32 bit number."
            ::= { gx2OA100BDAnalogEntry 32}

      oa100bdmaxValueOptOutPower          OBJECT-TYPE
			   SYNTAX           Float
			   ACCESS           read-only
			   STATUS           mandatory
			   DESCRIPTION
			   "The value of this object provides the maximum value
			          of the Optical Output Power Analog parameter. This value is a floating
			    point number that is represented as an IEEE 32 bit number."
            ::= { gx2OA100BDAnalogEntry 33}

      oa100bdalarmStateOptOutPower        OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Optical Output Power Analog parameter."
            ::= { gx2OA100BDAnalogEntry 34}

-- // New Parameter - Main TEC temperature

      oa100bdlabelMainTECTemp              OBJECT-TYPE
			   SYNTAX           DisplayString (SIZE (0..80))
			   ACCESS           read-only
			   STATUS           optional
			   DESCRIPTION
			   "The value of this object provides the label of the
			    TEC Temperature Analog parameter."
            ::= { gx2OA100BDAnalogEntry 35}

      oa100bduomMainTECTemp                OBJECT-TYPE
			   SYNTAX           DisplayString (SIZE (0..80))
			   ACCESS           read-only
			   STATUS           optional
			   DESCRIPTION
			   "The value of this object provides the Unit of Measure of the
			    TEC Temperature Analog parameter."
            ::= { gx2OA100BDAnalogEntry 36}

      oa100bdmajorHighMainTECTemp          OBJECT-TYPE
			   SYNTAX           Float
			   ACCESS           read-only
			   STATUS           mandatory
			   DESCRIPTION
			   "The value of this object provides the Major High alarm value
             of the TEC Temperature Analog parameter. This value is a floating
			    point number that is represented as an IEEE 32 bit number."
            ::= { gx2OA100BDAnalogEntry 37}


      oa100bdmajorLowMainTECTemp           OBJECT-TYPE
			   SYNTAX           Float
			   ACCESS           read-only
			   STATUS           mandatory
			   DESCRIPTION
			   "The value of this object provides the Major Low alarm value
             of the TEC Temperature Analog parameter. This value is a floating
			    point number that is represented as an IEEE 32 bit number."
            ::= { gx2OA100BDAnalogEntry 38}

      oa100bdminorHighMainTECTemp          OBJECT-TYPE
			   SYNTAX           Float
			   ACCESS           read-only
			   STATUS           mandatory
			   DESCRIPTION
			   "The value of this object provides the Minor High alarm value
             of the TEC Temperature Analog parameter. This value is a floating
			    point number that is represented as an IEEE 32 bit number."
            ::= { gx2OA100BDAnalogEntry 39}

      oa100bdminorLowMainTECTemp           OBJECT-TYPE
			   SYNTAX           Float
			   ACCESS           read-only
			   STATUS           mandatory
			   DESCRIPTION
			   "The value of this object provides the Minor Low alarm value
             of the TEC Temperature Analog parameter. This value is a floating
			    point number that is represented as an IEEE 32 bit number."
            ::= { gx2OA100BDAnalogEntry 40}

      oa100bdcurrentValueMainTECTemp       OBJECT-TYPE
			   SYNTAX           Float
			   ACCESS           read-only
			   STATUS           mandatory
			   DESCRIPTION
			   "The value of this object provides the Current value
             of the TEC Temperature Analog parameter. This value is a floating
			    point number that is represented as an IEEE 32 bit number."
            ::= { gx2OA100BDAnalogEntry 41}

      oa100bdstateFlagMainTECTemp          OBJECT-TYPE
			   SYNTAX           INTEGER
								{
								hidden(1),
								read-only(2),
								updateable(3)
								}
			   ACCESS           read-only
			   STATUS           mandatory
			   DESCRIPTION
			   "The value of this object provides the state
			    of the TEC Temperature Analog parameter. (0-Hidden
			          1-Read-Only, 2-Updateable)."
            ::= { gx2OA100BDAnalogEntry 42}

      oa100bdminValueMainTECTemp           OBJECT-TYPE
			   SYNTAX           Float
			   ACCESS           read-only
			   STATUS           mandatory
			   DESCRIPTION
			   "The value of this object provides the minimum value
             of the TEC Temperature Analog parameter. This value is a floating
			    point number that is represented as an IEEE 32 bit number."
            ::= { gx2OA100BDAnalogEntry 43}

      oa100bdmaxValueMainTECTemp           OBJECT-TYPE
			   SYNTAX           Float
			   ACCESS           read-only
			   STATUS           mandatory
			   DESCRIPTION
			   "The value of this object provides the maximum value
             of the TEC Temperature Analog parameter. This value is a floating
			    point number that is represented as an IEEE 32 bit number."
            ::= { gx2OA100BDAnalogEntry 44}

      oa100bdalarmStateMainTECTemp         OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the TEC Temperature Analog parameter."
            ::= { gx2OA100BDAnalogEntry 45}

-- // New Parameter - Main Laser Power

      oa100bdlabelMainLaserPower              OBJECT-TYPE
			   SYNTAX           DisplayString (SIZE (0..80))
			   ACCESS           read-only
			   STATUS           optional
			   DESCRIPTION
			   "The value of this object provides the label of the
             Main Laser Power Analog parameter."
            ::= { gx2OA100BDAnalogEntry 46}

      oa100bduomMainLaserPower                OBJECT-TYPE
			   SYNTAX           DisplayString (SIZE (0..80))
			   ACCESS           read-only
			   STATUS           optional
			   DESCRIPTION
			   "The value of this object provides the Unit of Measure of the
             Main Laser Power Analog parameter."
            ::= { gx2OA100BDAnalogEntry 47}

      oa100bdmajorHighMainLaserPower          OBJECT-TYPE
			   SYNTAX           Float
			   ACCESS           read-only
			   STATUS           mandatory
			   DESCRIPTION
			   "The value of this object provides the Major High alarm value
             of the Main Laser Power Analog parameter. This value is a floating
			    point number that is represented as an IEEE 32 bit number."
            ::= { gx2OA100BDAnalogEntry 48}


      oa100bdmajorLowMainLaserPower           OBJECT-TYPE
			   SYNTAX           Float
			   ACCESS           read-only
			   STATUS           mandatory
			   DESCRIPTION
			   "The value of this object provides the Major Low alarm value
             of the Main Laser Power Analog parameter. This value is a floating
			    point number that is represented as an IEEE 32 bit number."
            ::= { gx2OA100BDAnalogEntry 49}

      oa100bdminorHighMainLaserPower          OBJECT-TYPE
			   SYNTAX           Float
			   ACCESS           read-only
			   STATUS           mandatory
			   DESCRIPTION
			   "The value of this object provides the Minor High alarm value
             of the Main Laser Power Analog parameter. This value is a floating
			    point number that is represented as an IEEE 32 bit number."
            ::= { gx2OA100BDAnalogEntry 50}

      oa100bdminorLowMainLaserPower           OBJECT-TYPE
			   SYNTAX           Float
			   ACCESS           read-only
			   STATUS           mandatory
			   DESCRIPTION
			   "The value of this object provides the Minor Low alarm value
             of the Main Laser Power Analog parameter. This value is a floating
			    point number that is represented as an IEEE 32 bit number."
            ::= { gx2OA100BDAnalogEntry 51}

      oa100bdcurrentValueMainLaserPower       OBJECT-TYPE
			   SYNTAX           Float
			   ACCESS           read-only
			   STATUS           mandatory
			   DESCRIPTION
			   "The value of this object provides the Current value
             of the Main Laser Power Analog parameter. This value is a floating
			    point number that is represented as an IEEE 32 bit number."
            ::= { gx2OA100BDAnalogEntry 52}

      oa100bdstateFlagMainLaserPower          OBJECT-TYPE
			   SYNTAX           INTEGER
								{
								hidden(1),
								read-only(2),
								updateable(3)
								}
			   ACCESS           read-only
			   STATUS           mandatory
			   DESCRIPTION
			   "The value of this object provides the state
             of the Main Laser Power Analog parameter. (0-Hidden
			          1-Read-Only, 2-Updateable)."
            ::= { gx2OA100BDAnalogEntry 53}

      oa100bdminValueMainLaserPower           OBJECT-TYPE
			   SYNTAX           Float
			   ACCESS           read-only
			   STATUS           mandatory
			   DESCRIPTION
			   "The value of this object provides the minimum value
             of the Main Laser Power Analog parameter. This value is a floating
			    point number that is represented as an IEEE 32 bit number."
            ::= { gx2OA100BDAnalogEntry 54}

      oa100bdmaxValueMainLaserPower           OBJECT-TYPE
			   SYNTAX           Float
			   ACCESS           read-only
			   STATUS           mandatory
			   DESCRIPTION
			   "The value of this object provides the maximum value
             of the Main Laser Power Analog parameter. This value is a floating
			    point number that is represented as an IEEE 32 bit number."
            ::= { gx2OA100BDAnalogEntry 55}

      oa100bdalarmStateMainLaserPower         OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
             the Main Laser Power Analog parameter."
            ::= { gx2OA100BDAnalogEntry 56}

-- // New Parameter - Aux TEC temperature

      oa100bdlabelAuxTECTemp              OBJECT-TYPE
            SYNTAX           DisplayString (SIZE (0..80))
            ACCESS           read-only
            STATUS           optional
            DESCRIPTION
            "The value of this object provides the label of the
             TEC Temperature Analog parameter."
            ::= { gx2OA100BDAnalogEntry 57}

      oa100bduomAuxTECTemp                OBJECT-TYPE
            SYNTAX           DisplayString (SIZE (0..80))
            ACCESS           read-only
            STATUS           optional
            DESCRIPTION
            "The value of this object provides the Unit of Measure of the
             TEC Temperature Analog parameter."
            ::= { gx2OA100BDAnalogEntry 58}

      oa100bdmajorHighAuxTECTemp          OBJECT-TYPE
            SYNTAX           Float
            ACCESS           read-only
            STATUS           mandatory
            DESCRIPTION
            "The value of this object provides the Major High alarm value
                   of the TEC Temperature Analog parameter. This value is a floating
             point number that is represented as an IEEE 32 bit number."
            ::= { gx2OA100BDAnalogEntry 59}


      oa100bdmajorLowAuxTECTemp           OBJECT-TYPE
            SYNTAX           Float
            ACCESS           read-only
            STATUS           mandatory
            DESCRIPTION
            "The value of this object provides the Major Low alarm value
                   of the TEC Temperature Analog parameter. This value is a floating
             point number that is represented as an IEEE 32 bit number."
            ::= { gx2OA100BDAnalogEntry 60}

      oa100bdminorHighAuxTECTemp          OBJECT-TYPE
            SYNTAX           Float
            ACCESS           read-only
            STATUS           mandatory
            DESCRIPTION
            "The value of this object provides the Minor High alarm value
                   of the TEC Temperature Analog parameter. This value is a floating
             point number that is represented as an IEEE 32 bit number."
            ::= { gx2OA100BDAnalogEntry 61}

      oa100bdminorLowAuxTECTemp           OBJECT-TYPE
            SYNTAX           Float
            ACCESS           read-only
            STATUS           mandatory
            DESCRIPTION
            "The value of this object provides the Minor Low alarm value
                   of the TEC Temperature Analog parameter. This value is a floating
             point number that is represented as an IEEE 32 bit number."
            ::= { gx2OA100BDAnalogEntry 62}

      oa100bdcurrentValueAuxTECTemp       OBJECT-TYPE
            SYNTAX           Float
            ACCESS           read-only
            STATUS           mandatory
            DESCRIPTION
            "The value of this object provides the Current value
                   of the TEC Temperature Analog parameter. This value is a floating
             point number that is represented as an IEEE 32 bit number."
            ::= { gx2OA100BDAnalogEntry 63}

      oa100bdstateFlagAuxTECTemp          OBJECT-TYPE
            SYNTAX           INTEGER
                        {
                        hidden(1),
                        read-only(2),
                        updateable(3)
                        }
            ACCESS           read-only
            STATUS           mandatory
            DESCRIPTION
            "The value of this object provides the state
             of the TEC Temperature Analog parameter. (0-Hidden
                   1-Read-Only, 2-Updateable)."
            ::= { gx2OA100BDAnalogEntry 64}

      oa100bdminValueAuxTECTemp           OBJECT-TYPE
            SYNTAX           Float
            ACCESS           read-only
            STATUS           mandatory
            DESCRIPTION
            "The value of this object provides the minimum value
                   of the TEC Temperature Analog parameter. This value is a floating
             point number that is represented as an IEEE 32 bit number."
            ::= { gx2OA100BDAnalogEntry 65}

      oa100bdmaxValueAuxTECTemp           OBJECT-TYPE
            SYNTAX           Float
            ACCESS           read-only
            STATUS           mandatory
            DESCRIPTION
            "The value of this object provides the maximum value
                   of the TEC Temperature Analog parameter. This value is a floating
             point number that is represented as an IEEE 32 bit number."
            ::= { gx2OA100BDAnalogEntry 66}

      oa100bdalarmStateAuxTECTemp         OBJECT-TYPE
            SYNTAX           INTEGER
                           {
                           noAlarm(1),
                           majorLowAlarm(2),
                           minorLowAlarm(3),
                           minorHighAlarm(4),
                           majorHighAlarm(5),
                           informational(6)
                           }
            ACCESS           read-only
            STATUS           mandatory
            DESCRIPTION
            "The value of this object provides the curent alarm state of
             the TEC Temperature Analog parameter."
            ::= { gx2OA100BDAnalogEntry 67}

-- // New Parameter - Aux Laser Power

      oa100bdlabelAuxLaserPower              OBJECT-TYPE
            SYNTAX           DisplayString (SIZE (0..80))
            ACCESS           read-only
            STATUS           optional
            DESCRIPTION
            "The value of this object provides the label of the
             Aux Laser Power Analog parameter."
            ::= { gx2OA100BDAnalogEntry 68}

      oa100bduomAuxLaserPower                OBJECT-TYPE
            SYNTAX           DisplayString (SIZE (0..80))
            ACCESS           read-only
            STATUS           optional
            DESCRIPTION
            "The value of this object provides the Unit of Measure of the
             Aux Laser Power Analog parameter."
            ::= { gx2OA100BDAnalogEntry 69}

      oa100bdmajorHighAuxLaserPower          OBJECT-TYPE
            SYNTAX           Float
            ACCESS           read-only
            STATUS           mandatory
            DESCRIPTION
            "The value of this object provides the Major High alarm value
             of the Aux Laser Power Analog parameter. This value is a floating
             point number that is represented as an IEEE 32 bit number."
            ::= { gx2OA100BDAnalogEntry 70}


      oa100bdmajorLowAuxLaserPower           OBJECT-TYPE
            SYNTAX           Float
            ACCESS           read-only
            STATUS           mandatory
            DESCRIPTION
            "The value of this object provides the Major Low alarm value
             of the Aux Laser Power Analog parameter. This value is a floating
             point number that is represented as an IEEE 32 bit number."
            ::= { gx2OA100BDAnalogEntry 71}

      oa100bdminorHighAuxLaserPower          OBJECT-TYPE
            SYNTAX           Float
            ACCESS           read-only
            STATUS           mandatory
            DESCRIPTION
            "The value of this object provides the Minor High alarm value
             of the Aux Laser Power Analog parameter. This value is a floating
             point number that is represented as an IEEE 32 bit number."
            ::= { gx2OA100BDAnalogEntry 72}

      oa100bdminorLowAuxLaserPower           OBJECT-TYPE
            SYNTAX           Float
            ACCESS           read-only
            STATUS           mandatory
            DESCRIPTION
            "The value of this object provides the Minor Low alarm value
             of the Aux Laser Power Analog parameter. This value is a floating
             point number that is represented as an IEEE 32 bit number."
            ::= { gx2OA100BDAnalogEntry 73}

      oa100bdcurrentValueAuxLaserPower       OBJECT-TYPE
            SYNTAX           Float
            ACCESS           read-only
            STATUS           mandatory
            DESCRIPTION
            "The value of this object provides the Current value
             of the Aux Laser Power Analog parameter. This value is a floating
             point number that is represented as an IEEE 32 bit number."
            ::= { gx2OA100BDAnalogEntry 74}

      oa100bdstateFlagAuxLaserPower          OBJECT-TYPE
            SYNTAX           INTEGER
                        {
                        hidden(1),
                        read-only(2),
                        updateable(3)
                        }
            ACCESS           read-only
            STATUS           mandatory
            DESCRIPTION
            "The value of this object provides the state
             of the Aux Laser Power Analog parameter. (0-Hidden
                   1-Read-Only, 2-Updateable)."
            ::= { gx2OA100BDAnalogEntry 75}

      oa100bdminValueAuxLaserPower           OBJECT-TYPE
            SYNTAX           Float
            ACCESS           read-only
            STATUS           mandatory
            DESCRIPTION
            "The value of this object provides the minimum value
             of the Aux Laser Power Analog parameter. This value is a floating
             point number that is represented as an IEEE 32 bit number."
            ::= { gx2OA100BDAnalogEntry 76}

      oa100bdmaxValueAuxLaserPower           OBJECT-TYPE
            SYNTAX           Float
            ACCESS           read-only
            STATUS           mandatory
            DESCRIPTION
            "The value of this object provides the maximum value
             of the Aux Laser Power Analog parameter. This value is a floating
             point number that is represented as an IEEE 32 bit number."
            ::= { gx2OA100BDAnalogEntry 77}

      oa100bdalarmStateAuxLaserPower         OBJECT-TYPE
            SYNTAX           INTEGER
                           {
                           noAlarm(1),
                           majorLowAlarm(2),
                           minorLowAlarm(3),
                           minorHighAlarm(4),
                           majorHighAlarm(5),
                           informational(6)
                           }
            ACCESS           read-only
            STATUS           mandatory
            DESCRIPTION
            "The value of this object provides the curent alarm state of
             the Aux Laser Power Analog parameter."
            ::= { gx2OA100BDAnalogEntry 78}


-- // New Parameter - Fan Current

      oa100bdlabelFanCurrent           OBJECT-TYPE
			   SYNTAX           DisplayString (SIZE (0..80))
			   ACCESS           read-only
			   STATUS           optional
			   DESCRIPTION
			   "The value of this object provides the label of the
			    Fan Current Analog parameter."
            ::= { gx2OA100BDAnalogEntry 79}

      oa100bduomFanCurrent             OBJECT-TYPE
			   SYNTAX           DisplayString (SIZE (0..80))
			   ACCESS           read-only
			   STATUS           optional
			   DESCRIPTION
			   "The value of this object provides the Unit of Measure of the
			    Fan Current Analog parameter."
            ::= { gx2OA100BDAnalogEntry 80}

      oa100bdmajorHighFanCurrent       OBJECT-TYPE
			   SYNTAX           Float
			   ACCESS           read-only
			   STATUS           mandatory
			   DESCRIPTION
			   "The value of this object provides the Major High alarm value
			          of the Fan Current Analog parameter. This value is a floating
			    point number that is represented as an IEEE 32 bit number."
            ::= { gx2OA100BDAnalogEntry 81}


      oa100bdmajorLowFanCurrent        OBJECT-TYPE
			   SYNTAX           Float
			   ACCESS           read-only
			   STATUS           mandatory
			   DESCRIPTION
			   "The value of this object provides the Major Low alarm value
			          of the Fan Current Analog parameter. This value is a floating
			    point number that is represented as an IEEE 32 bit number."
            ::= { gx2OA100BDAnalogEntry 82}

      oa100bdminorHighFanCurrent       OBJECT-TYPE
			   SYNTAX           Float
			   ACCESS           read-only
			   STATUS           mandatory
			   DESCRIPTION
			   "The value of this object provides the Minor High alarm value
			          of the Fan Current Analog parameter. This value is a floating
			    point number that is represented as an IEEE 32 bit number."
            ::= { gx2OA100BDAnalogEntry 83}

      oa100bdminorLowFanCurrent        OBJECT-TYPE
			   SYNTAX           Float
			   ACCESS           read-only
			   STATUS           mandatory
			   DESCRIPTION
			   "The value of this object provides the Minor Low alarm value
			          of the Fan Current Analog parameter. This value is a floating
			    point number that is represented as an IEEE 32 bit number."
            ::= { gx2OA100BDAnalogEntry 84}

      oa100bdcurrentValueFanCurrent    OBJECT-TYPE
			   SYNTAX           Float
			   ACCESS           read-only
			   STATUS           mandatory
			   DESCRIPTION
			   "The value of this object provides the Current value
			          of the Fan Current Analog parameter. This value is a floating
			    point number that is represented as an IEEE 32 bit number."
            ::= { gx2OA100BDAnalogEntry 85}

      oa100bdstateFlagFanCurrent       OBJECT-TYPE
			   SYNTAX           INTEGER
								{
								hidden(1),
								read-only(2),
								updateable(3)
								}

			   ACCESS           read-only
			   STATUS           mandatory
			   DESCRIPTION
			   "The value of this object provides the state
			    of the Fan Current Analog parameter. (0-Hidden
			          1-Read-Only, 2-Updateable)."
            ::= { gx2OA100BDAnalogEntry 86}

      oa100bdminValueFanCurrent        OBJECT-TYPE
			   SYNTAX           Float
			   ACCESS           read-only
			   STATUS           mandatory
			   DESCRIPTION
			   "The value of this object provides the minimum value
			          of the Fan Current Analog parameter. This value is a floating
			    point number that is represented as an IEEE 32 bit number."
            ::= { gx2OA100BDAnalogEntry 87}

      oa100bdmaxValueFanCurrent        OBJECT-TYPE
			   SYNTAX           Float
			   ACCESS           read-only
			   STATUS           mandatory
			   DESCRIPTION
			   "The value of this object provides the maximum value
			          of the Fan Current Analog parameter. This value is a floating
			    point number that is represented as an IEEE 32 bit number."
            ::= { gx2OA100BDAnalogEntry 88}

      oa100bdalarmStateFanCurrent      OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Fan Current Analog parameter."
            ::= { gx2OA100BDAnalogEntry 89}

-- // New Parameter - Output Power Setting

      oa100bdlabelOPSetting               OBJECT-TYPE
			   SYNTAX           DisplayString (SIZE (0..80))
			   ACCESS           read-only
			   STATUS           optional
			   DESCRIPTION
			   "The value of this object provides the label of the
			    Output Power Setting Analog parameter."
            ::= { gx2OA100BDAnalogEntry 90}

      oa100bduomOPSetting                 OBJECT-TYPE
			   SYNTAX           DisplayString (SIZE (0..80))
			   ACCESS           read-only
			   STATUS           optional
			   DESCRIPTION
			   "The value of this object provides the Unit of Measure of the
			    12v Current Analog parameter."
            ::= { gx2OA100BDAnalogEntry 91}

      oa100bdmajorHighOPSetting           OBJECT-TYPE
			   SYNTAX           Float
			   ACCESS           read-only
			   STATUS           mandatory
			   DESCRIPTION
			   "The value of this object provides the Major High alarm value
			          of the Output Power Setting Analog parameter. This value is a floating
			    point number that is represented as an IEEE 32 bit number."
            ::= { gx2OA100BDAnalogEntry 92}


      oa100bdmajorLowOPSetting            OBJECT-TYPE
			   SYNTAX           Float
			   ACCESS           read-only
			   STATUS           mandatory
			   DESCRIPTION
			   "The value of this object provides the Major Low alarm value
			          of the Output Power Setting Analog parameter. This value is a floating
			    point number that is represented as an IEEE 32 bit number."
            ::= { gx2OA100BDAnalogEntry 93}

      oa100bdminorHighOPSetting           OBJECT-TYPE
			   SYNTAX           Float
			   ACCESS           read-only
			   STATUS           mandatory
			   DESCRIPTION
			   "The value of this object provides the Minor High alarm value
			          of the Output Power Setting Analog parameter. This value is a floating
			    point number that is represented as an IEEE 32 bit number."
            ::= { gx2OA100BDAnalogEntry 94}

      oa100bdminorLowOPSetting            OBJECT-TYPE
			   SYNTAX           Float
			   ACCESS           read-only
			   STATUS           mandatory
			   DESCRIPTION
			   "The value of this object provides the Minor Low alarm value
			          of the Output Power Setting Analog parameter. This value is a floating
			    point number that is represented as an IEEE 32 bit number."
            ::= { gx2OA100BDAnalogEntry 95}

      oa100bdcurrentValueOPSetting        OBJECT-TYPE
			   SYNTAX           Float
			   ACCESS           read-write
			   STATUS           mandatory
			   DESCRIPTION
			   "The value of this object provides the Current value
			          of the Output Power Setting Analog parameter. This value is a floating
			    point number that is represented as an IEEE 32 bit number."
            ::= { gx2OA100BDAnalogEntry 96}

      oa100bdstateFlagOPSetting           OBJECT-TYPE
			   SYNTAX           INTEGER
								{
								hidden(1),
								read-only(2),
								updateable(3)
								}
			   ACCESS           read-only
			   STATUS           mandatory
			   DESCRIPTION
			   "The value of this object provides the state
			    of the Output Power Setting Analog parameter. (0-Hidden
			          1-Read-Only, 2-Updateable)."
            ::= { gx2OA100BDAnalogEntry 97}

      oa100bdminValueOPSetting            OBJECT-TYPE
			   SYNTAX           Float
			   ACCESS           read-only
			   STATUS           mandatory
			   DESCRIPTION
			   "The value of this object provides the minimum value
			          of the Output Power Setting Analog parameter. This value is a floating
			    point number that is represented as an IEEE 32 bit number."
            ::= { gx2OA100BDAnalogEntry 98}

      oa100bdmaxValueOPSetting            OBJECT-TYPE
			   SYNTAX           Float
			   ACCESS           read-only
			   STATUS           mandatory
			   DESCRIPTION
			   "The value of this object provides the maximum value
			          of the Output Power Setting Analog parameter. This value is a floating
			    point number that is represented as an IEEE 32 bit number."
            ::= { gx2OA100BDAnalogEntry 99}

      oa100bdalarmStateOPSetting          OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Output Power Setting Analog parameter."
            ::= { gx2OA100BDAnalogEntry 100}

-- // New Parameter - Laser Power Setting

      oa100bdlabelLPSetting               OBJECT-TYPE
			   SYNTAX           DisplayString (SIZE (0..80))
			   ACCESS           read-only
			   STATUS           optional
			   DESCRIPTION
			   "The value of this object provides the label of the
			    Laser Power Setting Analog parameter."
            ::= { gx2OA100BDAnalogEntry 101}

      oa100bduomLPSetting                 OBJECT-TYPE
			   SYNTAX           DisplayString (SIZE (0..80))
			   ACCESS           read-only
			   STATUS           optional
			   DESCRIPTION
			   "The value of this object provides the Unit of Measure of the
			    Laser Power Setting Analog parameter."
            ::= { gx2OA100BDAnalogEntry 102}

      oa100bdmajorHighLPSetting           OBJECT-TYPE
			   SYNTAX           Float
			   ACCESS           read-only
			   STATUS           mandatory
			   DESCRIPTION
			   "The value of this object provides the Major High alarm value
			          of the Laser Power Setting Analog parameter. This value is a floating
			    point number that is represented as an IEEE 32 bit number."
            ::= { gx2OA100BDAnalogEntry 103}


      oa100bdmajorLowLPSetting            OBJECT-TYPE
			   SYNTAX           Float
			   ACCESS           read-only
			   STATUS           mandatory
			   DESCRIPTION
			   "The value of this object provides the Major Low alarm value
			          of the Laser Power Setting Analog parameter. This value is a floating
			    point number that is represented as an IEEE 32 bit number."
            ::= { gx2OA100BDAnalogEntry 104}

      oa100bdminorHighLPSetting           OBJECT-TYPE
			   SYNTAX           Float
			   ACCESS           read-only
			   STATUS           mandatory
			   DESCRIPTION
			   "The value of this object provides the Minor High alarm value
			          of the Laser Power Setting Analog parameter. This value is a floating
			    point number that is represented as an IEEE 32 bit number."
            ::= { gx2OA100BDAnalogEntry 105}

      oa100bdminorLowLPSetting            OBJECT-TYPE
			   SYNTAX           Float
			   ACCESS           read-only
			   STATUS           mandatory
			   DESCRIPTION
			   "The value of this object provides the Minor Low alarm value
			          of the Laser Power Setting Analog parameter. This value is a floating
			    point number that is represented as an IEEE 32 bit number."
            ::= { gx2OA100BDAnalogEntry 106}

      oa100bdcurrentValueLPSetting        OBJECT-TYPE
			   SYNTAX           Float
			   ACCESS           read-write
			   STATUS           mandatory
			   DESCRIPTION
			   "The value of this object provides the Current value
			          of the Laser Power Setting Analog parameter. This value is a floating
			    point number that is represented as an IEEE 32 bit number."
            ::= { gx2OA100BDAnalogEntry 107}

      oa100bdstateFlagLPSetting           OBJECT-TYPE
			   SYNTAX           INTEGER
								{
								hidden(1),
								read-only(2),
								updateable(3)
								}
			   ACCESS           read-only
			   STATUS           mandatory
			   DESCRIPTION
			   "The value of this object provides the state
			    of the Laser Power Setting Analog parameter. (0-Hidden
			          1-Read-Only, 2-Updateable)."
            ::= { gx2OA100BDAnalogEntry 108}

      oa100bdminValueLPSetting            OBJECT-TYPE
			   SYNTAX           Float
			   ACCESS           read-only
			   STATUS           mandatory
			   DESCRIPTION
			   "The value of this object provides the minimum value
			          of the Laser Power Setting Analog parameter. This value is a floating
			    point number that is represented as an IEEE 32 bit number."
            ::= { gx2OA100BDAnalogEntry 109}

      oa100bdmaxValueLPSetting            OBJECT-TYPE
			   SYNTAX           Float
			   ACCESS           read-only
			   STATUS           mandatory
			   DESCRIPTION
			   "The value of this object provides the maximum value
			          of the Laser Power Setting Analog parameter. This value is a floating
			    point number that is represented as an IEEE 32 bit number."
            ::= { gx2OA100BDAnalogEntry 110}

      oa100bdalarmStateLPSetting          OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Laser Power Setting Analog parameter."
            ::= { gx2OA100BDAnalogEntry 111}

-- // New Parameter - Constant Gain Setting

      oa100bdlabelCGSetting               OBJECT-TYPE
			   SYNTAX           DisplayString (SIZE (0..80))
			   ACCESS           read-only
			   STATUS           optional
			   DESCRIPTION
			   "The value of this object provides the label of the
			    Constant Gain Setting Analog parameter."
            ::= { gx2OA100BDAnalogEntry 112}

      oa100bduomCGSetting                 OBJECT-TYPE
			   SYNTAX           DisplayString (SIZE (0..80))
			   ACCESS           read-only
			   STATUS           optional
			   DESCRIPTION
			   "The value of this object provides the Unit of Measure of the
			    Constant Gain Setting Analog parameter."
            ::= { gx2OA100BDAnalogEntry 113}

      oa100bdmajorHighCGSetting           OBJECT-TYPE
			   SYNTAX           Float
			   ACCESS           read-only
			   STATUS           mandatory
			   DESCRIPTION
			   "The value of this object provides the Major High alarm value
			          of the Constant Gain Setting Analog parameter. This value is a floating
			    point number that is represented as an IEEE 32 bit number."
            ::= { gx2OA100BDAnalogEntry 114}


      oa100bdmajorLowCGSetting            OBJECT-TYPE
			   SYNTAX           Float
			   ACCESS           read-only
			   STATUS           mandatory
			   DESCRIPTION
			   "The value of this object provides the Major Low alarm value
			          of the Constant Gain Setting Analog parameter. This value is a floating
			    point number that is represented as an IEEE 32 bit number."
            ::= { gx2OA100BDAnalogEntry 115}

      oa100bdminorHighCGSetting           OBJECT-TYPE
			   SYNTAX           Float
			   ACCESS           read-only
			   STATUS           mandatory
			   DESCRIPTION
			   "The value of this object provides the Minor High alarm value
			          of the Constant Gain Setting Analog parameter. This value is a floating
			    point number that is represented as an IEEE 32 bit number."
            ::= { gx2OA100BDAnalogEntry 116}

      oa100bdminorLowCGSetting            OBJECT-TYPE
			   SYNTAX           Float
			   ACCESS           read-only
			   STATUS           mandatory
			   DESCRIPTION
			   "The value of this object provides the Minor Low alarm value
			          of the Constant Gain Setting Analog parameter. This value is a floating
			    point number that is represented as an IEEE 32 bit number."
            ::= { gx2OA100BDAnalogEntry 117}

      oa100bdcurrentValueCGSetting        OBJECT-TYPE
			   SYNTAX           Float
			   ACCESS           read-write
			   STATUS           mandatory
			   DESCRIPTION
			   "The value of this object provides the Current value
			          of the Constant Gain Setting Analog parameter. This value is a floating
			    point number that is represented as an IEEE 32 bit number."
            ::= { gx2OA100BDAnalogEntry 118}

      oa100bdstateFlagCGSetting           OBJECT-TYPE
			   SYNTAX           INTEGER
								{
								hidden(1),
								read-only(2),
								updateable(3)
								}
			   ACCESS           read-only
			   STATUS           mandatory
			   DESCRIPTION
			   "The value of this object provides the state
			    of the Constant Gain Setting Analog parameter. (0-Hidden
			          1-Read-Only, 2-Updateable)."
            ::= { gx2OA100BDAnalogEntry 119}

      oa100bdminValueCGSetting            OBJECT-TYPE
			   SYNTAX           Float
			   ACCESS           read-only
			   STATUS           mandatory
			   DESCRIPTION
			   "The value of this object provides the minimum value
			          of the Constant Gain Setting Analog parameter. This value is a floating
			    point number that is represented as an IEEE 32 bit number."
            ::= { gx2OA100BDAnalogEntry 120}

      oa100bdmaxValueCGSetting            OBJECT-TYPE
			   SYNTAX           Float
			   ACCESS           read-only
			   STATUS           mandatory
			   DESCRIPTION
			   "The value of this object provides the maximum value
			          of the Constant Gain Setting Analog parameter. This value is a floating
			    point number that is represented as an IEEE 32 bit number."
            ::= { gx2OA100BDAnalogEntry 121}

      oa100bdalarmStateCGSetting          OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Constant Gain Setting Analog parameter."
            ::= { gx2OA100BDAnalogEntry 122}

-- // New Parameter - Optical Input Threshold

      oa100bdlabelOptThreshold               OBJECT-TYPE
			   SYNTAX           DisplayString (SIZE (0..80))
			   ACCESS           read-only
			   STATUS           optional
			   DESCRIPTION
			   "The value of this object provides the label of the
			    Optical Input Threshold Analog parameter."
            ::= { gx2OA100BDAnalogEntry 123}

      oa100bduomOptThreshold                 OBJECT-TYPE
			   SYNTAX           DisplayString (SIZE (0..80))
			   ACCESS           read-only
			   STATUS           optional
			   DESCRIPTION
			   "The value of this object provides the Unit of Measure of the
			    Optical Input Threshold Analog parameter."
            ::= { gx2OA100BDAnalogEntry 124}

      oa100bdmajorHighOptThreshold           OBJECT-TYPE
			   SYNTAX           Float
			   ACCESS           read-only
			   STATUS           mandatory
			   DESCRIPTION
			   "The value of this object provides the Major High alarm value
			          of the Optical Input Threshold Analog parameter. This value is a floating
			    point number that is represented as an IEEE 32 bit number."
            ::= { gx2OA100BDAnalogEntry 125}


      oa100bdmajorLowOptThreshold            OBJECT-TYPE
			   SYNTAX           Float
			   ACCESS           read-only
			   STATUS           mandatory
			   DESCRIPTION
			   "The value of this object provides the Major Low alarm value
			          of the Optical Input Threshold Analog parameter. This value is a floating
			    point number that is represented as an IEEE 32 bit number."
            ::= { gx2OA100BDAnalogEntry 126}

      oa100bdminorHighOptThreshold           OBJECT-TYPE
			   SYNTAX           Float
			   ACCESS           read-only
			   STATUS           mandatory
			   DESCRIPTION
			   "The value of this object provides the Minor High alarm value
			          of the Optical Input Threshold Analog parameter. This value is a floating
			    point number that is represented as an IEEE 32 bit number."
            ::= { gx2OA100BDAnalogEntry 127}

      oa100bdminorLowOptThreshold            OBJECT-TYPE
			   SYNTAX           Float
			   ACCESS           read-only
			   STATUS           mandatory
			   DESCRIPTION
			   "The value of this object provides the Minor Low alarm value
			          of the Optical Input Threshold Analog parameter. This value is a floating
			    point number that is represented as an IEEE 32 bit number."
            ::= { gx2OA100BDAnalogEntry 128}

      oa100bdcurrentValueOptThreshold        OBJECT-TYPE
			   SYNTAX           Float
			   ACCESS           read-write
			   STATUS           mandatory
			   DESCRIPTION
			   "The value of this object provides the Current value
			          of the Optical Input Threshold Analog parameter. This value is a floating
			    point number that is represented as an IEEE 32 bit number."
            ::= { gx2OA100BDAnalogEntry 129}

      oa100bdstateFlagOptThreshold           OBJECT-TYPE
			   SYNTAX           INTEGER
								{
								hidden(1),
								read-only(2),
								updateable(3)
								}
			   ACCESS           read-only
			   STATUS           mandatory
			   DESCRIPTION
			   "The value of this object provides the state
			    of the Optical Input Threshold Analog parameter. (0-Hidden
			          1-Read-Only, 2-Updateable)."
            ::= { gx2OA100BDAnalogEntry 130}

      oa100bdminValueOptThreshold            OBJECT-TYPE
			   SYNTAX           Float
			   ACCESS           read-only
			   STATUS           mandatory
			   DESCRIPTION
			   "The value of this object provides the minimum value
			          of the Optical Input Threshold Analog parameter. This value is a floating
			    point number that is represented as an IEEE 32 bit number."
            ::= { gx2OA100BDAnalogEntry 131}

      oa100bdmaxValueOptThreshold            OBJECT-TYPE
			   SYNTAX           Float
			   ACCESS           read-only
			   STATUS           mandatory
			   DESCRIPTION
			   "The value of this object provides the maximum value
			          of the Optical Input Threshold Analog parameter. This value is a floating
			    point number that is represented as an IEEE 32 bit number."
            ::= { gx2OA100BDAnalogEntry 132}

      oa100bdalarmStateOptThreshold          OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Optical Input Threshold Analog parameter."
            ::= { gx2OA100BDAnalogEntry 133}


-- // Section: Digital parameter detail

      gx2OA100BDDigitalTableIndex              OBJECT-TYPE
			   SYNTAX           INTEGER (1..4294967295)
			   ACCESS           read-only
			   STATUS           mandatory
			   DESCRIPTION
			   "The value of this object identifies the network
			    element. This index is equal to the
			    hfcCommonTableIndex for the same element."
            ::= { gx2OA100BDDigitalEntry 1}

-- // New parameter - Mode Setting
      oa100bdlabelModeSetting             OBJECT-TYPE
			   SYNTAX         	DisplayString (SIZE (0..80))
			   ACCESS           	read-only
			   STATUS           	optional
			   DESCRIPTION
			   "The value of this object provides the label of the
             OA100BD's Mode Digital parameter."
            ::= { gx2OA100BDDigitalEntry 2}

      oa100bdenumModeSetting              OBJECT-TYPE
			   SYNTAX         	DisplayString (SIZE (0..80))
			   ACCESS           	read-only
			   STATUS           	optional
			   DESCRIPTION
			   "The value of this object represents the Enumeration values
			    possible for the Digital parameter. Each Enumerated values is
			    separated by a common. The first value has a enumerated value of 0."
            ::= { gx2OA100BDDigitalEntry 3}

      oa100bdvalueModeSetting             OBJECT-TYPE
			   SYNTAX       		INTEGER
					    		{
							power-out-preset(1),
							power-out-set(2),
							laser-power-preset(3),
							laser-power-set(4),
							constant-gain-preset(5),
							constant-gain-set(6),
							invalid-mode(7)
					    		}

			   ACCESS           	read-write
			   STATUS           	mandatory
			   DESCRIPTION
			   "The value of this object is the current value of the parameter. It is an integer
                      value from 0 to 5 representing the operation mode of the module."
            ::= { gx2OA100BDDigitalEntry 4}

      oa100bdstateFlagModeSetting         OBJECT-TYPE
			   SYNTAX         	INTEGER
								{
								hidden(1),
								read-only(2),
								updateable(3)
								}
			   ACCESS           	read-only
			   STATUS           	mandatory
			   DESCRIPTION
			   "The value of this object provides the state
			    of the the parameter. (0-Hidden 1-Read-Only, 2-Updateable)."
            ::= { gx2OA100BDDigitalEntry 5}

-- // New parameter - Module State
      oa100bdlabelModuleState           OBJECT-TYPE
			   SYNTAX       		DisplayString (SIZE (0..80))
			   ACCESS           	read-only
			   STATUS           	optional
			   DESCRIPTION
			   "The value of this object provides the label of the
			    Module State Digital parameter."
            ::= { gx2OA100BDDigitalEntry 6}

      oa100bdenumModuleState           OBJECT-TYPE
			   SYNTAX       		DisplayString (SIZE (0..80))
			   ACCESS           	read-only
			   STATUS           	optional
			   DESCRIPTION
			   "The value of this object represents the Enumeration values
			    possible for the Digital parameter. Each Enumerated values is
			    separated by a common. The first value has a enumerated value of 1."
            ::= { gx2OA100BDDigitalEntry 7}

      oa100bdvalueModuleState          OBJECT-TYPE
			   SYNTAX       		INTEGER
					    		{
							off(1),
							on(2)
					    		}
			   ACCESS           	read-write
			   STATUS           	mandatory
			   DESCRIPTION
			   "The value of this object is the current value of the parameter."
            ::= { gx2OA100BDDigitalEntry 8}

      oa100bdstateFlagModuleState      OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
            ::= { gx2OA100BDDigitalEntry 9}

-- // New parameter - Factory Default
      oa100bdlabelFactoryDefault           OBJECT-TYPE
			   SYNTAX       		DisplayString (SIZE (0..80))
			   ACCESS           	read-only
			   STATUS           	optional
			   DESCRIPTION
			   "The value of this object provides the label of the
			    Factory Default Reset Digital parameter."
            ::= { gx2OA100BDDigitalEntry 10}

      oa100bdenumFactoryDefault           OBJECT-TYPE
			   SYNTAX       		DisplayString (SIZE (0..80))
			   ACCESS           	read-only
			   STATUS           	optional
			   DESCRIPTION
			   "The value of this object represents the Enumeration values
			    possible for the Digital parameter. Each Enumerated values is
			    separated by a common. The first value has a enumerated value of 1."
            ::= { gx2OA100BDDigitalEntry 11}

      oa100bdvalueFactoryDefault          OBJECT-TYPE
			   SYNTAX       		INTEGER
					    		{
							off(1),
							on(2)
					    		}
			   ACCESS           	read-write
			   STATUS           	mandatory
			   DESCRIPTION
			   "The value of this object is the current value of the parameter."
            ::= { gx2OA100BDDigitalEntry 12}

      oa100bdstateFlagFactoryDefault      OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
            ::= { gx2OA100BDDigitalEntry 13}

-- // Section: Status parameter detail

      gx2OA100BDStatusTableIndex              OBJECT-TYPE
			   SYNTAX           INTEGER (1..4294967295)
			   ACCESS           read-only
			   STATUS           mandatory
			   DESCRIPTION
			   "The value of this object identifies the network
			    element. This index is equal to the
			    hfcCommonTableIndex for the same element."
            ::= { gx2OA100BDStatusEntry 1}

-- // New Parameter - Boot status
      oa100bdlabelBoot                 OBJECT-TYPE
			   SYNTAX       		DisplayString (SIZE (0..80))
			   ACCESS           	read-only
			   STATUS           	optional
			   DESCRIPTION
			   "The value of this object provides the label of the
			    Boot Status  Status parameter."
            ::= { gx2OA100BDStatusEntry 2}

      oa100bdvalueBoot                    OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (0-Ok, 1-Undetermined
			    2-Warning, 3-Minor, 4-Major, 5-Critical)."
            ::= { gx2OA100BDStatusEntry 3}

      oa100bdstateflagBoot       OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
            ::= { gx2OA100BDStatusEntry 4}


-- // New Parameter - Flash status
      oa100bdlabelFlash                OBJECT-TYPE
			   SYNTAX       		DisplayString (SIZE (0..80))
			   ACCESS           	read-only
			   STATUS           	optional
			   DESCRIPTION
			   "The value of this object provides the label of the
			    Flash Status  Status parameter."
            ::= { gx2OA100BDStatusEntry 5}

      oa100bdvalueFlash                OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (0-Ok, 1-Undetermined
			    2-Warning, 3-Minor, 4-Major, 5-Critical)."
            ::= { gx2OA100BDStatusEntry 6}

      oa100bdstateflagFlash      OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
            ::= { gx2OA100BDStatusEntry 7}


-- // New Parameter - Factory Data CRC status
      oa100bdlabelFactoryDataCRC           OBJECT-TYPE
			   SYNTAX       		DisplayString (SIZE (0..80))
			   ACCESS           	read-only
			   STATUS           	optional
			   DESCRIPTION
			   "The value of this object provides the label of the
			    Factory Data CRC Status parameter."
            ::= { gx2OA100BDStatusEntry 8}

      oa100bdvalueFactoryDataCRC             OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (0-Ok, 1-Undetermined
			    2-Warning, 3-Minor, 4-Major, 5-Critical)."
            ::= { gx2OA100BDStatusEntry 9}

      oa100bdstateflagFactoryDataCRC      OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
            ::= { gx2OA100BDStatusEntry 10}


-- // New Parameter - Alarm Data CRC status
      oa100bdlabelAlarmDataCRC             OBJECT-TYPE
			   SYNTAX       		DisplayString (SIZE (0..80))
			   ACCESS           	read-only
			   STATUS           	optional
			   DESCRIPTION
			   "The value of this object provides the label of the
			    Alarm Data CRC Status parameter."
            ::= { gx2OA100BDStatusEntry 11}

      oa100bdvalueAlarmDataCRC            OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (0-Ok, 1-Undetermined
			    2-Warning, 3-Minor, 4-Major, 5-Critical)."
            ::= { gx2OA100BDStatusEntry 12}

      oa100bdstateflagAlarmDataCRC        OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
            ::= { gx2OA100BDStatusEntry 13}


-- // New Parameter - Calibration Data CRC status
      oa100bdlabelCalibrationDataCRC       OBJECT-TYPE
			   SYNTAX       		DisplayString (SIZE (0..80))
			   ACCESS           	read-only
			   STATUS           	optional
			   DESCRIPTION
			   "The value of this object provides the label of the
			    Calibration Data CRC Status parameter."
            ::= { gx2OA100BDStatusEntry 14}

      oa100bdvalueCalibrationDataCRC         OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (0-Ok, 1-Undetermined
			    2-Warning, 3-Minor, 4-Major, 5-Critical)."
            ::= { gx2OA100BDStatusEntry 15}

      oa100bdstateflagCalibrationDataCRC        OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
            ::= { gx2OA100BDStatusEntry 16}


-- // New Parameter - Optical power in shutdown status
      oa100bdlabelOptInShutdown       OBJECT-TYPE
			   SYNTAX       		DisplayString (SIZE (0..80))
			   ACCESS           	read-only
			   STATUS           	optional
			   DESCRIPTION
			   "The value of this object provides the label of the
			    Optical Input Power Shutdown Status parameter."
            ::= { gx2OA100BDStatusEntry 17}

      oa100bdvalueOptInShutdown        OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (0-Ok, 1-Undetermined
			    2-Warning, 3-Minor, 4-Major, 5-Critical)."
            ::= { gx2OA100BDStatusEntry 18}

      oa100bdstateflagOptInShutdown       OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
            ::= { gx2OA100BDStatusEntry 19}

-- // New Parameter - Main TEC temperature in shutdown status
      oa100bdlabelMainTECTempShutdown       OBJECT-TYPE
			   SYNTAX       		DisplayString (SIZE (0..80))
			   ACCESS           	read-only
			   STATUS           	optional
			   DESCRIPTION
			   "The value of this object provides the label of the
             Main TEC Temperature Shutdown Status parameter."
            ::= { gx2OA100BDStatusEntry 20}

      oa100bdvalueMainTECTempShutdown        OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (0-Ok, 1-Undetermined
			    2-Warning, 3-Minor, 4-Major, 5-Critical)."
            ::= { gx2OA100BDStatusEntry 21}

      oa100bdstateflagMainTECTempShutdown       OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
            ::= { gx2OA100BDStatusEntry 22}

-- // New Parameter - Aux TEC temperature in shutdown status
      oa100bdlabelAuxTECTempShutdown       OBJECT-TYPE
            SYNTAX            DisplayString (SIZE (0..80))
            ACCESS            read-only
            STATUS            optional
            DESCRIPTION
            "The value of this object provides the label of the
             Aux TEC Temperature Shutdown Status parameter."
            ::= { gx2OA100BDStatusEntry 23}

      oa100bdvalueAuxTECTempShutdown         OBJECT-TYPE
            SYNTAX            INTEGER
                           {
                           ok(1),
                           undetermined(2),
                           warning(3),
                           minor(4),
                           major(5),
                           critical(6)
                           }
            ACCESS            read-only
            STATUS            mandatory
            DESCRIPTION
            "The value of this object provides the current state of
             the parameter (0-Ok, 1-Undetermined
             2-Warning, 3-Minor, 4-Major, 5-Critical)."
            ::= { gx2OA100BDStatusEntry 24}

      oa100bdstateflagAuxTECTempShutdown     OBJECT-TYPE
            SYNTAX            INTEGER
                        {
                        hidden(1),
                        read-only(2),
                        updateable(3)
                        }
            ACCESS            read-only
            STATUS            mandatory
            DESCRIPTION
            "The value of this object provides the state
             of the the parameter. (0-Hidden 1-Read-Only, 2-Updateable)."
            ::= { gx2OA100BDStatusEntry 25}


-- // New Parameter - Power Supply Failure status
      oa100bdlabelPowerFail       OBJECT-TYPE
			   SYNTAX       		DisplayString (SIZE (0..80))
			   ACCESS           	read-only
			   STATUS           	optional
			   DESCRIPTION
			   "The value of this object provides the label of the
			    Power Supply Fail Status parameter."
            ::= { gx2OA100BDStatusEntry 26}

      oa100bdvaluePowerFail         OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (0-Ok, 1-Undetermined
			    2-Warning, 3-Minor, 4-Major, 5-Critical)."
            ::= { gx2OA100BDStatusEntry 27}

      oa100bdstateflagPowerFail     OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
            ::= { gx2OA100BDStatusEntry 28}

-- // New Parameter - Key Switch status
      oa100bdlabelKeySwitch       OBJECT-TYPE
			   SYNTAX       		DisplayString (SIZE (0..80))
			   ACCESS           	read-only
			   STATUS           	optional
			   DESCRIPTION
			   "The value of this object provides the label of the
			    Key Switch Setting Status parameter."
            ::= { gx2OA100BDStatusEntry 29}

      oa100bdvalueKeySwitch         OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (0-Ok, 1-Undetermined
			    2-Warning, 3-Minor, 4-Major, 5-Critical)."
            ::= { gx2OA100BDStatusEntry 30}

      oa100bdstateflagKeySwitch     OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
            ::= { gx2OA100BDStatusEntry 31}

-- // New Parameter - Main Laser Current Shutdown status
      oa100bdlabelMainLaserCurrShutdown       OBJECT-TYPE
			   SYNTAX       		DisplayString (SIZE (0..80))
			   ACCESS           	read-only
			   STATUS           	optional
			   DESCRIPTION
			   "The value of this object provides the label of the
             Main Laser Current Shutdown Status parameter."
            ::= { gx2OA100BDStatusEntry 32}

      oa100bdvalueMainLaserCurrShutdown         OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (0-Ok, 1-Undetermined
			    2-Warning, 3-Minor, 4-Major, 5-Critical)."
            ::= { gx2OA100BDStatusEntry 33}

      oa100bdstateflagMainLaserCurrShutdown     OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
            ::= { gx2OA100BDStatusEntry 34}

-- // New Parameter - Aux Laser Current Shutdown status
      oa100bdlabelAuxLaserCurrShutdown       OBJECT-TYPE
            SYNTAX            DisplayString (SIZE (0..80))
            ACCESS            read-only
            STATUS            optional
            DESCRIPTION
            "The value of this object provides the label of the
             AuxLaser Current Shutdown Status parameter."
            ::= { gx2OA100BDStatusEntry 35}

      oa100bdvalueAuxLaserCurrShutdown       OBJECT-TYPE
            SYNTAX            INTEGER
                           {
                           ok(1),
                           undetermined(2),
                           warning(3),
                           minor(4),
                           major(5),
                           critical(6)
                           }
            ACCESS            read-only
            STATUS            mandatory
            DESCRIPTION
            "The value of this object provides the current state of
             the parameter (0-Ok, 1-Undetermined
             2-Warning, 3-Minor, 4-Major, 5-Critical)."
            ::= { gx2OA100BDStatusEntry 36}

      oa100bdstateflagAuxLaserCurrShutdown      OBJECT-TYPE
            SYNTAX            INTEGER
                        {
                        hidden(1),
                        read-only(2),
                        updateable(3)
                        }
            ACCESS            read-only
            STATUS            mandatory
            DESCRIPTION
            "The value of this object provides the state
             of the the parameter. (0-Hidden 1-Read-Only, 2-Updateable)."
            ::= { gx2OA100BDStatusEntry 37}


-- // New Parameter - Main Laser Power Shutdown
      oa100bdlabelMainLaserPowShutdown       OBJECT-TYPE
			   SYNTAX       		DisplayString (SIZE (0..80))
			   ACCESS           	read-only
			   STATUS           	optional
			   DESCRIPTION
			   "The value of this object provides the label of the
             Main Laser Power Shutdown Status parameter."
            ::= { gx2OA100BDStatusEntry 38}

      oa100bdvalueMainLaserPowShutdown       OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (0-Ok, 1-Undetermined
			    2-Warning, 3-Minor, 4-Major, 5-Critical)."
            ::= { gx2OA100BDStatusEntry 39}

      oa100bdstateflagMainLaserPowShutdown      OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
            ::= { gx2OA100BDStatusEntry 40}

-- // New Parameter - Aux Laser Power Shutdown
      oa100bdlabelAuxLaserPowShutdown       OBJECT-TYPE
            SYNTAX            DisplayString (SIZE (0..80))
            ACCESS            read-only
            STATUS            optional
            DESCRIPTION
            "The value of this object provides the label of the
             Aux Laser Power Shutdown Status parameter."
            ::= { gx2OA100BDStatusEntry 41}

      oa100bdvalueAuxLaserPowShutdown        OBJECT-TYPE
            SYNTAX            INTEGER
                           {
                           ok(1),
                           undetermined(2),
                           warning(3),
                           minor(4),
                           major(5),
                           critical(6)
                           }
            ACCESS            read-only
            STATUS            mandatory
            DESCRIPTION
            "The value of this object provides the current state of
             the parameter (0-Ok, 1-Undetermined
             2-Warning, 3-Minor, 4-Major, 5-Critical)."
            ::= { gx2OA100BDStatusEntry 42}

      oa100bdstateflagAuxLaserPowShutdown       OBJECT-TYPE
            SYNTAX            INTEGER
                        {
                        hidden(1),
                        read-only(2),
                        updateable(3)
                        }
            ACCESS            read-only
            STATUS            mandatory
            DESCRIPTION
            "The value of this object provides the state
             of the the parameter. (0-Hidden 1-Read-Only, 2-Updateable)."
            ::= { gx2OA100BDStatusEntry 43}


-- // New Parameter - ADC status
      oa100bdlabelADCStatus       OBJECT-TYPE
			   SYNTAX       		DisplayString (SIZE (0..80))
			   ACCESS           	read-only
			   STATUS           	optional
			   DESCRIPTION
			   "The value of this object provides the label of the
			    ADC Operation Status parameter."
            ::= { gx2OA100BDStatusEntry 44}

      oa100bdvalueADCStatus         OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (0-Ok, 1-Undetermined
			    2-Warning, 3-Minor, 4-Major, 5-Critical)."
            ::= { gx2OA100BDStatusEntry 45}

      oa100bdstateflagADCStatus     OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
            ::= { gx2OA100BDStatusEntry 46}

-- // New Parameter - Constant Gain status
      oa100bdlabelConstGainStatus       OBJECT-TYPE
			   SYNTAX       		DisplayString (SIZE (0..80))
			   ACCESS           	read-only
			   STATUS           	optional
			   DESCRIPTION
			   "The value of this object provides the label of the
			    Constant Gain Status parameter."
            ::= { gx2OA100BDStatusEntry 47}

      oa100bdvalueConstGainStatus         OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (0-Ok, 1-Undetermined
			    2-Warning, 3-Minor, 4-Major, 5-Critical)."
            ::= { gx2OA100BDStatusEntry 48}

      oa100bdstateflagConstGainStatus     OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
            ::= { gx2OA100BDStatusEntry 49}

-- // New Parameter - Hardware Error status
      oa100bdlabelHardwareErrorStatus       OBJECT-TYPE
            SYNTAX            DisplayString (SIZE (0..80))
            ACCESS            read-only
            STATUS            optional
            DESCRIPTION
            "The value of this object provides the label of the
             Hardware Error Status parameter."
            ::= { gx2OA100BDStatusEntry 50}

      oa100bdvalueHardwareErrorStatus         OBJECT-TYPE
            SYNTAX            INTEGER
                           {
                           ok(1),
                           undetermined(2),
                           warning(3),
                           minor(4),
                           major(5),
                           critical(6)
                           }
            ACCESS            read-only
            STATUS            mandatory
            DESCRIPTION
            "The value of this object provides the current state of
             the parameter (0-Ok, 1-Undetermined
             2-Warning, 3-Minor, 4-Major, 5-Critical)."
            ::= { gx2OA100BDStatusEntry 51}

      oa100bdstateflagHardwareErrorStatus     OBJECT-TYPE
            SYNTAX            INTEGER
                        {
                        hidden(1),
                        read-only(2),
                        updateable(3)
                        }
            ACCESS            read-only
            STATUS            mandatory
            DESCRIPTION
            "The value of this object provides the state
             of the the parameter. (0-Hidden 1-Read-Only, 2-Updateable)."
            ::= { gx2OA100BDStatusEntry 52}

-- // New Parameter - Standby status
      oa100bdlabelStandbyStatus       OBJECT-TYPE
			   SYNTAX       		DisplayString (SIZE (0..80))
			   ACCESS           	read-only
			   STATUS           	optional
			   DESCRIPTION
			   "The value of this object provides the label of the
			    Standby Status parameter."
            ::= { gx2OA100BDStatusEntry 53}

      oa100bdvalueStandbyStatus        OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (0-Ok, 1-Undetermined
			    2-Warning, 3-Minor, 4-Major, 5-Critical)."
            ::= { gx2OA100BDStatusEntry 54}

      oa100bdstateflagStandbyStatus       OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
            ::= { gx2OA100BDStatusEntry 55}

-- // Section: Factory Data parameter detail

      gx2OA100BDFactoryTableIndex              OBJECT-TYPE
			   SYNTAX           INTEGER (1..4294967295)
			   ACCESS           read-only
			   STATUS           mandatory
			   DESCRIPTION
			   "The value of this object identifies the network
			    element. This index is equal to the
			    hfcCommonTableIndex for the same element."
            ::= { gx2OA100BDFactoryEntry 1}

-- // New Parameter - boot control byte
      oa100bdbootControlByte           OBJECT-TYPE
			   SYNTAX       		INTEGER
			   ACCESS           	read-only
			   STATUS           	mandatory
			   DESCRIPTION
			   "The value of this object indicates which bank the firmware
             is currently being boot from.

             Boot Control Byte bit definition as follows :
             bit 0 : boot bit (0=boot from bank 0, 1=boot from bank 1)
             bit 1 : bank 0 status (0=bank is blank/bad, 1=bank is OK)
             bit 2 : bank 1 status (0=bank is blank/bad, 1=bank is OK)
             bits 3-7 : not used"
            ::= { gx2OA100BDFactoryEntry 2}

-- // New Parameter - boot status byte
      oa100bdbootStatusByte            OBJECT-TYPE
			   SYNTAX       		INTEGER
			   ACCESS           	read-only
			   STATUS           	mandatory
			   DESCRIPTION
            "This object indicates the status of the last boot

            Boot Status Byte bit definitions as follows:
            bit 0 : bank 0 status (0=bank is OK or not used, 1=bank failed boot)
            bit 1 : bank 1 status (0=bank is OK or not used, 1=bank failed boot)
            bit 2 : active bank (0=bank 0 active, 1=bank 1 active)
            bits 3-7: not used"
            ::= { gx2OA100BDFactoryEntry 3}

-- // New Parameter - bank 0 CRC
      oa100bdbank0CRC               OBJECT-TYPE
			   SYNTAX       		INTEGER
			   ACCESS           	read-only
			   STATUS           	mandatory
			   DESCRIPTION
            "This object provides the CRC code of bank 0.
            The value is best displayed in Hex format"
            ::= { gx2OA100BDFactoryEntry 4}

-- // New Parameter - bank 1 CRC
      oa100bdbank1CRC               OBJECT-TYPE
			   SYNTAX       		INTEGER
			   ACCESS           	read-only
			   STATUS           	mandatory
			   DESCRIPTION
            "This object provides the CRC code of bank 1.
            The value is best displayed in Hex format"
            ::= { gx2OA100BDFactoryEntry 5}

-- // New Parameter - programmed EEPROM byte
      oa100bdprgEEPROMByte                OBJECT-TYPE
			   SYNTAX       		INTEGER
			   ACCESS           	read-only
			   STATUS           	mandatory
			   DESCRIPTION
            "This object indicates if the EEPROM has been programmed

            programmed EEPROM byte definitions as follows:
            0xBB = EEPROM is programmed
            0xDB = EEPROM is being restored to factory defaults
            0xFF = EEPROM is blank
            any other values are assumed to be blank EEPROM"
            ::= { gx2OA100BDFactoryEntry 6}

-- // New Parameter - factory CRC
      oa100bdfactoryCRC                OBJECT-TYPE
			   SYNTAX       		INTEGER
			   ACCESS           	read-only
			   STATUS           	mandatory
			   DESCRIPTION
            "This object provides the CRC code for the Factory data.
            The value is best displayed in Hex format"
            ::= { gx2OA100BDFactoryEntry 7}

-- // New Parameter - calculate CRC command
      oa100bdcalculateCRC              OBJECT-TYPE
			   SYNTAX       		INTEGER
					    		{
                                          factory(1),
							calibration(2),
							alarmdata(3)
					    		}
			   ACCESS           	read-only
            STATUS            obsolete
			   DESCRIPTION
            "This object indicates which of the Emnums will have the CRC calculated.

            Calculate CRC command defintions as follows :
            0x00 : recalculate factory data CRC
            0x01 : recalcualte calibration table CRC
            0x02 : recalculate alarm data CRC
            other values not defined"
            ::= { gx2OA100BDFactoryEntry 8}

-- // New Parameter - hour meter
      oa100bdhourMeter              OBJECT-TYPE
			   SYNTAX       		INTEGER
			   ACCESS           	read-only
			   STATUS           	mandatory
			   DESCRIPTION
			   "This object provides the hour meter reading of the module."
            ::= { gx2OA100BDFactoryEntry 9}

-- // New Parameter - flash program counter A
      oa100bdflashPrgCntA              OBJECT-TYPE
			   SYNTAX       		INTEGER
			   ACCESS           	read-only
			   STATUS           	mandatory
			   DESCRIPTION
			   "This object provides the number of times the flash has been
                      programmed on side A."
            ::= { gx2OA100BDFactoryEntry 10}

-- // New Parameter - flash program counter B
      oa100bdflashPrgCntB              OBJECT-TYPE
			   SYNTAX       		INTEGER
			   ACCESS           	read-only
			   STATUS           	mandatory
			   DESCRIPTION
			   "This object provides the number of times the flash has been
                      programmed on side B."
            ::= { gx2OA100BDFactoryEntry 11}

-- // New Parameter - Firmware Rev Bank 0
      oa100bdfwRev0                    OBJECT-TYPE
			   SYNTAX       		DisplayString (SIZE (0..80))
			   ACCESS           	read-only
			   STATUS           	mandatory
			   DESCRIPTION
            "This object provides the Revision of the firmware stores in bank 0.
            This value should be displayed as two ascii characters."
            ::= { gx2OA100BDFactoryEntry 12}

-- // New Parameter - Firmware Rev Bank 1
      oa100bdfwRev1                    OBJECT-TYPE
			   SYNTAX       		DisplayString (SIZE (0..80))
			   ACCESS           	read-only
			   STATUS           	mandatory
			   DESCRIPTION
            "This object provides the Revision of the firmware stores in bank 1.
            This value should be displayed as two ascii characters."
            ::= { gx2OA100BDFactoryEntry 13}


-- // Section: Factory Data parameter detail
-- ****************  Hold Time Parameters *************************************
	    Gx2OA100BDHoldTimeEntry    ::= SEQUENCE
	    {
		gx2OA100BDHoldTimeTableIndex        INTEGER,
		gx2OA100BDHoldTimeSpecIndex         INTEGER,
		gx2OA100BDHoldTimeData              INTEGER
		}


	gx2OA100BDHoldTimeTableIndex              OBJECT-TYPE
		   	   SYNTAX           INTEGER (1..4294967295)
			   ACCESS           read-only
			   STATUS           mandatory
			   DESCRIPTION
			   "The value of this object is the index of the data object."
			   ::= { gx2OA100BDHoldTimeEntry 1}

	gx2OA100BDHoldTimeSpecIndex              OBJECT-TYPE
       		           SYNTAX           INTEGER (1..4294967295)
			   ACCESS           read-only
			   STATUS           mandatory
			   DESCRIPTION
			   "The value of this object identifies the index of the alarm object to be modified."
			   ::= { gx2OA100BDHoldTimeEntry 2}

	gx2OA100BDHoldTimeData          	OBJECT-TYPE
		   SYNTAX       		INTEGER
			   ACCESS           	read-write
			   STATUS           	mandatory
			   DESCRIPTION
			   "The value of this object provides access to the hold timers used
			   to suppress nose on analog objects. This object is a 32 bit object.
			   Validation data is entered into bytes zero and one of the object.
			   Bytes three and four are used to entering the hold time for the
			   specified alarm object. The Hold timer data ranges from 0 to 1300 seconds.
			   The index of this object corresponds to the alarm object to be modified.
			   Alarm Hold timers correspond to the index of this object as follows:
			   Index 1 = xxx, index 2 = xxxx, Index 3 = xxxx,
			   The hold time is represented in seconds."
			   ::= { gx2OA100BDHoldTimeEntry 3}






-- // Section: Trap Definitions
-- ****************************************************************
--
-- TRAP DEFINITIONS
--
--
-- Every trap generated by an HFC agents will include first 9 identical
-- fields. If particular variable is not supported in
-- particular TRAP-TYPE then default value will be returned.
--
-- DESCRIPTION will include explanation of use of generic
-- variables (trapAdditionalInfo******.)  If no
-- DESCRIPTION is given then generic variables will contain
-- default values.
--
-- *****************************************************************
-- **************************************************************************
--                              OA100BD Module traps
-- **************************************************************************
-- // Trap 1  : integer congif change
   trapOA100BDConfigChangeInteger TRAP-TYPE
       ENTERPRISE gx2OA100BD
       VARIABLES
	       {
		trapIdentifier,
		trapNetworkElemModelNumber,
		trapNetworkElemSerialNum,
		trapPerceivedSeverity,
		trapNetworkElemOperState,
		trapNetworkElemAlarmStatus,
		trapNetworkElemAdminState,
		trapNetworkElemAvailStatus,
		trapText,
		trapChangedObjectId,
		trapChangedValueInteger,
		trapNETrapLastTrapTimeStamp
	       }
       DESCRIPTION
	"This trap is issued if configuration of a single variable
	 with integer type was changed (via ANY interface).
	 TrapChangedValueInteger variable may contain current reading
	 of that variable.
	 trapPerceivedSeverity - 'indeterminate'"
  ::= 1

-- // Trap 2  : string config change
   trapOA100BDConfigChangeDisplayString TRAP-TYPE
       ENTERPRISE gx2OA100BD
       VARIABLES
	       {
		trapIdentifier,
		trapNetworkElemModelNumber,
		trapNetworkElemSerialNum,
		trapPerceivedSeverity,
		trapNetworkElemOperState,
		trapNetworkElemAlarmStatus,
		trapNetworkElemAdminState,
		trapNetworkElemAvailStatus,
		trapText,
		trapChangedObjectId,
		trapChangedValueDisplayString,
		trapNETrapLastTrapTimeStamp
	       }
       DESCRIPTION
	"This trap is issued if configuration of a single variable
	 with DispalayString type was changed (via ANY interface).
	 TrapChangedValueDisplayString variable may contain current reading
	 of that variable.
	 trapPerceivedSeverity - 'indeterminate'"
  ::= 2

-- // Trap 3  : Module temperature alarm
  trapOA100BDModuleTemperatureAlarm TRAP-TYPE
   ENTERPRISE gx2OA100BD
	VARIABLES
		{
		 trapIdentifier,
		 trapNetworkElemModelNumber,
		 trapNetworkElemSerialNum,
		 trapPerceivedSeverity,
		 trapNetworkElemOperState,
		 trapNetworkElemAlarmStatus,
		 trapNetworkElemAdminState,
		 trapNetworkElemAvailStatus,
		 trapText,
		 trapChangedObjectId,
		 trapChangedValueInteger,
		 trapNETrapLastTrapTimeStamp
		}
	DESCRIPTION
   "This trap is issued when the OA100B Module's Temperature goes out of range."
  ::= 3

-- // Trap 4  : optical input power alarm
  trapOA100BDOpticalInPowerAlarm TRAP-TYPE
   ENTERPRISE gx2OA100BD
	VARIABLES
		{
		 trapIdentifier,
		 trapNetworkElemModelNumber,
		 trapNetworkElemSerialNum,
		 trapPerceivedSeverity,
		 trapNetworkElemOperState,
		 trapNetworkElemAlarmStatus,
		 trapNetworkElemAdminState,
		 trapNetworkElemAvailStatus,
		 trapText,
		 trapChangedObjectId,
		 trapChangedValueInteger,
		 trapNETrapLastTrapTimeStamp
		}
	DESCRIPTION
	"This trap is issued when the input Optical Input Power parameter
	 goes out of range."
  ::= 4

-- // Trap 5  : optical output power alarm
  trapOA100BDOpticalOutPowerAlarm TRAP-TYPE
   ENTERPRISE gx2OA100BD
	VARIABLES
		{
		 trapIdentifier,
		 trapNetworkElemModelNumber,
		 trapNetworkElemSerialNum,
		 trapPerceivedSeverity,
		 trapNetworkElemOperState,
		 trapNetworkElemAlarmStatus,
		 trapNetworkElemAdminState,
		 trapNetworkElemAvailStatus,
		 trapText,
		 trapChangedObjectId,
		 trapChangedValueInteger,
		 trapNETrapLastTrapTimeStamp
		}
	DESCRIPTION
	"This trap is issued when the input Optical Output Power parameter
	 goes out of range."
  ::= 5

-- // Trap 6  : Main TEC temperature alarm
  trapOA100BDMainTECTemperatureAlarm TRAP-TYPE
   ENTERPRISE gx2OA100BD
	VARIABLES
		{
		 trapIdentifier,
		 trapNetworkElemModelNumber,
		 trapNetworkElemSerialNum,
		 trapPerceivedSeverity,
		 trapNetworkElemOperState,
		 trapNetworkElemAlarmStatus,
		 trapNetworkElemAdminState,
		 trapNetworkElemAvailStatus,
		 trapText,
		 trapChangedObjectId,
		 trapChangedValueInteger,
		 trapNETrapLastTrapTimeStamp
		}
	DESCRIPTION
   "This trap is issued when the OA100B Main TEC Temperature goes out of range."
  ::= 6


-- // Trap 7  : Main Laser Power alarm
  trapOA100BDMainLaserPowerAlarm TRAP-TYPE
   ENTERPRISE gx2OA100BD
   VARIABLES
      {
       trapIdentifier,
       trapNetworkElemModelNumber,
       trapNetworkElemSerialNum,
       trapPerceivedSeverity,
       trapNetworkElemOperState,
       trapNetworkElemAlarmStatus,
       trapNetworkElemAdminState,
       trapNetworkElemAvailStatus,
       trapText,
       trapChangedObjectId,
       trapChangedValueInteger,
       trapNETrapLastTrapTimeStamp
      }
   DESCRIPTION
   "This trap is issued when the OA100B Main Laser Power goes out of range."
  ::= 7

-- // Trap 8  : Aux TEC temperature alarm
  trapOA100BDAuxTECTemperatureAlarm TRAP-TYPE
   ENTERPRISE gx2OA100BD
   VARIABLES
      {
       trapIdentifier,
       trapNetworkElemModelNumber,
       trapNetworkElemSerialNum,
       trapPerceivedSeverity,
       trapNetworkElemOperState,
       trapNetworkElemAlarmStatus,
       trapNetworkElemAdminState,
       trapNetworkElemAvailStatus,
       trapText,
       trapChangedObjectId,
       trapChangedValueInteger,
       trapNETrapLastTrapTimeStamp
      }
   DESCRIPTION
   "This trap is issued when the OA100B Aux TEC Temperature goes out of range."
  ::= 8

-- // Trap 9  : Aux Laser Power alarm
  trapOA100BDAuxLaserPowerAlarm TRAP-TYPE
   ENTERPRISE gx2OA100BD
	VARIABLES
		{
		 trapIdentifier,
		 trapNetworkElemModelNumber,
		 trapNetworkElemSerialNum,
		 trapPerceivedSeverity,
		 trapNetworkElemOperState,
		 trapNetworkElemAlarmStatus,
		 trapNetworkElemAdminState,
		 trapNetworkElemAvailStatus,
		 trapText,
		 trapChangedObjectId,
		 trapChangedValueInteger,
		 trapNETrapLastTrapTimeStamp
		}
	DESCRIPTION
   "This trap is issued when the OA100B Aux Laser Power goes out of range."
  ::= 9

-- // Trap 10 : Fan Current alarm
  trapOA100BDFanCurrentAlarm TRAP-TYPE
   ENTERPRISE gx2OA100BD
   VARIABLES
      {
       trapIdentifier,
       trapNetworkElemModelNumber,
       trapNetworkElemSerialNum,
       trapPerceivedSeverity,
       trapNetworkElemOperState,
       trapNetworkElemAlarmStatus,
       trapNetworkElemAdminState,
       trapNetworkElemAvailStatus,
       trapText,
       trapChangedObjectId,
       trapChangedValueInteger,
       trapNETrapLastTrapTimeStamp
      }
   DESCRIPTION
   "This trap is issued when the OA100B Module's Fan Currrent parameter
    goes out of range."
  ::= 10

-- // Trap 11 : Reset to factory default
    trapOA100BDResetFacDefault TRAP-TYPE
   ENTERPRISE gx2OA100BD
	VARIABLES
		{
		 trapIdentifier,
		 trapNetworkElemModelNumber,
		 trapNetworkElemSerialNum,
		 trapPerceivedSeverity,
		 trapNetworkElemOperState,
		 trapNetworkElemAlarmStatus,
		 trapNetworkElemAdminState,
		 trapNetworkElemAvailStatus,
		 trapText,
		 trapChangedObjectId,
		 trapChangedValueInteger,
		 trapNETrapLastTrapTimeStamp
		}
      DESCRIPTION
      "This trap is issued when the OA100B resets to factory defaults"
  ::= 11

-- // Trap 12 : Standby mode
    trapOA100BDStandbyMode TRAP-TYPE
   ENTERPRISE gx2OA100BD
	VARIABLES
		{
		 trapIdentifier,
		 trapNetworkElemModelNumber,
		 trapNetworkElemSerialNum,
		 trapPerceivedSeverity,
		 trapNetworkElemOperState,
		 trapNetworkElemAlarmStatus,
		 trapNetworkElemAdminState,
		 trapNetworkElemAvailStatus,
		 trapText,
		 trapChangedObjectId,
		 trapChangedValueInteger,
		 trapNETrapLastTrapTimeStamp
		}
      DESCRIPTION
      "This trap is issued when the OA100B is in Standby Mode."
  ::= 12

-- // Trap 13 : Optical input shutdown
    trapOA100BDOptInShutdown TRAP-TYPE
   ENTERPRISE gx2OA100BD
	VARIABLES
		{
		 trapIdentifier,
		 trapNetworkElemModelNumber,
		 trapNetworkElemSerialNum,
		 trapPerceivedSeverity,
		 trapNetworkElemOperState,
		 trapNetworkElemAlarmStatus,
		 trapNetworkElemAdminState,
		 trapNetworkElemAvailStatus,
		 trapText,
		 trapChangedObjectId,
		 trapChangedValueInteger,
		 trapNETrapLastTrapTimeStamp
		}
      DESCRIPTION
      "This trap is issued when the OA100B is in Optical Input Shutdown."
  ::= 13

-- // Trap 14 : Main TEC temperature shutdown
    trapOA100BDMainTECTempShutdown TRAP-TYPE
   ENTERPRISE gx2OA100BD
	VARIABLES
		{
		 trapIdentifier,
		 trapNetworkElemModelNumber,
		 trapNetworkElemSerialNum,
		 trapPerceivedSeverity,
		 trapNetworkElemOperState,
		 trapNetworkElemAlarmStatus,
		 trapNetworkElemAdminState,
		 trapNetworkElemAvailStatus,
		 trapText,
		 trapChangedObjectId,
		 trapChangedValueInteger,
		 trapNETrapLastTrapTimeStamp
		}
      DESCRIPTION
      "This trap is issued when the OA100B is in Main TEC Temperature Shutdown."
  ::= 14

-- // Trap 15 : Aux TEC temperature shutdown
    trapOA100BDAuxTECTempShutdown TRAP-TYPE
   ENTERPRISE gx2OA100BD
   VARIABLES
      {
       trapIdentifier,
       trapNetworkElemModelNumber,
       trapNetworkElemSerialNum,
       trapPerceivedSeverity,
       trapNetworkElemOperState,
       trapNetworkElemAlarmStatus,
       trapNetworkElemAdminState,
       trapNetworkElemAvailStatus,
       trapText,
       trapChangedObjectId,
       trapChangedValueInteger,
       trapNETrapLastTrapTimeStamp
      }
      DESCRIPTION
      "This trap is issued when the OA100B is in Aux TEC Temperature Shutdown."
  ::= 15

-- // Trap 16 : Key switch
    trapOA100BDKeySwitch TRAP-TYPE
   ENTERPRISE gx2OA100BD
	VARIABLES
		{
		 trapIdentifier,
		 trapNetworkElemModelNumber,
		 trapNetworkElemSerialNum,
		 trapPerceivedSeverity,
		 trapNetworkElemOperState,
		 trapNetworkElemAlarmStatus,
		 trapNetworkElemAdminState,
		 trapNetworkElemAvailStatus,
		 trapText,
		 trapChangedObjectId,
		 trapChangedValueInteger,
		 trapNETrapLastTrapTimeStamp
		}
      DESCRIPTION
      "This trap is issued when the Key Switch disables the OA100B."
  ::= 16

-- // Trap 17 : Power Fail
    trapOA100BDPowerFail TRAP-TYPE
   ENTERPRISE gx2OA100BD
	VARIABLES
		{
		 trapIdentifier,
		 trapNetworkElemModelNumber,
		 trapNetworkElemSerialNum,
		 trapPerceivedSeverity,
		 trapNetworkElemOperState,
		 trapNetworkElemAlarmStatus,
		 trapNetworkElemAdminState,
		 trapNetworkElemAvailStatus,
		 trapText,
		 trapChangedObjectId,
		 trapChangedValueInteger,
		 trapNETrapLastTrapTimeStamp
		}
      DESCRIPTION
      "This trap is issued when there is an OA100B Power Supply Failure."
  ::= 17

-- // Trap 18 : Main Laser Current shutdown
    trapOA100BDMainLasCurrShutdown TRAP-TYPE
   ENTERPRISE gx2OA100BD
	VARIABLES
		{
		 trapIdentifier,
		 trapNetworkElemModelNumber,
		 trapNetworkElemSerialNum,
		 trapPerceivedSeverity,
		 trapNetworkElemOperState,
		 trapNetworkElemAlarmStatus,
		 trapNetworkElemAdminState,
		 trapNetworkElemAvailStatus,
		 trapText,
		 trapChangedObjectId,
		 trapChangedValueInteger,
		 trapNETrapLastTrapTimeStamp
		}
      DESCRIPTION
      "This trap is issued when the OA100B is in Main Laser Current Shutdown."
  ::= 18

-- // Trap 19 : Aux Laser Current shutdown
    trapOA100BDAuxLasCurrShutdown TRAP-TYPE
   ENTERPRISE gx2OA100BD
   VARIABLES
      {
       trapIdentifier,
       trapNetworkElemModelNumber,
       trapNetworkElemSerialNum,
       trapPerceivedSeverity,
       trapNetworkElemOperState,
       trapNetworkElemAlarmStatus,
       trapNetworkElemAdminState,
       trapNetworkElemAvailStatus,
       trapText,
       trapChangedObjectId,
       trapChangedValueInteger,
       trapNETrapLastTrapTimeStamp
      }
      DESCRIPTION
      "This trap is issued when the OA100B is in Aux Laser Current Shutdown."
  ::= 19


-- // Trap 20 : Main Laser Power shutdown
    trapOA100BDMainLasPowerShutdown TRAP-TYPE
   ENTERPRISE gx2OA100BD
	VARIABLES
		{
		 trapIdentifier,
		 trapNetworkElemModelNumber,
		 trapNetworkElemSerialNum,
		 trapPerceivedSeverity,
		 trapNetworkElemOperState,
		 trapNetworkElemAlarmStatus,
		 trapNetworkElemAdminState,
		 trapNetworkElemAvailStatus,
		 trapText,
		 trapChangedObjectId,
		 trapChangedValueInteger,
		 trapNETrapLastTrapTimeStamp
		}
      DESCRIPTION
      "This trap is issued when the OA100B is in Main Laser Power Shutdown."
  ::= 20

-- // Trap 21 : Aux Laser Power shutdown
    trapOA100BDAuxLasPowerShutdown TRAP-TYPE
   ENTERPRISE gx2OA100BD
   VARIABLES
      {
       trapIdentifier,
       trapNetworkElemModelNumber,
       trapNetworkElemSerialNum,
       trapPerceivedSeverity,
       trapNetworkElemOperState,
       trapNetworkElemAlarmStatus,
       trapNetworkElemAdminState,
       trapNetworkElemAvailStatus,
       trapText,
       trapChangedObjectId,
       trapChangedValueInteger,
       trapNETrapLastTrapTimeStamp
      }
      DESCRIPTION
      "This trap is issued when the OA100B is in Aux Laser Power Shutdown."
  ::= 21


-- // Trap 22 : Invalid mode
    trapOA100BDInvalidMode TRAP-TYPE
   ENTERPRISE gx2OA100BD
	VARIABLES
		{
		 trapIdentifier,
		 trapNetworkElemModelNumber,
		 trapNetworkElemSerialNum,
		 trapPerceivedSeverity,
		 trapNetworkElemOperState,
		 trapNetworkElemAlarmStatus,
		 trapNetworkElemAdminState,
		 trapNetworkElemAvailStatus,
		 trapText,
		 trapChangedObjectId,
		 trapChangedValueInteger,
		 trapNETrapLastTrapTimeStamp
		}
      DESCRIPTION
      "This trap is issued when the OA100B is in an invalid mode."
  ::= 22

-- // Trap 23 : Flash alarm
  trapOA100BDFlashAlarm TRAP-TYPE
   ENTERPRISE gx2OA100BD
	VARIABLES
		{
		 trapIdentifier,
		 trapNetworkElemModelNumber,
		 trapNetworkElemSerialNum,
		 trapPerceivedSeverity,
		 trapNetworkElemOperState,
		 trapNetworkElemAlarmStatus,
		 trapNetworkElemAdminState,
		 trapNetworkElemAvailStatus,
		 trapText,
		 trapChangedObjectId,
		 trapChangedValueInteger,
		 trapNETrapLastTrapTimeStamp
		}
	DESCRIPTION
   "This trap is issued when the OA100B Module's boot or flash programming sequence has
       detected a Flash error."
  ::= 23

-- // Trap 24 : Boot 0 alarm
  trapOA100BDBoot0Alarm TRAP-TYPE
   ENTERPRISE gx2OA100BD
	VARIABLES
		{
		 trapIdentifier,
		 trapNetworkElemModelNumber,
		 trapNetworkElemSerialNum,
		 trapPerceivedSeverity,
		 trapNetworkElemOperState,
		 trapNetworkElemAlarmStatus,
		 trapNetworkElemAdminState,
		 trapNetworkElemAvailStatus,
		 trapText,
		 trapChangedObjectId,
		 trapChangedValueInteger,
		 trapNETrapLastTrapTimeStamp
		}
	DESCRIPTION
   "This trap is issued when the OA100B Module's Bank 0 Boot sequence has detected an error."
  ::= 24

-- // Trap 25 : Boot 1 alarm
  trapOA100BDBoot1Alarm TRAP-TYPE
   ENTERPRISE gx2OA100BD
	VARIABLES
		{
		 trapIdentifier,
		 trapNetworkElemModelNumber,
		 trapNetworkElemSerialNum,
		 trapPerceivedSeverity,
		 trapNetworkElemOperState,
		 trapNetworkElemAlarmStatus,
		 trapNetworkElemAdminState,
		 trapNetworkElemAvailStatus,
		 trapText,
		 trapChangedObjectId,
		 trapChangedValueInteger,
		 trapNETrapLastTrapTimeStamp
		}
	DESCRIPTION
   "This trap is issued when the OA100B Module's Bank 1 Boot sequence has detected an error."
  ::= 25

-- // Trap 26 : Alarm data CRC alarm
  trapOA100BDAlarmDataCRCAlarm TRAP-TYPE
   ENTERPRISE gx2OA100BD
	VARIABLES
		{
		 trapIdentifier,
		 trapNetworkElemModelNumber,
		 trapNetworkElemSerialNum,
		 trapPerceivedSeverity,
		 trapNetworkElemOperState,
		 trapNetworkElemAlarmStatus,
		 trapNetworkElemAdminState,
		 trapNetworkElemAvailStatus,
		 trapText,
		 trapChangedObjectId,
		 trapChangedValueInteger,
		 trapNETrapLastTrapTimeStamp
		}
      DESCRIPTION
      "This trap is issued when the OA100B Module detects an error calculating the alarm limit CRC."
  ::= 26

-- // Trap 27 : Factory Data CRC alarm
  trapOA100BDFactoryDataCRCAlarm TRAP-TYPE
   ENTERPRISE gx2OA100BD
	VARIABLES
		{
		 trapIdentifier,
		 trapNetworkElemModelNumber,
		 trapNetworkElemSerialNum,
		 trapPerceivedSeverity,
		 trapNetworkElemOperState,
		 trapNetworkElemAlarmStatus,
		 trapNetworkElemAdminState,
		 trapNetworkElemAvailStatus,
		 trapText,
		 trapChangedObjectId,
		 trapChangedValueInteger,
		 trapNETrapLastTrapTimeStamp
		}
      DESCRIPTION
      "This trap is issued when the OA100B Module detects an error calculating the Factory data CRC."
  ::= 27

-- // Trap 28 : Calibration Data CRC alarm
  trapOA100BDCalDataCRCAlarm TRAP-TYPE
   ENTERPRISE gx2OA100BD
	VARIABLES
		{
		 trapIdentifier,
		 trapNetworkElemModelNumber,
		 trapNetworkElemSerialNum,
		 trapPerceivedSeverity,
		 trapNetworkElemOperState,
		 trapNetworkElemAlarmStatus,
		 trapNetworkElemAdminState,
		 trapNetworkElemAvailStatus,
		 trapText,
		 trapChangedObjectId,
		 trapChangedValueInteger,
		 trapNETrapLastTrapTimeStamp
		}
      DESCRIPTION
      "This trap is issued when the OA100B Module detects an error calculating the Calibration data CRC."
  ::= 28

-- // Trap 29 : Calibration Floating Point Number alarm
  trapOA100BDFacCalFloatAlarm TRAP-TYPE
   ENTERPRISE gx2OA100BD
	VARIABLES
		{
		 trapIdentifier,
		 trapNetworkElemModelNumber,
		 trapNetworkElemSerialNum,
		 trapPerceivedSeverity,
		 trapNetworkElemOperState,
		 trapNetworkElemAlarmStatus,
		 trapNetworkElemAdminState,
		 trapNetworkElemAvailStatus,
		 trapText,
		 trapChangedObjectId,
		 trapChangedValueInteger,
		 trapNETrapLastTrapTimeStamp
		}
      DESCRIPTION
      "This trap is issued when the OA100B Module detects factory calibration float data alarm."
  ::= 29

-- // Trap 30 : Optical Input Threshold alarm
  trapOA100BDOptInThreshAlarm TRAP-TYPE
   ENTERPRISE gx2OA100BD
	VARIABLES
		{
		 trapIdentifier,
		 trapNetworkElemModelNumber,
		 trapNetworkElemSerialNum,
		 trapPerceivedSeverity,
		 trapNetworkElemOperState,
		 trapNetworkElemAlarmStatus,
		 trapNetworkElemAdminState,
		 trapNetworkElemAvailStatus,
		 trapText,
		 trapChangedObjectId,
		 trapChangedValueInteger,
		 trapNETrapLastTrapTimeStamp
		}
      DESCRIPTION
      "This trap is issued when the OA100B Module Optical Input drops below the user set threshold."
  ::= 30

-- // Trap 31 : Gain Error alarm
  trapOA100BDGainErrorAlarm TRAP-TYPE
   ENTERPRISE gx2OA100BD
	VARIABLES
		{
		 trapIdentifier,
		 trapNetworkElemModelNumber,
		 trapNetworkElemSerialNum,
		 trapPerceivedSeverity,
		 trapNetworkElemOperState,
		 trapNetworkElemAlarmStatus,
		 trapNetworkElemAdminState,
		 trapNetworkElemAvailStatus,
		 trapText,
		 trapChangedObjectId,
		 trapChangedValueInteger,
		 trapNETrapLastTrapTimeStamp
		}
      DESCRIPTION
      "This trap is issued when the OA100B Module can not produce the desired user set gain in Constant Gain Set Mode."
  ::= 31

-- // Trap 32 : Hardware Error alarm
  trapOA100BDHardwareErrorAlarm TRAP-TYPE
   ENTERPRISE gx2OA100BD
   VARIABLES
      {
       trapIdentifier,
       trapNetworkElemModelNumber,
       trapNetworkElemSerialNum,
       trapPerceivedSeverity,
       trapNetworkElemOperState,
       trapNetworkElemAlarmStatus,
       trapNetworkElemAdminState,
       trapNetworkElemAvailStatus,
       trapText,
       trapChangedObjectId,
       trapChangedValueInteger,
       trapNETrapLastTrapTimeStamp
      }
   DESCRIPTION
   "This trap is issued when any of the OA100BD Module's TEC,Laser, +12V, or +3.7V current parameters
    go out of range."
  ::= 32

  END
-- // Section: End of file
