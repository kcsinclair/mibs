--
-- she-tc-mib.mib
-- MIB generated by MG-SOFT Visual MIB Builder Version 6.0  Build 88
-- Wednesday, January 21, 2009 at 11:16:09
--

-- Start of ClearCase branch-information of current release:
-- she-tc-mib.mib   /main/she_main_grf/3
-- End of ClearCase branch-information.

	SHE-TC-MIB DEFINITIONS ::= BEGIN
 
		IMPORTS
			she			
				FROM AN-MIB			
			MODULE-IDENTITY			
				FROM SNMPv2-SMI			
			TEXTUAL-CONVENTION			
				FROM SNMPv2-TC;
	
	
--  1.3.6.1.4.1.231.7.1.2.2.1.7
		sheTcMib MODULE-IDENTITY 
			LAST-UPDATED "200901211100Z"		-- January 21, 2009 at 11:00 GMT
			ORGANIZATION 
				"Nokia Siemens Networks"
			CONTACT-INFO 
				"Gerd Barchmann
				COO BCS BBA RD HW1
				gerd.barchmann@nsn.com
				+493834 555654"
			DESCRIPTION 
				"Description."
			REVISION "200501101228Z"		-- January 10, 2005 at 12:28 GMT
			DESCRIPTION 
				"Change contens of SheAdminStateType to the corresponding standart values from if-Mib."
			REVISION "200608181450Z"		-- August 18, 2006 at 14:50 GMT
			DESCRIPTION 
				"Add enable type."
			REVISION "200811261024Z"		-- November 26, 2008 at 10:24 GMT
			DESCRIPTION 
				"Description of SheCardType with more details."
			REVISION "200901211114Z"		-- January 21, 2009 at 11:14 GMT
			DESCRIPTION 
				"Update cardtype list."
			::= { she 7 }

		
	
--
-- Textual conventions
--
	
		SheControlStatusType ::= TEXTUAL-CONVENTION
			STATUS current
			DESCRIPTION 
				"The control status of an control group entity."
			SYNTAX INTEGER
				{
				requestIdle(1),
				requestBusy(2),
				requestPassed(3),
				requestFailed(4)
				}

		ShePermissionType ::= TEXTUAL-CONVENTION
			STATUS current
			DESCRIPTION 
				"Used for setting the permission of NE function's."
			SYNTAX INTEGER
				{
				deny(0),
				permit(1)
				}

		SheOperStateType ::= TEXTUAL-CONVENTION
			STATUS current
			DESCRIPTION 
				"Used for showing the operstate of NE interfaces."
			SYNTAX INTEGER
				{
				enabled(1),
				disabled(2)
				}

		SheAdminStateType ::= TEXTUAL-CONVENTION
			STATUS current
			DESCRIPTION 
				"Used for setting the adminstate of NE interfaces."
			SYNTAX INTEGER
				{
				up(1),
				down(2),
				testing(3)
				}

		SheCardType ::= TEXTUAL-CONVENTION
			STATUS current
			DESCRIPTION 
				"Type for card's used for download/upload operations if supported.
				
				Central cards (support depend on NE release and used shelf):
				CXUGE:4E:E
				CXUCGE:4E:E
				CXUB1GE:4E:E
				CXUB2GE:4:E
				CXUC2GE:4:E
				CXUB3GE:4:E
				CXUB21GE:4:E
				CXUG1:2O:4E:E (>=3.7M)
				
				DSL IU card's (support depend on used NE release):
				IUSHDSL:48S:E
				IUSHDSL:48B:E
				IUADSL:48P:E
				IUADSL:72A:E
				IUADSL:72B:E
				IUADSL:72P:IFX
				IUADSL:72I:IFX
				IUADSL:72AI:WC
				IUADSL:72AJ:WC
				IUVDSL:24D:IFX
				IUVDSL:24D2:IFX
				IUADSL:72A:CG
				IUADSL:72B:CG
				IUVDSL:24P:E
				IUVDSL:48P:E
				IUVDSL:48I:E
				IUADSL:72A:CGH
				IUADSL:72B:CGH
				IUADSL:72J:CGH
				IUSHDSL:48E:E
				IUVDSL:48I2:E    (>=R2.8)
				IUVDSL:48P2:E    (>=R2.8)
				IUSHDSL:48E:ME:E (>=R3.7M)
				IUADSL:72B:M:CG  (>=R3.7M)
				IUADSL:72B:MM:CG (>=R3.7M)
				IUVDSL:48I3:M:E  (>=R3.7M)
				IUVDSL:48I3:ME:E (>=R3.7M)
				
				Subtending card (with R3.7M also used as UNI card):
				IU1GE:10O:SYN:E
				
				Other interface cards:
				IUCES:16E1:E     (>=R3.7M)
				
				VoIP-Cards (only supported if NE support VoIP at all):
				VPLU-S72-POTS:E
				IU:32I4:E
				IU:32I2:E
				VPLU:72P:E 
				VPLU:72P1:E  (>=R2.8M)
				VPLU:72P2:E  (>=R2.8M)
				
				Powermodules (support depend on NE release and used shelf):
				PM1:E
				PM2:E
				PM3:A
				PM:UPL:E
				PM:UPL:R:E
				PM:UPL:A
				PM1:R:E
				PM1:R:A
				PM:R:A
				
				Powermodules for new shelftypes 2. generation -> 2G (>= R2.8 maintenance):
				PM:UPL:2G:E
				PM:UPL:2G:A
				PM1:2G:E
				PM:R:2G:E
				PM:R:2G:A
				PM:ONU:2G:E
				
				Boards for hiX5622 R1.0: (obsolete because release was canceled)
				CXUMGE:4:E
				SBXDSL:16P:E
				SBXDSL:16:E
				
				Board for hiX5608 (MiniIPD):
				HIX5608:E"
			SYNTAX OCTET STRING (SIZE (0..20))

		SheSystemFileIndexType ::= TEXTUAL-CONVENTION
			STATUS current
			DESCRIPTION 
				"Sytem file index type."
			SYNTAX INTEGER (1..8)

		SheEnableType ::= TEXTUAL-CONVENTION
			STATUS current
			DESCRIPTION 
				"SHE enable type used for switching of various NE function's."
			SYNTAX INTEGER
				{
				disable(0),
				enable(1)
				}

	
--
-- Node definitions
--
	
	
	END

--
-- she-tc-mib.mib
--
